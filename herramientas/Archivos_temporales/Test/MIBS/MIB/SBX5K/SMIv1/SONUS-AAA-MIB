--
-- This SMIv1 module has been generated by smidump 0.2-cvs. Do not edit.
--

SONUS-AAA-MIB DEFINITIONS ::= BEGIN

IMPORTS
    OBJECT-TYPE
        FROM RFC-1212
    Counter, Gauge, IpAddress
        FROM RFC1155-SMI
    RowStatus
        FROM SNMPv2-TC
    sonusCommonSoftwarePlatformServicesMIBs
        FROM SONUS-SMI;

sonusAaaMIB OBJECT IDENTIFIER
    ::= { sonusCommonSoftwarePlatformServicesMIBs 18 }

-- sonusAaaMIB MODULE-IDENTITY
--     LAST-UPDATED    "201212310000Z"
--     ORGANIZATION    
--             "Ribbon Communications, Inc."
--     CONTACT-INFO    
--             "Customer Support        
--              Ribbon Communications, Inc. 
--              4 Technology Park Drive 
--              Westford, MA 01886      
--              USA                     
--                                      
--              Tel: 978-614-8100       
--              Fax: 978-614-8609"
--     DESCRIPTION     
--             "The MIB Module for AAA Services."
--     REVISION        "201212310000Z"
--     DESCRIPTION     
--             "Auto generated MIB."
--     ::= { sonusCommonSoftwarePlatformServicesMIBs 18 }


ConfdString ::=
    OCTET STRING

-- ConfdString ::= TEXTUAL-CONVENTION
--     DISPLAY-HINT    "1t"
--     STATUS          mandatory
--     DESCRIPTION     
--             "xs: and confd: types mapped to strings"
--     SYNTAX          OCTET STRING

InetAddressIP ::=
    OCTET STRING (SIZE(4 | 16))

-- InetAddressIP ::= TEXTUAL-CONVENTION
--     STATUS          mandatory
--     DESCRIPTION     
--             "confd:inetAddressIP"
--     SYNTAX          OCTET STRING (SIZE(4 | 16))

String ::=
    OCTET STRING

-- String ::= TEXTUAL-CONVENTION
--     DISPLAY-HINT    "1t"
--     STATUS          mandatory
--     DESCRIPTION     
--             "xs:string"
--     SYNTAX          OCTET STRING

SonusRsaKeyType ::=
    OCTET STRING (SIZE(0..10240))

-- SonusRsaKeyType ::= TEXTUAL-CONVENTION
--     DISPLAY-HINT    "1t"
--     STATUS          mandatory
--     DESCRIPTION     
--             "
--              Used to store the RSA key.
--              "
--     SYNTAX          OCTET STRING (SIZE(0..10240))

PasswordType ::=
    OCTET STRING (SIZE(0..32))

-- PasswordType ::= TEXTUAL-CONVENTION
--     DISPLAY-HINT    "1t"
--     STATUS          mandatory
--     DESCRIPTION     
--             ""
--     SYNTAX          OCTET STRING (SIZE(0..32))

sonusAAA OBJECT IDENTIFIER
    ::= { sonusAaaMIB 1 }

sonusAAAUserTable OBJECT-TYPE
    SYNTAX          SEQUENCE OF SonusAAAUserEntry
    ACCESS          not-accessible
    STATUS          obsolete
    DESCRIPTION     
            ""
    ::= { sonusAAA 1 }

sonusAAAUserEntry OBJECT-TYPE
    SYNTAX          SonusAAAUserEntry
    ACCESS          not-accessible
    STATUS          obsolete
    DESCRIPTION     
            ""
    INDEX           { sonusAAAUserName }
    ::= { sonusAAAUserTable 1 }

SonusAAAUserEntry ::=
    SEQUENCE {
        sonusAAAUserName                String,
        sonusAAAUserGroup               String,
        sonusAAAUserRowstatus           RowStatus
    }

sonusAAAUserName OBJECT-TYPE
    SYNTAX          String (SIZE(1..23))
    ACCESS          not-accessible
    STATUS          obsolete
    DESCRIPTION     
            "
             The name of the user.
             "
    ::= { sonusAAAUserEntry 1 }

sonusAAAUserGroup OBJECT-TYPE
    SYNTAX          String (SIZE(1..65535))
    ACCESS          read-write
    STATUS          obsolete
    DESCRIPTION     
            "
             The group that the user is a member of.
             "
    ::= { sonusAAAUserEntry 2 }

sonusAAAUserRowstatus OBJECT-TYPE
    SYNTAX          RowStatus
    ACCESS          read-write
    STATUS          obsolete
    DESCRIPTION     
            ""
    ::= { sonusAAAUserEntry 3 }

sonusAAAUserStatusTable OBJECT-TYPE
    SYNTAX          SEQUENCE OF SonusAAAUserStatusEntry
    ACCESS          not-accessible
    STATUS          mandatory
    DESCRIPTION     
            ""
    ::= { sonusAAA 3 }

sonusAAAUserStatusEntry OBJECT-TYPE
    SYNTAX          SonusAAAUserStatusEntry
    ACCESS          not-accessible
    STATUS          mandatory
    DESCRIPTION     
            ""
    INDEX           { sonusAAAUserStatusName }
    ::= { sonusAAAUserStatusTable 1 }

SonusAAAUserStatusEntry ::=
    SEQUENCE {
        sonusAAAUserStatusName          String,
        sonusAAAUserStatusCurrentStatus String,
        sonusAAAUserStatusUserId        INTEGER
    }

sonusAAAUserStatusName OBJECT-TYPE
    SYNTAX          String (SIZE(0..23))
    ACCESS          not-accessible
    STATUS          mandatory
    DESCRIPTION     
            "
             The name of the user.
             "
    ::= { sonusAAAUserStatusEntry 1 }

sonusAAAUserStatusCurrentStatus OBJECT-TYPE
    SYNTAX          String (SIZE(0..23))
    ACCESS          read-only
    STATUS          mandatory
    DESCRIPTION     
            "
             The current status of the user.
             "
    ::= { sonusAAAUserStatusEntry 2 }

sonusAAAUserStatusUserId OBJECT-TYPE
    SYNTAX          INTEGER
    ACCESS          read-only
    STATUS          mandatory
    DESCRIPTION     
            "
             User ID
             "
    ::= { sonusAAAUserStatusEntry 3 }

END -- end of module SONUS-AAA-MIB.
