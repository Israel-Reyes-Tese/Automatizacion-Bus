--
-- This SMIv1 module has been generated by smidump 0.2-cvs. Do not edit.
--

INTELCORPORATIONBASEBOARDMAPPERTRAP-MIB DEFINITIONS ::= BEGIN

IMPORTS
    dmiCompId, dmiEventAssociatedGroup, dmiEventDateTime, 
    dmiEventSeverity, dmiEventStateKey, dmiEventSubSystem, 
    dmiEventSystem
        FROM DMTF-DMI
    dmtfCoolingDeviceEvSub, dmtfCoolingDeviceEvSys, 
    dmtfCoolingUnitGlobalEvSub, dmtfCoolingUnitGlobalEvSys, 
    dmtfPhysicalContainerGlobalEvSub, dmtfPhysicalContainerGlobalEvSys, 
    dmtfPhysicalMemoryArrayEvSub, dmtfPhysicalMemoryArrayEvSys, 
    dmtfPowerSupplyEvSub, dmtfPowerSupplyEvSys, dmtfPowerUnitGlobalEvSub, 
    dmtfPowerUnitGlobalEvSys, dmtfProcessorEvSub, dmtfProcessorEvSys, 
    dmtfSystemSlotEvSub, dmtfSystemSlotEvSys, dmtfTemperatureProbeEvSub, 
    dmtfTemperatureProbeEvSys, dmtfVoltageProbeEvSub, 
    dmtfVoltageProbeEvSys
        FROM DMTF-SYSTEMS-TRAP
    a1005Selfid, a17PowerSupplyIndex, a19SlotIndex, a28CoolingUnitIndex, 
    a34MemoryArrayTableIndex, a54VoltageProbeIndex, 
    a55TemperatureProbeTableIndex, a64ContainerIndex, a67PowerUnitIndex, 
    a6ProcessorIndex, dmtf, dmtfStdMifs, mapperdmtfGroups
        FROM INTELCORPORATIONBASEBOARDMAPPER-MIB
    TRAP-TYPE
        FROM RFC-1215
    enterprises
        FROM RFC1155-SMI;

mapbaseMIB OBJECT IDENTIFIER
    ::= { intel 1 }

-- mapbaseMIB MODULE-IDENTITY
--     LAST-UPDATED    "190601091120Z"
--     ORGANIZATION    
--             "Intel Corporation"
--     CONTACT-INFO    
--             "Intel - Modular Telecom Server Divison
--              
--              Mailstop CBA1
--              100 Center Point Circle, Suite 210
--              Columbia, SC 29210"
--     DESCRIPTION     
--             "This MIB maps baseboard values translated from 
--              DMTF MIFs."
--     REVISION        "190601091120Z"
--     DESCRIPTION     
--             "Removed unnecessary DMIComponentIndex, DmiDisplayString, DmiOctetString, DmiCounter imports from INTELCORPORATIONBASEBOARDMAPPER-MIB. D. Berry"
--     REVISION        "190511171530Z"
--     DESCRIPTION     
--             "Added changes for SMIv2 compliance. D. Berry"
--     REVISION        "190511071200Z"
--     DESCRIPTION     
--             "Fixed identifier naming convention discrepancies. Fixed hanging
--              references -> DMTF-SYSTEMS & DMTF-DMI. D. Throckmorton"
--     REVISION        "190510101200Z"
--     DESCRIPTION     
--             "Fixed CoolingSensorsEv -> CoolingDeviceEv typo  A. Cress"
--     REVISION        "190508081200Z"
--     DESCRIPTION     
--             "Fixed compiler problem 
--              with tables having multiple objects instead 
--              of just one row.  Moved trap objects that were under tables by 
--              creating this separate mib, mapbase6t.mib.  D. Berry"
--     ::= { intel 1 }


intel OBJECT IDENTIFIER
    ::= { enterprises 343 }

products OBJECT IDENTIFIER
    ::= { intel 2 }

servermanagement OBJECT IDENTIFIER
    ::= { intel 2 10 }

dmtfGroups OBJECT IDENTIFIER
    ::= { intel 2 10 7 }

tCoolingSensors OBJECT IDENTIFIER
    ::= { dmtfStdMifs 4 3 }

tCoolingSensorsTraps OBJECT IDENTIFIER
    ::= { dmtfStdMifs 4 3 0 }

tProcessor OBJECT IDENTIFIER
    ::= { dmtfStdMifs 4 5 }

tProcessorTraps OBJECT IDENTIFIER
    ::= { dmtfStdMifs 4 5 0 }

tPowerSupply OBJECT IDENTIFIER
    ::= { dmtfStdMifs 4 16 }

tPowerSupplyTraps OBJECT IDENTIFIER
    ::= { dmtfStdMifs 4 16 0 }

tSystemSlots OBJECT IDENTIFIER
    ::= { dmtfStdMifs 4 18 }

tSystemSlotsTraps OBJECT IDENTIFIER
    ::= { dmtfStdMifs 4 18 0 }

tPhysicalMemoryArray OBJECT IDENTIFIER
    ::= { dmtfStdMifs 4 33 }

tPhysicalMemoryArrayTraps OBJECT IDENTIFIER
    ::= { dmtfStdMifs 4 33 0 }

tVoltageProbe OBJECT IDENTIFIER
    ::= { dmtfStdMifs 4 53 }

tVoltageProbeTraps OBJECT IDENTIFIER
    ::= { dmtfStdMifs 4 53 0 }

tTemperatureProbe OBJECT IDENTIFIER
    ::= { dmtfStdMifs 4 54 }

tTemperatureProbeTraps OBJECT IDENTIFIER
    ::= { dmtfStdMifs 4 54 0 }

tPhysicalContainerGlobal OBJECT IDENTIFIER
    ::= { dmtfStdMifs 4 63 }

tPhysicalContainerGlobalTableTraps OBJECT IDENTIFIER
    ::= { dmtfStdMifs 4 63 0 }

tPowerUnitGlobalTable OBJECT IDENTIFIER
    ::= { dmtfStdMifs 4 66 }

tPowerUnitGlobalTableTraps OBJECT IDENTIFIER
    ::= { dmtfStdMifs 4 66 0 }

tCoolingUnitGlobalTable OBJECT IDENTIFIER
    ::= { dmtfStdMifs 4 67 }

tCoolingUnitGlobalTableTraps OBJECT IDENTIFIER
    ::= { dmtfStdMifs 4 67 0 }

coolingSensorsCoolingDeviceFailure TRAP-TYPE
    ENTERPRISE      tSystemBios
    VARIABLES       { dmiEventDateTime, dmiCompId, dmiEventSeverity, 
                      dmiEventStateKey, dmiEventAssociatedGroup, 
                      dmtfCoolingDeviceEvSys, dmtfCoolingDeviceEvSub, 
                      a1005Selfid }
--     STATUS          mandatory
    DESCRIPTION     
            "Cooling Device Failure"
--     REFERENCE       
--             "'Intel|Cooling Sensors|002' 256"
    ::= 256

coolingSensorsCoolingDeviceOK TRAP-TYPE
    ENTERPRISE      tSystemBios
    VARIABLES       { dmiEventDateTime, dmiCompId, dmiEventSeverity, 
                      dmiEventStateKey, dmiEventAssociatedGroup, 
                      dmtfCoolingDeviceEvSys, dmtfCoolingDeviceEvSub, 
                      a1005Selfid }
--     STATUS          mandatory
    DESCRIPTION     
            "Cooling Device OK"
--     REFERENCE       
--             "'Intel|Cooling Sensors|002' 257"
    ::= 257

coolingSensorsCoolingDeviceInserted TRAP-TYPE
    ENTERPRISE      tSystemBios
    VARIABLES       { dmiEventDateTime, dmiCompId, dmiEventSeverity, 
                      dmiEventStateKey, dmiEventAssociatedGroup, 
                      dmtfCoolingDeviceEvSys, dmtfCoolingDeviceEvSub, 
                      a1005Selfid }
--     STATUS          mandatory
    DESCRIPTION     
            "Cooling Device Inserted"
--     REFERENCE       
--             "'Intel|Cooling Sensors|002' 258"
    ::= 258

coolingSensorsCoolingDeviceRemoved TRAP-TYPE
    ENTERPRISE      tSystemBios
    VARIABLES       { dmiEventDateTime, dmiCompId, dmiEventSeverity, 
                      dmiEventStateKey, dmiEventAssociatedGroup, 
                      dmtfCoolingDeviceEvSys, dmtfCoolingDeviceEvSub, 
                      a1005Selfid }
--     STATUS          mandatory
    DESCRIPTION     
            "Cooling Device Removed"
--     REFERENCE       
--             "'Intel|Cooling Sensors|002' 259"
    ::= 259

processorInternalError TRAP-TYPE
    ENTERPRISE      dmtfProcessorTable
    VARIABLES       { dmiEventDateTime, dmiCompId, dmiEventSeverity, 
                      dmiEventStateKey, dmiEventAssociatedGroup, 
                      dmtfProcessorEvSys, dmtfProcessorEvSub, 
                      a6ProcessorIndex }
--     STATUS          mandatory
    DESCRIPTION     
            "Processor Internal Error"
--     REFERENCE       
--             "'DMTF|Processor|009' 256"
    ::= 256

processorThermalTrip TRAP-TYPE
    ENTERPRISE      dmtfProcessorTable
    VARIABLES       { dmiEventDateTime, dmiCompId, dmiEventSeverity, 
                      dmiEventStateKey, dmiEventAssociatedGroup, 
                      dmtfProcessorEvSys, dmtfProcessorEvSub, 
                      a6ProcessorIndex }
--     STATUS          mandatory
    DESCRIPTION     
            "Processor Thermal Trip"
--     REFERENCE       
--             "'DMTF|Processor|009' 257"
    ::= 257

processorFRB-3Failure TRAP-TYPE
    ENTERPRISE      dmtfProcessorTable
    VARIABLES       { dmiEventDateTime, dmiCompId, dmiEventSeverity, 
                      dmiEventStateKey, dmiEventAssociatedGroup, 
                      dmtfProcessorEvSys, dmtfProcessorEvSub, 
                      a6ProcessorIndex }
--     STATUS          mandatory
    DESCRIPTION     
            "Processor FRB-3 Failure"
--     REFERENCE       
--             "'DMTF|Processor|009' 258"
    ::= 258

processorDisabled TRAP-TYPE
    ENTERPRISE      dmtfProcessorTable
    VARIABLES       { dmiEventDateTime, dmiCompId, dmiEventSeverity, 
                      dmiEventStateKey, dmiEventAssociatedGroup, 
                      dmtfProcessorEvSys, dmtfProcessorEvSub, 
                      a6ProcessorIndex }
--     STATUS          mandatory
    DESCRIPTION     
            "Processor Disabled"
--     REFERENCE       
--             "'DMTF|Processor|009' 259"
    ::= 259

powerSupplyFailed TRAP-TYPE
    ENTERPRISE      dmtfPowerSupplyTable
    VARIABLES       { dmiEventDateTime, dmiCompId, dmiEventSeverity, 
                      dmiEventStateKey, dmiEventAssociatedGroup, 
                      dmtfPowerSupplyEvSys, dmtfPowerSupplyEvSub, 
                      a17PowerSupplyIndex }
--     STATUS          mandatory
    DESCRIPTION     
            "Power Supply Failed"
--     REFERENCE       
--             "'DMTF|Power Supply|002' 256"
    ::= 256

powerSupplyOK TRAP-TYPE
    ENTERPRISE      dmtfPowerSupplyTable
    VARIABLES       { dmiEventDateTime, dmiCompId, dmiEventSeverity, 
                      dmiEventStateKey, dmiEventAssociatedGroup, 
                      dmtfPowerSupplyEvSys, dmtfPowerSupplyEvSub, 
                      a17PowerSupplyIndex }
--     STATUS          mandatory
    DESCRIPTION     
            "Power Supply OK"
--     REFERENCE       
--             "'DMTF|Power Supply|002' 257"
    ::= 257

powerSupplyLikelyToFail TRAP-TYPE
    ENTERPRISE      dmtfPowerSupplyTable
    VARIABLES       { dmiEventDateTime, dmiCompId, dmiEventSeverity, 
                      dmiEventStateKey, dmiEventAssociatedGroup, 
                      dmtfPowerSupplyEvSys, dmtfPowerSupplyEvSub, 
                      a17PowerSupplyIndex }
--     STATUS          mandatory
    DESCRIPTION     
            "Power Supply Likely To Fail"
--     REFERENCE       
--             "'DMTF|Power Supply|002' 258"
    ::= 258

powerSupplyInserted TRAP-TYPE
    ENTERPRISE      dmtfPowerSupplyTable
    VARIABLES       { dmiEventDateTime, dmiCompId, dmiEventSeverity, 
                      dmiEventStateKey, dmiEventAssociatedGroup, 
                      dmtfPowerSupplyEvSys, dmtfPowerSupplyEvSub, 
                      a17PowerSupplyIndex }
--     STATUS          mandatory
    DESCRIPTION     
            "Power Supply Inserted"
--     REFERENCE       
--             "'DMTF|Power Supply|002' 259"
    ::= 259

powerSupplyRemoved TRAP-TYPE
    ENTERPRISE      dmtfPowerSupplyTable
    VARIABLES       { dmiEventDateTime, dmiCompId, dmiEventSeverity, 
                      dmiEventStateKey, dmiEventAssociatedGroup, 
                      dmtfPowerSupplyEvSys, dmtfPowerSupplyEvSub, 
                      a17PowerSupplyIndex }
--     STATUS          mandatory
    DESCRIPTION     
            "Power Supply Removed"
--     REFERENCE       
--             "'DMTF|Power Supply|002' 260"
    ::= 260

powerSupplyACLost TRAP-TYPE
    ENTERPRISE      dmtfPowerSupplyTable
    VARIABLES       { dmiEventDateTime, dmiCompId, dmiEventSeverity, 
                      dmiEventStateKey, dmiEventAssociatedGroup, 
                      dmtfPowerSupplyEvSys, dmtfPowerSupplyEvSub, 
                      a17PowerSupplyIndex }
--     STATUS          mandatory
    DESCRIPTION     
            "Power Supply AC lost"
--     REFERENCE       
--             "'DMTF|Power Supply|002' 261"
    ::= 261

powerSupplyACLostOrOutOfRange TRAP-TYPE
    ENTERPRISE      dmtfPowerSupplyTable
    VARIABLES       { dmiEventDateTime, dmiCompId, dmiEventSeverity, 
                      dmiEventStateKey, dmiEventAssociatedGroup, 
                      dmtfPowerSupplyEvSys, dmtfPowerSupplyEvSub, 
                      a17PowerSupplyIndex }
--     STATUS          mandatory
    DESCRIPTION     
            "Power Supply AC lost or out-of-range"
--     REFERENCE       
--             "'DMTF|Power Supply|002' 262"
    ::= 262

powerSupplyOutOfRangeButPresent TRAP-TYPE
    ENTERPRISE      dmtfPowerSupplyTable
    VARIABLES       { dmiEventDateTime, dmiCompId, dmiEventSeverity, 
                      dmiEventStateKey, dmiEventAssociatedGroup, 
                      dmtfPowerSupplyEvSys, dmtfPowerSupplyEvSub, 
                      a17PowerSupplyIndex }
--     STATUS          mandatory
    DESCRIPTION     
            "Power Supply AC out-of-range, but present"
--     REFERENCE       
--             "'DMTF|Power Supply|002' 263"
    ::= 263

systemSlotsSlotStatusChangeToOK TRAP-TYPE
    ENTERPRISE      dmtfSystemSlotTable
    VARIABLES       { dmiEventDateTime, dmiCompId, dmiEventSeverity, 
                      dmiEventStateKey, dmiEventAssociatedGroup, 
                      dmtfSystemSlotEvSys, dmtfSystemSlotEvSub, 
                      a19SlotIndex }
--     STATUS          mandatory
    DESCRIPTION     
            "Slot status change to OK"
--     REFERENCE       
--             "'DMTF|System Slot|005' 1"
    ::= 1

systemSlotsSlotStatusChangeToNonCritical TRAP-TYPE
    ENTERPRISE      dmtfSystemSlotTable
    VARIABLES       { dmiEventDateTime, dmiCompId, dmiEventSeverity, 
                      dmiEventStateKey, dmiEventAssociatedGroup, 
                      dmtfSystemSlotEvSys, dmtfSystemSlotEvSub, 
                      a19SlotIndex }
--     STATUS          mandatory
    DESCRIPTION     
            "Slot status change to Non-Critical"
--     REFERENCE       
--             "'DMTF|System Slot|005' 2"
    ::= 2

systemSlotsSlotStatusChangeToCritical TRAP-TYPE
    ENTERPRISE      dmtfSystemSlotTable
    VARIABLES       { dmiEventDateTime, dmiCompId, dmiEventSeverity, 
                      dmiEventStateKey, dmiEventAssociatedGroup, 
                      dmtfSystemSlotEvSys, dmtfSystemSlotEvSub, 
                      a19SlotIndex }
--     STATUS          mandatory
    DESCRIPTION     
            "Slot status change to Critical"
--     REFERENCE       
--             "'DMTF|System Slot|005' 3"
    ::= 3

systemSlotsSlotPoweredOn TRAP-TYPE
    ENTERPRISE      dmtfSystemSlotTable
    VARIABLES       { dmiEventDateTime, dmiCompId, dmiEventSeverity, 
                      dmiEventStateKey, dmiEventAssociatedGroup, 
                      dmtfSystemSlotEvSys, dmtfSystemSlotEvSub, 
                      a19SlotIndex }
--     STATUS          mandatory
    DESCRIPTION     
            "Slot Powered On"
--     REFERENCE       
--             "'DMTF|System Slot|005' 4"
    ::= 4

systemSlotsSlotPoweredOff TRAP-TYPE
    ENTERPRISE      dmtfSystemSlotTable
    VARIABLES       { dmiEventDateTime, dmiCompId, dmiEventSeverity, 
                      dmiEventStateKey, dmiEventAssociatedGroup, 
                      dmtfSystemSlotEvSys, dmtfSystemSlotEvSub, 
                      a19SlotIndex }
--     STATUS          mandatory
    DESCRIPTION     
            "Slot Powered Off"
--     REFERENCE       
--             "'DMTF|System Slot|005' 5"
    ::= 5

systemSlotsSlotDisabled TRAP-TYPE
    ENTERPRISE      dmtfSystemSlotTable
    VARIABLES       { dmiEventDateTime, dmiCompId, dmiEventSeverity, 
                      dmiEventStateKey, dmiEventAssociatedGroup, 
                      dmtfSystemSlotEvSys, dmtfSystemSlotEvSub, 
                      a19SlotIndex }
--     STATUS          mandatory
    DESCRIPTION     
            "Slot is Disabled"
--     REFERENCE       
--             "'DMTF|System Slot|005' 6"
    ::= 6

physicalMemorySingleBitECCError TRAP-TYPE
    ENTERPRISE      dmtfPhysicalMemoryArrayTable
    VARIABLES       { dmiEventDateTime, dmiCompId, dmiEventSeverity, 
                      dmiEventStateKey, dmiEventAssociatedGroup, 
                      dmtfPhysicalMemoryArrayEvSys, 
                      dmtfPhysicalMemoryArrayEvSub, 
                      a34MemoryArrayTableIndex }
--     STATUS          mandatory
    DESCRIPTION     
            "Single BIT ECC Error"
--     REFERENCE       
--             "'DMTF|Physical Memory Array|001' 256"
    ::= 256

physicalMemoryMultiBitECCErrorFromPreviousBoot TRAP-TYPE
    ENTERPRISE      dmtfPhysicalMemoryArrayTable
    VARIABLES       { dmiEventDateTime, dmiCompId, dmiEventSeverity, 
                      dmiEventStateKey, dmiEventAssociatedGroup, 
                      dmtfPhysicalMemoryArrayEvSys, 
                      dmtfPhysicalMemoryArrayEvSub, 
                      a34MemoryArrayTableIndex }
--     STATUS          mandatory
    DESCRIPTION     
            "Multi BIT ECC Error from previous boot"
--     REFERENCE       
--             "'DMTF|Physical Memory Array|001' 257"
    ::= 257

physicalMemoryScrubFailed TRAP-TYPE
    ENTERPRISE      dmtfPhysicalMemoryArrayTable
    VARIABLES       { dmiEventDateTime, dmiCompId, dmiEventSeverity, 
                      dmiEventStateKey, dmiEventAssociatedGroup, 
                      dmtfPhysicalMemoryArrayEvSys, 
                      dmtfPhysicalMemoryArrayEvSub, 
                      a34MemoryArrayTableIndex }
--     STATUS          mandatory
    DESCRIPTION     
            "Memory Scrub Failed"
--     REFERENCE       
--             "'DMTF|Physical Memory Array|001' 258"
    ::= 258

physicalMemoryDeviceDisabled TRAP-TYPE
    ENTERPRISE      dmtfPhysicalMemoryArrayTable
    VARIABLES       { dmiEventDateTime, dmiCompId, dmiEventSeverity, 
                      dmiEventStateKey, dmiEventAssociatedGroup, 
                      dmtfPhysicalMemoryArrayEvSys, 
                      dmtfPhysicalMemoryArrayEvSub, 
                      a34MemoryArrayTableIndex }
--     STATUS          mandatory
    DESCRIPTION     
            "Memory Device Disabled"
--     REFERENCE       
--             "'DMTF|Physical Memory Array|001' 259"
    ::= 259

physicalMemoryErrorLoggingLimitReached TRAP-TYPE
    ENTERPRISE      dmtfPhysicalMemoryArrayTable
    VARIABLES       { dmiEventDateTime, dmiCompId, dmiEventSeverity, 
                      dmiEventStateKey, dmiEventAssociatedGroup, 
                      dmtfPhysicalMemoryArrayEvSys, 
                      dmtfPhysicalMemoryArrayEvSub, 
                      a34MemoryArrayTableIndex }
--     STATUS          mandatory
    DESCRIPTION     
            "Memory Error Logging Limit Reached"
--     REFERENCE       
--             "'DMTF|Physical Memory Array|001' 260"
    ::= 260

voltageProbeChangedToOK TRAP-TYPE
    ENTERPRISE      dmtfVoltageProbeTable
    VARIABLES       { dmiEventDateTime, dmiCompId, dmiEventSeverity, 
                      dmiEventStateKey, dmiEventAssociatedGroup, 
                      dmtfVoltageProbeEvSys, dmtfVoltageProbeEvSub, 
                      a54VoltageProbeIndex }
--     STATUS          mandatory
    DESCRIPTION     
            "Status Changed to OK"
--     REFERENCE       
--             "'DMTF|Voltage Probe|001' 256"
    ::= 256

voltageProbeChangedToUpperCritical TRAP-TYPE
    ENTERPRISE      dmtfVoltageProbeTable
    VARIABLES       { dmiEventDateTime, dmiCompId, dmiEventSeverity, 
                      dmiEventStateKey, dmiEventAssociatedGroup, 
                      dmtfVoltageProbeEvSys, dmtfVoltageProbeEvSub, 
                      a54VoltageProbeIndex }
--     STATUS          mandatory
    DESCRIPTION     
            "Status Changed to Upper Critical"
--     REFERENCE       
--             "'DMTF|Voltage Probe|001' 257"
    ::= 257

voltageProbeChangedToLowerCritical TRAP-TYPE
    ENTERPRISE      dmtfVoltageProbeTable
    VARIABLES       { dmiEventDateTime, dmiCompId, dmiEventSeverity, 
                      dmiEventStateKey, dmiEventAssociatedGroup, 
                      dmtfVoltageProbeEvSys, dmtfVoltageProbeEvSub, 
                      a54VoltageProbeIndex }
--     STATUS          mandatory
    DESCRIPTION     
            "Status Changed to Lower Critical"
--     REFERENCE       
--             "'DMTF|Voltage Probe|001' 258"
    ::= 258

voltageProbeChangedFromOKToUpperNonCritical TRAP-TYPE
    ENTERPRISE      dmtfVoltageProbeTable
    VARIABLES       { dmiEventDateTime, dmiCompId, dmiEventSeverity, 
                      dmiEventStateKey, dmiEventAssociatedGroup, 
                      dmtfVoltageProbeEvSys, dmtfVoltageProbeEvSub, 
                      a54VoltageProbeIndex }
--     STATUS          mandatory
    DESCRIPTION     
            "Status Changed to from OK to Upper Non Critical"
--     REFERENCE       
--             "'DMTF|Voltage Probe|001' 259"
    ::= 259

voltageProbeChangedFromOKToLowerNonCritical TRAP-TYPE
    ENTERPRISE      dmtfVoltageProbeTable
    VARIABLES       { dmiEventDateTime, dmiCompId, dmiEventSeverity, 
                      dmiEventStateKey, dmiEventAssociatedGroup, 
                      dmtfVoltageProbeEvSys, dmtfVoltageProbeEvSub, 
                      a54VoltageProbeIndex }
--     STATUS          mandatory
    DESCRIPTION     
            "Status Changed to from OK to Lower Non Critical"
--     REFERENCE       
--             "'DMTF|Voltage Probe|001' 260"
    ::= 260

voltageProbeChangedFromUpperCrtToUpperNonCrt TRAP-TYPE
    ENTERPRISE      dmtfVoltageProbeTable
    VARIABLES       { dmiEventDateTime, dmiCompId, dmiEventSeverity, 
                      dmiEventStateKey, dmiEventAssociatedGroup, 
                      dmtfVoltageProbeEvSys, dmtfVoltageProbeEvSub, 
                      a54VoltageProbeIndex }
--     STATUS          mandatory
    DESCRIPTION     
            "Status Changed to from Upper Critical to Upper Non Critical"
--     REFERENCE       
--             "'DMTF|Voltage Probe|001' 261"
    ::= 261

voltageProbeChangedFromLowerCrtToLowerNonCrt TRAP-TYPE
    ENTERPRISE      dmtfVoltageProbeTable
    VARIABLES       { dmiEventDateTime, dmiCompId, dmiEventSeverity, 
                      dmiEventStateKey, dmiEventAssociatedGroup, 
                      dmtfVoltageProbeEvSys, dmtfVoltageProbeEvSub, 
                      a54VoltageProbeIndex }
--     STATUS          mandatory
    DESCRIPTION     
            "Status Changed to from Lower Critical to Lower Non Critical"
--     REFERENCE       
--             "'DMTF|Voltage Probe|001' 262"
    ::= 262

temperatureProbeChangedToOK TRAP-TYPE
    ENTERPRISE      dmtfTemperatureProbeTable
    VARIABLES       { dmiEventDateTime, dmiCompId, dmiEventSeverity, 
                      dmiEventStateKey, dmiEventAssociatedGroup, 
                      dmtfTemperatureProbeEvSys, 
                      dmtfTemperatureProbeEvSub, 
                      a55TemperatureProbeTableIndex }
--     STATUS          mandatory
    DESCRIPTION     
            "Status Changed to OK"
--     REFERENCE       
--             "'DMTF|Temperature Probe|002' 256"
    ::= 256

temperatureProbeChangedToUpperCritical TRAP-TYPE
    ENTERPRISE      dmtfTemperatureProbeTable
    VARIABLES       { dmiEventDateTime, dmiCompId, dmiEventSeverity, 
                      dmiEventStateKey, dmiEventAssociatedGroup, 
                      dmtfTemperatureProbeEvSys, 
                      dmtfTemperatureProbeEvSub, 
                      a55TemperatureProbeTableIndex }
--     STATUS          mandatory
    DESCRIPTION     
            "Status Changed to Upper Critical"
--     REFERENCE       
--             "'DMTF|Temperature Probe|002' 257"
    ::= 257

temperatureProbeChangedToLowerCritical TRAP-TYPE
    ENTERPRISE      dmtfTemperatureProbeTable
    VARIABLES       { dmiEventDateTime, dmiCompId, dmiEventSeverity, 
                      dmiEventStateKey, dmiEventAssociatedGroup, 
                      dmtfTemperatureProbeEvSys, 
                      dmtfTemperatureProbeEvSub, 
                      a55TemperatureProbeTableIndex }
--     STATUS          mandatory
    DESCRIPTION     
            "Status Changed to Lower Critical"
--     REFERENCE       
--             "'DMTF|Temperature Probe|002' 258"
    ::= 258

temperatureProbeChangedFromOKToUpperNonCritical TRAP-TYPE
    ENTERPRISE      dmtfTemperatureProbeTable
    VARIABLES       { dmiEventDateTime, dmiCompId, dmiEventSeverity, 
                      dmiEventStateKey, dmiEventAssociatedGroup, 
                      dmtfTemperatureProbeEvSys, 
                      dmtfTemperatureProbeEvSub, 
                      a55TemperatureProbeTableIndex }
--     STATUS          mandatory
    DESCRIPTION     
            "Status Changed from OK to Upper Non Critical"
--     REFERENCE       
--             "'DMTF|Temperature Probe|002' 259"
    ::= 259

temperatureProbeChangedFromOKToLowerNonCritical TRAP-TYPE
    ENTERPRISE      dmtfTemperatureProbeTable
    VARIABLES       { dmiEventDateTime, dmiCompId, dmiEventSeverity, 
                      dmiEventStateKey, dmiEventAssociatedGroup, 
                      dmtfTemperatureProbeEvSys, 
                      dmtfTemperatureProbeEvSub, 
                      a55TemperatureProbeTableIndex }
--     STATUS          mandatory
    DESCRIPTION     
            "Status Changed from OK to Lower Non Critical"
--     REFERENCE       
--             "'DMTF|Temperature Probe|002' 260"
    ::= 260

temperatureProbeChangedFromUpperCrtToUpperNonCrt TRAP-TYPE
    ENTERPRISE      dmtfTemperatureProbeTable
    VARIABLES       { dmiEventDateTime, dmiCompId, dmiEventSeverity, 
                      dmiEventStateKey, dmiEventAssociatedGroup, 
                      dmtfTemperatureProbeEvSys, 
                      dmtfTemperatureProbeEvSub, 
                      a55TemperatureProbeTableIndex }
--     STATUS          mandatory
    DESCRIPTION     
            "Status Changed from Upper Critical to Upper Non Critical"
--     REFERENCE       
--             "'DMTF|Temperature Probe|002' 261"
    ::= 261

temperatureProbeChangedFromLowerCrtToLowerNonCrt TRAP-TYPE
    ENTERPRISE      dmtfTemperatureProbeTable
    VARIABLES       { dmiEventDateTime, dmiCompId, dmiEventSeverity, 
                      dmiEventStateKey, dmiEventAssociatedGroup, 
                      dmtfTemperatureProbeEvSys, 
                      dmtfTemperatureProbeEvSub, 
                      a55TemperatureProbeTableIndex }
--     STATUS          mandatory
    DESCRIPTION     
            "Status Changed from Lower Critical to Lower Non Critical"
--     REFERENCE       
--             "'DMTF|Temperature Probe|002' 262"
    ::= 262

physicalContainerSecurityBreached TRAP-TYPE
    ENTERPRISE      dmtfPhysicalContainerGlobalTable
    VARIABLES       { dmiEventDateTime, dmiCompId, dmiEventSeverity, 
                      dmiEventStateKey, dmiEventAssociatedGroup, 
                      dmtfPhysicalContainerGlobalEvSys, 
                      dmtfPhysicalContainerGlobalEvSub, 
                      a64ContainerIndex }
--     STATUS          mandatory
    DESCRIPTION     
            "Container Security Breached"
--     REFERENCE       
--             "'DMTF|Physical Container Global Table|001' 6"
    ::= 6

physicalContainerSecured TRAP-TYPE
    ENTERPRISE      dmtfPhysicalContainerGlobalTable
    VARIABLES       { dmiEventDateTime, dmiCompId, dmiEventSeverity, 
                      dmiEventStateKey, dmiEventAssociatedGroup, 
                      dmtfPhysicalContainerGlobalEvSys, 
                      dmtfPhysicalContainerGlobalEvSub, 
                      a64ContainerIndex }
--     STATUS          mandatory
    DESCRIPTION     
            "Container Secured"
--     REFERENCE       
--             "'DMTF|Physical Container Global Table|001' 256"
    ::= 256

powerUnitRedundancyLost TRAP-TYPE
    ENTERPRISE      dmtfPowerUnitGlobalTable
    VARIABLES       { dmiEventDateTime, dmiCompId, dmiEventSeverity, 
                      dmiEventStateKey, dmiEventAssociatedGroup, 
                      dmtfPowerUnitGlobalEvSys, dmtfPowerUnitGlobalEvSub, 
                      a67PowerUnitIndex }
--     STATUS          mandatory
    DESCRIPTION     
            "Power Unit Redundancy Lost"
--     REFERENCE       
--             "'DMTF|Power Unit Global Table|001' 1"
    ::= 1

powerUnitRedundancyRegained TRAP-TYPE
    ENTERPRISE      dmtfPowerUnitGlobalTable
    VARIABLES       { dmiEventDateTime, dmiCompId, dmiEventSeverity, 
                      dmiEventStateKey, dmiEventAssociatedGroup, 
                      dmtfPowerUnitGlobalEvSys, dmtfPowerUnitGlobalEvSub, 
                      a67PowerUnitIndex }
--     STATUS          mandatory
    DESCRIPTION     
            "Power Unit Redundancy Regained"
--     REFERENCE       
--             "'DMTF|Power Unit Global Table|001' 2"
    ::= 2

powerUnitDegraded TRAP-TYPE
    ENTERPRISE      dmtfPowerUnitGlobalTable
    VARIABLES       { dmiEventDateTime, dmiCompId, dmiEventSeverity, 
                      dmiEventStateKey, dmiEventAssociatedGroup, 
                      dmtfPowerUnitGlobalEvSys, dmtfPowerUnitGlobalEvSub, 
                      a67PowerUnitIndex }
--     STATUS          mandatory
    DESCRIPTION     
            "Power Unit Redundancy Degraded"
--     REFERENCE       
--             "'DMTF|Power Unit Global Table|001' 3"
    ::= 3

powerUnitVAShutdownConditionCleared TRAP-TYPE
    ENTERPRISE      dmtfPowerUnitGlobalTable
    VARIABLES       { dmiEventDateTime, dmiCompId, dmiEventSeverity, 
                      dmiEventStateKey, dmiEventAssociatedGroup, 
                      dmtfPowerUnitGlobalEvSys, dmtfPowerUnitGlobalEvSub, 
                      a67PowerUnitIndex }
--     STATUS          mandatory
    DESCRIPTION     
            "Power Unit VA Shutdown Condition Cleared"
--     REFERENCE       
--             "'DMTF|Power Unit Global Table|001' 4"
    ::= 4

powerUnitVAShutdownLimitExceeded TRAP-TYPE
    ENTERPRISE      dmtfPowerUnitGlobalTable
    VARIABLES       { dmiEventDateTime, dmiCompId, dmiEventSeverity, 
                      dmiEventStateKey, dmiEventAssociatedGroup, 
                      dmtfPowerUnitGlobalEvSys, dmtfPowerUnitGlobalEvSub, 
                      a67PowerUnitIndex }
--     STATUS          mandatory
    DESCRIPTION     
            "Power Unit VA Shutdown Limit Exceeded"
--     REFERENCE       
--             "'DMTF|Power Unit Global Table|001' 5"
    ::= 5

coolingUnitFanFullyRedundant TRAP-TYPE
    ENTERPRISE      dmtfCoolingUnitGlobalTable
    VARIABLES       { dmiEventDateTime, dmiCompId, dmiEventSeverity, 
                      dmiEventStateKey, dmiEventAssociatedGroup, 
                      dmtfCoolingUnitGlobalEvSys, 
                      dmtfCoolingUnitGlobalEvSub, a28CoolingUnitIndex }
--     STATUS          mandatory
    DESCRIPTION     
            "Fan Fully Redundant"
--     REFERENCE       
--             "'DMTF|Cooling Unit Global Table|001' 1"
    ::= 1

coolingUnitFanRedundancyLost TRAP-TYPE
    ENTERPRISE      dmtfCoolingUnitGlobalTable
    VARIABLES       { dmiEventDateTime, dmiCompId, dmiEventSeverity, 
                      dmiEventStateKey, dmiEventAssociatedGroup, 
                      dmtfCoolingUnitGlobalEvSys, 
                      dmtfCoolingUnitGlobalEvSub, a28CoolingUnitIndex }
--     STATUS          mandatory
    DESCRIPTION     
            "Fan Redundancy Lost"
--     REFERENCE       
--             "'DMTF|Cooling Unit Global Table|001' 2"
    ::= 2

coolingUnitFanRedundancyDegraded TRAP-TYPE
    ENTERPRISE      dmtfCoolingUnitGlobalTable
    VARIABLES       { dmiEventDateTime, dmiCompId, dmiEventSeverity, 
                      dmiEventStateKey, dmiEventAssociatedGroup, 
                      dmtfCoolingUnitGlobalEvSys, 
                      dmtfCoolingUnitGlobalEvSub, a28CoolingUnitIndex }
--     STATUS          mandatory
    DESCRIPTION     
            "Fan Redundancy Degraded"
--     REFERENCE       
--             "'DMTF|Cooling Unit Global Table|001' 3"
    ::= 3

coolingUnitFanSufficientResourcesFromRedundant TRAP-TYPE
    ENTERPRISE      dmtfCoolingUnitGlobalTable
    VARIABLES       { dmiEventDateTime, dmiCompId, dmiEventSeverity, 
                      dmiEventStateKey, dmiEventAssociatedGroup, 
                      dmtfCoolingUnitGlobalEvSys, 
                      dmtfCoolingUnitGlobalEvSub, a28CoolingUnitIndex }
--     STATUS          mandatory
    DESCRIPTION     
            "Fan Sufficient Resources From Redundant"
--     REFERENCE       
--             "'DMTF|Cooling Unit Global Table|001' 4"
    ::= 4

coolingUnitFanSufficientResourcesFromInsufficient TRAP-TYPE
    ENTERPRISE      dmtfCoolingUnitGlobalTable
    VARIABLES       { dmiEventDateTime, dmiCompId, dmiEventSeverity, 
                      dmiEventStateKey, dmiEventAssociatedGroup, 
                      dmtfCoolingUnitGlobalEvSys, 
                      dmtfCoolingUnitGlobalEvSub, a28CoolingUnitIndex }
--     STATUS          mandatory
    DESCRIPTION     
            "Fan Sufficient Resources From Insufficient"
--     REFERENCE       
--             "'DMTF|Cooling Unit Global Table|001' 5"
    ::= 5

coolingUnitFanNonRedundantInsufficientResources TRAP-TYPE
    ENTERPRISE      dmtfCoolingUnitGlobalTable
    VARIABLES       { dmiEventDateTime, dmiCompId, dmiEventSeverity, 
                      dmiEventStateKey, dmiEventAssociatedGroup, 
                      dmtfCoolingUnitGlobalEvSys, 
                      dmtfCoolingUnitGlobalEvSub, a28CoolingUnitIndex }
--     STATUS          mandatory
    DESCRIPTION     
            "Fan Non Redundant Insufficient Resources "
--     REFERENCE       
--             "'DMTF|Cooling Unit Global Table|001' 6"
    ::= 6

coolingUnitFanRedundancyDegradedFromFullyRedundant TRAP-TYPE
    ENTERPRISE      dmtfCoolingUnitGlobalTable
    VARIABLES       { dmiEventDateTime, dmiCompId, dmiEventSeverity, 
                      dmiEventStateKey, dmiEventAssociatedGroup, 
                      dmtfCoolingUnitGlobalEvSys, 
                      dmtfCoolingUnitGlobalEvSub, a28CoolingUnitIndex }
--     STATUS          mandatory
    DESCRIPTION     
            "Fan Redundancy Degraded From Fully Redundant"
--     REFERENCE       
--             "'DMTF|Cooling Unit Global Table|001' 7"
    ::= 7

coolingUnitFanRedundancyDegradedFromNonRedundant TRAP-TYPE
    ENTERPRISE      dmtfCoolingUnitGlobalTable
    VARIABLES       { dmiEventDateTime, dmiCompId, dmiEventSeverity, 
                      dmiEventStateKey, dmiEventAssociatedGroup, 
                      dmtfCoolingUnitGlobalEvSys, 
                      dmtfCoolingUnitGlobalEvSub, a28CoolingUnitIndex }
--     STATUS          mandatory
    DESCRIPTION     
            "Fan Redundancy Degraded From Non Redundant"
--     REFERENCE       
--             "'DMTF|Cooling Unit Global Table|001' 8"
    ::= 8

END -- end of module INTELCORPORATIONBASEBOARDMAPPERTRAP-MIB.
