--
-- This SMIv1 module has been generated by smidump 0.2-cvs. Do not edit.
--

NET-SNMP-MIB DEFINITIONS ::= BEGIN

IMPORTS
    enterprises
        FROM SNMPv2-SMI;

netSnmp OBJECT IDENTIFIER
    ::= { enterprises 8072 }

-- netSnmp MODULE-IDENTITY
--     LAST-UPDATED    "200201300000Z"
--     ORGANIZATION    
--             "www.net-snmp.org"
--     CONTACT-INFO    
--             "postal:   Wes Hardaker
--              P.O. Box 382
--              Davis CA  95617
--              
--              email:    net-snmp-coders@lists.sourceforge.net"
--     DESCRIPTION     
--             "Top-level infrastructure of the Net-SNMP project enterprise MIB tree"
--     REVISION        "200201300000Z"
--     DESCRIPTION     
--             "First draft"
--     ::= { enterprises 8072 }


netSnmpObjects OBJECT IDENTIFIER
    ::= { netSnmp 1 }

netSnmpEnumerations OBJECT IDENTIFIER
    ::= { netSnmp 3 }

netSnmpModuleIDs OBJECT IDENTIFIER
    ::= { netSnmpEnumerations 1 }

netSnmpAgentOIDs OBJECT IDENTIFIER
    ::= { netSnmpEnumerations 2 }

netSnmpDomains OBJECT IDENTIFIER
    ::= { netSnmpEnumerations 3 }

netSnmpNotificationPrefix OBJECT IDENTIFIER
    ::= { netSnmp 4 }

netSnmpNotifications OBJECT IDENTIFIER
    ::= { netSnmpNotificationPrefix 0 }

netSnmpNotificationObjects OBJECT IDENTIFIER
    ::= { netSnmpNotificationPrefix 1 }

netSnmpConformance OBJECT IDENTIFIER
    ::= { netSnmp 5 }

netSnmpCompliances OBJECT IDENTIFIER
    ::= { netSnmpConformance 1 }

netSnmpGroups OBJECT IDENTIFIER
    ::= { netSnmpConformance 2 }

netSnmpExperimental OBJECT IDENTIFIER
    ::= { netSnmp 9999 }

netSnmpPlaypen OBJECT IDENTIFIER
    ::= { netSnmpExperimental 9999 }

END -- end of module NET-SNMP-MIB.
