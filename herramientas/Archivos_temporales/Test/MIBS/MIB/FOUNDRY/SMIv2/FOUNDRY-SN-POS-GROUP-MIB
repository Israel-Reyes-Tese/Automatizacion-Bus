--
-- This SMIv2 module has been generated by smidump 0.2-cvs. Do not edit.
--

FOUNDRY-SN-POS-GROUP-MIB DEFINITIONS ::= BEGIN

IMPORTS
    snPOS
        FROM FOUNDRY-SN-ROOT-MIB
    Counter32, Gauge32, Integer32, OBJECT-TYPE
        FROM SNMPv2-SMI;

POSStatus ::=
    INTEGER { disabled(0), enabled(1) }

DisplayString ::=
    OCTET STRING

snPOSInfo OBJECT IDENTIFIER
    ::= { snPOS 1 }

snPOSInfoTable OBJECT-TYPE
    SYNTAX          SEQUENCE OF SnPOSInfoEntry
    MAX-ACCESS      not-accessible
    STATUS          current
    DESCRIPTION     
            "A specific snPOSInfo group consists of a number of 
             switch ports.  "
    ::= { snPOSInfo 1 }

snPOSInfoEntry OBJECT-TYPE
    SYNTAX          SnPOSInfoEntry
    MAX-ACCESS      not-accessible
    STATUS          current
    DESCRIPTION     
            "An entry in the snPOSInfo table indicates the 
             configuration on a specified port. A SNMP SET PDU 
             for a row of the snPOSInfoTable requires the entired 
             sequence of the MIB Objects in each 
             snPOSInfoEntry stored in one PDU.  Otherwise, 
             GENERR return-value will be returned."
    INDEX           { snPOSInfoPortNum }
    ::= { snPOSInfoTable 1 }

SnPOSInfoEntry ::=
    SEQUENCE {
        snPOSInfoPortNum                Integer32,
        snPOSIfIndex                    Integer32,
        snPOSDescr                      DisplayString,
        snPOSName                       DisplayString,
        snPOSInfoSpeed                  INTEGER,
        snPOSInfoAdminStatus            INTEGER,
        snPOSInfoLinkStatus             INTEGER,
        snPOSInfoClock                  INTEGER,
        snPOSInfoLoopBack               INTEGER,
        snPOSInfoScambleATM             POSStatus,
        snPOSInfoFraming                INTEGER,
        snPOSInfoCRC                    INTEGER,
        snPOSInfoKeepAlive              Integer32,
        snPOSInfoFlagC2                 Integer32,
        snPOSInfoFlagJ0                 Integer32,
        snPOSInfoFlagH1                 Integer32,
        snPOSStatsInFrames              Counter32,
        snPOSStatsOutFrames             Counter32,
        snPOSStatsAlignErrors           Counter32,
        snPOSStatsFCSErrors             Counter32,
        snPOSStatsFrameTooLongs         Counter32,
        snPOSStatsFrameTooShorts        Counter32,
        snPOSStatsInDiscard             Counter32,
        snPOSStatsOutDiscard            Counter32,
        snPOSInOctets                   OCTET STRING,
        snPOSOutOctets                  OCTET STRING,
        snPOSStatsInBitsPerSec          Gauge32,
        snPOSStatsOutBitsPerSec         Gauge32,
        snPOSStatsInPktsPerSec          Gauge32,
        snPOSStatsOutPktsPerSec         Gauge32,
        snPOSStatsInUtilization         Integer32,
        snPOSStatsOutUtilization        Integer32,
        snPOSTagType                    INTEGER
    }

snPOSInfoPortNum OBJECT-TYPE
    SYNTAX          Integer32
    MAX-ACCESS      read-only
    STATUS          current
    DESCRIPTION     
            "The port index.
             The bit 0 to bit 7: port number. 
             The bit 8 to bit 11: slot number (slot for chassis only)."
    ::= { snPOSInfoEntry 1 }

snPOSIfIndex OBJECT-TYPE
    SYNTAX          Integer32
    MAX-ACCESS      read-only
    STATUS          current
    DESCRIPTION     
            "In order to identify a particular interface, this
             object shall identify the instance of the ifIndex
             object, defined in RFC 1213 and RFC 1573."
    ::= { snPOSInfoEntry 2 }

snPOSDescr OBJECT-TYPE
    SYNTAX          DisplayString
    MAX-ACCESS      read-only
    STATUS          current
    DESCRIPTION     
            "A textual string containing the slot/port information
             about the interface."
    ::= { snPOSInfoEntry 3 }

snPOSName OBJECT-TYPE
    SYNTAX          DisplayString (SIZE(0..255))
    MAX-ACCESS      read-write
    STATUS          current
    DESCRIPTION     
            "Port Name string."
    ::= { snPOSInfoEntry 4 }

snPOSInfoSpeed OBJECT-TYPE
    SYNTAX          INTEGER { s155000(1), s622000(2), other(3) }
    MAX-ACCESS      read-write
    STATUS          current
    DESCRIPTION     
            "The speed configuration for a port. The values are:
             155000
             622000
             "
    ::= { snPOSInfoEntry 5 }

snPOSInfoAdminStatus OBJECT-TYPE
    SYNTAX          INTEGER { up(1), down(2), testing(3) }
    MAX-ACCESS      read-write
    STATUS          current
    DESCRIPTION     
            "The desired state of all ports.  The
             testing(3) state indicates that no operational
             packets can be passed. 
             (same as ifAdminStatus in MIB-II)"
    ::= { snPOSInfoEntry 6 }

snPOSInfoLinkStatus OBJECT-TYPE
    SYNTAX          INTEGER { up(1), down(2), testing(3) }
    MAX-ACCESS      read-only
    STATUS          current
    DESCRIPTION     
            "The current operational state of the interface.
             The testing(3) state indicates that no operational
             packets can be passed. 
             (same as ifOperStatus in MIB-II)"
    ::= { snPOSInfoEntry 7 }

snPOSInfoClock OBJECT-TYPE
    SYNTAX          INTEGER { internal(1), line(2) }
    MAX-ACCESS      read-write
    STATUS          current
    DESCRIPTION     
            "Clock default internal"
    ::= { snPOSInfoEntry 8 }

snPOSInfoLoopBack OBJECT-TYPE
    SYNTAX          INTEGER { line(1), internal(2), none(3) }
    MAX-ACCESS      read-write
    STATUS          current
    DESCRIPTION     
            "Loop back default none"
    ::= { snPOSInfoEntry 9 }

snPOSInfoScambleATM OBJECT-TYPE
    SYNTAX          POSStatus
    MAX-ACCESS      read-write
    STATUS          current
    DESCRIPTION     
            "ATM style scrambling default off"
    ::= { snPOSInfoEntry 10 }

snPOSInfoFraming OBJECT-TYPE
    SYNTAX          INTEGER { sonet(1), sdh(2) }
    MAX-ACCESS      read-write
    STATUS          current
    DESCRIPTION     
            "Framing default SONET"
    ::= { snPOSInfoEntry 11 }

snPOSInfoCRC OBJECT-TYPE
    SYNTAX          INTEGER { crc32bits(1), crc16bits(2) }
    MAX-ACCESS      read-write
    STATUS          current
    DESCRIPTION     
            "CRC default 32 bit"
    ::= { snPOSInfoEntry 12 }

snPOSInfoKeepAlive OBJECT-TYPE
    SYNTAX          Integer32 (0..32767)
    MAX-ACCESS      read-write
    STATUS          current
    DESCRIPTION     
            "Keep-alive default 10"
    ::= { snPOSInfoEntry 13 }

snPOSInfoFlagC2 OBJECT-TYPE
    SYNTAX          Integer32 (0..255)
    MAX-ACCESS      read-write
    STATUS          current
    DESCRIPTION     
            "C2 flag"
    ::= { snPOSInfoEntry 14 }

snPOSInfoFlagJ0 OBJECT-TYPE
    SYNTAX          Integer32 (0..255)
    MAX-ACCESS      read-write
    STATUS          current
    DESCRIPTION     
            "J0 flag"
    ::= { snPOSInfoEntry 15 }

snPOSInfoFlagH1 OBJECT-TYPE
    SYNTAX          Integer32 (0..255)
    MAX-ACCESS      read-write
    STATUS          current
    DESCRIPTION     
            "H1 flag"
    ::= { snPOSInfoEntry 16 }

snPOSStatsInFrames OBJECT-TYPE
    SYNTAX          Counter32
    MAX-ACCESS      read-only
    STATUS          current
    DESCRIPTION     
            "The total number of packets received on the interface."
    ::= { snPOSInfoEntry 17 }

snPOSStatsOutFrames OBJECT-TYPE
    SYNTAX          Counter32
    MAX-ACCESS      read-only
    STATUS          current
    DESCRIPTION     
            "The total number of packets transmitted out of the interface."
    ::= { snPOSInfoEntry 18 }

snPOSStatsAlignErrors OBJECT-TYPE
    SYNTAX          Counter32
    MAX-ACCESS      read-only
    STATUS          current
    DESCRIPTION     
            "dot3StatsAlignmentErrors : A count of frames 
             received on a particular interface that are 
             not an integral number of octets in length 
             and do not pass the FCS check.
             
             The count represented by an instance of this
             object is incremented when the alignmentError
             status is returned by the MAC service to the
             LLC (or other MAC user). Received frames for
             which multiple error conditions obtain are,
             according to the conventions of IEEE 802.3
             Layer Management, counted exclusively according
             to the error status presented to the LLC."
    ::= { snPOSInfoEntry 19 }

snPOSStatsFCSErrors OBJECT-TYPE
    SYNTAX          Counter32
    MAX-ACCESS      read-only
    STATUS          current
    DESCRIPTION     
            "dot3StatsFCSErrors : A count of frames received 
             on a particular interface that are an integral 
             number of octets in length but do not pass the 
             FCS check.
             
             The count represented by an instance of this
             object is incremented when the frameCheckError
             status is returned by the MAC service to the
             LLC (or other MAC user). Received frames for
             which multiple error conditions obtain are,
             according to the conventions of IEEE 802.3
             Layer Management, counted exclusively according
             to the error status presented to the LLC."
    ::= { snPOSInfoEntry 20 }

snPOSStatsFrameTooLongs OBJECT-TYPE
    SYNTAX          Counter32
    MAX-ACCESS      read-only
    STATUS          current
    DESCRIPTION     
            "dot3StatsFrameTooLongs : A count of frames 
             received on a particular interface that 
             exceed the maximum permitted frame size.
             
             The count represented by an instance of this
             object is incremented when the frameTooLong
             status is returned by the MAC service to the
             LLC (or other MAC user). Received frames for
             which multiple error conditions obtain are,
             according to the conventions of IEEE 802.3
             Layer Management, counted exclusively according
             to the error status presented to the LLC."
    ::= { snPOSInfoEntry 21 }

snPOSStatsFrameTooShorts OBJECT-TYPE
    SYNTAX          Counter32
    MAX-ACCESS      read-only
    STATUS          current
    DESCRIPTION     
            " A count of frames received on a particular 
             interface that below the minimum permitted 
             frame size."
    ::= { snPOSInfoEntry 22 }

snPOSStatsInDiscard OBJECT-TYPE
    SYNTAX          Counter32
    MAX-ACCESS      read-only
    STATUS          current
    DESCRIPTION     
            "The number of inbound packets which were chosen
             to be discarded even though no errors had been
             detected to prevent their being deliverable to a
             higher-layer protocol.  One possible reason for
             discarding such a packet could be to free up
             buffer space."
    ::= { snPOSInfoEntry 23 }

snPOSStatsOutDiscard OBJECT-TYPE
    SYNTAX          Counter32
    MAX-ACCESS      read-only
    STATUS          current
    DESCRIPTION     
            "The number of outbound packets which were chosen
             to be discarded even though no errors had been
             detected to prevent their being transmitted.  One
             possible reason for discarding such a packet could
             be to free up buffer space."
    ::= { snPOSInfoEntry 24 }

snPOSInOctets OBJECT-TYPE
    SYNTAX          OCTET STRING (SIZE(8))
    MAX-ACCESS      read-only
    STATUS          current
    DESCRIPTION     
            "The total number of octets received on the interface,
             including framing characters. This object is a 64-bit
             	counter of the ifInOctets object, defined in RFC 1213.
             	The octet string is in big-endian byte order."
    ::= { snPOSInfoEntry 25 }

snPOSOutOctets OBJECT-TYPE
    SYNTAX          OCTET STRING (SIZE(8))
    MAX-ACCESS      read-only
    STATUS          current
    DESCRIPTION     
            "The total number of octets transmitted out of the interface,
             including framing characters. This object is a 64-bit
             	counter of the ifOutOctets object, defined in RFC 1213.
             	The octet string is in big-endian byte order."
    ::= { snPOSInfoEntry 26 }

snPOSStatsInBitsPerSec OBJECT-TYPE
    SYNTAX          Gauge32
    MAX-ACCESS      read-only
    STATUS          current
    DESCRIPTION     
            "The number of bits per second received on the interface
             over a 5 minutes interval."
    ::= { snPOSInfoEntry 27 }

snPOSStatsOutBitsPerSec OBJECT-TYPE
    SYNTAX          Gauge32
    MAX-ACCESS      read-only
    STATUS          current
    DESCRIPTION     
            "The number of bits per second transmitted out of the interface
             over a 5 minutes interval."
    ::= { snPOSInfoEntry 28 }

snPOSStatsInPktsPerSec OBJECT-TYPE
    SYNTAX          Gauge32
    MAX-ACCESS      read-only
    STATUS          current
    DESCRIPTION     
            "The number of packets per second received on the interface
             over a 5 minutes interval."
    ::= { snPOSInfoEntry 29 }

snPOSStatsOutPktsPerSec OBJECT-TYPE
    SYNTAX          Gauge32
    MAX-ACCESS      read-only
    STATUS          current
    DESCRIPTION     
            "The number of packets per second transmitted out of the interface
             over a 5 minutes interval."
    ::= { snPOSInfoEntry 30 }

snPOSStatsInUtilization OBJECT-TYPE
    SYNTAX          Integer32 (0..10000)
    MAX-ACCESS      read-only
    STATUS          current
    DESCRIPTION     
            "The input network utilization in hundredths of a percent
             over a 5 minutes interval."
    ::= { snPOSInfoEntry 31 }

snPOSStatsOutUtilization OBJECT-TYPE
    SYNTAX          Integer32 (0..10000)
    MAX-ACCESS      read-only
    STATUS          current
    DESCRIPTION     
            "The output network utilization in hundredths of a percent
             over a 5 minutes interval."
    ::= { snPOSInfoEntry 32 }

snPOSTagType OBJECT-TYPE
    SYNTAX          INTEGER { tagged(1), untagged(2) }
    MAX-ACCESS      read-only
    STATUS          current
    DESCRIPTION     
            "For tagged port, we could have multiple VLANs 
             per port."
    ::= { snPOSInfoEntry 33 }

END -- end of module FOUNDRY-SN-POS-GROUP-MIB.
