--
-- This SMIv1 module has been generated by smidump 0.2-cvs. Do not edit.
--

RIVERSTONE-CAPACITY-MIB DEFINITIONS ::= BEGIN

IMPORTS
    OBJECT-TYPE
        FROM RFC-1212
    riverstoneMibs
        FROM RIVERSTONE-SMI-MIB;

rsCapacityMIB OBJECT IDENTIFIER
    ::= { riverstoneMibs 270 }

-- rsCapacityMIB MODULE-IDENTITY
--     LAST-UPDATED    "200304041300Z"
--     ORGANIZATION    
--             "Riverstone Networks, Inc"
--     CONTACT-INFO    
--             "Riverstone Networks, Inc
--              5200 Great America Parkway
--              Santa Clara CA USA 95054
--              PHONE:+1 408.878.6500
--              EMAIL: nms-eng@riverstonenet.com
--              WEB: http://www.riverstonenet.com"
--     DESCRIPTION     
--             "This module defines a schema to access RS system resource 
--              capacity statistics."
--     REVISION        "200304041300Z"
--     DESCRIPTION     
--             "First Version which only has objects for CPU utilization."
--     ::= { riverstoneMibs 270 }


rsCpu OBJECT IDENTIFIER
    ::= { rsCapacityMIB 5 }

rsCapCPUTable OBJECT-TYPE
    SYNTAX          SEQUENCE OF RsCapCPUEntry
    ACCESS          not-accessible
    STATUS          mandatory
    DESCRIPTION     
            "Summary of CPU statistics.  It is assumed that there is only 
             one CPU per line card."
    ::= { rsCpu 1 }

rsCapCPUEntry OBJECT-TYPE
    SYNTAX          RsCapCPUEntry
    ACCESS          not-accessible
    STATUS          mandatory
    DESCRIPTION     
            "An entry containing CPU utilization information."
    INDEX           { rsCapCPUModuleIndex }
    ::= { rsCapCPUTable 1 }

RsCapCPUEntry ::=
    SEQUENCE {
        rsCapCPUModuleIndex             Gauge,
        rsCapCPUCurrentUtilization5Sec  Gauge,
        rsCapCPUCurrentUtilization60Sec Gauge,
        rsCapCPUCurrentUtilization5Min  Gauge
    }

rsCapCPUModuleIndex OBJECT-TYPE
    SYNTAX          Gauge
    ACCESS          not-accessible
    STATUS          mandatory
    DESCRIPTION     
            "The Slot index in which the current CPU is residing."
    ::= { rsCapCPUEntry 1 }

rsCapCPUCurrentUtilization5Sec OBJECT-TYPE
    SYNTAX          Gauge (0..100)
    ACCESS          read-only
    STATUS          mandatory
    DESCRIPTION     
            "The CPU utilization expressed as an integer percentage.
             This is calculated over the last 5 seconds at a 0.1 second
             interval as a simple average."
    ::= { rsCapCPUEntry 2 }

rsCapCPUCurrentUtilization60Sec OBJECT-TYPE
    SYNTAX          Gauge (0..100)
    ACCESS          read-only
    STATUS          mandatory
    DESCRIPTION     
            "The CPU utilization expressed as an integer percentage.
             This is calculated over the last 60 seconds at a 0.1 second
             interval as a simple average."
    ::= { rsCapCPUEntry 3 }

rsCapCPUCurrentUtilization5Min OBJECT-TYPE
    SYNTAX          Gauge (0..100)
    ACCESS          read-only
    STATUS          mandatory
    DESCRIPTION     
            "The CPU utilization expressed as an integer percentage.
             This is calculated over the last  5 minutes at a 0.1 second
             interval as a simple average."
    ::= { rsCapCPUEntry 4 }

rsCapConformance OBJECT IDENTIFIER
    ::= { rsCapacityMIB 35 }

rsCapCompliances OBJECT IDENTIFIER
    ::= { rsCapConformance 1 }

rsCapGroups OBJECT IDENTIFIER
    ::= { rsCapConformance 2 }

rsCapConfGroupV1 OBJECT IDENTIFIER
    ::= { rsCapGroups 1 }

-- rsCapConfGroupV1 OBJECT-GROUP
--     OBJECTS         { rsCapCPUCurrentUtilization5Sec, 
--                       rsCapCPUCurrentUtilization60Sec, 
--                       rsCapCPUCurrentUtilization5Min }
--     STATUS          mandatory
--     DESCRIPTION     
--             "A set of managed objects that make up version 1.0 of the Riverstone Capacity mib."
--     ::= { rsCapGroups 1 }

rsCapComplianceV1 OBJECT IDENTIFIER
    ::= { rsCapCompliances 1 }

-- rsCapComplianceV1 MODULE-COMPLIANCE
--     STATUS          mandatory
--     DESCRIPTION     
--             "The compliance statement for the RIVERSTONE-CAPACITY-MIB."

--     MODULE          -- -- this module

--         MANDATORY-GROUPS    { rsCapConfGroupV1 }

--     ::= { rsCapCompliances 1 }

END -- end of module RIVERSTONE-CAPACITY-MIB.
