--
-- This SMIv1 module has been generated by smidump 0.2-cvs. Do not edit.
--

SONUS-DNS-MIB DEFINITIONS ::= BEGIN

IMPORTS
    Ipv6Address
        FROM IPV6-TC
    OBJECT-TYPE
        FROM RFC-1212
    TRAP-TYPE
        FROM RFC-1215
    Counter, IpAddress
        FROM RFC1155-SMI
    RowStatus
        FROM SNMPv2-TC
    sonusEventClass, sonusEventDescription, sonusEventLevel, 
    sonusEventTime, sonusSequenceId
        FROM SONUS-COMMON-MIB
    sonusSignallingMIBs
        FROM SONUS-SMI
    SonusAdminState, SonusBoolean, SonusName, SonusNameReference, 
    SonusServiceState
        FROM SONUS-TC;

sonusDnsMIB OBJECT IDENTIFIER
    ::= { sonusSignallingMIBs 10 }

-- sonusDnsMIB MODULE-IDENTITY
--     LAST-UPDATED    "201201240000Z"
--     ORGANIZATION    
--             "Sonus Networks, Inc."
--     CONTACT-INFO    
--             "   Customer Support    
--              Sonus Networks, Inc.
--              7 Technology Park Drive
--              Westford, MA 01886
--              USA
--              
--              Tel: 978-614-8100
--              Fax: 978-614-8609
--              E-mail: cs.snmp@sonusnet.com"
--     DESCRIPTION     
--             "The MIB Module for Local Host Name Service."
--     ::= { sonusSignallingMIBs 10 }


sonusDnsMIBObjects OBJECT IDENTIFIER
    ::= { sonusDnsMIB 1 }

sonusDnsRecordTableNextIndex OBJECT-TYPE
    SYNTAX          Gauge
    ACCESS          not-accessible
    STATUS          mandatory
    DESCRIPTION     
            "The next valid index to use when creating a new local name service record."
    ::= { sonusDnsMIBObjects 1 }

sonusDnsRecordTable OBJECT-TYPE
    SYNTAX          SEQUENCE OF SonusDnsRecordTableEntry
    ACCESS          not-accessible
    STATUS          mandatory
    DESCRIPTION     
            "This MIB table is used to create entries of local name service records.
             This is a container for linking all the record data entries."
    ::= { sonusDnsMIBObjects 2 }

sonusDnsRecordTableEntry OBJECT-TYPE
    SYNTAX          SonusDnsRecordTableEntry
    ACCESS          not-accessible
    STATUS          mandatory
    DESCRIPTION     
            "This MIB table is used to create a local name service record."
    INDEX           { sonusDnsRecordIndex }
    ::= { sonusDnsRecordTable 1 }

SonusDnsRecordTableEntry ::=
    SEQUENCE {
        sonusDnsRecordIndex             Gauge,
        sonusDnsRecordName              SonusName,
        sonusDnsRecordHostName          DisplayString,
        sonusDnsRecordMode              SonusServiceState,
        sonusDnsRecordOrder             INTEGER,
        sonusDnsRecordZoneName          SonusNameReference,
        sonusDnsRecordRowStatus         RowStatus
    }

sonusDnsRecordIndex OBJECT-TYPE
    SYNTAX          Gauge
    ACCESS          not-accessible
    STATUS          mandatory
    DESCRIPTION     
            "A unique index for this local name service record."
    ::= { sonusDnsRecordTableEntry 1 }

sonusDnsRecordName OBJECT-TYPE
    SYNTAX          SonusName
    ACCESS          read-write
    STATUS          mandatory
    DESCRIPTION     
            "The name of this local name service record."
    ::= { sonusDnsRecordTableEntry 2 }

sonusDnsRecordHostName OBJECT-TYPE
    SYNTAX          DisplayString (SIZE(0..127))
    ACCESS          read-write
    STATUS          mandatory
    DESCRIPTION     
            "The host name of this local name service record."
    ::= { sonusDnsRecordTableEntry 3 }

sonusDnsRecordMode OBJECT-TYPE
    SYNTAX          SonusServiceState
    ACCESS          read-write
    STATUS          mandatory
    DESCRIPTION     
            "The service mode of this local name service record. INSERVICE means
             that all of its record data entries will be returned on a record query.
             OUTOFSERVICE means that all of its record data entries will be skipped
             in a record query."
    DEFVAL          { inService }
    ::= { sonusDnsRecordTableEntry 4 }

sonusDnsRecordOrder OBJECT-TYPE
    SYNTAX          INTEGER { priority(1), roundrobin(2) }
    ACCESS          read-write
    STATUS          mandatory
    DESCRIPTION     
            "The lookup order of this local name service record. If set to priority (default), 
             the lookup order will be according to the record entries' priority assignment.
             If set to round robin, the lookup will be in a round robin fashion."
    DEFVAL          { priority }
    ::= { sonusDnsRecordTableEntry 5 }

sonusDnsRecordZoneName OBJECT-TYPE
    SYNTAX          SonusNameReference
    ACCESS          read-write
    STATUS          mandatory
    DESCRIPTION     
            "The DNS Zone to which this local name service record belongs to."
    DEFVAL          { "INTERNAL" }
    ::= { sonusDnsRecordTableEntry 6 }

sonusDnsRecordRowStatus OBJECT-TYPE
    SYNTAX          RowStatus
    ACCESS          read-write
    STATUS          mandatory
    DESCRIPTION     
            "This is for SNMP use."
    ::= { sonusDnsRecordTableEntry 7 }

sonusDnsRecordDataTable OBJECT-TYPE
    SYNTAX          SEQUENCE OF SonusDnsRecordDataEntry
    ACCESS          not-accessible
    STATUS          mandatory
    DESCRIPTION     
            "This MIB table is for local name service record data entries."
    ::= { sonusDnsMIBObjects 3 }

sonusDnsRecordDataEntry OBJECT-TYPE
    SYNTAX          SonusDnsRecordDataEntry
    ACCESS          not-accessible
    STATUS          mandatory
    DESCRIPTION     
            "This MIB table defines a local name service record data entry."
    INDEX           { sonusDnsRecordDataRecordIndex, 
                      sonusDnsRecordDataIndex }
    ::= { sonusDnsRecordDataTable 1 }

SonusDnsRecordDataEntry ::=
    SEQUENCE {
        sonusDnsRecordDataRecordIndex   Gauge,
        sonusDnsRecordDataIndex         Gauge,
        sonusDnsRecordDataType          INTEGER,
        sonusDnsRecordDataPriority      Gauge,
        sonusDnsRecordDataIpAddress     IpAddress,
        sonusDnsRecordDataMode          SonusServiceState,
        sonusDnsRecordDataRowStatus     RowStatus,
        sonusDnsRecordDataIpv6Address   Ipv6Address
    }

sonusDnsRecordDataRecordIndex OBJECT-TYPE
    SYNTAX          Gauge
    ACCESS          not-accessible
    STATUS          mandatory
    DESCRIPTION     
            "The local name service record index that this record data belongs to."
    ::= { sonusDnsRecordDataEntry 1 }

sonusDnsRecordDataIndex OBJECT-TYPE
    SYNTAX          Gauge
    ACCESS          read-only
    STATUS          mandatory
    DESCRIPTION     
            "The unique index of this local name service record data entry."
    ::= { sonusDnsRecordDataEntry 2 }

sonusDnsRecordDataType OBJECT-TYPE
    SYNTAX          INTEGER { a(1), aaaa(28) }
    ACCESS          read-write
    STATUS          mandatory
    DESCRIPTION     
            "Local name service record data type - mandatory parameter."
    DEFVAL          { a }
    ::= { sonusDnsRecordDataEntry 3 }

sonusDnsRecordDataPriority OBJECT-TYPE
    SYNTAX          Gauge (0..100)
    ACCESS          read-write
    STATUS          mandatory
    DESCRIPTION     
            "Local name service record data priority - mandatory parameter."
    DEFVAL          { 0 }
    ::= { sonusDnsRecordDataEntry 4 }

sonusDnsRecordDataIpAddress OBJECT-TYPE
    SYNTAX          IpAddress
    ACCESS          read-write
    STATUS          mandatory
    DESCRIPTION     
            "Local name service record data IP Address - mandatory parameter."
    ::= { sonusDnsRecordDataEntry 5 }

sonusDnsRecordDataMode OBJECT-TYPE
    SYNTAX          SonusServiceState
    ACCESS          read-write
    STATUS          mandatory
    DESCRIPTION     
            "The service mode of this local name service record data.
             INSERVICE means that this record data entry will be returned
             		 on a record query. OUTOFSERVICE means that this record data
             		 entry will be skipped in a record query."
    DEFVAL          { inService }
    ::= { sonusDnsRecordDataEntry 6 }

sonusDnsRecordDataRowStatus OBJECT-TYPE
    SYNTAX          RowStatus
    ACCESS          read-write
    STATUS          mandatory
    DESCRIPTION     
            "This is for SNMP use."
    ::= { sonusDnsRecordDataEntry 7 }

sonusDnsRecordDataIpv6Address OBJECT-TYPE
    SYNTAX          Ipv6Address
    ACCESS          read-write
    STATUS          mandatory
    DESCRIPTION     
            "Local name service record data IPv6 Address - mandatory parameter."
    ::= { sonusDnsRecordDataEntry 8 }

sonusDnsServer OBJECT IDENTIFIER
    ::= { sonusDnsMIBObjects 4 }

sonusDnsServerTableNextIndex OBJECT-TYPE
    SYNTAX          Gauge
    ACCESS          not-accessible
    STATUS          mandatory
    DESCRIPTION     
            "The next valid index to use when creating a new sonusServerTableEntry"
    ::= { sonusDnsServer 1 }

sonusDnsServerTable OBJECT-TYPE
    SYNTAX          SEQUENCE OF SonusDnsServerTableEntry
    ACCESS          not-accessible
    STATUS          mandatory
    DESCRIPTION     
            "This MIB table is used to create entries of DNS Servers."
    ::= { sonusDnsServer 2 }

sonusDnsServerTableEntry OBJECT-TYPE
    SYNTAX          SonusDnsServerTableEntry
    ACCESS          not-accessible
    STATUS          mandatory
    DESCRIPTION     
            "This MIB table object is used to create a DNS Service entry"
    INDEX           { sonusDnsServerIndex }
    ::= { sonusDnsServerTable 1 }

SonusDnsServerTableEntry ::=
    SEQUENCE {
        sonusDnsServerIndex             Gauge,
        sonusDnsServerAdminState        SonusAdminState,
        sonusDnsServerRowStatus         RowStatus,
        sonusDnsServerRecursionDesired  SonusBoolean,
        sonusDnsServerName              SonusName,
        sonusDnsServerIpAddress         IpAddress,
        sonusDnsServerPriority          Gauge,
        sonusDnsServerWeight            Gauge,
        sonusDnsServerDnsZoneName       SonusNameReference,
        sonusDnsServerIpv6Address       Ipv6Address,
        sonusDnsServerIpVersion         INTEGER,
        sonusDnsServerEdnsSupport       INTEGER
    }

sonusDnsServerIndex OBJECT-TYPE
    SYNTAX          Gauge
    ACCESS          not-accessible
    STATUS          mandatory
    DESCRIPTION     
            "The index of the DNS Server table entry."
    ::= { sonusDnsServerTableEntry 1 }

sonusDnsServerAdminState OBJECT-TYPE
    SYNTAX          SonusAdminState
    ACCESS          read-write
    STATUS          mandatory
    DESCRIPTION     
            "Admin state of DNS Server configuration."
    DEFVAL          { disabled }
    ::= { sonusDnsServerTableEntry 2 }

sonusDnsServerRowStatus OBJECT-TYPE
    SYNTAX          RowStatus
    ACCESS          read-write
    STATUS          mandatory
    DESCRIPTION     
            "This is for SNMP use."
    ::= { sonusDnsServerTableEntry 3 }

sonusDnsServerRecursionDesired OBJECT-TYPE
    SYNTAX          SonusBoolean
    ACCESS          read-write
    STATUS          mandatory
    DESCRIPTION     
            "Recursion desired flag for the  Dns Server."
    DEFVAL          { true }
    ::= { sonusDnsServerTableEntry 4 }

sonusDnsServerName OBJECT-TYPE
    SYNTAX          SonusName
    ACCESS          read-write
    STATUS          mandatory
    DESCRIPTION     
            "The name of this DNS Server Entry."
    ::= { sonusDnsServerTableEntry 5 }

sonusDnsServerIpAddress OBJECT-TYPE
    SYNTAX          IpAddress
    ACCESS          read-write
    STATUS          mandatory
    DESCRIPTION     
            "IP Addess of the DNS Server."
    ::= { sonusDnsServerTableEntry 6 }

sonusDnsServerPriority OBJECT-TYPE
    SYNTAX          Gauge (0..100)
    ACCESS          read-write
    STATUS          mandatory
    DESCRIPTION     
            "Priority of the  Dns Server."
    DEFVAL          { 0 }
    ::= { sonusDnsServerTableEntry 7 }

sonusDnsServerWeight OBJECT-TYPE
    SYNTAX          Gauge (0..100)
    ACCESS          read-write
    STATUS          mandatory
    DESCRIPTION     
            "Weight of the  Dns Server."
    DEFVAL          { 0 }
    ::= { sonusDnsServerTableEntry 8 }

sonusDnsServerDnsZoneName OBJECT-TYPE
    SYNTAX          SonusNameReference
    ACCESS          read-write
    STATUS          mandatory
    DESCRIPTION     
            "The DNS Zone to which this DNS Server Entry belongs to."
    DEFVAL          { "INTERNAL" }
    ::= { sonusDnsServerTableEntry 9 }

sonusDnsServerIpv6Address OBJECT-TYPE
    SYNTAX          Ipv6Address
    ACCESS          read-write
    STATUS          mandatory
    DESCRIPTION     
            "IPv6 Addess of the DNS Server."
    ::= { sonusDnsServerTableEntry 10 }

sonusDnsServerIpVersion OBJECT-TYPE
    SYNTAX          INTEGER { afInet(2), afInet6(24) }
    ACCESS          read-only
    STATUS          mandatory
    DESCRIPTION     
            "IP Version of the DNS Server."
    ::= { sonusDnsServerTableEntry 11 }

sonusDnsServerEdnsSupport OBJECT-TYPE
    SYNTAX          INTEGER { disabled(0), enabled(1), queryFailed(2) }
    ACCESS          read-write
    STATUS          mandatory
    DESCRIPTION     
            "E-DNS Support for the DNS Server"
    DEFVAL          { disabled }
    ::= { sonusDnsServerTableEntry 12 }

sonusDnsEntryStatusTable OBJECT-TYPE
    SYNTAX          SEQUENCE OF SonusDnsEntryStatusEntry
    ACCESS          not-accessible
    STATUS          mandatory
    DESCRIPTION     
            "This table presents the DNS entries."
    ::= { sonusDnsMIBObjects 5 }

sonusDnsEntryStatusEntry OBJECT-TYPE
    SYNTAX          SonusDnsEntryStatusEntry
    ACCESS          not-accessible
    STATUS          mandatory
    DESCRIPTION     
            "This entry presents the info on each each entry of the DNS entry."
    INDEX           { sonusDnsEntryStatusRecIndex }
    ::= { sonusDnsEntryStatusTable 1 }

SonusDnsEntryStatusEntry ::=
    SEQUENCE {
        sonusDnsEntryStatusRecIndex     Gauge,
        sonusDnsEntryStatusDomainName   DisplayString,
        sonusDnsEntryStatusType         INTEGER,
        sonusDnsEntryStatusForeignRecord SonusBoolean,
        sonusDnsEntryStatusZoneName     SonusNameReference,
        sonusDnsEntryStatusActive       SonusBoolean
    }

sonusDnsEntryStatusRecIndex OBJECT-TYPE
    SYNTAX          Gauge
    ACCESS          read-only
    STATUS          mandatory
    DESCRIPTION     
            "The record index  of the dns entry used to index records."
    ::= { sonusDnsEntryStatusEntry 1 }

sonusDnsEntryStatusDomainName OBJECT-TYPE
    SYNTAX          DisplayString (SIZE(1..120))
    ACCESS          read-only
    STATUS          mandatory
    DESCRIPTION     
            "The domain name of the dns entry record."
    ::= { sonusDnsEntryStatusEntry 2 }

sonusDnsEntryStatusType OBJECT-TYPE
    SYNTAX          INTEGER { a(1), ns(2), srv(33), aaaa(28), naptr(35) }
    ACCESS          read-only
    STATUS          mandatory
    DESCRIPTION     
            "The type  of the dns entry record."
    ::= { sonusDnsEntryStatusEntry 3 }

sonusDnsEntryStatusForeignRecord OBJECT-TYPE
    SYNTAX          SonusBoolean
    ACCESS          read-only
    STATUS          mandatory
    DESCRIPTION     
            "The flag indicating whether the record is foreign or locally created."
    ::= { sonusDnsEntryStatusEntry 4 }

sonusDnsEntryStatusZoneName OBJECT-TYPE
    SYNTAX          SonusNameReference
    ACCESS          read-only
    STATUS          mandatory
    DESCRIPTION     
            "The DNS Zone to which this DNS Server Statistics belongs to."
    ::= { sonusDnsEntryStatusEntry 5 }

sonusDnsEntryStatusActive OBJECT-TYPE
    SYNTAX          SonusBoolean
    ACCESS          read-only
    STATUS          mandatory
    DESCRIPTION     
            "The flag indicating whether the record is expired or active."
    ::= { sonusDnsEntryStatusEntry 6 }

sonusDnsServerStatisticsTable OBJECT-TYPE
    SYNTAX          SEQUENCE OF SonusDnsServerStatisticsEntry
    ACCESS          not-accessible
    STATUS          mandatory
    DESCRIPTION     
            "This table presents the statistics data of the DNS Servers in the DNCS client."
    ::= { sonusDnsMIBObjects 6 }

sonusDnsServerStatisticsEntry OBJECT-TYPE
    SYNTAX          SonusDnsServerStatisticsEntry
    ACCESS          not-accessible
    STATUS          mandatory
    DESCRIPTION     
            "This entry presents the status of the DNS entry."
    INDEX           { sonusDnsServerStatisticsIndex }
    ::= { sonusDnsServerStatisticsTable 1 }

SonusDnsServerStatisticsEntry ::=
    SEQUENCE {
        sonusDnsServerStatisticsIndex   Gauge,
        sonusDnsServerStatisticsIpAddress IpAddress,
        sonusDnsServerStatisticsNumQueries  Counter,
        sonusDnsServerStatisticsNumTimeouts   Counter,
        sonusDnsServerStatisticsNumErrors Counter,
        sonusDnsServerStatisticsNumReferrals    Counter,
        sonusDnsServerStatisticsReset   INTEGER,
        sonusDnsServerStatisticsDnsZoneName   SonusNameReference,
        sonusDnsServerStatisticsIpv6Address   Ipv6Address,
        sonusDnsServerStatisticsIpVersion INTEGER,
        sonusDnsServerStatisticsNumEdnsFailures       Counter,
        sonusDnsServerStatisticsEdnsStatus  INTEGER
    }

sonusDnsServerStatisticsIndex OBJECT-TYPE
    SYNTAX          Gauge
    ACCESS          read-only
    STATUS          mandatory
    DESCRIPTION     
            "The index  of the dns server for getting statistics data."
    ::= { sonusDnsServerStatisticsEntry 1 }

sonusDnsServerStatisticsIpAddress OBJECT-TYPE
    SYNTAX          IpAddress
    ACCESS          read-only
    STATUS          mandatory
    DESCRIPTION     
            "The ip address  of the dns server requested for the statistics data."
    ::= { sonusDnsServerStatisticsEntry 2 }

sonusDnsServerStatisticsNumQueries OBJECT-TYPE
    SYNTAX          Counter
    ACCESS          read-only
    STATUS          mandatory
    DESCRIPTION     
            "The number of queries made by the DNSC client to this dns server."
    ::= { sonusDnsServerStatisticsEntry 3 }

sonusDnsServerStatisticsNumTimeouts OBJECT-TYPE
    SYNTAX          Counter
    ACCESS          read-only
    STATUS          mandatory
    DESCRIPTION     
            "The number of timeouts resulted from queries made by the DNSC client to this dns server."
    ::= { sonusDnsServerStatisticsEntry 4 }

sonusDnsServerStatisticsNumErrors OBJECT-TYPE
    SYNTAX          Counter
    ACCESS          read-only
    STATUS          mandatory
    DESCRIPTION     
            "The number of errors resulted from queries made by the DNSC client to this dns server."
    ::= { sonusDnsServerStatisticsEntry 5 }

sonusDnsServerStatisticsNumReferrals OBJECT-TYPE
    SYNTAX          Counter
    ACCESS          read-only
    STATUS          mandatory
    DESCRIPTION     
            "The number of referrals resulted from queries made by the DNSC client to this dns server."
    ::= { sonusDnsServerStatisticsEntry 6 }

sonusDnsServerStatisticsReset OBJECT-TYPE
    SYNTAX          INTEGER { noreset(0), resetall(1) }
    ACCESS          read-write
    STATUS          mandatory
    DESCRIPTION     
            "set opertion on this object resets all the statistics counts to zero."
    ::= { sonusDnsServerStatisticsEntry 7 }

sonusDnsServerStatisticsDnsZoneName OBJECT-TYPE
    SYNTAX          SonusNameReference
    ACCESS          read-write
    STATUS          mandatory
    DESCRIPTION     
            "The DNS Zone to which this DNS Server Statistics belongs to."
    DEFVAL          { "INTERNAL" }
    ::= { sonusDnsServerStatisticsEntry 8 }

sonusDnsServerStatisticsIpv6Address OBJECT-TYPE
    SYNTAX          Ipv6Address
    ACCESS          read-only
    STATUS          mandatory
    DESCRIPTION     
            "The IPv6 address  of the dns server requested for the statistics data."
    ::= { sonusDnsServerStatisticsEntry 9 }

sonusDnsServerStatisticsIpVersion OBJECT-TYPE
    SYNTAX          INTEGER { afInet(2), afInet6(24) }
    ACCESS          read-only
    STATUS          mandatory
    DESCRIPTION     
            "The IP Version of the dns server requested for the statistics data."
    ::= { sonusDnsServerStatisticsEntry 10 }

sonusDnsServerStatisticsNumEdnsFailures OBJECT-TYPE
    SYNTAX          Counter
    ACCESS          read-only
    STATUS          mandatory
    DESCRIPTION     
            "The number of EDNS failures resulted from queries made by the DNSC client to this dns server."
    ::= { sonusDnsServerStatisticsEntry 11 }

sonusDnsServerStatisticsEdnsStatus OBJECT-TYPE
    SYNTAX          INTEGER { disabled(0), enabled(1), queryfailed(2) }
    ACCESS          read-write
    STATUS          mandatory
    DESCRIPTION     
            "Edns Query Status of the dns server"
    ::= { sonusDnsServerStatisticsEntry 12 }

sonusDnsEntryDataStatusTable OBJECT-TYPE
    SYNTAX          SEQUENCE OF SonusDnsEntryDataStatusEntry
    ACCESS          not-accessible
    STATUS          mandatory
    DESCRIPTION     
            "This table presents the status of the DNS data entries."
    ::= { sonusDnsMIBObjects 7 }

sonusDnsEntryDataStatusEntry OBJECT-TYPE
    SYNTAX          SonusDnsEntryDataStatusEntry
    ACCESS          not-accessible
    STATUS          mandatory
    DESCRIPTION     
            "This entry presents the status of the DNS entry data."
    INDEX           { sonusDnsEntryDataStatusType, 
                      sonusDnsEntryDataStatusDomainName, 
                      sonusDnsEntryDataStatusRecIndex, IMPLIED 
                      sonusDnsEntryDataStatusRecDataIndex }
    ::= { sonusDnsEntryDataStatusTable 1 }

SonusDnsEntryDataStatusEntry ::=
    SEQUENCE {
        sonusDnsEntryDataStatusDomainName DisplayString,
        sonusDnsEntryDataStatusRecIndex Gauge,
        sonusDnsEntryDataStatusType     INTEGER,
        sonusDnsEntryDataStatusRecDataIndex   Gauge,
        sonusDnsEntryDataStatusTTL      Gauge,
        sonusDnsEntryDataStatusPriority Gauge,
        sonusDnsEntryDataStatusWeight   Gauge,
        sonusDnsEntryDataStatusPortNum  Gauge,
        sonusDnsEntryDataStatusPreference Gauge,
        sonusDnsEntryDataStatusIpAddress IpAddress,
        sonusDnsEntryDataStatusService  DisplayString,
        sonusDnsEntryDataStatusHostName DisplayString,
        sonusDnsEntryDataStatusDnsZoneName  DisplayString,
        sonusDnsEntryDataStatusIpv6Address  Ipv6Address
    }

sonusDnsEntryDataStatusDomainName OBJECT-TYPE
    SYNTAX          DisplayString (SIZE(1..120))
    ACCESS          read-only
    STATUS          mandatory
    DESCRIPTION     
            "The domain name of the dns entry."
    ::= { sonusDnsEntryDataStatusEntry 1 }

sonusDnsEntryDataStatusRecIndex OBJECT-TYPE
    SYNTAX          Gauge
    ACCESS          read-only
    STATUS          mandatory
    DESCRIPTION     
            "The record index  of the dns entry used to index records."
    ::= { sonusDnsEntryDataStatusEntry 2 }

sonusDnsEntryDataStatusType OBJECT-TYPE
    SYNTAX          INTEGER { a(1), ns(2), srv(33), aaaa(28), naptr(35) }
    ACCESS          read-only
    STATUS          mandatory
    DESCRIPTION     
            "The type  of the dns entry."
    ::= { sonusDnsEntryDataStatusEntry 3 }

sonusDnsEntryDataStatusRecDataIndex OBJECT-TYPE
    SYNTAX          Gauge
    ACCESS          read-only
    STATUS          mandatory
    DESCRIPTION     
            "The record data index  of the dns entry used to index multiple record data."
    ::= { sonusDnsEntryDataStatusEntry 4 }

sonusDnsEntryDataStatusTTL OBJECT-TYPE
    SYNTAX          Gauge
    ACCESS          read-only
    STATUS          mandatory
    DESCRIPTION     
            "TTL for the entry"
    ::= { sonusDnsEntryDataStatusEntry 5 }

sonusDnsEntryDataStatusPriority OBJECT-TYPE
    SYNTAX          Gauge
    ACCESS          read-only
    STATUS          mandatory
    DESCRIPTION     
            "The priority  of the dns entry."
    ::= { sonusDnsEntryDataStatusEntry 6 }

sonusDnsEntryDataStatusWeight OBJECT-TYPE
    SYNTAX          Gauge
    ACCESS          read-only
    STATUS          mandatory
    DESCRIPTION     
            "The weight  of the dns entry."
    ::= { sonusDnsEntryDataStatusEntry 7 }

sonusDnsEntryDataStatusPortNum OBJECT-TYPE
    SYNTAX          Gauge
    ACCESS          read-only
    STATUS          mandatory
    DESCRIPTION     
            "The port number  of the dns entry."
    ::= { sonusDnsEntryDataStatusEntry 8 }

sonusDnsEntryDataStatusPreference OBJECT-TYPE
    SYNTAX          Gauge
    ACCESS          read-only
    STATUS          mandatory
    DESCRIPTION     
            "The preference  in the dns entry."
    ::= { sonusDnsEntryDataStatusEntry 9 }

sonusDnsEntryDataStatusIpAddress OBJECT-TYPE
    SYNTAX          IpAddress
    ACCESS          read-only
    STATUS          mandatory
    DESCRIPTION     
            "The IP address  of the dns entry."
    ::= { sonusDnsEntryDataStatusEntry 10 }

sonusDnsEntryDataStatusService OBJECT-TYPE
    SYNTAX          DisplayString (SIZE(0..31))
    ACCESS          read-only
    STATUS          mandatory
    DESCRIPTION     
            "The service type  of the dns entry."
    ::= { sonusDnsEntryDataStatusEntry 11 }

sonusDnsEntryDataStatusHostName OBJECT-TYPE
    SYNTAX          DisplayString (SIZE(0..127))
    ACCESS          read-only
    STATUS          mandatory
    DESCRIPTION     
            "The host name   of the dns entry."
    ::= { sonusDnsEntryDataStatusEntry 12 }

sonusDnsEntryDataStatusDnsZoneName OBJECT-TYPE
    SYNTAX          DisplayString (SIZE(0..23))
    ACCESS          read-only
    STATUS          mandatory
    DESCRIPTION     
            "The zone name of the dns entry."
    ::= { sonusDnsEntryDataStatusEntry 13 }

sonusDnsEntryDataStatusIpv6Address OBJECT-TYPE
    SYNTAX          Ipv6Address
    ACCESS          read-only
    STATUS          mandatory
    DESCRIPTION     
            "The IP address  of the dns entry."
    ::= { sonusDnsEntryDataStatusEntry 14 }

sonusDnsEntryDataDelObjects OBJECT IDENTIFIER
    ::= { sonusDnsMIBObjects 8 }

sonusDnsEntryDataDelDomainName OBJECT-TYPE
    SYNTAX          DisplayString (SIZE(1..120))
    ACCESS          read-write
    STATUS          mandatory
    DESCRIPTION     
            "The domain name of the record to be deleted."
    ::= { sonusDnsEntryDataDelObjects 1 }

sonusDnsEntryDataDelType OBJECT-TYPE
    SYNTAX          INTEGER { a(1), ns(2), srv(33), aaaa(28), naptr(35) }
    ACCESS          read-write
    STATUS          mandatory
    DESCRIPTION     
            "The domain name of the record to be deleted."
    DEFVAL          { a }
    ::= { sonusDnsEntryDataDelObjects 2 }

sonusDnsEntryDataDelZoneName OBJECT-TYPE
    SYNTAX          DisplayString (SIZE(0..23))
    ACCESS          read-write
    STATUS          mandatory
    DESCRIPTION     
            "The name  of zone for the record to be deleted."
    ::= { sonusDnsEntryDataDelObjects 3 }

sonusDnsGlobalConfigurationObjects OBJECT IDENTIFIER
    ::= { sonusDnsMIBObjects 9 }

sonusDnsGlobalIterationCount OBJECT-TYPE
    SYNTAX          Gauge (0..32)
    ACCESS          read-write
    STATUS          mandatory
    DESCRIPTION     
            "The global Iteration count limit for DNS iterations of server requests."
    DEFVAL          { 8 }
    ::= { sonusDnsGlobalConfigurationObjects 1 }

sonusDnsGlobalRetransmissionCount OBJECT-TYPE
    SYNTAX          Gauge (0..10)
    ACCESS          read-write
    STATUS          mandatory
    DESCRIPTION     
            "The global retransmission count limit for DNS iterations of server requests."
    DEFVAL          { 2 }
    ::= { sonusDnsGlobalConfigurationObjects 2 }

sonusDnsGlobalRetransmissionTimer OBJECT-TYPE
    SYNTAX          Gauge (100..10000)
    ACCESS          read-write
    STATUS          mandatory
    DESCRIPTION     
            "The global retransmission timer value for DNS iterations of server requests."
    DEFVAL          { 500 }
    ::= { sonusDnsGlobalConfigurationObjects 3 }

sonusDnsGlobalMonitoringInterval OBJECT-TYPE
    SYNTAX          Gauge (1..300)
    ACCESS          read-write
    STATUS          mandatory
    DESCRIPTION     
            "The global monitoring interval (in secs) for DNS Servers."
    DEFVAL          { 5 }
    ::= { sonusDnsGlobalConfigurationObjects 4 }

sonusDnsGlobalNumTimeouts OBJECT-TYPE
    SYNTAX          Gauge (0..32)
    ACCESS          read-write
    STATUS          mandatory
    DESCRIPTION     
            "The global number of timeouts for blacklisting a DNS Server."
    DEFVAL          { 0 }
    ::= { sonusDnsGlobalConfigurationObjects 5 }

sonusDnsGlobalProbeInterval OBJECT-TYPE
    SYNTAX          Gauge (1..300)
    ACCESS          read-write
    STATUS          mandatory
    DESCRIPTION     
            "The global probe interval (in secs) for blacklisted DNS Servers."
    DEFVAL          { 5 }
    ::= { sonusDnsGlobalConfigurationObjects 6 }

sonusDnsGlobalEdnsPayloadSize OBJECT-TYPE
    SYNTAX          Gauge (512..1600)
    ACCESS          read-write
    STATUS          mandatory
    DESCRIPTION     
            "Global Edns Payload Size."
    DEFVAL          { 1280 }
    ::= { sonusDnsGlobalConfigurationObjects 7 }

sonusDnsGlobalMaxEntriesPerRecord OBJECT-TYPE
    SYNTAX          Gauge (4..12)
    ACCESS          read-write
    STATUS          mandatory
    DESCRIPTION     
            "Global DNS Global Max Entries Per Record"
    DEFVAL          { 4 }
    ::= { sonusDnsGlobalConfigurationObjects 8 }

sonusDnsGlobalEdnsRetryAfter OBJECT-TYPE
    SYNTAX          Gauge (60..180)
    ACCESS          read-write
    STATUS          mandatory
    DESCRIPTION     
            "Global Edns Retry After"
    DEFVAL          { 180 }
    ::= { sonusDnsGlobalConfigurationObjects 9 }

sonusDnsGlobalMaxEdnsFailures OBJECT-TYPE
    SYNTAX          Gauge (1..5)
    ACCESS          read-write
    STATUS          mandatory
    DESCRIPTION     
            "Global Max Edns Failures"
    DEFVAL          { 3 }
    ::= { sonusDnsGlobalConfigurationObjects 10 }

sonusDnsGlobalEnableARecordRoundRobin OBJECT-TYPE
    SYNTAX          SonusBoolean
    ACCESS          read-write
    STATUS          mandatory
    DESCRIPTION     
            "Enable or Disable roundrobin for dynamic A records"
    DEFVAL          { false }
    ::= { sonusDnsGlobalConfigurationObjects 11 }

sonusDnsMIBNotifications OBJECT IDENTIFIER
    ::= { sonusDnsMIB 2 }

sonusDnsMIBNotificationsPrefix OBJECT IDENTIFIER
    ::= { sonusDnsMIBNotifications 0 }

sonusDnsMIBNotificationsObjects OBJECT IDENTIFIER
    ::= { sonusDnsMIBNotifications 1 }

sonusDnsEDnsQueryFailedNotification TRAP-TYPE
    ENTERPRISE      sonusDnsMIBNotifications
    VARIABLES       { sonusEventDescription, sonusEventClass, 
                      sonusEventLevel, sonusSequenceId, sonusEventTime }
--     STATUS          mandatory
    DESCRIPTION     
            "This trap indicates that a DNS server does not support eDNS query"
    ::= 1

sonusDnsServersNotRespondingNotification TRAP-TYPE
    ENTERPRISE      sonusDnsMIBNotifications
    VARIABLES       { sonusEventDescription, sonusEventClass, 
                      sonusEventLevel, sonusSequenceId, sonusEventTime }
--     STATUS          mandatory
    DESCRIPTION     
            "This trap indicates that a DNS server does not support eDNS query"
    ::= 2

sonusDnsClearServerNotRespondingNotification TRAP-TYPE
    ENTERPRISE      sonusDnsMIBNotifications
    VARIABLES       { sonusEventDescription, sonusEventClass, 
                      sonusEventLevel, sonusSequenceId, sonusEventTime }
--     STATUS          mandatory
    DESCRIPTION     
            "This trap is to clear the alarm raised when DNS servers are not responding "
    ::= 3

END -- end of module SONUS-DNS-MIB.
