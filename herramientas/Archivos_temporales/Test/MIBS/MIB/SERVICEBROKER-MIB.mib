SERVICEBROKER-MIB DEFINITIONS ::= BEGIN

IMPORTS
    OBJECT-TYPE, NOTIFICATION-TYPE, MODULE-IDENTITY,
    Integer32, Opaque, enterprises, Counter32, Unsigned32
        FROM SNMPv2-SMI

    TEXTUAL-CONVENTION, DisplayString, TruthValue
	FROM SNMPv2-TC;

servicebroker MODULE-IDENTITY
    LAST-UPDATED "202309020000Z"
    ORGANIZATION "Sparky Wits"
    CONTACT-INFO    
	"
        postal:   382 NE 191ST ST PMB 761874
                   MIAMI, FL 33179

         email:    alzrck@gmail.com
        "
    DESCRIPTION
	"This file defines the private SERVICEBROKER MIB extensions."

    ::= { enterprises 60914 }

sbTraps OBJECT IDENTIFIER ::= { servicebroker 251 }

pingFailed NOTIFICATION-TYPE
    STATUS	current
    DESCRIPTION
	"ping to a declared node failed"
    ::= { sbTraps 1 }
    
containerFailed	NOTIFICATION-TYPE
    STATUS current
    DESCRIPTION
	"a container is failed or missing"
    ::= { sbTraps 2 }

systemDFailed	NOTIFICATION-TYPE
    STATUS current
    DESCRIPTION
	"a process handled by systemd is down or failed"
    ::= { sbTraps 3 }

stirFailed	NOTIFICATION-TYPE
    STATUS current
    DESCRIPTION
	"stir and shaken service is degraded or failing"
    ::= { sbTraps 4 }

END
