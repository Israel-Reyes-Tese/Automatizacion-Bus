--
-- This SMIv2 module has been generated by smidump 0.2-cvs. Do not edit.
--

RIVERSTONE-PRODUCTS-MIB DEFINITIONS ::= BEGIN

IMPORTS
    riverstoneProducts
        FROM RIVERSTONE-SMI-MIB
    MODULE-IDENTITY, OBJECT-IDENTITY
        FROM SNMPv2-SMI;

rsFamilyMIB MODULE-IDENTITY
    LAST-UPDATED    "200210100000Z"
    ORGANIZATION    
            "Riverstone Networks, Inc"
    CONTACT-INFO    
            "Riverstone Networks, Inc
             5200 Great America Parkway
             Santa Clara CA USA 95054
             PHONE:+1 408.878.6500
             EMAIL: nms-eng@riverstonenet.com
             WEB: http://www.riverstonenet.com"
    DESCRIPTION     
            "This mib module defines system Object Identifier values for sysObjectID.0 for 
             network elements manufactured and sold by Riverstone Networks, Inc
             http://www.riverstonenet.com/products. 
             
             Contains sysObjectIDs for RS Procut Line of Multi Layer Switch Routers.
             
             Copyright (C) Riverstone Networks, Inc 2000"
    REVISION        "200004160000Z"
    DESCRIPTION     
            "Riverstone RS Family of products object IDs added."
    REVISION        "200011280000Z"
    DESCRIPTION     
            "Riverstone RS1000 object ID added. Changed IA1000->IA1100, IA1100->IA1200(typo)"
    REVISION        "200011290000Z"
    DESCRIPTION     
            "Riverstone IA1500 object ID added."
    REVISION        "200011300000Z"
    DESCRIPTION     
            "Riverstone RS38000 object ID added."
    REVISION        "200106140000Z"
    DESCRIPTION     
            "Riverstone RS16000 object ID added; Changed IA1500 to IA3000."
    REVISION        "200208130000Z"
    DESCRIPTION     
            "Riverstone ES family object IDs added - ES 500, ES 10170."
    REVISION        "200210100000Z"
    DESCRIPTION     
            "Riverstone RS1100, RS3100, RS3200 object IDs added."
    ::= { riverstoneProducts 1 }


rs8000 OBJECT-IDENTITY
    STATUS          current
    DESCRIPTION     
            "RS 8000 8-slot switch router. 
             http://www.riverstonenet.com/products/RS8x00/rs8x00.html"
    ::= { rsFamilyMIB 1 }

rs8600 OBJECT-IDENTITY
    STATUS          current
    DESCRIPTION     
            "RS 8000 16-slot switch router. 
             http://www.riverstonenet.com/products/RS8x00/rs8x00.html"
    ::= { rsFamilyMIB 2 }

rs2000 OBJECT-IDENTITY
    STATUS          current
    DESCRIPTION     
            "RS 2000 2-slot switch router with fixed 16 port 
             10/100 Ethernet TX
             http://www.riverstonenet.com/products/RS2x00"
    ::= { rsFamilyMIB 3 }

rs2100 OBJECT-IDENTITY
    STATUS          current
    DESCRIPTION     
            "RS 2100 Fixed 8 Port Gigabit Ethernet SX
             http://www.riverstonenet.com/products/RS2x00"
    ::= { rsFamilyMIB 4 }

rs3000 OBJECT-IDENTITY
    STATUS          current
    DESCRIPTION     
            "RS 3000 2-slot switch router with two fixed 
             16 port 10/100 Ethernet TX. 
             http://www.riverstonenet.com/products/RS3000"
    ::= { rsFamilyMIB 5 }

rs32000 OBJECT-IDENTITY
    STATUS          current
    DESCRIPTION     
            "RS 32000 16-slot 500 10/100 or 120 GigEthernet 
             switch router.
             http://www.riverstonenet.com/products/RS32000"
    ::= { rsFamilyMIB 6 }

rs1000 OBJECT-IDENTITY
    STATUS          current
    DESCRIPTION     
            "RS 1000 2-slot switch router
             URL TBD"
    ::= { rsFamilyMIB 8 }

rs38000 OBJECT-IDENTITY
    STATUS          current
    DESCRIPTION     
            "RS 38000 16-slot 500 10/100 or 120 GigEthernet 
             wire-speed switch router.
             http://www.riverstonenet.com/products/RS38000"
    ::= { rsFamilyMIB 9 }

rs16000 OBJECT-IDENTITY
    STATUS          current
    DESCRIPTION     
            "RS 16000 8-slot wire-speed switch router with 
             60 GigE ports.
             Also supports 10GigE and CWDM ports.
             http://www.riverstonenet.com/products/RS16000"
    ::= { rsFamilyMIB 10 }

rs3100 OBJECT-IDENTITY
    STATUS          current
    DESCRIPTION     
            "RS 3100 2-slot switch router with 5th Gen ASICs
             and with two fixed 16 port 10/100 Ethernet TX. 
             URL TBD"
    ::= { rsFamilyMIB 11 }

rs3200 OBJECT-IDENTITY
    STATUS          current
    DESCRIPTION     
            "RS 3200 2-slot switch router with 5th Gen ASICs
             and with two fixed 16 port 10/100 Ethernet FX. 
             URL TBD"
    ::= { rsFamilyMIB 12 }

rs1100 OBJECT-IDENTITY
    STATUS          current
    DESCRIPTION     
            "RS 1100 2-slot switch router with 5th Gen ASICs.
             URL TBD"
    ::= { rsFamilyMIB 13 }

rsIA1100 OBJECT-IDENTITY
    STATUS          current
    DESCRIPTION     
            "IA 1100 2-slot load balancer with fixed 16 port 10/100 Ethernet TX
             http://www.riverstonenet.com/products/internet-appliance"
    ::= { rsFamilyMIB 22 }

rsIA1200 OBJECT-IDENTITY
    STATUS          current
    DESCRIPTION     
            "IA 1200 Fixed 8 port Gigabit Ethernet load balancer
             http://www.riverstonenet.com/products/internet-appliance"
    ::= { rsFamilyMIB 23 }

rsIA3000 OBJECT-IDENTITY
    STATUS          current
    DESCRIPTION     
            "IA 3000 2-slot load balancer 
             http://www.riverstonenet.com/products/internet-appliance"
    ::= { rsFamilyMIB 27 }

es500 OBJECT-IDENTITY
    STATUS          current
    DESCRIPTION     
            "ES 500 edge switch 
             http://www.riverstonenet.com/products/"
    ::= { rsFamilyMIB 31 }

es10170 OBJECT-IDENTITY
    STATUS          current
    DESCRIPTION     
            "ES 10170 edge switch 
             http://www.riverstonenet.com/products/"
    ::= { rsFamilyMIB 32 }

xgs9016 OBJECT-IDENTITY
    STATUS          current
    DESCRIPTION     
            "XGS 9016 16 slot 320G L2/L3 switch 
             http://www.riverstonenet.com/products/"
    ::= { rsFamilyMIB 51 }

xgs9008 OBJECT-IDENTITY
    STATUS          current
    DESCRIPTION     
            "XGS 9008 8 slot 160G L2/L3 switch 
             http://www.riverstonenet.com/products/"
    ::= { rsFamilyMIB 52 }

END -- end of module RIVERSTONE-PRODUCTS-MIB.
