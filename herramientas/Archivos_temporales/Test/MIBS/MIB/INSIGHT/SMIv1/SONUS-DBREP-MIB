--
-- This SMIv1 module has been generated by smidump 0.2-cvs. Do not edit.
--

SONUS-DBREP-MIB DEFINITIONS ::= BEGIN

IMPORTS
    OBJECT-TYPE
        FROM RFC-1212
    TRAP-TYPE
        FROM RFC-1215
    DisplayString
        FROM SNMPv2-TC
    sonusEventClass, sonusEventDescription, sonusEventLevel, 
    sonusEventTime
        FROM SONUS-COMMON-MIB
    sonusHostID
        FROM SONUS-HOST-MIB
    sonusServicesMIBs
        FROM SONUS-SMI;

sonusDbRepMIB OBJECT IDENTIFIER
    ::= { sonusServicesMIBs 25 }

-- sonusDbRepMIB MODULE-IDENTITY
--     LAST-UPDATED    "200406080000Z"
--     ORGANIZATION    
--             "Sonus Networks, Inc."
--     CONTACT-INFO    
--             "   Customer Support    
--              Sonus Networks, Inc.
--              250 Apollo Drive
--              Chelmsford, MA 01824
--              USA
--              
--              Tel: 978-614-8100
--              Fax: 978-614-8609"
--     DESCRIPTION     
--             "The MIB Module for Sonus Database Replication Management."
--     ::= { sonusServicesMIBs 25 }


sonusDbRepMIBObjects OBJECT IDENTIFIER
    ::= { sonusDbRepMIB 1 }

sonusDbRepMIBNotifications OBJECT IDENTIFIER
    ::= { sonusDbRepMIB 2 }

sonusDbRepMIBNotificationsPrefix OBJECT IDENTIFIER
    ::= { sonusDbRepMIBNotifications 0 }

sonusDbRepMIBNotificationsObjects OBJECT IDENTIFIER
    ::= { sonusDbRepMIBNotifications 1 }

sonusDbRepReplicationComponent OBJECT-TYPE
    SYNTAX          INTEGER { extractor(1), exporter(2), importer(3), 
                        poster(4) }
    ACCESS          read-only
    STATUS          mandatory
    DESCRIPTION     
            "Specifies the database replication component.  Extractor is responsible for reading changes from the source database and writing to data queue.  Exporter takes changes in data queue and copies them to target.  Importer receives changes and forwards them to the poster which inserts them into the target database."
    ::= { sonusDbRepMIBNotificationsObjects 1 }

sonusDbRepOraReplicationComponent OBJECT-TYPE
    SYNTAX          INTEGER { extractor(1), poster(2) }
    ACCESS          read-only
    STATUS          mandatory
    DESCRIPTION     
            "Specifies the database replication component which directly interfaces to the database."
    ::= { sonusDbRepMIBNotificationsObjects 2 }

sonusDbRepOraErrReason OBJECT-TYPE
    SYNTAX          DisplayString
    ACCESS          read-only
    STATUS          mandatory
    DESCRIPTION     
            "The reason why the oracle API call failed."
    ::= { sonusDbRepMIBNotificationsObjects 3 }

sonusDbRepOraErrCode OBJECT-TYPE
    SYNTAX          INTEGER
    ACCESS          read-only
    STATUS          mandatory
    DESCRIPTION     
            "The oracle API call return code."
    ::= { sonusDbRepMIBNotificationsObjects 4 }

sonusDbRepInitErrCode OBJECT-TYPE
    SYNTAX          INTEGER { invalidArgs(1), lockfileExists(2), 
                        cannotWriteLogfile(3), dictionaryFileOpenFail(4), 
                        hostnameLookupFail(5), authorization(6), 
                        oracledConnectFail(7), other(8) }
    ACCESS          read-only
    STATUS          mandatory
    DESCRIPTION     
            "The reason that the database replication component initialization failed."
    ::= { sonusDbRepMIBNotificationsObjects 5 }

sonusDbRepConnectFailCode OBJECT-TYPE
    SYNTAX          INTEGER { connection(1), socket(2), fork(3), 
                        other(4) }
    ACCESS          read-only
    STATUS          mandatory
    DESCRIPTION     
            "The reason that the database replication connection failed."
    ::= { sonusDbRepMIBNotificationsObjects 6 }

sonusDbRepFileName OBJECT-TYPE
    SYNTAX          DisplayString
    ACCESS          read-only
    STATUS          mandatory
    DESCRIPTION     
            "The file or directory name being accessed by a database replication component."
    ::= { sonusDbRepMIBNotificationsObjects 7 }

sonusDbRepRTOpCode OBJECT-TYPE
    SYNTAX          INTEGER { read(1), copy(2), delete(3), link(4), 
                        unlink(5), other(6) }
    ACCESS          read-only
    STATUS          mandatory
    DESCRIPTION     
            "The file operation being attempted."
    ::= { sonusDbRepMIBNotificationsObjects 8 }

sonusDbRepOraErrNotification TRAP-TYPE
    ENTERPRISE      sonusDbRepMIBNotifications
    VARIABLES       { sonusEventDescription, sonusEventClass, 
                      sonusEventLevel, sonusEventTime, sonusHostID, 
                      sonusDbRepOraReplicationComponent, 
                      sonusDbRepOraErrReason, sonusDbRepOraErrCode }
--     STATUS          mandatory
    DESCRIPTION     
            "An error has occurred during a call to the oracle API.  The database replication component involved is specified in sonusDbRepOraReplicationComponent.  The error reason is return as sonusDbRepOraErrReason and the error code returned by the Oracle API call is specified in sonusDbRepOraErrCode.  Further details on the error codes can be found in XXXXX."
    ::= 1

sonusDbRepInitErrNotification TRAP-TYPE
    ENTERPRISE      sonusDbRepMIBNotifications
    VARIABLES       { sonusEventDescription, sonusEventClass, 
                      sonusEventLevel, sonusEventTime, sonusHostID, 
                      sonusDbRepReplicationComponent, 
                      sonusDbRepInitErrCode }
--     STATUS          mandatory
    DESCRIPTION     
            "A Database replication process has failed to initialize.  The component that failed is specified in sonusDbRepReplicationComponent.  The initialization failure reason is specified in sonusDbRepProcInitErrCode."
    ::= 2

sonusDbRepInitFileAccessErrNotification TRAP-TYPE
    ENTERPRISE      sonusDbRepMIBNotifications
    VARIABLES       { sonusEventDescription, sonusEventClass, 
                      sonusEventLevel, sonusEventTime, sonusHostID, 
                      sonusDbRepReplicationComponent, sonusDbRepFileName }
--     STATUS          mandatory
    DESCRIPTION     
            "A Database replication process has failed to initialize due to a file access error.  The component that failed is specified in sonusDbRepReplicationComponent.  The file or directory that could not be accessed is specified in sonusDbRepFileName."
    ::= 3

sonusDbRepInitSuccessNotification TRAP-TYPE
    ENTERPRISE      sonusDbRepMIBNotifications
    VARIABLES       { sonusEventDescription, sonusEventClass, 
                      sonusEventLevel, sonusEventTime, sonusHostID, 
                      sonusDbRepReplicationComponent }
--     STATUS          mandatory
    DESCRIPTION     
            "The database replication component identified by sonusDbRepReplicationComponent has initialized successfully."
    ::= 4

sonusDbRepDictionaryOutOfDateNotification TRAP-TYPE
    ENTERPRISE      sonusDbRepMIBNotifications
    VARIABLES       { sonusEventDescription, sonusEventClass, 
                      sonusEventLevel, sonusEventTime, sonusHostID, 
                      sonusDbRepOraReplicationComponent }
--     STATUS          mandatory
    DESCRIPTION     
            "The dictionary file used by database replication is out of date."
    ::= 5

sonusDbRepDictionaryUpToDateNotification TRAP-TYPE
    ENTERPRISE      sonusDbRepMIBNotifications
    VARIABLES       { sonusEventDescription, sonusEventClass, 
                      sonusEventLevel, sonusEventTime, sonusHostID, 
                      sonusDbRepOraReplicationComponent }
--     STATUS          mandatory
    DESCRIPTION     
            "The dictionary file used by database replication is up to date."
    ::= 6

sonusDbRepRTFileAccessErrNotification TRAP-TYPE
    ENTERPRISE      sonusDbRepMIBNotifications
    VARIABLES       { sonusEventDescription, sonusEventClass, 
                      sonusEventLevel, sonusEventTime, sonusHostID, 
                      sonusDbRepReplicationComponent, sonusDbRepFileName, 
                      sonusDbRepRTOpCode }
--     STATUS          mandatory
    DESCRIPTION     
            "A file access error has occurred during runtime in a database replication component.  The file being accessed is specified by sonusDbRepFileName and the operation being performed is specified by sonusDbRepRTOpCode."
    ::= 7

sonusDbRepConnectFailNotification TRAP-TYPE
    ENTERPRISE      sonusDbRepMIBNotifications
    VARIABLES       { sonusEventDescription, sonusEventClass, 
                      sonusEventLevel, sonusEventTime, sonusHostID, 
                      sonusDbRepReplicationComponent, 
                      sonusDbRepConnectFailCode }
--     STATUS          mandatory
    DESCRIPTION     
            "A connection failure occurred for a database replication component.  The reason for the failure is specified by sonusDbRepConnectFailCode."
    ::= 8

sonusDbRepConnectSuccessNotification TRAP-TYPE
    ENTERPRISE      sonusDbRepMIBNotifications
    VARIABLES       { sonusEventDescription, sonusEventClass, 
                      sonusEventLevel, sonusEventTime, sonusHostID, 
                      sonusDbRepOraReplicationComponent }
--     STATUS          mandatory
    DESCRIPTION     
            "A database replication connection was successfully established."
    ::= 9

END -- end of module SONUS-DBREP-MIB.
