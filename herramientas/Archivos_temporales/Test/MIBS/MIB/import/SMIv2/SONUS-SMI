--
-- This SMIv2 module has been generated by smidump 0.2-cvs. Do not edit.
--

SONUS-SMI DEFINITIONS ::= BEGIN

IMPORTS
    MODULE-IDENTITY, OBJECT-IDENTITY, enterprises
        FROM SNMPv2-SMI;

sonus MODULE-IDENTITY
    LAST-UPDATED    "201310070000Z"
    ORGANIZATION    
            "Sonus Networks, Inc."
    CONTACT-INFO    
            "   Customer Support    
             Sonus Networks, Inc.
             4 Technology Park Drive
             Westford, MA 01886
             USA
             
             Tel: 978-614-8100
             Fax: 978-614-8609"
    DESCRIPTION     
            "Initial version of this MIB module."
    ::= { enterprises 2879 }


sonusProducts OBJECT-IDENTITY
    STATUS          current
    DESCRIPTION     
            "sonusProducts is the root OBJECT IDENTIFIER from
             which sysObjectID values are assigned."
    ::= { sonus 1 }

sonusGSXProducts OBJECT-IDENTITY
    STATUS          current
    DESCRIPTION     
            "The Sonus GSX family of products."
    ::= { sonusProducts 1 }

sonusGSX9000 OBJECT-IDENTITY
    STATUS          current
    DESCRIPTION     
            "The Sonus GSX 9000."
    ::= { sonusGSXProducts 1 }

sonusGSX9000HD OBJECT-IDENTITY
    STATUS          current
    DESCRIPTION     
            "The Sonus GSX 9000HD."
    ::= { sonusGSXProducts 2 }

sonusGSX4000 OBJECT-IDENTITY
    STATUS          current
    DESCRIPTION     
            "The Sonus GSX 4000."
    ::= { sonusGSXProducts 3 }

sonusPSXProducts OBJECT-IDENTITY
    STATUS          current
    DESCRIPTION     
            "The Sonus GSX family of products."
    ::= { sonusProducts 2 }

sonusPSX6000 OBJECT-IDENTITY
    STATUS          current
    DESCRIPTION     
            "The Sonus PSX 6000."
    ::= { sonusPSXProducts 1 }

sonusSGXProducts OBJECT-IDENTITY
    STATUS          current
    DESCRIPTION     
            "The Sonus SGX family of products."
    ::= { sonusProducts 3 }

sonusSGX2000 OBJECT-IDENTITY
    STATUS          current
    DESCRIPTION     
            "The Sonus SGX 2000."
    ::= { sonusSGXProducts 1 }

sonusSGX4000 OBJECT-IDENTITY
    STATUS          current
    DESCRIPTION     
            "The Sonus SGX 4000."
    ::= { sonusSGXProducts 2 }

sonusASXProducts OBJECT-IDENTITY
    STATUS          current
    DESCRIPTION     
            "The Sonus ASX family of products."
    ::= { sonusProducts 4 }

sonusASX OBJECT-IDENTITY
    STATUS          current
    DESCRIPTION     
            "The Sonus Access Server (ASX.)"
    ::= { sonusASXProducts 1 }

sonusADS OBJECT-IDENTITY
    STATUS          current
    DESCRIPTION     
            "The Sonus Access Directory Server (ADS.)"
    ::= { sonusASXProducts 2 }

sonusInsightProducts OBJECT-IDENTITY
    STATUS          current
    DESCRIPTION     
            "The Sonus EMS family of products."
    ::= { sonusProducts 5 }

sonusEMS OBJECT-IDENTITY
    STATUS          current
    DESCRIPTION     
            "The Sonus Element Management System."
    ::= { sonusInsightProducts 1 }

sonusDSI OBJECT-IDENTITY
    STATUS          current
    DESCRIPTION     
            "The Sonus Data Stream Integrator."
    ::= { sonusInsightProducts 2 }

sonusCommunicator OBJECT-IDENTITY
    STATUS          current
    DESCRIPTION     
            "The Sonus Communicator."
    ::= { sonusInsightProducts 3 }

sonusIAS OBJECT-IDENTITY
    STATUS          current
    DESCRIPTION     
            "The Sonus Insight Application Server."
    ::= { sonusInsightProducts 4 }

sonusNFSProducts OBJECT-IDENTITY
    STATUS          current
    DESCRIPTION     
            "The Sonus NFS family of products."
    ::= { sonusProducts 6 }

sonusSolNFS OBJECT-IDENTITY
    STATUS          current
    DESCRIPTION     
            "The Sonus NFS agent for Solaris."
    ::= { sonusNFSProducts 1 }

sonusIMXProducts OBJECT-IDENTITY
    STATUS          current
    DESCRIPTION     
            "The Sonus IMX family of products."
    ::= { sonusProducts 7 }

sonusIMX OBJECT-IDENTITY
    STATUS          current
    DESCRIPTION     
            "The Sonus Multimedia Application Platform."
    ::= { sonusIMXProducts 1 }

sonusSRX OBJECT-IDENTITY
    STATUS          current
    DESCRIPTION     
            "The Sonus Call Session Control Function."
    ::= { sonusIMXProducts 2 }

sonusFMCAS OBJECT-IDENTITY
    STATUS          current
    DESCRIPTION     
            "The Sonus FMC Application Server."
    ::= { sonusIMXProducts 3 }

sonusSBXProducts OBJECT-IDENTITY
    STATUS          current
    DESCRIPTION     
            "The Sonus SBX family of products."
    ::= { sonusProducts 9 }

sonusSBX5000 OBJECT-IDENTITY
    STATUS          current
    DESCRIPTION     
            "Sonus Session Border Control Application Platform."
    ::= { sonusSBXProducts 1 }

sonusSBC5200 OBJECT-IDENTITY
    STATUS          current
    DESCRIPTION     
            "Sonus Session Border Control 5200."
    ::= { sonusSBXProducts 2 }

sonusSBC5100 OBJECT-IDENTITY
    STATUS          current
    DESCRIPTION     
            "Sonus Session Border Control 5100."
    ::= { sonusSBXProducts 3 }

slb OBJECT-IDENTITY
    STATUS          current
    DESCRIPTION     
            "Session Border Controller SLB."
    ::= { sonusSBXProducts 7 }

sonusWSX OBJECT-IDENTITY
    STATUS          current
    DESCRIPTION     
            "The WSX Product."
    ::= { sonusProducts 10 }

sonusDatanode OBJECT-IDENTITY
    STATUS          current
    DESCRIPTION     
            "The Data Warehouse product."
    ::= { sonusProducts 11 }

ribbonVnfm OBJECT-IDENTITY
    STATUS          current
    DESCRIPTION     
            "The VNFM product."
    ::= { sonusProducts 12 }

ribbonSTIProducts OBJECT-IDENTITY
    STATUS          current
    DESCRIPTION     
            "The Ribbon STI family of products."
    ::= { sonusProducts 13 }

ribbonSTI OBJECT-IDENTITY
    STATUS          current
    DESCRIPTION     
            "The Ribbon STI Service."
    ::= { ribbonSTIProducts 1 }

ribbonIDHProducts OBJECT-IDENTITY
    STATUS          current
    DESCRIPTION     
            "The Ribbon IDH family of products"
    ::= { sonusProducts 14 }

ribbonIDH OBJECT-IDENTITY
    STATUS          current
    DESCRIPTION     
            "The Ribbon IDH Service."
    ::= { ribbonIDHProducts 1 }

sonusMgmt OBJECT-IDENTITY
    STATUS          current
    DESCRIPTION     
            "sonusMgmt is the main subtree for mib configuration."
    ::= { sonus 2 }

sonusSystemMIBs OBJECT-IDENTITY
    STATUS          current
    DESCRIPTION     
            "Root MIB node for all System-related Sonus MIBs."
    ::= { sonusMgmt 1 }

sonusResourcesMIBs OBJECT-IDENTITY
    STATUS          current
    DESCRIPTION     
            "Root MIB node for all Resource-related Sonus MIBs."
    ::= { sonusMgmt 2 }

sonusPacketMIBs OBJECT-IDENTITY
    STATUS          current
    DESCRIPTION     
            "Root MIB node for all Packet-related Sonus MIBs."
    ::= { sonusMgmt 3 }

sonusCircuitMIBs OBJECT-IDENTITY
    STATUS          current
    DESCRIPTION     
            "Root MIB node for all Circuit-related Sonus MIBs."
    ::= { sonusMgmt 4 }

sonusServicesMIBs OBJECT-IDENTITY
    STATUS          current
    DESCRIPTION     
            "Root MIB node for all Services-related Sonus MIBs."
    ::= { sonusMgmt 5 }

sonusSignallingMIBs OBJECT-IDENTITY
    STATUS          current
    DESCRIPTION     
            "Root MIB node for all Signalling-related Sonus MIBs."
    ::= { sonusMgmt 6 }

sonusToolsMIBs OBJECT-IDENTITY
    STATUS          current
    DESCRIPTION     
            "Root MIB node for all Sonus development tools MIBs."
    ::= { sonusMgmt 7 }

sonusCommonSoftwarePlatformServicesMIBs OBJECT-IDENTITY
    STATUS          current
    DESCRIPTION     
            "Root MIB node for all Common Software Platform Services MIBs."
    ::= { sonusMgmt 8 }

sonusCspsNotificationMIBs OBJECT-IDENTITY
    STATUS          current
    DESCRIPTION     
            "Root MIB node for all Sonus NextGen Notification MIBs."
    ::= { sonusCommonSoftwarePlatformServicesMIBs 1 }

sonusSGX4000MIBs OBJECT-IDENTITY
    STATUS          current
    DESCRIPTION     
            "Root MIB node for all SGX4000 MIBs."
    ::= { sonusMgmt 9 }

sonusSGX4000NotificationMIBs OBJECT-IDENTITY
    STATUS          current
    DESCRIPTION     
            "Root MIB node for all Sonus SGX4000 Notification MIBs."
    ::= { sonusSGX4000MIBs 1 }

sonusSBX5000MIBs OBJECT-IDENTITY
    STATUS          current
    DESCRIPTION     
            "Root MIB node for all SBX5000 MIBs."
    ::= { sonusMgmt 10 }

sonusSBX5000NotificationMIBs OBJECT-IDENTITY
    STATUS          current
    DESCRIPTION     
            "Root MIB node for all Sonus SBX5000 Notification MIBs."
    ::= { sonusSBX5000MIBs 1 }

sonusWSXMIBs OBJECT-IDENTITY
    STATUS          current
    DESCRIPTION     
            "Root MIB node for all WSX MIBs."
    ::= { sonusMgmt 11 }

sonusWSXNotificationMIBs OBJECT-IDENTITY
    STATUS          current
    DESCRIPTION     
            "Root MIB node for all Sonus WSX Notification MIBs."
    ::= { sonusWSXMIBs 1 }

sonusDatanodeMIBs OBJECT-IDENTITY
    STATUS          current
    DESCRIPTION     
            "Root MIB node for all Datanode MIBs."
    ::= { sonusMgmt 12 }

sonusDatanodeNotificationMIBs OBJECT-IDENTITY
    STATUS          current
    DESCRIPTION     
            "Root MIB node for all Sonus Datanode Notification MIBs."
    ::= { sonusDatanodeMIBs 1 }

ribbonVnfmMIBs OBJECT-IDENTITY
    STATUS          current
    DESCRIPTION     
            "Root MIB node for all VNFM MIBs."
    ::= { sonusMgmt 13 }

ribbonVnfmNotificationMIBs OBJECT-IDENTITY
    STATUS          current
    DESCRIPTION     
            "The Ribbon Vnfm product."
    ::= { ribbonVnfmMIBs 1 }

sonusModules OBJECT-IDENTITY
    STATUS          current
    DESCRIPTION     
            "sonusModules provides a root object identifier
             from which MODULE-IDENTITY values may be assigned."
    ::= { sonus 3 }

END -- end of module SONUS-SMI.
