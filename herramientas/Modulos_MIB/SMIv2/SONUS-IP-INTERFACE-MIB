--
-- This SMIv2 module has been generated by smidump 0.2-cvs. Do not edit.
--

SONUS-IP-INTERFACE-MIB DEFINITIONS ::= BEGIN

IMPORTS
    AtmAddr
        FROM ATM-TC-MIB
    IANAifType
        FROM IANAifType-MIB
    Ipv6Address
        FROM IPV6-TC
    Counter32, Integer32, IpAddress, MODULE-IDENTITY, NOTIFICATION-TYPE, 
    OBJECT-TYPE, Unsigned32
        FROM SNMPv2-SMI
    DisplayString, PhysAddress, RowStatus
        FROM SNMPv2-TC
    sonusEventClass, sonusEventDescription, sonusEventLevel, 
    sonusEventTime, sonusSequenceId, sonusShelfIndex, sonusSlotIndex
        FROM SONUS-COMMON-MIB
    sonusPacketMIBs
        FROM SONUS-SMI
    SonusName, SonusNameReference, SonusShelfIndex, SonusSlotIndex
        FROM SONUS-TC;

sonusIpInterfaceMIB MODULE-IDENTITY
    LAST-UPDATED    "201404140000Z"
    ORGANIZATION    
            "Sonus Networks, Inc."
    CONTACT-INFO    
            "   Customer Support    
             Sonus Networks, Inc,
             7 Technology Park Drive
             Westford, MA 01886
             USA
             
             Tel: 978-614-8100
             Fax: 978-614-8609
             E-mail: cs.snmp@sonusnet.com"
    DESCRIPTION     
            "The MIB Module for IP Interface Management."
    ::= { sonusPacketMIBs 1 }


sonusIpInterfaceMIBObjects OBJECT IDENTIFIER
    ::= { sonusIpInterfaceMIB 1 }

sonusNrsConfigObjects OBJECT IDENTIFIER
    ::= { sonusIpInterfaceMIBObjects 1 }

sonusNrsVirtExtRouterEnable OBJECT-TYPE
    SYNTAX          INTEGER { disabled(1), enabled(2) }
    MAX-ACCESS      read-write
    STATUS          current
    DESCRIPTION     
            "The Virtual External Router administrative status.
             The value 'enabled' denotes that Gateway IP addresses
             will be advertised with one associated with each
             active PNS link and that learned routes will not be
             readvertised (to prevent routes through us).  The
             value 'disabled' denotes that routing will operate
             as usual."
    DEFVAL          { disabled }
    ::= { sonusNrsConfigObjects 1 }

sonusNrsTcpMss OBJECT-TYPE
    SYNTAX          Integer32 (536..1460)
    MAX-ACCESS      read-write
    STATUS          current
    DESCRIPTION     
            "Value of TCP maximum segment size (mss). Generally, this
             is set 40 bytes less than the interface MTU."
    DEFVAL          { 1452 }
    ::= { sonusNrsConfigObjects 2 }

sonusNrsLSAddrBindState OBJECT-TYPE
    SYNTAX          INTEGER { disabled(1), enabled(2) }
    MAX-ACCESS      read-write
    STATUS          current
    DESCRIPTION     
            "If enabled, logical addresses with matching subnets will
             be bound to the PNS NIFs."
    DEFVAL          { 1 }
    ::= { sonusNrsConfigObjects 3 }

sonusNrsPacketFilterMode OBJECT-TYPE
    SYNTAX          INTEGER { ipinputFilter(1), ipAcl(2), none(3) }
    MAX-ACCESS      read-write
    STATUS          current
    DESCRIPTION     
            "Kind of Packet filter mode for received IP packets."
    DEFVAL          { 3 }
    ::= { sonusNrsConfigObjects 4 }

sonusNrsTcpKeepAliveIdleTimeOut OBJECT-TYPE
    SYNTAX          Integer32 (120..7200)
    MAX-ACCESS      read-write
    STATUS          current
    DESCRIPTION     
            "Value of TCP keep alive Idle Time Out."
    DEFVAL          { 7200 }
    ::= { sonusNrsConfigObjects 5 }

sonusNrsLogicalBearerAddressTable OBJECT-TYPE
    SYNTAX          SEQUENCE OF SonusNrsLogicalBearerAddressEntry
    MAX-ACCESS      not-accessible
    STATUS          current
    DESCRIPTION     
            "The collection of NRS Gateway IP information for the
             specified instance."
    ::= { sonusIpInterfaceMIBObjects 2 }

sonusNrsLogicalBearerAddressEntry OBJECT-TYPE
    SYNTAX          SonusNrsLogicalBearerAddressEntry
    MAX-ACCESS      not-accessible
    STATUS          current
    DESCRIPTION     
            "The collection of NRS Gateway IP information for the
             specified instance."
    INDEX           { sonusNrsLogicalBearerAddressIpVersion, 
                      sonusNrsLogicalBearerAddressAddress, 
                      sonusNrsLogicalBearerIpv6AddressAddress }
    ::= { sonusNrsLogicalBearerAddressTable 1 }

SonusNrsLogicalBearerAddressEntry ::=
    SEQUENCE {
        sonusNrsLogicalBearerAddressAddress   IpAddress,
        sonusNrsLogicalBearerAddressMask IpAddress,
        sonusNrsLogicalBearerAddressSize Integer32,
        sonusNrsLogicalBearerAddressRowStatus     RowStatus,
        sonusNrsLogicalBearerIpv6AddressAddress       Ipv6Address,
        sonusNrsLogicalBearerAddressPrefixlength        Integer32,
        sonusNrsLogicalBearerAddressIpVersion     INTEGER
    }

sonusNrsLogicalBearerAddressAddress OBJECT-TYPE
    SYNTAX          IpAddress
    MAX-ACCESS      read-write
    STATUS          current
    DESCRIPTION     
            "The IP Address of this entry"
    ::= { sonusNrsLogicalBearerAddressEntry 1 }

sonusNrsLogicalBearerAddressMask OBJECT-TYPE
    SYNTAX          IpAddress
    MAX-ACCESS      read-write
    STATUS          current
    DESCRIPTION     
            "The IP mask of this entry.  May be a full host
             mask or a subnet mask.  Default is natural mask of
             Address"
    ::= { sonusNrsLogicalBearerAddressEntry 2 }

sonusNrsLogicalBearerAddressSize OBJECT-TYPE
    SYNTAX          Integer32
    MAX-ACCESS      read-write
    STATUS          current
    DESCRIPTION     
            "Size of the pool.  Default is full range given by mask."
    ::= { sonusNrsLogicalBearerAddressEntry 3 }

sonusNrsLogicalBearerAddressRowStatus OBJECT-TYPE
    SYNTAX          RowStatus
    MAX-ACCESS      read-write
    STATUS          current
    DESCRIPTION     
            ""
    ::= { sonusNrsLogicalBearerAddressEntry 4 }

sonusNrsLogicalBearerIpv6AddressAddress OBJECT-TYPE
    SYNTAX          Ipv6Address
    MAX-ACCESS      read-write
    STATUS          current
    DESCRIPTION     
            "The IPv6 Address of this entry"
    ::= { sonusNrsLogicalBearerAddressEntry 5 }

sonusNrsLogicalBearerAddressPrefixlength OBJECT-TYPE
    SYNTAX          Integer32
    MAX-ACCESS      read-write
    STATUS          current
    DESCRIPTION     
            "The Prefix Length for the logical bearear address"
    ::= { sonusNrsLogicalBearerAddressEntry 6 }

sonusNrsLogicalBearerAddressIpVersion OBJECT-TYPE
    SYNTAX          INTEGER { afInet(2), afInet6(24) }
    MAX-ACCESS      read-only
    STATUS          current
    DESCRIPTION     
            "IP Address Type"
    ::= { sonusNrsLogicalBearerAddressEntry 7 }

sonusNif OBJECT IDENTIFIER
    ::= { sonusIpInterfaceMIBObjects 3 }

sonusNifNextIndex OBJECT-TYPE
    SYNTAX          Integer32
    MAX-ACCESS      read-only
    STATUS          current
    DESCRIPTION     
            "The next valid index to use when creating an entry in
             the sonusNifTable."
    ::= { sonusNif 1 }

sonusNifTable OBJECT-TYPE
    SYNTAX          SEQUENCE OF SonusNifEntry
    MAX-ACCESS      not-accessible
    STATUS          current
    DESCRIPTION     
            "The collection of Interface information for the
             specified instance."
    ::= { sonusNif 2 }

sonusNifEntry OBJECT-TYPE
    SYNTAX          SonusNifEntry
    MAX-ACCESS      not-accessible
    STATUS          current
    DESCRIPTION     
            "The collection of Interface information for the
             specified instance."
    INDEX           { sonusNifIndex }
    ::= { sonusNifTable 1 }

SonusNifEntry ::=
    SEQUENCE {
        sonusNifIndex                   Integer32,
        sonusNifName                    SonusName,
        sonusNifType                    IANAifType,
        sonusNifIpAddress               IpAddress,
        sonusNifIpMask                  IpAddress,
        sonusNifMtu                     Integer32,
        sonusNifShelf                   SonusShelfIndex,
        sonusNifSlot                    SonusSlotIndex,
        sonusNifPort                    Integer32,
        sonusNifCircuit                 Integer32,
        sonusNifNextHopAddr             IpAddress,
        sonusNifMode                    INTEGER,
        sonusNifAction                  INTEGER,
        sonusNifTimeout                 Integer32,
        sonusNifState                   INTEGER,
        sonusNifOutOfServiceReason      INTEGER,
        sonusNifClass                   INTEGER,
        sonusNifRowStatus               RowStatus,
        sonusNifBwDeviation             Integer32,
        sonusNifBwContingency           Integer32,
        sonusNifConfAtmAddress          AtmAddr,
        sonusNifActAtmAddress           AtmAddr,
        sonusNifVlanTaggingState        INTEGER,
        sonusNifVlanTag                 Integer32,
        sonusNifDGPBucketSize           Integer32,
        sonusNifDGPFillRate             Integer32,
        sonusNifDGPState                INTEGER,
        sonusNifLGPState                INTEGER,
        sonusNifVLanPState              INTEGER,
        sonusNifVLanPBucketSize         Integer32,
        sonusNifVLanPFillRate           Integer32,
        sonusNifIpSecPolicyName         DisplayString,
        sonusNifXnqStrippingState       INTEGER,
        sonusNifIpv6Address             Ipv6Address,
        sonusNifIpv6NextHopAddr         Ipv6Address,
        sonusNifIpv6PrefixLength        Integer32,
        sonusNifIpv6LlAddress           Ipv6Address,
        sonusNifIpv6PrefixMask          Ipv6Address
    }

sonusNifIndex OBJECT-TYPE
    SYNTAX          Integer32
    MAX-ACCESS      read-only
    STATUS          current
    DESCRIPTION     
            "The ifIndex assigned to this NIF when it was created.
             This will not change until the NIF is deleted."
    ::= { sonusNifEntry 1 }

sonusNifName OBJECT-TYPE
    SYNTAX          SonusName
    MAX-ACCESS      read-write
    STATUS          current
    DESCRIPTION     
            "The administrative name of the NIF."
    ::= { sonusNifEntry 2 }

sonusNifType OBJECT-TYPE
    SYNTAX          IANAifType
    MAX-ACCESS      read-write
    STATUS          current
    DESCRIPTION     
            "The type of interface, distinguished according to the
             physical/link protocol(s) immediately 'below' the network
             layer in the protocol stack.
             
             Values are from the IANAifType TC."
    DEFVAL          { 6 }
    ::= { sonusNifEntry 3 }

sonusNifIpAddress OBJECT-TYPE
    SYNTAX          IpAddress
    MAX-ACCESS      read-write
    STATUS          current
    DESCRIPTION     
            "The IP Address of the Interface"
    ::= { sonusNifEntry 4 }

sonusNifIpMask OBJECT-TYPE
    SYNTAX          IpAddress
    MAX-ACCESS      read-write
    STATUS          current
    DESCRIPTION     
            "The IP subnet mask of this Interface."
    ::= { sonusNifEntry 5 }

sonusNifMtu OBJECT-TYPE
    SYNTAX          Integer32 (576..1500)
    MAX-ACCESS      read-only
    STATUS          current
    DESCRIPTION     
            "The size of the largest datagram that can be sent/received
             on the interface, specified in octets."
    ::= { sonusNifEntry 6 }

sonusNifShelf OBJECT-TYPE
    SYNTAX          SonusShelfIndex
    MAX-ACCESS      read-write
    STATUS          current
    DESCRIPTION     
            "A 32-bit integer identifying the shelf of the
             Interface"
    ::= { sonusNifEntry 7 }

sonusNifSlot OBJECT-TYPE
    SYNTAX          SonusSlotIndex
    MAX-ACCESS      read-write
    STATUS          current
    DESCRIPTION     
            "A 32-bit integer identifying the slot of the
             Interface"
    ::= { sonusNifEntry 8 }

sonusNifPort OBJECT-TYPE
    SYNTAX          Integer32 (1..4)
    MAX-ACCESS      read-write
    STATUS          current
    DESCRIPTION     
            "A 32-bit integer identifying the port of the
             Interface."
    ::= { sonusNifEntry 9 }

sonusNifCircuit OBJECT-TYPE
    SYNTAX          Integer32
    MAX-ACCESS      read-only
    STATUS          current
    DESCRIPTION     
            "A 32-bit integer identifying the circuit of the
             Interface.  For current hardware this must be 1."
    DEFVAL          { 1 }
    ::= { sonusNifEntry 10 }

sonusNifNextHopAddr OBJECT-TYPE
    SYNTAX          IpAddress
    MAX-ACCESS      read-write
    STATUS          current
    DESCRIPTION     
            "The next hop address to use for all traffic out this NIF."
    ::= { sonusNifEntry 11 }

sonusNifMode OBJECT-TYPE
    SYNTAX          INTEGER { outOfService(1), inService(2) }
    MAX-ACCESS      read-write
    STATUS          current
    DESCRIPTION     
            "The operation mode for NIF."
    DEFVAL          { inService }
    ::= { sonusNifEntry 12 }

sonusNifAction OBJECT-TYPE
    SYNTAX          INTEGER { dryUp(1), force(2) }
    MAX-ACCESS      read-write
    STATUS          current
    DESCRIPTION     
            "The dryup option for NIF."
    DEFVAL          { dryUp }
    ::= { sonusNifEntry 13 }

sonusNifTimeout OBJECT-TYPE
    SYNTAX          Integer32 (1..1440)
    MAX-ACCESS      read-write
    STATUS          current
    DESCRIPTION     
            "The dryup timeout in minute. The default is one hour "
    DEFVAL          { 60 }
    ::= { sonusNifEntry 14 }

sonusNifState OBJECT-TYPE
    SYNTAX          INTEGER { disabled(1), enabled(2) }
    MAX-ACCESS      read-write
    STATUS          current
    DESCRIPTION     
            "Administrative state of the interface.
             Changes may only be made while disabled and will only
             take effect when enabled next."
    ::= { sonusNifEntry 15 }

sonusNifOutOfServiceReason OBJECT-TYPE
    SYNTAX          INTEGER { notApplicable(1), admin(2), gateway(3), 
                        portDown(4), serverDown(5), vcsDown(6), noVc(7), 
                        srvrAbsent(8), linkDown(9), noAtmAddr(10), 
                        standby(11), noLogicalBearerAddress(12) }
    MAX-ACCESS      read-only
    STATUS          current
    DESCRIPTION     
            "The reason of NIF being out of service. The NIF could be out of service due to one 
             of the following reasons: operator initiated command, gateway not responding to 
             arp request, port failure/outOfService, or server failure/outOfService. The 
             		 notApplicable is set when the NIF is inService or dryUp state"
    ::= { sonusNifEntry 16 }

sonusNifClass OBJECT-TYPE
    SYNTAX          INTEGER { general(1), reserved(2) }
    MAX-ACCESS      read-write
    STATUS          current
    DESCRIPTION     
            "This object indicates whether a NIF is reserved or general(not reserved). The resources
             of a general NIF are used by marlin common IP calls whereas the resources of a reserved 
             NIF are used only by MGCP IP calls"
    DEFVAL          { general }
    ::= { sonusNifEntry 17 }

sonusNifRowStatus OBJECT-TYPE
    SYNTAX          RowStatus
    MAX-ACCESS      read-write
    STATUS          current
    DESCRIPTION     
            ""
    ::= { sonusNifEntry 18 }

sonusNifBwDeviation OBJECT-TYPE
    SYNTAX          Integer32 (0..100)
    MAX-ACCESS      read-write
    STATUS          current
    DESCRIPTION     
            "The deviation between actual and expected NIF bandwidth in percentage of the 
             overall NIF bandwidth. If actual bandwidth is greater than the expected 
             bandwdith plus deviation amount, a trap will be set and the trap will be 
             only cleared when the actual bandwidth dropped below the expected bandwidth.
             If the actual bandwidth is lower than the expected badniwdth minus 2 times
             of deviation amount, a different trap will be set and the trap will be
             cleared when the actual bandwdith reaches the expected bandwidth. "
    DEFVAL          { 0 }
    ::= { sonusNifEntry 19 }

sonusNifBwContingency OBJECT-TYPE
    SYNTAX          Integer32 (0..100)
    MAX-ACCESS      read-write
    STATUS          current
    DESCRIPTION     
            "The percentage of the overall NIF bandwidth is reserved for contigency. If actual 
             bandwidth is greater than the expected bandwdith and less than the overall NIF
             bandwidth minus contingency amount, calls will still be accepted. "
    DEFVAL          { 0 }
    ::= { sonusNifEntry 20 }

sonusNifConfAtmAddress OBJECT-TYPE
    SYNTAX          AtmAddr
    MAX-ACCESS      read-write
    STATUS          current
    DESCRIPTION     
            "This is user configured ATM address for IPOA/VTOA NIF."
    ::= { sonusNifEntry 22 }

sonusNifActAtmAddress OBJECT-TYPE
    SYNTAX          AtmAddr
    MAX-ACCESS      read-only
    STATUS          current
    DESCRIPTION     
            "This is the actual ATM address used for IPOA/VTOA NIF."
    ::= { sonusNifEntry 23 }

sonusNifVlanTaggingState OBJECT-TYPE
    SYNTAX          INTEGER { disabled(1), enabled(2) }
    MAX-ACCESS      read-write
    STATUS          current
    DESCRIPTION     
            "Administrative state of the VLAN tagging."
    DEFVAL          { disabled }
    ::= { sonusNifEntry 24 }

sonusNifVlanTag OBJECT-TYPE
    SYNTAX          Integer32 (1..4095)
    MAX-ACCESS      read-write
    STATUS          current
    DESCRIPTION     
            "The VLAN TAG assigned to this physical interface"
    ::= { sonusNifEntry 25 }

sonusNifDGPBucketSize OBJECT-TYPE
    SYNTAX          Integer32 (16..65520)
    MAX-ACCESS      read-write
    STATUS          current
    DESCRIPTION     
            "The per NIF dark gray policer bucket size, in bytes,
             used to policing all traffic that does not match a
             white list policer. The range is 16 bytes to 65520
             bytes, in 16 byte increments. 0 to 128 pseudo-packets
             in 1/32 packet increments."
    ::= { sonusNifEntry 26 }

sonusNifDGPFillRate OBJECT-TYPE
    SYNTAX          Integer32 (256..16776960)
    MAX-ACCESS      read-write
    STATUS          current
    DESCRIPTION     
            "The per NIF dark gray policer fill rate, in bytes
             per second, used to policing all traffic that does 
             not match a white list policer. The range is 256 
             bytes/sec to 16M bytes/second in increments of 
             256 bytes/sec, 0.5 to 32K pseudo-pps in increments 
             of 0.5 pps."
    ::= { sonusNifEntry 27 }

sonusNifDGPState OBJECT-TYPE
    SYNTAX          INTEGER { disabled(1), enabled(2) }
    MAX-ACCESS      read-write
    STATUS          current
    DESCRIPTION     
            "Administrative state of dark gray policer."
    DEFVAL          { disabled }
    ::= { sonusNifEntry 28 }

sonusNifLGPState OBJECT-TYPE
    SYNTAX          INTEGER { disabled(1), enabled(2) }
    MAX-ACCESS      read-write
    STATUS          current
    DESCRIPTION     
            "Administrative state of light gray policer."
    DEFVAL          { disabled }
    ::= { sonusNifEntry 29 }

sonusNifVLanPState OBJECT-TYPE
    SYNTAX          INTEGER { disabled(1), enabled(2) }
    MAX-ACCESS      read-write
    STATUS          current
    DESCRIPTION     
            "Administrative state of VLAN policer."
    DEFVAL          { disabled }
    ::= { sonusNifEntry 30 }

sonusNifVLanPBucketSize OBJECT-TYPE
    SYNTAX          Integer32 (16..65520)
    MAX-ACCESS      read-write
    STATUS          current
    DESCRIPTION     
            "The per Logical Interface/VLAN policer bucket size, in bytes,
             used to policing all signaling traffic at the logical interface level.
             The rate is 16 bytes to 65520 bytes, in 16 byte increments.  0 to 128
             pseudo-packets (512 bytes) in 1/32 packet increments."
    ::= { sonusNifEntry 31 }

sonusNifVLanPFillRate OBJECT-TYPE
    SYNTAX          Integer32 (256..16776960)
    MAX-ACCESS      read-write
    STATUS          current
    DESCRIPTION     
            "The per Logical Interface/VLAN policer fill rate, in bytes
             per second, used to policing all signaling traffic at the logical
             interface level.  The range is 256 bytes/sec to 16MBytes/second 
             in increments of 256 bytes/sec. 0.5 to 32K pseudo-packets/second
             in increments of 0.5 packets per second."
    ::= { sonusNifEntry 32 }

sonusNifIpSecPolicyName OBJECT-TYPE
    SYNTAX          DisplayString (SIZE(0..23))
    MAX-ACCESS      read-write
    STATUS          current
    DESCRIPTION     
            "The name of the IPsec Policy assigned to this NIF. Null if IPsec 
             disabled."
    ::= { sonusNifEntry 33 }

sonusNifXnqStrippingState OBJECT-TYPE
    SYNTAX          INTEGER { disabled(1), enabled(2) }
    MAX-ACCESS      read-write
    STATUS          current
    DESCRIPTION     
            "Administrative state of XNQ stripping."
    DEFVAL          { disabled }
    ::= { sonusNifEntry 34 }

sonusNifIpv6Address OBJECT-TYPE
    SYNTAX          Ipv6Address
    MAX-ACCESS      read-write
    STATUS          current
    DESCRIPTION     
            "The IPv6 Address of this entry"
    ::= { sonusNifEntry 35 }

sonusNifIpv6NextHopAddr OBJECT-TYPE
    SYNTAX          Ipv6Address
    MAX-ACCESS      read-write
    STATUS          current
    DESCRIPTION     
            "The next hop IPv6 Address of this entry"
    ::= { sonusNifEntry 36 }

sonusNifIpv6PrefixLength OBJECT-TYPE
    SYNTAX          Integer32
    MAX-ACCESS      read-write
    STATUS          current
    DESCRIPTION     
            "Ipv6 Prefix Length"
    ::= { sonusNifEntry 37 }

sonusNifIpv6LlAddress OBJECT-TYPE
    SYNTAX          Ipv6Address
    MAX-ACCESS      read-only
    STATUS          current
    DESCRIPTION     
            "The Link local IPv6 Address of this entry"
    ::= { sonusNifEntry 38 }

sonusNifIpv6PrefixMask OBJECT-TYPE
    SYNTAX          Ipv6Address
    MAX-ACCESS      read-only
    STATUS          current
    DESCRIPTION     
            "The IPv6 Prefix Mask of this entry"
    ::= { sonusNifEntry 39 }

sonusNrsLogicalBearerAddressBindingTable OBJECT-TYPE
    SYNTAX          SEQUENCE OF SonusNrsLogicalBearerAddressBindingEntry
    MAX-ACCESS      not-accessible
    STATUS          current
    DESCRIPTION     
            "The collection of NRS Gateway IP information for the
             specified instance."
    ::= { sonusIpInterfaceMIBObjects 4 }

sonusNrsLogicalBearerAddressBindingEntry OBJECT-TYPE
    SYNTAX          SonusNrsLogicalBearerAddressBindingEntry
    MAX-ACCESS      not-accessible
    STATUS          current
    DESCRIPTION     
            "The collection of NRS Logical Bearer Address Binding information
             for the specified instance."
    INDEX           { sonusNrsLogicalBearerAddressBindingIpVersion, 
                      sonusNrsLogicalBearerAddressBindingAddress, 
                      sonusNrsLogicalBearerIpv6AddressBindingAddress }
    ::= { sonusNrsLogicalBearerAddressBindingTable 1 }

SonusNrsLogicalBearerAddressBindingEntry ::=
    SEQUENCE {
        sonusNrsLogicalBearerAddressBindingAddress          IpAddress,
        sonusNrsLogicalBearerAddressBindingIndex        Integer32,
        sonusNrsLogicalBearerIpv6AddressBindingAddress              Ipv6Address,
        sonusNrsLogicalBearerAddressBindingIpVersion            INTEGER
    }

sonusNrsLogicalBearerAddressBindingAddress OBJECT-TYPE
    SYNTAX          IpAddress
    MAX-ACCESS      read-only
    STATUS          current
    DESCRIPTION     
            "The instantiated logical bearer address bound to the NIF"
    ::= { sonusNrsLogicalBearerAddressBindingEntry 1 }

sonusNrsLogicalBearerAddressBindingIndex OBJECT-TYPE
    SYNTAX          Integer32
    MAX-ACCESS      read-only
    STATUS          current
    DESCRIPTION     
            "The sonusNrsLogicalBearerAddressIndex from the
             sonusNrsLogicalBearerAddressTable of the entry from which this
             logical bearer address was allocated."
    ::= { sonusNrsLogicalBearerAddressBindingEntry 2 }

sonusNrsLogicalBearerIpv6AddressBindingAddress OBJECT-TYPE
    SYNTAX          Ipv6Address
    MAX-ACCESS      read-only
    STATUS          current
    DESCRIPTION     
            "The instantiated logical bearer ipv6 address bound to the NIF"
    ::= { sonusNrsLogicalBearerAddressBindingEntry 3 }

sonusNrsLogicalBearerAddressBindingIpVersion OBJECT-TYPE
    SYNTAX          INTEGER { afInet(2), afInet6(24) }
    MAX-ACCESS      read-only
    STATUS          current
    DESCRIPTION     
            "IP Address Type"
    ::= { sonusNrsLogicalBearerAddressBindingEntry 4 }

sonusNifAdmnTable OBJECT-TYPE
    SYNTAX          SEQUENCE OF SonusNifAdmnEntry
    MAX-ACCESS      not-accessible
    STATUS          current
    DESCRIPTION     
            "The collection of Interface information for the
             specified instance."
    ::= { sonusIpInterfaceMIBObjects 6 }

sonusNifAdmnEntry OBJECT-TYPE
    SYNTAX          SonusNifAdmnEntry
    MAX-ACCESS      not-accessible
    STATUS          current
    DESCRIPTION     
            "The collection of Interface information for the specified instance."
    INDEX           { sonusNifAdmnShelf, sonusNifAdmnSlot, 
                      sonusNifAdmnPort, sonusNifAdmnIndex }
    ::= { sonusNifAdmnTable 1 }

SonusNifAdmnEntry ::=
    SEQUENCE {
        sonusNifAdmnShelf               SonusShelfIndex,
        sonusNifAdmnSlot                SonusSlotIndex,
        sonusNifAdmnPort                Integer32,
        sonusNifAdmnIndex               Integer32
    }

sonusNifAdmnShelf OBJECT-TYPE
    SYNTAX          SonusShelfIndex
    MAX-ACCESS      read-only
    STATUS          current
    DESCRIPTION     
            "A 32-bit integer identifying the shelf of the Interface"
    ::= { sonusNifAdmnEntry 1 }

sonusNifAdmnSlot OBJECT-TYPE
    SYNTAX          SonusSlotIndex
    MAX-ACCESS      read-only
    STATUS          current
    DESCRIPTION     
            "A 32-bit integer identifying the slot of the Interface"
    ::= { sonusNifAdmnEntry 2 }

sonusNifAdmnPort OBJECT-TYPE
    SYNTAX          Integer32
    MAX-ACCESS      read-only
    STATUS          current
    DESCRIPTION     
            "A 32-bit integer identifying the port of the Interface."
    ::= { sonusNifAdmnEntry 3 }

sonusNifAdmnIndex OBJECT-TYPE
    SYNTAX          Integer32
    MAX-ACCESS      read-only
    STATUS          current
    DESCRIPTION     
            "The ifIndex assigned to this NIF when it was created.
             This will not change until the NIF is deleted."
    ::= { sonusNifAdmnEntry 4 }

sonusNrsMgmtIfTable OBJECT-TYPE
    SYNTAX          SEQUENCE OF SonusNrsMgmtIfEntry
    MAX-ACCESS      not-accessible
    STATUS          current
    DESCRIPTION     
            "The collection of Management Interface information for the
             specified instance."
    ::= { sonusIpInterfaceMIBObjects 7 }

sonusNrsMgmtIfEntry OBJECT-TYPE
    SYNTAX          SonusNrsMgmtIfEntry
    MAX-ACCESS      not-accessible
    STATUS          current
    DESCRIPTION     
            "The collection of Management Interface information for the
             specified instance."
    INDEX           { sonusNrsMgmtIfShelf, sonusNrsMgmtIfSlot, 
                      sonusNrsMgmtIfPort, sonusNrsMgmtIfCircuit }
    ::= { sonusNrsMgmtIfTable 1 }

SonusNrsMgmtIfEntry ::=
    SEQUENCE {
        sonusNrsMgmtIfIndex             Integer32,
        sonusNrsMgmtIfShelf             SonusShelfIndex,
        sonusNrsMgmtIfSlot              SonusSlotIndex,
        sonusNrsMgmtIfPort              Integer32,
        sonusNrsMgmtIfCircuit           Integer32,
        sonusNrsMgmtIfType              IANAifType,
        sonusNrsMgmtIfIpAddress         IpAddress,
        sonusNrsMgmtIfIpMask            IpAddress,
        sonusNrsMgmtIfMtu               Integer32,
        sonusNrsMgmtIfGatewayAddress    IpAddress,
        sonusNrsMgmtIfMode              INTEGER,
        sonusNrsMgmtIfAdminStatus       INTEGER,
        sonusNrsMgmtIfOperStatus        INTEGER,
        sonusNrsMgmtIfLogicMgmtIpAddress IpAddress,
        sonusNrsMgmtIfName              SonusName,
        sonusNrsMgmtIfDGPBucketSize     Integer32,
        sonusNrsMgmtIfDGPFillRate       Integer32,
        sonusNrsMgmtIfDGPAdminState     INTEGER,
        sonusNrsMgmtIfRowStatus         RowStatus,
        sonusNrsMgmtIfIpv6Address       Ipv6Address,
        sonusNrsMgmtIfGatewayIpv6Address Ipv6Address,
        sonusNrsMgmtIfIpv6Prefixlen     Integer32,
        sonusNrsMgmtIfLogicMgmtIpv6Address  Ipv6Address,
        sonusNrsMgmtIfLlIpv6Address     Ipv6Address
    }

sonusNrsMgmtIfIndex OBJECT-TYPE
    SYNTAX          Integer32
    MAX-ACCESS      read-only
    STATUS          current
    DESCRIPTION     
            "The ifIndex assigned to this management NIF when it was created.
             This will not change until the NIF is deleted."
    ::= { sonusNrsMgmtIfEntry 1 }

sonusNrsMgmtIfShelf OBJECT-TYPE
    SYNTAX          SonusShelfIndex
    MAX-ACCESS      read-write
    STATUS          current
    DESCRIPTION     
            "A 32-bit integer identifying the shelf of the Management
             Interface"
    ::= { sonusNrsMgmtIfEntry 2 }

sonusNrsMgmtIfSlot OBJECT-TYPE
    SYNTAX          SonusSlotIndex
    MAX-ACCESS      read-write
    STATUS          current
    DESCRIPTION     
            "A 32-bit integer identifying the slot of the Management
             Interface"
    ::= { sonusNrsMgmtIfEntry 3 }

sonusNrsMgmtIfPort OBJECT-TYPE
    SYNTAX          Integer32 (1..4)
    MAX-ACCESS      read-write
    STATUS          current
    DESCRIPTION     
            "A 32-bit integer identifying the port of the Management
             Interface.  For MNS10 or MNS11 hardware this must be 1 or 2.
             For	MNS20 or MNS25 hardware this can be up to 4."
    ::= { sonusNrsMgmtIfEntry 4 }

sonusNrsMgmtIfCircuit OBJECT-TYPE
    SYNTAX          Integer32 (1)
    MAX-ACCESS      read-write
    STATUS          current
    DESCRIPTION     
            "A 32-bit integer identifying the circuit of the Management
             Interface.  For current hardware this must be 1."
    DEFVAL          { 1 }
    ::= { sonusNrsMgmtIfEntry 5 }

sonusNrsMgmtIfType OBJECT-TYPE
    SYNTAX          IANAifType
    MAX-ACCESS      read-only
    STATUS          current
    DESCRIPTION     
            "The type of interface, distinguished according to the
             physical/link protocol(s) immediately 'below' the network
             layer in the protocol stack.
             
             Values are from RFC1213 for the ifType object.
             
             Current hardware supports only the ethernet-csmacd (6)
             type."
    ::= { sonusNrsMgmtIfEntry 6 }

sonusNrsMgmtIfIpAddress OBJECT-TYPE
    SYNTAX          IpAddress
    MAX-ACCESS      read-write
    STATUS          current
    DESCRIPTION     
            "The IP Address of the Management Interface"
    ::= { sonusNrsMgmtIfEntry 7 }

sonusNrsMgmtIfIpMask OBJECT-TYPE
    SYNTAX          IpAddress
    MAX-ACCESS      read-write
    STATUS          current
    DESCRIPTION     
            "The IP subnet mask of this Management Interface."
    ::= { sonusNrsMgmtIfEntry 8 }

sonusNrsMgmtIfMtu OBJECT-TYPE
    SYNTAX          Integer32
    MAX-ACCESS      read-write
    STATUS          current
    DESCRIPTION     
            "The size of the largest datagram that can be sent/received
             on the interface, specified in octets."
    ::= { sonusNrsMgmtIfEntry 9 }

sonusNrsMgmtIfGatewayAddress OBJECT-TYPE
    SYNTAX          IpAddress
    MAX-ACCESS      read-write
    STATUS          current
    DESCRIPTION     
            "The IP address of the default gateway for this Management
             Interface."
    ::= { sonusNrsMgmtIfEntry 10 }

sonusNrsMgmtIfMode OBJECT-TYPE
    SYNTAX          INTEGER { standby(1), active(2) }
    MAX-ACCESS      read-write
    STATUS          obsolete
    DESCRIPTION     
            "The requested mode of the interface."
    ::= { sonusNrsMgmtIfEntry 11 }

sonusNrsMgmtIfAdminStatus OBJECT-TYPE
    SYNTAX          INTEGER { disabled(1), enabled(2) }
    MAX-ACCESS      read-write
    STATUS          current
    DESCRIPTION     
            "The requested status of the interface."
    ::= { sonusNrsMgmtIfEntry 12 }

sonusNrsMgmtIfOperStatus OBJECT-TYPE
    SYNTAX          INTEGER { outOfService(1), inService(2), 
                        outOfServiceDisabled(3), outOfServiceLinkDown(4) }
    MAX-ACCESS      read-only
    STATUS          current
    DESCRIPTION     
            "The actual status of the management interface.  A link will
             be InService if the sonusNrsMgmtIfAdminStatus is enabled and
             the physical link is up.  It will be OutOfService if the admin
             status is enabled but the physical link is down.  It will be
             OutOfServiceDisabled if the physical link is up but the admin
             status is disabled.  It will be OutOfServiceLinkDown if the
             physical link is down and the admin status is disabled."
    ::= { sonusNrsMgmtIfEntry 13 }

sonusNrsMgmtIfLogicMgmtIpAddress OBJECT-TYPE
    SYNTAX          IpAddress
    MAX-ACCESS      read-only
    STATUS          current
    DESCRIPTION     
            "The logical Mgmt IP address assigned to the mgmt interface if
             this mgmt interface is active and in service."
    ::= { sonusNrsMgmtIfEntry 14 }

sonusNrsMgmtIfName OBJECT-TYPE
    SYNTAX          SonusName
    MAX-ACCESS      read-only
    STATUS          current
    DESCRIPTION     
            "The assigned name for this MGMT Interface."
    ::= { sonusNrsMgmtIfEntry 15 }

sonusNrsMgmtIfDGPBucketSize OBJECT-TYPE
    SYNTAX          Integer32 (4096..65520)
    MAX-ACCESS      read-write
    STATUS          current
    DESCRIPTION     
            "The per MGMT IF dark gray policer bucket size, in bytes,
             used to policing all traffic that does not match a
             white list policer. The range is 4096 bytes to 65520
             bytes, in 16 byte increments. 0 to 128 pseudo-packets
             in 1/32 packet increments."
    ::= { sonusNrsMgmtIfEntry 16 }

sonusNrsMgmtIfDGPFillRate OBJECT-TYPE
    SYNTAX          Integer32 (2048..16776960)
    MAX-ACCESS      read-write
    STATUS          current
    DESCRIPTION     
            "The per MGMT IF dark gray policer fill rate, in bytes
             per second, used to policing all traffic that does 
             not match a white list policer. The range is 2048 
             bytes/sec to 16M bytes/second in increments of 
             256 bytes/sec, 0.5 to 32K pseudo-pps in increments 
             of 0.5 pps."
    ::= { sonusNrsMgmtIfEntry 17 }

sonusNrsMgmtIfDGPAdminState OBJECT-TYPE
    SYNTAX          INTEGER { disabled(1), enabled(2) }
    MAX-ACCESS      read-write
    STATUS          current
    DESCRIPTION     
            "Administrative state of dark gray policer."
    ::= { sonusNrsMgmtIfEntry 18 }

sonusNrsMgmtIfRowStatus OBJECT-TYPE
    SYNTAX          RowStatus
    MAX-ACCESS      read-write
    STATUS          current
    DESCRIPTION     
            ""
    ::= { sonusNrsMgmtIfEntry 19 }

sonusNrsMgmtIfIpv6Address OBJECT-TYPE
    SYNTAX          Ipv6Address
    MAX-ACCESS      read-write
    STATUS          current
    DESCRIPTION     
            "The IPV6 Address of the Management Interface"
    ::= { sonusNrsMgmtIfEntry 20 }

sonusNrsMgmtIfGatewayIpv6Address OBJECT-TYPE
    SYNTAX          Ipv6Address
    MAX-ACCESS      read-write
    STATUS          current
    DESCRIPTION     
            "The IP address of the default gateway for this Management
             Interface."
    ::= { sonusNrsMgmtIfEntry 21 }

sonusNrsMgmtIfIpv6Prefixlen OBJECT-TYPE
    SYNTAX          Integer32 (0..128)
    MAX-ACCESS      read-write
    STATUS          current
    DESCRIPTION     
            "Ipv6 Prefix Length"
    ::= { sonusNrsMgmtIfEntry 22 }

sonusNrsMgmtIfLogicMgmtIpv6Address OBJECT-TYPE
    SYNTAX          Ipv6Address
    MAX-ACCESS      read-only
    STATUS          current
    DESCRIPTION     
            "The logical Mgmt IPV6 address assigned to the mgmt interface if
             this mgmt interface is active and in service."
    ::= { sonusNrsMgmtIfEntry 23 }

sonusNrsMgmtIfLlIpv6Address OBJECT-TYPE
    SYNTAX          Ipv6Address
    MAX-ACCESS      read-only
    STATUS          current
    DESCRIPTION     
            "The Link local IPV6 Address assigned to the mgmt interface."
    ::= { sonusNrsMgmtIfEntry 24 }

sonusNrsLogicMgmtIfAdmnTable OBJECT-TYPE
    SYNTAX          SEQUENCE OF SonusNrsLogicMgmtIfAdmnEntry
    MAX-ACCESS      not-accessible
    STATUS          current
    DESCRIPTION     
            "The collection of logical IP addresses for the node"
    ::= { sonusIpInterfaceMIBObjects 8 }

sonusNrsLogicMgmtIfAdmnEntry OBJECT-TYPE
    SYNTAX          SonusNrsLogicMgmtIfAdmnEntry
    MAX-ACCESS      not-accessible
    STATUS          current
    DESCRIPTION     
            "The collection of logical IP addresses for the node"
    INDEX           { sonusNrsLogicMgmtIfAdmnShelf }
    ::= { sonusNrsLogicMgmtIfAdmnTable 1 }

SonusNrsLogicMgmtIfAdmnEntry ::=
    SEQUENCE {
        sonusNrsLogicMgmtIfAdmnShelf    SonusShelfIndex,
        sonusNrsLogicMgmtIfAdmnIpAddress IpAddress,
        sonusNrsLogicMgmtIfAdmnIpAddressB IpAddress,
        sonusNrsLogicMgmtIfAdmnIp6Address Ipv6Address,
        sonusNrsLogicMgmtIfAdmnIp6AddressB  Ipv6Address
    }

sonusNrsLogicMgmtIfAdmnShelf OBJECT-TYPE
    SYNTAX          SonusShelfIndex
    MAX-ACCESS      read-write
    STATUS          current
    DESCRIPTION     
            "A 32-bit integer identifying the shelf of the logical ip address assigned to"
    ::= { sonusNrsLogicMgmtIfAdmnEntry 1 }

sonusNrsLogicMgmtIfAdmnIpAddress OBJECT-TYPE
    SYNTAX          IpAddress
    MAX-ACCESS      read-write
    STATUS          current
    DESCRIPTION     
            "The Logical IP address of the shelf"
    ::= { sonusNrsLogicMgmtIfAdmnEntry 2 }

sonusNrsLogicMgmtIfAdmnIpAddressB OBJECT-TYPE
    SYNTAX          IpAddress
    MAX-ACCESS      read-write
    STATUS          current
    DESCRIPTION     
            "The second logical IP address for the shelf if the MNS ports are on the
             different subnet."
    ::= { sonusNrsLogicMgmtIfAdmnEntry 3 }

sonusNrsLogicMgmtIfAdmnIp6Address OBJECT-TYPE
    SYNTAX          Ipv6Address
    MAX-ACCESS      read-write
    STATUS          current
    DESCRIPTION     
            "The Logical IPV6 address of the shelf"
    ::= { sonusNrsLogicMgmtIfAdmnEntry 4 }

sonusNrsLogicMgmtIfAdmnIp6AddressB OBJECT-TYPE
    SYNTAX          Ipv6Address
    MAX-ACCESS      read-write
    STATUS          current
    DESCRIPTION     
            "The second logical IPV6 address for the shelf if the MNS ports are on the
             different subnet."
    ::= { sonusNrsLogicMgmtIfAdmnEntry 5 }

sonusNrsLinkFailureParamAdmnTable OBJECT-TYPE
    SYNTAX          SEQUENCE OF SonusNrsLinkFailureParamAdmnEntry
    MAX-ACCESS      not-accessible
    STATUS          deprecated
    DESCRIPTION     
            "This table is replaced by sonusNrsLinkFailureDetectionParamTable, sonusNrsLinkDetectionGroupTable, and sonusNrsLinkDetectionGroupClientTable "
    ::= { sonusIpInterfaceMIBObjects 9 }

sonusNrsLinkFailureParamAdmnEntry OBJECT-TYPE
    SYNTAX          SonusNrsLinkFailureParamAdmnEntry
    MAX-ACCESS      not-accessible
    STATUS          deprecated
    DESCRIPTION     
            "One set of parameters configured for a server"
    INDEX           { sonusNrsLinkFailureParamAdmnShelf, 
                      sonusNrsLinkFailureParamAdmnSlot }
    ::= { sonusNrsLinkFailureParamAdmnTable 1 }

SonusNrsLinkFailureParamAdmnEntry ::=
    SEQUENCE {
        sonusNrsLinkFailureParamAdmnShelf SonusShelfIndex,
        sonusNrsLinkFailureParamAdmnSlot SonusSlotIndex,
        sonusNrsLinkFailureParamAdmnThreshold     Integer32,
        sonusNrsLinkFailureParamAdmnRetries   Integer32,
        sonusNrsLinkFailureParamAdmnVerifyTimer       Integer32,
        sonusNrsLinkFailureParamAdmnReattemptTimer          Integer32,
        sonusNrsLinkFailureParamAdmnState INTEGER,
        sonusNrsLinkFailureParamAdmnSwitchTestState           INTEGER
    }

sonusNrsLinkFailureParamAdmnShelf OBJECT-TYPE
    SYNTAX          SonusShelfIndex
    MAX-ACCESS      read-only
    STATUS          deprecated
    DESCRIPTION     
            "The shelf index of the server"
    ::= { sonusNrsLinkFailureParamAdmnEntry 1 }

sonusNrsLinkFailureParamAdmnSlot OBJECT-TYPE
    SYNTAX          SonusSlotIndex
    MAX-ACCESS      read-only
    STATUS          deprecated
    DESCRIPTION     
            "The slot index of the server"
    ::= { sonusNrsLinkFailureParamAdmnEntry 2 }

sonusNrsLinkFailureParamAdmnThreshold OBJECT-TYPE
    SYNTAX          Integer32 (0..100)
    MAX-ACCESS      read-write
    STATUS          deprecated
    DESCRIPTION     
            "The number of failed port accepted before failing over the server.
             0 Threshold means the link/port failure will not trigger failover."
    ::= { sonusNrsLinkFailureParamAdmnEntry 3 }

sonusNrsLinkFailureParamAdmnRetries OBJECT-TYPE
    SYNTAX          Integer32 (0..10)
    MAX-ACCESS      read-write
    STATUS          deprecated
    DESCRIPTION     
            "The number of retries before declare the link failure"
    DEFVAL          { 2 }
    ::= { sonusNrsLinkFailureParamAdmnEntry 4 }

sonusNrsLinkFailureParamAdmnVerifyTimer OBJECT-TYPE
    SYNTAX          Integer32 (0..60000)
    MAX-ACCESS      read-write
    STATUS          deprecated
    DESCRIPTION     
            "The verify timer in ms unit defined when link is up"
    DEFVAL          { 500 }
    ::= { sonusNrsLinkFailureParamAdmnEntry 5 }

sonusNrsLinkFailureParamAdmnReattemptTimer OBJECT-TYPE
    SYNTAX          Integer32 (0..60000)
    MAX-ACCESS      read-write
    STATUS          deprecated
    DESCRIPTION     
            "The re-attempt timer in ms unit defined between retires"
    DEFVAL          { 250 }
    ::= { sonusNrsLinkFailureParamAdmnEntry 6 }

sonusNrsLinkFailureParamAdmnState OBJECT-TYPE
    SYNTAX          INTEGER { disabled(1), enabled(2) }
    MAX-ACCESS      read-write
    STATUS          deprecated
    DESCRIPTION     
            "The administrative state of turning on/off link failure detection."
    DEFVAL          { disabled }
    ::= { sonusNrsLinkFailureParamAdmnEntry 7 }

sonusNrsLinkFailureParamAdmnSwitchTestState OBJECT-TYPE
    SYNTAX          INTEGER { disabled(1), enabled(2) }
    MAX-ACCESS      read-write
    STATUS          deprecated
    DESCRIPTION     
            "The administrative state of turning on/off per-call-destination link failure testing."
    DEFVAL          { enabled }
    ::= { sonusNrsLinkFailureParamAdmnEntry 8 }

sonusNrsLinkFailureStatTable OBJECT-TYPE
    SYNTAX          SEQUENCE OF SonusNrsLinkFailureStatEntry
    MAX-ACCESS      not-accessible
    STATUS          current
    DESCRIPTION     
            "statistics for link failure detection"
    ::= { sonusIpInterfaceMIBObjects 10 }

sonusNrsLinkFailureStatEntry OBJECT-TYPE
    SYNTAX          SonusNrsLinkFailureStatEntry
    MAX-ACCESS      not-accessible
    STATUS          current
    DESCRIPTION     
            ""
    INDEX           { sonusNrsLinkFailureStatShelf, 
                      sonusNrsLinkFailureStatSlot }
    ::= { sonusNrsLinkFailureStatTable 1 }

SonusNrsLinkFailureStatEntry ::=
    SEQUENCE {
        sonusNrsLinkFailureStatShelf    SonusShelfIndex,
        sonusNrsLinkFailureStatSlot     SonusSlotIndex,
        sonusNrsLinkFailureStatFailures Integer32,
        sonusNrsLinkFailureStatRedundFailures     Integer32
    }

sonusNrsLinkFailureStatShelf OBJECT-TYPE
    SYNTAX          SonusShelfIndex
    MAX-ACCESS      read-only
    STATUS          current
    DESCRIPTION     
            "shelf index for target server"
    ::= { sonusNrsLinkFailureStatEntry 1 }

sonusNrsLinkFailureStatSlot OBJECT-TYPE
    SYNTAX          SonusSlotIndex
    MAX-ACCESS      read-only
    STATUS          current
    DESCRIPTION     
            "slot index for target server"
    ::= { sonusNrsLinkFailureStatEntry 2 }

sonusNrsLinkFailureStatFailures OBJECT-TYPE
    SYNTAX          Integer32
    MAX-ACCESS      read-only
    STATUS          current
    DESCRIPTION     
            "number of failures detected on this server"
    ::= { sonusNrsLinkFailureStatEntry 3 }

sonusNrsLinkFailureStatRedundFailures OBJECT-TYPE
    SYNTAX          Integer32
    MAX-ACCESS      read-only
    STATUS          current
    DESCRIPTION     
            "number of failures detected on the redundant server"
    ::= { sonusNrsLinkFailureStatEntry 4 }

sonusNrsPerDestLinkFailureStatTable OBJECT-TYPE
    SYNTAX          SEQUENCE OF SonusNrsPerDestLinkFailureStatEntry
    MAX-ACCESS      not-accessible
    STATUS          current
    DESCRIPTION     
            "statistics for link failure detected per destination"
    ::= { sonusIpInterfaceMIBObjects 11 }

sonusNrsPerDestLinkFailureStatEntry OBJECT-TYPE
    SYNTAX          SonusNrsPerDestLinkFailureStatEntry
    MAX-ACCESS      not-accessible
    STATUS          current
    DESCRIPTION     
            ""
    INDEX           { sonusNrsPerDestLinkFailureStatIfIndex, 
                      sonusNrsPerDestLinkFailureStatIpAddress, 
                      sonusNrsPerDestLinkFailureStatIp6Address, 
                      sonusNrsPerDestLinkFailureStatIpver }
    ::= { sonusNrsPerDestLinkFailureStatTable 1 }

SonusNrsPerDestLinkFailureStatEntry ::=
    SEQUENCE {
        sonusNrsPerDestLinkFailureStatIfIndex     Integer32,
        sonusNrsPerDestLinkFailureStatIpAddress       IpAddress,
        sonusNrsPerDestLinkFailureStatMinTime     Integer32,
        sonusNrsPerDestLinkFailureStatMaxTime     Integer32,
        sonusNrsPerDestLinkFailureStatAverageTime         Integer32,
        sonusNrsPerDestLinkFailureStatSumTime     Integer32,
        sonusNrsPerDestLinkFailureStat1Failure      Integer32,
        sonusNrsPerDestLinkFailureStat2Failure      Integer32,
        sonusNrsPerDestLinkFailureStatFailures      Integer32,
        sonusNrsPerDestLinkFailureStatReplies     Integer32,
        sonusNrsPerDestLinkFailureStatDupeReplies         Integer32,
        sonusNrsPerDestLinkFailureStatLateReplies         Integer32,
        sonusNrsPerDestLinkFailureStatIp6Address        Ipv6Address,
        sonusNrsPerDestLinkFailureStatIpver   INTEGER
    }

sonusNrsPerDestLinkFailureStatIfIndex OBJECT-TYPE
    SYNTAX          Integer32
    MAX-ACCESS      read-only
    STATUS          current
    DESCRIPTION     
            "The ifindex"
    ::= { sonusNrsPerDestLinkFailureStatEntry 1 }

sonusNrsPerDestLinkFailureStatIpAddress OBJECT-TYPE
    SYNTAX          IpAddress
    MAX-ACCESS      read-only
    STATUS          current
    DESCRIPTION     
            "The destination IP address."
    ::= { sonusNrsPerDestLinkFailureStatEntry 2 }

sonusNrsPerDestLinkFailureStatMinTime OBJECT-TYPE
    SYNTAX          Integer32
    MAX-ACCESS      read-only
    STATUS          current
    DESCRIPTION     
            "The minimum time used for get reply for a echo request packet."
    ::= { sonusNrsPerDestLinkFailureStatEntry 3 }

sonusNrsPerDestLinkFailureStatMaxTime OBJECT-TYPE
    SYNTAX          Integer32
    MAX-ACCESS      read-only
    STATUS          current
    DESCRIPTION     
            "The maximum time used for get reply for a echo request packet."
    ::= { sonusNrsPerDestLinkFailureStatEntry 4 }

sonusNrsPerDestLinkFailureStatAverageTime OBJECT-TYPE
    SYNTAX          Integer32
    MAX-ACCESS      read-only
    STATUS          current
    DESCRIPTION     
            "The average time used for get reply for a echo request packet."
    ::= { sonusNrsPerDestLinkFailureStatEntry 5 }

sonusNrsPerDestLinkFailureStatSumTime OBJECT-TYPE
    SYNTAX          Integer32
    MAX-ACCESS      read-only
    STATUS          current
    DESCRIPTION     
            "The summary of time"
    ::= { sonusNrsPerDestLinkFailureStatEntry 6 }

sonusNrsPerDestLinkFailureStat1Failure OBJECT-TYPE
    SYNTAX          Integer32
    MAX-ACCESS      read-only
    STATUS          current
    DESCRIPTION     
            "The number of single failures for this destination."
    ::= { sonusNrsPerDestLinkFailureStatEntry 7 }

sonusNrsPerDestLinkFailureStat2Failure OBJECT-TYPE
    SYNTAX          Integer32
    MAX-ACCESS      read-only
    STATUS          current
    DESCRIPTION     
            "The number of double failures for this destination."
    ::= { sonusNrsPerDestLinkFailureStatEntry 8 }

sonusNrsPerDestLinkFailureStatFailures OBJECT-TYPE
    SYNTAX          Integer32
    MAX-ACCESS      read-only
    STATUS          current
    DESCRIPTION     
            "The number of >2 failures for this destination."
    ::= { sonusNrsPerDestLinkFailureStatEntry 9 }

sonusNrsPerDestLinkFailureStatReplies OBJECT-TYPE
    SYNTAX          Integer32
    MAX-ACCESS      read-only
    STATUS          current
    DESCRIPTION     
            "The number of replies"
    ::= { sonusNrsPerDestLinkFailureStatEntry 10 }

sonusNrsPerDestLinkFailureStatDupeReplies OBJECT-TYPE
    SYNTAX          Integer32
    MAX-ACCESS      read-only
    STATUS          current
    DESCRIPTION     
            "The number of dupe replies"
    ::= { sonusNrsPerDestLinkFailureStatEntry 11 }

sonusNrsPerDestLinkFailureStatLateReplies OBJECT-TYPE
    SYNTAX          Integer32
    MAX-ACCESS      read-only
    STATUS          current
    DESCRIPTION     
            "The number of late replies."
    ::= { sonusNrsPerDestLinkFailureStatEntry 12 }

sonusNrsPerDestLinkFailureStatIp6Address OBJECT-TYPE
    SYNTAX          Ipv6Address
    MAX-ACCESS      read-write
    STATUS          current
    DESCRIPTION     
            "The Stat IPv6 address"
    ::= { sonusNrsPerDestLinkFailureStatEntry 13 }

sonusNrsPerDestLinkFailureStatIpver OBJECT-TYPE
    SYNTAX          INTEGER { afInet(2), afInet6(24) }
    MAX-ACCESS      read-only
    STATUS          current
    DESCRIPTION     
            "IP Address Type"
    ::= { sonusNrsPerDestLinkFailureStatEntry 14 }

sonusSrvrEthernetSwitchIpTable OBJECT-TYPE
    SYNTAX          SEQUENCE OF SonusSrvrEthernetSwitchIpEntry
    MAX-ACCESS      not-accessible
    STATUS          current
    DESCRIPTION     
            "The table of ethernet switch IP address for servers"
    ::= { sonusIpInterfaceMIBObjects 12 }

sonusSrvrEthernetSwitchIpEntry OBJECT-TYPE
    SYNTAX          SonusSrvrEthernetSwitchIpEntry
    MAX-ACCESS      not-accessible
    STATUS          current
    DESCRIPTION     
            "ethernet switch IP address for a server"
    INDEX           { sonusSrvrEthernetSwitchIpShelf, 
                      sonusSrvrEthernetSwitchIpSlot, 
                      sonusSrvrEthernetSwitchIpPort }
    ::= { sonusSrvrEthernetSwitchIpTable 1 }

SonusSrvrEthernetSwitchIpEntry ::=
    SEQUENCE {
        sonusSrvrEthernetSwitchIpShelf  SonusShelfIndex,
        sonusSrvrEthernetSwitchIpSlot   SonusSlotIndex,
        sonusSrvrEthernetSwitchIpIpAddress  IpAddress,
        sonusSrvrEthernetSwitchIpPort   Integer32,
        sonusSrvrEthernetSwitchIp6IpAddress   Ipv6Address,
        sonusSrvrEthernetSwitchIpVer    INTEGER
    }

sonusSrvrEthernetSwitchIpShelf OBJECT-TYPE
    SYNTAX          SonusShelfIndex
    MAX-ACCESS      read-only
    STATUS          current
    DESCRIPTION     
            "The shelf index of the server"
    ::= { sonusSrvrEthernetSwitchIpEntry 1 }

sonusSrvrEthernetSwitchIpSlot OBJECT-TYPE
    SYNTAX          SonusSlotIndex
    MAX-ACCESS      read-only
    STATUS          current
    DESCRIPTION     
            "The slot index of the server"
    ::= { sonusSrvrEthernetSwitchIpEntry 2 }

sonusSrvrEthernetSwitchIpIpAddress OBJECT-TYPE
    SYNTAX          IpAddress
    MAX-ACCESS      read-write
    STATUS          current
    DESCRIPTION     
            "The ethernet switch IP address for this server."
    ::= { sonusSrvrEthernetSwitchIpEntry 3 }

sonusSrvrEthernetSwitchIpPort OBJECT-TYPE
    SYNTAX          Integer32 (0..65535)
    MAX-ACCESS      read-write
    STATUS          current
    DESCRIPTION     
            "The port index of the server"
    ::= { sonusSrvrEthernetSwitchIpEntry 4 }

sonusSrvrEthernetSwitchIp6IpAddress OBJECT-TYPE
    SYNTAX          Ipv6Address
    MAX-ACCESS      read-write
    STATUS          current
    DESCRIPTION     
            "The ethernet switch IPv6 address for this server."
    ::= { sonusSrvrEthernetSwitchIpEntry 5 }

sonusSrvrEthernetSwitchIpVer OBJECT-TYPE
    SYNTAX          INTEGER { afInet(2), afInet6(24) }
    MAX-ACCESS      read-only
    STATUS          current
    DESCRIPTION     
            "IP Address Type"
    ::= { sonusSrvrEthernetSwitchIpEntry 6 }

sonusNrsSocketAccessAdmnTable OBJECT-TYPE
    SYNTAX          SEQUENCE OF SonusNrsSocketAccessAdmnEntry
    MAX-ACCESS      not-accessible
    STATUS          deprecated
    DESCRIPTION     
            "The table of socket access definitions. These access
             definitions are subsumed (and hence made redundant)
             by IP input filters."
    ::= { sonusIpInterfaceMIBObjects 13 }

sonusNrsSocketAccessAdmnEntry OBJECT-TYPE
    SYNTAX          SonusNrsSocketAccessAdmnEntry
    MAX-ACCESS      not-accessible
    STATUS          deprecated
    DESCRIPTION     
            "socket access definition for a server"
    INDEX           { sonusNrsSocketAccessProtocol, 
                      sonusNrsSocketAccessPort, 
                      sonusNrsSocketAccessIfIndex }
    ::= { sonusNrsSocketAccessAdmnTable 1 }

SonusNrsSocketAccessAdmnEntry ::=
    SEQUENCE {
        sonusNrsSocketAccessProtocol    INTEGER,
        sonusNrsSocketAccessPort        Integer32,
        sonusNrsSocketAccessIfIndex     Integer32,
        sonusNrsSocketAccessPermission  INTEGER,
        sonusNrsSocketAccessRowStatus   RowStatus
    }

sonusNrsSocketAccessProtocol OBJECT-TYPE
    SYNTAX          INTEGER { tcp(6), udp(17) }
    MAX-ACCESS      read-only
    STATUS          deprecated
    DESCRIPTION     
            "The protocol definition"
    DEFVAL          { tcp }
    ::= { sonusNrsSocketAccessAdmnEntry 1 }

sonusNrsSocketAccessPort OBJECT-TYPE
    SYNTAX          Integer32 (1..65535)
    MAX-ACCESS      read-only
    STATUS          deprecated
    DESCRIPTION     
            "The port number, value between 1-65535"
    ::= { sonusNrsSocketAccessAdmnEntry 2 }

sonusNrsSocketAccessIfIndex OBJECT-TYPE
    SYNTAX          Integer32 (1..65535)
    MAX-ACCESS      read-only
    STATUS          deprecated
    DESCRIPTION     
            "A non-zero unsigned long ifindex assigned to the port where defines the access permition."
    ::= { sonusNrsSocketAccessAdmnEntry 3 }

sonusNrsSocketAccessPermission OBJECT-TYPE
    SYNTAX          INTEGER { deny(1), permit(2) }
    MAX-ACCESS      read-write
    STATUS          deprecated
    DESCRIPTION     
            "The access permission"
    DEFVAL          { permit }
    ::= { sonusNrsSocketAccessAdmnEntry 4 }

sonusNrsSocketAccessRowStatus OBJECT-TYPE
    SYNTAX          RowStatus
    MAX-ACCESS      read-write
    STATUS          deprecated
    DESCRIPTION     
            ""
    ::= { sonusNrsSocketAccessAdmnEntry 5 }

sonusNrsPortRedundancyGroup OBJECT IDENTIFIER
    ::= { sonusIpInterfaceMIBObjects 14 }

sonusNrsPortRedundancyGroupNextIndex OBJECT-TYPE
    SYNTAX          Integer32
    MAX-ACCESS      read-only
    STATUS          current
    DESCRIPTION     
            "The next valid index to use when creating an entry in sonusNrsPortRedundancyGroupAdmnTable"
    ::= { sonusNrsPortRedundancyGroup 1 }

sonusNrsPortRedundancyGroupAdmnTable OBJECT-TYPE
    SYNTAX          SEQUENCE OF SonusNrsPortRedundancyGroupAdmnEntry
    MAX-ACCESS      not-accessible
    STATUS          current
    DESCRIPTION     
            "The table of user configured port redundancy group"
    ::= { sonusNrsPortRedundancyGroup 2 }

sonusNrsPortRedundancyGroupAdmnEntry OBJECT-TYPE
    SYNTAX          SonusNrsPortRedundancyGroupAdmnEntry
    MAX-ACCESS      not-accessible
    STATUS          current
    DESCRIPTION     
            "a collection of port redundancy group configured"
    INDEX           { sonusNrsPortRedundancyGroupIndex }
    ::= { sonusNrsPortRedundancyGroupAdmnTable 1 }

SonusNrsPortRedundancyGroupAdmnEntry ::=
    SEQUENCE {
        sonusNrsPortRedundancyGroupIndex Integer32,
        sonusNrsPortRedundancyGroupName SonusName,
        sonusNrsPortRedundancyGroupShelf SonusShelfIndex,
        sonusNrsPortRedundancyGroupSlot SonusSlotIndex,
        sonusNrsPortRedundancyGroupLayer INTEGER,
        sonusNrsPortRedundancyGroupRowStatus    RowStatus
    }

sonusNrsPortRedundancyGroupIndex OBJECT-TYPE
    SYNTAX          Integer32
    MAX-ACCESS      read-only
    STATUS          current
    DESCRIPTION     
            "The index assigned to this port redundancy group when it
             was created."
    ::= { sonusNrsPortRedundancyGroupAdmnEntry 1 }

sonusNrsPortRedundancyGroupName OBJECT-TYPE
    SYNTAX          SonusName
    MAX-ACCESS      read-write
    STATUS          current
    DESCRIPTION     
            "The administrative name of the port redundancy group"
    ::= { sonusNrsPortRedundancyGroupAdmnEntry 2 }

sonusNrsPortRedundancyGroupShelf OBJECT-TYPE
    SYNTAX          SonusShelfIndex
    MAX-ACCESS      read-write
    STATUS          current
    DESCRIPTION     
            "A 32-bit integer identifying the shelf"
    ::= { sonusNrsPortRedundancyGroupAdmnEntry 3 }

sonusNrsPortRedundancyGroupSlot OBJECT-TYPE
    SYNTAX          SonusSlotIndex
    MAX-ACCESS      read-write
    STATUS          current
    DESCRIPTION     
            "A 32-bit integer identifying the slot"
    ::= { sonusNrsPortRedundancyGroupAdmnEntry 4 }

sonusNrsPortRedundancyGroupLayer OBJECT-TYPE
    SYNTAX          INTEGER { enetLayer2(1), enetLayer3(2) }
    MAX-ACCESS      read-write
    STATUS          current
    DESCRIPTION     
            "redundancy layer definition"
    DEFVAL          { enetLayer2 }
    ::= { sonusNrsPortRedundancyGroupAdmnEntry 5 }

sonusNrsPortRedundancyGroupRowStatus OBJECT-TYPE
    SYNTAX          RowStatus
    MAX-ACCESS      read-write
    STATUS          current
    DESCRIPTION     
            ""
    ::= { sonusNrsPortRedundancyGroupAdmnEntry 6 }

sonusNrsPortRedundancyGroupClient OBJECT IDENTIFIER
    ::= { sonusIpInterfaceMIBObjects 15 }

sonusNrsPortRedundancyGroupClientTable OBJECT-TYPE
    SYNTAX          SEQUENCE OF SonusNrsPortRedundancyGroupClientEntry
    MAX-ACCESS      not-accessible
    STATUS          current
    DESCRIPTION     
            "This table specifies the port redundancy group client list."
    ::= { sonusNrsPortRedundancyGroupClient 1 }

sonusNrsPortRedundancyGroupClientEntry OBJECT-TYPE
    SYNTAX          SonusNrsPortRedundancyGroupClientEntry
    MAX-ACCESS      not-accessible
    STATUS          current
    DESCRIPTION     
            ""
    INDEX           { sonusNrsPortRedundancyGroupClientIndex, 
                      sonusNrsPortRedundancyGroupClientPort }
    ::= { sonusNrsPortRedundancyGroupClientTable 1 }

SonusNrsPortRedundancyGroupClientEntry ::=
    SEQUENCE {
        sonusNrsPortRedundancyGroupClientIndex      Integer32,
        sonusNrsPortRedundancyGroupClientPort     Integer32,
        sonusNrsPortRedundancyGroupClientRowStatus          RowStatus
    }

sonusNrsPortRedundancyGroupClientIndex OBJECT-TYPE
    SYNTAX          Integer32
    MAX-ACCESS      read-only
    STATUS          current
    DESCRIPTION     
            "The index of the port redundancy group to which this client belongs to."
    ::= { sonusNrsPortRedundancyGroupClientEntry 1 }

sonusNrsPortRedundancyGroupClientPort OBJECT-TYPE
    SYNTAX          Integer32
    MAX-ACCESS      read-only
    STATUS          current
    DESCRIPTION     
            "The port id of this client entry"
    ::= { sonusNrsPortRedundancyGroupClientEntry 2 }

sonusNrsPortRedundancyGroupClientRowStatus OBJECT-TYPE
    SYNTAX          RowStatus
    MAX-ACCESS      read-write
    STATUS          current
    DESCRIPTION     
            ""
    ::= { sonusNrsPortRedundancyGroupClientEntry 3 }

sonusNrsLinkDetectionGroup OBJECT IDENTIFIER
    ::= { sonusIpInterfaceMIBObjects 16 }

sonusNrsLinkDetectionGroupNextIndex OBJECT-TYPE
    SYNTAX          Integer32
    MAX-ACCESS      read-only
    STATUS          current
    DESCRIPTION     
            "The next valid index to use when creating an entry in sonusNrsLinkDetectionGroupTable"
    ::= { sonusNrsLinkDetectionGroup 1 }

sonusNrsLinkDetectionGroupTable OBJECT-TYPE
    SYNTAX          SEQUENCE OF SonusNrsLinkDetectionGroupEntry
    MAX-ACCESS      not-accessible
    STATUS          current
    DESCRIPTION     
            "The table of user configured link detection group"
    ::= { sonusNrsLinkDetectionGroup 2 }

sonusNrsLinkDetectionGroupEntry OBJECT-TYPE
    SYNTAX          SonusNrsLinkDetectionGroupEntry
    MAX-ACCESS      not-accessible
    STATUS          current
    DESCRIPTION     
            "a collection of link detection group"
    INDEX           { sonusNrsLinkDetectionGroupIndex }
    ::= { sonusNrsLinkDetectionGroupTable 1 }

SonusNrsLinkDetectionGroupEntry ::=
    SEQUENCE {
        sonusNrsLinkDetectionGroupIndex Integer32,
        sonusNrsLinkDetectionGroupName  SonusName,
        sonusNrsLinkDetectionGroupShelf SonusShelfIndex,
        sonusNrsLinkDetectionGroupSlot  SonusSlotIndex,
        sonusNrsLinkDetectionGroupThreshold   Integer32,
        sonusNrsLinkDetectionGroupRowStatus   RowStatus
    }

sonusNrsLinkDetectionGroupIndex OBJECT-TYPE
    SYNTAX          Integer32
    MAX-ACCESS      read-only
    STATUS          current
    DESCRIPTION     
            "The index assigned to this link detection group when it was created"
    ::= { sonusNrsLinkDetectionGroupEntry 1 }

sonusNrsLinkDetectionGroupName OBJECT-TYPE
    SYNTAX          SonusName
    MAX-ACCESS      read-write
    STATUS          current
    DESCRIPTION     
            "The administrative name of the link detection group"
    ::= { sonusNrsLinkDetectionGroupEntry 2 }

sonusNrsLinkDetectionGroupShelf OBJECT-TYPE
    SYNTAX          SonusShelfIndex
    MAX-ACCESS      read-write
    STATUS          current
    DESCRIPTION     
            "A 32-bit integer identifying the shelf"
    ::= { sonusNrsLinkDetectionGroupEntry 3 }

sonusNrsLinkDetectionGroupSlot OBJECT-TYPE
    SYNTAX          SonusSlotIndex
    MAX-ACCESS      read-write
    STATUS          current
    DESCRIPTION     
            "A 32-bit integer identifying the slot"
    ::= { sonusNrsLinkDetectionGroupEntry 4 }

sonusNrsLinkDetectionGroupThreshold OBJECT-TYPE
    SYNTAX          Integer32 (0..10)
    MAX-ACCESS      read-write
    STATUS          current
    DESCRIPTION     
            "link detection group threshold"
    ::= { sonusNrsLinkDetectionGroupEntry 5 }

sonusNrsLinkDetectionGroupRowStatus OBJECT-TYPE
    SYNTAX          RowStatus
    MAX-ACCESS      read-write
    STATUS          current
    DESCRIPTION     
            ""
    ::= { sonusNrsLinkDetectionGroupEntry 6 }

sonusNrsLinkDetectionGroupClient OBJECT IDENTIFIER
    ::= { sonusIpInterfaceMIBObjects 17 }

sonusNrsLinkDetectionGroupClientTable OBJECT-TYPE
    SYNTAX          SEQUENCE OF SonusNrsLinkDetectionGroupClientEntry
    MAX-ACCESS      not-accessible
    STATUS          current
    DESCRIPTION     
            "This table specifies the link detection group client list."
    ::= { sonusNrsLinkDetectionGroupClient 1 }

sonusNrsLinkDetectionGroupClientEntry OBJECT-TYPE
    SYNTAX          SonusNrsLinkDetectionGroupClientEntry
    MAX-ACCESS      not-accessible
    STATUS          current
    DESCRIPTION     
            ""
    INDEX           { sonusNrsLinkDetectionGroupClientIndex, 
                      sonusNrsLinkDetectionGroupClientPort }
    ::= { sonusNrsLinkDetectionGroupClientTable 1 }

SonusNrsLinkDetectionGroupClientEntry ::=
    SEQUENCE {
        sonusNrsLinkDetectionGroupClientIndex     Integer32,
        sonusNrsLinkDetectionGroupClientPort    Integer32,
        sonusNrsLinkDetectionGroupClientRowStatus         RowStatus
    }

sonusNrsLinkDetectionGroupClientIndex OBJECT-TYPE
    SYNTAX          Integer32
    MAX-ACCESS      read-only
    STATUS          current
    DESCRIPTION     
            "The index of the link detection group to which this client belongs to."
    ::= { sonusNrsLinkDetectionGroupClientEntry 1 }

sonusNrsLinkDetectionGroupClientPort OBJECT-TYPE
    SYNTAX          Integer32
    MAX-ACCESS      read-write
    STATUS          current
    DESCRIPTION     
            "The port id of this client entry"
    ::= { sonusNrsLinkDetectionGroupClientEntry 2 }

sonusNrsLinkDetectionGroupClientRowStatus OBJECT-TYPE
    SYNTAX          RowStatus
    MAX-ACCESS      read-write
    STATUS          current
    DESCRIPTION     
            ""
    ::= { sonusNrsLinkDetectionGroupClientEntry 3 }

sonusNrsLinkFailureDetectionParamTable OBJECT-TYPE
    SYNTAX          SEQUENCE OF SonusNrsLinkFailureDetectionParamEntry
    MAX-ACCESS      not-accessible
    STATUS          current
    DESCRIPTION     
            "The table of user configured parameters for link failure detection"
    ::= { sonusIpInterfaceMIBObjects 18 }

sonusNrsLinkFailureDetectionParamEntry OBJECT-TYPE
    SYNTAX          SonusNrsLinkFailureDetectionParamEntry
    MAX-ACCESS      not-accessible
    STATUS          current
    DESCRIPTION     
            "One set of parameters configured for link failure detection"
    INDEX           { sonusNrsLinkFailureDetectionParamShelfIndex, 
                      sonusNrsLinkFailureDetectionParamSlotIndex, 
                      sonusNrsLinkFailureDetectionParamPortIndex }
    ::= { sonusNrsLinkFailureDetectionParamTable 1 }

SonusNrsLinkFailureDetectionParamEntry ::=
    SEQUENCE {
        sonusNrsLinkFailureDetectionParamShelfIndex           SonusShelfIndex,
        sonusNrsLinkFailureDetectionParamSlotIndex          SonusSlotIndex,
        sonusNrsLinkFailureDetectionParamPortIndex          Integer32,
        sonusNrsLinkFailureDetectionParamRetries        Integer32,
        sonusNrsLinkFailureDetectionParamVerifyTimer            Integer32,
        sonusNrsLinkFailureDetectionParamReattemptTimer               Integer32,
        sonusNrsLinkFailureDetectionParamState      INTEGER,
        sonusNrsLinkFailureDetectionParamSwitchTestState                INTEGER
    }

sonusNrsLinkFailureDetectionParamShelfIndex OBJECT-TYPE
    SYNTAX          SonusShelfIndex
    MAX-ACCESS      read-write
    STATUS          current
    DESCRIPTION     
            "The shelf Index"
    ::= { sonusNrsLinkFailureDetectionParamEntry 1 }

sonusNrsLinkFailureDetectionParamSlotIndex OBJECT-TYPE
    SYNTAX          SonusSlotIndex
    MAX-ACCESS      read-write
    STATUS          current
    DESCRIPTION     
            "The slot index"
    ::= { sonusNrsLinkFailureDetectionParamEntry 2 }

sonusNrsLinkFailureDetectionParamPortIndex OBJECT-TYPE
    SYNTAX          Integer32 (1..4)
    MAX-ACCESS      read-write
    STATUS          current
    DESCRIPTION     
            "The port index"
    ::= { sonusNrsLinkFailureDetectionParamEntry 3 }

sonusNrsLinkFailureDetectionParamRetries OBJECT-TYPE
    SYNTAX          Integer32 (0..10)
    MAX-ACCESS      read-write
    STATUS          current
    DESCRIPTION     
            "The number of retries before declare the link failure"
    DEFVAL          { 2 }
    ::= { sonusNrsLinkFailureDetectionParamEntry 4 }

sonusNrsLinkFailureDetectionParamVerifyTimer OBJECT-TYPE
    SYNTAX          Integer32 (0..60000)
    MAX-ACCESS      read-write
    STATUS          current
    DESCRIPTION     
            "The verify timer in ms unit defined when link is up"
    DEFVAL          { 500 }
    ::= { sonusNrsLinkFailureDetectionParamEntry 5 }

sonusNrsLinkFailureDetectionParamReattemptTimer OBJECT-TYPE
    SYNTAX          Integer32 (0..60000)
    MAX-ACCESS      read-write
    STATUS          current
    DESCRIPTION     
            "The re-attempt timer in ms unit defined between retires"
    DEFVAL          { 250 }
    ::= { sonusNrsLinkFailureDetectionParamEntry 6 }

sonusNrsLinkFailureDetectionParamState OBJECT-TYPE
    SYNTAX          INTEGER { disabled(1), enabled(2) }
    MAX-ACCESS      read-write
    STATUS          current
    DESCRIPTION     
            "The administrative state of turning on/off link failure detection."
    DEFVAL          { disabled }
    ::= { sonusNrsLinkFailureDetectionParamEntry 7 }

sonusNrsLinkFailureDetectionParamSwitchTestState OBJECT-TYPE
    SYNTAX          INTEGER { disabled(1), enabled(2) }
    MAX-ACCESS      read-write
    STATUS          current
    DESCRIPTION     
            "The administrative state of turning on/off per-call-destination link failure testing."
    DEFVAL          { enabled }
    ::= { sonusNrsLinkFailureDetectionParamEntry 8 }

sonusNrsLogicalSigAddressBindingTable OBJECT-TYPE
    SYNTAX          SEQUENCE OF SonusNrsLogicalSigAddressBindingEntry
    MAX-ACCESS      not-accessible
    STATUS          current
    DESCRIPTION     
            "The collection of logical signaling address bindings"
    ::= { sonusIpInterfaceMIBObjects 19 }

sonusNrsLogicalSigAddressBindingEntry OBJECT-TYPE
    SYNTAX          SonusNrsLogicalSigAddressBindingEntry
    MAX-ACCESS      not-accessible
    STATUS          current
    DESCRIPTION     
            "The collection of NRS Logical Signaling Address Binding 
             information for the specified instance."
    INDEX           { sonusNrsLogicalSigAddressBindingNifIndex, 
                      sonusNrsLogicalSigAddressBindingLSindex }
    ::= { sonusNrsLogicalSigAddressBindingTable 1 }

SonusNrsLogicalSigAddressBindingEntry ::=
    SEQUENCE {
        sonusNrsLogicalSigAddressBindingNifIndex        Integer32,
        sonusNrsLogicalSigAddressBindingLSindex       Integer32,
        sonusNrsLogicalSigAddressBindingAddress       IpAddress,
        sonusNrsLogicalSigAddressBindingIp6Address          Ipv6Address,
        sonusNrsLogicalSigAddressBindingAddressVersion              INTEGER
    }

sonusNrsLogicalSigAddressBindingNifIndex OBJECT-TYPE
    SYNTAX          Integer32
    MAX-ACCESS      read-only
    STATUS          current
    DESCRIPTION     
            "Interface index of the Nif this logical address was bound
             to"
    ::= { sonusNrsLogicalSigAddressBindingEntry 1 }

sonusNrsLogicalSigAddressBindingLSindex OBJECT-TYPE
    SYNTAX          Integer32
    MAX-ACCESS      read-only
    STATUS          current
    DESCRIPTION     
            "Index into the list of logical addresses on a given NIF"
    ::= { sonusNrsLogicalSigAddressBindingEntry 2 }

sonusNrsLogicalSigAddressBindingAddress OBJECT-TYPE
    SYNTAX          IpAddress
    MAX-ACCESS      read-only
    STATUS          current
    DESCRIPTION     
            "The instantiated logical signaling address bound to the
             NIF"
    ::= { sonusNrsLogicalSigAddressBindingEntry 3 }

sonusNrsLogicalSigAddressBindingIp6Address OBJECT-TYPE
    SYNTAX          Ipv6Address
    MAX-ACCESS      read-only
    STATUS          current
    DESCRIPTION     
            "The instantiated logical signaling Ipv6 address bound to the
             NIF"
    ::= { sonusNrsLogicalSigAddressBindingEntry 4 }

sonusNrsLogicalSigAddressBindingAddressVersion OBJECT-TYPE
    SYNTAX          INTEGER { afInet(2), afInet6(24) }
    MAX-ACCESS      read-only
    STATUS          current
    DESCRIPTION     
            "The instantiated logical signaling address version bound to the
             NIF"
    ::= { sonusNrsLogicalSigAddressBindingEntry 5 }

sonusNrsSubInterface OBJECT IDENTIFIER
    ::= { sonusIpInterfaceMIBObjects 20 }

sonusNrsSubInterfaceNextIndex OBJECT-TYPE
    SYNTAX          Integer32
    MAX-ACCESS      read-only
    STATUS          current
    DESCRIPTION     
            "The next valid index to use when creating an entry in
             the sonusNrsSubInterfaceTable."
    ::= { sonusNrsSubInterface 1 }

sonusNrsSubInterfaceTable OBJECT-TYPE
    SYNTAX          SEQUENCE OF SonusNrsSubInterfaceEntry
    MAX-ACCESS      not-accessible
    STATUS          current
    DESCRIPTION     
            "The collection of sub-interfaces"
    ::= { sonusNrsSubInterface 2 }

sonusNrsSubInterfaceEntry OBJECT-TYPE
    SYNTAX          SonusNrsSubInterfaceEntry
    MAX-ACCESS      not-accessible
    STATUS          current
    DESCRIPTION     
            "The collection of sub-interfaces"
    INDEX           { sonusNrsSubInterfaceIfIndex }
    ::= { sonusNrsSubInterfaceTable 1 }

SonusNrsSubInterfaceEntry ::=
    SEQUENCE {
        sonusNrsSubInterfaceIfIndex     Integer32,
        sonusNrsSubInterfaceName        SonusName,
        sonusNrsSubInterfaceNifIndex    Integer32,
        sonusNrsSubInterfaceVlanTag     Integer32,
        sonusNrsSubInterfaceIpAddress   IpAddress,
        sonusNrsSubInterfaceIpMask      IpAddress,
        sonusNrsSubInterfaceNexthopAddress  IpAddress,
        sonusNrsSubInterfaceType        INTEGER,
        sonusNrsSubInterfaceMode        INTEGER,
        sonusNrsSubInterfaceAction      INTEGER,
        sonusNrsSubInterfaceTimeout     Integer32,
        sonusNrsSubInterfaceMtu         Integer32,
        sonusNrsSubInterfaceOOSReason   INTEGER,
        sonusNrsSubInterfaceBwDeviation Integer32,
        sonusNrsSubInterfaceBwContingency Integer32,
        sonusNrsSubInterfaceBw          Integer32,
        sonusNrsSubInterfaceState       INTEGER,
        sonusNrsSubInterfaceRowStatus   RowStatus,
        sonusNrsSubInterfaceNifShelf    SonusShelfIndex,
        sonusNrsSubInterfaceNifSlot     SonusSlotIndex,
        sonusNrsSubInterfaceNifPort     Integer32,
        sonusNrsSubInterfaceVLanPBucketSize   Integer32,
        sonusNrsSubInterfaceVLanPFillRate Integer32,
        sonusNrsSubInterfaceIpSecPolicyName   DisplayString,
        sonusNrsSubInterfaceIpv6Address Ipv6Address,
        sonusNrsSubInterfaceIpv6NextHop Ipv6Address,
        sonusNrsSubInterfaceIpv6PrefixLength    Integer32,
        sonusNrsSubInterfaceIpv6PrefixMask  Ipv6Address,
        sonusNrsSubInterfaceLlIpv6Address Ipv6Address
    }

sonusNrsSubInterfaceIfIndex OBJECT-TYPE
    SYNTAX          Integer32
    MAX-ACCESS      read-only
    STATUS          current
    DESCRIPTION     
            "The ifindex assigned to this sub-interface when it was created.
             This will not change until the sub-interface is deleted.."
    ::= { sonusNrsSubInterfaceEntry 1 }

sonusNrsSubInterfaceName OBJECT-TYPE
    SYNTAX          SonusName
    MAX-ACCESS      read-write
    STATUS          current
    DESCRIPTION     
            "The administrative name of the sub-interface."
    ::= { sonusNrsSubInterfaceEntry 2 }

sonusNrsSubInterfaceNifIndex OBJECT-TYPE
    SYNTAX          Integer32
    MAX-ACCESS      read-write
    STATUS          current
    DESCRIPTION     
            "The ifindex assigned to NIF of this sub-interface."
    ::= { sonusNrsSubInterfaceEntry 3 }

sonusNrsSubInterfaceVlanTag OBJECT-TYPE
    SYNTAX          Integer32 (1..4095)
    MAX-ACCESS      read-write
    STATUS          current
    DESCRIPTION     
            "The VLAN TAG assigned to this sub-interface."
    ::= { sonusNrsSubInterfaceEntry 4 }

sonusNrsSubInterfaceIpAddress OBJECT-TYPE
    SYNTAX          IpAddress
    MAX-ACCESS      read-write
    STATUS          current
    DESCRIPTION     
            "The IP Address of the sub-interface"
    ::= { sonusNrsSubInterfaceEntry 5 }

sonusNrsSubInterfaceIpMask OBJECT-TYPE
    SYNTAX          IpAddress
    MAX-ACCESS      read-write
    STATUS          current
    DESCRIPTION     
            "The IP subnet mask of the sub-interface"
    ::= { sonusNrsSubInterfaceEntry 6 }

sonusNrsSubInterfaceNexthopAddress OBJECT-TYPE
    SYNTAX          IpAddress
    MAX-ACCESS      read-write
    STATUS          current
    DESCRIPTION     
            "The next hop address of the sub-interface"
    ::= { sonusNrsSubInterfaceEntry 7 }

sonusNrsSubInterfaceType OBJECT-TYPE
    SYNTAX          INTEGER { ethernetCsmacd8021q(1), 
                        gigabitEthernet8021q(2) }
    MAX-ACCESS      read-only
    STATUS          current
    DESCRIPTION     
            "The type of sub-interface, ethernetCsmacd8021q, gigabitEthernet8021q"
    ::= { sonusNrsSubInterfaceEntry 8 }

sonusNrsSubInterfaceMode OBJECT-TYPE
    SYNTAX          INTEGER { outOfService(1), inService(2) }
    MAX-ACCESS      read-write
    STATUS          current
    DESCRIPTION     
            "The operation mode for sub-interface."
    DEFVAL          { inService }
    ::= { sonusNrsSubInterfaceEntry 9 }

sonusNrsSubInterfaceAction OBJECT-TYPE
    SYNTAX          INTEGER { dryUp(1), force(2) }
    MAX-ACCESS      read-write
    STATUS          current
    DESCRIPTION     
            "The dryup option for sub-interface."
    DEFVAL          { dryUp }
    ::= { sonusNrsSubInterfaceEntry 10 }

sonusNrsSubInterfaceTimeout OBJECT-TYPE
    SYNTAX          Integer32 (1..1440)
    MAX-ACCESS      read-write
    STATUS          current
    DESCRIPTION     
            "The dryup timeout in minute. The default is one hour "
    DEFVAL          { 60 }
    ::= { sonusNrsSubInterfaceEntry 11 }

sonusNrsSubInterfaceMtu OBJECT-TYPE
    SYNTAX          Integer32 (576..1500)
    MAX-ACCESS      read-only
    STATUS          current
    DESCRIPTION     
            "The size of the largest datagram that can be sent/received
             on the interface, specified in octets."
    ::= { sonusNrsSubInterfaceEntry 12 }

sonusNrsSubInterfaceOOSReason OBJECT-TYPE
    SYNTAX          INTEGER { notApplicable(1), admin(2), gateway(3), 
                        portDown(4), serverDown(5), srvrAbsent(6), 
                        linkDown(7), standby(8), 
                        noLogicalBearerAddress(9) }
    MAX-ACCESS      read-only
    STATUS          current
    DESCRIPTION     
            "The reason of SIF being out of service. The SIF could 
             be out of service due to one of the following reasons: 
             operator initiated command, gateway not responding to 
             arp request, port failure/outOfService, or server 
             failure/outOfService. The notApplicable is set when 
             the SIF is inService or dryUp state"
    ::= { sonusNrsSubInterfaceEntry 13 }

sonusNrsSubInterfaceBwDeviation OBJECT-TYPE
    SYNTAX          Integer32 (0..100)
    MAX-ACCESS      read-write
    STATUS          current
    DESCRIPTION     
            "The deviation between actual and expected SIF bandwidth in percentage of the overall SIF bandwidth. 
             If actual bandwidth is greater than the expected bandwdith plus deviation amount, a trap will be set 
             and the trap will be only cleared when the actual bandwidth dropped below the expected bandwidth. 
             If the actual bandwidth is lower than the expected badniwdth minus 2 times of deviation amount, a 
             different trap will be set and the trap will be cleared when the actual bandwdith reaches the 
             expected bandwidth. "
    DEFVAL          { 0 }
    ::= { sonusNrsSubInterfaceEntry 14 }

sonusNrsSubInterfaceBwContingency OBJECT-TYPE
    SYNTAX          Integer32 (0..100)
    MAX-ACCESS      read-write
    STATUS          current
    DESCRIPTION     
            "The percentage of the overall SIF bandwidth is reserved for contigency. If actual bandwidth is 
             greater than the expected bandwdith and less than the overall SIF bandwidth minus contingency 
             amount, calls will still be accepted. "
    DEFVAL          { 0 }
    ::= { sonusNrsSubInterfaceEntry 15 }

sonusNrsSubInterfaceBw OBJECT-TYPE
    SYNTAX          Integer32
    MAX-ACCESS      read-write
    STATUS          current
    DESCRIPTION     
            "Configured bandwidth for this sub-interface."
    ::= { sonusNrsSubInterfaceEntry 16 }

sonusNrsSubInterfaceState OBJECT-TYPE
    SYNTAX          INTEGER { disabled(1), enabled(2) }
    MAX-ACCESS      read-write
    STATUS          current
    DESCRIPTION     
            "Administrative state of the sub-interface."
    ::= { sonusNrsSubInterfaceEntry 17 }

sonusNrsSubInterfaceRowStatus OBJECT-TYPE
    SYNTAX          RowStatus
    MAX-ACCESS      read-write
    STATUS          current
    DESCRIPTION     
            ""
    ::= { sonusNrsSubInterfaceEntry 18 }

sonusNrsSubInterfaceNifShelf OBJECT-TYPE
    SYNTAX          SonusShelfIndex
    MAX-ACCESS      read-only
    STATUS          current
    DESCRIPTION     
            "A 32-bit integer identifying the shelf of the
             Interface"
    ::= { sonusNrsSubInterfaceEntry 19 }

sonusNrsSubInterfaceNifSlot OBJECT-TYPE
    SYNTAX          SonusSlotIndex
    MAX-ACCESS      read-only
    STATUS          current
    DESCRIPTION     
            "A 32-bit integer identifying the slot of the
             Interface"
    ::= { sonusNrsSubInterfaceEntry 20 }

sonusNrsSubInterfaceNifPort OBJECT-TYPE
    SYNTAX          Integer32
    MAX-ACCESS      read-only
    STATUS          current
    DESCRIPTION     
            "A 32-bit integer identifying the port of the
             Interface"
    ::= { sonusNrsSubInterfaceEntry 21 }

sonusNrsSubInterfaceVLanPBucketSize OBJECT-TYPE
    SYNTAX          Integer32 (16..65520)
    MAX-ACCESS      read-write
    STATUS          current
    DESCRIPTION     
            "The per Logical Interface/VLAN policer bucket size, in bytes,
             used to policing all signaling traffic at the logical interface level.
             The rate is 16 bytes to 65520 bytes, in 16 byte increments.  0 to 128
             pseudo-packets (512 bytes) in 1/32 packet increments."
    ::= { sonusNrsSubInterfaceEntry 22 }

sonusNrsSubInterfaceVLanPFillRate OBJECT-TYPE
    SYNTAX          Integer32 (256..16776960)
    MAX-ACCESS      read-write
    STATUS          current
    DESCRIPTION     
            "The per Logical Interface/VLAN policer fill rate, in bytes
             per second, used to policing all signaling traffic at the logical
             interface level.  The range is 256 bytes/sec to 16MBytes/second 
             in increments of 256 bytes/sec. 0.5 to 32K pseudo-packets/second
             in increments of 0.5 packets per second."
    ::= { sonusNrsSubInterfaceEntry 23 }

sonusNrsSubInterfaceIpSecPolicyName OBJECT-TYPE
    SYNTAX          DisplayString (SIZE(0..23))
    MAX-ACCESS      read-write
    STATUS          current
    DESCRIPTION     
            "The name of the IPsec Policy assigned to this SIF. Null if IPsec 
             disabled."
    ::= { sonusNrsSubInterfaceEntry 24 }

sonusNrsSubInterfaceIpv6Address OBJECT-TYPE
    SYNTAX          Ipv6Address
    MAX-ACCESS      read-write
    STATUS          current
    DESCRIPTION     
            "The IPv6 Address of this entry"
    ::= { sonusNrsSubInterfaceEntry 25 }

sonusNrsSubInterfaceIpv6NextHop OBJECT-TYPE
    SYNTAX          Ipv6Address
    MAX-ACCESS      read-write
    STATUS          current
    DESCRIPTION     
            "The next hop IPv6 Address of this entry"
    ::= { sonusNrsSubInterfaceEntry 26 }

sonusNrsSubInterfaceIpv6PrefixLength OBJECT-TYPE
    SYNTAX          Integer32 (0..128)
    MAX-ACCESS      read-write
    STATUS          current
    DESCRIPTION     
            "Ipv6 Prefix Length"
    ::= { sonusNrsSubInterfaceEntry 27 }

sonusNrsSubInterfaceIpv6PrefixMask OBJECT-TYPE
    SYNTAX          Ipv6Address
    MAX-ACCESS      read-write
    STATUS          current
    DESCRIPTION     
            "The next hop IPv6 Address of this entry"
    ::= { sonusNrsSubInterfaceEntry 28 }

sonusNrsSubInterfaceLlIpv6Address OBJECT-TYPE
    SYNTAX          Ipv6Address
    MAX-ACCESS      read-only
    STATUS          current
    DESCRIPTION     
            "The Link local IPv6 Address of this entry"
    ::= { sonusNrsSubInterfaceEntry 29 }

sonusSifAdmnTable OBJECT-TYPE
    SYNTAX          SEQUENCE OF SonusSifAdmnEntry
    MAX-ACCESS      not-accessible
    STATUS          current
    DESCRIPTION     
            "The collection of Sub Interface information for the
             specified instance."
    ::= { sonusIpInterfaceMIBObjects 21 }

sonusSifAdmnEntry OBJECT-TYPE
    SYNTAX          SonusSifAdmnEntry
    MAX-ACCESS      not-accessible
    STATUS          current
    DESCRIPTION     
            "The collection of Sub Interface information for the specified instance."
    INDEX           { sonusSifAdmnShelf, sonusSifAdmnSlot, 
                      sonusSifAdmnPort, sonusSifAdmnNifAdmnIndex, 
                      sonusSifAdmnIfIndex }
    ::= { sonusSifAdmnTable 1 }

SonusSifAdmnEntry ::=
    SEQUENCE {
        sonusSifAdmnNifAdmnIndex        Integer32,
        sonusSifAdmnIfIndex             Integer32,
        sonusSifAdmnShelf               SonusShelfIndex,
        sonusSifAdmnSlot                SonusSlotIndex,
        sonusSifAdmnPort                Integer32
    }

sonusSifAdmnNifAdmnIndex OBJECT-TYPE
    SYNTAX          Integer32
    MAX-ACCESS      read-only
    STATUS          current
    DESCRIPTION     
            "The ifIndex assigned to this NIF when it was created.
             This will not change until the NIF is deleted."
    ::= { sonusSifAdmnEntry 1 }

sonusSifAdmnIfIndex OBJECT-TYPE
    SYNTAX          Integer32
    MAX-ACCESS      read-only
    STATUS          current
    DESCRIPTION     
            "The ifIndex assigned to this SIF when it was created"
    ::= { sonusSifAdmnEntry 2 }

sonusSifAdmnShelf OBJECT-TYPE
    SYNTAX          SonusShelfIndex
    MAX-ACCESS      read-only
    STATUS          current
    DESCRIPTION     
            "A 32-bit integer identifying the shelf of the Interface"
    ::= { sonusSifAdmnEntry 3 }

sonusSifAdmnSlot OBJECT-TYPE
    SYNTAX          SonusSlotIndex
    MAX-ACCESS      read-only
    STATUS          current
    DESCRIPTION     
            "A 32-bit integer identifying the slot of the Interface"
    ::= { sonusSifAdmnEntry 4 }

sonusSifAdmnPort OBJECT-TYPE
    SYNTAX          Integer32
    MAX-ACCESS      read-only
    STATUS          current
    DESCRIPTION     
            "A 32-bit integer identifying the port of the Interface."
    ::= { sonusSifAdmnEntry 5 }

sonusNrsDebugIfTable OBJECT-TYPE
    SYNTAX          SEQUENCE OF SonusNrsDebugIfEntry
    MAX-ACCESS      not-accessible
    STATUS          current
    DESCRIPTION     
            "The collection of Debug Interface information for the
             specified instance."
    ::= { sonusIpInterfaceMIBObjects 99 }

sonusNrsDebugIfEntry OBJECT-TYPE
    SYNTAX          SonusNrsDebugIfEntry
    MAX-ACCESS      not-accessible
    STATUS          current
    DESCRIPTION     
            "The collection of Debug Interface information for the
             specified instance."
    INDEX           { sonusNrsDebugIfShelf, sonusNrsDebugIfSlot }
    ::= { sonusNrsDebugIfTable 1 }

SonusNrsDebugIfEntry ::=
    SEQUENCE {
        sonusNrsDebugIfIndex            Integer32,
        sonusNrsDebugIfShelf            SonusShelfIndex,
        sonusNrsDebugIfSlot             SonusSlotIndex,
        sonusNrsDebugIfPort             Integer32,
        sonusNrsDebugIfCircuit          Integer32,
        sonusNrsDebugIfType             IANAifType,
        sonusNrsDebugIfIpAddress        IpAddress,
        sonusNrsDebugIfIpMask           IpAddress,
        sonusNrsDebugIfMtu              Integer32,
        sonusNrsDebugIfGatewayAddress   IpAddress,
        sonusNrsDebugIfAdminStatus      INTEGER,
        sonusNrsDebugIfOperStatus       INTEGER,
        sonusNrsDebugIfIpv6Address      Ipv6Address,
        sonusNrsDebugIfGatewayIpv6Address Ipv6Address,
        sonusNrsDebugIfIpv6PrefixLength Integer32
    }

sonusNrsDebugIfIndex OBJECT-TYPE
    SYNTAX          Integer32
    MAX-ACCESS      read-only
    STATUS          current
    DESCRIPTION     
            "The ifIndex assigned to this debug NIF when it was created.
             This will not change until the NIF is deleted."
    ::= { sonusNrsDebugIfEntry 1 }

sonusNrsDebugIfShelf OBJECT-TYPE
    SYNTAX          SonusShelfIndex
    MAX-ACCESS      read-only
    STATUS          current
    DESCRIPTION     
            "A 32-bit integer identifying the shelf of the Debug
             Interface"
    ::= { sonusNrsDebugIfEntry 2 }

sonusNrsDebugIfSlot OBJECT-TYPE
    SYNTAX          SonusSlotIndex
    MAX-ACCESS      read-only
    STATUS          current
    DESCRIPTION     
            "A 32-bit integer identifying the slot of the Debug
             Interface"
    ::= { sonusNrsDebugIfEntry 3 }

sonusNrsDebugIfPort OBJECT-TYPE
    SYNTAX          Integer32
    MAX-ACCESS      read-write
    STATUS          current
    DESCRIPTION     
            "A 32-bit integer identifying the port of the Debug
             Interface.  For current hardware this must be 1."
    ::= { sonusNrsDebugIfEntry 4 }

sonusNrsDebugIfCircuit OBJECT-TYPE
    SYNTAX          Integer32
    MAX-ACCESS      read-write
    STATUS          current
    DESCRIPTION     
            "A 32-bit integer identifying the circuit of the Debug
             Interface.  For current hardware this must be 1."
    ::= { sonusNrsDebugIfEntry 5 }

sonusNrsDebugIfType OBJECT-TYPE
    SYNTAX          IANAifType
    MAX-ACCESS      read-write
    STATUS          current
    DESCRIPTION     
            "The type of interface, distinguished according to the
             physical/link protocol(s) immediately 'below' the network
             layer in the protocol stack.
             
             Values are from RFC1213 for the ifType object.
             
             Current hardware supports only the ethernet-csmacd (6)
             type."
    ::= { sonusNrsDebugIfEntry 6 }

sonusNrsDebugIfIpAddress OBJECT-TYPE
    SYNTAX          IpAddress
    MAX-ACCESS      read-write
    STATUS          current
    DESCRIPTION     
            "The IP Address of the Debug Interface"
    ::= { sonusNrsDebugIfEntry 7 }

sonusNrsDebugIfIpMask OBJECT-TYPE
    SYNTAX          IpAddress
    MAX-ACCESS      read-write
    STATUS          current
    DESCRIPTION     
            "The IP subnet mask of this Debug Interface."
    ::= { sonusNrsDebugIfEntry 8 }

sonusNrsDebugIfMtu OBJECT-TYPE
    SYNTAX          Integer32
    MAX-ACCESS      read-write
    STATUS          current
    DESCRIPTION     
            "The size of the largest datagram that can be sent/received
             on the interface, specified in octets."
    ::= { sonusNrsDebugIfEntry 9 }

sonusNrsDebugIfGatewayAddress OBJECT-TYPE
    SYNTAX          IpAddress
    MAX-ACCESS      read-write
    STATUS          current
    DESCRIPTION     
            "The IP address of the default gateway for this Debug
             Interface."
    ::= { sonusNrsDebugIfEntry 10 }

sonusNrsDebugIfAdminStatus OBJECT-TYPE
    SYNTAX          INTEGER { disabled(1), enabled(2) }
    MAX-ACCESS      read-write
    STATUS          current
    DESCRIPTION     
            "The requested status of the interface."
    ::= { sonusNrsDebugIfEntry 11 }

sonusNrsDebugIfOperStatus OBJECT-TYPE
    SYNTAX          INTEGER { outOfService(1), inService(2), 
                        outOfServiceDisabled(3), outOfServiceLinkDown(4) }
    MAX-ACCESS      read-only
    STATUS          current
    DESCRIPTION     
            "The actual status of the debug interface.  A link will
             be InService if the sonusNrsDebugIfAdminStatus is enabled and
             the physical link is up.  It will be OutOfService if the admin
             status is enabled but the physical link is down.  It will be
             OutOfServiceDisabled if the physical link is up but the admin
             status is disabled.  It will be OutOfServiceLinkDown if the
             physical link is down and the admin status is disabled."
    ::= { sonusNrsDebugIfEntry 12 }

sonusNrsDebugIfIpv6Address OBJECT-TYPE
    SYNTAX          Ipv6Address
    MAX-ACCESS      read-write
    STATUS          current
    DESCRIPTION     
            "The IPv6 Address of this entry"
    ::= { sonusNrsDebugIfEntry 13 }

sonusNrsDebugIfGatewayIpv6Address OBJECT-TYPE
    SYNTAX          Ipv6Address
    MAX-ACCESS      read-write
    STATUS          current
    DESCRIPTION     
            "The next hop IPv6 Address of this entry"
    ::= { sonusNrsDebugIfEntry 14 }

sonusNrsDebugIfIpv6PrefixLength OBJECT-TYPE
    SYNTAX          Integer32
    MAX-ACCESS      read-write
    STATUS          current
    DESCRIPTION     
            "Ipv6 Prefix Length"
    ::= { sonusNrsDebugIfEntry 15 }

sonusIpInterfaceMIBNotifications OBJECT IDENTIFIER
    ::= { sonusIpInterfaceMIB 2 }

sonusIpInterfaceMIBNotificationsPrefix OBJECT IDENTIFIER
    ::= { sonusIpInterfaceMIBNotifications 0 }

sonusIpInterfaceMIBNotificationsObjects OBJECT IDENTIFIER
    ::= { sonusIpInterfaceMIBNotifications 1 }

sonusNrsOosSifCount OBJECT-TYPE
    SYNTAX          Integer32
    MAX-ACCESS      read-only
    STATUS          current
    DESCRIPTION     
            "Represents number of sub-interfaces that are out of service."
    ::= { sonusIpInterfaceMIBNotificationsObjects 1 }

sonusTCPGenMIBNotifications OBJECT IDENTIFIER
    ::= { sonusIpInterfaceMIB 3 }

sonusTCPGenMIBNotificationsPrefix OBJECT IDENTIFIER
    ::= { sonusTCPGenMIBNotifications 0 }

sonusTCPGenMIBNotificationsObjects OBJECT IDENTIFIER
    ::= { sonusTCPGenMIBNotifications 1 }

sonusNifGrpObjects OBJECT IDENTIFIER
    ::= { sonusPacketMIBs 9 }

sonusNifGrpTableObjects OBJECT IDENTIFIER
    ::= { sonusNifGrpObjects 1 }

sonusNifGrpTableNextIndex OBJECT-TYPE
    SYNTAX          Integer32
    MAX-ACCESS      not-accessible
    STATUS          current
    DESCRIPTION     
            "The next valid index to use when creating a new NIF Group."
    ::= { sonusNifGrpTableObjects 1 }

sonusNifGrpTableTable OBJECT-TYPE
    SYNTAX          SEQUENCE OF SonusNifGrpTableEntry
    MAX-ACCESS      not-accessible
    STATUS          current
    DESCRIPTION     
            "This mib table is used to create a name for a NIF Group."
    ::= { sonusNifGrpTableObjects 2 }

sonusNifGrpTableEntry OBJECT-TYPE
    SYNTAX          SonusNifGrpTableEntry
    MAX-ACCESS      not-accessible
    STATUS          current
    DESCRIPTION     
            "This mib table is used to create a name for a NIF Group table."
    INDEX           { sonusNifGrpIndex }
    ::= { sonusNifGrpTableTable 1 }

SonusNifGrpTableEntry ::=
    SEQUENCE {
        sonusNifGrpIndex                Integer32,
        sonusNifGrpName                 SonusName,
        sonusNifGrpAdminState           INTEGER,
        sonusNifGrpRowStatus            RowStatus
    }

sonusNifGrpIndex OBJECT-TYPE
    SYNTAX          Integer32
    MAX-ACCESS      not-accessible
    STATUS          current
    DESCRIPTION     
            "A unique index for this NIF group name."
    ::= { sonusNifGrpTableEntry 1 }

sonusNifGrpName OBJECT-TYPE
    SYNTAX          SonusName
    MAX-ACCESS      read-write
    STATUS          current
    DESCRIPTION     
            "The name of the NIF group."
    ::= { sonusNifGrpTableEntry 2 }

sonusNifGrpAdminState OBJECT-TYPE
    SYNTAX          INTEGER { disabled(1), enabled(2) }
    MAX-ACCESS      read-write
    STATUS          current
    DESCRIPTION     
            "The adminstration state of this NIF group."
    DEFVAL          { disabled }
    ::= { sonusNifGrpTableEntry 3 }

sonusNifGrpRowStatus OBJECT-TYPE
    SYNTAX          RowStatus
    MAX-ACCESS      read-write
    STATUS          current
    DESCRIPTION     
            "This is for SNMP use."
    ::= { sonusNifGrpTableEntry 4 }

sonusNifGrpIntfObjects OBJECT IDENTIFIER
    ::= { sonusNifGrpObjects 2 }

sonusNifGrpIntfTable OBJECT-TYPE
    SYNTAX          SEQUENCE OF SonusNifGrpIntfEntry
    MAX-ACCESS      not-accessible
    STATUS          current
    DESCRIPTION     
            "This mib table is for Nif Group Table Entries."
    ::= { sonusNifGrpIntfObjects 1 }

sonusNifGrpIntfEntry OBJECT-TYPE
    SYNTAX          SonusNifGrpIntfEntry
    MAX-ACCESS      not-accessible
    STATUS          current
    DESCRIPTION     
            "This mib table is for Nif Group Table Entries."
    INDEX           { sonusNifGroupIndex, sonusNifGrpIntfIfIndex }
    ::= { sonusNifGrpIntfTable 1 }

SonusNifGrpIntfEntry ::=
    SEQUENCE {
        sonusNifGroupIndex              Integer32,
        sonusNifGrpIntfIfIndex          Integer32,
        sonusNifGrpIntfRowStatus        RowStatus
    }

sonusNifGroupIndex OBJECT-TYPE
    SYNTAX          Integer32
    MAX-ACCESS      not-accessible
    STATUS          current
    DESCRIPTION     
            "Unique NIF group table index that this NIF interface element belongs to."
    ::= { sonusNifGrpIntfEntry 1 }

sonusNifGrpIntfIfIndex OBJECT-TYPE
    SYNTAX          Integer32
    MAX-ACCESS      read-only
    STATUS          current
    DESCRIPTION     
            "NIF Interface index."
    ::= { sonusNifGrpIntfEntry 2 }

sonusNifGrpIntfRowStatus OBJECT-TYPE
    SYNTAX          RowStatus
    MAX-ACCESS      read-write
    STATUS          current
    DESCRIPTION     
            "This is for SNMP use."
    ::= { sonusNifGrpIntfEntry 3 }

sonusMirrorGrpObjects OBJECT IDENTIFIER
    ::= { sonusPacketMIBs 11 }

sonusMirrorGrpTableObjects OBJECT IDENTIFIER
    ::= { sonusMirrorGrpObjects 1 }

sonusMirrorGrpTableNextIndex OBJECT-TYPE
    SYNTAX          Integer32
    MAX-ACCESS      not-accessible
    STATUS          current
    DESCRIPTION     
            "The next valid index to use when creating a new Mirror Group."
    ::= { sonusMirrorGrpTableObjects 1 }

sonusMirrorGrpTable OBJECT-TYPE
    SYNTAX          SEQUENCE OF SonusMirrorGrpTableEntry
    MAX-ACCESS      not-accessible
    STATUS          current
    DESCRIPTION     
            "This mib table is used to create a name for a Mirror Group."
    ::= { sonusMirrorGrpTableObjects 2 }

sonusMirrorGrpTableEntry OBJECT-TYPE
    SYNTAX          SonusMirrorGrpTableEntry
    MAX-ACCESS      not-accessible
    STATUS          current
    DESCRIPTION     
            "This is to create a Mirror Group table entry."
    INDEX           { sonusMirrorGrpIndex }
    ::= { sonusMirrorGrpTable 1 }

SonusMirrorGrpTableEntry ::=
    SEQUENCE {
        sonusMirrorGrpIndex             Unsigned32,
        sonusMirrorGrpName              SonusName,
        sonusMirrorGrpMirrorIfName      SonusNameReference,
        sonusMirrorGrpMirrorIfIndex     Integer32,
        sonusMirrorGrpMirrorEtherType   Integer32,
        sonusMirrorGrpDestinationMac    PhysAddress,
        sonusMirrorGrpAdminState        INTEGER,
        sonusMirrorGrpRowStatus         RowStatus,
        sonusMirrorGrpDstMacStr         DisplayString
    }

sonusMirrorGrpIndex OBJECT-TYPE
    SYNTAX          Unsigned32
    MAX-ACCESS      not-accessible
    STATUS          current
    DESCRIPTION     
            "A unique index for this Mirror Group."
    ::= { sonusMirrorGrpTableEntry 1 }

sonusMirrorGrpName OBJECT-TYPE
    SYNTAX          SonusName
    MAX-ACCESS      read-create
    STATUS          current
    DESCRIPTION     
            "The name of the Mirror Group."
    ::= { sonusMirrorGrpTableEntry 2 }

sonusMirrorGrpMirrorIfName OBJECT-TYPE
    SYNTAX          SonusNameReference
    MAX-ACCESS      read-create
    STATUS          current
    DESCRIPTION     
            "The name of the Mirror Interface for this Mirror Group."
    ::= { sonusMirrorGrpTableEntry 3 }

sonusMirrorGrpMirrorIfIndex OBJECT-TYPE
    SYNTAX          Integer32
    MAX-ACCESS      read-only
    STATUS          current
    DESCRIPTION     
            "The IF index of the Mirror Interface for this Mirror Group."
    ::= { sonusMirrorGrpTableEntry 4 }

sonusMirrorGrpMirrorEtherType OBJECT-TYPE
    SYNTAX          Integer32
    MAX-ACCESS      read-create
    STATUS          current
    DESCRIPTION     
            "The EtherType value of the mirrored packets sent by the Mirror Interface of this Mirror Group."
    DEFVAL          { 0 }
    ::= { sonusMirrorGrpTableEntry 5 }

sonusMirrorGrpDestinationMac OBJECT-TYPE
    SYNTAX          PhysAddress
    MAX-ACCESS      read-create
    STATUS          current
    DESCRIPTION     
            "The Destination MAC address of the mirrored packets sent by the Mirror Interface of this Mirror Group."
    ::= { sonusMirrorGrpTableEntry 6 }

sonusMirrorGrpAdminState OBJECT-TYPE
    SYNTAX          INTEGER { disabled(1), enabled(2) }
    MAX-ACCESS      read-create
    STATUS          current
    DESCRIPTION     
            "The adminstration state of this Mirror Group."
    DEFVAL          { disabled }
    ::= { sonusMirrorGrpTableEntry 7 }

sonusMirrorGrpRowStatus OBJECT-TYPE
    SYNTAX          RowStatus
    MAX-ACCESS      read-create
    STATUS          current
    DESCRIPTION     
            "This is for SNMP use."
    ::= { sonusMirrorGrpTableEntry 8 }

sonusMirrorGrpDstMacStr OBJECT-TYPE
    SYNTAX          DisplayString (SIZE(0..23))
    MAX-ACCESS      read-create
    STATUS          current
    DESCRIPTION     
            "The Destination MAC address in string format of the mirrored packets sent by the 
             Mirror Interface of this Mirror Group."
    DEFVAL          { "00:10:6b:01:c8:d8" }
    ::= { sonusMirrorGrpTableEntry 9 }

sonusMirrorGrpIntfObjects OBJECT IDENTIFIER
    ::= { sonusMirrorGrpObjects 2 }

sonusMirrorGrpIntfTable OBJECT-TYPE
    SYNTAX          SEQUENCE OF SonusMirrorGrpIntfEntry
    MAX-ACCESS      not-accessible
    STATUS          current
    DESCRIPTION     
            "This is the Mirror Group Inetrface Table."
    ::= { sonusMirrorGrpIntfObjects 1 }

sonusMirrorGrpIntfEntry OBJECT-TYPE
    SYNTAX          SonusMirrorGrpIntfEntry
    MAX-ACCESS      not-accessible
    STATUS          current
    DESCRIPTION     
            "This is the Mirror Group Interface Table Entry."
    INDEX           { sonusMirrorGroupIndex, sonusMirrorGrpIntfIfIndex }
    ::= { sonusMirrorGrpIntfTable 1 }

SonusMirrorGrpIntfEntry ::=
    SEQUENCE {
        sonusMirrorGroupIndex           Unsigned32,
        sonusMirrorGrpIntfIfIndex       Integer32,
        sonusMirrorGrpIntfMirrorDirection INTEGER,
        sonusMirrorGrpIntfRowStatus     RowStatus
    }

sonusMirrorGroupIndex OBJECT-TYPE
    SYNTAX          Unsigned32
    MAX-ACCESS      not-accessible
    STATUS          current
    DESCRIPTION     
            "The Mirror Group Table index that this LIF interface belongs to."
    ::= { sonusMirrorGrpIntfEntry 1 }

sonusMirrorGrpIntfIfIndex OBJECT-TYPE
    SYNTAX          Integer32
    MAX-ACCESS      read-only
    STATUS          current
    DESCRIPTION     
            "The IF index of this LIF."
    ::= { sonusMirrorGrpIntfEntry 2 }

sonusMirrorGrpIntfMirrorDirection OBJECT-TYPE
    SYNTAX          INTEGER { inbound(1), outbound(2), both(3) }
    MAX-ACCESS      read-write
    STATUS          current
    DESCRIPTION     
            "The Packet Mirroring direction (Inbound/Outbound or both) of this Mirror Group Interface."
    DEFVAL          { both }
    ::= { sonusMirrorGrpIntfEntry 3 }

sonusMirrorGrpIntfRowStatus OBJECT-TYPE
    SYNTAX          RowStatus
    MAX-ACCESS      read-write
    STATUS          current
    DESCRIPTION     
            "This is for SNMP use."
    ::= { sonusMirrorGrpIntfEntry 4 }

sonusMirrorGrpStatTableObjects OBJECT IDENTIFIER
    ::= { sonusMirrorGrpObjects 3 }

sonusMirrorGrpStatTable OBJECT-TYPE
    SYNTAX          SEQUENCE OF SonusMirrorGrpStatTableEntry
    MAX-ACCESS      not-accessible
    STATUS          current
    DESCRIPTION     
            "Table of the Mirror Group statistics data"
    ::= { sonusMirrorGrpStatTableObjects 1 }

sonusMirrorGrpStatTableEntry OBJECT-TYPE
    SYNTAX          SonusMirrorGrpStatTableEntry
    MAX-ACCESS      not-accessible
    STATUS          current
    DESCRIPTION     
            "This is to create a Mirror Group Statistics table entry."
    INDEX           { sonusMirrorGrpStatIndex }
    ::= { sonusMirrorGrpStatTable 1 }

SonusMirrorGrpStatTableEntry ::=
    SEQUENCE {
        sonusMirrorGrpStatIndex         Unsigned32,
        sonusMirrorGrpStatReset         INTEGER,
        sonusMirrorGrpStatMirrorGrpName SonusName,
        sonusMirrorGrpStatMirrorIfName  DisplayString,
        sonusMirrorGrpInboundPacketsTotal Counter32,
        sonusMirrorGrpOutboundPacketsTotal  Counter32,
        sonusMirrorGrpInboundDiscardedPacketsTotal          Counter32,
        sonusMirrorGrpOutboundDiscardedPacketsTotal           Counter32,
        sonusMirrorGrpDiscardedPacketsNoBuffer      Counter32,
        sonusMirrorGrpDiscardedPacketsOther   Counter32,
        sonusMirrorGrpDiscardedPacketsPolicing      Counter32,
        sonusMirrorGrpDiscardedPacketsLinkDown      Counter32
    }

sonusMirrorGrpStatIndex OBJECT-TYPE
    SYNTAX          Unsigned32
    MAX-ACCESS      read-only
    STATUS          current
    DESCRIPTION     
            "A unique index for this Mirror Group Statistics Table."
    ::= { sonusMirrorGrpStatTableEntry 1 }

sonusMirrorGrpStatReset OBJECT-TYPE
    SYNTAX          INTEGER { unknown(1), reset(2) }
    MAX-ACCESS      read-write
    STATUS          current
    DESCRIPTION     
            "Reset all statistics data for this Mirror Group."
    ::= { sonusMirrorGrpStatTableEntry 2 }

sonusMirrorGrpStatMirrorGrpName OBJECT-TYPE
    SYNTAX          SonusName
    MAX-ACCESS      read-only
    STATUS          current
    DESCRIPTION     
            "Identify the Mirror Group"
    ::= { sonusMirrorGrpStatTableEntry 3 }

sonusMirrorGrpStatMirrorIfName OBJECT-TYPE
    SYNTAX          DisplayString (SIZE(0..23))
    MAX-ACCESS      read-only
    STATUS          current
    DESCRIPTION     
            "Identify the Mirror Interface"
    ::= { sonusMirrorGrpStatTableEntry 4 }

sonusMirrorGrpInboundPacketsTotal OBJECT-TYPE
    SYNTAX          Counter32
    MAX-ACCESS      read-only
    STATUS          current
    DESCRIPTION     
            "Total inbound packets mirrored for this Mirror Group."
    ::= { sonusMirrorGrpStatTableEntry 5 }

sonusMirrorGrpOutboundPacketsTotal OBJECT-TYPE
    SYNTAX          Counter32
    MAX-ACCESS      read-only
    STATUS          current
    DESCRIPTION     
            "Total outbound packets mirrored for this Mirror Group."
    ::= { sonusMirrorGrpStatTableEntry 6 }

sonusMirrorGrpInboundDiscardedPacketsTotal OBJECT-TYPE
    SYNTAX          Counter32
    MAX-ACCESS      read-only
    STATUS          current
    DESCRIPTION     
            "Total inbound packets not mirrored due to congestion or other reasons."
    ::= { sonusMirrorGrpStatTableEntry 7 }

sonusMirrorGrpOutboundDiscardedPacketsTotal OBJECT-TYPE
    SYNTAX          Counter32
    MAX-ACCESS      read-only
    STATUS          current
    DESCRIPTION     
            "Total outbound packets not mirrored due to congestion or other reasons."
    ::= { sonusMirrorGrpStatTableEntry 8 }

sonusMirrorGrpDiscardedPacketsNoBuffer OBJECT-TYPE
    SYNTAX          Counter32
    MAX-ACCESS      read-only
    STATUS          current
    DESCRIPTION     
            "Packets not mirrored due to no packet buffers."
    ::= { sonusMirrorGrpStatTableEntry 9 }

sonusMirrorGrpDiscardedPacketsOther OBJECT-TYPE
    SYNTAX          Counter32
    MAX-ACCESS      read-only
    STATUS          current
    DESCRIPTION     
            "Packets not mirrored due to various other internal reasons."
    ::= { sonusMirrorGrpStatTableEntry 10 }

sonusMirrorGrpDiscardedPacketsPolicing OBJECT-TYPE
    SYNTAX          Counter32
    MAX-ACCESS      read-only
    STATUS          current
    DESCRIPTION     
            "Packets not mirrored due to policing."
    ::= { sonusMirrorGrpStatTableEntry 11 }

sonusMirrorGrpDiscardedPacketsLinkDown OBJECT-TYPE
    SYNTAX          Counter32
    MAX-ACCESS      read-only
    STATUS          current
    DESCRIPTION     
            "Packets not mirrored due mirror LIF link down."
    ::= { sonusMirrorGrpStatTableEntry 12 }

sonusMirrorGrpIntfStatObjects OBJECT IDENTIFIER
    ::= { sonusMirrorGrpObjects 4 }

sonusMirrorGrpIntfStatTable OBJECT-TYPE
    SYNTAX          SEQUENCE OF SonusMirrorGrpIntfStatTableEntry
    MAX-ACCESS      not-accessible
    STATUS          current
    DESCRIPTION     
            "Table of the Mirror Group Interface statistics data"
    ::= { sonusMirrorGrpIntfStatObjects 1 }

sonusMirrorGrpIntfStatTableEntry OBJECT-TYPE
    SYNTAX          SonusMirrorGrpIntfStatTableEntry
    MAX-ACCESS      not-accessible
    STATUS          current
    DESCRIPTION     
            "This is to create a Mirror Group Interfaces Statistics table entry."
    INDEX           { sonusMirrorGrpIntfStatGrpIndex, 
                      sonusMirrorGrpIntfStatIfIndex }
    ::= { sonusMirrorGrpIntfStatTable 1 }

SonusMirrorGrpIntfStatTableEntry ::=
    SEQUENCE {
        sonusMirrorGrpIntfStatGrpIndex  Integer32,
        sonusMirrorGrpIntfStatIfIndex   Integer32,
        sonusMirrorGrpIntfStatReset     INTEGER,
        sonusMirrorGrpIntfStatMirrorGrpName   DisplayString,
        sonusMirrorGrpIntfStatMonitoredIfName     DisplayString,
        sonusMirrorGrpIntfInboundPacketsTotal     Counter32,
        sonusMirrorGrpIntfOutboundPacketsTotal      Counter32,
        sonusMirrorGrpIntfInboundDiscardedPacketsTotal              Counter32,
        sonusMirrorGrpIntfOutboundDiscardedPacketsTotal               Counter32,
        sonusMirrorGrpIntfDiscardedPacketsNoBuffer          Counter32,
        sonusMirrorGrpIntfDiscardedPacketsOther       Counter32,
        sonusMirrorGrpIntfDiscardedPacketsPolicing          Counter32,
        sonusMirrorGrpIntfDiscardedPacketsLinkDown          Counter32
    }

sonusMirrorGrpIntfStatGrpIndex OBJECT-TYPE
    SYNTAX          Integer32
    MAX-ACCESS      read-only
    STATUS          current
    DESCRIPTION     
            "A unique Mirror Group index for this Mirror Group Interfaces Statistics Table."
    ::= { sonusMirrorGrpIntfStatTableEntry 1 }

sonusMirrorGrpIntfStatIfIndex OBJECT-TYPE
    SYNTAX          Integer32
    MAX-ACCESS      read-only
    STATUS          current
    DESCRIPTION     
            "A unique Monitored LIF index for this Mirror Group Interfaces Statistics Table."
    ::= { sonusMirrorGrpIntfStatTableEntry 2 }

sonusMirrorGrpIntfStatReset OBJECT-TYPE
    SYNTAX          INTEGER { unknown(1), reset(2) }
    MAX-ACCESS      read-write
    STATUS          current
    DESCRIPTION     
            "Reset all statistics data for this Mirror Group Interface Table."
    ::= { sonusMirrorGrpIntfStatTableEntry 3 }

sonusMirrorGrpIntfStatMirrorGrpName OBJECT-TYPE
    SYNTAX          DisplayString (SIZE(0..23))
    MAX-ACCESS      read-only
    STATUS          current
    DESCRIPTION     
            "Identify the Mirror Group that this Monitored Interface belongs to"
    ::= { sonusMirrorGrpIntfStatTableEntry 4 }

sonusMirrorGrpIntfStatMonitoredIfName OBJECT-TYPE
    SYNTAX          DisplayString (SIZE(0..23))
    MAX-ACCESS      read-only
    STATUS          current
    DESCRIPTION     
            "Identify the Monitored Interface"
    ::= { sonusMirrorGrpIntfStatTableEntry 5 }

sonusMirrorGrpIntfInboundPacketsTotal OBJECT-TYPE
    SYNTAX          Counter32
    MAX-ACCESS      read-only
    STATUS          current
    DESCRIPTION     
            "Total inbound packets mirrored for this Monitored Interface."
    ::= { sonusMirrorGrpIntfStatTableEntry 6 }

sonusMirrorGrpIntfOutboundPacketsTotal OBJECT-TYPE
    SYNTAX          Counter32
    MAX-ACCESS      read-only
    STATUS          current
    DESCRIPTION     
            "Total outbound packets mirrored for this Monitored Interface."
    ::= { sonusMirrorGrpIntfStatTableEntry 7 }

sonusMirrorGrpIntfInboundDiscardedPacketsTotal OBJECT-TYPE
    SYNTAX          Counter32
    MAX-ACCESS      read-only
    STATUS          current
    DESCRIPTION     
            "Total inbound mirrored packets not sent due to congestion or other reasons for this Monitored Interface."
    ::= { sonusMirrorGrpIntfStatTableEntry 8 }

sonusMirrorGrpIntfOutboundDiscardedPacketsTotal OBJECT-TYPE
    SYNTAX          Counter32
    MAX-ACCESS      read-only
    STATUS          current
    DESCRIPTION     
            "Total outbound mirrored packets not sent due to congestion or other reasons for this Monitored Interface."
    ::= { sonusMirrorGrpIntfStatTableEntry 9 }

sonusMirrorGrpIntfDiscardedPacketsNoBuffer OBJECT-TYPE
    SYNTAX          Counter32
    MAX-ACCESS      read-only
    STATUS          current
    DESCRIPTION     
            "Mirrored Packets not sent due to no packet buffers for this Monitored Interface."
    ::= { sonusMirrorGrpIntfStatTableEntry 10 }

sonusMirrorGrpIntfDiscardedPacketsOther OBJECT-TYPE
    SYNTAX          Counter32
    MAX-ACCESS      read-only
    STATUS          current
    DESCRIPTION     
            "Mirrored Packets not sent due to various other internal reasons for this Monitored Interface."
    ::= { sonusMirrorGrpIntfStatTableEntry 11 }

sonusMirrorGrpIntfDiscardedPacketsPolicing OBJECT-TYPE
    SYNTAX          Counter32
    MAX-ACCESS      read-only
    STATUS          current
    DESCRIPTION     
            "Mirrored Packets not sent due to policing for this Monitored Interface."
    ::= { sonusMirrorGrpIntfStatTableEntry 12 }

sonusMirrorGrpIntfDiscardedPacketsLinkDown OBJECT-TYPE
    SYNTAX          Counter32
    MAX-ACCESS      read-only
    STATUS          current
    DESCRIPTION     
            "Mirrored Packets not sent due to mirror LIF link down."
    ::= { sonusMirrorGrpIntfStatTableEntry 13 }

sonusNrsNifInServiceNotification NOTIFICATION-TYPE
    OBJECTS         { sonusNifShelf, sonusNifSlot, sonusNifPort, 
                      sonusNifIndex, sonusNifName, sonusEventDescription, 
                      sonusEventClass, sonusEventLevel, sonusSequenceId, 
                      sonusEventTime }
    STATUS          current
    DESCRIPTION     
            "This trap indicates that a NIF is available to support
             call processing."
    ::= { sonusIpInterfaceMIBNotificationsPrefix 1 }

sonusNrsNifOutOfServiceNotification NOTIFICATION-TYPE
    OBJECTS         { sonusNifShelf, sonusNifSlot, sonusNifPort, 
                      sonusNifIndex, sonusNifName, 
                      sonusNifOutOfServiceReason, sonusEventDescription, 
                      sonusEventClass, sonusEventLevel, sonusSequenceId, 
                      sonusEventTime }
    STATUS          current
    DESCRIPTION     
            "This trap indicates that a NIF is no longer available to
             support call processing."
    ::= { sonusIpInterfaceMIBNotificationsPrefix 2 }

sonusNrsNifEnabledNotification NOTIFICATION-TYPE
    OBJECTS         { sonusNifShelf, sonusNifSlot, sonusNifPort, 
                      sonusNifIndex, sonusNifName, sonusEventDescription, 
                      sonusEventClass, sonusEventLevel, sonusSequenceId, 
                      sonusEventTime }
    STATUS          current
    DESCRIPTION     
            "This trap indicates that a NIF's configuration is enabled."
    ::= { sonusIpInterfaceMIBNotificationsPrefix 3 }

sonusNrsNifDisabledNotification NOTIFICATION-TYPE
    OBJECTS         { sonusNifShelf, sonusNifSlot, sonusNifPort, 
                      sonusNifIndex, sonusNifName, sonusEventDescription, 
                      sonusEventClass, sonusEventLevel, sonusSequenceId, 
                      sonusEventTime }
    STATUS          current
    DESCRIPTION     
            "This trap indicates that a NIF's configuration is disabled."
    ::= { sonusIpInterfaceMIBNotificationsPrefix 4 }

sonusNrsNifDeletedNotification NOTIFICATION-TYPE
    OBJECTS         { sonusNifShelf, sonusNifSlot, sonusNifPort, 
                      sonusNifIndex, sonusNifName, sonusEventDescription, 
                      sonusEventClass, sonusEventLevel, sonusSequenceId, 
                      sonusEventTime }
    STATUS          current
    DESCRIPTION     
            "This trap indicates that a NIF's configuration is deleted."
    ::= { sonusIpInterfaceMIBNotificationsPrefix 5 }

sonusNrsNifHighWatermarkNotification NOTIFICATION-TYPE
    OBJECTS         { sonusNifShelf, sonusNifSlot, sonusNifPort, 
                      sonusNifIndex, sonusNifName, sonusEventDescription, 
                      sonusEventClass, sonusEventLevel, sonusSequenceId, 
                      sonusEventTime }
    STATUS          current
    DESCRIPTION     
            "This trap indicates that a NIF's high watermark has been reached 
             the first time since the NIF's low watermark has beend reached."
    ::= { sonusIpInterfaceMIBNotificationsPrefix 6 }

sonusNrsNifLowWatermarkNotification NOTIFICATION-TYPE
    OBJECTS         { sonusNifShelf, sonusNifSlot, sonusNifPort, 
                      sonusNifIndex, sonusNifName, sonusEventDescription, 
                      sonusEventClass, sonusEventLevel, sonusSequenceId, 
                      sonusEventTime }
    STATUS          current
    DESCRIPTION     
            "This trap indicates that a NIF's low watermark has been reached
             the first time since the NIF's high watermark has been reached."
    ::= { sonusIpInterfaceMIBNotificationsPrefix 7 }

sonusNrsNifBwHighDeviationNotification NOTIFICATION-TYPE
    OBJECTS         { sonusNifShelf, sonusNifSlot, sonusNifPort, 
                      sonusNifIndex, sonusNifName, sonusEventDescription, 
                      sonusEventClass, sonusEventLevel, sonusSequenceId, 
                      sonusEventTime }
    STATUS          current
    DESCRIPTION     
            "This trap indicates that a NIF's actual bandwidth is greater than the 
             expected bandwidth plus deviation amount. This trap will be re-armed
             when the actual bandwdith dropped below the expected level. "
    ::= { sonusIpInterfaceMIBNotificationsPrefix 8 }

sonusNrsNifBwLowDeviationNotification NOTIFICATION-TYPE
    OBJECTS         { sonusNifShelf, sonusNifSlot, sonusNifPort, 
                      sonusNifIndex, sonusNifName, sonusEventDescription, 
                      sonusEventClass, sonusEventLevel, sonusSequenceId, 
                      sonusEventTime }
    STATUS          current
    DESCRIPTION     
            "This trap indicates that a NIF's actual bandwidth is lower than the
             expected bandwidth minus 2 times the deviation amount.This trap will 
             be re-armed when the actual bandwdith reached the expected level."
    ::= { sonusIpInterfaceMIBNotificationsPrefix 9 }

sonusNrsLinkDownNotification NOTIFICATION-TYPE
    OBJECTS         { sonusShelfIndex, sonusSlotIndex, 
                      sonusEventDescription, sonusEventClass, 
                      sonusEventLevel, sonusSequenceId, sonusEventTime }
    STATUS          current
    DESCRIPTION     
            "This trap indicates that a link down event has been detected on a server"
    ::= { sonusIpInterfaceMIBNotificationsPrefix 10 }

sonusNrsLinkUpNotification NOTIFICATION-TYPE
    OBJECTS         { sonusShelfIndex, sonusSlotIndex, 
                      sonusEventDescription, sonusEventClass, 
                      sonusEventLevel, sonusSequenceId, sonusEventTime }
    STATUS          current
    DESCRIPTION     
            "This trap indicates that a link up event has event detected on a server"
    ::= { sonusIpInterfaceMIBNotificationsPrefix 11 }

sonusNrsNifCreatedNotification NOTIFICATION-TYPE
    OBJECTS         { sonusNifShelf, sonusNifSlot, sonusNifPort, 
                      sonusNifIndex, sonusNifName, sonusEventDescription, 
                      sonusEventClass, sonusEventLevel, sonusSequenceId, 
                      sonusEventTime }
    STATUS          current
    DESCRIPTION     
            "This trap indicates that a NIF's configuration is created."
    ::= { sonusIpInterfaceMIBNotificationsPrefix 12 }

sonusNrsSifOutOfServiceNotification NOTIFICATION-TYPE
    OBJECTS         { sonusNifShelf, sonusNifSlot, sonusNifPort, 
                      sonusNifIndex, sonusNifName, sonusNrsOosSifCount, 
                      sonusEventDescription, sonusEventClass, 
                      sonusEventLevel, sonusSequenceId, sonusEventTime }
    STATUS          current
    DESCRIPTION     
            "This trap indicates that a number of SIFs on a NIF are no longer
             available to
             support call processing."
    ::= { sonusIpInterfaceMIBNotificationsPrefix 13 }

sonusNrsLinkDetectionEnabledNotification NOTIFICATION-TYPE
    OBJECTS         { sonusNifShelf, sonusNifSlot, sonusNifPort, 
                      sonusEventDescription, sonusEventClass, 
                      sonusEventLevel, sonusSequenceId, sonusEventTime }
    STATUS          current
    DESCRIPTION     
            "This trap indicates that Link Detection is enabled."
    ::= { sonusIpInterfaceMIBNotificationsPrefix 14 }

sonusNrsLinkDetectionDisabledNotification NOTIFICATION-TYPE
    OBJECTS         { sonusNifShelf, sonusNifSlot, sonusNifPort, 
                      sonusEventDescription, sonusEventClass, 
                      sonusEventLevel, sonusSequenceId, sonusEventTime }
    STATUS          current
    DESCRIPTION     
            "This trap indicates that Link Detection is disabled."
    ::= { sonusIpInterfaceMIBNotificationsPrefix 15 }

sonusNrsLinkDetectionDestDownNotification NOTIFICATION-TYPE
    OBJECTS         { sonusNifShelf, sonusNifSlot, sonusNifPort, 
                      sonusNifIndex, sonusNifName, sonusNifIpAddress, 
                      sonusEventDescription, sonusEventClass, 
                      sonusEventLevel, sonusSequenceId, sonusEventTime }
    STATUS          current
    DESCRIPTION     
            "This trap indicates that Link Detection destination is down"
    ::= { sonusIpInterfaceMIBNotificationsPrefix 16 }

sonusNrsLinkDetectionDestUpNotification NOTIFICATION-TYPE
    OBJECTS         { sonusNifShelf, sonusNifSlot, sonusNifPort, 
                      sonusNifIndex, sonusNifName, sonusNifIpAddress, 
                      sonusEventDescription, sonusEventClass, 
                      sonusEventLevel, sonusSequenceId, sonusEventTime }
    STATUS          current
    DESCRIPTION     
            "This trap indicates that Link Detection destination is up"
    ::= { sonusIpInterfaceMIBNotificationsPrefix 17 }

sonusNrsPacketFilterModeChangeNotification NOTIFICATION-TYPE
    OBJECTS         { sonusNrsPacketFilterMode, sonusEventDescription, 
                      sonusEventClass, sonusEventLevel, sonusSequenceId, 
                      sonusEventTime }
    STATUS          current
    DESCRIPTION     
            "This trap indicates that Packet Filter Mode has changed"
    ::= { sonusIpInterfaceMIBNotificationsPrefix 18 }

sonusNrsLinkDetectionDestDownNotificationV6 NOTIFICATION-TYPE
    OBJECTS         { sonusNifShelf, sonusNifSlot, sonusNifPort, 
                      sonusNifIndex, sonusNifName, sonusNifIpv6Address, 
                      sonusEventDescription, sonusEventClass, 
                      sonusEventLevel, sonusSequenceId, sonusEventTime }
    STATUS          current
    DESCRIPTION     
            "This trap indicates that Link Detection destination is down"
    ::= { sonusIpInterfaceMIBNotificationsPrefix 19 }

sonusNrsLinkDetectionDestUpNotificationV6 NOTIFICATION-TYPE
    OBJECTS         { sonusNifShelf, sonusNifSlot, sonusNifPort, 
                      sonusNifIndex, sonusNifName, sonusNifIpv6Address, 
                      sonusEventDescription, sonusEventClass, 
                      sonusEventLevel, sonusSequenceId, sonusEventTime }
    STATUS          current
    DESCRIPTION     
            "This trap indicates that Link Detection destination is up"
    ::= { sonusIpInterfaceMIBNotificationsPrefix 20 }

sonusNrsDestinationFilterEntriesMaxNotification NOTIFICATION-TYPE
    OBJECTS         { sonusNifShelf, sonusNifSlot, sonusEventDescription, 
                      sonusEventClass, sonusEventLevel, sonusSequenceId, 
                      sonusEventTime }
    STATUS          current
    DESCRIPTION     
            "This trap indicates that we have reached maximum number
             of destination filter entries"
    ::= { sonusIpInterfaceMIBNotificationsPrefix 21 }

sonusTCPKeepAliveIdleTimeOutChangeNotification NOTIFICATION-TYPE
    OBJECTS         { sonusEventDescription, sonusEventClass, 
                      sonusEventLevel, sonusSequenceId, sonusEventTime, 
                      sonusNrsTcpKeepAliveIdleTimeOut, 
                      sonusNrsTcpKeepAliveIdleTimeOut }
    STATUS          current
    DESCRIPTION     
            "This trap indicates change in TCP KEEPALIVE IDLE TIME OUT value"
    ::= { sonusTCPGenMIBNotificationsPrefix 1 }

END -- end of module SONUS-IP-INTERFACE-MIB.
