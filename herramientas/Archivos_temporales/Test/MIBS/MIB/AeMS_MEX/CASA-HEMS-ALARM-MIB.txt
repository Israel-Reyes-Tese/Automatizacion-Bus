--
-- CASA-HEMS-ALARM-MIB.txt
-- TXT generated by MG-SOFT MIB Explorer Version 15.0 Build 1500
-- lunes, septiembre 05, 2022 at 09:42:21
--

CASA-HEMS-ALARM-MIB DEFINITIONS ::= BEGIN

	IMPORTS

		enterprises, MODULE-IDENTITY, NOTIFICATION-TYPE
			FROM SNMPv2-SMI;

--
-- Node definitions
--
	-- 1.3.6.1.4.1.20858.10.104.101
	casaHeMSAlarmMib MODULE-IDENTITY
		LAST-UPDATED "201804300000Z"		-- abril 30, 2018 at 00:00 GMT (201804300000Z)
		ORGANIZATION
			"CASA Systems Inc."
		CONTACT-INFO
			"Casa Systems Inc.     
			100 Old River Road, Suite 100           
			Andover, MA 01810     
			TEL: +1 978 688 6706     
			FAX: +1 978 688 6584		
			E-mail: support@casa-systems.com"
		DESCRIPTION
			"The Casa HeMS ALARM  MIB"
	::= { 1 3 6 1 4 1 20858 10 104 101 }

	-- 1.3.6.1.4.1.20858.10.104.101.1
	casaHeMSAlarmObjects OBJECT IDENTIFIER ::= { casaHeMSAlarmMib 1 }

	-- 1.3.6.1.4.1.20858.10.104.101.1.1
	neIdentity OBJECT-TYPE
		SYNTAX OCTET STRING
		MAX-ACCESS accessible-for-notify
		STATUS current
		DESCRIPTION
			"Ne Identity"
	::= { casaHeMSAlarmObjects 1 }

	-- 1.3.6.1.4.1.20858.10.104.101.1.2
	alarmID OBJECT-TYPE
		SYNTAX OCTET STRING
		MAX-ACCESS accessible-for-notify
		STATUS current
		DESCRIPTION
			"alarm ID"
	::= { casaHeMSAlarmObjects 2 }

	-- 1.3.6.1.4.1.20858.10.104.101.1.3
	notificationType OBJECT-TYPE
		SYNTAX OCTET STRING
		MAX-ACCESS accessible-for-notify
		STATUS current
		DESCRIPTION
			"alarm notificationType:
			'NewAlarm',
			'ChangedAlarm',
			'ClearedAlarm'"
	::= { casaHeMSAlarmObjects 3 }

	-- 1.3.6.1.4.1.20858.10.104.101.1.4
	eventType OBJECT-TYPE
		SYNTAX OCTET STRING
		MAX-ACCESS accessible-for-notify
		STATUS current
		DESCRIPTION
			"alarm eventType:
			'Communication Alarm',
			'Processing error Alarm',
			'Equipment Alarm',
			'Environmental Alarm',
			'Quality of Service Alarm',
			'Integrity Violation',
			'Operational Violation',
			'Physical Violation',
			'Security Service or Mechanism Violation'"
	::= { casaHeMSAlarmObjects 4 }

	-- 1.3.6.1.4.1.20858.10.104.101.1.5
	probableCause OBJECT-TYPE
		SYNTAX OCTET STRING
		MAX-ACCESS accessible-for-notify
		STATUS current
		DESCRIPTION
			"alarm probableCause"
	::= { casaHeMSAlarmObjects 5 }

	-- 1.3.6.1.4.1.20858.10.104.101.1.6
	specificProblem OBJECT-TYPE
		SYNTAX OCTET STRING
		MAX-ACCESS accessible-for-notify
		STATUS current
		DESCRIPTION
			"alarm specificProblem"
	::= { casaHeMSAlarmObjects 6 }

	-- 1.3.6.1.4.1.20858.10.104.101.1.7
	perceivedSeverity OBJECT-TYPE
		SYNTAX OCTET STRING
		MAX-ACCESS accessible-for-notify
		STATUS current
		DESCRIPTION
			"alarm perceivedSeverity:
			'Critical,
			'Major',
			'Minor',
			'Warning',
			'Indeterminate'"
	::= { casaHeMSAlarmObjects 7 }

	-- 1.3.6.1.4.1.20858.10.104.101.1.8
	additionalText OBJECT-TYPE
		SYNTAX OCTET STRING
		MAX-ACCESS accessible-for-notify
		STATUS current
		DESCRIPTION
			"This provides a textual string which is vendor defined."
	::= { casaHeMSAlarmObjects 8 }

	-- 1.3.6.1.4.1.20858.10.104.101.1.9
	additionalInformation OBJECT-TYPE
		SYNTAX OCTET STRING
		MAX-ACCESS accessible-for-notify
		STATUS current
		DESCRIPTION
			"This contains additional information about the alarm and is vendor defined."
	::= { casaHeMSAlarmObjects 9 }

	-- 1.3.6.1.4.1.20858.10.104.101.1.10
	eventTime OBJECT-TYPE
		SYNTAX OCTET STRING
		MAX-ACCESS accessible-for-notify
		STATUS current
		DESCRIPTION
			"Indicates the date and time when the alarm event occurs."
	::= { casaHeMSAlarmObjects 10 }

	-- 1.3.6.1.4.1.20858.10.104.101.2
	casaHeMSAlarmTraps OBJECT IDENTIFIER ::= { casaHeMSAlarmMib 2 }

	-- 1.3.6.1.4.1.20858.10.104.101.2.1
	casaHeMSSystemAlarm OBJECT IDENTIFIER ::= { casaHeMSAlarmTraps 1 }

	-- 1.3.6.1.4.1.20858.10.104.101.2.1.1
	memoryUsageIsHigh NOTIFICATION-TYPE
		OBJECTS { neIdentity, alarmID, notificationType, eventType, probableCause, 
		specificProblem, perceivedSeverity, additionalText, 
		additionalInformation, eventTime } 
		STATUS current
		DESCRIPTION
			"AeMS Memory usage is high"
	::= { casaHeMSSystemAlarm 1 }

	-- 1.3.6.1.4.1.20858.10.104.101.2.1.2
	cpuUsageIsHigh NOTIFICATION-TYPE
		OBJECTS { neIdentity, alarmID, notificationType, eventType, probableCause, 
		specificProblem, perceivedSeverity, additionalText, 
		additionalInformation, eventTime } 
		STATUS current
		DESCRIPTION
			"AeMS CPU usage is high"
	::= { casaHeMSSystemAlarm 2 }

	-- 1.3.6.1.4.1.20858.10.104.101.2.1.3
	hardDiskUsageIsHigh NOTIFICATION-TYPE
		OBJECTS { neIdentity, alarmID, notificationType, eventType, probableCause, 
		specificProblem, perceivedSeverity, additionalText, 
		additionalInformation, eventTime } 
		STATUS current
		DESCRIPTION
			"AeMS Hard disk usage is high"
	::= { casaHeMSSystemAlarm 3 }

	-- 1.3.6.1.4.1.20858.10.104.101.2.1.4
	haCommunicationAlarm NOTIFICATION-TYPE
		OBJECTS { neIdentity, alarmID, notificationType, eventType, probableCause, 
		specificProblem, perceivedSeverity, additionalText, 
		additionalInformation, eventTime } 
		STATUS current
		DESCRIPTION
			"AeMS HA communication alarm"
	::= { casaHeMSSystemAlarm 4 }

	-- 1.3.6.1.4.1.20858.10.104.101.2.1.5
	dbSlaveConnectionAlarm NOTIFICATION-TYPE
		OBJECTS { neIdentity, alarmID, notificationType, eventType, probableCause, 
		specificProblem, perceivedSeverity, additionalText, 
		additionalInformation, eventTime } 
		STATUS current
		DESCRIPTION
			"AeMS DB slave connection alarm"
	::= { casaHeMSSystemAlarm 5 }

	-- 1.3.6.1.4.1.20858.10.104.101.2.1.6
	dbArbiterConnectionAlarm NOTIFICATION-TYPE
		OBJECTS { neIdentity, alarmID, notificationType, eventType, probableCause, 
		specificProblem, perceivedSeverity, additionalText, 
		additionalInformation, eventTime } 
		STATUS current
		DESCRIPTION
			"AeMS DB arbiter connection alarm"
	::= { casaHeMSSystemAlarm 6 }

END

-- This feature is available only in the licensed version of MG-SOFT MIB Explorer.
-- Contact <sales@mg-soft.com> to order the licensed version of the software.
