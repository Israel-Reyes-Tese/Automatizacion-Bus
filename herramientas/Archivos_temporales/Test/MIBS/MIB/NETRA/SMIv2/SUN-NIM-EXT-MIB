--
-- This SMIv2 module has been generated by smidump 0.2-cvs. Do not edit.
--

SUN-NIM-EXT-MIB DEFINITIONS ::= BEGIN

IMPORTS
    entPhysicalIndex
        FROM ENTITY-MIB
    SnmpAdminString
        FROM SNMP-FRAMEWORK-MIB
    Integer32, MODULE-IDENTITY, NOTIFICATION-TYPE, OBJECT-IDENTITY, 
    OBJECT-TYPE, Unsigned32, enterprises
        FROM SNMPv2-SMI
    TEXTUAL-CONVENTION, TruthValue
        FROM SNMPv2-TC
    SunNimPercentage
        FROM SUN-NET-INFO-MIB;

sunNemMIB MODULE-IDENTITY
    LAST-UPDATED    "197001010000Z"
    ORGANIZATION    
            "Sun Microsystems, Inc."
    CONTACT-INFO    
            ""
    DESCRIPTION     
            "SUN-NIM-EXT-MIB.mib Version 1.8
             Copyright (c) 2000, by Sun Microsystems, Inc.
             All rights reserved.
             
             This MIB module provides extensions to the SUN-NET-INFO-MIB to provide
             attributes in addition to those presented in ITU-T M.3100.
             
             The SUN-NET-INFO-MIB provides extensions to the ENTITY-MIB (RFC2737)
             where each physical entity modelled in the system is represented by
             means of extensions to the entPhyscialTable. Certain of the attributes
             in the entPhyscialTable are not applicable to the model presented by
             the SUN-NET-INFO-MIB, but are to the SUN-NIM-EXT-MIB, and so are
             explained below:
             
             The entries in the entPhysicalTable have the following significance
             with respect to the SUN-NIM-EXT-MIB model:
             
             entPhysicalIndex           Index for table extensions.
             entPhysicalDescr           modelDescr
             entPhysicalVendorType      n/a
             entPhysicalContainedIn     n/a
             entPhysicalClass           Used to select applicable table extensions.
             entPhysicalParentRelPos    n/a
             entPhysicalName            logicalName
             entPhysicalHardwareRev     n/a
             entPhysicalFirmwareRev     n/a
             entPhysicalSoftwareRev     n/a
             entPhysicalSerialNum       serialNumber
             entPhysicalMfgName         n/a
             entPhysicalModelName       partNumber
             entPhysicalAlias           n/a
             entPhysicalAssetID         n/a
             entPhysicalIsFRU           n/a
             
             modelDescr
             This is a read-only SnmpAdminString which gives the manufacturers 
             model name for the entity.
             
             logicalName
             This is a read-only SnmpAdminString which gives the logical name
             by which the entity is known to the system, e.g. 'ttya'.
             
             serialNumber
             This is a read-write SnmpAdminString which gives the manufacturers
             serial number for the entity, if applicable. This attribute may
             be implemented as read-only.
             
             partNumber
             This is a read-only SnmpAdminString which gives the customer visible
             part number for the entity, if applicable.
             
             Note that attributes such as serialNumber and partNumber are only
             meaningful when accompanied by the entPhysicalMfgName which is
             populated by the SUN-NET-INFO-MIB model."
    REVISION        "197001010000Z"
    DESCRIPTION     
            "Initial version of MIB module SUN-NIM-EXT-MIB."
    ::= { enterprises 42 2 25 99 3 }


SunNemPhysicalClass ::= TEXTUAL-CONVENTION
    STATUS          current
    DESCRIPTION     
            "An enumeration of possible physical classes where entPhysicalClass
             is specified as other(1)."
    SYNTAX          INTEGER { other(1), alarm(2), watchdog(3) }

SunNemSensorClass ::= TEXTUAL-CONVENTION
    STATUS          current
    DESCRIPTION     
            "An enumeration of possible sensor classes where entPhysicalClass
             is specified as sensor(8)."
    SYNTAX          INTEGER { binary(1), numeric(2) }

SunNemSensorType ::= TEXTUAL-CONVENTION
    STATUS          current
    DESCRIPTION     
            "An enumeration of possible sensor types where entPhysicalClass
             is specified as sensor(8)."
    SYNTAX          INTEGER { other(1), unknown(2), temperature(3), 
                        voltage(4), current(5), tachometer(6), 
                        counter(7), switch(8), lock(9), humidity(10), 
                        smokeDetection(11), presence(12), airFlow(13) }

SunNemBaseUnits ::= TEXTUAL-CONVENTION
    STATUS          current
    DESCRIPTION     
            "Physical values are represented in the units obtained by 
             (sunNemBaseUnits * 10 raised to the power of sunNemExponent). For 
             example, if sunNemBaseUnits is volts(6) and sunNemExponent is -6, 
             then the units of the values returned are microVolts."
    SYNTAX          INTEGER { other(1), unknown(2), degC(3), degF(4), 
                        degK(5), volts(6), amps(7), watts(8), joules(9), 
                        coulombs(10), va(11), nits(12), lumens(13), 
                        lux(14), candelas(15), kPa(16), psi(17), 
                        newtons(18), cfm(19), rpm(20), hertz(21), 
                        seconds(22), minutes(23), hours(24), days(25), 
                        weeks(26), mils(27), inches(28), feet(29), 
                        cubicInches(30), cubicFeet(31), meters(32), 
                        cubicCentimeters(33), cubicMeters(34), 
                        liters(35), fluidOunces(36), radians(37), 
                        steradians(38), revolutions(39), cycles(40), 
                        gravities(41), ounces(42), pounds(43), 
                        footPounds(44), ounceInches(45), gauss(46), 
                        gilberts(47), henries(48), farads(49), ohms(50), 
                        siemens(51), moles(52), becquerels(53), ppm(54), 
                        decibels(55), dBA(56), dbC(57), grays(58), 
                        sieverts(59), colorTemperatureDegK(60), bits(61), 
                        bytes(62), words(63), doubleWords(64), 
                        quadWords(65), percentage(66) }

SunNemRateUnits ::= TEXTUAL-CONVENTION
    STATUS          current
    DESCRIPTION     
            "If sunNemRateUnits is set to a value other than none(1), 
             then the units specified by sunNemBaseUnits are further 
             qualified as rate units. For example, if sunNemBaseUnits
             is set to degC(3), and sunNemRateUnits is set to perSecond(4), 
             then the value represented has the units degC/Second."
    SYNTAX          INTEGER { none(1), perMicroSecond(2), 
                        perMilliSecond(3), perSecond(4), perMinute(5), 
                        perHour(6), perDay(7), perWeek(8), perMonth(9), 
                        perYear(10) }

SunNemAlarmType ::= TEXTUAL-CONVENTION
    STATUS          current
    DESCRIPTION     
            "This indicates the type of alarm - i.e. the means by which the
             alarm condition is communicated."
    SYNTAX          INTEGER { other(1), audible(2), visible(3), 
                        motion(4), switch(5) }

SunNemAlarmState ::= TEXTUAL-CONVENTION
    STATUS          current
    DESCRIPTION     
            "This indicates the state of the alarm."
    SYNTAX          INTEGER { unknown(1), off(2), steady(3), 
                        alternating(4) }

SunNemWatchdogAction ::= TEXTUAL-CONVENTION
    STATUS          current
    DESCRIPTION     
            "This indicates the action taken by the watchdog if it is not reset
             within the period specified by sunNemWatchdogTimeout."
    SYNTAX          INTEGER { statusOnly(1), systemInterrupt(2), 
                        systemReset(3), systemPowerOff(4), 
                        systemPowerCycle(5) }

sun OBJECT IDENTIFIER
    ::= { enterprises 42 }

products OBJECT IDENTIFIER
    ::= { enterprises 42 2 }

netra OBJECT IDENTIFIER
    ::= { enterprises 42 2 25 }

netra-test OBJECT IDENTIFIER
    ::= { enterprises 42 2 25 99 }

sunNemMIBObjects OBJECT IDENTIFIER
    ::= { sunNemMIB 1 }

sunNemPhysicalTable OBJECT-TYPE
    SYNTAX          SEQUENCE OF SunNemPhysicalEntry
    MAX-ACCESS      not-accessible
    STATUS          current
    DESCRIPTION     
            "The NEM Physical Class Table extension. This table is used to define
             the physical class of the entity if it is classified as other(1).
             
             The sunNemPhysicalTable is valid for the entPhysicalClass value of
             other(1)."
    ::= { sunNemMIBObjects 1 }

sunNemPhysicalEntry OBJECT-TYPE
    SYNTAX          SunNemPhysicalEntry
    MAX-ACCESS      not-accessible
    STATUS          current
    DESCRIPTION     
            "An entry in the NEM Physical Class Table extension.  Each entry
             of this table represents a piece of equipment with an
             entPhysicalClass of other(1)."
    INDEX           { entPhysicalIndex }
    ::= { sunNemPhysicalTable 1 }

SunNemPhysicalEntry ::=
    SEQUENCE {
        sunNemPhysicalClass             SunNemPhysicalClass
    }

sunNemPhysicalClass OBJECT-TYPE
    SYNTAX          SunNemPhysicalClass
    MAX-ACCESS      read-only
    STATUS          current
    DESCRIPTION     
            "An enumeration of possible physical classes where entPhysicalClass
             is specified as other(1)."
    ::= { sunNemPhysicalEntry 1 }

sunNemSensorTable OBJECT-TYPE
    SYNTAX          SEQUENCE OF SunNemSensorEntry
    MAX-ACCESS      not-accessible
    STATUS          current
    DESCRIPTION     
            "The NEM Sensor Table extension. This table augments the 
             entPhysicalTable to provide the attributes common to all sensors.
             
             The sunNemSensorTable is valid for the entPhysicalClass value of
             sensor(8)."
    ::= { sunNemMIBObjects 2 }

sunNemSensorEntry OBJECT-TYPE
    SYNTAX          SunNemSensorEntry
    MAX-ACCESS      not-accessible
    STATUS          current
    DESCRIPTION     
            "An entry in the NEM Sensor Table extension.  Each entry
             of this table represents a piece of equipment with an
             entPhysicalClass of sensor(8)."
    INDEX           { entPhysicalIndex }
    ::= { sunNemSensorTable 1 }

SunNemSensorEntry ::=
    SEQUENCE {
        sunNemSensorClass               SunNemSensorClass,
        sunNemSensorType                SunNemSensorType,
        sunNemSensorLatency             Unsigned32
    }

sunNemSensorClass OBJECT-TYPE
    SYNTAX          SunNemSensorClass
    MAX-ACCESS      read-only
    STATUS          current
    DESCRIPTION     
            "An enumeration of possible sensor classes where entPhysicalClass
             is specified as sensor(8)."
    ::= { sunNemSensorEntry 1 }

sunNemSensorType OBJECT-TYPE
    SYNTAX          SunNemSensorType
    MAX-ACCESS      read-only
    STATUS          current
    DESCRIPTION     
            "An enumeration of possible sensor types where entPhysicalClass
             is specified as sensor(8)."
    ::= { sunNemSensorEntry 2 }

sunNemSensorLatency OBJECT-TYPE
    SYNTAX          Unsigned32
    MAX-ACCESS      read-only
    STATUS          current
    DESCRIPTION     
            "Where the sensor is polled this value represents the update interval
             for this sensor measured in mS. Where the sensor is event driven
             rather than polled, this value should represent the maximum expected
             latency in processing that event."
    ::= { sunNemSensorEntry 3 }

sunNemBinarySensorTable OBJECT-TYPE
    SYNTAX          SEQUENCE OF SunNemBinarySensorEntry
    MAX-ACCESS      not-accessible
    STATUS          current
    DESCRIPTION     
            "The NEM BinarySensor Table extension. This table augments the 
             sunNemSensorTable to provide the attributes specific to binary sensors.
             
             The sunNemBinarySensorTable is valid for the sunNemSensorClass value of
             binary(1)."
    ::= { sunNemMIBObjects 3 }

sunNemBinarySensorEntry OBJECT-TYPE
    SYNTAX          SunNemBinarySensorEntry
    MAX-ACCESS      not-accessible
    STATUS          current
    DESCRIPTION     
            "An entry in the NEM BinarySensor Table extension.  Each entry
             of this table represents a sensor with a sunNemSensorClass value of
             binary(1)."
    INDEX           { entPhysicalIndex }
    ::= { sunNemBinarySensorTable 1 }

SunNemBinarySensorEntry ::=
    SEQUENCE {
        sunNemBinarySensorCurrent       TruthValue,
        sunNemBinarySensorExpected      TruthValue,
        sunNemBinarySensorInterpretTrue SnmpAdminString,
        sunNemBinarySensorInterpretFalse SnmpAdminString
    }

sunNemBinarySensorCurrent OBJECT-TYPE
    SYNTAX          TruthValue
    MAX-ACCESS      read-only
    STATUS          current
    DESCRIPTION     
            "The current state of the sensor."
    ::= { sunNemBinarySensorEntry 1 }

sunNemBinarySensorExpected OBJECT-TYPE
    SYNTAX          TruthValue
    MAX-ACCESS      read-only
    STATUS          current
    DESCRIPTION     
            "The expected state of the sensor. If there is no expected value then
             no value is returned for this attribute."
    ::= { sunNemBinarySensorEntry 2 }

sunNemBinarySensorInterpretTrue OBJECT-TYPE
    SYNTAX          SnmpAdminString
    MAX-ACCESS      read-only
    STATUS          current
    DESCRIPTION     
            "The interpretation to be applied to a sensor reading of true."
    ::= { sunNemBinarySensorEntry 3 }

sunNemBinarySensorInterpretFalse OBJECT-TYPE
    SYNTAX          SnmpAdminString
    MAX-ACCESS      read-only
    STATUS          current
    DESCRIPTION     
            "The interpretation to be applied to a sensor reading of false."
    ::= { sunNemBinarySensorEntry 4 }

sunNemNumericSensorTable OBJECT-TYPE
    SYNTAX          SEQUENCE OF SunNemNumericSensorEntry
    MAX-ACCESS      not-accessible
    STATUS          current
    DESCRIPTION     
            "The NEM NumericSensor Table extension. This table augments the 
             sunNemSensorTable to provide the attributes specific to numeric 
             sensors.
             
             The sunNemNumericSensorTable is valid for the sunNemSensorClass value 
             of numeric(1)."
    ::= { sunNemMIBObjects 4 }

sunNemNumericSensorEntry OBJECT-TYPE
    SYNTAX          SunNemNumericSensorEntry
    MAX-ACCESS      not-accessible
    STATUS          current
    DESCRIPTION     
            "An entry in the NEM NumericSensor Table extension.  Each entry
             of this table represents a sensor with a sunNemSensorClass value of
             numeric(1)."
    INDEX           { entPhysicalIndex }
    ::= { sunNemNumericSensorTable 1 }

SunNemNumericSensorEntry ::=
    SEQUENCE {
        sunNemNumericSensorBaseUnits    SunNemBaseUnits,
        sunNemNumericSensorExponent     Integer32,
        sunNemNumericSensorRateUnits    SunNemRateUnits,
        sunNemNumericSensorCurrent      Integer32,
        sunNemNumericSensorNormalMin    Integer32,
        sunNemNumericSensorNormalMax    Integer32,
        sunNemNumericSensorAccuracy     SunNimPercentage
    }

sunNemNumericSensorBaseUnits OBJECT-TYPE
    SYNTAX          SunNemBaseUnits
    MAX-ACCESS      read-only
    STATUS          current
    DESCRIPTION     
            "The base unit of the values returned by this Sensor.
             
             Physical values are represented in the units obtained by 
             (sunNemBaseUnits * 10 raised to the power of sunNemExponent). For 
             example, if sunNemBaseUnits is volts(6) and sunNemExponent is -6, 
             then the units of the values returned are microVolts."
    ::= { sunNemNumericSensorEntry 1 }

sunNemNumericSensorExponent OBJECT-TYPE
    SYNTAX          Integer32
    MAX-ACCESS      read-only
    STATUS          current
    DESCRIPTION     
            "The exponent to be applied to the units returned by this sensor."
    ::= { sunNemNumericSensorEntry 2 }

sunNemNumericSensorRateUnits OBJECT-TYPE
    SYNTAX          SunNemRateUnits
    MAX-ACCESS      read-only
    STATUS          current
    DESCRIPTION     
            "If sunNemRateUnits is set to a value other than none(1), 
             then the units specified by sunNemBaseUnits are further 
             qualified as rate units. For example, if sunNemBaseUnits
             is set to degC(3), and sunNemRateUnits is set to perSecond(4), 
             then the value represented has the units degC/Second."
    ::= { sunNemNumericSensorEntry 3 }

sunNemNumericSensorCurrent OBJECT-TYPE
    SYNTAX          Integer32
    MAX-ACCESS      read-only
    STATUS          current
    DESCRIPTION     
            "The current state of the sensor."
    ::= { sunNemNumericSensorEntry 4 }

sunNemNumericSensorNormalMin OBJECT-TYPE
    SYNTAX          Integer32
    MAX-ACCESS      read-only
    STATUS          current
    DESCRIPTION     
            "The lowest expected value from this sensor. If there is no minimum
             value then no value is returned for this attribute."
    ::= { sunNemNumericSensorEntry 5 }

sunNemNumericSensorNormalMax OBJECT-TYPE
    SYNTAX          Integer32
    MAX-ACCESS      read-only
    STATUS          current
    DESCRIPTION     
            "The highest expected value from this sensor. If there is no maximum
             value then no value is returned for this attribute."
    ::= { sunNemNumericSensorEntry 6 }

sunNemNumericSensorAccuracy OBJECT-TYPE
    SYNTAX          SunNimPercentage
    MAX-ACCESS      read-only
    STATUS          current
    DESCRIPTION     
            "The accuracy of this sensor expressed as a +/-% value."
    ::= { sunNemNumericSensorEntry 7 }

sunNemFanTable OBJECT-TYPE
    SYNTAX          SEQUENCE OF SunNemFanEntry
    MAX-ACCESS      not-accessible
    STATUS          current
    DESCRIPTION     
            "The NEM Fan Table extension. This table augments the 
             entPhysicalTable to provide the attributes common to all fans.
             
             The sunNemFanTable is valid for the entPhysicalClass value of
             fan(7)."
    ::= { sunNemMIBObjects 5 }

sunNemFanEntry OBJECT-TYPE
    SYNTAX          SunNemFanEntry
    MAX-ACCESS      not-accessible
    STATUS          current
    DESCRIPTION     
            "An entry in the NEM Fan Table extension.  Each entry
             of this table represents a piece of equipment with an
             entPhysicalClass of fan(7)."
    INDEX           { entPhysicalIndex }
    ::= { sunNemFanTable 1 }

SunNemFanEntry ::=
    SEQUENCE {
        sunNemFanVariableSpeed          TruthValue
    }

sunNemFanVariableSpeed OBJECT-TYPE
    SYNTAX          TruthValue
    MAX-ACCESS      read-only
    STATUS          current
    DESCRIPTION     
            "A boolean which is set to true if the fan speed is variable."
    ::= { sunNemFanEntry 1 }

sunNemAlarmTable OBJECT-TYPE
    SYNTAX          SEQUENCE OF SunNemAlarmEntry
    MAX-ACCESS      not-accessible
    STATUS          current
    DESCRIPTION     
            "The NEM Alarm Table extension. This table augments the 
             entPhysicalTable to provide indications of alarm states.
             
             The sunNemAlarmTable is valid for the sunNemPhysicalClass value of
             alarm(2)."
    ::= { sunNemMIBObjects 6 }

sunNemAlarmEntry OBJECT-TYPE
    SYNTAX          SunNemAlarmEntry
    MAX-ACCESS      not-accessible
    STATUS          current
    DESCRIPTION     
            "An entry in the NEM Alarm Table extension.  Each entry
             of this table represents a piece of equipment with an
             sunNemPhysicalClass of alarm(2)."
    INDEX           { entPhysicalIndex }
    ::= { sunNemAlarmTable 1 }

SunNemAlarmEntry ::=
    SEQUENCE {
        sunNemAlarmType                 SunNemAlarmType,
        sunNemAlarmState                SunNemAlarmState
    }

sunNemAlarmType OBJECT-TYPE
    SYNTAX          SunNemAlarmType
    MAX-ACCESS      read-only
    STATUS          current
    DESCRIPTION     
            "This indicates the type of alarm - i.e. the means by which the
             alarm condition is communicated."
    ::= { sunNemAlarmEntry 1 }

sunNemAlarmState OBJECT-TYPE
    SYNTAX          SunNemAlarmState
    MAX-ACCESS      read-only
    STATUS          current
    DESCRIPTION     
            "This indicates the state of the alarm."
    ::= { sunNemAlarmEntry 2 }

sunNemWatchdogTable OBJECT-TYPE
    SYNTAX          SEQUENCE OF SunNemWatchdogEntry
    MAX-ACCESS      not-accessible
    STATUS          current
    DESCRIPTION     
            "The NEM Watchdog Table extension. This table augments the 
             entPhysicalTable to provide information about a watchdog timer.
             
             The sunNemWatchdogTable is valid for the sunNemPhysicalClass value of
             watchdog(3)."
    ::= { sunNemMIBObjects 7 }

sunNemWatchdogEntry OBJECT-TYPE
    SYNTAX          SunNemWatchdogEntry
    MAX-ACCESS      not-accessible
    STATUS          current
    DESCRIPTION     
            "An entry in the NEM Watchdog Table extension.  Each entry
             of this table represents a piece of equipment with an
             sunNemPhysicalClass of watchdog(3)."
    INDEX           { entPhysicalIndex }
    ::= { sunNemWatchdogTable 1 }

SunNemWatchdogEntry ::=
    SEQUENCE {
        sunNemWatchdogTimeout           Unsigned32,
        sunNemWatchdogAction            SunNemWatchdogAction
    }

sunNemWatchdogTimeout OBJECT-TYPE
    SYNTAX          Unsigned32
    MAX-ACCESS      read-only
    STATUS          current
    DESCRIPTION     
            "This indicates the interval in mS after which the watchdog will
             timeout if not reset."
    ::= { sunNemWatchdogEntry 1 }

sunNemWatchdogAction OBJECT-TYPE
    SYNTAX          SunNemWatchdogAction
    MAX-ACCESS      read-only
    STATUS          current
    DESCRIPTION     
            "This indicates the action taken by the watchdog if it is not reset
             within the period specified by sunNemWatchdogTimeout."
    ::= { sunNemWatchdogEntry 2 }

END -- end of module SUN-NIM-EXT-MIB.
