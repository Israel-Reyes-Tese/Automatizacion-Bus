--
-- This SMIv2 module has been generated by smidump 0.2-cvs. Do not edit.
--

DVMRP-MIB DEFINITIONS ::= BEGIN

IMPORTS
    ifIndex
        FROM RFC1213-MIB
    MODULE-COMPLIANCE, OBJECT-GROUP
        FROM SNMPv2-CONF
    Counter32, Gauge32, Integer32, IpAddress, MODULE-IDENTITY, 
    OBJECT-TYPE, TimeTicks, experimental
        FROM SNMPv2-SMI
    DisplayString, RowStatus
        FROM SNMPv2-TC;

dvmrpMIB MODULE-IDENTITY
    LAST-UPDATED    "199704171500Z"
    ORGANIZATION    
            "IETF IDMR Working Group."
    CONTACT-INFO    
            " Dave Thaler
             University of Michigan
             1301 Beal Ave.
             Ann Arbor, MI 48109-2122
             EMail: thalerd@eecs.umich.edu"
    DESCRIPTION     
            "The MIB module for management of DVMRP routers."
    ::= { experimental 62 }


dvmrpMIBObjects OBJECT IDENTIFIER
    ::= { dvmrpMIB 1 }

dvmrp OBJECT IDENTIFIER
    ::= { dvmrpMIBObjects 1 }

dvmrpVersionString OBJECT-TYPE
    SYNTAX          DisplayString
    MAX-ACCESS      read-only
    STATUS          current
    DESCRIPTION     
            "The router's DVMRP version information."
    ::= { dvmrp 1 }

dvmrpGenerationId OBJECT-TYPE
    SYNTAX          Integer32
    MAX-ACCESS      read-only
    STATUS          current
    DESCRIPTION     
            "The generation identifier for the routing process.  This is
             used by neighboring routers to detect whether the DVMRP
             routing table should be resent."
    ::= { dvmrp 2 }

dvmrpInterfaceTable OBJECT-TYPE
    SYNTAX          SEQUENCE OF DvmrpInterfaceEntry
    MAX-ACCESS      not-accessible
    STATUS          current
    DESCRIPTION     
            "The (conceptual) table listing the router's multicast-
             capable interfaces."
    ::= { dvmrp 3 }

dvmrpInterfaceEntry OBJECT-TYPE
    SYNTAX          DvmrpInterfaceEntry
    MAX-ACCESS      not-accessible
    STATUS          current
    DESCRIPTION     
            "An entry (conceptual row) in the dvmrpInterfaceTable.
             This row augments ipMRouteInterfaceEntry in the IP
             Multicast MIB, where the threshold object resides."
    INDEX           { ifIndex }
    ::= { dvmrpInterfaceTable 1 }

DvmrpInterfaceEntry ::=
    SEQUENCE {
        dvmrpInterfaceType              INTEGER,
        dvmrpInterfaceOperState         INTEGER,
        dvmrpInterfaceLocalAddress      IpAddress,
        dvmrpInterfaceRemoteAddress     IpAddress,
        dvmrpInterfaceRemoteSubnetMask  IpAddress,
        dvmrpInterfaceMetric            Integer32,
        dvmrpInterfaceRateLimit         Integer32,
        dvmrpInterfaceInPkts            Counter32,
        dvmrpInterfaceOutPkts           Counter32,
        dvmrpInterfaceInOctets          Counter32,
        dvmrpInterfaceOutOctets         Counter32,
        dvmrpInterfaceStatus            RowStatus,
        dvmrpInterfaceRcvBadPkts        Counter32,
        dvmrpInterfaceRcvBadRoutes      Counter32
    }

dvmrpInterfaceType OBJECT-TYPE
    SYNTAX          INTEGER { tunnel(1), srcrt(2), querier(3), subnet(4) }
    MAX-ACCESS      read-only
    STATUS          deprecated
    DESCRIPTION     
            "The type of this DVMRP interface, whether it uses
             a tunnel, source routing, a physical interface for which
             we are a querier, or a physical interface for which we are
             not a querier.  This object is deprecated in favor of
             ifType."
    DEFVAL          { tunnel }
    ::= { dvmrpInterfaceEntry 2 }

dvmrpInterfaceOperState OBJECT-TYPE
    SYNTAX          INTEGER { up(1), down(2) }
    MAX-ACCESS      read-only
    STATUS          deprecated
    DESCRIPTION     
            "The current operational state of this DVMRP interface.
             This object is deprecated in favor of ifOperStatus."
    ::= { dvmrpInterfaceEntry 3 }

dvmrpInterfaceLocalAddress OBJECT-TYPE
    SYNTAX          IpAddress
    MAX-ACCESS      read-create
    STATUS          current
    DESCRIPTION     
            "The IP address this system will use as a source
             address on this interface.  On unnumbered interfaces,
             it must be the same value as dvmrpInterfaceLocalAddress
             for some interface on the system."
    ::= { dvmrpInterfaceEntry 4 }

dvmrpInterfaceRemoteAddress OBJECT-TYPE
    SYNTAX          IpAddress
    MAX-ACCESS      read-create
    STATUS          deprecated
    DESCRIPTION     
            "The IP address of the remote end of this DVMRP virtual
             interface.  For a tunnel (including source routed), this
             is the IP address of the neighboring router.  For a subnet,
             this is the subnet address.  This object is deprecated in
             favor of address information associated with the
             underlying ifEntry."
    ::= { dvmrpInterfaceEntry 5 }

dvmrpInterfaceRemoteSubnetMask OBJECT-TYPE
    SYNTAX          IpAddress
    MAX-ACCESS      read-only
    STATUS          deprecated
    DESCRIPTION     
            "The subnet mask for a directly connected subnet.  For
             a tunnel, this should be 0.0.0.0.  This object is
             deprecated in favor of address information associated
             with the underlying ifEntry."
    ::= { dvmrpInterfaceEntry 6 }

dvmrpInterfaceMetric OBJECT-TYPE
    SYNTAX          Integer32 (1..31)
    MAX-ACCESS      read-create
    STATUS          current
    DESCRIPTION     
            "The distance metric for this interface which is used to
             calculate distance vectors."
    DEFVAL          { 1 }
    ::= { dvmrpInterfaceEntry 7 }

dvmrpInterfaceRateLimit OBJECT-TYPE
    SYNTAX          Integer32
    MAX-ACCESS      read-create
    STATUS          deprecated
    DESCRIPTION     
            "The rate-limit, in kilobits per second, of forwarded
             multicast traffic on the interface.  A rate-limit of 0
             indicates that no rate limiting is done.  This object
             has been moved to the IP Multicast MIB."
    DEFVAL          { 0 }
    ::= { dvmrpInterfaceEntry 8 }

dvmrpInterfaceInPkts OBJECT-TYPE
    SYNTAX          Counter32
    MAX-ACCESS      read-only
    STATUS          deprecated
    DESCRIPTION     
            "The number of multicast packets that have arrived on the
             interface.  This object is deprecated in favor of
             ifInMulticastPkts in the Interfaces MIB [8]."
    ::= { dvmrpInterfaceEntry 9 }

dvmrpInterfaceOutPkts OBJECT-TYPE
    SYNTAX          Counter32
    MAX-ACCESS      read-only
    STATUS          deprecated
    DESCRIPTION     
            "The number of multicast packets that have been sent on the
             interface.  This object is deprecated in favor of
             ifOutMulticastPkts in the Interfaces MIB [8]."
    ::= { dvmrpInterfaceEntry 10 }

dvmrpInterfaceInOctets OBJECT-TYPE
    SYNTAX          Counter32
    MAX-ACCESS      read-only
    STATUS          deprecated
    DESCRIPTION     
            "The number of octets in multicast packets that have arrived
             on the interface.  This object has been moved to the
             IP Multicast MIB."
    ::= { dvmrpInterfaceEntry 11 }

dvmrpInterfaceOutOctets OBJECT-TYPE
    SYNTAX          Counter32
    MAX-ACCESS      read-only
    STATUS          deprecated
    DESCRIPTION     
            "The number of octets in multicast packets that have been
             sent
             on the interface.  This object has been moved to the
             IP Multicast MIB."
    ::= { dvmrpInterfaceEntry 12 }

dvmrpInterfaceStatus OBJECT-TYPE
    SYNTAX          RowStatus
    MAX-ACCESS      read-create
    STATUS          current
    DESCRIPTION     
            "The status of this entry.  Creating the entry enables
             DVMRP on the virtual interface; destroying the entry
             or setting it to notInService disables DVMRP on the
             virtual interface."
    ::= { dvmrpInterfaceEntry 13 }

dvmrpInterfaceRcvBadPkts OBJECT-TYPE
    SYNTAX          Counter32
    MAX-ACCESS      read-only
    STATUS          current
    DESCRIPTION     
            "The number of DVMRP packets received on the interface
             by the DVMRP process which were subsequently discarded
             as invalid (e.g. invalid packet format, or a route
             report from an unknown neighbor)."
    ::= { dvmrpInterfaceEntry 14 }

dvmrpInterfaceRcvBadRoutes OBJECT-TYPE
    SYNTAX          Counter32
    MAX-ACCESS      read-only
    STATUS          current
    DESCRIPTION     
            "The number of routes, in valid DVMRP packets, which
             were ignored because the entry was invalid."
    ::= { dvmrpInterfaceEntry 15 }

dvmrpNeighborTable OBJECT-TYPE
    SYNTAX          SEQUENCE OF DvmrpNeighborEntry
    MAX-ACCESS      not-accessible
    STATUS          current
    DESCRIPTION     
            "The (conceptual) table listing the router's DVMRP
             neighbors, as discovered by receiving DVMRP messages."
    ::= { dvmrp 4 }

dvmrpNeighborEntry OBJECT-TYPE
    SYNTAX          DvmrpNeighborEntry
    MAX-ACCESS      not-accessible
    STATUS          current
    DESCRIPTION     
            "An entry (conceptual row) in the dvmrpNeighborTable."
    INDEX           { dvmrpNeighborIfIndex, dvmrpNeighborAddress }
    ::= { dvmrpNeighborTable 1 }

DvmrpNeighborEntry ::=
    SEQUENCE {
        dvmrpNeighborIfIndex            Integer32,
        dvmrpNeighborAddress            IpAddress,
        dvmrpNeighborUpTime             TimeTicks,
        dvmrpNeighborExpiryTime         TimeTicks,
        dvmrpNeighborGenerationId       Integer32,
        dvmrpNeighborMajorVersion       Integer32,
        dvmrpNeighborMinorVersion       Integer32,
        dvmrpNeighborCapabilities       INTEGER,
        dvmrpNeighborRcvRoutes          Counter32,
        dvmrpNeighborRcvBadPkts         Counter32,
        dvmrpNeighborRcvBadRoutes       Counter32
    }

dvmrpNeighborIfIndex OBJECT-TYPE
    SYNTAX          Integer32
    MAX-ACCESS      not-accessible
    STATUS          current
    DESCRIPTION     
            "The value of ifIndex for the virtual interface used to
             reach this DVMRP neighbor."
    ::= { dvmrpNeighborEntry 1 }

dvmrpNeighborAddress OBJECT-TYPE
    SYNTAX          IpAddress
    MAX-ACCESS      not-accessible
    STATUS          current
    DESCRIPTION     
            "The IP address of the DVMRP neighbor for which this entry
             contains information."
    ::= { dvmrpNeighborEntry 2 }

dvmrpNeighborUpTime OBJECT-TYPE
    SYNTAX          TimeTicks
    MAX-ACCESS      read-only
    STATUS          current
    DESCRIPTION     
            "The time since this DVMRP neighbor (last) became a neighbor
             of the local router."
    ::= { dvmrpNeighborEntry 3 }

dvmrpNeighborExpiryTime OBJECT-TYPE
    SYNTAX          TimeTicks
    MAX-ACCESS      read-only
    STATUS          current
    DESCRIPTION     
            "The minimum time remaining before this DVMRP neighbor will
             be aged out."
    ::= { dvmrpNeighborEntry 4 }

dvmrpNeighborGenerationId OBJECT-TYPE
    SYNTAX          Integer32
    MAX-ACCESS      read-only
    STATUS          current
    DESCRIPTION     
            "The neighboring router's generation identifier."
    ::= { dvmrpNeighborEntry 6 }

dvmrpNeighborMajorVersion OBJECT-TYPE
    SYNTAX          Integer32 (0..255)
    MAX-ACCESS      read-only
    STATUS          current
    DESCRIPTION     
            "The neighboring router's major DVMRP version number."
    ::= { dvmrpNeighborEntry 7 }

dvmrpNeighborMinorVersion OBJECT-TYPE
    SYNTAX          Integer32 (0..255)
    MAX-ACCESS      read-only
    STATUS          current
    DESCRIPTION     
            "The neighboring router's minor DVMRP version number."
    ::= { dvmrpNeighborEntry 8 }

dvmrpNeighborCapabilities OBJECT-TYPE
    SYNTAX          INTEGER { leaf(0), prune(1), generationID(2), 
                        mtrace(3) }
    MAX-ACCESS      read-only
    STATUS          current
    DESCRIPTION     
            "This object describes the neighboring router's
             capabilities.  The leaf bit indicates that the neighbor has
             only one interface with neighbors.  The prune bit indicates
             that the neighbor supports pruning.  The generationID bit
             indicates that the neighbor sends its generationID in Probe
             messages.  The mtrace bit indicates that the neighbor can
             handle mtrace requests."
    ::= { dvmrpNeighborEntry 9 }

dvmrpNeighborRcvRoutes OBJECT-TYPE
    SYNTAX          Counter32
    MAX-ACCESS      read-only
    STATUS          current
    DESCRIPTION     
            "The total number of routes received in valid DVMRP
             packets received from this neighbor.  This can be used to
             diagnose problems such as unicast route injection, as
             well as giving an indication of the level of DVMRP
             route exchange activity."
    ::= { dvmrpNeighborEntry 10 }

dvmrpNeighborRcvBadPkts OBJECT-TYPE
    SYNTAX          Counter32
    MAX-ACCESS      read-only
    STATUS          current
    DESCRIPTION     
            "The number of packet received from this neighbor which
             were discarded as invalid."
    ::= { dvmrpNeighborEntry 11 }

dvmrpNeighborRcvBadRoutes OBJECT-TYPE
    SYNTAX          Counter32
    MAX-ACCESS      read-only
    STATUS          current
    DESCRIPTION     
            "The number of routes, in valid DVMRP packets received
             from this neighbor, which were ignored because the entry
             was invalid."
    ::= { dvmrpNeighborEntry 12 }

dvmrpRouteTable OBJECT-TYPE
    SYNTAX          SEQUENCE OF DvmrpRouteEntry
    MAX-ACCESS      not-accessible
    STATUS          current
    DESCRIPTION     
            "The table of routes learned through DVMRP route exchange."
    ::= { dvmrp 5 }

dvmrpRouteEntry OBJECT-TYPE
    SYNTAX          DvmrpRouteEntry
    MAX-ACCESS      not-accessible
    STATUS          current
    DESCRIPTION     
            "An entry (conceptual row) containing the multicast routing
             information used by DVMRP in place of the unicast routing
             information."
    INDEX           { dvmrpRouteSource, dvmrpRouteSourceMask }
    ::= { dvmrpRouteTable 1 }

DvmrpRouteEntry ::=
    SEQUENCE {
        dvmrpRouteSource                IpAddress,
        dvmrpRouteSourceMask            IpAddress,
        dvmrpRouteUpstreamNeighbor      IpAddress,
        dvmrpRouteIfIndex               Integer32,
        dvmrpRouteMetric                Integer32,
        dvmrpRouteExpiryTime            TimeTicks,
        dvmrpRouteUpTime                TimeTicks
    }

dvmrpRouteSource OBJECT-TYPE
    SYNTAX          IpAddress
    MAX-ACCESS      not-accessible
    STATUS          current
    DESCRIPTION     
            "The network address which when combined with the
             corresponding value of dvmrpRouteSourceMask identifies the
             sources for which this entry contains multicast routing
             information."
    ::= { dvmrpRouteEntry 1 }

dvmrpRouteSourceMask OBJECT-TYPE
    SYNTAX          IpAddress
    MAX-ACCESS      not-accessible
    STATUS          current
    DESCRIPTION     
            "The network mask which when combined with the corresponding
             value of dvmrpRouteSource identifies the sources for which
             this entry contains multicast routing information."
    ::= { dvmrpRouteEntry 2 }

dvmrpRouteUpstreamNeighbor OBJECT-TYPE
    SYNTAX          IpAddress
    MAX-ACCESS      read-only
    STATUS          current
    DESCRIPTION     
            "The address of the upstream neighbor (e.g., RPF neighbor)
             from which IP datagrams from these sources are received."
    ::= { dvmrpRouteEntry 3 }

dvmrpRouteIfIndex OBJECT-TYPE
    SYNTAX          Integer32
    MAX-ACCESS      read-only
    STATUS          current
    DESCRIPTION     
            "The value of ifIndex for the interface on which IP
             datagrams
             sent by these sources are received."
    ::= { dvmrpRouteEntry 4 }

dvmrpRouteMetric OBJECT-TYPE
    SYNTAX          Integer32 (1..32)
    MAX-ACCESS      read-only
    STATUS          current
    DESCRIPTION     
            "The distance in hops to the source subnet."
    ::= { dvmrpRouteEntry 5 }

dvmrpRouteExpiryTime OBJECT-TYPE
    SYNTAX          TimeTicks
    MAX-ACCESS      read-only
    STATUS          current
    DESCRIPTION     
            "The minimum amount of time remaining before this entry will
             be aged out."
    ::= { dvmrpRouteEntry 6 }

dvmrpRouteUpTime OBJECT-TYPE
    SYNTAX          TimeTicks
    MAX-ACCESS      read-only
    STATUS          current
    DESCRIPTION     
            "The time since the route represented by this entry was
             learned by the router."
    ::= { dvmrpRouteEntry 7 }

dvmrpRouteNextHopTable OBJECT-TYPE
    SYNTAX          SEQUENCE OF DvmrpRouteNextHopEntry
    MAX-ACCESS      not-accessible
    STATUS          current
    DESCRIPTION     
            "The (conceptual) table containing information on the next
             hops on outgoing interfaces for routing IP multicast
             datagrams."
    ::= { dvmrp 6 }

dvmrpRouteNextHopEntry OBJECT-TYPE
    SYNTAX          DvmrpRouteNextHopEntry
    MAX-ACCESS      not-accessible
    STATUS          current
    DESCRIPTION     
            "An entry (conceptual row) in the list of next hops on
             outgoing interfaces to which IP multicast datagrams from
             particular sources are routed."
    INDEX           { dvmrpRouteNextHopSource, 
                      dvmrpRouteNextHopSourceMask, 
                      dvmrpRouteNextHopIfIndex }
    ::= { dvmrpRouteNextHopTable 1 }

DvmrpRouteNextHopEntry ::=
    SEQUENCE {
        dvmrpRouteNextHopSource         IpAddress,
        dvmrpRouteNextHopSourceMask     IpAddress,
        dvmrpRouteNextHopIfIndex        Integer32,
        dvmrpRouteNextHopType           INTEGER
    }

dvmrpRouteNextHopSource OBJECT-TYPE
    SYNTAX          IpAddress
    MAX-ACCESS      not-accessible
    STATUS          current
    DESCRIPTION     
            "The network address which when combined with the
             corresponding value of dvmrpRouteNextHopSourceMask
             identifies the sources for which this entry specifies
             a next hop on an outgoing interface."
    ::= { dvmrpRouteNextHopEntry 1 }

dvmrpRouteNextHopSourceMask OBJECT-TYPE
    SYNTAX          IpAddress
    MAX-ACCESS      not-accessible
    STATUS          current
    DESCRIPTION     
            "The network mask which when combined with the corresponding
             value of dvmrpRouteNextHopSource identifies the sources for
             which this entry specifies a next hop on an outgoing
             interface."
    ::= { dvmrpRouteNextHopEntry 2 }

dvmrpRouteNextHopIfIndex OBJECT-TYPE
    SYNTAX          Integer32
    MAX-ACCESS      not-accessible
    STATUS          current
    DESCRIPTION     
            "The ifIndex value of the interface for the outgoing inter-
             face
             for this next hop."
    ::= { dvmrpRouteNextHopEntry 3 }

dvmrpRouteNextHopType OBJECT-TYPE
    SYNTAX          INTEGER { leaf(1), branch(2) }
    MAX-ACCESS      read-only
    STATUS          current
    DESCRIPTION     
            "Type is leaf if no downstream dependent neighbors exist on
             the outgoing virtual interface.  Otherwise, type is branch."
    ::= { dvmrpRouteNextHopEntry 4 }

dvmrpAltNetTable OBJECT-TYPE
    SYNTAX          SEQUENCE OF DvmrpAltNetEntry
    MAX-ACCESS      not-accessible
    STATUS          deprecated
    DESCRIPTION     
            "The (conceptual) table listing the router's alternate
             subnets on physical interfaces for use in constructing
             the routing tables."
    ::= { dvmrp 8 }

dvmrpAltNetEntry OBJECT-TYPE
    SYNTAX          DvmrpAltNetEntry
    MAX-ACCESS      not-accessible
    STATUS          deprecated
    DESCRIPTION     
            "An entry (conceptual row) in the dvmrpAltNetTable."
    INDEX           { dvmrpAltNetIfIndex, dvmrpAltNetAddress, 
                      dvmrpAltNetMask }
    ::= { dvmrpAltNetTable 1 }

DvmrpAltNetEntry ::=
    SEQUENCE {
        dvmrpAltNetIfIndex              Integer32,
        dvmrpAltNetAddress              IpAddress,
        dvmrpAltNetMask                 IpAddress,
        dvmrpAltNetStatus               RowStatus
    }

dvmrpAltNetIfIndex OBJECT-TYPE
    SYNTAX          Integer32
    MAX-ACCESS      not-accessible
    STATUS          deprecated
    DESCRIPTION     
            "The ifIndex value of the interface to which this alternate
             subnet applies."
    ::= { dvmrpAltNetEntry 1 }

dvmrpAltNetAddress OBJECT-TYPE
    SYNTAX          IpAddress
    MAX-ACCESS      not-accessible
    STATUS          deprecated
    DESCRIPTION     
            "The subnet address of the alternate subnet."
    ::= { dvmrpAltNetEntry 2 }

dvmrpAltNetMask OBJECT-TYPE
    SYNTAX          IpAddress
    MAX-ACCESS      not-accessible
    STATUS          deprecated
    DESCRIPTION     
            "The subnet mask of the alternate subnet."
    ::= { dvmrpAltNetEntry 3 }

dvmrpAltNetStatus OBJECT-TYPE
    SYNTAX          RowStatus
    MAX-ACCESS      read-create
    STATUS          deprecated
    DESCRIPTION     
            "The status of this row, by which new entries may be
             created, or old entries deleted from this table."
    ::= { dvmrpAltNetEntry 4 }

dvmrpNumRoutes OBJECT-TYPE
    SYNTAX          Gauge32
    MAX-ACCESS      read-only
    STATUS          current
    DESCRIPTION     
            "The number of entries in the routing table.  This can
             be used to monitor the routing table size to detect
             illegal advertisements of unicast routes."
    ::= { dvmrp 9 }

dvmrpReachableRoutes OBJECT-TYPE
    SYNTAX          Gauge32
    MAX-ACCESS      read-only
    STATUS          current
    DESCRIPTION     
            "The number of entries in the routing table with non
             infinite metrics.  This can be used to detect network
             partitions by observing the ratio of reachable routes
             to total routes."
    ::= { dvmrp 10 }

dvmrpMIBConformance OBJECT IDENTIFIER
    ::= { dvmrpMIB 2 }

dvmrpMIBCompliances OBJECT IDENTIFIER
    ::= { dvmrpMIBConformance 1 }

dvmrpMIBGroups OBJECT IDENTIFIER
    ::= { dvmrpMIBConformance 2 }

dvmrpMIBGroup OBJECT-GROUP
    OBJECTS         { dvmrpVersionString, dvmrpGenerationId, 
                      dvmrpNumRoutes, dvmrpReachableRoutes, 
                      dvmrpInterfaceType, dvmrpInterfaceOperState, 
                      dvmrpInterfaceLocalAddress, 
                      dvmrpInterfaceRemoteAddress, 
                      dvmrpInterfaceRemoteSubnetMask, 
                      dvmrpInterfaceMetric, dvmrpInterfaceRateLimit, 
                      dvmrpInterfaceInPkts, dvmrpInterfaceOutPkts, 
                      dvmrpInterfaceInOctets, dvmrpInterfaceOutOctets, 
                      dvmrpInterfaceStatus, dvmrpNeighborUpTime, 
                      dvmrpNeighborExpiryTime, dvmrpNeighborGenerationId, 
                      dvmrpNeighborMajorVersion, 
                      dvmrpNeighborMinorVersion, 
                      dvmrpNeighborCapabilities, 
                      dvmrpRouteUpstreamNeighbor, dvmrpRouteIfIndex, 
                      dvmrpRouteMetric, dvmrpRouteExpiryTime, 
                      dvmrpRouteNextHopType, dvmrpAltNetStatus }
    STATUS          deprecated
    DESCRIPTION     
            "A collection of objects to support management of DVMRP
             routers."
    ::= { dvmrpMIBGroups 1 }

dvmrpGeneralGroup OBJECT-GROUP
    OBJECTS         { dvmrpVersionString, dvmrpGenerationId, 
                      dvmrpNumRoutes, dvmrpReachableRoutes }
    STATUS          current
    DESCRIPTION     
            "A collection of objects used to describe general DVMRP
             configuration information."
    ::= { dvmrpMIBGroups 2 }

dvmrpInterfaceGroup OBJECT-GROUP
    OBJECTS         { dvmrpInterfaceLocalAddress, dvmrpInterfaceMetric, 
                      dvmrpInterfaceStatus, dvmrpInterfaceRcvBadPkts, 
                      dvmrpInterfaceRcvBadRoutes }
    STATUS          current
    DESCRIPTION     
            "A collection of objects used to describe DVMRP interface
             configuration and statistics."
    ::= { dvmrpMIBGroups 3 }

dvmrpNeighborGroup OBJECT-GROUP
    OBJECTS         { dvmrpNeighborUpTime, dvmrpNeighborExpiryTime, 
                      dvmrpNeighborGenerationId, 
                      dvmrpNeighborMajorVersion, 
                      dvmrpNeighborMinorVersion, 
                      dvmrpNeighborCapabilities, dvmrpNeighborRcvRoutes, 
                      dvmrpNeighborRcvBadPkts, dvmrpNeighborRcvBadRoutes }
    STATUS          current
    DESCRIPTION     
            "A collection of objects used to describe DVMRP peer
             configuration and statistics."
    ::= { dvmrpMIBGroups 4 }

dvmrpRoutingGroup OBJECT-GROUP
    OBJECTS         { dvmrpRouteUpstreamNeighbor, dvmrpRouteIfIndex, 
                      dvmrpRouteMetric, dvmrpRouteExpiryTime, 
                      dvmrpRouteUpTime, dvmrpRouteNextHopType }
    STATUS          current
    DESCRIPTION     
            "A collection of objects used to store the DVMRP
             routing table."
    ::= { dvmrpMIBGroups 5 }

dvmrpMIBCompliance MODULE-COMPLIANCE
    STATUS          current
    DESCRIPTION     
            "The compliance statement for the DVMRP MIB."

    MODULE          -- this module

        MANDATORY-GROUPS    { dvmrpGeneralGroup, dvmrpInterfaceGroup, 
                      dvmrpNeighborGroup, dvmrpRoutingGroup }

    ::= { dvmrpMIBCompliances 1 }

END -- end of module DVMRP-MIB.
