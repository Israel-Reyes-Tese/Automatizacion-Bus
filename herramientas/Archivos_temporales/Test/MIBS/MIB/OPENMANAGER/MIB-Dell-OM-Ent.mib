-------------------------------------------------------------------------------
-- OM Enterprise MIB : OMEnt.mib
--
-- Copyright (c) 2019 Dell Inc.
-- All Rights Reserved.
--
-- The information and functionality described by this MIB file
-- is subject to change without notice.
-- Please examine the version number of this MIB and compare it
-- to the version number you are expecting.
--
-- MIB Version 1.0                      01 Apr 2017
--
-- MIB Version 1.1						01 Jun 2019
-- Added metric related traps and objects.
--
-------------------------------------------------------------------------------


-------------------------------------------------------------------------------
-- Begin MIB
-------------------------------------------------------------------------------

MIB-Dell-OM-Ent DEFINITIONS ::= BEGIN

IMPORTS
    enterprises
        FROM RFC1155-SMI
    OBJECT-TYPE
        FROM RFC-1212
    TRAP-TYPE
        FROM RFC-1215
    DisplayString
        FROM RFC1213-MIB;


-------------------------------------------------------------------------------
-- OM Enterprise Branch Location (.1.3.6.1.4.1.674.11000.1000.500)
-------------------------------------------------------------------------------

dell                            OBJECT IDENTIFIER ::= { enterprises    674   }
enterpriseSW                    OBJECT IDENTIFIER ::= { dell           11000 }
sysMgmtBranch                   OBJECT IDENTIFIER ::= { enterpriseSW   1000  }
omEnterpriseMIB	               	OBJECT IDENTIFIER ::= { sysMgmtBranch   500  }
omEnterpriseTrap                   OBJECT IDENTIFIER ::= { omEnterpriseMIB   1  }

-------------------------------------------------------------------------------
--
-- Custom Types
--
-------------------------------------------------------------------------------

DellString                      ::= DisplayString (SIZE (0..512))
DellString1                      ::= DisplayString (SIZE (0..128))

-------------------------------------------------------------------------------
--
-- Trap Attributes (Varbinds)
--
-------------------------------------------------------------------------------

omEntAlertMessage                           OBJECT-TYPE
    SYNTAX      DellString
    ACCESS      read-only
    STATUS      mandatory
    DESCRIPTION
       "Message in the alert."
    ::= { omEnterpriseTrap 1 }
omEntAlertDevice                           OBJECT-TYPE
    SYNTAX      DellString
    ACCESS      read-only
    STATUS      mandatory
    DESCRIPTION
       "Name of the device where alert originated."
    ::= { omEnterpriseTrap 2 }
omEntAlertSeverity                 OBJECT-TYPE
      SYNTAX         DellString1
      ACCESS         read-only
      STATUS         mandatory
      DESCRIPTION
         "Original severity of the alert."
    ::= { omEnterpriseTrap 3 }
omEntAlertDataSources                 OBJECT-TYPE
      SYNTAX         DellString
      ACCESS         read-only
      STATUS         mandatory
      DESCRIPTION
         "List of the data sources for which change in health status has been observed."
    ::= { omEnterpriseTrap 4 }
omEntRawAlertInfo                 OBJECT-TYPE
      SYNTAX         DellString
      ACCESS         read-only
      STATUS         mandatory
      DESCRIPTION
         "Message string capturing the overall status update indication.
		  It is a combination of global status|agent Id,from status,to status
		  ('|' delimited further for each data source) attributes. Agent Id is a
		  unique identifier for every data source. Global/from/to status attributes
		  identify every health state (e.g. 2-Unknown, 4-OK, 8-Warning, 16-Critical).
		  These attributes are integer type and are specific to OpenManage Enterprise only.
		  Format - <global-status>|<agentId-1>,<from-status>,<to-status>|...
		  Example - 8|2,4,8|7,4,8"
    ::= { omEnterpriseTrap 5 }
omEntAlertMessageId                           OBJECT-TYPE
    SYNTAX      DellString
    ACCESS      read-only
    STATUS      mandatory
    DESCRIPTION
       "Message Id or event code in the alert."
    ::= { omEnterpriseTrap 6 }
omEntAlertGroup                           OBJECT-TYPE
    SYNTAX      DellString
    ACCESS      read-only
    STATUS      mandatory
    DESCRIPTION
       "Name of the device group where alert originated."
    ::= { omEnterpriseTrap 7 }
omEntAlertMetricType  						OBJECT-TYPE
	SYNTAX     INTEGER {
		maxPower (1),					-- Maximum System Power Consumption
		minPower (2),					-- Minimum System Power Consumption
		avgPower (3),					-- Average System Power Consumption
		instantPower (4),				-- Instant System Power
		maxTemperature (5),				-- Maximum Inlet Temperature
		minTemperature (6),				-- Minimum Inlet Temperature
		avgTemperature (7),				-- Average Inlet Temperature
		instantTemperature (8),			-- Instant Inlet Temperature
		maxUtilCPU (9),					-- Maximum CPU Utilization
		minUtilCPU (10),				-- Minimum CPU Utilization
		avgUtilCPU (11),				-- Average CPU Utilization
		maxUtilMemory (12),				-- Maximum Memory Utilization
		minUtilMemory (13),				-- Minimum Memory Utilization
		avgUtilMemory (14),				-- Average Memory Utilization
		maxUtilIO (15),					-- Maximum I/O Utilization
		minUtilIO (16),					-- Minimum I/O Utilization
		avgUtilIO (17),					-- Average I/O Utilization
		sysAirflow (18),				-- System Air Flow
		sysEnergy (19)					-- System Energy Consumption
	}
	ACCESS     read-only
	STATUS     mandatory
	DESCRIPTION 
		"The metric type of threshold event."
	::= { omEnterpriseTrap 8 }
omEntAlertMetricUnit  						OBJECT-TYPE
	SYNTAX     INTEGER {
		watt (1),						-- Watt for Power
		celsius (2),					-- Celsius for Temperature
		cfm (3),						-- CFM for Air Flow
		percentage (4),					-- Percentage for Utilization
		kWh (5)							-- Kilowatt Hour
	}
	ACCESS     read-only
	STATUS     mandatory
	DESCRIPTION 
		"The metric unit of threshold event."
	::= { omEnterpriseTrap 9 }
omEntAlertCondition  						OBJECT-TYPE
	SYNTAX     INTEGER {
		upper (1),						-- Upper Threshold
		lower (2)						-- Lower Threshold
	}
	ACCESS     read-only
	STATUS     mandatory
	DESCRIPTION 
		"Condition for evaluation of a threshold."
	::= { omEnterpriseTrap 10 }
omEntAlertThresholdValue  					OBJECT-TYPE
	SYNTAX     DellString1
	ACCESS     read-only
	STATUS     mandatory
	DESCRIPTION 
		"Threshold value for a metric."
	::= { omEnterpriseTrap 11 }
omEntAlertCurrentValue  					OBJECT-TYPE
	SYNTAX     DellString1
	ACCESS     read-only
	STATUS     mandatory
	DESCRIPTION 
		"Current value of a metric."
	::= { omEnterpriseTrap 12 }
omEntAlertExtension  						OBJECT-TYPE
	SYNTAX     DellString
	ACCESS     read-only
	STATUS     mandatory
	DESCRIPTION 
		"Name of the extension owning the threshold setting."
	::= { omEnterpriseTrap 13 }

-------------------------------------------------------------------------------
--
-- Traps
--
-------------------------------------------------------------------------------

omEntTestAlert           TRAP-TYPE
    ENTERPRISE  omEnterpriseTrap
    VARIABLES  { omEntAlertMessage}
    DESCRIPTION
       "Test alert forwarded from OM Enterprise."

    --#TYPE		"Test alert forwarded from OM Enterprise."
    --#SUMMARY	 	"Test alert from OM Enterprise. Message: %s."
    --#ARGUMENTS	{0}
    --#SEVERITY	 	INFORMATIONAL
    ::= 1

omEntAlertSystemUp                                   TRAP-TYPE
    ENTERPRISE  omEnterpriseTrap
    VARIABLES { omEntAlertMessage, omEntAlertDevice }
    DESCRIPTION
       "System up message from OM Enterprise. Sent when OM Enterprise detects a device has come online."

    --#TYPE       	"System Up Message from OM Enterprise"
    --#SUMMARY		"%s: %s"
    --#ARGUMENTS	{0,1}
    --#SEVERITY   	INFORMATIONAL

    ::= 1000

omEntAlertSystemDown               TRAP-TYPE
    ENTERPRISE  omEnterpriseTrap
    VARIABLES  { omEntAlertMessage, omEntAlertDevice }
    DESCRIPTION
       "System down message from OM Enterprise. Sent when OM Enterprise detects a device has gone offline."

    --#TYPE		"System Down Message from OM Enterprise"
    --#SUMMARY		"%s: %s"
    --#ARGUMENTS	{0,1}
    --#SEVERITY		CRITICAL

    ::= 1001

omEntAlertForwardedAlert           TRAP-TYPE
    ENTERPRISE  omEnterpriseTrap
    VARIABLES  { omEntAlertMessage, omEntAlertDevice, omEntAlertSeverity, omEntAlertMessageId }
    DESCRIPTION
       "Forwarded alert from OM Enterprise. The event may have originated as an SNMP trap to the OM Enterprise application. The alert format is normalized."

    --#TYPE		"Forwarded Alert from OM Enterprise"
    --#SUMMARY	 	"Forwarded Alert from OM Enterprise. Sending device: %s, Severity: %s, Message: %s, MessageId: %s."
    --#ARGUMENTS	{1,2,0,3}
    --#SEVERITY	 	INFORMATIONAL
    ::= 2000

--
-- Device Status Internal Alerts.
--

omEntAlertUnknownStatus           TRAP-TYPE
    ENTERPRISE  omEnterpriseTrap
    VARIABLES  { omEntAlertMessage, omEntAlertDevice, omEntAlertDataSources, omEntRawAlertInfo }
    DESCRIPTION
       "System monitoring alert from OM Enterprise. Sent when status of the remote device is Unknown."

    --#TYPE		"Status Alert"
    --#SUMMARY	 	"Device %s has changed status to Unknown. Data Sources: %s"
    --#ARGUMENTS	{1,2}
    --#SEVERITY	 	MINOR
    ::= 3001

omEntAlertNormalStatus           TRAP-TYPE
    ENTERPRISE  omEnterpriseTrap
    VARIABLES  { omEntAlertMessage, omEntAlertDevice, omEntAlertDataSources, omEntRawAlertInfo }
    DESCRIPTION
       "System monitoring alert from OM Enterprise. Sent when status of the remote device is Normal."

    --#TYPE		"Status Alert"
    --#SUMMARY	 	"Device %s has changed status to Normal. Data Sources: %s"
    --#ARGUMENTS	{1,2}
    --#SEVERITY	 	INFORMATIONAL
    ::= 3002

omEntAlertWarningStatus           TRAP-TYPE
    ENTERPRISE  omEnterpriseTrap
    VARIABLES  { omEntAlertMessage, omEntAlertDevice, omEntAlertDataSources, omEntRawAlertInfo }
    DESCRIPTION
       "System monitoring alert from OM Enterprise. Sent when status of the remote device is Warning."

    --#TYPE		"Status Alert"
    --#SUMMARY	 	"Device %s has changed status to Warning. Data Sources: %s"
    --#ARGUMENTS	{1,2}
    --#SEVERITY	 	MINOR
    ::= 3003

omEntAlertCriticalStatus           TRAP-TYPE
    ENTERPRISE  omEnterpriseTrap
    VARIABLES  { omEntAlertMessage, omEntAlertDevice, omEntAlertDataSources, omEntRawAlertInfo }
    DESCRIPTION
       "System monitoring alert from OM Enterprise. Sent when status of the remote device is Critical."

    --#TYPE		"Status Alert"
    --#SUMMARY	 	"Device %s has changed status to Critical. Data Sources: %s"
    --#ARGUMENTS	{1,2}
    --#SEVERITY	 	CRITICAL
    ::= 3004

--
-- Metric Threshold Internal Alerts.
--	

-- If the critical or warning metric threshold is set on a device or group and returns to normalcy after being exceeded, this trap is sent.
-- This trap's omEntAlertMessage is default final display message which is populated by OM Enterprise.
-- For example, this trap's omEntAlertMessage maybe as "The current device average power of dev123 has returned to normal. It is 260 W which no longer violates the upper threshold of 270 W set by Power Manager."
omEntAlertNormalMetric           TRAP-TYPE
    ENTERPRISE  omEnterpriseTrap
    VARIABLES  { omEntAlertMessage, omEntAlertDevice, omEntAlertMessageId }
    DESCRIPTION
       "If the critical or warning metric threshold is set on a device or group and returns to normalcy after being exceeded, this trap is sent."

    --#TYPE		"Threshold Alert"
    --#SUMMARY	 	"%s"
    --#ARGUMENTS	{0}
    --#SEVERITY	 	NORMAL
    ::= 4000

-- If the warning metric threshold is set on a device or group and the threshold is exceeded, this trap is sent.
-- This trap's omEntAlertMessage is default final display message which is populated by OM Enterprise.
-- For example, this trap's omEntAlertMessage maybe as "The current device average power of dev123 is 200 W which violates the upper threshold of 180 W set by Power Manager."
omEntAlertWarningMetric           TRAP-TYPE
    ENTERPRISE  omEnterpriseTrap
    VARIABLES  { omEntAlertMessage, omEntAlertDevice, omEntAlertMessageId }
    DESCRIPTION
       "If the warning metric threshold is set on a device or group and the threshold is exceeded, this trap is sent."

    --#TYPE		"Threshold Alert"
    --#SUMMARY	 	"%s"
    --#ARGUMENTS	{0}
    --#SEVERITY	 	MINOR
    ::= 4001
	
-- If the critical metric threshold is set on a device or group and the threshold is exceeded, this trap is sent.
-- This trap's omEntAlertMessage is default final display message which is populated by OM Enterprise.
-- For example, this trap's omEntAlertMessage maybe as "The current device average power of dev123 is 200 W which violates the upper threshold of 180 W set by Power Manager."
omEntAlertCriticalMetric           TRAP-TYPE
    ENTERPRISE  omEnterpriseTrap
    VARIABLES  { omEntAlertMessage, omEntAlertDevice, omEntAlertMessageId }
    DESCRIPTION
       "If the critical metric threshold is set on a device or group and the threshold is exceeded, this trap is sent."

    --#TYPE		"Threshold Alert"
    --#SUMMARY	 	"%s"
    --#ARGUMENTS	{0}
    --#SEVERITY	 	CRITICAL
    ::= 4002

END

-------------------------------------------------------------------------------
-- End MIB
-------------------------------------------------------------------------------
