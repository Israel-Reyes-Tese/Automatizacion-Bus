--
-- This SMIv2 module has been generated by smidump 0.2-cvs. Do not edit.
--

SONUS-LOCAL-POLICY-SERVICES-MIB DEFINITIONS ::= BEGIN

IMPORTS
    Ipv6Address
        FROM IPV6-TC
    Integer32, IpAddress, MODULE-IDENTITY, OBJECT-TYPE, Unsigned32
        FROM SNMPv2-SMI
    DisplayString, RowStatus
        FROM SNMPv2-TC
    sonusServicesMIBs
        FROM SONUS-SMI
    SonusAdminState, SonusBoolean, SonusName, SonusTransportProtocolType
        FROM SONUS-TC;

sonusLocalPolicyServicesMIB MODULE-IDENTITY
    LAST-UPDATED    "201403210000Z"
    ORGANIZATION    
            "Sonus Networks, Inc."
    CONTACT-INFO    
            "   Customer Support    
             Sonus Networks, Inc.
             7 Technology Park Drive
             Westford, MA 01886
             USA
             
             Tel: 978-614-8100
             Fax: 978-614-8609"
    DESCRIPTION     
            "The MIB Module for Local Policy Services Management."
    ::= { sonusServicesMIBs 30 }


sonusLocalPolicyServicesMIBObjects OBJECT IDENTIFIER
    ::= { sonusLocalPolicyServicesMIB 1 }

sonusDsLpSRouteObjects OBJECT IDENTIFIER
    ::= { sonusLocalPolicyServicesMIBObjects 1 }

sonusDsLpSRouteNextIndex OBJECT-TYPE
    SYNTAX          Integer32
    MAX-ACCESS      read-only
    STATUS          current
    DESCRIPTION     
            "The next valid index to use when creating a new sonusDsLpSRouteEntry"
    ::= { sonusDsLpSRouteObjects 1 }

sonusDsLpSRouteTable OBJECT-TYPE
    SYNTAX          SEQUENCE OF SonusDsLpSRouteEntry
    MAX-ACCESS      not-accessible
    STATUS          current
    DESCRIPTION     
            "Each entry of this table defines a Standard route
             Local Policy server."
    ::= { sonusDsLpSRouteObjects 2 }

sonusDsLpSRouteEntry OBJECT-TYPE
    SYNTAX          SonusDsLpSRouteEntry
    MAX-ACCESS      not-accessible
    STATUS          current
    DESCRIPTION     
            "Definition of a Local Policy Standard Route."
    INDEX           { sonusDsLpSRouteIndex }
    ::= { sonusDsLpSRouteTable 1 }

SonusDsLpSRouteEntry ::=
    SEQUENCE {
        sonusDsLpSRouteIndex            Unsigned32,
        sonusDsLpSRouteSrcTgIndex       Unsigned32,
        sonusDsLpSRouteDestNumPrefix    DisplayString,
        sonusDsLpSRouteRoutLblIndex     Unsigned32,
        sonusDsLpSRouteRowStatus        RowStatus
    }

sonusDsLpSRouteIndex OBJECT-TYPE
    SYNTAX          Unsigned32
    MAX-ACCESS      read-only
    STATUS          current
    DESCRIPTION     
            "A unique index for each Standard Route entry."
    ::= { sonusDsLpSRouteEntry 1 }

sonusDsLpSRouteSrcTgIndex OBJECT-TYPE
    SYNTAX          Unsigned32 (0..2048)
    MAX-ACCESS      read-write
    STATUS          current
    DESCRIPTION     
            "The index of the source trunk group of the call."
    ::= { sonusDsLpSRouteEntry 2 }

sonusDsLpSRouteDestNumPrefix OBJECT-TYPE
    SYNTAX          DisplayString (SIZE(0..16))
    MAX-ACCESS      read-write
    STATUS          current
    DESCRIPTION     
            "The Destination Number Prefix for the route lookup."
    ::= { sonusDsLpSRouteEntry 3 }

sonusDsLpSRouteRoutLblIndex OBJECT-TYPE
    SYNTAX          Unsigned32 (0..4096)
    MAX-ACCESS      read-write
    STATUS          current
    DESCRIPTION     
            "The Routing Label name of this standard route."
    ::= { sonusDsLpSRouteEntry 4 }

sonusDsLpSRouteRowStatus OBJECT-TYPE
    SYNTAX          RowStatus
    MAX-ACCESS      read-write
    STATUS          current
    DESCRIPTION     
            "This is for SNMP use."
    ::= { sonusDsLpSRouteEntry 5 }

sonusDsLpRoutLblObjects OBJECT IDENTIFIER
    ::= { sonusLocalPolicyServicesMIBObjects 2 }

sonusDsLpRoutLblNextIndex OBJECT-TYPE
    SYNTAX          Integer32
    MAX-ACCESS      read-only
    STATUS          current
    DESCRIPTION     
            "The next valid index to use when creating a new sonusDsLpRoutLblEntry"
    ::= { sonusDsLpRoutLblObjects 1 }

sonusDsLpRoutLblTable OBJECT-TYPE
    SYNTAX          SEQUENCE OF SonusDsLpRoutLblEntry
    MAX-ACCESS      not-accessible
    STATUS          current
    DESCRIPTION     
            "Each entry of this table defines a Routing Label in the
             Local Policy server."
    ::= { sonusDsLpRoutLblObjects 2 }

sonusDsLpRoutLblEntry OBJECT-TYPE
    SYNTAX          SonusDsLpRoutLblEntry
    MAX-ACCESS      not-accessible
    STATUS          current
    DESCRIPTION     
            "Definition of a Local Policy Routing Label."
    INDEX           { sonusDsLpRoutLblIndex }
    ::= { sonusDsLpRoutLblTable 1 }

SonusDsLpRoutLblEntry ::=
    SEQUENCE {
        sonusDsLpRoutLblIndex           Unsigned32,
        sonusDsLpRoutLblName            SonusName,
        sonusDsLpRoutLblPriRouteType    INTEGER,
        sonusDsLpRoutLblPriTgIndex      Unsigned32,
        sonusDsLpRoutLblPriSigPeerIndex Unsigned32,
        sonusDsLpRoutLblPriAdminState   SonusAdminState,
        sonusDsLpRoutLblSecRouteType    INTEGER,
        sonusDsLpRoutLblSecTgIndex      Unsigned32,
        sonusDsLpRoutLblSecSigPeerIndex Unsigned32,
        sonusDsLpRoutLblSecAdminState   SonusAdminState,
        sonusDsLpRoutLblRowStatus       RowStatus
    }

sonusDsLpRoutLblIndex OBJECT-TYPE
    SYNTAX          Unsigned32
    MAX-ACCESS      read-only
    STATUS          current
    DESCRIPTION     
            "A unique index for each Local Policy Routing Label."
    ::= { sonusDsLpRoutLblEntry 1 }

sonusDsLpRoutLblName OBJECT-TYPE
    SYNTAX          SonusName
    MAX-ACCESS      read-write
    STATUS          current
    DESCRIPTION     
            "The name of this Local Policy Routing Label."
    ::= { sonusDsLpRoutLblEntry 2 }

sonusDsLpRoutLblPriRouteType OBJECT-TYPE
    SYNTAX          INTEGER { none(1), gsx(2), sip(3), psx(4) }
    MAX-ACCESS      read-write
    STATUS          current
    DESCRIPTION     
            "The signaling type for this route entry. GSX is for local PSTN
             trunk group only and no GWIP-GWIP signaling."
    DEFVAL          { none }
    ::= { sonusDsLpRoutLblEntry 3 }

sonusDsLpRoutLblPriTgIndex OBJECT-TYPE
    SYNTAX          Unsigned32 (0..2048)
    MAX-ACCESS      read-write
    STATUS          current
    DESCRIPTION     
            "The primary PSTN trunk group name."
    DEFVAL          { 0 }
    ::= { sonusDsLpRoutLblEntry 4 }

sonusDsLpRoutLblPriSigPeerIndex OBJECT-TYPE
    SYNTAX          Unsigned32 (0..4096)
    MAX-ACCESS      read-write
    STATUS          current
    DESCRIPTION     
            "The primary IP Signaling Peer."
    DEFVAL          { 0 }
    ::= { sonusDsLpRoutLblEntry 5 }

sonusDsLpRoutLblPriAdminState OBJECT-TYPE
    SYNTAX          SonusAdminState
    MAX-ACCESS      read-write
    STATUS          current
    DESCRIPTION     
            "The admin state of the secondary route. The route is skipped
             if not ENABLED."
    DEFVAL          { disabled }
    ::= { sonusDsLpRoutLblEntry 6 }

sonusDsLpRoutLblSecRouteType OBJECT-TYPE
    SYNTAX          INTEGER { none(1), gsx(2), sip(3) }
    MAX-ACCESS      read-write
    STATUS          current
    DESCRIPTION     
            "The signaling type for this route entry. GSX is for PSTN
             trunk group only and no GWIP-GWIP signaling."
    DEFVAL          { none }
    ::= { sonusDsLpRoutLblEntry 7 }

sonusDsLpRoutLblSecTgIndex OBJECT-TYPE
    SYNTAX          Unsigned32 (0..2048)
    MAX-ACCESS      read-write
    STATUS          current
    DESCRIPTION     
            "The secondary route PSTN trunk group name."
    DEFVAL          { 0 }
    ::= { sonusDsLpRoutLblEntry 8 }

sonusDsLpRoutLblSecSigPeerIndex OBJECT-TYPE
    SYNTAX          Unsigned32 (0..4096)
    MAX-ACCESS      read-write
    STATUS          current
    DESCRIPTION     
            "The secondary route IP Signaling Peer."
    DEFVAL          { 0 }
    ::= { sonusDsLpRoutLblEntry 9 }

sonusDsLpRoutLblSecAdminState OBJECT-TYPE
    SYNTAX          SonusAdminState
    MAX-ACCESS      read-write
    STATUS          current
    DESCRIPTION     
            "The admin state of secondary route. The route is skipped
             if not ENABLED."
    DEFVAL          { disabled }
    ::= { sonusDsLpRoutLblEntry 10 }

sonusDsLpRoutLblRowStatus OBJECT-TYPE
    SYNTAX          RowStatus
    MAX-ACCESS      read-write
    STATUS          current
    DESCRIPTION     
            "This is for SNMP use."
    ::= { sonusDsLpRoutLblEntry 11 }

sonusDsLpTgProfileObjects OBJECT IDENTIFIER
    ::= { sonusLocalPolicyServicesMIBObjects 3 }

sonusDsLpTgProfileNextIndex OBJECT-TYPE
    SYNTAX          Integer32
    MAX-ACCESS      read-only
    STATUS          current
    DESCRIPTION     
            "The next valid index to use when creating a new sonusDsLpTgProfileEntry"
    ::= { sonusDsLpTgProfileObjects 1 }

sonusDsLpTgProfileTable OBJECT-TYPE
    SYNTAX          SEQUENCE OF SonusDsLpTgProfileEntry
    MAX-ACCESS      not-accessible
    STATUS          current
    DESCRIPTION     
            "Each entry of this table defines a Local Policy Trunk Group Profile."
    ::= { sonusDsLpTgProfileObjects 2 }

sonusDsLpTgProfileEntry OBJECT-TYPE
    SYNTAX          SonusDsLpTgProfileEntry
    MAX-ACCESS      not-accessible
    STATUS          current
    DESCRIPTION     
            "Definition of a LP Trunk Group Profile."
    INDEX           { sonusDsLpTgProfIndex }
    ::= { sonusDsLpTgProfileTable 1 }

SonusDsLpTgProfileEntry ::=
    SEQUENCE {
        sonusDsLpTgProfIndex            Unsigned32,
        sonusDsLpTgProfName             SonusName,
        sonusDsLpTgProfSigProfIndex     Unsigned32,
        sonusDsLpTgProfIpSigProfIndex   Unsigned32,
        sonusDsLpTgProfPspIndex         Unsigned32,
        sonusDsLpTgProfDialPlanIndex    Unsigned32,
        sonusDsLpTgProfCountryCode      DisplayString,
        sonusDsLpTgProfSigFlag          INTEGER,
        sonusDsLpTgProfDestSwitchType   INTEGER,
        sonusDsLpTgProfAdminState       SonusAdminState,
        sonusDsLpTgProfRowStatus        RowStatus,
        sonusDsLpTgProfSipDomain        DisplayString,
        sonusDsLpTgProfToneAnnProfIndex Unsigned32,
        sonusDsLpTgProfProcessEnumdi    SonusBoolean
    }

sonusDsLpTgProfIndex OBJECT-TYPE
    SYNTAX          Unsigned32
    MAX-ACCESS      read-only
    STATUS          current
    DESCRIPTION     
            "A unique index for each LP Trunk Group Profile."
    ::= { sonusDsLpTgProfileEntry 1 }

sonusDsLpTgProfName OBJECT-TYPE
    SYNTAX          SonusName
    MAX-ACCESS      read-write
    STATUS          current
    DESCRIPTION     
            "The name of this LP Trunk Group Profile."
    ::= { sonusDsLpTgProfileEntry 2 }

sonusDsLpTgProfSigProfIndex OBJECT-TYPE
    SYNTAX          Unsigned32 (0..2048)
    MAX-ACCESS      read-write
    STATUS          current
    DESCRIPTION     
            "The Signaling Profile assigned to this LP Trunk Group Profile."
    DEFVAL          { 0 }
    ::= { sonusDsLpTgProfileEntry 3 }

sonusDsLpTgProfIpSigProfIndex OBJECT-TYPE
    SYNTAX          Unsigned32 (0..2048)
    MAX-ACCESS      read-write
    STATUS          current
    DESCRIPTION     
            "The IP Signaling Profile assigned to this LP Trunk Group Profile."
    DEFVAL          { 0 }
    ::= { sonusDsLpTgProfileEntry 4 }

sonusDsLpTgProfPspIndex OBJECT-TYPE
    SYNTAX          Unsigned32 (1..2048)
    MAX-ACCESS      read-write
    STATUS          current
    DESCRIPTION     
            "The Packet Service Profile assigned to this LP Trunk Group Profile."
    DEFVAL          { 1 }
    ::= { sonusDsLpTgProfileEntry 5 }

sonusDsLpTgProfDialPlanIndex OBJECT-TYPE
    SYNTAX          Unsigned32 (0..2048)
    MAX-ACCESS      read-write
    STATUS          current
    DESCRIPTION     
            "The Dial Plan Profile assigned to this LP Trunk Group Profile."
    DEFVAL          { 0 }
    ::= { sonusDsLpTgProfileEntry 6 }

sonusDsLpTgProfCountryCode OBJECT-TYPE
    SYNTAX          DisplayString (SIZE(1..3))
    MAX-ACCESS      read-write
    STATUS          current
    DESCRIPTION     
            "The Country Code associated with this LP Trunk Group Profile."
    ::= { sonusDsLpTgProfileEntry 7 }

sonusDsLpTgProfSigFlag OBJECT-TYPE
    SYNTAX          INTEGER { btiup(1), gr317isup(2), gr394isup(3), 
                        itu(4), japanisup(5), chinaisup(6), sip(7), 
                        sipi(8) }
    MAX-ACCESS      read-write
    STATUS          current
    DESCRIPTION     
            "The signaling flag associated with this LP Trunk Group Profile."
    DEFVAL          { gr394isup }
    ::= { sonusDsLpTgProfileEntry 8 }

sonusDsLpTgProfDestSwitchType OBJECT-TYPE
    SYNTAX          INTEGER { access(1), eaeo(2), international(3), 
                        ixc(4), noneaeo(5), tandem(6) }
    MAX-ACCESS      read-write
    STATUS          current
    DESCRIPTION     
            "The destination switch type  of this LP Trunk Group Profile."
    DEFVAL          { access }
    ::= { sonusDsLpTgProfileEntry 9 }

sonusDsLpTgProfAdminState OBJECT-TYPE
    SYNTAX          SonusAdminState
    MAX-ACCESS      read-write
    STATUS          current
    DESCRIPTION     
            "The admin state of the this LP Trunk Group Profile."
    DEFVAL          { disabled }
    ::= { sonusDsLpTgProfileEntry 10 }

sonusDsLpTgProfRowStatus OBJECT-TYPE
    SYNTAX          RowStatus
    MAX-ACCESS      read-write
    STATUS          current
    DESCRIPTION     
            "This is for SNMP use."
    ::= { sonusDsLpTgProfileEntry 11 }

sonusDsLpTgProfSipDomain OBJECT-TYPE
    SYNTAX          DisplayString (SIZE(0..63))
    MAX-ACCESS      read-write
    STATUS          current
    DESCRIPTION     
            "The name of this LP Trunk Group Profile SIP Domain Name."
    ::= { sonusDsLpTgProfileEntry 12 }

sonusDsLpTgProfToneAnnProfIndex OBJECT-TYPE
    SYNTAX          Unsigned32 (0..2048)
    MAX-ACCESS      read-write
    STATUS          current
    DESCRIPTION     
            "The Tone and announcement Profile assigned to this LP Trunk Group Profile."
    DEFVAL          { 0 }
    ::= { sonusDsLpTgProfileEntry 13 }

sonusDsLpTgProfProcessEnumdi OBJECT-TYPE
    SYNTAX          SonusBoolean
    MAX-ACCESS      read-write
    STATUS          current
    DESCRIPTION     
            "This flag will tell whether to process the enumdi parameter of not."
    DEFVAL          { false }
    ::= { sonusDsLpTgProfileEntry 14 }

sonusDsLpIpSigPeerObjects OBJECT IDENTIFIER
    ::= { sonusLocalPolicyServicesMIBObjects 4 }

sonusDsLpIpSigPeerNextIndex OBJECT-TYPE
    SYNTAX          Integer32
    MAX-ACCESS      read-only
    STATUS          current
    DESCRIPTION     
            "The next valid index to use when creating a new sonusDsLpIpSigPeerEntry"
    ::= { sonusDsLpIpSigPeerObjects 1 }

sonusDsLpIpSigPeerTable OBJECT-TYPE
    SYNTAX          SEQUENCE OF SonusDsLpIpSigPeerEntry
    MAX-ACCESS      not-accessible
    STATUS          current
    DESCRIPTION     
            "Each entry of this table defines a Signaling Peer."
    ::= { sonusDsLpIpSigPeerObjects 2 }

sonusDsLpIpSigPeerEntry OBJECT-TYPE
    SYNTAX          SonusDsLpIpSigPeerEntry
    MAX-ACCESS      not-accessible
    STATUS          current
    DESCRIPTION     
            "Definition of a Signaling Peer Group."
    INDEX           { sonusDsLpIpSigPeerIndex }
    ::= { sonusDsLpIpSigPeerTable 1 }

SonusDsLpIpSigPeerEntry ::=
    SEQUENCE {
        sonusDsLpIpSigPeerIndex         Unsigned32,
        sonusDsLpIpSigPeerName          SonusName,
        sonusDsLpIpSigPeerZoneIndex     Unsigned32,
        sonusDsLpIpSigPeerIpAddress     IpAddress,
        sonusDsLpIpSigPeerFqdn          DisplayString,
        sonusDsLpIpSigPeerIpPortNum     Unsigned32,
        sonusDsLpIpSigPeerRowStatus     RowStatus,
        sonusDsLpIpSigPeerIp6Address    Ipv6Address,
        sonusDsLpIpSigPeerIpVersion     INTEGER
    }

sonusDsLpIpSigPeerIndex OBJECT-TYPE
    SYNTAX          Unsigned32
    MAX-ACCESS      read-only
    STATUS          current
    DESCRIPTION     
            "A unique index for each IP Signaling Peer."
    ::= { sonusDsLpIpSigPeerEntry 1 }

sonusDsLpIpSigPeerName OBJECT-TYPE
    SYNTAX          SonusName
    MAX-ACCESS      read-write
    STATUS          current
    DESCRIPTION     
            "The name of this IP Signaling Peer."
    ::= { sonusDsLpIpSigPeerEntry 2 }

sonusDsLpIpSigPeerZoneIndex OBJECT-TYPE
    SYNTAX          Unsigned32 (1..2048)
    MAX-ACCESS      read-write
    STATUS          current
    DESCRIPTION     
            "The Signaling Zone ID this peer belongs to."
    DEFVAL          { 1 }
    ::= { sonusDsLpIpSigPeerEntry 3 }

sonusDsLpIpSigPeerIpAddress OBJECT-TYPE
    SYNTAX          IpAddress
    MAX-ACCESS      read-write
    STATUS          current
    DESCRIPTION     
            "The IP address of this peer."
    ::= { sonusDsLpIpSigPeerEntry 4 }

sonusDsLpIpSigPeerFqdn OBJECT-TYPE
    SYNTAX          DisplayString (SIZE(0..127))
    MAX-ACCESS      read-write
    STATUS          current
    DESCRIPTION     
            "The Fully Qualified Domain Name (FQDN) of this peer."
    ::= { sonusDsLpIpSigPeerEntry 5 }

sonusDsLpIpSigPeerIpPortNum OBJECT-TYPE
    SYNTAX          Unsigned32 (1..65535)
    MAX-ACCESS      read-write
    STATUS          current
    DESCRIPTION     
            "UDP/TCP port number of IP Signalling Peer (default is 5060)."
    DEFVAL          { 5060 }
    ::= { sonusDsLpIpSigPeerEntry 6 }

sonusDsLpIpSigPeerRowStatus OBJECT-TYPE
    SYNTAX          RowStatus
    MAX-ACCESS      read-write
    STATUS          current
    DESCRIPTION     
            "This is for SNMP use."
    ::= { sonusDsLpIpSigPeerEntry 7 }

sonusDsLpIpSigPeerIp6Address OBJECT-TYPE
    SYNTAX          Ipv6Address
    MAX-ACCESS      read-write
    STATUS          current
    DESCRIPTION     
            "The IPv6 address of this peer."
    ::= { sonusDsLpIpSigPeerEntry 8 }

sonusDsLpIpSigPeerIpVersion OBJECT-TYPE
    SYNTAX          INTEGER { afInet(2), afInet6(24) }
    MAX-ACCESS      read-only
    STATUS          current
    DESCRIPTION     
            "The IP address type of this peer."
    ::= { sonusDsLpIpSigPeerEntry 9 }

sonusDsLpSigProfileObjects OBJECT IDENTIFIER
    ::= { sonusLocalPolicyServicesMIBObjects 5 }

sonusDsLpSigProfileNextIndex OBJECT-TYPE
    SYNTAX          Integer32
    MAX-ACCESS      read-only
    STATUS          current
    DESCRIPTION     
            "The next valid index to use when creating a new sonusDsLpSigProfileEntry"
    ::= { sonusDsLpSigProfileObjects 1 }

sonusDsLpSigProfileTable OBJECT-TYPE
    SYNTAX          SEQUENCE OF SonusDsLpSigProfileEntry
    MAX-ACCESS      not-accessible
    STATUS          current
    DESCRIPTION     
            "Each entry of this table defines a Signaling Profile."
    ::= { sonusDsLpSigProfileObjects 2 }

sonusDsLpSigProfileEntry OBJECT-TYPE
    SYNTAX          SonusDsLpSigProfileEntry
    MAX-ACCESS      not-accessible
    STATUS          current
    DESCRIPTION     
            "Definition of a Signaling Profile."
    INDEX           { sonusDsLpSigProfIndex }
    ::= { sonusDsLpSigProfileTable 1 }

SonusDsLpSigProfileEntry ::=
    SEQUENCE {
        sonusDsLpSigProfIndex           Unsigned32,
        sonusDsLpSigProfName            SonusName,
        sonusDsLpSigProfRowStatus       RowStatus,
        sonusDsLpSigProfIngressFlagsDontGenerateExitMsg               SonusBoolean,
        sonusDsLpSigProfIngressFlagsPropagateFeParameter                SonusBoolean,
        sonusDsLpSigProfEgressFlagsConvertNum2E164Format                SonusBoolean
    }

sonusDsLpSigProfIndex OBJECT-TYPE
    SYNTAX          Unsigned32
    MAX-ACCESS      read-only
    STATUS          current
    DESCRIPTION     
            "A unique index for each Signaling Profile."
    ::= { sonusDsLpSigProfileEntry 1 }

sonusDsLpSigProfName OBJECT-TYPE
    SYNTAX          SonusName
    MAX-ACCESS      read-write
    STATUS          current
    DESCRIPTION     
            "The name of this Signaling Profile."
    ::= { sonusDsLpSigProfileEntry 2 }

sonusDsLpSigProfRowStatus OBJECT-TYPE
    SYNTAX          RowStatus
    MAX-ACCESS      read-write
    STATUS          current
    DESCRIPTION     
            "This is for SNMP use."
    ::= { sonusDsLpSigProfileEntry 3 }

sonusDsLpSigProfIngressFlagsDontGenerateExitMsg OBJECT-TYPE
    SYNTAX          SonusBoolean
    MAX-ACCESS      read-write
    STATUS          current
    DESCRIPTION     
            "This flag controls the generation of the EXM message on the
             associated ingress trunk group. Exit message (EXM) is an SS7/ISUP
             message that is generated when a call is passed from one network to
             another (e.g. an access tandem generates this message when passing
             a call to an IXC)."
    DEFVAL          { false }
    ::= { sonusDsLpSigProfileEntry 4 }

sonusDsLpSigProfIngressFlagsPropagateFeParameter OBJECT-TYPE
    SYNTAX          SonusBoolean
    MAX-ACCESS      read-write
    STATUS          current
    DESCRIPTION     
            "This flag controls the propagation of the FE parameter in the
             backward directions for call arriving on the associated trunk group.
             The FE parameter includes the terminating switch ID, the terminating
             trunk group ID, and the trunk member on which a call completed.
             When enabled, the FE parameter is propagated in the backward direction
             for calls arriving on that trunk group. The FE is passed to provide
             call termination information in the billing record generated by the
             switch that originated the call."
    DEFVAL          { false }
    ::= { sonusDsLpSigProfileEntry 5 }

sonusDsLpSigProfEgressFlagsConvertNum2E164Format OBJECT-TYPE
    SYNTAX          SonusBoolean
    MAX-ACCESS      read-write
    STATUS          current
    DESCRIPTION     
            "When set to TRUE, numbers are converted to E.164 format. 
             It is used to globalize the numbers on Egress ISUP trunks
             in E.164 format."
    DEFVAL          { false }
    ::= { sonusDsLpSigProfileEntry 6 }

sonusDsLpIpSigProfileObjects OBJECT IDENTIFIER
    ::= { sonusLocalPolicyServicesMIBObjects 6 }

sonusDsLpIpSigProfileNextIndex OBJECT-TYPE
    SYNTAX          Unsigned32
    MAX-ACCESS      read-only
    STATUS          current
    DESCRIPTION     
            "The next valid index to use when creating a new sonusDsLpIpSigProfileEntry"
    ::= { sonusDsLpIpSigProfileObjects 1 }

sonusDsLpIpSigProfileTable OBJECT-TYPE
    SYNTAX          SEQUENCE OF SonusDsLpIpSigProfileEntry
    MAX-ACCESS      not-accessible
    STATUS          current
    DESCRIPTION     
            "Each entry of this table defines an IP Signaling Profile."
    ::= { sonusDsLpIpSigProfileObjects 2 }

sonusDsLpIpSigProfileEntry OBJECT-TYPE
    SYNTAX          SonusDsLpIpSigProfileEntry
    MAX-ACCESS      not-accessible
    STATUS          current
    DESCRIPTION     
            "Definition of an IP Signaling Profile."
    INDEX           { sonusDsLpIpSigProfIndex }
    ::= { sonusDsLpIpSigProfileTable 1 }

SonusDsLpIpSigProfileEntry ::=
    SEQUENCE {
        sonusDsLpIpSigProfIndex         Unsigned32,
        sonusDsLpIpSigProfName          SonusName,
        sonusDsLpIpSigProfRowStatus     RowStatus,
        sonusDsLpIpSigProfCommonDiscardReceivedReasonHeader                   SonusBoolean,
        sonusDsLpIpSigProfCommonIncludeReasonHeader           SonusBoolean,
        sonusDsLpIpSigProfCommonNoSilenceSuppression            SonusBoolean,
        sonusDsLpIpSigProfEgressIpProtocolType      INTEGER,
        sonusDsLpIpSigProfEgressSignalingMimeContentTypeVersion                       Unsigned32,
        sonusDsLpIpSigProfEgressFlagsDispositionHandlingRequired                        SonusBoolean,
        sonusDsLpIpSigProfEgressFlagsGlobalizeNumbers             SonusBoolean,
        sonusDsLpIpSigProfEgressFlagsMap181or182to183             SonusBoolean,
        sonusDsLpIpSigProfEgressBciInterworkEncountered               SonusBoolean,
        sonusDsLpIpSigProfEgressBciIsdnAccess     SonusBoolean,
        sonusDsLpIpSigProfEgressNumberPortabilityAttributesNpdiOptions                              INTEGER,
        sonusDsLpIpSigProfEgressNumberPortabilityAttributesFlagsDisableRn                                 SonusBoolean,
        sonusDsLpIpSigProfEgressPrivacyTransparency           SonusBoolean,
        sonusDsLpIpSigProfEgressPrivacyPrivacyInfo          INTEGER,
        sonusDsLpIpSigProfEgressPrivacyFlagsIncludePrivacy                  SonusBoolean,
        sonusDsLpIpSigProfEgressPrivacyFlagsPrivacyRequiredByProxy                          SonusBoolean,
        sonusDsLpIpSigProfEgressSipCauseMappingInternal2Sip                   Unsigned32,
        sonusDsLpIpSigProfEgressSipCauseMappingSip2Internal                   Unsigned32,
        sonusDsLpIpSigProfEgressSipHeadersParamsSipToHeaderMapping                          INTEGER,
        sonusDsLpIpSigProfCommonCreatePchargingVector             SonusBoolean,
        sonusDsLpIpSigProfEgressSipHeadersParamsFlagsIncludeCpcInfo                           SonusBoolean,
        sonusDsLpIpSigProfEgressSipHeadersParamsFlagsIncludeNpi                       SonusBoolean,
        sonusDsLpIpSigProfEgressSipHeadersParamsFlagsIncludeOlip                        SonusBoolean,
        sonusDsLpIpSigProfEgressTransportType1      SonusTransportProtocolType,
        sonusDsLpIpSigProfEgressTransportType2      SonusTransportProtocolType,
        sonusDsLpIpSigProfEgressTransportType3      SonusTransportProtocolType,
        sonusDsLpIpSigProfEgressTransportType4      SonusTransportProtocolType,
        sonusDsLpIpSigProfIngressFlags181Supported          SonusBoolean,
        sonusDsLpIpSigProfIngressFlags182Supported          SonusBoolean,
        sonusDsLpIpSigProfIngressFlagsNoSdpIn180Supported                 SonusBoolean,
        sonusDsLpIpSigProfIngressFlagsSendSdpIn200OkIf18xReliable                         SonusBoolean,
        sonusDsLpIpSigProfCommonCallHoldInterworking            SonusBoolean,
        sonusDsLpIpSigProfCommonTerminalPortabilityInterworking                       SonusBoolean,
        sonusDsLpIpSigProfCommonInsertPeerAddressAsTopRouteHeader                         SonusBoolean,
        sonusDsLpIpSigProfCommonAlertInfoTransparency             SonusBoolean,
        sonusDsLpIpSigProfCommonAuthcodeTransparency            SonusBoolean,
        sonusDsLpIpSigProfCommonErrorInfoTransparency             SonusBoolean,
        sonusDsLpIpSigProfCommonFromTransparency        SonusBoolean,
        sonusDsLpIpSigProfCommonMaxForwardsTransparency               SonusBoolean,
        sonusDsLpIpSigProfCommonMWIBodyTransparency           SonusBoolean,
        sonusDsLpIpSigProfCommonPChargingVectorTransparency                   SonusBoolean,
        sonusDsLpIpSigProfCommonPEarlyMediaTransparency               SonusBoolean,
        sonusDsLpIpSigProfCommonPathTransparency        SonusBoolean,
        sonusDsLpIpSigProfCommonQsigBodyTransparency            SonusBoolean,
        sonusDsLpIpSigProfCommonReasonTransparency          SonusBoolean,
        sonusDsLpIpSigProfCommonReferredByTransparency              SonusBoolean,
        sonusDsLpIpSigProfCommonRequestUriTransparency              SonusBoolean,
        sonusDsLpIpSigProfCommonRouteTransparency         SonusBoolean,
        sonusDsLpIpSigProfCommonServiceRouteTransparency                SonusBoolean,
        sonusDsLpIpSigProfCommonSipBodyTransparency           SonusBoolean,
        sonusDsLpIpSigProfCommonSipfragBodyTransparency               SonusBoolean,
        sonusDsLpIpSigProfCommonToTransparency      SonusBoolean,
        sonusDsLpIpSigProfCommonToneBodyTransparency            SonusBoolean,
        sonusDsLpIpSigProfCommonUnknownBodyTransparency               SonusBoolean,
        sonusDsLpIpSigProfCommonUnknownHeaderTransparency                 SonusBoolean,
        sonusDsLpIpSigProfCommonDTMFBodyRelay     SonusBoolean,
        sonusDsLpIpSigProfCommonInfoRelay SonusBoolean,
        sonusDsLpIpSigProfCommonMessageRelay    SonusBoolean,
        sonusDsLpIpSigProfCommonNotifyRelay   SonusBoolean,
        sonusDsLpIpSigProfCommonOptionsRelay    SonusBoolean,
        sonusDsLpIpSigProfCommonReferRelay  SonusBoolean,
        sonusDsLpIpSigProfCommonSonusMediaBodyRelay           SonusBoolean,
        sonusDsLpIpSigProfCommonStatusCode3xxRelay          SonusBoolean,
        sonusDsLpIpSigProfCommonStatusCode4xxTo6xxRelay               SonusBoolean,
        sonusDsLpIpSigProfCommonThirdPartyBodyRelay           SonusBoolean,
        sonusDsLpIpSigProfCommonAddPathServiceRoutePerTG                SonusBoolean,
        sonusDsLpIpSigProfCommonCreatePathHeader        SonusBoolean,
        sonusDsLpIpSigProfCommonCreateServiceRouteHeader                SonusBoolean,
        sonusDsLpIpSigProfCommonDisableHostTranslation              SonusBoolean,
        sonusDsLpIpSigProfCommonDoNotIncludeSSAttributeInReInvite                         SonusBoolean,
        sonusDsLpIpSigProfCommonIncludeSSAttributeInInitialInvite                         SonusBoolean,
        sonusDsLpIpSigProfCommonIncludeTransportTypeInContactHeader                           SonusBoolean,
        sonusDsLpIpSigProfCommonReQueryPsxOnRegisterRequest                   SonusBoolean,
        sonusDsLpIpSigProfCommonSendDirectMediaInfoInSdpAttribute                         SonusBoolean,
        sonusDsLpIpSigProfCommonStorePathHeader       SonusBoolean,
        sonusDsLpIpSigProfCommonStoreServiceRouteHeader               SonusBoolean,
        sonusDsLpIpSigProfIngressFlagsSendSdpInSubsequent18x                    SonusBoolean,
        sonusDsLpIpSigProfEgressFlagsConvertInactiveToSendRecv                      SonusBoolean,
        sonusDsLpIpSigProfEgressFlagsSuppressUnregister               SonusBoolean,
        sonusDsLpIpSigProfEgressDomainNamePreserveIngressFromDomainName                               SonusBoolean,
        sonusDsLpIpSigProfEgressDomainNamePreserveIngressRURIDomainName                               SonusBoolean,
        sonusDsLpIpSigProfEgressDomainNameUseSipDomainNameInFromField                             SonusBoolean,
        sonusDsLpIpSigProfEgressDomainNameUseSIPDomainNameInRequestUri                              SonusBoolean,
        sonusDsLpIpSigProfEgressSipHeadersParamsFlagsTransparency                         SonusBoolean,
        sonusDsLpIpSigProfEgressRedirectMode    INTEGER,
        sonusDsLpIpSigProfEgressRedirectContactHandling               INTEGER,
        sonusDsLpIpSigProfCommonHistoryInfoTransparency               SonusBoolean,
        sonusDsLpIpSigProfCommonHandleIpAddrressesNotPresent                    INTEGER,
        sonusDsLpIpSigProfCommonForceReRouteViaPolicyQuery                  SonusBoolean,
        sonusDsLpIpSigProfCommonTargetDialogTransparency                SonusBoolean,
        sonusDsLpSigProfFlagsCommonEnablingRTCPinfo           SonusBoolean
    }

sonusDsLpIpSigProfIndex OBJECT-TYPE
    SYNTAX          Unsigned32
    MAX-ACCESS      read-only
    STATUS          current
    DESCRIPTION     
            "A unique index for each IP Signaling Profile."
    ::= { sonusDsLpIpSigProfileEntry 1 }

sonusDsLpIpSigProfName OBJECT-TYPE
    SYNTAX          SonusName
    MAX-ACCESS      read-write
    STATUS          current
    DESCRIPTION     
            "The name of this IP Signaling Profile."
    ::= { sonusDsLpIpSigProfileEntry 2 }

sonusDsLpIpSigProfRowStatus OBJECT-TYPE
    SYNTAX          RowStatus
    MAX-ACCESS      read-write
    STATUS          current
    DESCRIPTION     
            "This is for SNMP use."
    ::= { sonusDsLpIpSigProfileEntry 3 }

sonusDsLpIpSigProfCommonDiscardReceivedReasonHeader OBJECT-TYPE
    SYNTAX          SonusBoolean
    MAX-ACCESS      read-write
    STATUS          current
    DESCRIPTION     
            "Specifies whether to use the cause code in the Reason header
             received from the remote peer. When set to TRUE, the GSX
             ignores the cause code in the received Reason header.
             When set to FALSE, the GSX uses the cause code in the
             received Reason header."
    DEFVAL          { false }
    ::= { sonusDsLpIpSigProfileEntry 4 }

sonusDsLpIpSigProfCommonIncludeReasonHeader OBJECT-TYPE
    SYNTAX          SonusBoolean
    MAX-ACCESS      read-write
    STATUS          current
    DESCRIPTION     
            "When set to TRUE, the GSX includes the Reason header in
             18x, 4xx, 5xx, Cancel, and Bye messages in the forward
             direction. It is provisioned on the egress trunk group."
    DEFVAL          { false }
    ::= { sonusDsLpIpSigProfileEntry 5 }

sonusDsLpIpSigProfCommonNoSilenceSuppression OBJECT-TYPE
    SYNTAX          SonusBoolean
    MAX-ACCESS      read-write
    STATUS          obsolete
    DESCRIPTION     
            "This flag is obsolete in 7.3 LP as it no longer exists in PSX.
             Specifies whether the GSX sends silence suppression to the
              remote peer. When set to TRUE, the GSX does
              not send silence suppression (no a=silenceSupp is sent)
              in the SDP to the remote peer. When set to FALSE, and
              when silence suppression is off, the GSX sends
              a=silenceSupp:off in the SDP to the remote peer.
              Note that a=silenceSupp:on is never sent to the remote
              peer in the Sonus implementation when silence suppression is on."
    DEFVAL          { false }
    ::= { sonusDsLpIpSigProfileEntry 6 }

sonusDsLpIpSigProfEgressIpProtocolType OBJECT-TYPE
    SYNTAX          INTEGER { siponly(1), sipi(2) }
    MAX-ACCESS      read-write
    STATUS          current
    DESCRIPTION     
            "Select either SIP-Only or SIP-I depending on
             the protocol being supported by the associated trunk group."
    DEFVAL          { siponly }
    ::= { sonusDsLpIpSigProfileEntry 7 }

sonusDsLpIpSigProfEgressSignalingMimeContentTypeVersion OBJECT-TYPE
    SYNTAX          Unsigned32 (1..128)
    MAX-ACCESS      read-write
    STATUS          current
    DESCRIPTION     
            "Selects the unique version identifier for the version
             of the content type selected. It is the
             version of ISUP in the MIME body of the SIP-I call.
             By selecting a particular number here, you select the
             associated version of ISUP specified in the GSX ISUP signaling
             group version ID."
    DEFVAL          { 1 }
    ::= { sonusDsLpIpSigProfileEntry 8 }

sonusDsLpIpSigProfEgressFlagsDispositionHandlingRequired OBJECT-TYPE
    SYNTAX          SonusBoolean
    MAX-ACCESS      read-write
    STATUS          current
    DESCRIPTION     
            "This flag indicates how the receiving SIP peer should
             handle MIME content (either a content type or a content
             type version) that it does not understand. If set to
             TRUE and the MIME content is not understood, the
             receiver should reject the call. If set to FALSE and
             the receiver does not understand the MIME contents, those
             contents can be ignored. The setting of this flag is
             used to create a Content-Disposition header that is
             included in the INVITE message."
    DEFVAL          { true }
    ::= { sonusDsLpIpSigProfileEntry 9 }

sonusDsLpIpSigProfEgressFlagsGlobalizeNumbers OBJECT-TYPE
    SYNTAX          SonusBoolean
    MAX-ACCESS      read-write
    STATUS          current
    DESCRIPTION     
            "When set to TRUE, all numbers will be converted into
             SIP global number format. set to FALSE, the format of
             numbers is not modified."
    DEFVAL          { false }
    ::= { sonusDsLpIpSigProfileEntry 10 }

sonusDsLpIpSigProfEgressFlagsMap181or182to183 OBJECT-TYPE
    SYNTAX          SonusBoolean
    MAX-ACCESS      read-write
    STATUS          current
    DESCRIPTION     
            "This is used by the GSX to control SIP response
             processing. When set to TRUE, the GSX maps 181 or 182
             response messages to 183. When set to FALSE, the GSX
             handles 1xx response messages normally."
    DEFVAL          { false }
    ::= { sonusDsLpIpSigProfileEntry 11 }

sonusDsLpIpSigProfEgressBciInterworkEncountered OBJECT-TYPE
    SYNTAX          SonusBoolean
    MAX-ACCESS      read-write
    STATUS          current
    DESCRIPTION     
            "If set tot TRUE, the GSX sets the Inter-working
             Indicator bit in the BCI parameter of backward SS7
             messages (e.g., ACM or ANM). This is applicable to
             SIP Servers."
    DEFVAL          { false }
    ::= { sonusDsLpIpSigProfileEntry 12 }

sonusDsLpIpSigProfEgressBciIsdnAccess OBJECT-TYPE
    SYNTAX          SonusBoolean
    MAX-ACCESS      read-write
    STATUS          current
    DESCRIPTION     
            "If this is set to TRUE, the GSX sets the ISDN Access
             Indicator bit in the BCI parameter of backward SS7
             messages (e.g., ACM or ANM). This is applicable to
             SIP Servers."
    DEFVAL          { false }
    ::= { sonusDsLpIpSigProfileEntry 13 }

sonusDsLpIpSigProfEgressNumberPortabilityAttributesNpdiOptions OBJECT-TYPE
    SYNTAX          INTEGER { includenpdi(1), includenpdiyes(2), 
                        donotincludenpdi(3) }
    MAX-ACCESS      read-write
    STATUS          current
    DESCRIPTION     
            "Three values control whether the GSX send the SIP npdi
             parameter in the egress INVITE message when LNP translation has
             been performed by the preceding switch (local policy server does not perform
             LNP translation). When includenpdi is selected, the GSX
             sends npdi in the userinfo portion of the Request
             URI. When includenpdiyes is selected, the GSX
             sends npdi=yes. When donotincludenpdi is
             selected,the GSX do not send the npdi parameter."
    DEFVAL          { includenpdi }
    ::= { sonusDsLpIpSigProfileEntry 14 }

sonusDsLpIpSigProfEgressNumberPortabilityAttributesFlagsDisableRn OBJECT-TYPE
    SYNTAX          SonusBoolean
    MAX-ACCESS      read-write
    STATUS          current
    DESCRIPTION     
            "Controls whether the GSX send the SIP rn parameter
             in the egress INVITE message when an LNP translated
             number is present. When set to FALSE, the GSX send
             rn=NNNN in the userinfo portion of the Request URI,
             where NNNN is the LNP translated number. When set to
             TRUE, the GSX do not send the rn parameter."
    DEFVAL          { false }
    ::= { sonusDsLpIpSigProfileEntry 15 }

sonusDsLpIpSigProfEgressPrivacyTransparency OBJECT-TYPE
    SYNTAX          SonusBoolean
    MAX-ACCESS      read-write
    STATUS          current
    DESCRIPTION     
            "When set to TRUE, the ingress Privacy information is
             passed through unchanged."
    DEFVAL          { false }
    ::= { sonusDsLpIpSigProfileEntry 16 }

sonusDsLpIpSigProfEgressPrivacyPrivacyInfo OBJECT-TYPE
    SYNTAX          INTEGER { ppreferredid(1), passertedid(2), 
                        remotepartyid(3) }
    MAX-ACCESS      read-write
    STATUS          current
    DESCRIPTION     
            "Specifies which of the following headers the GSX will
             use when sending privacy information in outgoing SIP
             INVITE messages:
             ppreferredid: Used by a User Agent (UA) to carry the
                identity the caller wishes to be used, and sent to a
                trusted proxy to be inserted in the P-Asserted-Identity
                field. 
             passertedid: Used among trusted SIP entities (typically
                intermediaries) to carry the identity of the caller as
                it was verified by authentication.
             remotepartyid: Used among trusted SIP entities (typically
                intermediaries) to carry the identity of the caller as
                it was verified by authentication. This header is
                specified in an earlier RFC that continues to be supported."
    DEFVAL          { ppreferredid }
    ::= { sonusDsLpIpSigProfileEntry 17 }

sonusDsLpIpSigProfEgressPrivacyFlagsIncludePrivacy OBJECT-TYPE
    SYNTAX          SonusBoolean
    MAX-ACCESS      read-write
    STATUS          current
    DESCRIPTION     
            "Specifies whether the GSX includes privacy
             information in outgoing SIP INVITE messages. If set to
             TRUE, the GSX will include either a P-Preferred-Identity
             header or a P-Asserted-Identity header (provisioned in
             Privacy Information above) in outgoing SIP INVITE messages.
             The GSX will also insert an Anonymous identifier in the SIP
             From field and the GSX will include a Privacy header that
             contains a Critical token.
             If set to FALSE, the GSX will not include a
             P-Preferred-Identity header or a P-Asserted-Identity header,
             an Anonymous identifier in the SIP From field, or a Privacy
             header that contains a Critical token in outgoing SIP INVITE
             messages. The default setting is TRUE."
    DEFVAL          { true }
    ::= { sonusDsLpIpSigProfileEntry 18 }

sonusDsLpIpSigProfEgressPrivacyFlagsPrivacyRequiredByProxy OBJECT-TYPE
    SYNTAX          SonusBoolean
    MAX-ACCESS      read-write
    STATUS          current
    DESCRIPTION     
            "If set to TRUE, indicates that privacy service is mandated
             for any calls to the SIP trunk (proxy). In this case the
             GSX will include a Proxy-Require header with a privacy value,
             and critical token in the Privacy header in the INVITE message.
             The privacy service must be applied by the proxy or the
             call will be rejected. If set to FALSE, the GSX will not
             include a Proxy-Require header with privacy value. The proxy
             will accept the call even if it cannot provide privacy service.
             The default setting is FALSE."
    DEFVAL          { false }
    ::= { sonusDsLpIpSigProfileEntry 19 }

sonusDsLpIpSigProfEgressSipCauseMappingInternal2Sip OBJECT-TYPE
    SYNTAX          Unsigned32 (1..64)
    MAX-ACCESS      read-write
    STATUS          current
    DESCRIPTION     
            "The specified index number will be used by the GSX to
             locate the corresponding CPC-to-SIP cause mapping
             profile on the GSX. The profile maps internal CPC
             (Call Processing Component) cause codes to SIP
             status codes."
    DEFVAL          { 1 }
    ::= { sonusDsLpIpSigProfileEntry 20 }

sonusDsLpIpSigProfEgressSipCauseMappingSip2Internal OBJECT-TYPE
    SYNTAX          Unsigned32 (1..64)
    MAX-ACCESS      read-write
    STATUS          current
    DESCRIPTION     
            "The specified index number will be used by the GSX
             to locate the corresponding SIP-to-CPC cause mapping
             profile on the GSX. The profile maps SIP status codes
             to internal CPC (Call Processing Component) cause codes."
    DEFVAL          { 1 }
    ::= { sonusDsLpIpSigProfileEntry 21 }

sonusDsLpIpSigProfEgressSipHeadersParamsSipToHeaderMapping OBJECT-TYPE
    SYNTAX          INTEGER { callednumber(1), orginalcallednumber(2), 
                        gapdialednumber(3) }
    MAX-ACCESS      read-write
    STATUS          current
    DESCRIPTION     
            "Indicates which number is mapped and returned in the
             outgoing SIP To header. Possible choices are: 
              - Called Number (default)
              - Original Called Number (OCN) 
              - GAP Dialed Number"
    DEFVAL          { callednumber }
    ::= { sonusDsLpIpSigProfileEntry 22 }

sonusDsLpIpSigProfCommonCreatePchargingVector OBJECT-TYPE
    SYNTAX          SonusBoolean
    MAX-ACCESS      read-write
    STATUS          current
    DESCRIPTION     
            "Controls whether a P-Charging-Vector header is created
             in outgoing SIP messages. When set to TRUE, the NBS creates
             a new P-Charging-Vector header in the outgoing message.
             When set to FALSE, the NBS does not create a new
             P-Charging-Vector header. Creating P-Charging-Vector headers
             is supported in INVITE and REGISTER messages. It is also
             supported in SUBSCRIBE, OPTIONS, and NOTIFY messages when
             received from the same direction as the REGISTER message.
             The P-Charging-Vector header contains the ICID value, which
             is used to correlate charging records among Sonus entities."
    DEFVAL          { false }
    ::= { sonusDsLpIpSigProfileEntry 23 }

sonusDsLpIpSigProfEgressSipHeadersParamsFlagsIncludeCpcInfo OBJECT-TYPE
    SYNTAX          SonusBoolean
    MAX-ACCESS      read-write
    STATUS          current
    DESCRIPTION     
            "If set to TRUE, the GSX will include the Calling Party
             Category (CPC) parameter value in the From header of
             outgoing SIP INVITE messages. The CPC parameter
             characterizes the station used to originate a call,
             such as ordinary, priority, data, test, operator,
             payphone, prison, hotel or unknown."
    DEFVAL          { false }
    ::= { sonusDsLpIpSigProfileEntry 24 }

sonusDsLpIpSigProfEgressSipHeadersParamsFlagsIncludeNpi OBJECT-TYPE
    SYNTAX          SonusBoolean
    MAX-ACCESS      read-write
    STATUS          current
    DESCRIPTION     
            "If set to TRUE, the GSX will include the Numbering
             Plan Indicator in a npi= parameter in outgoing INVITE
             messages."
    DEFVAL          { false }
    ::= { sonusDsLpIpSigProfileEntry 25 }

sonusDsLpIpSigProfEgressSipHeadersParamsFlagsIncludeOlip OBJECT-TYPE
    SYNTAX          SonusBoolean
    MAX-ACCESS      read-write
    STATUS          current
    DESCRIPTION     
            "If set to TRUE, the GSX will include the Originating
             Line Information Parameter in a oli= parameter in
             outgoing INVITE messages."
    DEFVAL          { false }
    ::= { sonusDsLpIpSigProfileEntry 26 }

sonusDsLpIpSigProfEgressTransportType1 OBJECT-TYPE
    SYNTAX          SonusTransportProtocolType
    MAX-ACCESS      read-write
    STATUS          current
    DESCRIPTION     
            "This configures the transport mode for SIP signaling."
    DEFVAL          { none }
    ::= { sonusDsLpIpSigProfileEntry 27 }

sonusDsLpIpSigProfEgressTransportType2 OBJECT-TYPE
    SYNTAX          SonusTransportProtocolType
    MAX-ACCESS      read-write
    STATUS          current
    DESCRIPTION     
            "This configures the transport mode for SIP signaling."
    DEFVAL          { none }
    ::= { sonusDsLpIpSigProfileEntry 28 }

sonusDsLpIpSigProfEgressTransportType3 OBJECT-TYPE
    SYNTAX          SonusTransportProtocolType
    MAX-ACCESS      read-write
    STATUS          current
    DESCRIPTION     
            "This configures the transport mode for SIP signaling."
    DEFVAL          { none }
    ::= { sonusDsLpIpSigProfileEntry 29 }

sonusDsLpIpSigProfEgressTransportType4 OBJECT-TYPE
    SYNTAX          SonusTransportProtocolType
    MAX-ACCESS      read-write
    STATUS          current
    DESCRIPTION     
            "This configures the transport mode for SIP signaling."
    DEFVAL          { none }
    ::= { sonusDsLpIpSigProfileEntry 30 }

sonusDsLpIpSigProfIngressFlags181Supported OBJECT-TYPE
    SYNTAX          SonusBoolean
    MAX-ACCESS      read-write
    STATUS          current
    DESCRIPTION     
            "When set to TRUE, the GSX supports SIP 181 Call Is Being
             Forwarded messages in the backward direction.
             It is provisioned on the ingress trunk group."
    DEFVAL          { false }
    ::= { sonusDsLpIpSigProfileEntry 31 }

sonusDsLpIpSigProfIngressFlags182Supported OBJECT-TYPE
    SYNTAX          SonusBoolean
    MAX-ACCESS      read-write
    STATUS          current
    DESCRIPTION     
            "When set to TRUE, the GSX supports SIP 182 Queued
             messages in the backward direction.
             It is provisioned on the ingress trunk group."
    DEFVAL          { false }
    ::= { sonusDsLpIpSigProfileEntry 32 }

sonusDsLpIpSigProfIngressFlagsNoSdpIn180Supported OBJECT-TYPE
    SYNTAX          SonusBoolean
    MAX-ACCESS      read-write
    STATUS          current
    DESCRIPTION     
            "By default, the GSX includes SDP in outbound 180
             messages. When set to TRUE, the GSX does not include
             SDP in outbound 180 messages. It converts the 180
             message to a 183 message instead. When set to FALSE,
             the GSX includes SDP in outbound 180 messages."
    DEFVAL          { false }
    ::= { sonusDsLpIpSigProfileEntry 33 }

sonusDsLpIpSigProfIngressFlagsSendSdpIn200OkIf18xReliable OBJECT-TYPE
    SYNTAX          SonusBoolean
    MAX-ACCESS      read-write
    STATUS          current
    DESCRIPTION     
            "When set to TRUE, the GSX sends SDP in final 200 OK
             response messages when provisional 18x responses are
             reliable. When set to FALSE, the GSX does not send
             SDP in final 200 OK response messages. The default
             behavior in previous releases was to send SDP in final
             200 OK response messages, and during an upgrade to this
             release, this flag is automatically selected for current
             IP signaling configurations. However, the default behavior
             in this release is to not send SDP in final 200 OK response
             messages, and if you are creating a new IP signaling
             profile, you must manually set this field to TRUE."
    DEFVAL          { false }
    ::= { sonusDsLpIpSigProfileEntry 34 }

sonusDsLpIpSigProfCommonCallHoldInterworking OBJECT-TYPE
    SYNTAX          SonusBoolean
    MAX-ACCESS      read-write
    STATUS          current
    DESCRIPTION     
            "This control determines whether or not call hold via
             CPG messages will be supported.  By default this support
             is turned off."
    DEFVAL          { false }
    ::= { sonusDsLpIpSigProfileEntry 35 }

sonusDsLpIpSigProfCommonTerminalPortabilityInterworking OBJECT-TYPE
    SYNTAX          SonusBoolean
    MAX-ACCESS      read-write
    STATUS          current
    DESCRIPTION     
            "This control determines whether or not terminal portability
             via SUS/RES messages will be supported.  By default this 
             support is turned off."
    DEFVAL          { false }
    ::= { sonusDsLpIpSigProfileEntry 36 }

sonusDsLpIpSigProfCommonInsertPeerAddressAsTopRouteHeader OBJECT-TYPE
    SYNTAX          SonusBoolean
    MAX-ACCESS      read-write
    STATUS          current
    DESCRIPTION     
            "This flag controls whether GSX will insert next-hop as top-most
             route in outgoing INVITE message.  By default this insertion is
             		 turned off."
    DEFVAL          { false }
    ::= { sonusDsLpIpSigProfileEntry 37 }

sonusDsLpIpSigProfCommonAlertInfoTransparency OBJECT-TYPE
    SYNTAX          SonusBoolean
    MAX-ACCESS      read-write
    STATUS          current
    DESCRIPTION     
            "When set to TRUE, the ingress Alert information is
             passed through unchanged."
    DEFVAL          { false }
    ::= { sonusDsLpIpSigProfileEntry 38 }

sonusDsLpIpSigProfCommonAuthcodeTransparency OBJECT-TYPE
    SYNTAX          SonusBoolean
    MAX-ACCESS      read-write
    STATUS          current
    DESCRIPTION     
            "When set to TRUE, the ingress Authcode information is
             passed through unchanged."
    DEFVAL          { false }
    ::= { sonusDsLpIpSigProfileEntry 39 }

sonusDsLpIpSigProfCommonErrorInfoTransparency OBJECT-TYPE
    SYNTAX          SonusBoolean
    MAX-ACCESS      read-write
    STATUS          current
    DESCRIPTION     
            "When set to TRUE, the ingress Error-Info information is
             passed through unchanged."
    DEFVAL          { false }
    ::= { sonusDsLpIpSigProfileEntry 40 }

sonusDsLpIpSigProfCommonFromTransparency OBJECT-TYPE
    SYNTAX          SonusBoolean
    MAX-ACCESS      read-write
    STATUS          current
    DESCRIPTION     
            "When set to TRUE, the ingress FROM header information is
             passed through unchanged."
    DEFVAL          { false }
    ::= { sonusDsLpIpSigProfileEntry 41 }

sonusDsLpIpSigProfCommonMaxForwardsTransparency OBJECT-TYPE
    SYNTAX          SonusBoolean
    MAX-ACCESS      read-write
    STATUS          current
    DESCRIPTION     
            "When set to TRUE, the ingress Max-Forwards header information is
             passed through unchanged."
    DEFVAL          { false }
    ::= { sonusDsLpIpSigProfileEntry 42 }

sonusDsLpIpSigProfCommonMWIBodyTransparency OBJECT-TYPE
    SYNTAX          SonusBoolean
    MAX-ACCESS      read-write
    STATUS          current
    DESCRIPTION     
            "When set to TRUE, the ingress MWI-Body information is
             passed through unchanged."
    DEFVAL          { false }
    ::= { sonusDsLpIpSigProfileEntry 43 }

sonusDsLpIpSigProfCommonPChargingVectorTransparency OBJECT-TYPE
    SYNTAX          SonusBoolean
    MAX-ACCESS      read-write
    STATUS          current
    DESCRIPTION     
            "When set to TRUE, the ingress P-Charging-Vector information is
             passed through unchanged."
    DEFVAL          { false }
    ::= { sonusDsLpIpSigProfileEntry 44 }

sonusDsLpIpSigProfCommonPEarlyMediaTransparency OBJECT-TYPE
    SYNTAX          SonusBoolean
    MAX-ACCESS      read-write
    STATUS          current
    DESCRIPTION     
            "When set to TRUE, the ingress P-Early-Media information is
             passed through unchanged."
    DEFVAL          { false }
    ::= { sonusDsLpIpSigProfileEntry 45 }

sonusDsLpIpSigProfCommonPathTransparency OBJECT-TYPE
    SYNTAX          SonusBoolean
    MAX-ACCESS      read-write
    STATUS          current
    DESCRIPTION     
            "When set to TRUE, the ingress Path header information is
             passed through unchanged."
    DEFVAL          { false }
    ::= { sonusDsLpIpSigProfileEntry 46 }

sonusDsLpIpSigProfCommonQsigBodyTransparency OBJECT-TYPE
    SYNTAX          SonusBoolean
    MAX-ACCESS      read-write
    STATUS          current
    DESCRIPTION     
            "When set to TRUE, the ingress Qsig-Body information is
             passed through unchanged."
    DEFVAL          { false }
    ::= { sonusDsLpIpSigProfileEntry 47 }

sonusDsLpIpSigProfCommonReasonTransparency OBJECT-TYPE
    SYNTAX          SonusBoolean
    MAX-ACCESS      read-write
    STATUS          current
    DESCRIPTION     
            "When set to TRUE, the ingress Reason Header information is
             passed through unchanged."
    DEFVAL          { false }
    ::= { sonusDsLpIpSigProfileEntry 48 }

sonusDsLpIpSigProfCommonReferredByTransparency OBJECT-TYPE
    SYNTAX          SonusBoolean
    MAX-ACCESS      read-write
    STATUS          current
    DESCRIPTION     
            "When set to TRUE, the ingress Referred-By information is
             passed through unchanged."
    DEFVAL          { false }
    ::= { sonusDsLpIpSigProfileEntry 49 }

sonusDsLpIpSigProfCommonRequestUriTransparency OBJECT-TYPE
    SYNTAX          SonusBoolean
    MAX-ACCESS      read-write
    STATUS          current
    DESCRIPTION     
            "When set to TRUE, the ingress Request-Uri header information is
             passed through unchanged."
    DEFVAL          { false }
    ::= { sonusDsLpIpSigProfileEntry 50 }

sonusDsLpIpSigProfCommonRouteTransparency OBJECT-TYPE
    SYNTAX          SonusBoolean
    MAX-ACCESS      read-write
    STATUS          current
    DESCRIPTION     
            "When set to TRUE, the ingress Route Header information is
             passed through unchanged."
    DEFVAL          { false }
    ::= { sonusDsLpIpSigProfileEntry 51 }

sonusDsLpIpSigProfCommonServiceRouteTransparency OBJECT-TYPE
    SYNTAX          SonusBoolean
    MAX-ACCESS      read-write
    STATUS          current
    DESCRIPTION     
            "When set to TRUE, the ingress Service-Route Header information is
             passed through unchanged."
    DEFVAL          { false }
    ::= { sonusDsLpIpSigProfileEntry 52 }

sonusDsLpIpSigProfCommonSipBodyTransparency OBJECT-TYPE
    SYNTAX          SonusBoolean
    MAX-ACCESS      read-write
    STATUS          current
    DESCRIPTION     
            "When set to TRUE, the ingress SIP-Body information is
             passed through unchanged."
    DEFVAL          { false }
    ::= { sonusDsLpIpSigProfileEntry 53 }

sonusDsLpIpSigProfCommonSipfragBodyTransparency OBJECT-TYPE
    SYNTAX          SonusBoolean
    MAX-ACCESS      read-write
    STATUS          current
    DESCRIPTION     
            "When set to TRUE, the ingress SIPFRAG-Body information is
             passed through unchanged."
    DEFVAL          { false }
    ::= { sonusDsLpIpSigProfileEntry 54 }

sonusDsLpIpSigProfCommonToTransparency OBJECT-TYPE
    SYNTAX          SonusBoolean
    MAX-ACCESS      read-write
    STATUS          current
    DESCRIPTION     
            "When set to TRUE, the ingress To header information is
             passed through unchanged."
    DEFVAL          { false }
    ::= { sonusDsLpIpSigProfileEntry 55 }

sonusDsLpIpSigProfCommonToneBodyTransparency OBJECT-TYPE
    SYNTAX          SonusBoolean
    MAX-ACCESS      read-write
    STATUS          current
    DESCRIPTION     
            "When set to TRUE, the ingress Tone Body information is
             passed through unchanged."
    DEFVAL          { false }
    ::= { sonusDsLpIpSigProfileEntry 56 }

sonusDsLpIpSigProfCommonUnknownBodyTransparency OBJECT-TYPE
    SYNTAX          SonusBoolean
    MAX-ACCESS      read-write
    STATUS          current
    DESCRIPTION     
            "When set to TRUE, the ingress Unknown Body information is
             passed through unchanged."
    DEFVAL          { false }
    ::= { sonusDsLpIpSigProfileEntry 57 }

sonusDsLpIpSigProfCommonUnknownHeaderTransparency OBJECT-TYPE
    SYNTAX          SonusBoolean
    MAX-ACCESS      read-write
    STATUS          current
    DESCRIPTION     
            "When set to TRUE, the ingress Unknown Header information is
             passed through unchanged."
    DEFVAL          { false }
    ::= { sonusDsLpIpSigProfileEntry 58 }

sonusDsLpIpSigProfCommonDTMFBodyRelay OBJECT-TYPE
    SYNTAX          SonusBoolean
    MAX-ACCESS      read-write
    STATUS          current
    DESCRIPTION     
            "When set to TRUE, the ingress DTMF Body is
             relayed."
    DEFVAL          { false }
    ::= { sonusDsLpIpSigProfileEntry 59 }

sonusDsLpIpSigProfCommonInfoRelay OBJECT-TYPE
    SYNTAX          SonusBoolean
    MAX-ACCESS      read-write
    STATUS          current
    DESCRIPTION     
            "When set to TRUE, the ingress INFO message is
             relayed."
    DEFVAL          { false }
    ::= { sonusDsLpIpSigProfileEntry 60 }

sonusDsLpIpSigProfCommonMessageRelay OBJECT-TYPE
    SYNTAX          SonusBoolean
    MAX-ACCESS      read-write
    STATUS          current
    DESCRIPTION     
            "When set to TRUE, the ingress MESSAGE message is
             relayed."
    DEFVAL          { false }
    ::= { sonusDsLpIpSigProfileEntry 61 }

sonusDsLpIpSigProfCommonNotifyRelay OBJECT-TYPE
    SYNTAX          SonusBoolean
    MAX-ACCESS      read-write
    STATUS          current
    DESCRIPTION     
            "When set to TRUE, the ingress NOTIFY message is
             relayed."
    DEFVAL          { false }
    ::= { sonusDsLpIpSigProfileEntry 62 }

sonusDsLpIpSigProfCommonOptionsRelay OBJECT-TYPE
    SYNTAX          SonusBoolean
    MAX-ACCESS      read-write
    STATUS          current
    DESCRIPTION     
            "When set to TRUE, the ingress OPTIONS message is
             relayed."
    DEFVAL          { false }
    ::= { sonusDsLpIpSigProfileEntry 63 }

sonusDsLpIpSigProfCommonReferRelay OBJECT-TYPE
    SYNTAX          SonusBoolean
    MAX-ACCESS      read-write
    STATUS          current
    DESCRIPTION     
            "When set to TRUE, the ingress REFER message is
             relayed."
    DEFVAL          { false }
    ::= { sonusDsLpIpSigProfileEntry 64 }

sonusDsLpIpSigProfCommonSonusMediaBodyRelay OBJECT-TYPE
    SYNTAX          SonusBoolean
    MAX-ACCESS      read-write
    STATUS          current
    DESCRIPTION     
            "When set to TRUE, the ingress Sonus Media Body is
             relayed."
    DEFVAL          { false }
    ::= { sonusDsLpIpSigProfileEntry 65 }

sonusDsLpIpSigProfCommonStatusCode3xxRelay OBJECT-TYPE
    SYNTAX          SonusBoolean
    MAX-ACCESS      read-write
    STATUS          current
    DESCRIPTION     
            "When set to TRUE, the ingress 3xx message is
             relayed."
    DEFVAL          { false }
    ::= { sonusDsLpIpSigProfileEntry 66 }

sonusDsLpIpSigProfCommonStatusCode4xxTo6xxRelay OBJECT-TYPE
    SYNTAX          SonusBoolean
    MAX-ACCESS      read-write
    STATUS          current
    DESCRIPTION     
            "When set to TRUE, the ingress 4xx-6xx message is
             relayed."
    DEFVAL          { false }
    ::= { sonusDsLpIpSigProfileEntry 67 }

sonusDsLpIpSigProfCommonThirdPartyBodyRelay OBJECT-TYPE
    SYNTAX          SonusBoolean
    MAX-ACCESS      read-write
    STATUS          current
    DESCRIPTION     
            "When set to TRUE, the ingress Third Pary Body is
             relayed."
    DEFVAL          { false }
    ::= { sonusDsLpIpSigProfileEntry 68 }

sonusDsLpIpSigProfCommonAddPathServiceRoutePerTG OBJECT-TYPE
    SYNTAX          SonusBoolean
    MAX-ACCESS      read-write
    STATUS          current
    DESCRIPTION     
            "When enabled, trunk group information is added to
             to pushed Path and Service Route headers"
    DEFVAL          { false }
    ::= { sonusDsLpIpSigProfileEntry 69 }

sonusDsLpIpSigProfCommonCreatePathHeader OBJECT-TYPE
    SYNTAX          SonusBoolean
    MAX-ACCESS      read-write
    STATUS          current
    DESCRIPTION     
            "When enabled, the NBS creates a new Path header in the outgoing REGISTER message"
    DEFVAL          { false }
    ::= { sonusDsLpIpSigProfileEntry 70 }

sonusDsLpIpSigProfCommonCreateServiceRouteHeader OBJECT-TYPE
    SYNTAX          SonusBoolean
    MAX-ACCESS      read-write
    STATUS          current
    DESCRIPTION     
            "When enabled, the NBS creates a new Service Route header in the outgoing REGISTER message"
    DEFVAL          { false }
    ::= { sonusDsLpIpSigProfileEntry 71 }

sonusDsLpIpSigProfCommonDisableHostTranslation OBJECT-TYPE
    SYNTAX          SonusBoolean
    MAX-ACCESS      read-write
    STATUS          current
    DESCRIPTION     
            "When set to true, host name translation is disabled.
             When set to false, host name translation is enabled.
             This applies to all URL style headers that require transparency and
             defines the processing that GSX is to apply to the hostname portion of
             these headers before forwarding."
    DEFVAL          { false }
    ::= { sonusDsLpIpSigProfileEntry 72 }

sonusDsLpIpSigProfCommonDoNotIncludeSSAttributeInReInvite OBJECT-TYPE
    SYNTAX          SonusBoolean
    MAX-ACCESS      read-write
    STATUS          current
    DESCRIPTION     
            "When enabled, the GSX does not send silence
             suppression (no a=silenceSupp is sent) in the SDP to the remote peer.
             When disabled, and when silence suppression is off, the
             GSX sends a=silenceSupp:off in the SDP to the remote peer."
    DEFVAL          { false }
    ::= { sonusDsLpIpSigProfileEntry 73 }

sonusDsLpIpSigProfCommonIncludeSSAttributeInInitialInvite OBJECT-TYPE
    SYNTAX          SonusBoolean
    MAX-ACCESS      read-write
    STATUS          current
    DESCRIPTION     
            "When enabled, the a=silenceSupp:off
             is sent in the Initial Invite SDP to the remote peer when Silence
             Suppression is OFF. When disabled, a=silenceSupp is
             not sent in the Initial Invite SDP to the remote peer."
    DEFVAL          { false }
    ::= { sonusDsLpIpSigProfileEntry 74 }

sonusDsLpIpSigProfCommonIncludeTransportTypeInContactHeader OBJECT-TYPE
    SYNTAX          SonusBoolean
    MAX-ACCESS      read-write
    STATUS          current
    DESCRIPTION     
            "When enabled, the PSX SIPE includes the Transport Type
             parameter in the Contact headers of 3XX responses. When 
             disabled , the PSX SIPE does not include the Transport Type
             parameter."
    DEFVAL          { false }
    ::= { sonusDsLpIpSigProfileEntry 75 }

sonusDsLpIpSigProfCommonReQueryPsxOnRegisterRequest OBJECT-TYPE
    SYNTAX          SonusBoolean
    MAX-ACCESS      read-write
    STATUS          current
    DESCRIPTION     
            "When enabled, the GSX will requery the Policy Server when it
             receives a register refresh message, which may result in a new or
             updated result for the register relay. When disabled 
             (default), the GSX does not requery the Policy Request on a register refresh.
             "
    DEFVAL          { false }
    ::= { sonusDsLpIpSigProfileEntry 76 }

sonusDsLpIpSigProfCommonSendDirectMediaInfoInSdpAttribute OBJECT-TYPE
    SYNTAX          SonusBoolean
    MAX-ACCESS      read-write
    STATUS          current
    DESCRIPTION     
            "When enabled, the GSX sends direct media
             information in the SDP attribute X-dmi. When disabled,
             the GSX does not send direct media information."
    DEFVAL          { false }
    ::= { sonusDsLpIpSigProfileEntry 77 }

sonusDsLpIpSigProfCommonStorePathHeader OBJECT-TYPE
    SYNTAX          SonusBoolean
    MAX-ACCESS      read-write
    STATUS          current
    DESCRIPTION     
            "Controls whether a Path header received in an incoming SIP message
             should be stored/cached locally on the NBS. When enabled, the
             received Path header is stored."
    DEFVAL          { false }
    ::= { sonusDsLpIpSigProfileEntry 78 }

sonusDsLpIpSigProfCommonStoreServiceRouteHeader OBJECT-TYPE
    SYNTAX          SonusBoolean
    MAX-ACCESS      read-write
    STATUS          current
    DESCRIPTION     
            "Controls whether a Service-Route header received in a 200-class
             response to a REGISTER request should be stored/cached locally on the
             NBS. When enabled, the received Service-Route header is stored."
    DEFVAL          { false }
    ::= { sonusDsLpIpSigProfileEntry 79 }

sonusDsLpIpSigProfIngressFlagsSendSdpInSubsequent18x OBJECT-TYPE
    SYNTAX          SonusBoolean
    MAX-ACCESS      read-write
    STATUS          current
    DESCRIPTION     
            "When disabled, the GSX may not send SDP in subsequent 18x response messages."
    DEFVAL          { false }
    ::= { sonusDsLpIpSigProfileEntry 80 }

sonusDsLpIpSigProfEgressFlagsConvertInactiveToSendRecv OBJECT-TYPE
    SYNTAX          SonusBoolean
    MAX-ACCESS      read-write
    STATUS          current
    DESCRIPTION     
            "When enabled, the GSX converts a=inactive to a=sendrecv in the egress INVITE message."
    DEFVAL          { false }
    ::= { sonusDsLpIpSigProfileEntry 81 }

sonusDsLpIpSigProfEgressFlagsSuppressUnregister OBJECT-TYPE
    SYNTAX          SonusBoolean
    MAX-ACCESS      read-write
    STATUS          current
    DESCRIPTION     
            "When enabled, the GSX does not send an unregister
             message (Register=0) to the registrar upon expiration of a SIP UA
             registration."
    DEFVAL          { false }
    ::= { sonusDsLpIpSigProfileEntry 82 }

sonusDsLpIpSigProfEgressDomainNamePreserveIngressFromDomainName OBJECT-TYPE
    SYNTAX          SonusBoolean
    MAX-ACCESS      read-write
    STATUS          current
    DESCRIPTION     
            "When enabled, the PSX/GSX sends the domain name
             received in the FROM field as the originating domain name in outgoing
             SIP INVITE messages."
    DEFVAL          { false }
    ::= { sonusDsLpIpSigProfileEntry 83 }

sonusDsLpIpSigProfEgressDomainNamePreserveIngressRURIDomainName OBJECT-TYPE
    SYNTAX          SonusBoolean
    MAX-ACCESS      read-write
    STATUS          current
    DESCRIPTION     
            "When enabled, the PSX/GSX uses the domain name
             received in the Request-URI as the destination domain name in outgoing
             SIP INVITE messages."
    DEFVAL          { false }
    ::= { sonusDsLpIpSigProfileEntry 84 }

sonusDsLpIpSigProfEgressDomainNameUseSipDomainNameInFromField OBJECT-TYPE
    SYNTAX          SonusBoolean
    MAX-ACCESS      read-write
    STATUS          current
    DESCRIPTION     
            "If enabled, the GSX
             will use the originating gateway information returned in the policy
             response as the host-port of the FROM URI in the outgoing INVITE
             message."
    DEFVAL          { false }
    ::= { sonusDsLpIpSigProfileEntry 85 }

sonusDsLpIpSigProfEgressDomainNameUseSIPDomainNameInRequestUri OBJECT-TYPE
    SYNTAX          SonusBoolean
    MAX-ACCESS      read-write
    STATUS          current
    DESCRIPTION     
            "When enabled, the GSX includes the trunk group
             domain associated with the egress trunk group as the destination domain
             name in outgoing SIP INVITE messages."
    DEFVAL          { false }
    ::= { sonusDsLpIpSigProfileEntry 86 }

sonusDsLpIpSigProfEgressSipHeadersParamsFlagsTransparency OBJECT-TYPE
    SYNTAX          SonusBoolean
    MAX-ACCESS      read-write
    STATUS          current
    DESCRIPTION     
            "When enabled, the ingress Diversion header is passed
             through unchanged. Call forwarding data mapping transparency applies
             to Diversion header only."
    DEFVAL          { false }
    ::= { sonusDsLpIpSigProfileEntry 87 }

sonusDsLpIpSigProfEgressRedirectMode OBJECT-TYPE
    SYNTAX          INTEGER { accept(0), allowsingleattempt(1), 
                        reject(2) }
    MAX-ACCESS      read-write
    STATUS          current
    DESCRIPTION     
            "Accept Redirection: Multiple redirections are allowed. (the default)
             Allow Single Redirect Attempt: Only a single Redirect is allowed per
                   route. Additional Redirects cause crankback to be performed.
             Reject Redirection: If a Redirect is received, crank back is performed."
    DEFVAL          { accept }
    ::= { sonusDsLpIpSigProfileEntry 88 }

sonusDsLpIpSigProfEgressRedirectContactHandling OBJECT-TYPE
    SYNTAX          INTEGER { merge(1), purge(2) }
    MAX-ACCESS      read-write
    STATUS          current
    DESCRIPTION     
            "Merge Received Contacts with Existing Contacts OR Purge Existing Contacts"
    DEFVAL          { merge }
    ::= { sonusDsLpIpSigProfileEntry 89 }

sonusDsLpIpSigProfCommonHistoryInfoTransparency OBJECT-TYPE
    SYNTAX          SonusBoolean
    MAX-ACCESS      read-write
    STATUS          current
    DESCRIPTION     
            "When set to TRUE, the ingress History Info information is
             passed through unchanged."
    DEFVAL          { false }
    ::= { sonusDsLpIpSigProfileEntry 90 }

sonusDsLpIpSigProfCommonHandleIpAddrressesNotPresent OBJECT-TYPE
    SYNTAX          INTEGER { rejectcall(1), defaultzoneiptg(2), 
                        defaultiptg(3), transferringiptg(4) }
    MAX-ACCESS      read-write
    STATUS          current
    DESCRIPTION     
            "This Flag is used select call transfer mode for a call"
    DEFVAL          { transferringiptg }
    ::= { sonusDsLpIpSigProfileEntry 91 }

sonusDsLpIpSigProfCommonForceReRouteViaPolicyQuery OBJECT-TYPE
    SYNTAX          SonusBoolean
    MAX-ACCESS      read-write
    STATUS          current
    DESCRIPTION     
            "This Flag is used select call transfer mode for a call"
    DEFVAL          { false }
    ::= { sonusDsLpIpSigProfileEntry 92 }

sonusDsLpIpSigProfCommonTargetDialogTransparency OBJECT-TYPE
    SYNTAX          SonusBoolean
    MAX-ACCESS      read-write
    STATUS          current
    DESCRIPTION     
            "When set to TRUE, the ingress Target-Dialog header is
             passed through unchanged, but if matching dialog exists on 
             NBS it would be changed to peer dialog."
    DEFVAL          { false }
    ::= { sonusDsLpIpSigProfileEntry 93 }

sonusDsLpSigProfFlagsCommonEnablingRTCPinfo OBJECT-TYPE
    SYNTAX          SonusBoolean
    MAX-ACCESS      read-write
    STATUS          current
    DESCRIPTION     
            "When set to TRUE, optional rtcp attribute is published in outgoing SDP"
    DEFVAL          { false }
    ::= { sonusDsLpIpSigProfileEntry 94 }

sonusDsLpDialPlanObjects OBJECT IDENTIFIER
    ::= { sonusLocalPolicyServicesMIBObjects 7 }

sonusDsLpDialPlanNextIndex OBJECT-TYPE
    SYNTAX          Integer32
    MAX-ACCESS      read-only
    STATUS          current
    DESCRIPTION     
            "The next valid index to use when creating a new sonusDsLpDialPlanEntry"
    ::= { sonusDsLpDialPlanObjects 1 }

sonusDsLpDialPlanTable OBJECT-TYPE
    SYNTAX          SEQUENCE OF SonusDsLpDialPlanEntry
    MAX-ACCESS      not-accessible
    STATUS          current
    DESCRIPTION     
            "Each entry of this table defines a Dial Plan Profile."
    ::= { sonusDsLpDialPlanObjects 2 }

sonusDsLpDialPlanEntry OBJECT-TYPE
    SYNTAX          SonusDsLpDialPlanEntry
    MAX-ACCESS      not-accessible
    STATUS          current
    DESCRIPTION     
            "Definition of a Dial Plan Profile."
    INDEX           { sonusDsLpDialPlanIndex }
    ::= { sonusDsLpDialPlanTable 1 }

SonusDsLpDialPlanEntry ::=
    SEQUENCE {
        sonusDsLpDialPlanIndex          Unsigned32,
        sonusDsLpDialPlanName           SonusName,
        sonusDsLpDialPlanNationalAccessCode   DisplayString,
        sonusDsLpDialPlanInternationalAccessCode        DisplayString,
        sonusDsLpDialPlanOperatorNumber DisplayString,
        sonusDsLpDialPlanCalledPartyNumberDigitMax          Unsigned32,
        sonusDsLpDialPlanCalledPartyNumberDigitMin          Unsigned32,
        sonusDsLpDialPlanRowStatus      RowStatus
    }

sonusDsLpDialPlanIndex OBJECT-TYPE
    SYNTAX          Unsigned32
    MAX-ACCESS      read-only
    STATUS          current
    DESCRIPTION     
            "A unique index for each Dial Plan Profile."
    ::= { sonusDsLpDialPlanEntry 1 }

sonusDsLpDialPlanName OBJECT-TYPE
    SYNTAX          SonusName
    MAX-ACCESS      read-write
    STATUS          current
    DESCRIPTION     
            "The name of this Dial Plan Profile."
    ::= { sonusDsLpDialPlanEntry 2 }

sonusDsLpDialPlanNationalAccessCode OBJECT-TYPE
    SYNTAX          DisplayString (SIZE(0..10))
    MAX-ACCESS      read-write
    STATUS          current
    DESCRIPTION     
            "The National Acceess Code for this dial plan profile."
    ::= { sonusDsLpDialPlanEntry 3 }

sonusDsLpDialPlanInternationalAccessCode OBJECT-TYPE
    SYNTAX          DisplayString (SIZE(0..10))
    MAX-ACCESS      read-write
    STATUS          current
    DESCRIPTION     
            "The International Acceess Code for this dial plan profile."
    ::= { sonusDsLpDialPlanEntry 4 }

sonusDsLpDialPlanOperatorNumber OBJECT-TYPE
    SYNTAX          DisplayString (SIZE(0..30))
    MAX-ACCESS      read-write
    STATUS          current
    DESCRIPTION     
            "The Operator Number for this dial plan profile."
    ::= { sonusDsLpDialPlanEntry 5 }

sonusDsLpDialPlanCalledPartyNumberDigitMax OBJECT-TYPE
    SYNTAX          Unsigned32 (0..30)
    MAX-ACCESS      read-write
    STATUS          current
    DESCRIPTION     
            "Maximum digits in a Called Party Number for this dial plan profile (default is 0)."
    DEFVAL          { 0 }
    ::= { sonusDsLpDialPlanEntry 6 }

sonusDsLpDialPlanCalledPartyNumberDigitMin OBJECT-TYPE
    SYNTAX          Unsigned32 (0..30)
    MAX-ACCESS      read-write
    STATUS          current
    DESCRIPTION     
            "Minimum digits in a Called Party Number this dial plan profile (default is 0)."
    DEFVAL          { 0 }
    ::= { sonusDsLpDialPlanEntry 7 }

sonusDsLpDialPlanRowStatus OBJECT-TYPE
    SYNTAX          RowStatus
    MAX-ACCESS      read-write
    STATUS          current
    DESCRIPTION     
            "This is for SNMP use."
    ::= { sonusDsLpDialPlanEntry 8 }

sonusDsLpToneAnnProfileObjects OBJECT IDENTIFIER
    ::= { sonusLocalPolicyServicesMIBObjects 8 }

sonusDsLpToneAnnProfNextIndex OBJECT-TYPE
    SYNTAX          Integer32
    MAX-ACCESS      read-only
    STATUS          current
    DESCRIPTION     
            "The next valid index to use when creating a new sonusDsLpToneAnnProfileEntry"
    ::= { sonusDsLpToneAnnProfileObjects 1 }

sonusDsLpToneAnnProfileTable OBJECT-TYPE
    SYNTAX          SEQUENCE OF SonusDsLpToneAnnProfileEntry
    MAX-ACCESS      not-accessible
    STATUS          current
    DESCRIPTION     
            "Each entry of this table defines a Tone And Announcement Profile."
    ::= { sonusDsLpToneAnnProfileObjects 2 }

sonusDsLpToneAnnProfileEntry OBJECT-TYPE
    SYNTAX          SonusDsLpToneAnnProfileEntry
    MAX-ACCESS      not-accessible
    STATUS          current
    DESCRIPTION     
            "Definition of Tone and Announcement Profile."
    INDEX           { sonusDsLpToneAnnProfIndex }
    ::= { sonusDsLpToneAnnProfileTable 1 }

SonusDsLpToneAnnProfileEntry ::=
    SEQUENCE {
        sonusDsLpToneAnnProfIndex       Unsigned32,
        sonusDsLpToneAnnProfName        SonusName,
        sonusDsLpToneAnnProfRowStatus   RowStatus,
        sonusDsLpToneAnnProfLrbtSignalingTonePackageId              Unsigned32,
        sonusDsLpToneAnnProfLrbtMakeInBandToneAvailable               SonusBoolean,
        sonusDsLpToneAnnProfLrbtPrecedence  INTEGER
    }

sonusDsLpToneAnnProfIndex OBJECT-TYPE
    SYNTAX          Unsigned32
    MAX-ACCESS      read-only
    STATUS          current
    DESCRIPTION     
            "A unique index for each Tone and Announcement Profile."
    ::= { sonusDsLpToneAnnProfileEntry 1 }

sonusDsLpToneAnnProfName OBJECT-TYPE
    SYNTAX          SonusName
    MAX-ACCESS      read-write
    STATUS          current
    DESCRIPTION     
            "The name of this Tone and Announcement Profile."
    ::= { sonusDsLpToneAnnProfileEntry 2 }

sonusDsLpToneAnnProfRowStatus OBJECT-TYPE
    SYNTAX          RowStatus
    MAX-ACCESS      read-write
    STATUS          current
    DESCRIPTION     
            "This is for SNMP use."
    ::= { sonusDsLpToneAnnProfileEntry 3 }

sonusDsLpToneAnnProfLrbtSignalingTonePackageId OBJECT-TYPE
    SYNTAX          Unsigned32 (1..2048)
    MAX-ACCESS      read-write
    STATUS          current
    DESCRIPTION     
            "Specifies which signaling tone package to use"
    DEFVAL          { 1 }
    ::= { sonusDsLpToneAnnProfileEntry 4 }

sonusDsLpToneAnnProfLrbtMakeInBandToneAvailable OBJECT-TYPE
    SYNTAX          SonusBoolean
    MAX-ACCESS      read-write
    STATUS          current
    DESCRIPTION     
            "Specifies whether In band tone should be is used 
             or not. When set to TRUE , the GSX uses in band tone"
    DEFVAL          { false }
    ::= { sonusDsLpToneAnnProfileEntry 5 }

sonusDsLpToneAnnProfLrbtPrecedence OBJECT-TYPE
    SYNTAX          INTEGER { lower(1), higher(2) }
    MAX-ACCESS      read-write
    STATUS          current
    DESCRIPTION     
            "Specifies the priority of LRBT profile on LP TG.
             When set to HIGHER , the LRBT profile with HIGHER priority
             will be used by GSX."
    DEFVAL          { lower }
    ::= { sonusDsLpToneAnnProfileEntry 6 }

sonusDsLpTransEntryObjects OBJECT IDENTIFIER
    ::= { sonusLocalPolicyServicesMIBObjects 9 }

sonusDsLpTransEntryNextIndex OBJECT-TYPE
    SYNTAX          Integer32
    MAX-ACCESS      read-only
    STATUS          current
    DESCRIPTION     
            "The next valid index to use when creating a new sonusDsLpTranslationEntry"
    ::= { sonusDsLpTransEntryObjects 1 }

sonusDsLpTranslationEntryTable OBJECT-TYPE
    SYNTAX          SEQUENCE OF SonusDsLpTransEntryObject
    MAX-ACCESS      not-accessible
    STATUS          current
    DESCRIPTION     
            "Each entry of this table defines a Translation Entry table
             Local Policy server."
    ::= { sonusDsLpTransEntryObjects 2 }

sonusDsLpTransEntryObject OBJECT-TYPE
    SYNTAX          SonusDsLpTransEntryObject
    MAX-ACCESS      not-accessible
    STATUS          current
    DESCRIPTION     
            "Definition of a Local Policy Translation Entry table."
    INDEX           { sonusDsLpTransEntryIndex }
    ::= { sonusDsLpTranslationEntryTable 1 }

SonusDsLpTransEntryObject ::=
    SEQUENCE {
        sonusDsLpTransEntryIndex        Unsigned32,
        sonusDsLpTransEntrySrcTgIndex   Unsigned32,
        sonusDsLpTransEntryDestNumPrefix DisplayString,
        sonusDsLpTransEntryTransLblIndex Unsigned32,
        sonusDsLpTransEntryRowStatus    RowStatus
    }

sonusDsLpTransEntryIndex OBJECT-TYPE
    SYNTAX          Unsigned32
    MAX-ACCESS      read-only
    STATUS          current
    DESCRIPTION     
            "A unique index for each Translation Entry table entry."
    ::= { sonusDsLpTransEntryObject 1 }

sonusDsLpTransEntrySrcTgIndex OBJECT-TYPE
    SYNTAX          Unsigned32 (0..2048)
    MAX-ACCESS      read-write
    STATUS          current
    DESCRIPTION     
            "The index of the source trunk group of the call."
    ::= { sonusDsLpTransEntryObject 2 }

sonusDsLpTransEntryDestNumPrefix OBJECT-TYPE
    SYNTAX          DisplayString (SIZE(0..16))
    MAX-ACCESS      read-write
    STATUS          current
    DESCRIPTION     
            "The Destination Number Prefix for the Translation Entry lookup."
    ::= { sonusDsLpTransEntryObject 3 }

sonusDsLpTransEntryTransLblIndex OBJECT-TYPE
    SYNTAX          Unsigned32 (0..4096)
    MAX-ACCESS      read-write
    STATUS          current
    DESCRIPTION     
            "The Translation Labelname of this Translation Entry table."
    ::= { sonusDsLpTransEntryObject 4 }

sonusDsLpTransEntryRowStatus OBJECT-TYPE
    SYNTAX          RowStatus
    MAX-ACCESS      read-write
    STATUS          current
    DESCRIPTION     
            "This is for SNMP use."
    ::= { sonusDsLpTransEntryObject 5 }

sonusDsLpTransLblObjects OBJECT IDENTIFIER
    ::= { sonusLocalPolicyServicesMIBObjects 10 }

sonusDsLpTransLblNextIndex OBJECT-TYPE
    SYNTAX          Integer32
    MAX-ACCESS      read-only
    STATUS          current
    DESCRIPTION     
            "The next valid index to use when creating a new sonusDsLpTransLblEntry"
    ::= { sonusDsLpTransLblObjects 1 }

sonusDsLpTransLblTable OBJECT-TYPE
    SYNTAX          SEQUENCE OF SonusDsLpTransLblEntry
    MAX-ACCESS      not-accessible
    STATUS          current
    DESCRIPTION     
            "Each entry of this table defines a Translation Labelin the
             Local Policy server."
    ::= { sonusDsLpTransLblObjects 2 }

sonusDsLpTransLblEntry OBJECT-TYPE
    SYNTAX          SonusDsLpTransLblEntry
    MAX-ACCESS      not-accessible
    STATUS          current
    DESCRIPTION     
            "Definition of a Local Policy Routing Label."
    INDEX           { sonusDsLpTransLblIndex }
    ::= { sonusDsLpTransLblTable 1 }

SonusDsLpTransLblEntry ::=
    SEQUENCE {
        sonusDsLpTransLblIndex          Unsigned32,
        sonusDsLpTransLblName           SonusName,
        sonusDsLpTransLblType           INTEGER,
        sonusDsLpTransLblDnsZoneName    SonusName,
        sonusDsLpTransLblSignalingZoneName  SonusName,
        sonusDsLpTransLblEnumRoot       SonusName,
        sonusDsLpTransLblAdminState     SonusAdminState,
        sonusDsLpTransLblRowStatus      RowStatus
    }

sonusDsLpTransLblIndex OBJECT-TYPE
    SYNTAX          Unsigned32
    MAX-ACCESS      read-only
    STATUS          current
    DESCRIPTION     
            "A unique index for each Local Policy Routing Label."
    ::= { sonusDsLpTransLblEntry 1 }

sonusDsLpTransLblName OBJECT-TYPE
    SYNTAX          SonusName
    MAX-ACCESS      read-write
    STATUS          current
    DESCRIPTION     
            "The name of this Local Policy Routing Label."
    ::= { sonusDsLpTransLblEntry 2 }

sonusDsLpTransLblType OBJECT-TYPE
    SYNTAX          INTEGER { none(1), enumaor(2), enumlnp(3) }
    MAX-ACCESS      read-write
    STATUS          current
    DESCRIPTION     
            "The label type for this entry. "
    DEFVAL          { none }
    ::= { sonusDsLpTransLblEntry 3 }

sonusDsLpTransLblDnsZoneName OBJECT-TYPE
    SYNTAX          SonusName
    MAX-ACCESS      read-write
    STATUS          current
    DESCRIPTION     
            "The DNS Zone Name ."
    ::= { sonusDsLpTransLblEntry 4 }

sonusDsLpTransLblSignalingZoneName OBJECT-TYPE
    SYNTAX          SonusName
    MAX-ACCESS      read-write
    STATUS          current
    DESCRIPTION     
            "The Signaling Zone Name."
    ::= { sonusDsLpTransLblEntry 5 }

sonusDsLpTransLblEnumRoot OBJECT-TYPE
    SYNTAX          SonusName
    MAX-ACCESS      read-write
    STATUS          current
    DESCRIPTION     
            "The ENUM root string."
    ::= { sonusDsLpTransLblEntry 6 }

sonusDsLpTransLblAdminState OBJECT-TYPE
    SYNTAX          SonusAdminState
    MAX-ACCESS      read-write
    STATUS          current
    DESCRIPTION     
            "The admin state of the secondary route. The route is skipped
             if not ENABLED."
    DEFVAL          { disabled }
    ::= { sonusDsLpTransLblEntry 7 }

sonusDsLpTransLblRowStatus OBJECT-TYPE
    SYNTAX          RowStatus
    MAX-ACCESS      read-write
    STATUS          current
    DESCRIPTION     
            "This is for SNMP use."
    ::= { sonusDsLpTransLblEntry 8 }

sonusDsLpDomainSelTblObjects OBJECT IDENTIFIER
    ::= { sonusLocalPolicyServicesMIBObjects 11 }

sonusDsLpDomainSelTbl OBJECT-TYPE
    SYNTAX          SEQUENCE OF SonusDsLpDoaminSelTblEntry
    MAX-ACCESS      not-accessible
    STATUS          current
    DESCRIPTION     
            "Each entry of this table defines a mapping for a domain
             name to a trunk group based on signalling zone."
    ::= { sonusDsLpDomainSelTblObjects 1 }

sonusDsLpDoaminSelTblEntry OBJECT-TYPE
    SYNTAX          SonusDsLpDoaminSelTblEntry
    MAX-ACCESS      not-accessible
    STATUS          current
    DESCRIPTION     
            "Definition of a domain selection table entry."
    INDEX           { sonusDsLpDomainSelTblIndex }
    ::= { sonusDsLpDomainSelTbl 1 }

SonusDsLpDoaminSelTblEntry ::=
    SEQUENCE {
        sonusDsLpDomainSelTblIndex      Unsigned32,
        sonusDsLpDomainName             DisplayString,
        sonusDsLpSigZoneId              Unsigned32,
        sonusDsLpTgName                 DisplayString
    }

sonusDsLpDomainSelTblIndex OBJECT-TYPE
    SYNTAX          Unsigned32
    MAX-ACCESS      read-only
    STATUS          current
    DESCRIPTION     
            "A unique index for each entry."
    ::= { sonusDsLpDoaminSelTblEntry 1 }

sonusDsLpDomainName OBJECT-TYPE
    SYNTAX          DisplayString (SIZE(1..120))
    MAX-ACCESS      read-only
    STATUS          current
    DESCRIPTION     
            "The Domain name."
    ::= { sonusDsLpDoaminSelTblEntry 2 }

sonusDsLpSigZoneId OBJECT-TYPE
    SYNTAX          Unsigned32
    MAX-ACCESS      read-only
    STATUS          current
    DESCRIPTION     
            "The signalling zone id associated with that domain name. "
    ::= { sonusDsLpDoaminSelTblEntry 3 }

sonusDsLpTgName OBJECT-TYPE
    SYNTAX          DisplayString (SIZE(1..120))
    MAX-ACCESS      read-only
    STATUS          current
    DESCRIPTION     
            "The Trunk Group index to be selected for the domain name. "
    ::= { sonusDsLpDoaminSelTblEntry 4 }

END -- end of module SONUS-LOCAL-POLICY-SERVICES-MIB.
