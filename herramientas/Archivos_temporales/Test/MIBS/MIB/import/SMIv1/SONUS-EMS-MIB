--
-- This SMIv1 module has been generated by smidump 0.2-cvs. Do not edit.
--

SONUS-EMS-MIB DEFINITIONS ::= BEGIN

IMPORTS
    InetAddress, InetAddressType
        FROM INET-ADDRESS-MIB
    OBJECT-TYPE
        FROM RFC-1212
    TRAP-TYPE
        FROM RFC-1215
    IpAddress
        FROM RFC1155-SMI
    sysName, sysObjectID
        FROM SNMPv2-MIB
    DisplayString
        FROM SNMPv2-TC
    sonusEventClass, sonusEventDescription, sonusEventLevel, 
    sonusEventTime, sonusSequenceId
        FROM SONUS-COMMON-MIB
    sonusHostID
        FROM SONUS-HOST-MIB
    sonusSystemMIBs
        FROM SONUS-SMI;

sonusEmsMIB OBJECT IDENTIFIER
    ::= { sonusSystemMIBs 7 }

-- sonusEmsMIB MODULE-IDENTITY
--     LAST-UPDATED    "201604220000Z"
--     ORGANIZATION    
--             "Sonus Networks, Inc."
--     CONTACT-INFO    
--             "   Customer Support    
--              Sonus Networks, Inc.
--              250 Apollo Drive
--              Chelmsford, MA 01824
--              USA
--              
--              Tel: 978-614-8100
--              Fax: 978-614-8609"
--     DESCRIPTION     
--             "The MIB Module for EMS related objects."
--     ::= { sonusSystemMIBs 7 }


sonusEmsMIBObjects OBJECT IDENTIFIER
    ::= { sonusEmsMIB 1 }

sonusEmsNotifications OBJECT IDENTIFIER
    ::= { sonusEmsMIB 2 }

sonusEmsNotificationsNewPrefix OBJECT IDENTIFIER
    ::= { sonusEmsNotifications 0 }

sonusEmsNotificationsPrefix OBJECT IDENTIFIER
    ::= { sonusEmsNotifications 1 }

sonusEmsNotificationsObjects OBJECT IDENTIFIER
    ::= { sonusEmsNotifications 2 }

sonusEmsThresholdObjects OBJECT IDENTIFIER
    ::= { sonusEmsNotificationsObjects 1 }

sonusEmsThresholdObjectId OBJECT-TYPE
    SYNTAX          OBJECT IDENTIFIER
    ACCESS          read-only
    STATUS          mandatory
    DESCRIPTION     
            "The OID of the performance measure that was crossed."
    ::= { sonusEmsThresholdObjects 1 }

sonusEmsThresholdTriggerValue OBJECT-TYPE
    SYNTAX          INTEGER
    ACCESS          read-only
    STATUS          mandatory
    DESCRIPTION     
            "The threshold value that was crossed (the rising or
             falling value set for the threshold)."
    ::= { sonusEmsThresholdObjects 2 }

sonusEmsThresholdSampleValue OBJECT-TYPE
    SYNTAX          INTEGER
    ACCESS          read-only
    STATUS          mandatory
    DESCRIPTION     
            "The actual value measured that denotes that the
             threshold was crossed (should be greater than or
             equal to the rising trigger value or less than
             or equal to the falling trigger value)."
    ::= { sonusEmsThresholdObjects 3 }

sonusEmsThresholdIpAddress OBJECT-TYPE
    SYNTAX          IpAddress
    ACCESS          read-only
    STATUS          deprecated
    DESCRIPTION     
            "The IP address of the device on which the threshold was
             crossed."
    ::= { sonusEmsThresholdObjects 4 }

sonusEmsThresholdLocationIndexes OBJECT-TYPE
    SYNTAX          DisplayString
    ACCESS          read-only
    STATUS          mandatory
    DESCRIPTION     
            "The indexes of the location within the device at which
             the threshold was crossed; may be shelf, slot number,
              interface number, trunk group number, etc, depending on
              where the threshold event occurred."
    ::= { sonusEmsThresholdObjects 5 }

sonusEmsThresholdIdentifier OBJECT-TYPE
    SYNTAX          DisplayString
    ACCESS          read-only
    STATUS          mandatory
    DESCRIPTION     
            "A key that uniquely indentifies this threshold for
             managing duplicate alarms and clearing (matching
             the falling notification with the rising)."
    ::= { sonusEmsThresholdObjects 6 }

sonusEmsV2ThresholdIpAddressType OBJECT-TYPE
    SYNTAX          InetAddressType
    ACCESS          read-only
    STATUS          mandatory
    DESCRIPTION     
            "The address type of sonusEmsV2ThresholdIpAddress."
    ::= { sonusEmsThresholdObjects 7 }

sonusEmsV2ThresholdIpAddress OBJECT-TYPE
    SYNTAX          InetAddress
    ACCESS          read-only
    STATUS          mandatory
    DESCRIPTION     
            "The IP address of the device on which the threshold was
             crossed. The type of this address is determined by the 
             value of sonusEmsV2ThresholdIpAddressType."
    ::= { sonusEmsThresholdObjects 8 }

sonusEmsReachabilityObjects OBJECT IDENTIFIER
    ::= { sonusEmsNotificationsObjects 2 }

sonusEmsNodeIpAddress OBJECT-TYPE
    SYNTAX          IpAddress
    ACCESS          read-only
    STATUS          deprecated
    DESCRIPTION     
            "The IP address of the node that was polled."
    ::= { sonusEmsReachabilityObjects 1 }

sonusEmsNodeId OBJECT-TYPE
    SYNTAX          DisplayString
    ACCESS          read-only
    STATUS          mandatory
    DESCRIPTION     
            "The internal ID of the node that was polled."
    ::= { sonusEmsReachabilityObjects 2 }

sonusEmsV2NodeIpAddressType OBJECT-TYPE
    SYNTAX          InetAddressType
    ACCESS          read-only
    STATUS          mandatory
    DESCRIPTION     
            "The address type of sonusEmsV2NodeIpAddress."
    ::= { sonusEmsReachabilityObjects 3 }

sonusEmsV2NodeIpAddress OBJECT-TYPE
    SYNTAX          InetAddress
    ACCESS          read-only
    STATUS          mandatory
    DESCRIPTION     
            "The IP address of the node that was polled. The type
             of this address is determined by the value of
              sonusEmsV2NodeIpAddressType."
    ::= { sonusEmsReachabilityObjects 4 }

sonusEmsProfileName OBJECT-TYPE
    SYNTAX          DisplayString
    ACCESS          read-only
    STATUS          mandatory
    DESCRIPTION     
            "Profile Name for Performance Collection"
    ::= { sonusEmsReachabilityObjects 5 }

sonusEmsForwardingObjects OBJECT IDENTIFIER
    ::= { sonusEmsNotificationsObjects 4 }

sonusEmsTrapOriginator OBJECT-TYPE
    SYNTAX          IpAddress
    ACCESS          read-only
    STATUS          deprecated
    DESCRIPTION     
            "The IP address of the node that originated the trap."
    ::= { sonusEmsForwardingObjects 1 }

sonusEmsTrapForwardCounter64 OBJECT-TYPE
    SYNTAX          OCTET STRING (SIZE(1..128))
    ACCESS          read-only
    STATUS          mandatory
    DESCRIPTION     
            "Internal use only. Specifies a 64 bit counter oid and value in the format oid:value ."
    ::= { sonusEmsForwardingObjects 2 }

sonusEmsV2TrapOriginatorType OBJECT-TYPE
    SYNTAX          InetAddressType
    ACCESS          read-only
    STATUS          mandatory
    DESCRIPTION     
            "The address type of sonusEmsV2TrapOriginator."
    ::= { sonusEmsForwardingObjects 3 }

sonusEmsV2TrapOriginator OBJECT-TYPE
    SYNTAX          InetAddress
    ACCESS          read-only
    STATUS          mandatory
    DESCRIPTION     
            "The IP address of the node that originated the trap.
             The type of this address is determined by the value of
              sonusEmsV2TrapOriginatorType."
    ::= { sonusEmsForwardingObjects 4 }

sonusDeviceHostName OBJECT-TYPE
    SYNTAX          DisplayString
    ACCESS          read-only
    STATUS          mandatory
    DESCRIPTION     
            "Hostname/device Id of the device."
    ::= { sonusEmsForwardingObjects 5 }

sonusEmsFmObjects OBJECT IDENTIFIER
    ::= { sonusEmsNotificationsObjects 5 }

sonusEmsFmSequenceId OBJECT-TYPE
    SYNTAX          Gauge
    ACCESS          read-only
    STATUS          mandatory
    DESCRIPTION     
            "The sequence number expected as the next in the series."
    ::= { sonusEmsFmObjects 1 }

sonusEmsFmSequenceEndGapId OBJECT-TYPE
    SYNTAX          Gauge
    ACCESS          read-only
    STATUS          mandatory
    DESCRIPTION     
            "The last sequence number in a sequence gap."
    ::= { sonusEmsFmObjects 2 }

sonusEmsFmSequenceResetId OBJECT-TYPE
    SYNTAX          Gauge
    ACCESS          read-only
    STATUS          mandatory
    DESCRIPTION     
            "The value to which the expected sequence number was reset."
    ::= { sonusEmsFmObjects 3 }

sonusEmsFmTrapFwdProfileName OBJECT-TYPE
    SYNTAX          DisplayString
    ACCESS          read-only
    STATUS          mandatory
    DESCRIPTION     
            "Name of the FM Trap Forwarder Profile for which queue overflowed."
    ::= { sonusEmsFmObjects 4 }

sonusEmsFmTrapReSyncDelimiter OBJECT-TYPE
    SYNTAX          INTEGER { start(1), stop(2) }
    ACCESS          read-only
    STATUS          mandatory
    DESCRIPTION     
            "Represents delimiter used while OSS trap re-sync."
    ::= { sonusEmsFmObjects 5 }

sonusEmsFmEnableOSSTrapReSync OBJECT-TYPE
    SYNTAX          INTEGER { enable(1) }
    ACCESS          read-write
    STATUS          mandatory
    DESCRIPTION     
            "Enables Trap re-sync for OSS."
    ::= { sonusEmsFmObjects 6 }

sonusEmsPMObjects OBJECT IDENTIFIER
    ::= { sonusEmsNotificationsObjects 6 }

sonusEmsPMStatsNames OBJECT-TYPE
    SYNTAX          DisplayString
    ACCESS          read-only
    STATUS          mandatory
    DESCRIPTION     
            "Comma-separated names of relevant PM stats (e.g. SystemStats,CallCountStats)"
    ::= { sonusEmsPMObjects 1 }

sonusEmsPMExportCsvFile OBJECT-TYPE
    SYNTAX          DisplayString
    ACCESS          read-only
    STATUS          mandatory
    DESCRIPTION     
            "Directory name and file name of the PM export CSV file which did not have any data."
    ::= { sonusEmsPMObjects 2 }

sonusRemoteServer OBJECT-TYPE
    SYNTAX          DisplayString
    ACCESS          read-only
    STATUS          mandatory
    DESCRIPTION     
            "Remote server where SFTP of stats needs to be performed."
    ::= { sonusEmsPMObjects 3 }

sonusEmsFileRepObjects OBJECT IDENTIFIER
    ::= { sonusEmsNotificationsObjects 7 }

sonusFileRepNotifyPID OBJECT-TYPE
    SYNTAX          INTEGER
    ACCESS          read-only
    STATUS          mandatory
    DESCRIPTION     
            "The process id of the process to be notified."
    ::= { sonusEmsFileRepObjects 1 }

sonusFileRepFilename OBJECT-TYPE
    SYNTAX          DisplayString
    ACCESS          read-only
    STATUS          mandatory
    DESCRIPTION     
            "The name of the file which failed replication."
    ::= { sonusEmsFileRepObjects 2 }

sonusEmsLoginObjects OBJECT IDENTIFIER
    ::= { sonusEmsNotificationsObjects 8 }

sonusEmsLoginIPAddress OBJECT-TYPE
    SYNTAX          IpAddress
    ACCESS          read-only
    STATUS          deprecated
    DESCRIPTION     
            "The IP address of the node from which a login attempt was made."
    ::= { sonusEmsLoginObjects 1 }

sonusEmsLoginUserName OBJECT-TYPE
    SYNTAX          OCTET STRING (SIZE(1..20))
    ACCESS          read-only
    STATUS          mandatory
    DESCRIPTION     
            "The user name provided during a login attempt."
    ::= { sonusEmsLoginObjects 2 }

sonusEmsV2LoginIPAddressType OBJECT-TYPE
    SYNTAX          InetAddressType
    ACCESS          read-only
    STATUS          mandatory
    DESCRIPTION     
            "The address type of sonusEmsV2LoginIPAddress."
    ::= { sonusEmsLoginObjects 3 }

sonusEmsV2LoginIPAddress OBJECT-TYPE
    SYNTAX          InetAddress
    ACCESS          read-only
    STATUS          mandatory
    DESCRIPTION     
            "The IP address of the node from which a login attempt was 
             made. The type of this address is determined by the value of
              sonusEmsV2LoginIPAddressType."
    ::= { sonusEmsLoginObjects 4 }

sonusEmsASXColdStandByAutomationObjects OBJECT IDENTIFIER
    ::= { sonusEmsNotificationsObjects 9 }

sonusEmsASXColdStandByAutomationASXRedundancyMode OBJECT-TYPE
    SYNTAX          INTEGER { primary(1), backup(2) }
    ACCESS          read-only
    STATUS          mandatory
    DESCRIPTION     
            "ASX redundancy mode."
    ::= { sonusEmsASXColdStandByAutomationObjects 1 }

sonusEmsASXColdStandByAutomationConfigGRStateFailedInfo OBJECT-TYPE
    SYNTAX          DisplayString (SIZE(0..128))
    ACCESS          read-only
    STATUS          mandatory
    DESCRIPTION     
            "Configuring GR operational status fail reason."
    ::= { sonusEmsASXColdStandByAutomationObjects 2 }

sonusEmsNPServicesObjects OBJECT IDENTIFIER
    ::= { sonusEmsNotificationsObjects 10 }

sonusEmsNPServicesMCHName OBJECT-TYPE
    SYNTAX          DisplayString (SIZE(0..128))
    ACCESS          read-only
    STATUS          mandatory
    DESCRIPTION     
            "Name of the clearing house hosting Number Portability data."
    ::= { sonusEmsNPServicesObjects 1 }

sonusEmsNPServicesBulkRequestTransactionId OBJECT-TYPE
    SYNTAX          DisplayString (SIZE(0..256))
    ACCESS          read-only
    STATUS          mandatory
    DESCRIPTION     
            "Transaction Id of bulk data file request."
    ::= { sonusEmsNPServicesObjects 2 }

sonusEmsSBCMgmtNotificationObjects OBJECT IDENTIFIER
    ::= { sonusEmsNotificationsObjects 11 }

scheduleId OBJECT-TYPE
    SYNTAX          DisplayString
    ACCESS          read-only
    STATUS          mandatory
    DESCRIPTION     
            "The name of the file which failed replication."
    ::= { sonusEmsSBCMgmtNotificationObjects 1 }

scheduleName OBJECT-TYPE
    SYNTAX          DisplayString
    ACCESS          read-only
    STATUS          mandatory
    DESCRIPTION     
            "The name of the file which failed replication."
    ::= { sonusEmsSBCMgmtNotificationObjects 2 }

failedNodes OBJECT-TYPE
    SYNTAX          DisplayString
    ACCESS          read-only
    STATUS          mandatory
    DESCRIPTION     
            "The name of the file which failed replication."
    ::= { sonusEmsSBCMgmtNotificationObjects 3 }

sonusEmsClusterMgmtNotificationObjects OBJECT IDENTIFIER
    ::= { sonusEmsNotificationsObjects 12 }

nodename OBJECT-TYPE
    SYNTAX          DisplayString
    ACCESS          read-only
    STATUS          mandatory
    DESCRIPTION     
            "The name of the Node."
    ::= { sonusEmsClusterMgmtNotificationObjects 1 }

nodeip OBJECT-TYPE
    SYNTAX          DisplayString
    ACCESS          read-only
    STATUS          mandatory
    DESCRIPTION     
            "It represents Node IP value."
    ::= { sonusEmsClusterMgmtNotificationObjects 2 }

clustername OBJECT-TYPE
    SYNTAX          DisplayString
    ACCESS          read-only
    STATUS          mandatory
    DESCRIPTION     
            "The name of the cluster."
    ::= { sonusEmsClusterMgmtNotificationObjects 3 }

reason OBJECT-TYPE
    SYNTAX          DisplayString
    ACCESS          read-only
    STATUS          mandatory
    DESCRIPTION     
            "Describes notification reason "
    ::= { sonusEmsClusterMgmtNotificationObjects 4 }

clusterid OBJECT-TYPE
    SYNTAX          DisplayString
    ACCESS          read-only
    STATUS          mandatory
    DESCRIPTION     
            "The id of the cluster"
    ::= { sonusEmsClusterMgmtNotificationObjects 5 }

sonusEmsLINotificationObjects OBJECT IDENTIFIER
    ::= { sonusEmsNotificationsObjects 13 }

mediationServerIP OBJECT-TYPE
    SYNTAX          DisplayString
    ACCESS          read-only
    STATUS          mandatory
    DESCRIPTION     
            "IP Address of the mediation server"
    ::= { sonusEmsLINotificationObjects 1 }

sonusEmsVnfrMgmtNotificationObjects OBJECT IDENTIFIER
    ::= { sonusEmsNotificationsObjects 14 }

vnfmIp OBJECT-TYPE
    SYNTAX          DisplayString
    ACCESS          read-only
    STATUS          mandatory
    DESCRIPTION     
            "It represents VNFM IP value."
    ::= { sonusEmsVnfrMgmtNotificationObjects 1 }

restResponseCode OBJECT-TYPE
    SYNTAX          DisplayString
    ACCESS          read-only
    STATUS          mandatory
    DESCRIPTION     
            "It represents response code return from VNFM when tried to register."
    ::= { sonusEmsVnfrMgmtNotificationObjects 2 }

lastHeartbeatTime OBJECT-TYPE
    SYNTAX          DisplayString
    ACCESS          read-only
    STATUS          mandatory
    DESCRIPTION     
            "It represents last Heartbeat received from VNFM"
    ::= { sonusEmsVnfrMgmtNotificationObjects 3 }

sonusEmsFileRepNotifyFailNotification TRAP-TYPE
    ENTERPRISE      sonusEmsNotifications
    VARIABLES       { sonusEventTime, sonusEventDescription, 
                      sonusEventClass, sonusEventLevel, sonusHostID, 
                      sonusFileRepNotifyPID }
--     STATUS          mandatory
    DESCRIPTION     
            "The EMS file replication service has failed to notify the fault manager process. The process id to which notification was attempted is specified by sonusFileRepNotifyPID."
    ::= 31

sonusEmsFileRepSourceCopyFailNotification TRAP-TYPE
    ENTERPRISE      sonusEmsNotifications
    VARIABLES       { sonusEventTime, sonusEventDescription, 
                      sonusEventClass, sonusEventLevel, sonusHostID, 
                      sonusFileRepFilename }
--     STATUS          mandatory
    DESCRIPTION     
            "The EMS file replication service has failed to copy the file specified by sonusFileRepFileName from the source to the target."
    ::= 32

sonusEmsFileRepTargetCopyFailNotification TRAP-TYPE
    ENTERPRISE      sonusEmsNotifications
    VARIABLES       { sonusEventTime, sonusEventDescription, 
                      sonusEventClass, sonusEventLevel, sonusHostID, 
                      sonusFileRepFilename }
--     STATUS          mandatory
    DESCRIPTION     
            "The EMS file replication service has failed to copy a replicated file specified by sonusRepFileName from a temporary directory to a permanent directory."
    ::= 33

sonusEmsLoginFailureNotification TRAP-TYPE
    ENTERPRISE      sonusEmsNotifications
    VARIABLES       { sonusEventTime, sonusEventDescription, 
                      sonusEventClass, sonusEventLevel, 
                      sonusEmsLoginIPAddress, sonusEmsLoginUserName }
--     STATUS          deprecated
    DESCRIPTION     
            "Specifies that a login attempt failed for the user specified by sonusEmsLoginUserName from host specified by sonusEmsLoginIPAddress."
    ::= 34

sonusEmsFMTrapFwdProfileReadErrorNotification TRAP-TYPE
    ENTERPRISE      sonusEmsNotifications
    VARIABLES       { sysName, sysObjectID, sonusEventTime, 
                      sonusEventDescription, sonusEventClass, 
                      sonusEventLevel }
--     STATUS          mandatory
    DESCRIPTION     
            "There was an error reading FM Trap Forwarder profiles. Possible causes include problem connecting to database, incorrect database password etc."
    ::= 35

sonusEmsFMTrapFwdWOQueueOverflowNotification TRAP-TYPE
    ENTERPRISE      sonusEmsNotifications
    VARIABLES       { sysName, sysObjectID, sonusEventTime, 
                      sonusEventDescription, sonusEventClass, 
                      sonusEventLevel, sonusEmsFmTrapFwdProfileName }
--     STATUS          mandatory
    DESCRIPTION     
            "FM Trap Forwarder incoming work order trap queue has overflown for the specified profile, based on the configured tolerance."
    ::= 36

sonusEmsFMTrapFwdBrassAgtQueueOverflowNotification TRAP-TYPE
    ENTERPRISE      sonusEmsNotifications
    VARIABLES       { sysName, sysObjectID, sonusEventTime, 
                      sonusEventDescription, sonusEventClass, 
                      sonusEventLevel }
--     STATUS          mandatory
    DESCRIPTION     
            "Brass Agent queue overflow warnings in emsSNMP.log."
    ::= 37

sonusEmsFMTrapFwdLogOutOfMemoryNotification TRAP-TYPE
    ENTERPRISE      sonusEmsNotifications
    VARIABLES       { sysName, sysObjectID, sonusEventTime, 
                      sonusEventDescription, sonusEventClass, 
                      sonusEventLevel }
--     STATUS          mandatory
    DESCRIPTION     
            "Java out of memory warnings in emsFM.log."
    ::= 38

sonusEmsPrimRadiusAuthServerUnreachableNotification TRAP-TYPE
    ENTERPRISE      sonusEmsNotifications
    VARIABLES       { sysName, sysObjectID, sonusEventTime, 
                      sonusEventDescription, sonusEventClass, 
                      sonusEventLevel }
--     STATUS          mandatory
    DESCRIPTION     
            "Specifies that the primary radius authentication server was unreachable when attempting to authenticate using the user specified by sonusEmsLoginUserName from the host specified by sonusEmsLoginIPAddress."
    ::= 41

sonusEmsPrimRadiusAuthServerReachableNotification TRAP-TYPE
    ENTERPRISE      sonusEmsNotifications
    VARIABLES       { sysName, sysObjectID, sonusEventTime, 
                      sonusEventDescription, sonusEventClass, 
                      sonusEventLevel }
--     STATUS          mandatory
    DESCRIPTION     
            "Specifies that the primary radius authentication server was reachable when attempting to authenticate using the user specified by sonusEmsLoginUserName from the host specified by sonusEmsLoginIPAddress."
    ::= 42

sonusEmsPrimAndSecRadiusAuthServerUnreachableNotification TRAP-TYPE
    ENTERPRISE      sonusEmsNotifications
    VARIABLES       { sysName, sysObjectID, sonusEventTime, 
                      sonusEventDescription, sonusEventClass, 
                      sonusEventLevel }
--     STATUS          mandatory
    DESCRIPTION     
            "Specifies that the primary and secondary radius authentication servers were unreachable when attempting to authenticate using the user specified by sonusEmsLoginUserName from the host specified by sonusEmsLoginIPAddress."
    ::= 43

sonusEmsPrimAndSecRadiusAuthServerReachableNotification TRAP-TYPE
    ENTERPRISE      sonusEmsNotifications
    VARIABLES       { sysName, sysObjectID, sonusEventTime, 
                      sonusEventDescription, sonusEventClass, 
                      sonusEventLevel }
--     STATUS          mandatory
    DESCRIPTION     
            "Specifies that the primary and secondary radius authentication servers were reachable when attempting to authenticate using the user specified by sonusEmsLoginUserName from the host specified by sonusEmsLoginIPAddress."
    ::= 44

sonusEmsPrimRadiusAccServerUnreachableNotification TRAP-TYPE
    ENTERPRISE      sonusEmsNotifications
    VARIABLES       { sysName, sysObjectID, sonusEventTime, 
                      sonusEventDescription, sonusEventClass, 
                      sonusEventLevel }
--     STATUS          mandatory
    DESCRIPTION     
            "Specifies that the primary radius accounting server was unreachable when attempting to authenticate using the user specified by sonusEmsLoginUserName from the host specified by sonusEmsLoginIPAddress."
    ::= 45

sonusEmsPrimRadiusAccServerReachableNotification TRAP-TYPE
    ENTERPRISE      sonusEmsNotifications
    VARIABLES       { sysName, sysObjectID, sonusEventTime, 
                      sonusEventDescription, sonusEventClass, 
                      sonusEventLevel }
--     STATUS          mandatory
    DESCRIPTION     
            "Specifies that the primary radius accounting server was reachable when attempting to authenticate using the user specified by sonusEmsLoginUserName from the host specified by sonusEmsLoginIPAddress."
    ::= 46

sonusEmsPrimAndSecRadiusAccServerUnreachableNotification TRAP-TYPE
    ENTERPRISE      sonusEmsNotifications
    VARIABLES       { sysName, sysObjectID, sonusEventTime, 
                      sonusEventDescription, sonusEventClass, 
                      sonusEventLevel }
--     STATUS          mandatory
    DESCRIPTION     
            "Specifies that the primary and secondary radius accounting servers were unreachable when attempting to authenticate using the user specified by sonusEmsLoginUserName from the host specified by sonusEmsLoginIPAddress."
    ::= 47

sonusEmsPrimAndSecRadiusAccServerReachableNotification TRAP-TYPE
    ENTERPRISE      sonusEmsNotifications
    VARIABLES       { sysName, sysObjectID, sonusEventTime, 
                      sonusEventDescription, sonusEventClass, 
                      sonusEventLevel }
--     STATUS          mandatory
    DESCRIPTION     
            "Specifies that the primary and secondary radius accounting servers were reachable when attempting to authenticate using the user specified by sonusEmsLoginUserName from the host specified by sonusEmsLoginIPAddress."
    ::= 48

sonusEmsASXGROperationalStateChangeFailureNotification TRAP-TYPE
    ENTERPRISE      sonusEmsNotifications
    VARIABLES       { sonusEventTime, sonusEventDescription, 
                      sonusEventClass, sonusEventLevel, sonusHostID, 
                      sonusEmsNodeId, 
                      sonusEmsASXColdStandByAutomationASXRedundancyMode, 
                      sonusEmsASXColdStandByAutomationConfigGRStateFailedInfo }
--     STATUS          mandatory
    DESCRIPTION     
            "EMS fails to set GR operational state against a Home ASX."
    ::= 49

sonusEmsASXGROperationalStateChangeSuccessNotification TRAP-TYPE
    ENTERPRISE      sonusEmsNotifications
    VARIABLES       { sonusEventTime, sonusEventDescription, 
                      sonusEventClass, sonusEventLevel, sonusHostID, 
                      sonusEmsNodeId, 
                      sonusEmsASXColdStandByAutomationASXRedundancyMode }
--     STATUS          mandatory
    DESCRIPTION     
            "EMS succeeds to set GR operational status against a Home ASX."
    ::= 50

sonusEmsV2RisingEventNotification TRAP-TYPE
    ENTERPRISE      sonusEmsNotifications
    VARIABLES       { sysName, sysObjectID, sonusEventTime, 
                      sonusEventDescription, sonusEventClass, 
                      sonusEventLevel, sonusEmsV2ThresholdIpAddressType, 
                      sonusEmsV2ThresholdIpAddress, 
                      sonusEmsThresholdObjectId, 
                      sonusEmsThresholdTriggerValue, 
                      sonusEmsThresholdSampleValue, 
                      sonusEmsThresholdLocationIndexes, 
                      sonusEmsThresholdIdentifier }
--     STATUS          mandatory
    DESCRIPTION     
            "A rising event notification informs that a given
             performance measure has crossed a given threshold
             - it has risen above a defined rising threshold
             value."
    ::= 51

sonusEmsV2FallingEventNotification TRAP-TYPE
    ENTERPRISE      sonusEmsNotifications
    VARIABLES       { sysName, sysObjectID, sonusEventTime, 
                      sonusEventDescription, sonusEventClass, 
                      sonusEventLevel, sonusEmsV2ThresholdIpAddressType, 
                      sonusEmsV2ThresholdIpAddress, 
                      sonusEmsThresholdObjectId, 
                      sonusEmsThresholdTriggerValue, 
                      sonusEmsThresholdSampleValue, 
                      sonusEmsThresholdLocationIndexes, 
                      sonusEmsThresholdIdentifier }
--     STATUS          mandatory
    DESCRIPTION     
            "A falling event notification informs that a given
             performance measure for which a previous rising event
             notification was generated has returned below a defined
             falling value for that threshold and should be cleared."
    ::= 52

sonusEmsV2NodeUnreachableNotification TRAP-TYPE
    ENTERPRISE      sonusEmsNotifications
    VARIABLES       { sysName, sysObjectID, sonusEventTime, 
                      sonusEventDescription, sonusEventClass, 
                      sonusEventLevel, sonusEmsV2NodeIpAddressType, 
                      sonusEmsV2NodeIpAddress, sonusEmsNodeId }
--     STATUS          mandatory
    DESCRIPTION     
            "The specified node is not reachable by the EMS."
    ::= 53

sonusEmsV2NodeReachableNotification TRAP-TYPE
    ENTERPRISE      sonusEmsNotifications
    VARIABLES       { sysName, sysObjectID, sonusEventTime, 
                      sonusEventDescription, sonusEventClass, 
                      sonusEventLevel, sonusEmsV2NodeIpAddressType, 
                      sonusEmsV2NodeIpAddress, sonusEmsNodeId }
--     STATUS          mandatory
    DESCRIPTION     
            "The specified node is now reachable by the EMS."
    ::= 54

sonusEmsV2NodeRestartedNotification TRAP-TYPE
    ENTERPRISE      sonusEmsNotifications
    VARIABLES       { sysName, sysObjectID, sonusEventTime, 
                      sonusEventDescription, sonusEventClass, 
                      sonusEventLevel, sonusEmsV2NodeIpAddressType, 
                      sonusEmsV2NodeIpAddress, sonusEmsNodeId }
--     STATUS          mandatory
    DESCRIPTION     
            "The specified node has been restarted since last polled by the EMS."
    ::= 55

sonusEmsV2NodeCfgFailNotification TRAP-TYPE
    ENTERPRISE      sonusEmsNotifications
    VARIABLES       { sysName, sysObjectID, sonusEventTime, 
                      sonusEventDescription, sonusEventClass, 
                      sonusEventLevel, sonusEmsV2NodeIpAddressType, 
                      sonusEmsV2NodeIpAddress, sonusEmsNodeId }
--     STATUS          mandatory
    DESCRIPTION     
            "EMS failed to configure the specified node."
    ::= 56

sonusEmsV2NodeCfgDoneNotification TRAP-TYPE
    ENTERPRISE      sonusEmsNotifications
    VARIABLES       { sysName, sysObjectID, sonusEventTime, 
                      sonusEventDescription, sonusEventClass, 
                      sonusEventLevel, sonusEmsV2NodeIpAddressType, 
                      sonusEmsV2NodeIpAddress, sonusEmsNodeId }
--     STATUS          mandatory
    DESCRIPTION     
            "Successfully configured the specified node."
    ::= 57

sonusEmsV2FmSequenceGapNotification TRAP-TYPE
    ENTERPRISE      sonusEmsNotifications
    VARIABLES       { sysName, sysObjectID, sonusEventTime, 
                      sonusEventDescription, sonusEventClass, 
                      sonusEventLevel, sonusEmsV2NodeIpAddressType, 
                      sonusEmsV2NodeIpAddress, sonusEmsNodeId, 
                      sonusEmsFmSequenceId, sonusEmsFmSequenceEndGapId }
--     STATUS          mandatory
    DESCRIPTION     
            "The fm manager has observed a sequence gap in INFORM traps from the device."
    ::= 58

sonusEmsV2FmSequenceResetNotification TRAP-TYPE
    ENTERPRISE      sonusEmsNotifications
    VARIABLES       { sysName, sysObjectID, sonusEventTime, 
                      sonusEventDescription, sonusEventClass, 
                      sonusEventLevel, sonusEmsV2NodeIpAddressType, 
                      sonusEmsV2NodeIpAddress, sonusEmsNodeId, 
                      sonusEmsFmSequenceId, sonusEmsFmSequenceResetId }
--     STATUS          mandatory
    DESCRIPTION     
            "The fm manager has observed a situation which caused it to rest the expected sequence number.  This can be due to a agent reset or reboot."
    ::= 59

sonusEmsV2FmSequenceQOverflowNotification TRAP-TYPE
    ENTERPRISE      sonusEmsNotifications
    VARIABLES       { sysName, sysObjectID, sonusEventTime, 
                      sonusEventDescription, sonusEventClass, 
                      sonusEventLevel, sonusEmsV2NodeIpAddressType, 
                      sonusEmsV2NodeIpAddress, sonusEmsNodeId, 
                      sonusEmsFmSequenceId }
--     STATUS          mandatory
    DESCRIPTION     
            "The queue used by sequence handling code has overflowed. This may cause traps to be handled out of order."
    ::= 60

sonusEmsV2NodeCfgPartialNotification TRAP-TYPE
    ENTERPRISE      sonusEmsNotifications
    VARIABLES       { sysName, sysObjectID, sonusEventTime, 
                      sonusEventDescription, sonusEventClass, 
                      sonusEventLevel, sonusEmsV2NodeIpAddressType, 
                      sonusEmsV2NodeIpAddress, sonusEmsNodeId }
--     STATUS          mandatory
    DESCRIPTION     
            "Partially configured the specified node.  One of the hosts of a redundant configuration was not successfully configured."
    ::= 61

sonusEmsV2HostCfgSuccessNotification TRAP-TYPE
    ENTERPRISE      sonusEmsNotifications
    VARIABLES       { sysName, sysObjectID, sonusEventTime, 
                      sonusEventDescription, sonusEventClass, 
                      sonusEventLevel, sonusEmsV2NodeIpAddressType, 
                      sonusEmsV2NodeIpAddress, sonusEmsNodeId, 
                      sonusHostID }
--     STATUS          mandatory
    DESCRIPTION     
            "The host identified by sonusHostID was configured successfully."
    ::= 62

sonusEmsV2HostCfgFailureNotification TRAP-TYPE
    ENTERPRISE      sonusEmsNotifications
    VARIABLES       { sysName, sysObjectID, sonusEventTime, 
                      sonusEventDescription, sonusEventClass, 
                      sonusEventLevel, sonusEmsV2NodeIpAddressType, 
                      sonusEmsV2NodeIpAddress, sonusEmsNodeId, 
                      sonusHostID }
--     STATUS          mandatory
    DESCRIPTION     
            "The host identified by sonusHostID was not configured successfully."
    ::= 63

sonusV2VfyMgrNodeTypeFailNotification TRAP-TYPE
    ENTERPRISE      sonusEmsNotifications
    VARIABLES       { sysName, sysObjectID, sonusEventTime, 
                      sonusEventDescription, sonusEventClass, 
                      sonusEventLevel, sonusEmsV2NodeIpAddressType, 
                      sonusEmsV2NodeIpAddress, sonusEmsNodeId, 
                      sonusHostID }
--     STATUS          mandatory
    DESCRIPTION     
            "The agent on the host identified by sonusHostID does not contain the instrumentation component needed to manage the registered node."
    ::= 64

sonusV2VfyMgrNodeTypeSuccessNotification TRAP-TYPE
    ENTERPRISE      sonusEmsNotifications
    VARIABLES       { sysName, sysObjectID, sonusEventTime, 
                      sonusEventDescription, sonusEventClass, 
                      sonusEventLevel, sonusEmsV2NodeIpAddressType, 
                      sonusEmsV2NodeIpAddress, sonusEmsNodeId, 
                      sonusHostID }
--     STATUS          mandatory
    DESCRIPTION     
            "The agent on the host identified by sonusHostID contains the instrumentation component needed to manage the registered node."
    ::= 65

sonusV2VfyMgrApplVersionFailNotification TRAP-TYPE
    ENTERPRISE      sonusEmsNotifications
    VARIABLES       { sysName, sysObjectID, sonusEventTime, 
                      sonusEventDescription, sonusEventClass, 
                      sonusEventLevel, sonusEmsV2NodeIpAddressType, 
                      sonusEmsV2NodeIpAddress, sonusEmsNodeId, 
                      sonusHostID }
--     STATUS          mandatory
    DESCRIPTION     
            "The agent on the host identified by sonusHostID reports a different application version than that contained in the EMS node model. The application version is that of the instrumented device. For example PSX or SGX."
    ::= 66

sonusV2VfyMgrApplVersionSuccessNotification TRAP-TYPE
    ENTERPRISE      sonusEmsNotifications
    VARIABLES       { sysName, sysObjectID, sonusEventTime, 
                      sonusEventDescription, sonusEventClass, 
                      sonusEventLevel, sonusEmsV2NodeIpAddressType, 
                      sonusEmsV2NodeIpAddress, sonusEmsNodeId, 
                      sonusHostID }
--     STATUS          mandatory
    DESCRIPTION     
            "The agent on the host identified by sonusHostID reports the same application version as that contained in the EMS node model. The application version is that of the instrumented device. For example PSX or SGX."
    ::= 67

sonusV2VfyMgrMgmtClientFailNotification TRAP-TYPE
    ENTERPRISE      sonusEmsNotifications
    VARIABLES       { sysName, sysObjectID, sonusEventTime, 
                      sonusEventDescription, sonusEventClass, 
                      sonusEventLevel, sonusEmsV2NodeIpAddressType, 
                      sonusEmsV2NodeIpAddress, sonusEmsNodeId, 
                      sonusHostID }
--     STATUS          mandatory
    DESCRIPTION     
            "The agent on the host identified by sonusHostID does not contain a fault subscription entry for the EMS."
    ::= 68

sonusV2VfyMgrMgmtClientSuccessNotification TRAP-TYPE
    ENTERPRISE      sonusEmsNotifications
    VARIABLES       { sysName, sysObjectID, sonusEventTime, 
                      sonusEventDescription, sonusEventClass, 
                      sonusEventLevel, sonusEmsV2NodeIpAddressType, 
                      sonusEmsV2NodeIpAddress, sonusEmsNodeId, 
                      sonusHostID }
--     STATUS          mandatory
    DESCRIPTION     
            "The agent on the host identified by sonusHostID contains a fault subscription entry for the EMS."
    ::= 69

sonusV2VfyMgrSnmpAccessFailNotification TRAP-TYPE
    ENTERPRISE      sonusEmsNotifications
    VARIABLES       { sysName, sysObjectID, sonusEventTime, 
                      sonusEventDescription, sonusEventClass, 
                      sonusEventLevel, sonusEmsV2NodeIpAddressType, 
                      sonusEmsV2NodeIpAddress, sonusEmsNodeId, 
                      sonusHostID }
--     STATUS          mandatory
    DESCRIPTION     
            "The agent on the host identified by sonusHostID does not allow SNMP Read access priviledge for Insight."
    ::= 70

sonusV2VfyMgrSnmpAccessSuccessNotification TRAP-TYPE
    ENTERPRISE      sonusEmsNotifications
    VARIABLES       { sysName, sysObjectID, sonusEventTime, 
                      sonusEventDescription, sonusEventClass, 
                      sonusEventLevel, sonusEmsV2NodeIpAddressType, 
                      sonusEmsV2NodeIpAddress, sonusEmsNodeId, 
                      sonusHostID }
--     STATUS          mandatory
    DESCRIPTION     
            "The agent on the host identified by sonusHostID allows SNMP Read access priviledge for Insight."
    ::= 71

sonusV2VfyMgrAgentVersionFailNotification TRAP-TYPE
    ENTERPRISE      sonusEmsNotifications
    VARIABLES       { sysName, sysObjectID, sonusEventTime, 
                      sonusEventDescription, sonusEventClass, 
                      sonusEventLevel, sonusEmsV2NodeIpAddressType, 
                      sonusEmsV2NodeIpAddress, sonusEmsNodeId, 
                      sonusHostID }
--     STATUS          mandatory
    DESCRIPTION     
            "The agent on the host identified by sonusHostID reports a different version than that stored in the EMS."
    ::= 72

sonusV2VfyMgrAgentVersionSuccessNotification TRAP-TYPE
    ENTERPRISE      sonusEmsNotifications
    VARIABLES       { sysName, sysObjectID, sonusEventTime, 
                      sonusEventDescription, sonusEventClass, 
                      sonusEventLevel, sonusEmsV2NodeIpAddressType, 
                      sonusEmsV2NodeIpAddress, sonusEmsNodeId, 
                      sonusHostID }
--     STATUS          mandatory
    DESCRIPTION     
            "The agent on the host identified by sonusHostID reports the same version as that stored in the EMS."
    ::= 73

sonusEmsV2HostUnreachableNotification TRAP-TYPE
    ENTERPRISE      sonusEmsNotifications
    VARIABLES       { sysName, sysObjectID, sonusEventTime, 
                      sonusEventDescription, sonusEventClass, 
                      sonusEventLevel, sonusEmsV2NodeIpAddressType, 
                      sonusEmsV2NodeIpAddress, sonusEmsNodeId }
--     STATUS          mandatory
    DESCRIPTION     
            "The specified host is not reachable by the EMS."
    ::= 74

sonusEmsV2HostReachableNotification TRAP-TYPE
    ENTERPRISE      sonusEmsNotifications
    VARIABLES       { sysName, sysObjectID, sonusEventTime, 
                      sonusEventDescription, sonusEventClass, 
                      sonusEventLevel, sonusEmsV2NodeIpAddressType, 
                      sonusEmsV2NodeIpAddress, sonusEmsNodeId }
--     STATUS          mandatory
    DESCRIPTION     
            "The specified host is now reachable by the EMS."
    ::= 75

sonusEmsV2HostRestartedNotification TRAP-TYPE
    ENTERPRISE      sonusEmsNotifications
    VARIABLES       { sysName, sysObjectID, sonusEventTime, 
                      sonusEventDescription, sonusEventClass, 
                      sonusEventLevel, sonusEmsV2NodeIpAddressType, 
                      sonusEmsV2NodeIpAddress, sonusEmsNodeId }
--     STATUS          mandatory
    DESCRIPTION     
            "The specified host has been restarted since last polled by the EMS."
    ::= 76

sonusEmsV2PifCollectFailNotification TRAP-TYPE
    ENTERPRISE      sonusEmsNotifications
    VARIABLES       { sysName, sysObjectID, sonusEventTime, 
                      sonusEventDescription, sonusEventClass, 
                      sonusEventLevel, sonusEmsV2NodeIpAddressType, 
                      sonusEmsV2NodeIpAddress, sonusEmsNodeId }
--     STATUS          mandatory
    DESCRIPTION     
            "EMS failed to complete PIF collection for the specified node."
    ::= 77

sonusEmsV2PifCollectDoneNotification TRAP-TYPE
    ENTERPRISE      sonusEmsNotifications
    VARIABLES       { sysName, sysObjectID, sonusEventTime, 
                      sonusEventDescription, sonusEventClass, 
                      sonusEventLevel, sonusEmsV2NodeIpAddressType, 
                      sonusEmsV2NodeIpAddress, sonusEmsNodeId }
--     STATUS          mandatory
    DESCRIPTION     
            "Successfully complete PIF collection for the specified node."
    ::= 78

sonusEmsV2PMCollectionTaskStopped TRAP-TYPE
    ENTERPRISE      sonusEmsNotifications
    VARIABLES       { sysName, sysObjectID, sonusEventTime, 
                      sonusEventDescription, sonusEventClass, 
                      sonusEventLevel, sonusEmsV2NodeIpAddressType, 
                      sonusEmsV2NodeIpAddress, sonusEmsNodeId }
--     STATUS          mandatory
    DESCRIPTION     
            "PM Collection task has stopped and PMWatchdog is restarting the task."
    ::= 79

sonusEmsV2PMExportWithNoData TRAP-TYPE
    ENTERPRISE      sonusEmsNotifications
    VARIABLES       { sysName, sysObjectID, sonusEventTime, 
                      sonusEventDescription, sonusEventClass, 
                      sonusEventLevel, sonusEmsV2NodeIpAddressType, 
                      sonusEmsV2NodeIpAddress, sonusEmsNodeId, 
                      sonusEmsPMStatsNames, sonusEmsPMExportCsvFile }
--     STATUS          mandatory
    DESCRIPTION     
            "PM Exporter wrote the CSV file without any data (i.e with only header information)."
    ::= 80

sonusEmsV2LoginFailureNotification TRAP-TYPE
    ENTERPRISE      sonusEmsNotifications
    VARIABLES       { sonusEventTime, sonusEventDescription, 
                      sonusEventClass, sonusEventLevel, 
                      sonusEmsV2LoginIPAddressType, 
                      sonusEmsV2LoginIPAddress, sonusEmsLoginUserName }
--     STATUS          mandatory
    DESCRIPTION     
            "Specifies that a login attempt failed for the user specified by sonusEmsLoginUserName from host specified by sonusEmsV2LoginIPAddress."
    ::= 81

sonusEmsLnpBddFileDownloadErrorNotification TRAP-TYPE
    ENTERPRISE      sonusEmsNotifications
    VARIABLES       { sysName, sysObjectID, sonusEventTime, 
                      sonusEventDescription, sonusEventClass, 
                      sonusEventLevel, sonusEmsNodeId, sonusHostID }
--     STATUS          mandatory
    DESCRIPTION     
            "EMS was not able to download Bulk Data Download File."
    ::= 82

sonusEmsLnpBddFileDownloadCompletedNotification TRAP-TYPE
    ENTERPRISE      sonusEmsNotifications
    VARIABLES       { sysName, sysObjectID, sonusEventTime, 
                      sonusEventDescription, sonusEventClass, 
                      sonusEventLevel, sonusEmsNodeId, sonusHostID }
--     STATUS          mandatory
    DESCRIPTION     
            "EMS downloaded Bulk Data Download File correctly and was able to obtain last transaction id."
    ::= 83

sonusEmsLnpDataSyncErrorNotification TRAP-TYPE
    ENTERPRISE      sonusEmsNotifications
    VARIABLES       { sysName, sysObjectID, sonusEventTime, 
                      sonusEventDescription, sonusEventClass, 
                      sonusEventLevel, sonusEmsNodeId, sonusHostID }
--     STATUS          mandatory
    DESCRIPTION     
            "EMS/IAS was not able to sync LNP/MNP data between MCH server and PSX."
    ::= 84

sonusEmsNPBulkFileReadyNotification TRAP-TYPE
    ENTERPRISE      sonusEmsNotifications
    VARIABLES       { sysName, sysObjectID, sonusEventTime, 
                      sonusEventDescription, sonusEventClass, 
                      sonusEventLevel, sonusEmsNodeId, sonusHostID, 
                      sonusEmsNPServicesMCHName, 
                      sonusEmsNPServicesBulkRequestTransactionId }
--     STATUS          mandatory
    DESCRIPTION     
            "MCH has generated the bulk file corresponding to request sent by EMS and is ready for download."
    ::= 85

sonusEmsNPBulkFileRequestRejectedNotification TRAP-TYPE
    ENTERPRISE      sonusEmsNotifications
    VARIABLES       { sysName, sysObjectID, sonusEventTime, 
                      sonusEventDescription, sonusEventClass, 
                      sonusEventLevel, sonusEmsNodeId, sonusHostID, 
                      sonusEmsNPServicesMCHName, 
                      sonusEmsNPServicesBulkRequestTransactionId }
--     STATUS          mandatory
    DESCRIPTION     
            "MCH has rejected the bulk file generation request, check the request and resubmit. 
             Possible reasons include wrong time range, incorrect user credentials"
    ::= 86

sonusEmsNPBulkProvisioningCompletedNotification TRAP-TYPE
    ENTERPRISE      sonusEmsNotifications
    VARIABLES       { sysName, sysObjectID, sonusEventTime, 
                      sonusEventDescription, sonusEventClass, 
                      sonusEventLevel, sonusEmsNodeId, sonusHostID, 
                      sonusEmsNPServicesMCHName, 
                      sonusEmsNPServicesBulkRequestTransactionId }
--     STATUS          mandatory
    DESCRIPTION     
            "Provisioning of Partial Bulk File is completed successfully."
    ::= 87

sonusEmsNPBulkProvisioningFailedNotification TRAP-TYPE
    ENTERPRISE      sonusEmsNotifications
    VARIABLES       { sysName, sysObjectID, sonusEventTime, 
                      sonusEventDescription, sonusEventClass, 
                      sonusEventLevel, sonusEmsNodeId, sonusHostID, 
                      sonusEmsNPServicesMCHName, 
                      sonusEmsNPServicesBulkRequestTransactionId }
--     STATUS          mandatory
    DESCRIPTION     
            "Provisioning of Partial Bulk File failed."
    ::= 88

sonusEmsUpgradeJobFailedErrorNotification TRAP-TYPE
    ENTERPRISE      sonusEmsNotifications
    VARIABLES       { sysName, sysObjectID, sonusEventTime, 
                      sonusEventDescription, sonusEventClass, 
                      sonusEventLevel, scheduleId, scheduleName, 
                      failedNodes }
--     STATUS          mandatory
    DESCRIPTION     
            "SBC management Upgrade schedule error notification"
    ::= 89

sonusEmsBackupJobFailedErrorNotification TRAP-TYPE
    ENTERPRISE      sonusEmsNotifications
    VARIABLES       { sysName, sysObjectID, sonusEventTime, 
                      sonusEventDescription, sonusEventClass, 
                      sonusEventLevel, scheduleId, scheduleName, 
                      failedNodes }
--     STATUS          mandatory
    DESCRIPTION     
            "SBC management Backup schedule error notification"
    ::= 90

sonusEmsConfigurationJobFailedErrorNotification TRAP-TYPE
    ENTERPRISE      sonusEmsNotifications
    VARIABLES       { sysName, sysObjectID, sonusEventTime, 
                      sonusEventDescription, sonusEventClass, 
                      sonusEventLevel, scheduleId, scheduleName, 
                      failedNodes }
--     STATUS          mandatory
    DESCRIPTION     
            "SBC management Configuration schedule error notification"
    ::= 91

sonusEmsRestoreFailedErrorNotification TRAP-TYPE
    ENTERPRISE      sonusEmsNotifications
    VARIABLES       { sysName, sysObjectID, sonusEventTime, 
                      sonusEventDescription, sonusEventClass, 
                      failedNodes }
--     STATUS          mandatory
    DESCRIPTION     
            "SBC management Restore Operation error notification"
    ::= 92

sonusEmsV2PMStatsFileCollectionFailed TRAP-TYPE
    ENTERPRISE      sonusEmsNotifications
    VARIABLES       { sysName, sysObjectID, sonusEventTime, 
                      sonusEventDescription, sonusEventClass, 
                      sonusEventLevel, sonusEmsV2NodeIpAddressType, 
                      sonusEmsV2NodeIpAddress, sonusEmsNodeId }
--     STATUS          mandatory
    DESCRIPTION     
            "Downloading of statistics file from device failed."
    ::= 93

sonusEmsPartialConfigurationJobFailedErrorNotification TRAP-TYPE
    ENTERPRISE      sonusEmsNotifications
    VARIABLES       { sysName, sysObjectID, sonusEventTime, 
                      sonusEventDescription, sonusEventClass, 
                      sonusEventLevel, scheduleId, scheduleName, 
                      failedNodes }
--     STATUS          mandatory
    DESCRIPTION     
            "SBC management Partial Configuration schedule error notification"
    ::= 94

sonusEmsClusterNodeRegistrationRejectedNotification TRAP-TYPE
    ENTERPRISE      sonusEmsNotifications
    VARIABLES       { sysName, sysObjectID, sonusEventTime, 
                      sonusEventDescription, sonusEventClass, nodename, 
                      nodeip, clustername }
--     STATUS          mandatory
    DESCRIPTION     
            "Cluster dynamic node registration rejected"
    ::= 95

sonusEmsClusterInstanceUpNotReceivedNotification TRAP-TYPE
    ENTERPRISE      sonusEmsNotifications
    VARIABLES       { sysName, sysObjectID, sonusEventTime, 
                      sonusEventDescription, sonusEventClass, nodename, 
                      nodeip, clustername }
--     STATUS          mandatory
    DESCRIPTION     
            "Instanceup request never received for the node"
    ::= 96

sonusEmsClusterNodeIPIsInUseNotification TRAP-TYPE
    ENTERPRISE      sonusEmsNotifications
    VARIABLES       { sysName, sysObjectID, sonusEventTime, 
                      sonusEventDescription, sonusEventClass, nodename, 
                      nodeip, clustername }
--     STATUS          mandatory
    DESCRIPTION     
            "EMS detecting another node is already registered with same IP"
    ::= 97

sonusEmsClusterConfigUpdateFailedNotification TRAP-TYPE
    ENTERPRISE      sonusEmsNotifications
    VARIABLES       { sysName, sysObjectID, sonusEventTime, 
                      sonusEventDescription, sonusEventClass, nodename, 
                      nodeip, clustername }
--     STATUS          mandatory
    DESCRIPTION     
            "Configuration update failed for node"
    ::= 98

sonusEMSClusterNodeDeRegistrationNotification TRAP-TYPE
    ENTERPRISE      sonusEmsNotifications
    VARIABLES       { sysName, sysObjectID, sonusEventTime, 
                      sonusEventDescription, sonusEventClass, nodename, 
                      nodeip, clustername, reason }
--     STATUS          mandatory
    DESCRIPTION     
            "Cluster dynamic node deregistration rejected"
    ::= 99

sonusEMSClusterNodePurgeNotification TRAP-TYPE
    ENTERPRISE      sonusEmsNotifications
    VARIABLES       { sysName, sysObjectID, sonusEventTime, 
                      sonusEventDescription, sonusEventClass, nodename, 
                      nodeip, clustername, reason }
--     STATUS          mandatory
    DESCRIPTION     
            "Cluster dynamic node purge rejected"
    ::= 100

sonusEMSClusterNodeDiscoveryFailedNotification TRAP-TYPE
    ENTERPRISE      sonusEmsNotifications
    VARIABLES       { sysName, sysObjectID, sonusEventTime, 
                      sonusEventDescription, sonusEventClass, nodename, 
                      nodeip, clustername, reason }
--     STATUS          mandatory
    DESCRIPTION     
            "Cluster dynamic node purge rejected"
    ::= 101

sonusEmsClusterNodeIPIsInUseUnRegisterNotification TRAP-TYPE
    ENTERPRISE      sonusEmsNotifications
    VARIABLES       { sysName, sysObjectID, sonusEventTime, 
                      sonusEventDescription, sonusEventClass, nodename, 
                      nodeip, clustername, reason }
--     STATUS          mandatory
    DESCRIPTION     
            "Cluster node ip is in use got UnRegister"
    ::= 102

sonusEmsClusterBelowConfiguredNodeCountNotification TRAP-TYPE
    ENTERPRISE      sonusEmsNotifications
    VARIABLES       { sysName, sysObjectID, sonusEventTime, 
                      sonusEventDescription, sonusEventClass, nodename, 
                      nodeip, clustername, clusterid }
--     STATUS          mandatory
    DESCRIPTION     
            "Number of nodes in the cluster is below the configured limit"
    ::= 103

sonusEmsClusterReachedConfiguredNodeCountNotification TRAP-TYPE
    ENTERPRISE      sonusEmsNotifications
    VARIABLES       { sysName, sysObjectID, sonusEventTime, 
                      sonusEventDescription, sonusEventClass, nodename, 
                      nodeip, clustername, clusterid }
--     STATUS          mandatory
    DESCRIPTION     
            "Number of nodes in the cluster reached the minimum configured limit"
    ::= 104

sonusEmsPMProfileAssignmentFailedNotification TRAP-TYPE
    ENTERPRISE      sonusEmsNotifications
    VARIABLES       { sysName, sysObjectID, sonusEventTime, 
                      sonusEventDescription, sonusEventClass, 
                      sonusEventLevel, sonusEmsV2NodeIpAddressType, 
                      sonusEmsV2NodeIpAddress, sonusEmsNodeId }
--     STATUS          mandatory
    DESCRIPTION     
            "Warning indicating that PM Profile assignment onto device failed."
    ::= 105

sonusEmsPMPollSkipNotification TRAP-TYPE
    ENTERPRISE      sonusEmsNotifications
    VARIABLES       { sysName, sysObjectID, sonusEventTime, 
                      sonusEventDescription, sonusEventClass, 
                      sonusEventLevel, sonusEmsV2NodeIpAddressType, 
                      sonusEmsV2NodeIpAddress, sonusEmsNodeId }
--     STATUS          mandatory
    DESCRIPTION     
            "It describes the event when a PM skips a poll for node"
    ::= 106

sonusEMSLIX1InterfaceDownNotification TRAP-TYPE
    ENTERPRISE      sonusEmsNotifications
    VARIABLES       { sysName, sysObjectID, sonusEventTime, 
                      sonusEventDescription, sonusEventClass, 
                      mediationServerIP }
--     STATUS          mandatory
    DESCRIPTION     
            "X1 Interface Connection Terminated."
    ::= 107

sonusEMSLIX1InterfaceUpNotification TRAP-TYPE
    ENTERPRISE      sonusEmsNotifications
    VARIABLES       { sysName, sysObjectID, sonusEventTime, 
                      sonusEventDescription, sonusEventClass, 
                      mediationServerIP }
--     STATUS          mandatory
    DESCRIPTION     
            "X1 Interface Connection Established."
    ::= 108

sonusEmsSANEServerUnreachableNotification TRAP-TYPE
    ENTERPRISE      sonusEmsNotifications
    VARIABLES       { sysName, sysObjectID, sonusEventTime, 
                      sonusEventDescription, sonusEventClass, 
                      sonusEventLevel }
--     STATUS          mandatory
    DESCRIPTION     
            "The SANE server was unreachable when attempting to authenticate SANE user."
    ::= 109

sonusEmsPMBacklogExportNotification TRAP-TYPE
    ENTERPRISE      sonusEmsNotifications
    VARIABLES       { sysName, sysObjectID, sonusEventTime, 
                      sonusEventDescription, sonusEventClass, 
                      sonusEventLevel, sonusEmsV2NodeIpAddressType, 
                      sonusEmsV2NodeIpAddress, sonusEmsNodeId }
--     STATUS          mandatory
    DESCRIPTION     
            "It describes the event when a PM backlog export  happens for  a  node."
    ::= 110

sonusEmsSANECertificateExpiryNotification TRAP-TYPE
    ENTERPRISE      sonusEmsNotifications
    VARIABLES       { sysName, sysObjectID, sonusEventTime, 
                      sonusEventDescription, sonusEventClass, 
                      sonusEventLevel }
--     STATUS          mandatory
    DESCRIPTION     
            "It describes the SANE certificate expiry event."
    ::= 111

sonusEMSVnfrRegistrationFailedNotification TRAP-TYPE
    ENTERPRISE      sonusEmsNotifications
    VARIABLES       { sysName, sonusEventTime, sonusEventDescription, 
                      sonusEventClass, sonusEventLevel, vnfmIp, 
                      restResponseCode }
--     STATUS          mandatory
    DESCRIPTION     
            "VNFR registration with VNFM failed"
    ::= 112

sonusEMSVnfrRegistrationSuccessNotification TRAP-TYPE
    ENTERPRISE      sonusEmsNotifications
    VARIABLES       { sysName, sonusEventTime, sonusEventDescription, 
                      sonusEventClass, sonusEventLevel, vnfmIp, 
                      restResponseCode }
--     STATUS          mandatory
    DESCRIPTION     
            "VNFR successfully registered with VNFM after initial failure"
    ::= 113

sonusEMSVnfrHeartbeatDownNotification TRAP-TYPE
    ENTERPRISE      sonusEmsNotifications
    VARIABLES       { sysName, sonusEventTime, sonusEventDescription, 
                      sonusEventClass, sonusEventLevel, vnfmIp, 
                      lastHeartbeatTime }
--     STATUS          mandatory
    DESCRIPTION     
            "VNFR has stopped receiving heartbeat messages from the VNFM"
    ::= 114

sonusEMSVnfrHeartbeatUpNotification TRAP-TYPE
    ENTERPRISE      sonusEmsNotifications
    VARIABLES       { sysName, sonusEventTime, sonusEventDescription, 
                      sonusEventClass, sonusEventLevel, vnfmIp, 
                      lastHeartbeatTime }
--     STATUS          mandatory
    DESCRIPTION     
            "VNFR has started receiving heartbeat messages from the VNFM again"
    ::= 115

sonusEmsClusterConfigHeadendOutofsyncNotification TRAP-TYPE
    ENTERPRISE      sonusEmsNotifications
    VARIABLES       { sysName, sysObjectID, sonusEventTime, 
                      sonusEventDescription, sonusEventClass, nodename, 
                      nodeip, clustername, clusterid }
--     STATUS          mandatory
    DESCRIPTION     
            "An SBC head end has been updating the cluster configuration for a longer than expected duration and not yet activated it"
    ::= 116

sonusEmsClusterConfigHeadendActivatedNotification TRAP-TYPE
    ENTERPRISE      sonusEmsNotifications
    VARIABLES       { sysName, sysObjectID, sonusEventTime, 
                      sonusEventDescription, sonusEventClass, nodename, 
                      nodeip, clustername, clusterid }
--     STATUS          mandatory
    DESCRIPTION     
            "An SBC head end has updated and activated a cluster configuration"
    ::= 117

sonusEmsClusterInvalidNodeRegistrationNotification TRAP-TYPE
    ENTERPRISE      sonusEmsNotifications
    VARIABLES       { sysName, sysObjectID, sonusEventTime, 
                      sonusEventDescription, sonusEventClass, nodename, 
                      nodeip, clustername, clusterid, reason }
--     STATUS          mandatory
    DESCRIPTION     
            "Invalid cluster node registration received"
    ::= 118

sonusEmsInsightDBConnectionPoolExhaustedNotification TRAP-TYPE
    ENTERPRISE      sonusEmsNotifications
    VARIABLES       { sysName, sysObjectID, sonusEventTime, 
                      sonusEventDescription, sonusEventClass, 
                      sonusEventLevel }
--     STATUS          mandatory
    DESCRIPTION     
            "The Insight DB Connection pool is empty."
    ::= 119

sonusEmsPMProfileProfileAssignmentSuccessNotification TRAP-TYPE
    ENTERPRISE      sonusEmsNotifications
    VARIABLES       { sysName, sysObjectID, sonusEventTime, 
                      sonusEventDescription, sonusEventClass, 
                      sonusEventLevel, sonusEmsProfileName }
--     STATUS          mandatory
    DESCRIPTION     
            "Indicating that PM Profile assignment succeeded."
    ::= 120

sonusEmsPMProfileProfileAssignmentFailedNotification TRAP-TYPE
    ENTERPRISE      sonusEmsNotifications
    VARIABLES       { sysName, sysObjectID, sonusEventTime, 
                      sonusEventDescription, sonusEventClass, 
                      sonusEventLevel, sonusEmsProfileName }
--     STATUS          mandatory
    DESCRIPTION     
            "Warning indicating that PM Profile assignment failed."
    ::= 121

sonusEmsFingerprintChangeNotification TRAP-TYPE
    ENTERPRISE      sonusEmsNotifications
    VARIABLES       { sysName, sysObjectID, sonusEventTime, 
                      sonusEventDescription, sonusEventClass, 
                      sonusEventLevel }
--     STATUS          mandatory
    DESCRIPTION     
            "Indicating that Fingerprint is changed on device side."
    ::= 122

sonusEmsFingerprintMismatchNotification TRAP-TYPE
    ENTERPRISE      sonusEmsNotifications
    VARIABLES       { sysName, sysObjectID, sonusEventTime, 
                      sonusEventDescription, sonusEventClass, 
                      sonusEventLevel }
--     STATUS          mandatory
    DESCRIPTION     
            "Indicating that Fingerprint verification failed on the device."
    ::= 123

sonusEmsNodeSnmpV3SetFailedNotification TRAP-TYPE
    ENTERPRISE      sonusEmsNotifications
    VARIABLES       { sysName, sysObjectID, sonusEventTime, 
                      sonusEventDescription, sonusEventClass, 
                      sonusEventLevel, sonusEmsV2NodeIpAddressType, 
                      sonusEmsV2NodeIpAddress, sonusEmsNodeId }
--     STATUS          mandatory
    DESCRIPTION     
            "Node SNMP trap setting is out sync with the config. Reset the config."
    ::= 124

sonusDBaasFileSystemUtilizationNotification TRAP-TYPE
    ENTERPRISE      sonusEmsNotifications
    VARIABLES       { sonusHostID, sonusEventDescription, 
                      sonusEventClass, sonusEventLevel, sonusEventTime }
--     STATUS          mandatory
    DESCRIPTION     
            "Database file system utilization "
    ::= 125

sonusDBaasDownNotification TRAP-TYPE
    ENTERPRISE      sonusEmsNotifications
    VARIABLES       { sonusHostID, sonusEventDescription, 
                      sonusEventClass, sonusEventLevel, sonusEventTime }
--     STATUS          mandatory
    DESCRIPTION     
            "Database is down "
    ::= 126

sonusDBaasStandbyLagNotification TRAP-TYPE
    ENTERPRISE      sonusEmsNotifications
    VARIABLES       { sonusHostID, sonusEventDescription, 
                      sonusEventClass, sonusEventLevel, sonusEventTime }
--     STATUS          mandatory
    DESCRIPTION     
            "Standby node Lag "
    ::= 127

sonusDBaasStandbyInactiveNotification TRAP-TYPE
    ENTERPRISE      sonusEmsNotifications
    VARIABLES       { sonusHostID, sonusEventDescription, 
                      sonusEventClass, sonusEventLevel, sonusEventTime }
--     STATUS          mandatory
    DESCRIPTION     
            "Standby node is inactive "
    ::= 128

sonusDBaasClearNotification TRAP-TYPE
    ENTERPRISE      sonusEmsNotifications
    VARIABLES       { sonusHostID, sonusEventDescription, 
                      sonusEventClass, sonusEventLevel, sonusEventTime }
--     STATUS          mandatory
    DESCRIPTION     
            "Clear trap for DBaas notification "
    ::= 129

sonusEmsTrapReSyncDelimiterNotification TRAP-TYPE
    ENTERPRISE      sonusEmsNotifications
    VARIABLES       { sonusEventDescription, sonusEventLevel, 
                      sonusEmsFmTrapReSyncDelimiter }
--     STATUS          mandatory
    DESCRIPTION     
            "Trap Re-sync delimiter notification."
    ::= 130

sonusEmsLDAPServerErrorNotification TRAP-TYPE
    ENTERPRISE      sonusEmsNotifications
    VARIABLES       { sonusHostID, sonusEventDescription, 
                      sonusEventClass, sonusEventLevel, sonusEventTime }
--     STATUS          mandatory
    DESCRIPTION     
            "LDAP Server Error Notification"
    ::= 131

sonusEmsRisingEventNotification TRAP-TYPE
    ENTERPRISE      sonusEmsNotificationsPrefix
    VARIABLES       { sysName, sysObjectID, sonusEventTime, 
                      sonusEventDescription, sonusEventClass, 
                      sonusEventLevel, sonusEmsThresholdIpAddress, 
                      sonusEmsThresholdObjectId, 
                      sonusEmsThresholdTriggerValue, 
                      sonusEmsThresholdSampleValue, 
                      sonusEmsThresholdLocationIndexes, 
                      sonusEmsThresholdIdentifier }
--     STATUS          deprecated
    DESCRIPTION     
            "A rising event notification informs that a given
             performance measure has crossed a given threshold
             - it has risen above a defined rising threshold
             value."
    ::= 1

sonusEmsFallingEventNotification TRAP-TYPE
    ENTERPRISE      sonusEmsNotificationsPrefix
    VARIABLES       { sysName, sysObjectID, sonusEventTime, 
                      sonusEventDescription, sonusEventClass, 
                      sonusEventLevel, sonusEmsThresholdIpAddress, 
                      sonusEmsThresholdObjectId, 
                      sonusEmsThresholdTriggerValue, 
                      sonusEmsThresholdSampleValue, 
                      sonusEmsThresholdLocationIndexes, 
                      sonusEmsThresholdIdentifier }
--     STATUS          deprecated
    DESCRIPTION     
            "A falling event notification informs that a given
             performance measure for which a previous rising event
             notification was generated has returned below a defined
             falling value for that threshold and should be cleared."
    ::= 2

sonusEmsNodeUnreachableNotification TRAP-TYPE
    ENTERPRISE      sonusEmsNotificationsPrefix
    VARIABLES       { sysName, sysObjectID, sonusEventTime, 
                      sonusEventDescription, sonusEventClass, 
                      sonusEventLevel, sonusEmsNodeIpAddress, 
                      sonusEmsNodeId }
--     STATUS          deprecated
    DESCRIPTION     
            "The specified node is not reachable by the EMS."
    ::= 3

sonusEmsNodeReachableNotification TRAP-TYPE
    ENTERPRISE      sonusEmsNotificationsPrefix
    VARIABLES       { sysName, sysObjectID, sonusEventTime, 
                      sonusEventDescription, sonusEventClass, 
                      sonusEventLevel, sonusEmsNodeIpAddress, 
                      sonusEmsNodeId }
--     STATUS          deprecated
    DESCRIPTION     
            "The specified node is now reachable by the EMS."
    ::= 4

sonusEmsNodeRestartedNotification TRAP-TYPE
    ENTERPRISE      sonusEmsNotificationsPrefix
    VARIABLES       { sysName, sysObjectID, sonusEventTime, 
                      sonusEventDescription, sonusEventClass, 
                      sonusEventLevel, sonusEmsNodeIpAddress, 
                      sonusEmsNodeId }
--     STATUS          deprecated
    DESCRIPTION     
            "The specified node has been restarted since last polled by the EMS."
    ::= 5

sonusEmsNodeCfgFailNotification TRAP-TYPE
    ENTERPRISE      sonusEmsNotificationsPrefix
    VARIABLES       { sysName, sysObjectID, sonusEventTime, 
                      sonusEventDescription, sonusEventClass, 
                      sonusEventLevel, sonusEmsNodeIpAddress, 
                      sonusEmsNodeId }
--     STATUS          deprecated
    DESCRIPTION     
            "EMS failed to configure the specified node."
    ::= 6

sonusEmsNodeCfgDoneNotification TRAP-TYPE
    ENTERPRISE      sonusEmsNotificationsPrefix
    VARIABLES       { sysName, sysObjectID, sonusEventTime, 
                      sonusEventDescription, sonusEventClass, 
                      sonusEventLevel, sonusEmsNodeIpAddress, 
                      sonusEmsNodeId }
--     STATUS          deprecated
    DESCRIPTION     
            "Successfully configured the specified node."
    ::= 7

sonusEmsFmSequenceGapNotification TRAP-TYPE
    ENTERPRISE      sonusEmsNotificationsPrefix
    VARIABLES       { sysName, sysObjectID, sonusEventTime, 
                      sonusEventDescription, sonusEventClass, 
                      sonusEventLevel, sonusEmsNodeIpAddress, 
                      sonusEmsNodeId, sonusEmsFmSequenceId, 
                      sonusEmsFmSequenceEndGapId }
--     STATUS          deprecated
    DESCRIPTION     
            "The fm manager has observed a sequence gap in INFORM traps from the device."
    ::= 8

sonusEmsFmSequenceResetNotification TRAP-TYPE
    ENTERPRISE      sonusEmsNotificationsPrefix
    VARIABLES       { sysName, sysObjectID, sonusEventTime, 
                      sonusEventDescription, sonusEventClass, 
                      sonusEventLevel, sonusEmsNodeIpAddress, 
                      sonusEmsNodeId, sonusEmsFmSequenceId, 
                      sonusEmsFmSequenceResetId }
--     STATUS          deprecated
    DESCRIPTION     
            "The fm manager has observed a situation which caused it to rest the expected sequence number.  This can be due to a agent reset or reboot."
    ::= 9

sonusEmsFmSequenceQOverflowNotification TRAP-TYPE
    ENTERPRISE      sonusEmsNotificationsPrefix
    VARIABLES       { sysName, sysObjectID, sonusEventTime, 
                      sonusEventDescription, sonusEventClass, 
                      sonusEventLevel, sonusEmsNodeIpAddress, 
                      sonusEmsNodeId, sonusEmsFmSequenceId }
--     STATUS          deprecated
    DESCRIPTION     
            "The queue used by sequence handling code has overflowed. This may cause traps to be handled out of order."
    ::= 10

sonusEmsNodeCfgPartialNotification TRAP-TYPE
    ENTERPRISE      sonusEmsNotificationsPrefix
    VARIABLES       { sysName, sysObjectID, sonusEventTime, 
                      sonusEventDescription, sonusEventClass, 
                      sonusEventLevel, sonusEmsNodeIpAddress, 
                      sonusEmsNodeId }
--     STATUS          deprecated
    DESCRIPTION     
            "Partially configured the specified node.  One of the hosts of a redundant configuration was not successfully configured."
    ::= 11

sonusEmsHostCfgSuccessNotification TRAP-TYPE
    ENTERPRISE      sonusEmsNotificationsPrefix
    VARIABLES       { sysName, sysObjectID, sonusEventTime, 
                      sonusEventDescription, sonusEventClass, 
                      sonusEventLevel, sonusEmsNodeIpAddress, 
                      sonusEmsNodeId, sonusHostID }
--     STATUS          deprecated
    DESCRIPTION     
            "The host identified by sonusHostID was configured successfully."
    ::= 12

sonusEmsHostCfgFailureNotification TRAP-TYPE
    ENTERPRISE      sonusEmsNotificationsPrefix
    VARIABLES       { sysName, sysObjectID, sonusEventTime, 
                      sonusEventDescription, sonusEventClass, 
                      sonusEventLevel, sonusEmsNodeIpAddress, 
                      sonusEmsNodeId, sonusHostID }
--     STATUS          deprecated
    DESCRIPTION     
            "The host identified by sonusHostID was not configured successfully."
    ::= 13

sonusVfyMgrNodeTypeFailNotification TRAP-TYPE
    ENTERPRISE      sonusEmsNotificationsPrefix
    VARIABLES       { sysName, sysObjectID, sonusEventTime, 
                      sonusEventDescription, sonusEventClass, 
                      sonusEventLevel, sonusEmsNodeIpAddress, 
                      sonusEmsNodeId, sonusHostID }
--     STATUS          deprecated
    DESCRIPTION     
            "The agent on the host identified by sonusHostID does not contain the instrumentation component needed to manage the registered node."
    ::= 14

sonusVfyMgrNodeTypeSuccessNotification TRAP-TYPE
    ENTERPRISE      sonusEmsNotificationsPrefix
    VARIABLES       { sysName, sysObjectID, sonusEventTime, 
                      sonusEventDescription, sonusEventClass, 
                      sonusEventLevel, sonusEmsNodeIpAddress, 
                      sonusEmsNodeId, sonusHostID }
--     STATUS          deprecated
    DESCRIPTION     
            "The agent on the host identified by sonusHostID contains the instrumentation component needed to manage the registered node."
    ::= 15

sonusVfyMgrApplVersionFailNotification TRAP-TYPE
    ENTERPRISE      sonusEmsNotificationsPrefix
    VARIABLES       { sysName, sysObjectID, sonusEventTime, 
                      sonusEventDescription, sonusEventClass, 
                      sonusEventLevel, sonusEmsNodeIpAddress, 
                      sonusEmsNodeId, sonusHostID }
--     STATUS          deprecated
    DESCRIPTION     
            "The agent on the host identified by sonusHostID reports a different application version than that contained in the EMS node model. The application version is that of the instrumented device. For example PSX or SGX."
    ::= 16

sonusVfyMgrApplVersionSuccessNotification TRAP-TYPE
    ENTERPRISE      sonusEmsNotificationsPrefix
    VARIABLES       { sysName, sysObjectID, sonusEventTime, 
                      sonusEventDescription, sonusEventClass, 
                      sonusEventLevel, sonusEmsNodeIpAddress, 
                      sonusEmsNodeId, sonusHostID }
--     STATUS          deprecated
    DESCRIPTION     
            "The agent on the host identified by sonusHostID reports the same application version as that contained in the EMS node model. The application version is that of the instrumented device. For example PSX or SGX."
    ::= 17

sonusVfyMgrMgmtClientFailNotification TRAP-TYPE
    ENTERPRISE      sonusEmsNotificationsPrefix
    VARIABLES       { sysName, sysObjectID, sonusEventTime, 
                      sonusEventDescription, sonusEventClass, 
                      sonusEventLevel, sonusEmsNodeIpAddress, 
                      sonusEmsNodeId, sonusHostID }
--     STATUS          deprecated
    DESCRIPTION     
            "The agent on the host identified by sonusHostID does not contain a fault subscription entry for the EMS."
    ::= 18

sonusVfyMgrMgmtClientSuccessNotification TRAP-TYPE
    ENTERPRISE      sonusEmsNotificationsPrefix
    VARIABLES       { sysName, sysObjectID, sonusEventTime, 
                      sonusEventDescription, sonusEventClass, 
                      sonusEventLevel, sonusEmsNodeIpAddress, 
                      sonusEmsNodeId, sonusHostID }
--     STATUS          deprecated
    DESCRIPTION     
            "The agent on the host identified by sonusHostID contains a fault subscription entry for the EMS."
    ::= 19

sonusVfyMgrSnmpAccessFailNotification TRAP-TYPE
    ENTERPRISE      sonusEmsNotificationsPrefix
    VARIABLES       { sysName, sysObjectID, sonusEventTime, 
                      sonusEventDescription, sonusEventClass, 
                      sonusEventLevel, sonusEmsNodeIpAddress, 
                      sonusEmsNodeId, sonusHostID }
--     STATUS          deprecated
    DESCRIPTION     
            "The agent on the host identified by sonusHostID does not allow SNMP Read access priviledge for Insight."
    ::= 20

sonusVfyMgrSnmpAccessSuccessNotification TRAP-TYPE
    ENTERPRISE      sonusEmsNotificationsPrefix
    VARIABLES       { sysName, sysObjectID, sonusEventTime, 
                      sonusEventDescription, sonusEventClass, 
                      sonusEventLevel, sonusEmsNodeIpAddress, 
                      sonusEmsNodeId, sonusHostID }
--     STATUS          deprecated
    DESCRIPTION     
            "The agent on the host identified by sonusHostID allows SNMP Read access priviledge for Insight."
    ::= 21

sonusVfyMgrAgentVersionFailNotification TRAP-TYPE
    ENTERPRISE      sonusEmsNotificationsPrefix
    VARIABLES       { sysName, sysObjectID, sonusEventTime, 
                      sonusEventDescription, sonusEventClass, 
                      sonusEventLevel, sonusEmsNodeIpAddress, 
                      sonusEmsNodeId, sonusHostID }
--     STATUS          deprecated
    DESCRIPTION     
            "The agent on the host identified by sonusHostID reports a different version than that stored in the EMS."
    ::= 22

sonusVfyMgrAgentVersionSuccessNotification TRAP-TYPE
    ENTERPRISE      sonusEmsNotificationsPrefix
    VARIABLES       { sysName, sysObjectID, sonusEventTime, 
                      sonusEventDescription, sonusEventClass, 
                      sonusEventLevel, sonusEmsNodeIpAddress, 
                      sonusEmsNodeId, sonusHostID }
--     STATUS          deprecated
    DESCRIPTION     
            "The agent on the host identified by sonusHostID reports the same version as that stored in the EMS."
    ::= 23

sonusEmsHostUnreachableNotification TRAP-TYPE
    ENTERPRISE      sonusEmsNotificationsPrefix
    VARIABLES       { sysName, sysObjectID, sonusEventTime, 
                      sonusEventDescription, sonusEventClass, 
                      sonusEventLevel, sonusEmsNodeIpAddress, 
                      sonusEmsNodeId }
--     STATUS          deprecated
    DESCRIPTION     
            "The specified host is not reachable by the EMS."
    ::= 24

sonusEmsHostReachableNotification TRAP-TYPE
    ENTERPRISE      sonusEmsNotificationsPrefix
    VARIABLES       { sysName, sysObjectID, sonusEventTime, 
                      sonusEventDescription, sonusEventClass, 
                      sonusEventLevel, sonusEmsNodeIpAddress, 
                      sonusEmsNodeId }
--     STATUS          deprecated
    DESCRIPTION     
            "The specified host is now reachable by the EMS."
    ::= 25

sonusEmsHostRestartedNotification TRAP-TYPE
    ENTERPRISE      sonusEmsNotificationsPrefix
    VARIABLES       { sysName, sysObjectID, sonusEventTime, 
                      sonusEventDescription, sonusEventClass, 
                      sonusEventLevel, sonusEmsNodeIpAddress, 
                      sonusEmsNodeId }
--     STATUS          deprecated
    DESCRIPTION     
            "The specified host has been restarted since last polled by the EMS."
    ::= 26

sonusEmsPifCollectFailNotification TRAP-TYPE
    ENTERPRISE      sonusEmsNotificationsPrefix
    VARIABLES       { sysName, sysObjectID, sonusEventTime, 
                      sonusEventDescription, sonusEventClass, 
                      sonusEventLevel, sonusEmsNodeIpAddress, 
                      sonusEmsNodeId }
--     STATUS          deprecated
    DESCRIPTION     
            "EMS failed to complete PIF collection for the specified node."
    ::= 27

sonusEmsPifCollectDoneNotification TRAP-TYPE
    ENTERPRISE      sonusEmsNotificationsPrefix
    VARIABLES       { sysName, sysObjectID, sonusEventTime, 
                      sonusEventDescription, sonusEventClass, 
                      sonusEventLevel, sonusEmsNodeIpAddress, 
                      sonusEmsNodeId }
--     STATUS          deprecated
    DESCRIPTION     
            "Successfully complete PIF collection for the specified node."
    ::= 28

sonusEmsPMCollectionTaskStopped TRAP-TYPE
    ENTERPRISE      sonusEmsNotificationsPrefix
    VARIABLES       { sysName, sysObjectID, sonusEventTime, 
                      sonusEventDescription, sonusEventClass, 
                      sonusEventLevel, sonusEmsNodeIpAddress, 
                      sonusEmsNodeId }
--     STATUS          deprecated
    DESCRIPTION     
            "PM Collection task has stopped and PMWatchdog is restarting the task."
    ::= 29

sonusEmsPMExportWithNoData TRAP-TYPE
    ENTERPRISE      sonusEmsNotificationsPrefix
    VARIABLES       { sysName, sysObjectID, sonusEventTime, 
                      sonusEventDescription, sonusEventClass, 
                      sonusEventLevel, sonusEmsNodeIpAddress, 
                      sonusEmsNodeId, sonusEmsPMStatsNames, 
                      sonusEmsPMExportCsvFile }
--     STATUS          deprecated
    DESCRIPTION     
            "PM Exporter wrote the CSV file without any data (i.e with only header information)."
    ::= 30

sonusEmsPMExportSFTPFailNotification TRAP-TYPE
    ENTERPRISE      sonusEmsNotificationsPrefix
    VARIABLES       { sysName, sysObjectID, sonusEventTime, 
                      sonusEventDescription, sonusEventClass, 
                      sonusEventLevel, sonusRemoteServer }
--     STATUS          mandatory
    DESCRIPTION     
            "PM Exporter: Problem SCP'ing files to host."
    ::= 31

sonusEmsPMExportSFTPFailClearNotification TRAP-TYPE
    ENTERPRISE      sonusEmsNotificationsPrefix
    VARIABLES       { sysName, sysObjectID, sonusEventTime, 
                      sonusEventDescription, sonusEventClass, 
                      sonusEventLevel, sonusRemoteServer }
--     STATUS          mandatory
    DESCRIPTION     
            "PM Exporter: Rectified SCP'ing files to host."
    ::= 32

END -- end of module SONUS-EMS-MIB.
