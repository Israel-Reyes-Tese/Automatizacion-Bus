--
-- This SMIv1 module has been generated by smidump 0.2-cvs. Do not edit.
--

SONUS-ATM-EXTENSIONS-MIB DEFINITIONS ::= BEGIN

IMPORTS
    AtmVcIdentifier, AtmVpIdentifier
        FROM ATM-TC-MIB
    InterfaceIndex
        FROM IF-MIB
    OBJECT-TYPE
        FROM RFC-1212
    TRAP-TYPE
        FROM RFC-1215
    Counter
        FROM RFC1155-SMI
    RowStatus
        FROM SNMPv2-TC
    sonusEventClass, sonusEventDescription, sonusEventLevel, 
    sonusEventTime, sonusSequenceId
        FROM SONUS-COMMON-MIB
    sonusNifIndex, sonusNifPort, sonusNifShelf, sonusNifSlot
        FROM SONUS-IP-INTERFACE-MIB
    sonusPacketMIBs
        FROM SONUS-SMI
    SonusShelfIndex, SonusSlotIndex
        FROM SONUS-TC;

sonusAtmExtMIB OBJECT IDENTIFIER
    ::= { sonusPacketMIBs 5 }

-- sonusAtmExtMIB MODULE-IDENTITY
--     LAST-UPDATED    "200703280000Z"
--     ORGANIZATION    
--             "Sonus Networks, Inc."
--     CONTACT-INFO    
--             "   Customer Support    
--              Sonus Networks, Inc.
--              7 Technology Park Drive
--              Westford, MA 01886
--              USA
--              
--              Tel: 978-614-8100
--              Fax: 978-614-8609"
--     DESCRIPTION     
--             "The MIB Module for Sonus ATM extensions."
--     ::= { sonusPacketMIBs 5 }


sonusAtmExtMIBObjects OBJECT IDENTIFIER
    ::= { sonusAtmExtMIB 1 }

sonusAtmExtVclAdmnTable OBJECT-TYPE
    SYNTAX          SEQUENCE OF SonusAtmExtVclAdmnEntry
    ACCESS          not-accessible
    STATUS          mandatory
    DESCRIPTION     
            "The Virtual Channel Link (VCL) Extension table."
    ::= { sonusAtmExtMIBObjects 1 }

sonusAtmExtVclAdmnEntry OBJECT-TYPE
    SYNTAX          SonusAtmExtVclAdmnEntry
    ACCESS          not-accessible
    STATUS          mandatory
    DESCRIPTION     
            "An entry in the VCL Extension table. This entry 
             adds additional objects to the atmVclTable.  A row
                  is added to this table when a row is created in the
                  atmVclTable."
    INDEX           { sonusAtmExtVclAdmnIfIndex, sonusAtmExtVclAdmnVpi, 
                      sonusAtmExtVclAdmnVci }
    ::= { sonusAtmExtVclAdmnTable 1 }

SonusAtmExtVclAdmnEntry ::=
    SEQUENCE {
        sonusAtmExtVclAdmnIfIndex       INTEGER,
        sonusAtmExtVclAdmnVpi           INTEGER,
        sonusAtmExtVclAdmnVci           INTEGER,
        sonusAtmExtVclAdmnMode          INTEGER,
        sonusAtmExtVclAdmnAction        INTEGER,
        sonusAtmExtVclAdmnTimeout       INTEGER,
        sonusAtmExtVclAdmnState         INTEGER,
        sonusAtmExtVclAdmnOutOfServiceReason    INTEGER,
        sonusAtmExtVclAdmnRowStatus     RowStatus,
        sonusAtmExtVclAdmnBwDeviation   INTEGER,
        sonusAtmExtVclAdmnBwContingency INTEGER
    }

sonusAtmExtVclAdmnIfIndex OBJECT-TYPE
    SYNTAX          INTEGER
    ACCESS          read-only
    STATUS          mandatory
    DESCRIPTION     
            "The ifIndex value of the NIF that VCL is on."
    ::= { sonusAtmExtVclAdmnEntry 1 }

sonusAtmExtVclAdmnVpi OBJECT-TYPE
    SYNTAX          INTEGER
    ACCESS          read-only
    STATUS          mandatory
    DESCRIPTION     
            "The VPI value of the VCL."
    ::= { sonusAtmExtVclAdmnEntry 2 }

sonusAtmExtVclAdmnVci OBJECT-TYPE
    SYNTAX          INTEGER
    ACCESS          read-only
    STATUS          mandatory
    DESCRIPTION     
            "The VCI value of the VCL."
    ::= { sonusAtmExtVclAdmnEntry 3 }

sonusAtmExtVclAdmnMode OBJECT-TYPE
    SYNTAX          INTEGER { outOfService(1), inService(2) }
    ACCESS          read-write
    STATUS          mandatory
    DESCRIPTION     
            "The operation mode for VC."
    DEFVAL          { inService }
    ::= { sonusAtmExtVclAdmnEntry 4 }

sonusAtmExtVclAdmnAction OBJECT-TYPE
    SYNTAX          INTEGER { dryUp(1), force(2) }
    ACCESS          read-write
    STATUS          mandatory
    DESCRIPTION     
            "The dryup option for VC."
    DEFVAL          { dryUp }
    ::= { sonusAtmExtVclAdmnEntry 5 }

sonusAtmExtVclAdmnTimeout OBJECT-TYPE
    SYNTAX          INTEGER (1..1440)
    ACCESS          read-write
    STATUS          mandatory
    DESCRIPTION     
            "The dryup timeout in minute. The default is one hour "
    DEFVAL          { 60 }
    ::= { sonusAtmExtVclAdmnEntry 6 }

sonusAtmExtVclAdmnState OBJECT-TYPE
    SYNTAX          INTEGER { disabled(1), enabled(2) }
    ACCESS          read-write
    STATUS          mandatory
    DESCRIPTION     
            "A VCL must be enabled before System Manager will fully
             recognize it.  The VCL must be disabled before the server
             module can be deleted."
    ::= { sonusAtmExtVclAdmnEntry 7 }

sonusAtmExtVclAdmnOutOfServiceReason OBJECT-TYPE
    SYNTAX          INTEGER { notApplicable(1), admin(2), gateway(3), 
                        portDown(4), serverDown(5), srvrAbsent(6) }
    ACCESS          read-only
    STATUS          mandatory
    DESCRIPTION     
            "The reason of ATM VC being out of service. The NIF could be out of service due to one 
             of the following reasons: operator initiated command, gateway not responding to 
             arp request, port failure/outOfService, or server failure/outOfService. The 
             		 notApplicable is set when the ATM VC is inService or dryUp state"
    ::= { sonusAtmExtVclAdmnEntry 8 }

sonusAtmExtVclAdmnRowStatus OBJECT-TYPE
    SYNTAX          RowStatus
    ACCESS          read-write
    STATUS          mandatory
    DESCRIPTION     
            ""
    ::= { sonusAtmExtVclAdmnEntry 9 }

sonusAtmExtVclAdmnBwDeviation OBJECT-TYPE
    SYNTAX          INTEGER (0..100)
    ACCESS          read-write
    STATUS          mandatory
    DESCRIPTION     
            "The deviation between actual and expected VCL bandwidth in percentage of the 
             overall VCL bandwidth. If actual bandwidth is greater than the expected 
             bandwdith plus deviation amount, a trap will be set and the trap will be 
             only cleared when the actual bandwidth dropped below the expected bandwidth.
             If the actual bandwidth is lower than the expected badniwdth minus 2 times
             of deviation amount, a different trap will be set and the trap will be
             cleared when the actual bandwdith reaches the expected bandwidth. "
    DEFVAL          { 0 }
    ::= { sonusAtmExtVclAdmnEntry 10 }

sonusAtmExtVclAdmnBwContingency OBJECT-TYPE
    SYNTAX          INTEGER (0..100)
    ACCESS          read-write
    STATUS          mandatory
    DESCRIPTION     
            "The percentage of the overall VCL bandwidth is reserved for contigency. If actual 
             bandwidth is greater than the expected bandwdith and less than the overall VCL
             bandwidth minus contingency amount, calls will still be accepted. "
    DEFVAL          { 0 }
    ::= { sonusAtmExtVclAdmnEntry 11 }

sonusAtmExtVclStatTable OBJECT-TYPE
    SYNTAX          SEQUENCE OF SonusAtmExtVclStatEntry
    ACCESS          not-accessible
    STATUS          mandatory
    DESCRIPTION     
            "The Virtual Channel Link (VCL) Extension stat table."
    ::= { sonusAtmExtMIBObjects 2 }

sonusAtmExtVclStatEntry OBJECT-TYPE
    SYNTAX          SonusAtmExtVclStatEntry
    ACCESS          not-accessible
    STATUS          mandatory
    DESCRIPTION     
            "An entry in the VCL Extension stat table."
    INDEX           { sonusAtmExtVclStatIfIndex, sonusAtmExtVclStatVpi, 
                      sonusAtmExtVclStatVci }
    ::= { sonusAtmExtVclStatTable 1 }

SonusAtmExtVclStatEntry ::=
    SEQUENCE {
        sonusAtmExtVclStatIfIndex       INTEGER,
        sonusAtmExtVclStatVpi           INTEGER,
        sonusAtmExtVclStatVci           INTEGER,
        sonusAtmExtVclStatState         INTEGER,
        sonusAtmExtVclStatCallNum       INTEGER,
        sonusAtmExtVclStatSpeedCur      INTEGER,
        sonusAtmExtVclStatSpeedMax      INTEGER,
        sonusAtmExtVclStatSpeedActual   INTEGER,
        sonusAtmExtVclStatSpeedDeviation INTEGER
    }

sonusAtmExtVclStatIfIndex OBJECT-TYPE
    SYNTAX          INTEGER
    ACCESS          read-only
    STATUS          mandatory
    DESCRIPTION     
            "The ifIndex value of the NIF that VCL is on."
    ::= { sonusAtmExtVclStatEntry 1 }

sonusAtmExtVclStatVpi OBJECT-TYPE
    SYNTAX          INTEGER
    ACCESS          read-only
    STATUS          mandatory
    DESCRIPTION     
            "The VPI value of the VCL."
    ::= { sonusAtmExtVclStatEntry 2 }

sonusAtmExtVclStatVci OBJECT-TYPE
    SYNTAX          INTEGER
    ACCESS          read-only
    STATUS          mandatory
    DESCRIPTION     
            "The VCI value of the VCL."
    ::= { sonusAtmExtVclStatEntry 3 }

sonusAtmExtVclStatState OBJECT-TYPE
    SYNTAX          INTEGER { outOfService(1), inService(2), dryUp(3) }
    ACCESS          read-only
    STATUS          mandatory
    DESCRIPTION     
            "VCL enrties are created with a state of inService.  A VCL 
             which is outOfService has had all active calls terminated.
             A VCL must be outOfService in order to change its
             state to disabled."
    ::= { sonusAtmExtVclStatEntry 4 }

sonusAtmExtVclStatCallNum OBJECT-TYPE
    SYNTAX          INTEGER
    ACCESS          read-only
    STATUS          mandatory
    DESCRIPTION     
            "The number of calls on this VCL"
    ::= { sonusAtmExtVclStatEntry 5 }

sonusAtmExtVclStatSpeedCur OBJECT-TYPE
    SYNTAX          INTEGER
    ACCESS          read-only
    STATUS          mandatory
    DESCRIPTION     
            "The current speed(bandwidth) allocated on this VCL"
    ::= { sonusAtmExtVclStatEntry 6 }

sonusAtmExtVclStatSpeedMax OBJECT-TYPE
    SYNTAX          INTEGER
    ACCESS          read-only
    STATUS          mandatory
    DESCRIPTION     
            "The maximum speed allowed on this VCL"
    ::= { sonusAtmExtVclStatEntry 7 }

sonusAtmExtVclStatSpeedActual OBJECT-TYPE
    SYNTAX          INTEGER
    ACCESS          read-only
    STATUS          mandatory
    DESCRIPTION     
            "The actual speed(bandwidth) on this VCL"
    ::= { sonusAtmExtVclStatEntry 8 }

sonusAtmExtVclStatSpeedDeviation OBJECT-TYPE
    SYNTAX          INTEGER
    ACCESS          read-only
    STATUS          mandatory
    DESCRIPTION     
            "The actual speed(bandwidth) deviation on this VCL"
    ::= { sonusAtmExtVclStatEntry 9 }

sonusAtmExtAtmLayerTable OBJECT-TYPE
    SYNTAX          SEQUENCE OF SonusAtmExtAtmLayerEntry
    ACCESS          not-accessible
    STATUS          mandatory
    DESCRIPTION     
            "The ATM layer table.  This table maps ATM layer ifIndex
             to a shelf, slot, and port."
    ::= { sonusAtmExtMIBObjects 3 }

sonusAtmExtAtmLayerEntry OBJECT-TYPE
    SYNTAX          SonusAtmExtAtmLayerEntry
    ACCESS          not-accessible
    STATUS          mandatory
    DESCRIPTION     
            "An entry in the ATM layer table. This entry 
             maps the ifIndex of the ATM layer to a shelf, slot
             and port.  A row is added to this table when a SONET
             port is created"
    INDEX           { sonusAtmExtAtmLayerShelfIndex, 
                      sonusAtmExtAtmLayerSlotIndex, 
                      sonusAtmExtAtmLayerPortIndex }
    ::= { sonusAtmExtAtmLayerTable 1 }

SonusAtmExtAtmLayerEntry ::=
    SEQUENCE {
        sonusAtmExtAtmLayerShelfIndex   SonusShelfIndex,
        sonusAtmExtAtmLayerSlotIndex    SonusSlotIndex,
        sonusAtmExtAtmLayerPortIndex    INTEGER,
        sonusAtmExtAtmLayerIfIndex      INTEGER,
        sonusAtmExtAtmLayerRowStatus    RowStatus
    }

sonusAtmExtAtmLayerShelfIndex OBJECT-TYPE
    SYNTAX          SonusShelfIndex
    ACCESS          not-accessible
    STATUS          mandatory
    DESCRIPTION     
            "The index for a Sonus shelf."
    ::= { sonusAtmExtAtmLayerEntry 1 }

sonusAtmExtAtmLayerSlotIndex OBJECT-TYPE
    SYNTAX          SonusSlotIndex
    ACCESS          not-accessible
    STATUS          mandatory
    DESCRIPTION     
            "The index for a Sonus slot."
    ::= { sonusAtmExtAtmLayerEntry 2 }

sonusAtmExtAtmLayerPortIndex OBJECT-TYPE
    SYNTAX          INTEGER
    ACCESS          not-accessible
    STATUS          mandatory
    DESCRIPTION     
            "The index for a logical ATM layer port."
    ::= { sonusAtmExtAtmLayerEntry 3 }

sonusAtmExtAtmLayerIfIndex OBJECT-TYPE
    SYNTAX          INTEGER
    ACCESS          read-only
    STATUS          mandatory
    DESCRIPTION     
            "The ifIndex at the ATM layer for this shelf, slot, and port."
    ::= { sonusAtmExtAtmLayerEntry 4 }

sonusAtmExtAtmLayerRowStatus OBJECT-TYPE
    SYNTAX          RowStatus
    ACCESS          read-write
    STATUS          mandatory
    DESCRIPTION     
            "This object is used to create, delete,
             or modify a row in this table."
    ::= { sonusAtmExtAtmLayerEntry 5 }

sonusAtmExtAal5LayerTable OBJECT-TYPE
    SYNTAX          SEQUENCE OF SonusAtmExtAal5LayerEntry
    ACCESS          not-accessible
    STATUS          mandatory
    DESCRIPTION     
            "The AAL5 layer table.  This table maps AAL5 layer ifIndex
             to a shelf, slot, and port."
    ::= { sonusAtmExtMIBObjects 4 }

sonusAtmExtAal5LayerEntry OBJECT-TYPE
    SYNTAX          SonusAtmExtAal5LayerEntry
    ACCESS          not-accessible
    STATUS          mandatory
    DESCRIPTION     
            "An entry in the AAL5 layer table. This entry 
             maps the ifIndex of the AAL5 layer to a shelf, slot
             and port.  A row is added to this table when a SONET
             port is created"
    INDEX           { sonusAtmExtAal5LayerShelfIndex, 
                      sonusAtmExtAal5LayerSlotIndex, 
                      sonusAtmExtAal5LayerPortIndex }
    ::= { sonusAtmExtAal5LayerTable 1 }

SonusAtmExtAal5LayerEntry ::=
    SEQUENCE {
        sonusAtmExtAal5LayerShelfIndex  SonusShelfIndex,
        sonusAtmExtAal5LayerSlotIndex   SonusSlotIndex,
        sonusAtmExtAal5LayerPortIndex   INTEGER,
        sonusAtmExtAal5LayerIfIndex     INTEGER,
        sonusAtmExtAal5LayerRowStatus   RowStatus
    }

sonusAtmExtAal5LayerShelfIndex OBJECT-TYPE
    SYNTAX          SonusShelfIndex
    ACCESS          not-accessible
    STATUS          mandatory
    DESCRIPTION     
            "The index for a Sonus shelf."
    ::= { sonusAtmExtAal5LayerEntry 1 }

sonusAtmExtAal5LayerSlotIndex OBJECT-TYPE
    SYNTAX          SonusSlotIndex
    ACCESS          not-accessible
    STATUS          mandatory
    DESCRIPTION     
            "The index for a Sonus slot."
    ::= { sonusAtmExtAal5LayerEntry 2 }

sonusAtmExtAal5LayerPortIndex OBJECT-TYPE
    SYNTAX          INTEGER
    ACCESS          not-accessible
    STATUS          mandatory
    DESCRIPTION     
            "The index for a logical AAL5 layer port."
    ::= { sonusAtmExtAal5LayerEntry 3 }

sonusAtmExtAal5LayerIfIndex OBJECT-TYPE
    SYNTAX          INTEGER
    ACCESS          read-only
    STATUS          mandatory
    DESCRIPTION     
            "The ifIndex at the AAL5 layer for this shelf, slot, and port."
    ::= { sonusAtmExtAal5LayerEntry 4 }

sonusAtmExtAal5LayerRowStatus OBJECT-TYPE
    SYNTAX          RowStatus
    ACCESS          read-write
    STATUS          mandatory
    DESCRIPTION     
            "This object is used to create, delete,
             or modify a row in this table."
    ::= { sonusAtmExtAal5LayerEntry 5 }

sonusAtmExtOamF5Table OBJECT-TYPE
    SYNTAX          SEQUENCE OF SonusAtmExtOamF5Entry
    ACCESS          not-accessible
    STATUS          mandatory
    DESCRIPTION     
            "A list of ATM OAM F5 entries."
    ::= { sonusAtmExtMIBObjects 5 }

sonusAtmExtOamF5Entry OBJECT-TYPE
    SYNTAX          SonusAtmExtOamF5Entry
    ACCESS          not-accessible
    STATUS          mandatory
    DESCRIPTION     
            "An entry of sonusAtmExtOamF5Table which is used to provide OAM feature for 
             Virtual circuit in this ATM interface. Three major OAM functions are 
             supported in this MIB entry. The first function is the Loopback 
             capability for this virtual circuit which includes both of End2end 
             Loopback and UNILoopback.  The second function is the OAM continuity 
             capability for this virtual circuit which uses Loopback cells to 
             transmit periodically. Transmit and recieve loopback cell statisitics
             can be used to determine if there is continuity. 
             The third function is basic fault management feature using 
             AIS/RDI cells to inform the upstream/downstream failure condition, 
             the counters are used to keep failure statistics."
    INDEX           { sonusAtmExtOamF5IfIndex, sonusAtmExtOamF5Vpi, 
                      sonusAtmExtOamF5Vci }
    ::= { sonusAtmExtOamF5Table 1 }

SonusAtmExtOamF5Entry ::=
    SEQUENCE {
        sonusAtmExtOamF5IfIndex         InterfaceIndex,
        sonusAtmExtOamF5Vpi             AtmVpIdentifier,
        sonusAtmExtOamF5Vci             AtmVcIdentifier,
        sonusAtmExtOamF5Enable          INTEGER,
        sonusAtmExtOamF5LoopbackType    INTEGER,
        sonusAtmExtOamF5LoopbackTimer   INTEGER,
        sonusAtmExtOamF5ReceiveEnd2EndLoopbackFailure             Counter,
        sonusAtmExtOamF5ReceiveUNILoopbackFailure         Counter,
        sonusAtmExtOamF5TransmitEnd2EndLoopback       Counter,
        sonusAtmExtOamF5TransmitUNILoopback   Counter,
        sonusAtmExtOamF5ReceiveEnd2EndLoopback      Counter,
        sonusAtmExtOamF5ReceiveUNILoopback  Counter,
        sonusAtmExtOamF5ReceiveEnd2EndAIS Counter,
        sonusAtmExtOamF5ReceiveEnd2EndRDI Counter,
        sonusAtmExtOamF5TransmitEnd2EndRDI  Counter
    }

sonusAtmExtOamF5IfIndex OBJECT-TYPE
    SYNTAX          InterfaceIndex
    ACCESS          not-accessible
    STATUS          mandatory
    DESCRIPTION     
            "The ifIndex of this entry."
    ::= { sonusAtmExtOamF5Entry 1 }

sonusAtmExtOamF5Vpi OBJECT-TYPE
    SYNTAX          AtmVpIdentifier
    ACCESS          not-accessible
    STATUS          mandatory
    DESCRIPTION     
            "The virtual path identifier of this entry"
    ::= { sonusAtmExtOamF5Entry 2 }

sonusAtmExtOamF5Vci OBJECT-TYPE
    SYNTAX          AtmVcIdentifier
    ACCESS          not-accessible
    STATUS          mandatory
    DESCRIPTION     
            "The virtual circuit identifier of this entry"
    ::= { sonusAtmExtOamF5Entry 3 }

sonusAtmExtOamF5Enable OBJECT-TYPE
    SYNTAX          INTEGER { enable(1), disable(2) }
    ACCESS          read-write
    STATUS          mandatory
    DESCRIPTION     
            "This objects is used to enable or disable the F5 OAM loopback cells.  Whenever
             this object is set to enable, at least one F5 OAM loopback cell will be sent.
             If the loopback timer is non-zero, then F5 OAM loopback cells will be
             sent continuosly at the interval defined by the loopback timer to perform
             a continuity test."
    DEFVAL          { disable }
    ::= { sonusAtmExtOamF5Entry 4 }

sonusAtmExtOamF5LoopbackType OBJECT-TYPE
    SYNTAX          INTEGER { end2end(1), uni(2) }
    ACCESS          read-write
    STATUS          mandatory
    DESCRIPTION     
            "This object is used to define the F5 OAM loopback type for this virtual 
             circuit.  Loopback cells may be sent to the local UNI or end to end."
    DEFVAL          { end2end }
    ::= { sonusAtmExtOamF5Entry 5 }

sonusAtmExtOamF5LoopbackTimer OBJECT-TYPE
    SYNTAX          INTEGER (0..20)
    ACCESS          read-write
    STATUS          mandatory
    DESCRIPTION     
            "This object is used to define the time between OAM F5 loopback cells.  If
             this object is set to zero, then a single F5 OAM cell will be sent every time
             the sonusAtmOamF5Enable object is set to enable.  If this obkect is non-zero, 
             then loopback cells will be sent continuously at the interval defined by this 
             object to perform a continuity test."
    DEFVAL          { 10 }
    ::= { sonusAtmExtOamF5Entry 6 }

sonusAtmExtOamF5ReceiveEnd2EndLoopbackFailure OBJECT-TYPE
    SYNTAX          Counter
    ACCESS          read-only
    STATUS          mandatory
    DESCRIPTION     
            "This is a counter object to collect the end2endLoopback failure 
             statistics for this virtual circuit.  It counts end to end F5 OAM loopback 
             cells received with an error."
    ::= { sonusAtmExtOamF5Entry 7 }

sonusAtmExtOamF5ReceiveUNILoopbackFailure OBJECT-TYPE
    SYNTAX          Counter
    ACCESS          read-only
    STATUS          mandatory
    DESCRIPTION     
            "This is a counter object to collect the UNILoopback failure 
             statistics for this virtual circuit.  It counts UNI F5 OAM loopback 
             cells received with an error."
    ::= { sonusAtmExtOamF5Entry 8 }

sonusAtmExtOamF5TransmitEnd2EndLoopback OBJECT-TYPE
    SYNTAX          Counter
    ACCESS          read-only
    STATUS          mandatory
    DESCRIPTION     
            "This is a counter object to collect the all transmitted 
             end2endLoopback statistics for this virtual circuit.  It counts 
             end to end F5 OAM loopback cells sent."
    ::= { sonusAtmExtOamF5Entry 9 }

sonusAtmExtOamF5TransmitUNILoopback OBJECT-TYPE
    SYNTAX          Counter
    ACCESS          read-only
    STATUS          mandatory
    DESCRIPTION     
            "This is a counter object to collect the all transmitted 
             UNILoopback statistics for this virtual circuit.  It counts 
             UNI F5 OAM loopback cells sent."
    ::= { sonusAtmExtOamF5Entry 10 }

sonusAtmExtOamF5ReceiveEnd2EndLoopback OBJECT-TYPE
    SYNTAX          Counter
    ACCESS          read-only
    STATUS          mandatory
    DESCRIPTION     
            "This is a counter object to collect the all received 
             end2endLoopback statistics for this virtual circuit.  It counts 
             good end to end F5 OAM loopback cells received."
    ::= { sonusAtmExtOamF5Entry 11 }

sonusAtmExtOamF5ReceiveUNILoopback OBJECT-TYPE
    SYNTAX          Counter
    ACCESS          read-only
    STATUS          mandatory
    DESCRIPTION     
            "This is a counter object to collect the all received UNILoopback 
             statistics for this virtual circuit.  It counts 
             good UNI F5 OAM loopback cells received."
    ::= { sonusAtmExtOamF5Entry 12 }

sonusAtmExtOamF5ReceiveEnd2EndAIS OBJECT-TYPE
    SYNTAX          Counter
    ACCESS          read-only
    STATUS          mandatory
    DESCRIPTION     
            "This is a counter object to collect the end2endAIS cells received 
             in this virtual circuit."
    ::= { sonusAtmExtOamF5Entry 13 }

sonusAtmExtOamF5ReceiveEnd2EndRDI OBJECT-TYPE
    SYNTAX          Counter
    ACCESS          read-only
    STATUS          mandatory
    DESCRIPTION     
            "This is a counter object to collect the end2endRDI cells received 
             in this virtual circuit."
    ::= { sonusAtmExtOamF5Entry 14 }

sonusAtmExtOamF5TransmitEnd2EndRDI OBJECT-TYPE
    SYNTAX          Counter
    ACCESS          read-only
    STATUS          mandatory
    DESCRIPTION     
            "This is a counter object to collect the end2endRDI cells transmit 
             in this virtual circuit."
    ::= { sonusAtmExtOamF5Entry 15 }

sonusAtmExtVclMIBNotifications OBJECT IDENTIFIER
    ::= { sonusAtmExtMIB 2 }

sonusAtmExtVclMIBNotificationsPrefix OBJECT IDENTIFIER
    ::= { sonusAtmExtVclMIBNotifications 0 }

sonusAtmExtVclMIBNotificationsObjects OBJECT IDENTIFIER
    ::= { sonusAtmExtVclMIBNotifications 1 }

sonusAtmExtVclInServiceNotification TRAP-TYPE
    ENTERPRISE      sonusAtmExtVclMIBNotifications
    VARIABLES       { sonusNifShelf, sonusNifSlot, sonusNifPort, 
                      sonusNifIndex, sonusAtmExtVclAdmnVpi, 
                      sonusAtmExtVclAdmnVci, sonusEventDescription, 
                      sonusEventClass, sonusEventLevel, sonusSequenceId, 
                      sonusEventTime }
--     STATUS          mandatory
    DESCRIPTION     
            "This trap indicates that an ATM VC is available to support
             call processing."
    ::= 1

sonusAtmExtVclOutOfServiceNotification TRAP-TYPE
    ENTERPRISE      sonusAtmExtVclMIBNotifications
    VARIABLES       { sonusNifShelf, sonusNifSlot, sonusNifPort, 
                      sonusNifIndex, sonusAtmExtVclAdmnVpi, 
                      sonusAtmExtVclAdmnVci, 
                      sonusAtmExtVclAdmnOutOfServiceReason, 
                      sonusEventDescription, sonusEventClass, 
                      sonusEventLevel, sonusSequenceId, sonusEventTime }
--     STATUS          mandatory
    DESCRIPTION     
            "This trap indicates that an ATM VC is no longer available to
             support call processing."
    ::= 2

sonusAtmExtVclEnabledNotification TRAP-TYPE
    ENTERPRISE      sonusAtmExtVclMIBNotifications
    VARIABLES       { sonusNifShelf, sonusNifSlot, sonusNifPort, 
                      sonusNifIndex, sonusAtmExtVclAdmnVpi, 
                      sonusAtmExtVclAdmnVci, sonusEventDescription, 
                      sonusEventClass, sonusEventLevel, sonusSequenceId, 
                      sonusEventTime }
--     STATUS          mandatory
    DESCRIPTION     
            "This trap indicates that an ATM VC's configuration is enabled."
    ::= 3

sonusAtmExtVclDisabledNotification TRAP-TYPE
    ENTERPRISE      sonusAtmExtVclMIBNotifications
    VARIABLES       { sonusNifShelf, sonusNifSlot, sonusNifPort, 
                      sonusNifIndex, sonusAtmExtVclAdmnVpi, 
                      sonusAtmExtVclAdmnVci, sonusEventDescription, 
                      sonusEventClass, sonusEventLevel, sonusSequenceId, 
                      sonusEventTime }
--     STATUS          mandatory
    DESCRIPTION     
            "This trap indicates that an ATM VC's configuration is disabled."
    ::= 4

sonusAtmExtVclDeletedNotification TRAP-TYPE
    ENTERPRISE      sonusAtmExtVclMIBNotifications
    VARIABLES       { sonusNifShelf, sonusNifSlot, sonusNifPort, 
                      sonusNifIndex, sonusAtmExtVclAdmnVpi, 
                      sonusAtmExtVclAdmnVci, sonusEventDescription, 
                      sonusEventClass, sonusEventLevel, sonusSequenceId, 
                      sonusEventTime }
--     STATUS          mandatory
    DESCRIPTION     
            "This trap indicates that an ATM VC's configuration is deleted."
    ::= 5

sonusAtmExtVclHighWatermarkNotification TRAP-TYPE
    ENTERPRISE      sonusAtmExtVclMIBNotifications
    VARIABLES       { sonusNifShelf, sonusNifSlot, sonusNifPort, 
                      sonusNifIndex, sonusAtmExtVclAdmnVpi, 
                      sonusAtmExtVclAdmnVci, sonusEventDescription, 
                      sonusEventClass, sonusEventLevel, sonusSequenceId, 
                      sonusEventTime }
--     STATUS          mandatory
    DESCRIPTION     
            "This trap indicates that an ATM VC's high watermark has been reached 
             the first time since the ATM VC's low watermark has beend reached."
    ::= 6

sonusAtmExtVclLowWatermarkNotification TRAP-TYPE
    ENTERPRISE      sonusAtmExtVclMIBNotifications
    VARIABLES       { sonusNifShelf, sonusNifSlot, sonusNifPort, 
                      sonusNifIndex, sonusAtmExtVclAdmnVpi, 
                      sonusAtmExtVclAdmnVci, sonusEventDescription, 
                      sonusEventClass, sonusEventLevel, sonusSequenceId, 
                      sonusEventTime }
--     STATUS          mandatory
    DESCRIPTION     
            "This trap indicates that an ATM VC's low watermark has been reached
             the first time since the ATM VC's high watermark has been reached."
    ::= 7

sonusAtmExtVclBwHighDeviationNotification TRAP-TYPE
    ENTERPRISE      sonusAtmExtVclMIBNotifications
    VARIABLES       { sonusNifShelf, sonusNifSlot, sonusNifPort, 
                      sonusNifIndex, sonusAtmExtVclAdmnVpi, 
                      sonusAtmExtVclAdmnVci, sonusEventDescription, 
                      sonusEventClass, sonusEventLevel, sonusSequenceId, 
                      sonusEventTime }
--     STATUS          mandatory
    DESCRIPTION     
            "This trap indicates that a VCL's actual bandwidth is greater than the 
             expected bandwidth plus deviation amount. This trap will be re-armed
             when the actual bandwdith dropped below the expected level. "
    ::= 8

sonusAtmExtVclBwLowDeviationNotification TRAP-TYPE
    ENTERPRISE      sonusAtmExtVclMIBNotifications
    VARIABLES       { sonusNifShelf, sonusNifSlot, sonusNifPort, 
                      sonusNifIndex, sonusAtmExtVclAdmnVpi, 
                      sonusAtmExtVclAdmnVci, sonusEventDescription, 
                      sonusEventClass, sonusEventLevel, sonusSequenceId, 
                      sonusEventTime }
--     STATUS          mandatory
    DESCRIPTION     
            "This trap indicates that a VCL's actual bandwidth is lower than the
             expected bandwidth minus 2 times the deviation amount.This trap will 
             be re-armed when the actual bandwdith reached the expected level."
    ::= 9

END -- end of module SONUS-ATM-EXTENSIONS-MIB.
