--
-- This SMIv1 module has been generated by smidump 0.2-cvs. Do not edit.
--

IFT-RAID-MIB DEFINITIONS ::= BEGIN

IMPORTS
    OBJECT-TYPE
        FROM RFC-1212
    TRAP-TYPE
        FROM RFC-1215
    enterprises
        FROM RFC1155-SMI;

infortrend OBJECT IDENTIFIER
    ::= { enterprises 1714 }

iftRaid OBJECT IDENTIFIER
    ::= { infortrend 1 }

iftMgm OBJECT IDENTIFIER
    ::= { iftRaid 2 }

iftNpc OBJECT IDENTIFIER
    ::= { iftMgm 3 }

iftSnmpTrap OBJECT IDENTIFIER
    ::= { iftNpc 1 }

iftEventText OBJECT-TYPE
    SYNTAX          OCTET STRING
    ACCESS          read-only
    STATUS          mandatory
    DESCRIPTION     
            "The description of the event"
    ::= { iftSnmpTrap 1 }

iftCtlrEventTrap TRAP-TYPE
    ENTERPRISE      infortrend
    VARIABLES       { iftEventText }
--     STATUS          mandatory
    DESCRIPTION     
            "There is a controller event occurred"
    ::= 1

END -- end of module IFT-RAID-MIB.
