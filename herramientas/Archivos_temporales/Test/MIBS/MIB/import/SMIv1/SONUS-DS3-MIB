--
-- This SMIv1 module has been generated by smidump 0.2-cvs. Do not edit.
--

SONUS-DS3-MIB DEFINITIONS ::= BEGIN

IMPORTS
    PerfCurrentCount
        FROM PerfHist-TC-MIB
    OBJECT-TYPE
        FROM RFC-1212
    TRAP-TYPE
        FROM RFC-1215
    Counter
        FROM RFC1155-SMI
    RowStatus, TruthValue
        FROM SNMPv2-TC
    sonusDs3Index, sonusEventClass, sonusEventDescription, 
    sonusEventLevel, sonusEventTime, sonusPortIndex, sonusSequenceId, 
    sonusShelfIndex, sonusSlotIndex
        FROM SONUS-COMMON-MIB
    sonusCircuitMIBs
        FROM SONUS-SMI
    SonusAdminAction, SonusAdminState, SonusName, SonusServiceState, 
    SonusShelfIndex, SonusSlotIndex
        FROM SONUS-TC;

sonusDsx3MIB OBJECT IDENTIFIER
    ::= { sonusCircuitMIBs 2 }

-- sonusDsx3MIB MODULE-IDENTITY
--     LAST-UPDATED    "200708150000Z"
--     ORGANIZATION    
--             "Sonus Networks, Inc."
--     CONTACT-INFO    
--             "   Customer Support    
--              Sonus Networks, Inc.
--              7 Technology Park Drive
--              Westford, MA 01886
--              USA
--              
--              Tel: 978-614-8100
--              Fax: 978-614-8609"
--     DESCRIPTION     
--             "The MIB Module DS3 management."
--     ::= { sonusCircuitMIBs 2 }


sonusDsx3MIBObjects OBJECT IDENTIFIER
    ::= { sonusDsx3MIB 1 }

sonusDsx3Admn OBJECT IDENTIFIER
    ::= { sonusDsx3MIBObjects 1 }

sonusDsx3AdmnNextIndex OBJECT IDENTIFIER
    ::= { sonusDsx3Admn 1 }

sonusDsx3AdmnTable OBJECT-TYPE
    SYNTAX          SEQUENCE OF SonusDsx3AdmnEntry
    ACCESS          not-accessible
    STATUS          mandatory
    DESCRIPTION     
            "Table of Sonus Enterprise Configurations for all DS3s"
    ::= { sonusDsx3Admn 2 }

sonusDsx3AdmnEntry OBJECT-TYPE
    SYNTAX          SonusDsx3AdmnEntry
    ACCESS          not-accessible
    STATUS          mandatory
    DESCRIPTION     
            "Entry in Table consisting of the all the Sonus Enterprise DS3 Configurations"
    INDEX           { sonusDsx3AdmnShelfIndex, sonusDsx3AdmnSlotIndex, 
                      sonusDsx3AdmnPortIndex, sonusDsx3AdmnDs3Index }
    ::= { sonusDsx3AdmnTable 1 }

SonusDsx3AdmnEntry ::=
    SEQUENCE {
        sonusDsx3AdmnRowStatus          RowStatus,
        sonusDsx3AdmnName               SonusName,
        sonusDsx3AdmnShelfIndex         SonusShelfIndex,
        sonusDsx3AdmnSlotIndex          SonusSlotIndex,
        sonusDsx3AdmnPortIndex          INTEGER,
        sonusDsx3AdmnDs3Index           INTEGER,
        sonusDsx3AdmnIfIndex            INTEGER,
        sonusDsx3AdmnState              SonusAdminState,
        sonusDsx3AdmnTimeout            INTEGER,
        sonusDsx3AdmnMode               SonusServiceState,
        sonusDsx3AdmnAction             SonusAdminAction,
        sonusDsx3AdmnAvailDs1s          OCTET STRING,
        sonusDsx3AdmnDs1ModeOverride    SonusAdminState,
        sonusDsx3AdmnInitCounters       SonusAdminState,
        sonusDsx3AdmnCircuitId          DisplayString,
        sonusDsx3AdmnPayloadMapping     INTEGER,
        sonusDsx3AdmnLCVThreshold       INTEGER,
        sonusDsx3AdmnLESThreshold       INTEGER,
        sonusDsx3AdmnLSESThreshold      INTEGER,
        sonusDsx3AdmnPCVThreshold       INTEGER,
        sonusDsx3AdmnPESThreshold       INTEGER,
        sonusDsx3AdmnPSESThreshold      INTEGER,
        sonusDsx3AdmnUASThreshold       INTEGER,
        sonusDsx3AdmnDayLCVThreshold    INTEGER,
        sonusDsx3AdmnDayLESThreshold    INTEGER,
        sonusDsx3AdmnDayLSESThreshold   INTEGER,
        sonusDsx3AdmnDayPCVThreshold    INTEGER,
        sonusDsx3AdmnDayPESThreshold    INTEGER,
        sonusDsx3AdmnDayPSESThreshold   INTEGER,
        sonusDsx3AdmnDayUASThreshold    INTEGER,
        sonusDsx3AdmnStatAction         INTEGER,
        sonusDsx3AdmnAlarmHierarchy     SonusAdminState,
        sonusDsx3AdmnLCVTcaFilter       SonusAdminState,
        sonusDsx3AdmnLESTcaFilter       SonusAdminState,
        sonusDsx3AdmnLSESTcaFilter      SonusAdminState,
        sonusDsx3AdmnPCVTcaFilter       SonusAdminState,
        sonusDsx3AdmnPESTcaFilter       SonusAdminState,
        sonusDsx3AdmnPSESTcaFilter      SonusAdminState,
        sonusDsx3AdmnUASTcaFilter       SonusAdminState
    }

sonusDsx3AdmnRowStatus OBJECT-TYPE
    SYNTAX          RowStatus
    ACCESS          read-write
    STATUS          mandatory
    DESCRIPTION     
            "DS3, Needed for SNMP"
    ::= { sonusDsx3AdmnEntry 1 }

sonusDsx3AdmnName OBJECT-TYPE
    SYNTAX          SonusName
    ACCESS          read-write
    STATUS          mandatory
    DESCRIPTION     
            "Name of this DS3"
    ::= { sonusDsx3AdmnEntry 2 }

sonusDsx3AdmnShelfIndex OBJECT-TYPE
    SYNTAX          SonusShelfIndex
    ACCESS          read-only
    STATUS          mandatory
    DESCRIPTION     
            "Shelf index for this table"
    ::= { sonusDsx3AdmnEntry 3 }

sonusDsx3AdmnSlotIndex OBJECT-TYPE
    SYNTAX          SonusSlotIndex
    ACCESS          read-only
    STATUS          mandatory
    DESCRIPTION     
            "Slot index for this table"
    ::= { sonusDsx3AdmnEntry 4 }

sonusDsx3AdmnPortIndex OBJECT-TYPE
    SYNTAX          INTEGER
    ACCESS          read-only
    STATUS          mandatory
    DESCRIPTION     
            "Port index for this table"
    ::= { sonusDsx3AdmnEntry 5 }

sonusDsx3AdmnDs3Index OBJECT-TYPE
    SYNTAX          INTEGER
    ACCESS          read-only
    STATUS          mandatory
    DESCRIPTION     
            "Ds3 Index into this table"
    ::= { sonusDsx3AdmnEntry 6 }

sonusDsx3AdmnIfIndex OBJECT-TYPE
    SYNTAX          INTEGER
    ACCESS          read-only
    STATUS          mandatory
    DESCRIPTION     
            "Ds3 If Index. Same as the If index of the standard table"
    ::= { sonusDsx3AdmnEntry 7 }

sonusDsx3AdmnState OBJECT-TYPE
    SYNTAX          SonusAdminState
    ACCESS          read-write
    STATUS          mandatory
    DESCRIPTION     
            "State of DS3, Enabled/Disabled"
    ::= { sonusDsx3AdmnEntry 8 }

sonusDsx3AdmnTimeout OBJECT-TYPE
    SYNTAX          INTEGER (0..1440)
    ACCESS          read-write
    STATUS          mandatory
    DESCRIPTION     
            "Max time in minutes before dryup takes place"
    DEFVAL          { 5 }
    ::= { sonusDsx3AdmnEntry 9 }

sonusDsx3AdmnMode OBJECT-TYPE
    SYNTAX          SonusServiceState
    ACCESS          read-write
    STATUS          mandatory
    DESCRIPTION     
            "DS3 is in service or out of service."
    DEFVAL          { outOfService }
    ::= { sonusDsx3AdmnEntry 10 }

sonusDsx3AdmnAction OBJECT-TYPE
    SYNTAX          SonusAdminAction
    ACCESS          read-write
    STATUS          mandatory
    DESCRIPTION     
            "Force out of service or wait for dryup"
    DEFVAL          { dryUp }
    ::= { sonusDsx3AdmnEntry 11 }

sonusDsx3AdmnAvailDs1s OBJECT-TYPE
    SYNTAX          OCTET STRING
--                       { ds1x1(0), ds1x2(1), ds1x3(2), ds1x4(3), 
--                         ds1x5(4), ds1x6(5), ds1x7(6), ds1x8(7), 
--                         ds1x9(8), ds1x10(9), ds1x11(10), ds1x12(11), 
--                         ds1x13(12), ds1x14(13), ds1x15(14), 
--                         ds1x16(15), ds1x17(16), ds1x18(17), 
--                         ds1x19(18), ds1x20(19), ds1x21(20), 
--                         ds1x22(21), ds1x23(22), ds1x24(23), 
--                         ds1x25(24), ds1x26(25), ds1x27(26), 
--                         ds1x28(27) }
    ACCESS          read-write
    STATUS          mandatory
    DESCRIPTION     
            "Bitstring map of Ds1s that are available on this DS3."
    ::= { sonusDsx3AdmnEntry 12 }

sonusDsx3AdmnDs1ModeOverride OBJECT-TYPE
    SYNTAX          SonusAdminState
    ACCESS          read-write
    STATUS          mandatory
    DESCRIPTION     
            "This flag controls whether the mode and state of the DS1's
             carried in the DS3 are modified when the mode and state of
             the DS3 is modified. If this flag is set to Enabled, the DS1
             state and mode are not changed when the DS3 mode and state
             are changed."
    DEFVAL          { disabled }
    ::= { sonusDsx3AdmnEntry 13 }

sonusDsx3AdmnInitCounters OBJECT-TYPE
    SYNTAX          SonusAdminState
    ACCESS          read-write
    STATUS          mandatory
    DESCRIPTION     
            "Used to initialize all counters. Once enabled clears all T3 counters."
    DEFVAL          { disabled }
    ::= { sonusDsx3AdmnEntry 14 }

sonusDsx3AdmnCircuitId OBJECT-TYPE
    SYNTAX          DisplayString (SIZE(1..23))
    ACCESS          read-write
    STATUS          mandatory
    DESCRIPTION     
            "The Circuit Id."
    ::= { sonusDsx3AdmnEntry 15 }

sonusDsx3AdmnPayloadMapping OBJECT-TYPE
    SYNTAX          INTEGER { notConfigured(1), t1(2), e1(3) }
    ACCESS          read-write
    STATUS          mandatory
    DESCRIPTION     
            "Specifies whether T1 or E1 payload is carried in DS3."
    DEFVAL          { notConfigured }
    ::= { sonusDsx3AdmnEntry 16 }

sonusDsx3AdmnLCVThreshold OBJECT-TYPE
    SYNTAX          INTEGER (1..16383)
    ACCESS          read-write
    STATUS          obsolete
    DESCRIPTION     
            "Line Code Violations threshold value for 15 minute interval. This is for near end.
             This object was obsoleted in Release 6.1."
    DEFVAL          { 387 }
    ::= { sonusDsx3AdmnEntry 17 }

sonusDsx3AdmnLESThreshold OBJECT-TYPE
    SYNTAX          INTEGER (1..900)
    ACCESS          read-write
    STATUS          obsolete
    DESCRIPTION     
            "Line Errored Seconds threshold value for 15 minute interval. This is for near end.
             This object was obsoleted in Release 6.1."
    DEFVAL          { 25 }
    ::= { sonusDsx3AdmnEntry 18 }

sonusDsx3AdmnLSESThreshold OBJECT-TYPE
    SYNTAX          INTEGER (1..900)
    ACCESS          read-write
    STATUS          obsolete
    DESCRIPTION     
            "Line Severely Errored Seconds threshold value for 15 minute interval. This is
             for near end.
             This object was obsoleted in Release 6.1."
    DEFVAL          { 4 }
    ::= { sonusDsx3AdmnEntry 19 }

sonusDsx3AdmnPCVThreshold OBJECT-TYPE
    SYNTAX          INTEGER (1..16383)
    ACCESS          read-write
    STATUS          obsolete
    DESCRIPTION     
            "Path Code Violations threshold value for 15 minute interval, for both
             P-bit and CP-bit. This is for near end.
             This object was obsoleted in Release 6.1."
    DEFVAL          { 382 }
    ::= { sonusDsx3AdmnEntry 20 }

sonusDsx3AdmnPESThreshold OBJECT-TYPE
    SYNTAX          INTEGER (1..900)
    ACCESS          read-write
    STATUS          obsolete
    DESCRIPTION     
            "Path Errored Seconds threshold value for 15 minute interval, for both
             P-bit and CP-bit. This is for near end.
             This object was obsoleted in Release 6.1."
    DEFVAL          { 25 }
    ::= { sonusDsx3AdmnEntry 21 }

sonusDsx3AdmnPSESThreshold OBJECT-TYPE
    SYNTAX          INTEGER (1..900)
    ACCESS          read-write
    STATUS          obsolete
    DESCRIPTION     
            "Path Severely Errored Seconds threshold value for 15 minute interval, for both
             P-bit and CP-bit. This is for near end.
             This object was obsoleted in Release 6.1."
    DEFVAL          { 4 }
    ::= { sonusDsx3AdmnEntry 22 }

sonusDsx3AdmnUASThreshold OBJECT-TYPE
    SYNTAX          INTEGER (1..900)
    ACCESS          read-write
    STATUS          obsolete
    DESCRIPTION     
            "Path Unavailable Seconds threshold value for 15 minute interval, for both
             P-bit and CP-bit. This is for near end.
             This object was obsoleted in Release 6.1."
    DEFVAL          { 10 }
    ::= { sonusDsx3AdmnEntry 23 }

sonusDsx3AdmnDayLCVThreshold OBJECT-TYPE
    SYNTAX          INTEGER (1..1048575)
    ACCESS          read-write
    STATUS          mandatory
    DESCRIPTION     
            "Line Code Violations threshold value for 24 hour interval.
             This object was obsoleted in Release 6.1."
    DEFVAL          { 3865 }
    ::= { sonusDsx3AdmnEntry 24 }

sonusDsx3AdmnDayLESThreshold OBJECT-TYPE
    SYNTAX          INTEGER (1..65535)
    ACCESS          read-write
    STATUS          obsolete
    DESCRIPTION     
            "Line Errored Seconds threshold value for 24 hour interval.
             This object was obsoleted in Release 6.1."
    DEFVAL          { 250 }
    ::= { sonusDsx3AdmnEntry 25 }

sonusDsx3AdmnDayLSESThreshold OBJECT-TYPE
    SYNTAX          INTEGER (1..65535)
    ACCESS          read-write
    STATUS          obsolete
    DESCRIPTION     
            "Line Severely Errored Seconds threshold value for 24 hour interval.
             This object was obsoleted in Release 6.1."
    DEFVAL          { 40 }
    ::= { sonusDsx3AdmnEntry 26 }

sonusDsx3AdmnDayPCVThreshold OBJECT-TYPE
    SYNTAX          INTEGER (1..65535)
    ACCESS          read-write
    STATUS          obsolete
    DESCRIPTION     
            "Path Code Violations threshold value for 24 hour interval, for both
             P-bit and CP-bit.
             This object was obsoleted in Release 6.1."
    DEFVAL          { 3820 }
    ::= { sonusDsx3AdmnEntry 27 }

sonusDsx3AdmnDayPESThreshold OBJECT-TYPE
    SYNTAX          INTEGER (1..65535)
    ACCESS          read-write
    STATUS          obsolete
    DESCRIPTION     
            "Path Errored Seconds threshold value for 24 hour interval, for both
             P-bit and CP-bit.
             This object was obsoleted in Release 6.1."
    DEFVAL          { 250 }
    ::= { sonusDsx3AdmnEntry 28 }

sonusDsx3AdmnDayPSESThreshold OBJECT-TYPE
    SYNTAX          INTEGER (1..65535)
    ACCESS          read-write
    STATUS          obsolete
    DESCRIPTION     
            "Path Severely Errored Seconds threshold value for 24 hour interval, for both
             P-bit and CP-bit.
             This object was obsoleted in Release 6.1."
    DEFVAL          { 40 }
    ::= { sonusDsx3AdmnEntry 29 }

sonusDsx3AdmnDayUASThreshold OBJECT-TYPE
    SYNTAX          INTEGER (1..65535)
    ACCESS          read-write
    STATUS          obsolete
    DESCRIPTION     
            "Path Unavailable Seconds threshold value for 24 hour interval, for both
             P-bit and CP-bit.
             This object was obsoleted in Release 6.1."
    DEFVAL          { 10 }
    ::= { sonusDsx3AdmnEntry 30 }

sonusDsx3AdmnStatAction OBJECT-TYPE
    SYNTAX          INTEGER { initLine15MinNearEnd(1), 
                        initPath15MinNearEnd(2), initPath15MinFarEnd(3), 
                        initLine24HourNearEnd(4), 
                        initPath24HourNearEnd(5), 
                        initPath24HourFarEnd(6) }
    ACCESS          read-write
    STATUS          mandatory
    DESCRIPTION     
            "Initialize Performance Monitoring Statistics."
    ::= { sonusDsx3AdmnEntry 31 }

sonusDsx3AdmnAlarmHierarchy OBJECT-TYPE
    SYNTAX          SonusAdminState
    ACCESS          read-write
    STATUS          mandatory
    DESCRIPTION     
            "Controls whether only the root-cause DS3 alarm is reported (via
             an event log and trap) and all DS1 interface alarms that result
             from the DS3 alarm are supressed. For example, if a  DS3 AIS alarm
             is detected, it will be reported, while the resulting DS1 AIS
             alarms will not be reported."
    DEFVAL          { enabled }
    ::= { sonusDsx3AdmnEntry 32 }

sonusDsx3AdmnLCVTcaFilter OBJECT-TYPE
    SYNTAX          SonusAdminState
    ACCESS          read-write
    STATUS          obsolete
    DESCRIPTION     
            "Controls whether a threshold Crossing Alert (TCA) is reported (via
             an event log and trap). Setting this object to Enabled will prevent
             the TCA from being reported (i.e will Filter the TCA report).
             This object was obsoleted in Release 6.1."
    DEFVAL          { disabled }
    ::= { sonusDsx3AdmnEntry 33 }

sonusDsx3AdmnLESTcaFilter OBJECT-TYPE
    SYNTAX          SonusAdminState
    ACCESS          read-write
    STATUS          obsolete
    DESCRIPTION     
            "Controls whether a threshold Crossing Alert (TCA) is reported (via
             an event log and trap). Setting this object to Enabled will prevent
             the TCA from being reported (i.e will Filter the TCA report).
             This object was obsoleted in Release 6.1."
    DEFVAL          { disabled }
    ::= { sonusDsx3AdmnEntry 34 }

sonusDsx3AdmnLSESTcaFilter OBJECT-TYPE
    SYNTAX          SonusAdminState
    ACCESS          read-write
    STATUS          obsolete
    DESCRIPTION     
            "Controls whether a threshold Crossing Alert (TCA) is reported (via
             an event log and trap). Setting this object to Enabled will prevent
             the TCA from being reported (i.e will Filter the TCA report).
             This object was obsoleted in Release 6.1."
    DEFVAL          { disabled }
    ::= { sonusDsx3AdmnEntry 35 }

sonusDsx3AdmnPCVTcaFilter OBJECT-TYPE
    SYNTAX          SonusAdminState
    ACCESS          read-write
    STATUS          obsolete
    DESCRIPTION     
            "Controls whether a threshold Crossing Alert (TCA) is reported (via
             an event log and trap). Setting this object to Enabled will prevent
             the TCA from being reported (i.e will Filter the TCA report).
             This object was obsoleted in Release 6.1."
    DEFVAL          { disabled }
    ::= { sonusDsx3AdmnEntry 36 }

sonusDsx3AdmnPESTcaFilter OBJECT-TYPE
    SYNTAX          SonusAdminState
    ACCESS          read-write
    STATUS          obsolete
    DESCRIPTION     
            "Controls whether a threshold Crossing Alert (TCA) is reported (via
             an event log and trap). Setting this object to Enabled will prevent
             the TCA from being reported (i.e will Filter the TCA report).
             This object was obsoleted in Release 6.1."
    DEFVAL          { disabled }
    ::= { sonusDsx3AdmnEntry 37 }

sonusDsx3AdmnPSESTcaFilter OBJECT-TYPE
    SYNTAX          SonusAdminState
    ACCESS          read-write
    STATUS          obsolete
    DESCRIPTION     
            "Controls whether a threshold Crossing Alert (TCA) is reported (via
             an event log and trap). Setting this object to Enabled will prevent
             the TCA from being reported (i.e will Filter the TCA report).
             This object was obsoleted in Release 6.1."
    DEFVAL          { disabled }
    ::= { sonusDsx3AdmnEntry 38 }

sonusDsx3AdmnUASTcaFilter OBJECT-TYPE
    SYNTAX          SonusAdminState
    ACCESS          read-write
    STATUS          obsolete
    DESCRIPTION     
            "Controls whether a threshold Crossing Alert (TCA) is reported (via
             an event log and trap). Setting this object to Enabled will prevent
             the TCA from being reported (i.e will Filter the TCA report).
             This object was obsoleted in Release 6.1."
    DEFVAL          { disabled }
    ::= { sonusDsx3AdmnEntry 39 }

sonusDsx3StatTable OBJECT-TYPE
    SYNTAX          SEQUENCE OF SonusDsx3StatEntry
    ACCESS          not-accessible
    STATUS          mandatory
    DESCRIPTION     
            "Table of Sonus Enterprise status for all DS3s"
    ::= { sonusDsx3MIBObjects 2 }

sonusDsx3StatEntry OBJECT-TYPE
    SYNTAX          SonusDsx3StatEntry
    ACCESS          not-accessible
    STATUS          mandatory
    DESCRIPTION     
            "Entry in Table consisting of the all the Sonus Enterprise DS3 Status"
    INDEX           { sonusDsx3StatShelfIndex, sonusDsx3StatSlotIndex, 
                      sonusDsx3StatPortIndex, sonusDsx3StatDs3Index }
    ::= { sonusDsx3StatTable 1 }

SonusDsx3StatEntry ::=
    SEQUENCE {
        sonusDsx3StatShelfIndex         SonusShelfIndex,
        sonusDsx3StatSlotIndex          SonusSlotIndex,
        sonusDsx3StatPortIndex          INTEGER,
        sonusDsx3StatDs3Index           INTEGER,
        sonusDsx3StatValidIntervals     INTEGER,
        sonusDsx3StatDs3LCV             Counter,
        sonusDsx3StatDs3FERR            Counter,
        sonusDsx3StatDs3EXZS            Counter,
        sonusDsx3StatDs3PERR            Counter,
        sonusDsx3StatDs3CPERR           Counter,
        sonusDsx3StatDs3FEBE            Counter,
        sonusDsx3StatDs3AIS             Counter,
        sonusDsx3StatDs3LOS             Counter,
        sonusDsx3StatLineStatStr        DisplayString,
        sonusDsx3StatLoopbackStr        DisplayString,
        sonusDsx3StatOperStatus         INTEGER,
        sonusDsx3StatDefectAIS          INTEGER,
        sonusDsx3StatDefectLOF          INTEGER,
        sonusDsx3StatDefectLOS          INTEGER,
        sonusDsx3StatDs3LOF             INTEGER,
        sonusDsx3StatValidDayIntervals  INTEGER,
        sonusDsx3StatDs3BPV             INTEGER,
        sonusDsx3StatAICApplication     INTEGER
    }

sonusDsx3StatShelfIndex OBJECT-TYPE
    SYNTAX          SonusShelfIndex
    ACCESS          read-only
    STATUS          mandatory
    DESCRIPTION     
            "Shelf index for this table"
    ::= { sonusDsx3StatEntry 1 }

sonusDsx3StatSlotIndex OBJECT-TYPE
    SYNTAX          SonusSlotIndex
    ACCESS          read-only
    STATUS          mandatory
    DESCRIPTION     
            "Slot index for this table"
    ::= { sonusDsx3StatEntry 2 }

sonusDsx3StatPortIndex OBJECT-TYPE
    SYNTAX          INTEGER
    ACCESS          read-only
    STATUS          mandatory
    DESCRIPTION     
            "Port index for this table"
    ::= { sonusDsx3StatEntry 3 }

sonusDsx3StatDs3Index OBJECT-TYPE
    SYNTAX          INTEGER
    ACCESS          read-only
    STATUS          mandatory
    DESCRIPTION     
            "Ds3 Index into this table"
    ::= { sonusDsx3StatEntry 4 }

sonusDsx3StatValidIntervals OBJECT-TYPE
    SYNTAX          INTEGER
    ACCESS          read-only
    STATUS          mandatory
    DESCRIPTION     
            "Number of intervals worth of Performance Data that is valid"
    ::= { sonusDsx3StatEntry 5 }

sonusDsx3StatDs3LCV OBJECT-TYPE
    SYNTAX          Counter
    ACCESS          read-only
    STATUS          mandatory
    DESCRIPTION     
            "Total number of line code violations"
    ::= { sonusDsx3StatEntry 6 }

sonusDsx3StatDs3FERR OBJECT-TYPE
    SYNTAX          Counter
    ACCESS          read-only
    STATUS          mandatory
    DESCRIPTION     
            "Total number of framing errors"
    ::= { sonusDsx3StatEntry 7 }

sonusDsx3StatDs3EXZS OBJECT-TYPE
    SYNTAX          Counter
    ACCESS          read-only
    STATUS          obsolete
    DESCRIPTION     
            "Total number of Excessive zeroes violations. This object was obsoleted in Release 7.0"
    ::= { sonusDsx3StatEntry 8 }

sonusDsx3StatDs3PERR OBJECT-TYPE
    SYNTAX          Counter
    ACCESS          read-only
    STATUS          mandatory
    DESCRIPTION     
            "Total number of parity errors"
    ::= { sonusDsx3StatEntry 9 }

sonusDsx3StatDs3CPERR OBJECT-TYPE
    SYNTAX          Counter
    ACCESS          read-only
    STATUS          mandatory
    DESCRIPTION     
            "Total number of C-Bit parity errors"
    ::= { sonusDsx3StatEntry 10 }

sonusDsx3StatDs3FEBE OBJECT-TYPE
    SYNTAX          Counter
    ACCESS          read-only
    STATUS          mandatory
    DESCRIPTION     
            "Total number of FEBE errors"
    ::= { sonusDsx3StatEntry 11 }

sonusDsx3StatDs3AIS OBJECT-TYPE
    SYNTAX          Counter
    ACCESS          read-only
    STATUS          mandatory
    DESCRIPTION     
            "Total number of AIS errors"
    ::= { sonusDsx3StatEntry 12 }

sonusDsx3StatDs3LOS OBJECT-TYPE
    SYNTAX          Counter
    ACCESS          read-only
    STATUS          mandatory
    DESCRIPTION     
            "Total number of Loss of signal errors"
    ::= { sonusDsx3StatEntry 13 }

sonusDsx3StatLineStatStr OBJECT-TYPE
    SYNTAX          DisplayString (SIZE(1..16))
    ACCESS          read-only
    STATUS          mandatory
    DESCRIPTION     
            "String display for DS3 line status"
    ::= { sonusDsx3StatEntry 14 }

sonusDsx3StatLoopbackStr OBJECT-TYPE
    SYNTAX          DisplayString (SIZE(1..32))
    ACCESS          read-only
    STATUS          mandatory
    DESCRIPTION     
            "String display for DS3 loopback status"
    ::= { sonusDsx3StatEntry 15 }

sonusDsx3StatOperStatus OBJECT-TYPE
    SYNTAX          INTEGER { up(1), down(2), dryingUp(3), remoteDown(4) }
    ACCESS          read-only
    STATUS          mandatory
    DESCRIPTION     
            "The actual status of the DS3 interface. Interface is 
             Up if it is administratively in service and there are no
             line failures or hardware failures. Interface is Down if
             it is administratively in service and there are line
             failures or hardware failures, or if it is administratively
             out of service. Interface is DryingUp if it is administratively
             out of service and is drying up (no new	calls, still carrying
             in-progress calls)."
    ::= { sonusDsx3StatEntry 16 }

sonusDsx3StatDefectAIS OBJECT-TYPE
    SYNTAX          INTEGER
    ACCESS          read-only
    STATUS          mandatory
    DESCRIPTION     
            "Total number of AIS defects"
    ::= { sonusDsx3StatEntry 17 }

sonusDsx3StatDefectLOF OBJECT-TYPE
    SYNTAX          INTEGER
    ACCESS          read-only
    STATUS          mandatory
    DESCRIPTION     
            "Total number of LOF defects"
    ::= { sonusDsx3StatEntry 18 }

sonusDsx3StatDefectLOS OBJECT-TYPE
    SYNTAX          INTEGER
    ACCESS          read-only
    STATUS          mandatory
    DESCRIPTION     
            "Total number of Loss of signal defects"
    ::= { sonusDsx3StatEntry 19 }

sonusDsx3StatDs3LOF OBJECT-TYPE
    SYNTAX          INTEGER
    ACCESS          read-only
    STATUS          mandatory
    DESCRIPTION     
            "Total number of LOF alarms"
    ::= { sonusDsx3StatEntry 20 }

sonusDsx3StatValidDayIntervals OBJECT-TYPE
    SYNTAX          INTEGER
    ACCESS          read-only
    STATUS          mandatory
    DESCRIPTION     
            "Number of intervals worth of day Performance Data that is valid"
    ::= { sonusDsx3StatEntry 21 }

sonusDsx3StatDs3BPV OBJECT-TYPE
    SYNTAX          INTEGER
    ACCESS          read-only
    STATUS          obsolete
    DESCRIPTION     
            "Total number of bipolar violations. This object was obsoleted in Release 7.0"
    ::= { sonusDsx3StatEntry 22 }

sonusDsx3StatAICApplication OBJECT-TYPE
    SYNTAX          INTEGER { cbit(1), m23(2), mismatch(3) }
    ACCESS          read-only
    STATUS          mandatory
    DESCRIPTION     
            "Indicates whether the near-end and far-end are configured for
             C-bit application, M23 application, or whether there is a
             mismatch between the near-end and far-end"
    ::= { sonusDsx3StatEntry 23 }

sonusDsx3CurrentTable OBJECT-TYPE
    SYNTAX          SEQUENCE OF SonusDsx3CurrentEntry
    ACCESS          not-accessible
    STATUS          mandatory
    DESCRIPTION     
            "The DS3 current table contains various statistics
             being collected for the near end current 15 minute
             interval."
    ::= { sonusDsx3MIBObjects 3 }

sonusDsx3CurrentEntry OBJECT-TYPE
    SYNTAX          SonusDsx3CurrentEntry
    ACCESS          not-accessible
    STATUS          mandatory
    DESCRIPTION     
            "An entry in the DS3 Current table."
    INDEX           { sonusDsx3CurrentShelfIndex, 
                      sonusDsx3CurrentSlotIndex, 
                      sonusDsx3CurrentPortIndex, 
                      sonusDsx3CurrentDs3Index }
    ::= { sonusDsx3CurrentTable 1 }

SonusDsx3CurrentEntry ::=
    SEQUENCE {
        sonusDsx3CurrentShelfIndex      SonusShelfIndex,
        sonusDsx3CurrentSlotIndex       SonusSlotIndex,
        sonusDsx3CurrentPortIndex       INTEGER,
        sonusDsx3CurrentDs3Index        INTEGER,
        sonusDsx3CurrentElapsedTime     INTEGER,
        sonusDsx3CurrentLCVs            PerfCurrentCount,
        sonusDsx3CurrentLESs            PerfCurrentCount,
        sonusDsx3CurrentLSESs           PerfCurrentCount,
        sonusDsx3CurrentCVPs            PerfCurrentCount,
        sonusDsx3CurrentCVCPs           PerfCurrentCount,
        sonusDsx3CurrentESPs            PerfCurrentCount,
        sonusDsx3CurrentESCPs           PerfCurrentCount,
        sonusDsx3CurrentSESPs           PerfCurrentCount,
        sonusDsx3CurrentSESCPs          PerfCurrentCount,
        sonusDsx3CurrentSASs            PerfCurrentCount,
        sonusDsx3CurrentUASPs           PerfCurrentCount,
        sonusDsx3CurrentUASCPs          PerfCurrentCount,
        sonusDsx3CurrentFC              INTEGER,
        sonusDsx3CurrentTcaLCV          TruthValue,
        sonusDsx3CurrentTcaLES          TruthValue,
        sonusDsx3CurrentTcaLSES         TruthValue,
        sonusDsx3CurrentTcaCVP          TruthValue,
        sonusDsx3CurrentTcaESP          TruthValue,
        sonusDsx3CurrentTcaSESP         TruthValue,
        sonusDsx3CurrentTcaUASP         TruthValue,
        sonusDsx3CurrentTcaCVCP         TruthValue,
        sonusDsx3CurrentTcaESCP         TruthValue,
        sonusDsx3CurrentTcaSESCP        TruthValue,
        sonusDsx3CurrentTcaUASCP        TruthValue,
        sonusDsx3CurrentMinorTcaLCV     TruthValue,
        sonusDsx3CurrentMinorTcaLES     TruthValue,
        sonusDsx3CurrentMinorTcaLSES    TruthValue,
        sonusDsx3CurrentMinorTcaCVP     TruthValue,
        sonusDsx3CurrentMinorTcaESP     TruthValue,
        sonusDsx3CurrentMinorTcaSESP    TruthValue,
        sonusDsx3CurrentMinorTcaUASP    TruthValue,
        sonusDsx3CurrentMinorTcaCVCP    TruthValue,
        sonusDsx3CurrentMinorTcaESCP    TruthValue,
        sonusDsx3CurrentMinorTcaSESCP   TruthValue,
        sonusDsx3CurrentMinorTcaUASCP   TruthValue,
        sonusDsx3CurrentMajorTcaLCV     TruthValue,
        sonusDsx3CurrentMajorTcaLES     TruthValue,
        sonusDsx3CurrentMajorTcaLSES    TruthValue,
        sonusDsx3CurrentMajorTcaCVP     TruthValue,
        sonusDsx3CurrentMajorTcaESP     TruthValue,
        sonusDsx3CurrentMajorTcaSESP    TruthValue,
        sonusDsx3CurrentMajorTcaUASP    TruthValue,
        sonusDsx3CurrentMajorTcaCVCP    TruthValue,
        sonusDsx3CurrentMajorTcaESCP    TruthValue,
        sonusDsx3CurrentMajorTcaSESCP   TruthValue,
        sonusDsx3CurrentMajorTcaUASCP   TruthValue,
        sonusDsx3CurrentCriticalTcaLCV  TruthValue,
        sonusDsx3CurrentCriticalTcaLES  TruthValue,
        sonusDsx3CurrentCriticalTcaLSES TruthValue,
        sonusDsx3CurrentCriticalTcaCVP  TruthValue,
        sonusDsx3CurrentCriticalTcaESP  TruthValue,
        sonusDsx3CurrentCriticalTcaSESP TruthValue,
        sonusDsx3CurrentCriticalTcaUASP TruthValue,
        sonusDsx3CurrentCriticalTcaCVCP TruthValue,
        sonusDsx3CurrentCriticalTcaESCP TruthValue,
        sonusDsx3CurrentCriticalTcaSESCP TruthValue,
        sonusDsx3CurrentCriticalTcaUASCP TruthValue
    }

sonusDsx3CurrentShelfIndex OBJECT-TYPE
    SYNTAX          SonusShelfIndex
    ACCESS          read-only
    STATUS          mandatory
    DESCRIPTION     
            "Shelf index into this table"
    ::= { sonusDsx3CurrentEntry 1 }

sonusDsx3CurrentSlotIndex OBJECT-TYPE
    SYNTAX          SonusSlotIndex
    ACCESS          read-only
    STATUS          mandatory
    DESCRIPTION     
            "Slot index into this table"
    ::= { sonusDsx3CurrentEntry 2 }

sonusDsx3CurrentPortIndex OBJECT-TYPE
    SYNTAX          INTEGER
    ACCESS          read-only
    STATUS          mandatory
    DESCRIPTION     
            "Port Index into this table"
    ::= { sonusDsx3CurrentEntry 3 }

sonusDsx3CurrentDs3Index OBJECT-TYPE
    SYNTAX          INTEGER
    ACCESS          read-only
    STATUS          mandatory
    DESCRIPTION     
            "Ds3 Index into this table"
    ::= { sonusDsx3CurrentEntry 4 }

sonusDsx3CurrentElapsedTime OBJECT-TYPE
    SYNTAX          INTEGER
    ACCESS          read-only
    STATUS          mandatory
    DESCRIPTION     
            "Elapsed time in the current period"
    ::= { sonusDsx3CurrentEntry 5 }

sonusDsx3CurrentLCVs OBJECT-TYPE
    SYNTAX          PerfCurrentCount
    ACCESS          read-only
    STATUS          mandatory
    DESCRIPTION     
            "The number of Line Code Violations (LCVs)."
    ::= { sonusDsx3CurrentEntry 6 }

sonusDsx3CurrentLESs OBJECT-TYPE
    SYNTAX          PerfCurrentCount
    ACCESS          read-only
    STATUS          mandatory
    DESCRIPTION     
            "The number of Line Errored Seconds."
    ::= { sonusDsx3CurrentEntry 7 }

sonusDsx3CurrentLSESs OBJECT-TYPE
    SYNTAX          PerfCurrentCount
    ACCESS          read-only
    STATUS          mandatory
    DESCRIPTION     
            "The number of Line Severely Errored Seconds."
    ::= { sonusDsx3CurrentEntry 8 }

sonusDsx3CurrentCVPs OBJECT-TYPE
    SYNTAX          PerfCurrentCount
    ACCESS          read-only
    STATUS          mandatory
    DESCRIPTION     
            "The number of Path P-bit Coding Violations."
    ::= { sonusDsx3CurrentEntry 9 }

sonusDsx3CurrentCVCPs OBJECT-TYPE
    SYNTAX          PerfCurrentCount
    ACCESS          read-only
    STATUS          mandatory
    DESCRIPTION     
            "The number of Path CP-bit Coding Violations."
    ::= { sonusDsx3CurrentEntry 10 }

sonusDsx3CurrentESPs OBJECT-TYPE
    SYNTAX          PerfCurrentCount
    ACCESS          read-only
    STATUS          mandatory
    DESCRIPTION     
            "The number of Path P-bit Errored Seconds."
    ::= { sonusDsx3CurrentEntry 11 }

sonusDsx3CurrentESCPs OBJECT-TYPE
    SYNTAX          PerfCurrentCount
    ACCESS          read-only
    STATUS          mandatory
    DESCRIPTION     
            "The number of Path CP-bit Errored Seconds."
    ::= { sonusDsx3CurrentEntry 12 }

sonusDsx3CurrentSESPs OBJECT-TYPE
    SYNTAX          PerfCurrentCount
    ACCESS          read-only
    STATUS          mandatory
    DESCRIPTION     
            "The number of Path P-bit Severely Errored Seconds."
    ::= { sonusDsx3CurrentEntry 13 }

sonusDsx3CurrentSESCPs OBJECT-TYPE
    SYNTAX          PerfCurrentCount
    ACCESS          read-only
    STATUS          mandatory
    DESCRIPTION     
            "The number of Path CP-bit Severely Errored Seconds."
    ::= { sonusDsx3CurrentEntry 14 }

sonusDsx3CurrentSASs OBJECT-TYPE
    SYNTAX          PerfCurrentCount
    ACCESS          read-only
    STATUS          mandatory
    DESCRIPTION     
            "The number of SEF/AIS Errored Seconds."
    ::= { sonusDsx3CurrentEntry 15 }

sonusDsx3CurrentUASPs OBJECT-TYPE
    SYNTAX          PerfCurrentCount
    ACCESS          read-only
    STATUS          mandatory
    DESCRIPTION     
            "The number of P-bit Unavailable Seconds."
    ::= { sonusDsx3CurrentEntry 16 }

sonusDsx3CurrentUASCPs OBJECT-TYPE
    SYNTAX          PerfCurrentCount
    ACCESS          read-only
    STATUS          mandatory
    DESCRIPTION     
            "The number of CP-bit Unavailable Seconds."
    ::= { sonusDsx3CurrentEntry 17 }

sonusDsx3CurrentFC OBJECT-TYPE
    SYNTAX          INTEGER
    ACCESS          read-only
    STATUS          mandatory
    DESCRIPTION     
            "The number of LOF or AIS failures detected."
    ::= { sonusDsx3CurrentEntry 18 }

sonusDsx3CurrentTcaLCV OBJECT-TYPE
    SYNTAX          TruthValue
    ACCESS          read-only
    STATUS          obsolete
    DESCRIPTION     
            "Indicates status of threshold crossing for Line Code Violations."
    ::= { sonusDsx3CurrentEntry 19 }

sonusDsx3CurrentTcaLES OBJECT-TYPE
    SYNTAX          TruthValue
    ACCESS          read-only
    STATUS          obsolete
    DESCRIPTION     
            "Indicates status of threshold crossing for Line Errored Seconds."
    ::= { sonusDsx3CurrentEntry 20 }

sonusDsx3CurrentTcaLSES OBJECT-TYPE
    SYNTAX          TruthValue
    ACCESS          read-only
    STATUS          obsolete
    DESCRIPTION     
            "Indicates status of threshold crossing for Line Severely Errored Seconds."
    ::= { sonusDsx3CurrentEntry 21 }

sonusDsx3CurrentTcaCVP OBJECT-TYPE
    SYNTAX          TruthValue
    ACCESS          read-only
    STATUS          obsolete
    DESCRIPTION     
            "Indicates status of threshold crossing for P-bit Code Violations."
    ::= { sonusDsx3CurrentEntry 22 }

sonusDsx3CurrentTcaESP OBJECT-TYPE
    SYNTAX          TruthValue
    ACCESS          read-only
    STATUS          obsolete
    DESCRIPTION     
            "Indicates status of threshold crossing for P-bit Errored Seconds."
    ::= { sonusDsx3CurrentEntry 23 }

sonusDsx3CurrentTcaSESP OBJECT-TYPE
    SYNTAX          TruthValue
    ACCESS          read-only
    STATUS          obsolete
    DESCRIPTION     
            "Indicates status of threshold crossing for P-bit Severely Errored Seconds."
    ::= { sonusDsx3CurrentEntry 24 }

sonusDsx3CurrentTcaUASP OBJECT-TYPE
    SYNTAX          TruthValue
    ACCESS          read-only
    STATUS          obsolete
    DESCRIPTION     
            "Indicates status of threshold crossing for P-bit Unavailable Seconds."
    ::= { sonusDsx3CurrentEntry 25 }

sonusDsx3CurrentTcaCVCP OBJECT-TYPE
    SYNTAX          TruthValue
    ACCESS          read-only
    STATUS          obsolete
    DESCRIPTION     
            "Indicates status of threshold crossing for CP-bit Code Violations."
    ::= { sonusDsx3CurrentEntry 26 }

sonusDsx3CurrentTcaESCP OBJECT-TYPE
    SYNTAX          TruthValue
    ACCESS          read-only
    STATUS          obsolete
    DESCRIPTION     
            "Indicates status of threshold crossing for CP-bit Errored Seconds."
    ::= { sonusDsx3CurrentEntry 27 }

sonusDsx3CurrentTcaSESCP OBJECT-TYPE
    SYNTAX          TruthValue
    ACCESS          read-only
    STATUS          obsolete
    DESCRIPTION     
            "Indicates status of threshold crossing for CP-bit Severely Errored Seconds."
    ::= { sonusDsx3CurrentEntry 28 }

sonusDsx3CurrentTcaUASCP OBJECT-TYPE
    SYNTAX          TruthValue
    ACCESS          read-only
    STATUS          obsolete
    DESCRIPTION     
            "Indicates status of threshold crossing for CP-bit Unavailable Seconds."
    ::= { sonusDsx3CurrentEntry 29 }

sonusDsx3CurrentMinorTcaLCV OBJECT-TYPE
    SYNTAX          TruthValue
    ACCESS          read-only
    STATUS          mandatory
    DESCRIPTION     
            "Indicates status of Minor threshold crossing for Line Code Violations."
    ::= { sonusDsx3CurrentEntry 30 }

sonusDsx3CurrentMinorTcaLES OBJECT-TYPE
    SYNTAX          TruthValue
    ACCESS          read-only
    STATUS          mandatory
    DESCRIPTION     
            "Indicates status of Minor threshold crossing for Line Errored Seconds."
    ::= { sonusDsx3CurrentEntry 31 }

sonusDsx3CurrentMinorTcaLSES OBJECT-TYPE
    SYNTAX          TruthValue
    ACCESS          read-only
    STATUS          mandatory
    DESCRIPTION     
            "Indicates status of Minor threshold crossing for Line Severely Errored Seconds."
    ::= { sonusDsx3CurrentEntry 32 }

sonusDsx3CurrentMinorTcaCVP OBJECT-TYPE
    SYNTAX          TruthValue
    ACCESS          read-only
    STATUS          mandatory
    DESCRIPTION     
            "Indicates status of Minor threshold crossing for P-bit Code Violations."
    ::= { sonusDsx3CurrentEntry 33 }

sonusDsx3CurrentMinorTcaESP OBJECT-TYPE
    SYNTAX          TruthValue
    ACCESS          read-only
    STATUS          mandatory
    DESCRIPTION     
            "Indicates status of Minor threshold crossing for P-bit Errored Seconds."
    ::= { sonusDsx3CurrentEntry 34 }

sonusDsx3CurrentMinorTcaSESP OBJECT-TYPE
    SYNTAX          TruthValue
    ACCESS          read-only
    STATUS          mandatory
    DESCRIPTION     
            "Indicates status of Minor threshold crossing for P-bit Severely Errored Seconds."
    ::= { sonusDsx3CurrentEntry 35 }

sonusDsx3CurrentMinorTcaUASP OBJECT-TYPE
    SYNTAX          TruthValue
    ACCESS          read-only
    STATUS          mandatory
    DESCRIPTION     
            "Indicates status of Minor threshold crossing for P-bit Unavailable Seconds."
    ::= { sonusDsx3CurrentEntry 36 }

sonusDsx3CurrentMinorTcaCVCP OBJECT-TYPE
    SYNTAX          TruthValue
    ACCESS          read-only
    STATUS          mandatory
    DESCRIPTION     
            "Indicates status of Minor threshold crossing for CP-bit Code Violations."
    ::= { sonusDsx3CurrentEntry 37 }

sonusDsx3CurrentMinorTcaESCP OBJECT-TYPE
    SYNTAX          TruthValue
    ACCESS          read-only
    STATUS          mandatory
    DESCRIPTION     
            "Indicates status of Minor threshold crossing for CP-bit Errored Seconds."
    ::= { sonusDsx3CurrentEntry 38 }

sonusDsx3CurrentMinorTcaSESCP OBJECT-TYPE
    SYNTAX          TruthValue
    ACCESS          read-only
    STATUS          mandatory
    DESCRIPTION     
            "Indicates status of Minor threshold crossing for CP-bit Severely Errored Seconds."
    ::= { sonusDsx3CurrentEntry 39 }

sonusDsx3CurrentMinorTcaUASCP OBJECT-TYPE
    SYNTAX          TruthValue
    ACCESS          read-only
    STATUS          mandatory
    DESCRIPTION     
            "Indicates status of Minor threshold crossing for CP-bit Unavailable Seconds."
    ::= { sonusDsx3CurrentEntry 40 }

sonusDsx3CurrentMajorTcaLCV OBJECT-TYPE
    SYNTAX          TruthValue
    ACCESS          read-only
    STATUS          mandatory
    DESCRIPTION     
            "Indicates status of Major threshold crossing for Line Code Violations."
    ::= { sonusDsx3CurrentEntry 41 }

sonusDsx3CurrentMajorTcaLES OBJECT-TYPE
    SYNTAX          TruthValue
    ACCESS          read-only
    STATUS          mandatory
    DESCRIPTION     
            "Indicates status of Major threshold crossing for Line Errored Seconds."
    ::= { sonusDsx3CurrentEntry 42 }

sonusDsx3CurrentMajorTcaLSES OBJECT-TYPE
    SYNTAX          TruthValue
    ACCESS          read-only
    STATUS          mandatory
    DESCRIPTION     
            "Indicates status of Major threshold crossing for Line Severely Errored Seconds."
    ::= { sonusDsx3CurrentEntry 43 }

sonusDsx3CurrentMajorTcaCVP OBJECT-TYPE
    SYNTAX          TruthValue
    ACCESS          read-only
    STATUS          mandatory
    DESCRIPTION     
            "Indicates status of Major threshold crossing for P-bit Code Violations."
    ::= { sonusDsx3CurrentEntry 44 }

sonusDsx3CurrentMajorTcaESP OBJECT-TYPE
    SYNTAX          TruthValue
    ACCESS          read-only
    STATUS          mandatory
    DESCRIPTION     
            "Indicates status of Major threshold crossing for P-bit Errored Seconds."
    ::= { sonusDsx3CurrentEntry 45 }

sonusDsx3CurrentMajorTcaSESP OBJECT-TYPE
    SYNTAX          TruthValue
    ACCESS          read-only
    STATUS          mandatory
    DESCRIPTION     
            "Indicates status of Major threshold crossing for P-bit Severely Errored Seconds."
    ::= { sonusDsx3CurrentEntry 46 }

sonusDsx3CurrentMajorTcaUASP OBJECT-TYPE
    SYNTAX          TruthValue
    ACCESS          read-only
    STATUS          mandatory
    DESCRIPTION     
            "Indicates status of Major threshold crossing for P-bit Unavailable Seconds."
    ::= { sonusDsx3CurrentEntry 47 }

sonusDsx3CurrentMajorTcaCVCP OBJECT-TYPE
    SYNTAX          TruthValue
    ACCESS          read-only
    STATUS          mandatory
    DESCRIPTION     
            "Indicates status of Major threshold crossing for CP-bit Code Violations."
    ::= { sonusDsx3CurrentEntry 48 }

sonusDsx3CurrentMajorTcaESCP OBJECT-TYPE
    SYNTAX          TruthValue
    ACCESS          read-only
    STATUS          mandatory
    DESCRIPTION     
            "Indicates status of Major threshold crossing for CP-bit Errored Seconds."
    ::= { sonusDsx3CurrentEntry 49 }

sonusDsx3CurrentMajorTcaSESCP OBJECT-TYPE
    SYNTAX          TruthValue
    ACCESS          read-only
    STATUS          mandatory
    DESCRIPTION     
            "Indicates status of Major threshold crossing for CP-bit Severely Errored Seconds."
    ::= { sonusDsx3CurrentEntry 50 }

sonusDsx3CurrentMajorTcaUASCP OBJECT-TYPE
    SYNTAX          TruthValue
    ACCESS          read-only
    STATUS          mandatory
    DESCRIPTION     
            "Indicates status of Major threshold crossing for CP-bit Unavailable Seconds."
    ::= { sonusDsx3CurrentEntry 51 }

sonusDsx3CurrentCriticalTcaLCV OBJECT-TYPE
    SYNTAX          TruthValue
    ACCESS          read-only
    STATUS          mandatory
    DESCRIPTION     
            "Indicates status of Critical threshold crossing for Line Code Violations."
    ::= { sonusDsx3CurrentEntry 52 }

sonusDsx3CurrentCriticalTcaLES OBJECT-TYPE
    SYNTAX          TruthValue
    ACCESS          read-only
    STATUS          mandatory
    DESCRIPTION     
            "Indicates status of Critical threshold crossing for Line Errored Seconds."
    ::= { sonusDsx3CurrentEntry 53 }

sonusDsx3CurrentCriticalTcaLSES OBJECT-TYPE
    SYNTAX          TruthValue
    ACCESS          read-only
    STATUS          mandatory
    DESCRIPTION     
            "Indicates status of Critical threshold crossing for Line Severely Errored Seconds."
    ::= { sonusDsx3CurrentEntry 54 }

sonusDsx3CurrentCriticalTcaCVP OBJECT-TYPE
    SYNTAX          TruthValue
    ACCESS          read-only
    STATUS          mandatory
    DESCRIPTION     
            "Indicates status of Critical threshold crossing for P-bit Code Violations."
    ::= { sonusDsx3CurrentEntry 55 }

sonusDsx3CurrentCriticalTcaESP OBJECT-TYPE
    SYNTAX          TruthValue
    ACCESS          read-only
    STATUS          mandatory
    DESCRIPTION     
            "Indicates status of Critical threshold crossing for P-bit Errored Seconds."
    ::= { sonusDsx3CurrentEntry 56 }

sonusDsx3CurrentCriticalTcaSESP OBJECT-TYPE
    SYNTAX          TruthValue
    ACCESS          read-only
    STATUS          mandatory
    DESCRIPTION     
            "Indicates status of Critical threshold crossing for P-bit Severely Errored Seconds."
    ::= { sonusDsx3CurrentEntry 57 }

sonusDsx3CurrentCriticalTcaUASP OBJECT-TYPE
    SYNTAX          TruthValue
    ACCESS          read-only
    STATUS          mandatory
    DESCRIPTION     
            "Indicates status of Critical threshold crossing for P-bit Unavailable Seconds."
    ::= { sonusDsx3CurrentEntry 58 }

sonusDsx3CurrentCriticalTcaCVCP OBJECT-TYPE
    SYNTAX          TruthValue
    ACCESS          read-only
    STATUS          mandatory
    DESCRIPTION     
            "Indicates status of Critical threshold crossing for CP-bit Code Violations."
    ::= { sonusDsx3CurrentEntry 59 }

sonusDsx3CurrentCriticalTcaESCP OBJECT-TYPE
    SYNTAX          TruthValue
    ACCESS          read-only
    STATUS          mandatory
    DESCRIPTION     
            "Indicates status of Critical threshold crossing for CP-bit Errored Seconds."
    ::= { sonusDsx3CurrentEntry 60 }

sonusDsx3CurrentCriticalTcaSESCP OBJECT-TYPE
    SYNTAX          TruthValue
    ACCESS          read-only
    STATUS          mandatory
    DESCRIPTION     
            "Indicates status of Critical threshold crossing for CP-bit Severely Errored Seconds."
    ::= { sonusDsx3CurrentEntry 61 }

sonusDsx3CurrentCriticalTcaUASCP OBJECT-TYPE
    SYNTAX          TruthValue
    ACCESS          read-only
    STATUS          mandatory
    DESCRIPTION     
            "Indicates status of Critical threshold crossing for CP-bit Unavailable Seconds."
    ::= { sonusDsx3CurrentEntry 62 }

sonusDsx3FarEndCurrentTable OBJECT-TYPE
    SYNTAX          SEQUENCE OF SonusDsx3FarEndCurrentEntry
    ACCESS          not-accessible
    STATUS          mandatory
    DESCRIPTION     
            "The DS3 current table contains various statistics
             being collected for the far end current 15 minute
             interval."
    ::= { sonusDsx3MIBObjects 4 }

sonusDsx3FarEndCurrentEntry OBJECT-TYPE
    SYNTAX          SonusDsx3FarEndCurrentEntry
    ACCESS          not-accessible
    STATUS          mandatory
    DESCRIPTION     
            "An entry in the DS3 Current table."
    INDEX           { sonusDsx3FarEndCurrentShelfIndex, 
                      sonusDsx3FarEndCurrentSlotIndex, 
                      sonusDsx3FarEndCurrentPortIndex, 
                      sonusDsx3FarEndCurrentDs3Index }
    ::= { sonusDsx3FarEndCurrentTable 1 }

SonusDsx3FarEndCurrentEntry ::=
    SEQUENCE {
        sonusDsx3FarEndCurrentShelfIndex SonusShelfIndex,
        sonusDsx3FarEndCurrentSlotIndex SonusSlotIndex,
        sonusDsx3FarEndCurrentPortIndex INTEGER,
        sonusDsx3FarEndCurrentDs3Index  INTEGER,
        sonusDsx3FarEndCurrentElapsedTime INTEGER,
        sonusDsx3FarEndCurrentCVCPs     PerfCurrentCount,
        sonusDsx3FarEndCurrentESCPs     PerfCurrentCount,
        sonusDsx3FarEndCurrentSESCPs    PerfCurrentCount,
        sonusDsx3FarEndCurrentSASCPs    PerfCurrentCount,
        sonusDsx3FarEndCurrentUASCPs    PerfCurrentCount,
        sonusDsx3FarEndCurrentFCCP      INTEGER,
        sonusDsx3FarEndCurrentTcaCVCP   TruthValue,
        sonusDsx3FarEndCurrentTcaESCP   TruthValue,
        sonusDsx3FarEndCurrentTcaSESCP  TruthValue,
        sonusDsx3FarEndCurrentTcaUASCP  TruthValue,
        sonusDsx3FarEndCurrentMinorTcaCVCP  TruthValue,
        sonusDsx3FarEndCurrentMinorTcaESCP  TruthValue,
        sonusDsx3FarEndCurrentMinorTcaSESCP   TruthValue,
        sonusDsx3FarEndCurrentMinorTcaUASCP   TruthValue,
        sonusDsx3FarEndCurrentMajorTcaCVCP  TruthValue,
        sonusDsx3FarEndCurrentMajorTcaESCP  TruthValue,
        sonusDsx3FarEndCurrentMajorTcaSESCP   TruthValue,
        sonusDsx3FarEndCurrentMajorTcaUASCP   TruthValue,
        sonusDsx3FarEndCurrentCriticalTcaCVCP     TruthValue,
        sonusDsx3FarEndCurrentCriticalTcaESCP     TruthValue,
        sonusDsx3FarEndCurrentCriticalTcaSESCP      TruthValue,
        sonusDsx3FarEndCurrentCriticalTcaUASCP      TruthValue
    }

sonusDsx3FarEndCurrentShelfIndex OBJECT-TYPE
    SYNTAX          SonusShelfIndex
    ACCESS          read-only
    STATUS          mandatory
    DESCRIPTION     
            "Shelf index into this table"
    ::= { sonusDsx3FarEndCurrentEntry 1 }

sonusDsx3FarEndCurrentSlotIndex OBJECT-TYPE
    SYNTAX          SonusSlotIndex
    ACCESS          read-only
    STATUS          mandatory
    DESCRIPTION     
            "Slot index into this table"
    ::= { sonusDsx3FarEndCurrentEntry 2 }

sonusDsx3FarEndCurrentPortIndex OBJECT-TYPE
    SYNTAX          INTEGER
    ACCESS          read-only
    STATUS          mandatory
    DESCRIPTION     
            "Port Index into this table"
    ::= { sonusDsx3FarEndCurrentEntry 3 }

sonusDsx3FarEndCurrentDs3Index OBJECT-TYPE
    SYNTAX          INTEGER
    ACCESS          read-only
    STATUS          mandatory
    DESCRIPTION     
            "Ds3 Index into this table"
    ::= { sonusDsx3FarEndCurrentEntry 4 }

sonusDsx3FarEndCurrentElapsedTime OBJECT-TYPE
    SYNTAX          INTEGER
    ACCESS          read-only
    STATUS          mandatory
    DESCRIPTION     
            "Elapsed time in the current period"
    ::= { sonusDsx3FarEndCurrentEntry 5 }

sonusDsx3FarEndCurrentCVCPs OBJECT-TYPE
    SYNTAX          PerfCurrentCount
    ACCESS          read-only
    STATUS          mandatory
    DESCRIPTION     
            "The number of Path CP-bit Coding Violations."
    ::= { sonusDsx3FarEndCurrentEntry 6 }

sonusDsx3FarEndCurrentESCPs OBJECT-TYPE
    SYNTAX          PerfCurrentCount
    ACCESS          read-only
    STATUS          mandatory
    DESCRIPTION     
            "The number of Path CP-bit Errored Seconds."
    ::= { sonusDsx3FarEndCurrentEntry 7 }

sonusDsx3FarEndCurrentSESCPs OBJECT-TYPE
    SYNTAX          PerfCurrentCount
    ACCESS          read-only
    STATUS          mandatory
    DESCRIPTION     
            "The number of Path CP-bit Severely Errored Seconds."
    ::= { sonusDsx3FarEndCurrentEntry 8 }

sonusDsx3FarEndCurrentSASCPs OBJECT-TYPE
    SYNTAX          PerfCurrentCount
    ACCESS          read-only
    STATUS          mandatory
    DESCRIPTION     
            "The number of SEF/AIS Errored Seconds."
    ::= { sonusDsx3FarEndCurrentEntry 9 }

sonusDsx3FarEndCurrentUASCPs OBJECT-TYPE
    SYNTAX          PerfCurrentCount
    ACCESS          read-only
    STATUS          mandatory
    DESCRIPTION     
            "The number of CP-bit Unavailable Seconds."
    ::= { sonusDsx3FarEndCurrentEntry 10 }

sonusDsx3FarEndCurrentFCCP OBJECT-TYPE
    SYNTAX          INTEGER
    ACCESS          read-only
    STATUS          mandatory
    DESCRIPTION     
            "The number of RAI failures detected."
    ::= { sonusDsx3FarEndCurrentEntry 11 }

sonusDsx3FarEndCurrentTcaCVCP OBJECT-TYPE
    SYNTAX          TruthValue
    ACCESS          read-only
    STATUS          obsolete
    DESCRIPTION     
            "Indicates status of threshold crossing for CP-bit Code Violations."
    ::= { sonusDsx3FarEndCurrentEntry 12 }

sonusDsx3FarEndCurrentTcaESCP OBJECT-TYPE
    SYNTAX          TruthValue
    ACCESS          read-only
    STATUS          obsolete
    DESCRIPTION     
            "Indicates status of threshold crossing for CP-bit Errored Seconds."
    ::= { sonusDsx3FarEndCurrentEntry 13 }

sonusDsx3FarEndCurrentTcaSESCP OBJECT-TYPE
    SYNTAX          TruthValue
    ACCESS          read-only
    STATUS          obsolete
    DESCRIPTION     
            "Indicates status of threshold crossing for CP-bit Severely Errored Seconds."
    ::= { sonusDsx3FarEndCurrentEntry 14 }

sonusDsx3FarEndCurrentTcaUASCP OBJECT-TYPE
    SYNTAX          TruthValue
    ACCESS          read-only
    STATUS          obsolete
    DESCRIPTION     
            "Indicates status of threshold crossing for CP-bit Unavailable Seconds."
    ::= { sonusDsx3FarEndCurrentEntry 15 }

sonusDsx3FarEndCurrentMinorTcaCVCP OBJECT-TYPE
    SYNTAX          TruthValue
    ACCESS          read-only
    STATUS          mandatory
    DESCRIPTION     
            "Indicates status of Minor threshold crossing for CP-bit Code Violations."
    ::= { sonusDsx3FarEndCurrentEntry 16 }

sonusDsx3FarEndCurrentMinorTcaESCP OBJECT-TYPE
    SYNTAX          TruthValue
    ACCESS          read-only
    STATUS          mandatory
    DESCRIPTION     
            "Indicates status of Minor threshold crossing for CP-bit Errored Seconds."
    ::= { sonusDsx3FarEndCurrentEntry 17 }

sonusDsx3FarEndCurrentMinorTcaSESCP OBJECT-TYPE
    SYNTAX          TruthValue
    ACCESS          read-only
    STATUS          mandatory
    DESCRIPTION     
            "Indicates status of Minor threshold crossing for CP-bit Severely Errored Seconds."
    ::= { sonusDsx3FarEndCurrentEntry 18 }

sonusDsx3FarEndCurrentMinorTcaUASCP OBJECT-TYPE
    SYNTAX          TruthValue
    ACCESS          read-only
    STATUS          mandatory
    DESCRIPTION     
            "Indicates status of Minor threshold crossing for CP-bit Unavailable Seconds."
    ::= { sonusDsx3FarEndCurrentEntry 19 }

sonusDsx3FarEndCurrentMajorTcaCVCP OBJECT-TYPE
    SYNTAX          TruthValue
    ACCESS          read-only
    STATUS          mandatory
    DESCRIPTION     
            "Indicates status of Major threshold crossing for CP-bit Code Violations."
    ::= { sonusDsx3FarEndCurrentEntry 20 }

sonusDsx3FarEndCurrentMajorTcaESCP OBJECT-TYPE
    SYNTAX          TruthValue
    ACCESS          read-only
    STATUS          mandatory
    DESCRIPTION     
            "Indicates status of Major threshold crossing for CP-bit Errored Seconds."
    ::= { sonusDsx3FarEndCurrentEntry 21 }

sonusDsx3FarEndCurrentMajorTcaSESCP OBJECT-TYPE
    SYNTAX          TruthValue
    ACCESS          read-only
    STATUS          mandatory
    DESCRIPTION     
            "Indicates status of Major threshold crossing for CP-bit Severely Errored Seconds."
    ::= { sonusDsx3FarEndCurrentEntry 22 }

sonusDsx3FarEndCurrentMajorTcaUASCP OBJECT-TYPE
    SYNTAX          TruthValue
    ACCESS          read-only
    STATUS          mandatory
    DESCRIPTION     
            "Indicates status of Major threshold crossing for CP-bit Unavailable Seconds."
    ::= { sonusDsx3FarEndCurrentEntry 23 }

sonusDsx3FarEndCurrentCriticalTcaCVCP OBJECT-TYPE
    SYNTAX          TruthValue
    ACCESS          read-only
    STATUS          mandatory
    DESCRIPTION     
            "Indicates status of Critical threshold crossing for CP-bit Code Violations."
    ::= { sonusDsx3FarEndCurrentEntry 24 }

sonusDsx3FarEndCurrentCriticalTcaESCP OBJECT-TYPE
    SYNTAX          TruthValue
    ACCESS          read-only
    STATUS          mandatory
    DESCRIPTION     
            "Indicates status of Critical threshold crossing for CP-bit Errored Seconds."
    ::= { sonusDsx3FarEndCurrentEntry 25 }

sonusDsx3FarEndCurrentCriticalTcaSESCP OBJECT-TYPE
    SYNTAX          TruthValue
    ACCESS          read-only
    STATUS          mandatory
    DESCRIPTION     
            "Indicates status of Critical threshold crossing for CP-bit Severely Errored Seconds."
    ::= { sonusDsx3FarEndCurrentEntry 26 }

sonusDsx3FarEndCurrentCriticalTcaUASCP OBJECT-TYPE
    SYNTAX          TruthValue
    ACCESS          read-only
    STATUS          mandatory
    DESCRIPTION     
            "Indicates status of Critical threshold crossing for CP-bit Unavailable Seconds."
    ::= { sonusDsx3FarEndCurrentEntry 27 }

sonusDsx3IntervalTable OBJECT-TYPE
    SYNTAX          SEQUENCE OF SonusDsx3IntervalEntry
    ACCESS          not-accessible
    STATUS          mandatory
    DESCRIPTION     
            "The DS3 Interval Table contains various
             near end statistics collected by each DS3 interface
             over the previous 24 hours of operation."
    ::= { sonusDsx3MIBObjects 5 }

sonusDsx3IntervalEntry OBJECT-TYPE
    SYNTAX          SonusDsx3IntervalEntry
    ACCESS          not-accessible
    STATUS          mandatory
    DESCRIPTION     
            "An entry in the DS3 Interval table."
    INDEX           { sonusDsx3IntervalShelfIndex, 
                      sonusDsx3IntervalSlotIndex, 
                      sonusDsx3IntervalPortIndex, 
                      sonusDsx3IntervalDs3Index, sonusDsx3IntervalNumber }
    ::= { sonusDsx3IntervalTable 1 }

SonusDsx3IntervalEntry ::=
    SEQUENCE {
        sonusDsx3IntervalShelfIndex     SonusShelfIndex,
        sonusDsx3IntervalSlotIndex      SonusSlotIndex,
        sonusDsx3IntervalPortIndex      INTEGER,
        sonusDsx3IntervalDs3Index       INTEGER,
        sonusDsx3IntervalNumber         INTEGER,
        sonusDsx3IntervalLCVs           PerfCurrentCount,
        sonusDsx3IntervalLESs           PerfCurrentCount,
        sonusDsx3IntervalLSESs          PerfCurrentCount,
        sonusDsx3IntervalCVPs           PerfCurrentCount,
        sonusDsx3IntervalCVCPs          PerfCurrentCount,
        sonusDsx3IntervalESPs           PerfCurrentCount,
        sonusDsx3IntervalESCPs          PerfCurrentCount,
        sonusDsx3IntervalSESPs          PerfCurrentCount,
        sonusDsx3IntervalSESCPs         PerfCurrentCount,
        sonusDsx3IntervalSASs           PerfCurrentCount,
        sonusDsx3IntervalUASPs          PerfCurrentCount,
        sonusDsx3IntervalUASCPs         PerfCurrentCount,
        sonusDsx3IntervalLineIDF        TruthValue,
        sonusDsx3IntervalPathIDF        TruthValue,
        sonusDsx3IntervalFC             INTEGER
    }

sonusDsx3IntervalShelfIndex OBJECT-TYPE
    SYNTAX          SonusShelfIndex
    ACCESS          read-only
    STATUS          mandatory
    DESCRIPTION     
            "Shelf index into this table"
    ::= { sonusDsx3IntervalEntry 1 }

sonusDsx3IntervalSlotIndex OBJECT-TYPE
    SYNTAX          SonusSlotIndex
    ACCESS          read-only
    STATUS          mandatory
    DESCRIPTION     
            "Slot index into this table"
    ::= { sonusDsx3IntervalEntry 2 }

sonusDsx3IntervalPortIndex OBJECT-TYPE
    SYNTAX          INTEGER
    ACCESS          read-only
    STATUS          mandatory
    DESCRIPTION     
            "Port Index into this table"
    ::= { sonusDsx3IntervalEntry 3 }

sonusDsx3IntervalDs3Index OBJECT-TYPE
    SYNTAX          INTEGER
    ACCESS          read-only
    STATUS          mandatory
    DESCRIPTION     
            "Ds3 Index into this table"
    ::= { sonusDsx3IntervalEntry 4 }

sonusDsx3IntervalNumber OBJECT-TYPE
    SYNTAX          INTEGER (1..32)
    ACCESS          read-only
    STATUS          mandatory
    DESCRIPTION     
            "A number between 1 and 32, where 1 is the most
             recently completed 15 minute interval."
    ::= { sonusDsx3IntervalEntry 5 }

sonusDsx3IntervalLCVs OBJECT-TYPE
    SYNTAX          PerfCurrentCount
    ACCESS          read-only
    STATUS          mandatory
    DESCRIPTION     
            "The number of Line Code Violations (LCVs)."
    ::= { sonusDsx3IntervalEntry 6 }

sonusDsx3IntervalLESs OBJECT-TYPE
    SYNTAX          PerfCurrentCount
    ACCESS          read-only
    STATUS          mandatory
    DESCRIPTION     
            "The number of Line Errored Seconds."
    ::= { sonusDsx3IntervalEntry 7 }

sonusDsx3IntervalLSESs OBJECT-TYPE
    SYNTAX          PerfCurrentCount
    ACCESS          read-only
    STATUS          mandatory
    DESCRIPTION     
            "The number of Line Severely Errored Seconds."
    ::= { sonusDsx3IntervalEntry 8 }

sonusDsx3IntervalCVPs OBJECT-TYPE
    SYNTAX          PerfCurrentCount
    ACCESS          read-only
    STATUS          mandatory
    DESCRIPTION     
            "The number of Path P-bit Coding Violations."
    ::= { sonusDsx3IntervalEntry 9 }

sonusDsx3IntervalCVCPs OBJECT-TYPE
    SYNTAX          PerfCurrentCount
    ACCESS          read-only
    STATUS          mandatory
    DESCRIPTION     
            "The number of Path CP-bit Coding Violations."
    ::= { sonusDsx3IntervalEntry 10 }

sonusDsx3IntervalESPs OBJECT-TYPE
    SYNTAX          PerfCurrentCount
    ACCESS          read-only
    STATUS          mandatory
    DESCRIPTION     
            "The number of Path P-bit Errored Seconds."
    ::= { sonusDsx3IntervalEntry 11 }

sonusDsx3IntervalESCPs OBJECT-TYPE
    SYNTAX          PerfCurrentCount
    ACCESS          read-only
    STATUS          mandatory
    DESCRIPTION     
            "The number of Path CP-bit Errored Seconds."
    ::= { sonusDsx3IntervalEntry 12 }

sonusDsx3IntervalSESPs OBJECT-TYPE
    SYNTAX          PerfCurrentCount
    ACCESS          read-only
    STATUS          mandatory
    DESCRIPTION     
            "The number of Path P-bit Severely Errored Seconds."
    ::= { sonusDsx3IntervalEntry 13 }

sonusDsx3IntervalSESCPs OBJECT-TYPE
    SYNTAX          PerfCurrentCount
    ACCESS          read-only
    STATUS          mandatory
    DESCRIPTION     
            "The number of Path CP-bit Severely Errored Seconds."
    ::= { sonusDsx3IntervalEntry 14 }

sonusDsx3IntervalSASs OBJECT-TYPE
    SYNTAX          PerfCurrentCount
    ACCESS          read-only
    STATUS          mandatory
    DESCRIPTION     
            "The number of SEF/AIS Errored Seconds."
    ::= { sonusDsx3IntervalEntry 15 }

sonusDsx3IntervalUASPs OBJECT-TYPE
    SYNTAX          PerfCurrentCount
    ACCESS          read-only
    STATUS          mandatory
    DESCRIPTION     
            "The number of P-bit Unavailable Seconds."
    ::= { sonusDsx3IntervalEntry 16 }

sonusDsx3IntervalUASCPs OBJECT-TYPE
    SYNTAX          PerfCurrentCount
    ACCESS          read-only
    STATUS          mandatory
    DESCRIPTION     
            "The number of CP-bit Unavailable Seconds."
    ::= { sonusDsx3IntervalEntry 17 }

sonusDsx3IntervalLineIDF OBJECT-TYPE
    SYNTAX          TruthValue
    ACCESS          read-only
    STATUS          mandatory
    DESCRIPTION     
            "This variable indicates if the Line data for this
             interval is valid."
    ::= { sonusDsx3IntervalEntry 18 }

sonusDsx3IntervalPathIDF OBJECT-TYPE
    SYNTAX          TruthValue
    ACCESS          read-only
    STATUS          mandatory
    DESCRIPTION     
            "This variable indicates if the Path data for this
             interval is valid."
    ::= { sonusDsx3IntervalEntry 19 }

sonusDsx3IntervalFC OBJECT-TYPE
    SYNTAX          INTEGER
    ACCESS          read-only
    STATUS          mandatory
    DESCRIPTION     
            "The number of LOF or AIS failures detected."
    ::= { sonusDsx3IntervalEntry 20 }

sonusDsx3FarEndIntervalTable OBJECT-TYPE
    SYNTAX          SEQUENCE OF SonusDsx3FarEndIntervalEntry
    ACCESS          not-accessible
    STATUS          mandatory
    DESCRIPTION     
            "The DS3 Interval Table contains various
             far end statistics collected by each DS3 interface
             over the previous 24 hours of operation."
    ::= { sonusDsx3MIBObjects 6 }

sonusDsx3FarEndIntervalEntry OBJECT-TYPE
    SYNTAX          SonusDsx3FarEndIntervalEntry
    ACCESS          not-accessible
    STATUS          mandatory
    DESCRIPTION     
            "An entry in the DS3 Far End Interval table."
    INDEX           { sonusDsx3FarEndIntervalShelfIndex, 
                      sonusDsx3FarEndIntervalSlotIndex, 
                      sonusDsx3FarEndIntervalPortIndex, 
                      sonusDsx3FarEndIntervalDs3Index, 
                      sonusDsx3FarEndIntervalNumber }
    ::= { sonusDsx3FarEndIntervalTable 1 }

SonusDsx3FarEndIntervalEntry ::=
    SEQUENCE {
        sonusDsx3FarEndIntervalShelfIndex SonusShelfIndex,
        sonusDsx3FarEndIntervalSlotIndex SonusSlotIndex,
        sonusDsx3FarEndIntervalPortIndex INTEGER,
        sonusDsx3FarEndIntervalDs3Index INTEGER,
        sonusDsx3FarEndIntervalNumber   INTEGER,
        sonusDsx3FarEndIntervalCVCPs    PerfCurrentCount,
        sonusDsx3FarEndIntervalESCPs    PerfCurrentCount,
        sonusDsx3FarEndIntervalSESCPs   PerfCurrentCount,
        sonusDsx3FarEndIntervalSASCPs   PerfCurrentCount,
        sonusDsx3FarEndIntervalUASCPs   PerfCurrentCount,
        sonusDsx3FarEndIntervalPathIDF  TruthValue,
        sonusDsx3FarEndIntervalFCCP     INTEGER
    }

sonusDsx3FarEndIntervalShelfIndex OBJECT-TYPE
    SYNTAX          SonusShelfIndex
    ACCESS          read-only
    STATUS          mandatory
    DESCRIPTION     
            "Shelf index into this table"
    ::= { sonusDsx3FarEndIntervalEntry 1 }

sonusDsx3FarEndIntervalSlotIndex OBJECT-TYPE
    SYNTAX          SonusSlotIndex
    ACCESS          read-only
    STATUS          mandatory
    DESCRIPTION     
            "Slot index into this table"
    ::= { sonusDsx3FarEndIntervalEntry 2 }

sonusDsx3FarEndIntervalPortIndex OBJECT-TYPE
    SYNTAX          INTEGER
    ACCESS          read-only
    STATUS          mandatory
    DESCRIPTION     
            "Port Index into this table"
    ::= { sonusDsx3FarEndIntervalEntry 3 }

sonusDsx3FarEndIntervalDs3Index OBJECT-TYPE
    SYNTAX          INTEGER
    ACCESS          read-only
    STATUS          mandatory
    DESCRIPTION     
            "Ds3 Index into this table"
    ::= { sonusDsx3FarEndIntervalEntry 4 }

sonusDsx3FarEndIntervalNumber OBJECT-TYPE
    SYNTAX          INTEGER (1..32)
    ACCESS          read-only
    STATUS          mandatory
    DESCRIPTION     
            "A number between 1 and 32, where 1 is the most
             recently completed 15 minute interval."
    ::= { sonusDsx3FarEndIntervalEntry 5 }

sonusDsx3FarEndIntervalCVCPs OBJECT-TYPE
    SYNTAX          PerfCurrentCount
    ACCESS          read-only
    STATUS          mandatory
    DESCRIPTION     
            "The number of Path CP-bit Coding Violations."
    ::= { sonusDsx3FarEndIntervalEntry 6 }

sonusDsx3FarEndIntervalESCPs OBJECT-TYPE
    SYNTAX          PerfCurrentCount
    ACCESS          read-only
    STATUS          mandatory
    DESCRIPTION     
            "The number of Path CP-bit Errored Seconds."
    ::= { sonusDsx3FarEndIntervalEntry 7 }

sonusDsx3FarEndIntervalSESCPs OBJECT-TYPE
    SYNTAX          PerfCurrentCount
    ACCESS          read-only
    STATUS          mandatory
    DESCRIPTION     
            "The number of Path CP-bit Severely Errored Seconds."
    ::= { sonusDsx3FarEndIntervalEntry 8 }

sonusDsx3FarEndIntervalSASCPs OBJECT-TYPE
    SYNTAX          PerfCurrentCount
    ACCESS          read-only
    STATUS          mandatory
    DESCRIPTION     
            "The number of SEF/AIS Errored Seconds."
    ::= { sonusDsx3FarEndIntervalEntry 9 }

sonusDsx3FarEndIntervalUASCPs OBJECT-TYPE
    SYNTAX          PerfCurrentCount
    ACCESS          read-only
    STATUS          mandatory
    DESCRIPTION     
            "The number of CP-bit Unavailable Seconds."
    ::= { sonusDsx3FarEndIntervalEntry 10 }

sonusDsx3FarEndIntervalPathIDF OBJECT-TYPE
    SYNTAX          TruthValue
    ACCESS          read-only
    STATUS          mandatory
    DESCRIPTION     
            "This variable indicates if the Path data for this
             interval is valid."
    ::= { sonusDsx3FarEndIntervalEntry 11 }

sonusDsx3FarEndIntervalFCCP OBJECT-TYPE
    SYNTAX          INTEGER
    ACCESS          read-only
    STATUS          mandatory
    DESCRIPTION     
            "The number of RAI failures detected."
    ::= { sonusDsx3FarEndIntervalEntry 12 }

sonusDsx3CurrentDayTable OBJECT-TYPE
    SYNTAX          SEQUENCE OF SonusDsx3CurrentDayEntry
    ACCESS          not-accessible
    STATUS          mandatory
    DESCRIPTION     
            "The DS3 current table contains various statistics
             being collected for the near end current 15 minute
             interval."
    ::= { sonusDsx3MIBObjects 7 }

sonusDsx3CurrentDayEntry OBJECT-TYPE
    SYNTAX          SonusDsx3CurrentDayEntry
    ACCESS          not-accessible
    STATUS          mandatory
    DESCRIPTION     
            "An entry in the DS3 Current Day table."
    INDEX           { sonusDsx3CurrentDayShelfIndex, 
                      sonusDsx3CurrentDaySlotIndex, 
                      sonusDsx3CurrentDayPortIndex, 
                      sonusDsx3CurrentDayDs3Index }
    ::= { sonusDsx3CurrentDayTable 1 }

SonusDsx3CurrentDayEntry ::=
    SEQUENCE {
        sonusDsx3CurrentDayShelfIndex   SonusShelfIndex,
        sonusDsx3CurrentDaySlotIndex    SonusSlotIndex,
        sonusDsx3CurrentDayPortIndex    INTEGER,
        sonusDsx3CurrentDayDs3Index     INTEGER,
        sonusDsx3CurrentDayElapsedTime  INTEGER,
        sonusDsx3CurrentDayLCVs         PerfCurrentCount,
        sonusDsx3CurrentDayLESs         PerfCurrentCount,
        sonusDsx3CurrentDayLSESs        PerfCurrentCount,
        sonusDsx3CurrentDayCVPs         PerfCurrentCount,
        sonusDsx3CurrentDayCVCPs        PerfCurrentCount,
        sonusDsx3CurrentDayESPs         PerfCurrentCount,
        sonusDsx3CurrentDayESCPs        PerfCurrentCount,
        sonusDsx3CurrentDaySESPs        PerfCurrentCount,
        sonusDsx3CurrentDaySESCPs       PerfCurrentCount,
        sonusDsx3CurrentDaySASs         PerfCurrentCount,
        sonusDsx3CurrentDayUASPs        PerfCurrentCount,
        sonusDsx3CurrentDayUASCPs       PerfCurrentCount,
        sonusDsx3CurrentDayFC           INTEGER,
        sonusDsx3CurrentDayTcaLCV       TruthValue,
        sonusDsx3CurrentDayTcaLES       TruthValue,
        sonusDsx3CurrentDayTcaLSES      TruthValue,
        sonusDsx3CurrentDayTcaCVP       TruthValue,
        sonusDsx3CurrentDayTcaESP       TruthValue,
        sonusDsx3CurrentDayTcaSESP      TruthValue,
        sonusDsx3CurrentDayTcaUASP      TruthValue,
        sonusDsx3CurrentDayTcaCVCP      TruthValue,
        sonusDsx3CurrentDayTcaESCP      TruthValue,
        sonusDsx3CurrentDayTcaSESCP     TruthValue,
        sonusDsx3CurrentDayTcaUASCP     TruthValue,
        sonusDsx3CurrentDayMinorTcaLCV  TruthValue,
        sonusDsx3CurrentDayMinorTcaLES  TruthValue,
        sonusDsx3CurrentDayMinorTcaLSES TruthValue,
        sonusDsx3CurrentDayMinorTcaCVP  TruthValue,
        sonusDsx3CurrentDayMinorTcaESP  TruthValue,
        sonusDsx3CurrentDayMinorTcaSESP TruthValue,
        sonusDsx3CurrentDayMinorTcaUASP TruthValue,
        sonusDsx3CurrentDayMinorTcaCVCP TruthValue,
        sonusDsx3CurrentDayMinorTcaESCP TruthValue,
        sonusDsx3CurrentDayMinorTcaSESCP TruthValue,
        sonusDsx3CurrentDayMinorTcaUASCP TruthValue,
        sonusDsx3CurrentDayMajorTcaLCV  TruthValue,
        sonusDsx3CurrentDayMajorTcaLES  TruthValue,
        sonusDsx3CurrentDayMajorTcaLSES TruthValue,
        sonusDsx3CurrentDayMajorTcaCVP  TruthValue,
        sonusDsx3CurrentDayMajorTcaESP  TruthValue,
        sonusDsx3CurrentDayMajorTcaSESP TruthValue,
        sonusDsx3CurrentDayMajorTcaUASP TruthValue,
        sonusDsx3CurrentDayMajorTcaCVCP TruthValue,
        sonusDsx3CurrentDayMajorTcaESCP TruthValue,
        sonusDsx3CurrentDayMajorTcaSESCP TruthValue,
        sonusDsx3CurrentDayMajorTcaUASCP TruthValue,
        sonusDsx3CurrentDayCriticalTcaLCV TruthValue,
        sonusDsx3CurrentDayCriticalTcaLES TruthValue,
        sonusDsx3CurrentDayCriticalTcaLSES  TruthValue,
        sonusDsx3CurrentDayCriticalTcaCVP TruthValue,
        sonusDsx3CurrentDayCriticalTcaESP TruthValue,
        sonusDsx3CurrentDayCriticalTcaSESP  TruthValue,
        sonusDsx3CurrentDayCriticalTcaUASP  TruthValue,
        sonusDsx3CurrentDayCriticalTcaCVCP  TruthValue,
        sonusDsx3CurrentDayCriticalTcaESCP  TruthValue,
        sonusDsx3CurrentDayCriticalTcaSESCP   TruthValue,
        sonusDsx3CurrentDayCriticalTcaUASCP   TruthValue
    }

sonusDsx3CurrentDayShelfIndex OBJECT-TYPE
    SYNTAX          SonusShelfIndex
    ACCESS          read-only
    STATUS          mandatory
    DESCRIPTION     
            "Shelf index into this table"
    ::= { sonusDsx3CurrentDayEntry 1 }

sonusDsx3CurrentDaySlotIndex OBJECT-TYPE
    SYNTAX          SonusSlotIndex
    ACCESS          read-only
    STATUS          mandatory
    DESCRIPTION     
            "Slot index into this table"
    ::= { sonusDsx3CurrentDayEntry 2 }

sonusDsx3CurrentDayPortIndex OBJECT-TYPE
    SYNTAX          INTEGER
    ACCESS          read-only
    STATUS          mandatory
    DESCRIPTION     
            "Port Index into this table"
    ::= { sonusDsx3CurrentDayEntry 3 }

sonusDsx3CurrentDayDs3Index OBJECT-TYPE
    SYNTAX          INTEGER
    ACCESS          read-only
    STATUS          mandatory
    DESCRIPTION     
            "Ds3 Index into this table"
    ::= { sonusDsx3CurrentDayEntry 4 }

sonusDsx3CurrentDayElapsedTime OBJECT-TYPE
    SYNTAX          INTEGER
    ACCESS          read-only
    STATUS          mandatory
    DESCRIPTION     
            "Elapsed time in the current period"
    ::= { sonusDsx3CurrentDayEntry 5 }

sonusDsx3CurrentDayLCVs OBJECT-TYPE
    SYNTAX          PerfCurrentCount
    ACCESS          read-only
    STATUS          mandatory
    DESCRIPTION     
            "The number of Line Code Violations (LCVs)."
    ::= { sonusDsx3CurrentDayEntry 6 }

sonusDsx3CurrentDayLESs OBJECT-TYPE
    SYNTAX          PerfCurrentCount
    ACCESS          read-only
    STATUS          mandatory
    DESCRIPTION     
            "The number of Line Errored Seconds."
    ::= { sonusDsx3CurrentDayEntry 7 }

sonusDsx3CurrentDayLSESs OBJECT-TYPE
    SYNTAX          PerfCurrentCount
    ACCESS          read-only
    STATUS          mandatory
    DESCRIPTION     
            "The number of Line Severely Errored Seconds."
    ::= { sonusDsx3CurrentDayEntry 8 }

sonusDsx3CurrentDayCVPs OBJECT-TYPE
    SYNTAX          PerfCurrentCount
    ACCESS          read-only
    STATUS          mandatory
    DESCRIPTION     
            "The number of Path P-bit Coding Violations."
    ::= { sonusDsx3CurrentDayEntry 9 }

sonusDsx3CurrentDayCVCPs OBJECT-TYPE
    SYNTAX          PerfCurrentCount
    ACCESS          read-only
    STATUS          mandatory
    DESCRIPTION     
            "The number of Path CP-bit Coding Violations."
    ::= { sonusDsx3CurrentDayEntry 10 }

sonusDsx3CurrentDayESPs OBJECT-TYPE
    SYNTAX          PerfCurrentCount
    ACCESS          read-only
    STATUS          mandatory
    DESCRIPTION     
            "The number of Path P-bit Errored Seconds."
    ::= { sonusDsx3CurrentDayEntry 11 }

sonusDsx3CurrentDayESCPs OBJECT-TYPE
    SYNTAX          PerfCurrentCount
    ACCESS          read-only
    STATUS          mandatory
    DESCRIPTION     
            "The number of Path CP-bit Errored Seconds."
    ::= { sonusDsx3CurrentDayEntry 12 }

sonusDsx3CurrentDaySESPs OBJECT-TYPE
    SYNTAX          PerfCurrentCount
    ACCESS          read-only
    STATUS          mandatory
    DESCRIPTION     
            "The number of Path P-bit Severely Errored Seconds."
    ::= { sonusDsx3CurrentDayEntry 13 }

sonusDsx3CurrentDaySESCPs OBJECT-TYPE
    SYNTAX          PerfCurrentCount
    ACCESS          read-only
    STATUS          mandatory
    DESCRIPTION     
            "The number of Path CP-bit Severely Errored Seconds."
    ::= { sonusDsx3CurrentDayEntry 14 }

sonusDsx3CurrentDaySASs OBJECT-TYPE
    SYNTAX          PerfCurrentCount
    ACCESS          read-only
    STATUS          mandatory
    DESCRIPTION     
            "The number of SEF/AIS Errored Seconds."
    ::= { sonusDsx3CurrentDayEntry 15 }

sonusDsx3CurrentDayUASPs OBJECT-TYPE
    SYNTAX          PerfCurrentCount
    ACCESS          read-only
    STATUS          mandatory
    DESCRIPTION     
            "The number of P-bit Unavailable Seconds."
    ::= { sonusDsx3CurrentDayEntry 16 }

sonusDsx3CurrentDayUASCPs OBJECT-TYPE
    SYNTAX          PerfCurrentCount
    ACCESS          read-only
    STATUS          mandatory
    DESCRIPTION     
            "The number of CP-bit Unavailable Seconds."
    ::= { sonusDsx3CurrentDayEntry 17 }

sonusDsx3CurrentDayFC OBJECT-TYPE
    SYNTAX          INTEGER
    ACCESS          read-only
    STATUS          mandatory
    DESCRIPTION     
            "The number of LOF or AIS failures detected."
    ::= { sonusDsx3CurrentDayEntry 18 }

sonusDsx3CurrentDayTcaLCV OBJECT-TYPE
    SYNTAX          TruthValue
    ACCESS          read-only
    STATUS          obsolete
    DESCRIPTION     
            "Indicates status of threshold crossing for Line Code Violations."
    ::= { sonusDsx3CurrentDayEntry 19 }

sonusDsx3CurrentDayTcaLES OBJECT-TYPE
    SYNTAX          TruthValue
    ACCESS          read-only
    STATUS          obsolete
    DESCRIPTION     
            "Indicates status of threshold crossing for Line Errored Seconds."
    ::= { sonusDsx3CurrentDayEntry 20 }

sonusDsx3CurrentDayTcaLSES OBJECT-TYPE
    SYNTAX          TruthValue
    ACCESS          read-only
    STATUS          obsolete
    DESCRIPTION     
            "Indicates status of threshold crossing for Line Severely Errored Seconds."
    ::= { sonusDsx3CurrentDayEntry 21 }

sonusDsx3CurrentDayTcaCVP OBJECT-TYPE
    SYNTAX          TruthValue
    ACCESS          read-only
    STATUS          obsolete
    DESCRIPTION     
            "Indicates status of threshold crossing for P-bit Code Violations."
    ::= { sonusDsx3CurrentDayEntry 22 }

sonusDsx3CurrentDayTcaESP OBJECT-TYPE
    SYNTAX          TruthValue
    ACCESS          read-only
    STATUS          obsolete
    DESCRIPTION     
            "Indicates status of threshold crossing for P-bit Errored Seconds."
    ::= { sonusDsx3CurrentDayEntry 23 }

sonusDsx3CurrentDayTcaSESP OBJECT-TYPE
    SYNTAX          TruthValue
    ACCESS          read-only
    STATUS          obsolete
    DESCRIPTION     
            "Indicates status of threshold crossing for P-bit Severely Errored Seconds."
    ::= { sonusDsx3CurrentDayEntry 24 }

sonusDsx3CurrentDayTcaUASP OBJECT-TYPE
    SYNTAX          TruthValue
    ACCESS          read-only
    STATUS          obsolete
    DESCRIPTION     
            "Indicates status of threshold crossing for P-bit Unavailable Seconds."
    ::= { sonusDsx3CurrentDayEntry 25 }

sonusDsx3CurrentDayTcaCVCP OBJECT-TYPE
    SYNTAX          TruthValue
    ACCESS          read-only
    STATUS          obsolete
    DESCRIPTION     
            "Indicates status of threshold crossing for CP-bit Code Violations."
    ::= { sonusDsx3CurrentDayEntry 26 }

sonusDsx3CurrentDayTcaESCP OBJECT-TYPE
    SYNTAX          TruthValue
    ACCESS          read-only
    STATUS          obsolete
    DESCRIPTION     
            "Indicates status of threshold crossing for CP-bit Errored Seconds."
    ::= { sonusDsx3CurrentDayEntry 27 }

sonusDsx3CurrentDayTcaSESCP OBJECT-TYPE
    SYNTAX          TruthValue
    ACCESS          read-only
    STATUS          obsolete
    DESCRIPTION     
            "Indicates status of threshold crossing for CP-bit Severely Errored Seconds."
    ::= { sonusDsx3CurrentDayEntry 28 }

sonusDsx3CurrentDayTcaUASCP OBJECT-TYPE
    SYNTAX          TruthValue
    ACCESS          read-only
    STATUS          obsolete
    DESCRIPTION     
            "Indicates status of threshold crossing for CP-bit Unavailable Seconds."
    ::= { sonusDsx3CurrentDayEntry 29 }

sonusDsx3CurrentDayMinorTcaLCV OBJECT-TYPE
    SYNTAX          TruthValue
    ACCESS          read-only
    STATUS          mandatory
    DESCRIPTION     
            "Indicates status of Minor threshold crossing for Line Code Violations."
    ::= { sonusDsx3CurrentDayEntry 30 }

sonusDsx3CurrentDayMinorTcaLES OBJECT-TYPE
    SYNTAX          TruthValue
    ACCESS          read-only
    STATUS          mandatory
    DESCRIPTION     
            "Indicates status of Minor threshold crossing for Line Errored Seconds."
    ::= { sonusDsx3CurrentDayEntry 31 }

sonusDsx3CurrentDayMinorTcaLSES OBJECT-TYPE
    SYNTAX          TruthValue
    ACCESS          read-only
    STATUS          mandatory
    DESCRIPTION     
            "Indicates status of Minor threshold crossing for Line Severely Errored Seconds."
    ::= { sonusDsx3CurrentDayEntry 32 }

sonusDsx3CurrentDayMinorTcaCVP OBJECT-TYPE
    SYNTAX          TruthValue
    ACCESS          read-only
    STATUS          mandatory
    DESCRIPTION     
            "Indicates status of Minor threshold crossing for P-bit Code Violations."
    ::= { sonusDsx3CurrentDayEntry 33 }

sonusDsx3CurrentDayMinorTcaESP OBJECT-TYPE
    SYNTAX          TruthValue
    ACCESS          read-only
    STATUS          mandatory
    DESCRIPTION     
            "Indicates status of Minor threshold crossing for P-bit Errored Seconds."
    ::= { sonusDsx3CurrentDayEntry 34 }

sonusDsx3CurrentDayMinorTcaSESP OBJECT-TYPE
    SYNTAX          TruthValue
    ACCESS          read-only
    STATUS          mandatory
    DESCRIPTION     
            "Indicates status of Minor threshold crossing for P-bit Severely Errored Seconds."
    ::= { sonusDsx3CurrentDayEntry 35 }

sonusDsx3CurrentDayMinorTcaUASP OBJECT-TYPE
    SYNTAX          TruthValue
    ACCESS          read-only
    STATUS          mandatory
    DESCRIPTION     
            "Indicates status of Minor threshold crossing for P-bit Unavailable Seconds."
    ::= { sonusDsx3CurrentDayEntry 36 }

sonusDsx3CurrentDayMinorTcaCVCP OBJECT-TYPE
    SYNTAX          TruthValue
    ACCESS          read-only
    STATUS          mandatory
    DESCRIPTION     
            "Indicates status of Minor threshold crossing for CP-bit Code Violations."
    ::= { sonusDsx3CurrentDayEntry 37 }

sonusDsx3CurrentDayMinorTcaESCP OBJECT-TYPE
    SYNTAX          TruthValue
    ACCESS          read-only
    STATUS          mandatory
    DESCRIPTION     
            "Indicates status of Minor threshold crossing for CP-bit Errored Seconds."
    ::= { sonusDsx3CurrentDayEntry 38 }

sonusDsx3CurrentDayMinorTcaSESCP OBJECT-TYPE
    SYNTAX          TruthValue
    ACCESS          read-only
    STATUS          mandatory
    DESCRIPTION     
            "Indicates status of Minor threshold crossing for CP-bit Severely Errored Seconds."
    ::= { sonusDsx3CurrentDayEntry 39 }

sonusDsx3CurrentDayMinorTcaUASCP OBJECT-TYPE
    SYNTAX          TruthValue
    ACCESS          read-only
    STATUS          mandatory
    DESCRIPTION     
            "Indicates status of Minor threshold crossing for CP-bit Unavailable Seconds."
    ::= { sonusDsx3CurrentDayEntry 40 }

sonusDsx3CurrentDayMajorTcaLCV OBJECT-TYPE
    SYNTAX          TruthValue
    ACCESS          read-only
    STATUS          mandatory
    DESCRIPTION     
            "Indicates status of Major threshold crossing for Line Code Violations."
    ::= { sonusDsx3CurrentDayEntry 41 }

sonusDsx3CurrentDayMajorTcaLES OBJECT-TYPE
    SYNTAX          TruthValue
    ACCESS          read-only
    STATUS          mandatory
    DESCRIPTION     
            "Indicates status of Major threshold crossing for Line Errored Seconds."
    ::= { sonusDsx3CurrentDayEntry 42 }

sonusDsx3CurrentDayMajorTcaLSES OBJECT-TYPE
    SYNTAX          TruthValue
    ACCESS          read-only
    STATUS          mandatory
    DESCRIPTION     
            "Indicates status of Major threshold crossing for Line Severely Errored Seconds."
    ::= { sonusDsx3CurrentDayEntry 43 }

sonusDsx3CurrentDayMajorTcaCVP OBJECT-TYPE
    SYNTAX          TruthValue
    ACCESS          read-only
    STATUS          mandatory
    DESCRIPTION     
            "Indicates status of Major threshold crossing for P-bit Code Violations."
    ::= { sonusDsx3CurrentDayEntry 44 }

sonusDsx3CurrentDayMajorTcaESP OBJECT-TYPE
    SYNTAX          TruthValue
    ACCESS          read-only
    STATUS          mandatory
    DESCRIPTION     
            "Indicates status of Major threshold crossing for P-bit Errored Seconds."
    ::= { sonusDsx3CurrentDayEntry 45 }

sonusDsx3CurrentDayMajorTcaSESP OBJECT-TYPE
    SYNTAX          TruthValue
    ACCESS          read-only
    STATUS          mandatory
    DESCRIPTION     
            "Indicates status of Major threshold crossing for P-bit Severely Errored Seconds."
    ::= { sonusDsx3CurrentDayEntry 46 }

sonusDsx3CurrentDayMajorTcaUASP OBJECT-TYPE
    SYNTAX          TruthValue
    ACCESS          read-only
    STATUS          mandatory
    DESCRIPTION     
            "Indicates status of Major threshold crossing for P-bit Unavailable Seconds."
    ::= { sonusDsx3CurrentDayEntry 47 }

sonusDsx3CurrentDayMajorTcaCVCP OBJECT-TYPE
    SYNTAX          TruthValue
    ACCESS          read-only
    STATUS          mandatory
    DESCRIPTION     
            "Indicates status of Major threshold crossing for CP-bit Code Violations."
    ::= { sonusDsx3CurrentDayEntry 48 }

sonusDsx3CurrentDayMajorTcaESCP OBJECT-TYPE
    SYNTAX          TruthValue
    ACCESS          read-only
    STATUS          mandatory
    DESCRIPTION     
            "Indicates status of Major threshold crossing for CP-bit Errored Seconds."
    ::= { sonusDsx3CurrentDayEntry 49 }

sonusDsx3CurrentDayMajorTcaSESCP OBJECT-TYPE
    SYNTAX          TruthValue
    ACCESS          read-only
    STATUS          mandatory
    DESCRIPTION     
            "Indicates status of Major threshold crossing for CP-bit Severely Errored Seconds."
    ::= { sonusDsx3CurrentDayEntry 50 }

sonusDsx3CurrentDayMajorTcaUASCP OBJECT-TYPE
    SYNTAX          TruthValue
    ACCESS          read-only
    STATUS          mandatory
    DESCRIPTION     
            "Indicates status of Major threshold crossing for CP-bit Unavailable Seconds."
    ::= { sonusDsx3CurrentDayEntry 51 }

sonusDsx3CurrentDayCriticalTcaLCV OBJECT-TYPE
    SYNTAX          TruthValue
    ACCESS          read-only
    STATUS          mandatory
    DESCRIPTION     
            "Indicates status of Critical threshold crossing for Line Code Violations."
    ::= { sonusDsx3CurrentDayEntry 52 }

sonusDsx3CurrentDayCriticalTcaLES OBJECT-TYPE
    SYNTAX          TruthValue
    ACCESS          read-only
    STATUS          mandatory
    DESCRIPTION     
            "Indicates status of Critical threshold crossing for Line Errored Seconds."
    ::= { sonusDsx3CurrentDayEntry 53 }

sonusDsx3CurrentDayCriticalTcaLSES OBJECT-TYPE
    SYNTAX          TruthValue
    ACCESS          read-only
    STATUS          mandatory
    DESCRIPTION     
            "Indicates status of Critical threshold crossing for Line Severely Errored Seconds."
    ::= { sonusDsx3CurrentDayEntry 54 }

sonusDsx3CurrentDayCriticalTcaCVP OBJECT-TYPE
    SYNTAX          TruthValue
    ACCESS          read-only
    STATUS          mandatory
    DESCRIPTION     
            "Indicates status of Critical threshold crossing for P-bit Code Violations."
    ::= { sonusDsx3CurrentDayEntry 55 }

sonusDsx3CurrentDayCriticalTcaESP OBJECT-TYPE
    SYNTAX          TruthValue
    ACCESS          read-only
    STATUS          mandatory
    DESCRIPTION     
            "Indicates status of Critical threshold crossing for P-bit Errored Seconds."
    ::= { sonusDsx3CurrentDayEntry 56 }

sonusDsx3CurrentDayCriticalTcaSESP OBJECT-TYPE
    SYNTAX          TruthValue
    ACCESS          read-only
    STATUS          mandatory
    DESCRIPTION     
            "Indicates status of Critical threshold crossing for P-bit Severely Errored Seconds."
    ::= { sonusDsx3CurrentDayEntry 57 }

sonusDsx3CurrentDayCriticalTcaUASP OBJECT-TYPE
    SYNTAX          TruthValue
    ACCESS          read-only
    STATUS          mandatory
    DESCRIPTION     
            "Indicates status of Critical threshold crossing for P-bit Unavailable Seconds."
    ::= { sonusDsx3CurrentDayEntry 58 }

sonusDsx3CurrentDayCriticalTcaCVCP OBJECT-TYPE
    SYNTAX          TruthValue
    ACCESS          read-only
    STATUS          mandatory
    DESCRIPTION     
            "Indicates status of Critical threshold crossing for CP-bit Code Violations."
    ::= { sonusDsx3CurrentDayEntry 59 }

sonusDsx3CurrentDayCriticalTcaESCP OBJECT-TYPE
    SYNTAX          TruthValue
    ACCESS          read-only
    STATUS          mandatory
    DESCRIPTION     
            "Indicates status of Critical threshold crossing for CP-bit Errored Seconds."
    ::= { sonusDsx3CurrentDayEntry 60 }

sonusDsx3CurrentDayCriticalTcaSESCP OBJECT-TYPE
    SYNTAX          TruthValue
    ACCESS          read-only
    STATUS          mandatory
    DESCRIPTION     
            "Indicates status of Critical threshold crossing for CP-bit Severely Errored Seconds."
    ::= { sonusDsx3CurrentDayEntry 61 }

sonusDsx3CurrentDayCriticalTcaUASCP OBJECT-TYPE
    SYNTAX          TruthValue
    ACCESS          read-only
    STATUS          mandatory
    DESCRIPTION     
            "Indicates status of Critical threshold crossing for CP-bit Unavailable Seconds."
    ::= { sonusDsx3CurrentDayEntry 62 }

sonusDsx3FarEndCurrentDayTable OBJECT-TYPE
    SYNTAX          SEQUENCE OF SonusDsx3FarEndCurrentDayEntry
    ACCESS          not-accessible
    STATUS          mandatory
    DESCRIPTION     
            "The DS3 current table contains various statistics
             being collected for the far end current 15 minute
             interval."
    ::= { sonusDsx3MIBObjects 8 }

sonusDsx3FarEndCurrentDayEntry OBJECT-TYPE
    SYNTAX          SonusDsx3FarEndCurrentDayEntry
    ACCESS          not-accessible
    STATUS          mandatory
    DESCRIPTION     
            "An entry in the DS3 Current table."
    INDEX           { sonusDsx3FarEndCurrentDayShelfIndex, 
                      sonusDsx3FarEndCurrentDaySlotIndex, 
                      sonusDsx3FarEndCurrentDayPortIndex, 
                      sonusDsx3FarEndCurrentDayDs3Index }
    ::= { sonusDsx3FarEndCurrentDayTable 1 }

SonusDsx3FarEndCurrentDayEntry ::=
    SEQUENCE {
        sonusDsx3FarEndCurrentDayShelfIndex   SonusShelfIndex,
        sonusDsx3FarEndCurrentDaySlotIndex  SonusSlotIndex,
        sonusDsx3FarEndCurrentDayPortIndex  INTEGER,
        sonusDsx3FarEndCurrentDayDs3Index INTEGER,
        sonusDsx3FarEndCurrentDayElapsedTime    INTEGER,
        sonusDsx3FarEndCurrentDayCVCPs  PerfCurrentCount,
        sonusDsx3FarEndCurrentDayESCPs  PerfCurrentCount,
        sonusDsx3FarEndCurrentDaySESCPs PerfCurrentCount,
        sonusDsx3FarEndCurrentDaySASCPs PerfCurrentCount,
        sonusDsx3FarEndCurrentDayUASCPs PerfCurrentCount,
        sonusDsx3FarEndCurrentDayFCCP   INTEGER,
        sonusDsx3FarEndCurrentDayTcaCVCP TruthValue,
        sonusDsx3FarEndCurrentDayTcaESCP TruthValue,
        sonusDsx3FarEndCurrentDayTcaSESCP TruthValue,
        sonusDsx3FarEndCurrentDayTcaUASCP TruthValue,
        sonusDsx3FarEndCurrentDayMinorTcaCVCP     TruthValue,
        sonusDsx3FarEndCurrentDayMinorTcaESCP     TruthValue,
        sonusDsx3FarEndCurrentDayMinorTcaSESCP      TruthValue,
        sonusDsx3FarEndCurrentDayMinorTcaUASCP      TruthValue,
        sonusDsx3FarEndCurrentDayMajorTcaCVCP     TruthValue,
        sonusDsx3FarEndCurrentDayMajorTcaESCP     TruthValue,
        sonusDsx3FarEndCurrentDayMajorTcaSESCP      TruthValue,
        sonusDsx3FarEndCurrentDayMajorTcaUASCP      TruthValue,
        sonusDsx3FarEndCurrentDayCriticalTcaCVCP        TruthValue,
        sonusDsx3FarEndCurrentDayCriticalTcaESCP        TruthValue,
        sonusDsx3FarEndCurrentDayCriticalTcaSESCP         TruthValue,
        sonusDsx3FarEndCurrentDayCriticalTcaUASCP         TruthValue
    }

sonusDsx3FarEndCurrentDayShelfIndex OBJECT-TYPE
    SYNTAX          SonusShelfIndex
    ACCESS          read-only
    STATUS          mandatory
    DESCRIPTION     
            "Shelf index into this table"
    ::= { sonusDsx3FarEndCurrentDayEntry 1 }

sonusDsx3FarEndCurrentDaySlotIndex OBJECT-TYPE
    SYNTAX          SonusSlotIndex
    ACCESS          read-only
    STATUS          mandatory
    DESCRIPTION     
            "Slot index into this table"
    ::= { sonusDsx3FarEndCurrentDayEntry 2 }

sonusDsx3FarEndCurrentDayPortIndex OBJECT-TYPE
    SYNTAX          INTEGER
    ACCESS          read-only
    STATUS          mandatory
    DESCRIPTION     
            "Port Index into this table"
    ::= { sonusDsx3FarEndCurrentDayEntry 3 }

sonusDsx3FarEndCurrentDayDs3Index OBJECT-TYPE
    SYNTAX          INTEGER
    ACCESS          read-only
    STATUS          mandatory
    DESCRIPTION     
            "Ds3 Index into this table"
    ::= { sonusDsx3FarEndCurrentDayEntry 4 }

sonusDsx3FarEndCurrentDayElapsedTime OBJECT-TYPE
    SYNTAX          INTEGER
    ACCESS          read-only
    STATUS          mandatory
    DESCRIPTION     
            "Elapsed time in the current period"
    ::= { sonusDsx3FarEndCurrentDayEntry 5 }

sonusDsx3FarEndCurrentDayCVCPs OBJECT-TYPE
    SYNTAX          PerfCurrentCount
    ACCESS          read-only
    STATUS          mandatory
    DESCRIPTION     
            "The number of Path CP-bit Coding Violations."
    ::= { sonusDsx3FarEndCurrentDayEntry 6 }

sonusDsx3FarEndCurrentDayESCPs OBJECT-TYPE
    SYNTAX          PerfCurrentCount
    ACCESS          read-only
    STATUS          mandatory
    DESCRIPTION     
            "The number of Path CP-bit Errored Seconds."
    ::= { sonusDsx3FarEndCurrentDayEntry 7 }

sonusDsx3FarEndCurrentDaySESCPs OBJECT-TYPE
    SYNTAX          PerfCurrentCount
    ACCESS          read-only
    STATUS          mandatory
    DESCRIPTION     
            "The number of Path CP-bit Severely Errored Seconds."
    ::= { sonusDsx3FarEndCurrentDayEntry 8 }

sonusDsx3FarEndCurrentDaySASCPs OBJECT-TYPE
    SYNTAX          PerfCurrentCount
    ACCESS          read-only
    STATUS          mandatory
    DESCRIPTION     
            "The number of SEF/AIS Errored Seconds."
    ::= { sonusDsx3FarEndCurrentDayEntry 9 }

sonusDsx3FarEndCurrentDayUASCPs OBJECT-TYPE
    SYNTAX          PerfCurrentCount
    ACCESS          read-only
    STATUS          mandatory
    DESCRIPTION     
            "The number of CP-bit Unavailable Seconds."
    ::= { sonusDsx3FarEndCurrentDayEntry 10 }

sonusDsx3FarEndCurrentDayFCCP OBJECT-TYPE
    SYNTAX          INTEGER
    ACCESS          read-only
    STATUS          mandatory
    DESCRIPTION     
            "The number of RAI failures detected."
    ::= { sonusDsx3FarEndCurrentDayEntry 11 }

sonusDsx3FarEndCurrentDayTcaCVCP OBJECT-TYPE
    SYNTAX          TruthValue
    ACCESS          read-only
    STATUS          obsolete
    DESCRIPTION     
            "Indicates status of threshold crossing for CP-bit Code Violations."
    ::= { sonusDsx3FarEndCurrentDayEntry 12 }

sonusDsx3FarEndCurrentDayTcaESCP OBJECT-TYPE
    SYNTAX          TruthValue
    ACCESS          read-only
    STATUS          obsolete
    DESCRIPTION     
            "Indicates status of threshold crossing for CP-bit Errored Seconds."
    ::= { sonusDsx3FarEndCurrentDayEntry 13 }

sonusDsx3FarEndCurrentDayTcaSESCP OBJECT-TYPE
    SYNTAX          TruthValue
    ACCESS          read-only
    STATUS          obsolete
    DESCRIPTION     
            "Indicates status of threshold crossing for CP-bit Severely Errored Seconds."
    ::= { sonusDsx3FarEndCurrentDayEntry 14 }

sonusDsx3FarEndCurrentDayTcaUASCP OBJECT-TYPE
    SYNTAX          TruthValue
    ACCESS          read-only
    STATUS          obsolete
    DESCRIPTION     
            "Indicates status of threshold crossing for CP-bit Unavailable Seconds."
    ::= { sonusDsx3FarEndCurrentDayEntry 15 }

sonusDsx3FarEndCurrentDayMinorTcaCVCP OBJECT-TYPE
    SYNTAX          TruthValue
    ACCESS          read-only
    STATUS          mandatory
    DESCRIPTION     
            "Indicates status of Minor threshold crossing for CP-bit Code Violations."
    ::= { sonusDsx3FarEndCurrentDayEntry 16 }

sonusDsx3FarEndCurrentDayMinorTcaESCP OBJECT-TYPE
    SYNTAX          TruthValue
    ACCESS          read-only
    STATUS          mandatory
    DESCRIPTION     
            "Indicates status of Minor threshold crossing for CP-bit Errored Seconds."
    ::= { sonusDsx3FarEndCurrentDayEntry 17 }

sonusDsx3FarEndCurrentDayMinorTcaSESCP OBJECT-TYPE
    SYNTAX          TruthValue
    ACCESS          read-only
    STATUS          mandatory
    DESCRIPTION     
            "Indicates status of Minor threshold crossing for CP-bit Severely Errored Seconds."
    ::= { sonusDsx3FarEndCurrentDayEntry 18 }

sonusDsx3FarEndCurrentDayMinorTcaUASCP OBJECT-TYPE
    SYNTAX          TruthValue
    ACCESS          read-only
    STATUS          mandatory
    DESCRIPTION     
            "Indicates status of Minor threshold crossing for CP-bit Unavailable Seconds."
    ::= { sonusDsx3FarEndCurrentDayEntry 19 }

sonusDsx3FarEndCurrentDayMajorTcaCVCP OBJECT-TYPE
    SYNTAX          TruthValue
    ACCESS          read-only
    STATUS          mandatory
    DESCRIPTION     
            "Indicates status of Major threshold crossing for CP-bit Code Violations."
    ::= { sonusDsx3FarEndCurrentDayEntry 20 }

sonusDsx3FarEndCurrentDayMajorTcaESCP OBJECT-TYPE
    SYNTAX          TruthValue
    ACCESS          read-only
    STATUS          mandatory
    DESCRIPTION     
            "Indicates status of Major threshold crossing for CP-bit Errored Seconds."
    ::= { sonusDsx3FarEndCurrentDayEntry 21 }

sonusDsx3FarEndCurrentDayMajorTcaSESCP OBJECT-TYPE
    SYNTAX          TruthValue
    ACCESS          read-only
    STATUS          mandatory
    DESCRIPTION     
            "Indicates status of Major threshold crossing for CP-bit Severely Errored Seconds."
    ::= { sonusDsx3FarEndCurrentDayEntry 22 }

sonusDsx3FarEndCurrentDayMajorTcaUASCP OBJECT-TYPE
    SYNTAX          TruthValue
    ACCESS          read-only
    STATUS          mandatory
    DESCRIPTION     
            "Indicates status of Major threshold crossing for CP-bit Unavailable Seconds."
    ::= { sonusDsx3FarEndCurrentDayEntry 23 }

sonusDsx3FarEndCurrentDayCriticalTcaCVCP OBJECT-TYPE
    SYNTAX          TruthValue
    ACCESS          read-only
    STATUS          mandatory
    DESCRIPTION     
            "Indicates status of Critical threshold crossing for CP-bit Code Violations."
    ::= { sonusDsx3FarEndCurrentDayEntry 24 }

sonusDsx3FarEndCurrentDayCriticalTcaESCP OBJECT-TYPE
    SYNTAX          TruthValue
    ACCESS          read-only
    STATUS          mandatory
    DESCRIPTION     
            "Indicates status of Critical threshold crossing for CP-bit Errored Seconds."
    ::= { sonusDsx3FarEndCurrentDayEntry 25 }

sonusDsx3FarEndCurrentDayCriticalTcaSESCP OBJECT-TYPE
    SYNTAX          TruthValue
    ACCESS          read-only
    STATUS          mandatory
    DESCRIPTION     
            "Indicates status of Critical threshold crossing for CP-bit Severely Errored Seconds."
    ::= { sonusDsx3FarEndCurrentDayEntry 26 }

sonusDsx3FarEndCurrentDayCriticalTcaUASCP OBJECT-TYPE
    SYNTAX          TruthValue
    ACCESS          read-only
    STATUS          mandatory
    DESCRIPTION     
            "Indicates status of Critical threshold crossing for CP-bit Unavailable Seconds."
    ::= { sonusDsx3FarEndCurrentDayEntry 27 }

sonusDsx3IntervalDayTable OBJECT-TYPE
    SYNTAX          SEQUENCE OF SonusDsx3IntervalDayEntry
    ACCESS          not-accessible
    STATUS          mandatory
    DESCRIPTION     
            "The DS3 Interval Table contains various
             near end statistics collected by each DS3 interface
             over the previous 24 hours of operation."
    ::= { sonusDsx3MIBObjects 9 }

sonusDsx3IntervalDayEntry OBJECT-TYPE
    SYNTAX          SonusDsx3IntervalDayEntry
    ACCESS          not-accessible
    STATUS          mandatory
    DESCRIPTION     
            "An entry in the DS3 Interval table."
    INDEX           { sonusDsx3IntervalDayShelfIndex, 
                      sonusDsx3IntervalDaySlotIndex, 
                      sonusDsx3IntervalDayPortIndex, 
                      sonusDsx3IntervalDayDs3Index }
    ::= { sonusDsx3IntervalDayTable 1 }

SonusDsx3IntervalDayEntry ::=
    SEQUENCE {
        sonusDsx3IntervalDayShelfIndex  SonusShelfIndex,
        sonusDsx3IntervalDaySlotIndex   SonusSlotIndex,
        sonusDsx3IntervalDayPortIndex   INTEGER,
        sonusDsx3IntervalDayDs3Index    INTEGER,
        sonusDsx3IntervalDayLCVs        PerfCurrentCount,
        sonusDsx3IntervalDayLESs        PerfCurrentCount,
        sonusDsx3IntervalDayLSESs       PerfCurrentCount,
        sonusDsx3IntervalDayCVPs        PerfCurrentCount,
        sonusDsx3IntervalDayCVCPs       PerfCurrentCount,
        sonusDsx3IntervalDayESPs        PerfCurrentCount,
        sonusDsx3IntervalDayESCPs       PerfCurrentCount,
        sonusDsx3IntervalDaySESPs       PerfCurrentCount,
        sonusDsx3IntervalDaySESCPs      PerfCurrentCount,
        sonusDsx3IntervalDaySASs        PerfCurrentCount,
        sonusDsx3IntervalDayUASPs       PerfCurrentCount,
        sonusDsx3IntervalDayUASCPs      PerfCurrentCount,
        sonusDsx3IntervalDayLineIDF     TruthValue,
        sonusDsx3IntervalDayPathIDF     TruthValue,
        sonusDsx3IntervalDayFC          INTEGER
    }

sonusDsx3IntervalDayShelfIndex OBJECT-TYPE
    SYNTAX          SonusShelfIndex
    ACCESS          read-only
    STATUS          mandatory
    DESCRIPTION     
            "Shelf index into this table"
    ::= { sonusDsx3IntervalDayEntry 1 }

sonusDsx3IntervalDaySlotIndex OBJECT-TYPE
    SYNTAX          SonusSlotIndex
    ACCESS          read-only
    STATUS          mandatory
    DESCRIPTION     
            "Slot index into this table"
    ::= { sonusDsx3IntervalDayEntry 2 }

sonusDsx3IntervalDayPortIndex OBJECT-TYPE
    SYNTAX          INTEGER
    ACCESS          read-only
    STATUS          mandatory
    DESCRIPTION     
            "Port Index into this table"
    ::= { sonusDsx3IntervalDayEntry 3 }

sonusDsx3IntervalDayDs3Index OBJECT-TYPE
    SYNTAX          INTEGER
    ACCESS          read-only
    STATUS          mandatory
    DESCRIPTION     
            "Ds3 Index into this table"
    ::= { sonusDsx3IntervalDayEntry 4 }

sonusDsx3IntervalDayLCVs OBJECT-TYPE
    SYNTAX          PerfCurrentCount
    ACCESS          read-only
    STATUS          mandatory
    DESCRIPTION     
            "The number of Line Code Violations (LCVs)."
    ::= { sonusDsx3IntervalDayEntry 5 }

sonusDsx3IntervalDayLESs OBJECT-TYPE
    SYNTAX          PerfCurrentCount
    ACCESS          read-only
    STATUS          mandatory
    DESCRIPTION     
            "The number of Line Errored Seconds."
    ::= { sonusDsx3IntervalDayEntry 6 }

sonusDsx3IntervalDayLSESs OBJECT-TYPE
    SYNTAX          PerfCurrentCount
    ACCESS          read-only
    STATUS          mandatory
    DESCRIPTION     
            "The number of Line Severely Errored Seconds."
    ::= { sonusDsx3IntervalDayEntry 7 }

sonusDsx3IntervalDayCVPs OBJECT-TYPE
    SYNTAX          PerfCurrentCount
    ACCESS          read-only
    STATUS          mandatory
    DESCRIPTION     
            "The number of Path P-bit Coding Violations."
    ::= { sonusDsx3IntervalDayEntry 8 }

sonusDsx3IntervalDayCVCPs OBJECT-TYPE
    SYNTAX          PerfCurrentCount
    ACCESS          read-only
    STATUS          mandatory
    DESCRIPTION     
            "The number of Path CP-bit Coding Violations."
    ::= { sonusDsx3IntervalDayEntry 9 }

sonusDsx3IntervalDayESPs OBJECT-TYPE
    SYNTAX          PerfCurrentCount
    ACCESS          read-only
    STATUS          mandatory
    DESCRIPTION     
            "The number of Path P-bit Errored Seconds."
    ::= { sonusDsx3IntervalDayEntry 10 }

sonusDsx3IntervalDayESCPs OBJECT-TYPE
    SYNTAX          PerfCurrentCount
    ACCESS          read-only
    STATUS          mandatory
    DESCRIPTION     
            "The number of Path CP-bit Errored Seconds."
    ::= { sonusDsx3IntervalDayEntry 11 }

sonusDsx3IntervalDaySESPs OBJECT-TYPE
    SYNTAX          PerfCurrentCount
    ACCESS          read-only
    STATUS          mandatory
    DESCRIPTION     
            "The number of Path P-bit Severely Errored Seconds."
    ::= { sonusDsx3IntervalDayEntry 12 }

sonusDsx3IntervalDaySESCPs OBJECT-TYPE
    SYNTAX          PerfCurrentCount
    ACCESS          read-only
    STATUS          mandatory
    DESCRIPTION     
            "The number of Path CP-bit Severely Errored Seconds."
    ::= { sonusDsx3IntervalDayEntry 13 }

sonusDsx3IntervalDaySASs OBJECT-TYPE
    SYNTAX          PerfCurrentCount
    ACCESS          read-only
    STATUS          mandatory
    DESCRIPTION     
            "The number of SEF/AIS Errored Seconds."
    ::= { sonusDsx3IntervalDayEntry 14 }

sonusDsx3IntervalDayUASPs OBJECT-TYPE
    SYNTAX          PerfCurrentCount
    ACCESS          read-only
    STATUS          mandatory
    DESCRIPTION     
            "The number of P-bit Unavailable Seconds."
    ::= { sonusDsx3IntervalDayEntry 15 }

sonusDsx3IntervalDayUASCPs OBJECT-TYPE
    SYNTAX          PerfCurrentCount
    ACCESS          read-only
    STATUS          mandatory
    DESCRIPTION     
            "The number of CP-bit Unavailable Seconds."
    ::= { sonusDsx3IntervalDayEntry 16 }

sonusDsx3IntervalDayLineIDF OBJECT-TYPE
    SYNTAX          TruthValue
    ACCESS          read-only
    STATUS          mandatory
    DESCRIPTION     
            "This variable indicates if the Line data for this
             interval is valid."
    ::= { sonusDsx3IntervalDayEntry 17 }

sonusDsx3IntervalDayPathIDF OBJECT-TYPE
    SYNTAX          TruthValue
    ACCESS          read-only
    STATUS          mandatory
    DESCRIPTION     
            "This variable indicates if the Path data for this
             interval is valid."
    ::= { sonusDsx3IntervalDayEntry 18 }

sonusDsx3IntervalDayFC OBJECT-TYPE
    SYNTAX          INTEGER
    ACCESS          read-only
    STATUS          mandatory
    DESCRIPTION     
            "The number of LOF or AIS failures detected."
    ::= { sonusDsx3IntervalDayEntry 19 }

sonusDsx3FarEndIntervalDayTable OBJECT-TYPE
    SYNTAX          SEQUENCE OF SonusDsx3FarEndIntervalDayEntry
    ACCESS          not-accessible
    STATUS          mandatory
    DESCRIPTION     
            "The DS3 Interval Table contains various
             far end statistics collected by each DS3 interface
             over the previous 24 hours of operation."
    ::= { sonusDsx3MIBObjects 10 }

sonusDsx3FarEndIntervalDayEntry OBJECT-TYPE
    SYNTAX          SonusDsx3FarEndIntervalDayEntry
    ACCESS          not-accessible
    STATUS          mandatory
    DESCRIPTION     
            "An entry in the DS3 Far End Interval table."
    INDEX           { sonusDsx3FarEndIntervalDayShelfIndex, 
                      sonusDsx3FarEndIntervalDaySlotIndex, 
                      sonusDsx3FarEndIntervalDayPortIndex, 
                      sonusDsx3FarEndIntervalDayDs3Index }
    ::= { sonusDsx3FarEndIntervalDayTable 1 }

SonusDsx3FarEndIntervalDayEntry ::=
    SEQUENCE {
        sonusDsx3FarEndIntervalDayShelfIndex    SonusShelfIndex,
        sonusDsx3FarEndIntervalDaySlotIndex   SonusSlotIndex,
        sonusDsx3FarEndIntervalDayPortIndex   INTEGER,
        sonusDsx3FarEndIntervalDayDs3Index  INTEGER,
        sonusDsx3FarEndIntervalDayCVCPs PerfCurrentCount,
        sonusDsx3FarEndIntervalDayESCPs PerfCurrentCount,
        sonusDsx3FarEndIntervalDaySESCPs PerfCurrentCount,
        sonusDsx3FarEndIntervalDaySASCPs PerfCurrentCount,
        sonusDsx3FarEndIntervalDayUASCPs PerfCurrentCount,
        sonusDsx3FarEndIntervalDayPathIDF TruthValue,
        sonusDsx3FarEndIntervalDayFCCP  INTEGER
    }

sonusDsx3FarEndIntervalDayShelfIndex OBJECT-TYPE
    SYNTAX          SonusShelfIndex
    ACCESS          read-only
    STATUS          mandatory
    DESCRIPTION     
            "Shelf index into this table"
    ::= { sonusDsx3FarEndIntervalDayEntry 1 }

sonusDsx3FarEndIntervalDaySlotIndex OBJECT-TYPE
    SYNTAX          SonusSlotIndex
    ACCESS          read-only
    STATUS          mandatory
    DESCRIPTION     
            "Slot index into this table"
    ::= { sonusDsx3FarEndIntervalDayEntry 2 }

sonusDsx3FarEndIntervalDayPortIndex OBJECT-TYPE
    SYNTAX          INTEGER
    ACCESS          read-only
    STATUS          mandatory
    DESCRIPTION     
            "Port Index into this table"
    ::= { sonusDsx3FarEndIntervalDayEntry 3 }

sonusDsx3FarEndIntervalDayDs3Index OBJECT-TYPE
    SYNTAX          INTEGER
    ACCESS          read-only
    STATUS          mandatory
    DESCRIPTION     
            "Ds3 Index into this table"
    ::= { sonusDsx3FarEndIntervalDayEntry 4 }

sonusDsx3FarEndIntervalDayCVCPs OBJECT-TYPE
    SYNTAX          PerfCurrentCount
    ACCESS          read-only
    STATUS          mandatory
    DESCRIPTION     
            "The number of Path CP-bit Coding Violations."
    ::= { sonusDsx3FarEndIntervalDayEntry 5 }

sonusDsx3FarEndIntervalDayESCPs OBJECT-TYPE
    SYNTAX          PerfCurrentCount
    ACCESS          read-only
    STATUS          mandatory
    DESCRIPTION     
            "The number of Path CP-bit Errored Seconds."
    ::= { sonusDsx3FarEndIntervalDayEntry 6 }

sonusDsx3FarEndIntervalDaySESCPs OBJECT-TYPE
    SYNTAX          PerfCurrentCount
    ACCESS          read-only
    STATUS          mandatory
    DESCRIPTION     
            "The number of Path CP-bit Severely Errored Seconds."
    ::= { sonusDsx3FarEndIntervalDayEntry 7 }

sonusDsx3FarEndIntervalDaySASCPs OBJECT-TYPE
    SYNTAX          PerfCurrentCount
    ACCESS          read-only
    STATUS          mandatory
    DESCRIPTION     
            "The number of SEF/AIS Errored Seconds."
    ::= { sonusDsx3FarEndIntervalDayEntry 8 }

sonusDsx3FarEndIntervalDayUASCPs OBJECT-TYPE
    SYNTAX          PerfCurrentCount
    ACCESS          read-only
    STATUS          mandatory
    DESCRIPTION     
            "The number of CP-bit Unavailable Seconds."
    ::= { sonusDsx3FarEndIntervalDayEntry 9 }

sonusDsx3FarEndIntervalDayPathIDF OBJECT-TYPE
    SYNTAX          TruthValue
    ACCESS          read-only
    STATUS          mandatory
    DESCRIPTION     
            "This variable indicates if the Path data for this
             interval is valid."
    ::= { sonusDsx3FarEndIntervalDayEntry 10 }

sonusDsx3FarEndIntervalDayFCCP OBJECT-TYPE
    SYNTAX          INTEGER
    ACCESS          read-only
    STATUS          mandatory
    DESCRIPTION     
            "The number of RAI failures detected."
    ::= { sonusDsx3FarEndIntervalDayEntry 11 }

sonusDsx3MIBNotifications OBJECT IDENTIFIER
    ::= { sonusDsx3MIB 2 }

sonusDsx3MIBNotificationsPrefix OBJECT IDENTIFIER
    ::= { sonusDsx3MIBNotifications 0 }

sonusDsx3MIBNotificationsObjects OBJECT IDENTIFIER
    ::= { sonusDsx3MIBNotifications 1 }

sonusDs3OutOfServiceReason OBJECT-TYPE
    SYNTAX          INTEGER { maintenance(1) }
    ACCESS          read-only
    STATUS          mandatory
    DESCRIPTION     
            "The reason for DS3 going out of service"
    ::= { sonusDsx3MIBNotificationsObjects 1 }

sonusDs3OutOfServiceType OBJECT-TYPE
    SYNTAX          INTEGER { admin(1), hwFailure(2) }
    ACCESS          read-only
    STATUS          mandatory
    DESCRIPTION     
            "The type of operation which caused DS3 to go out of service"
    ::= { sonusDsx3MIBNotificationsObjects 2 }

sonusDs3ThresholdType OBJECT-TYPE
    SYNTAX          INTEGER { currentLineCodeViolation(1), 
                        currentPbitParity(2), currentCbitParity(3), 
                        currentSeverelyErroredFramingSecs(4), 
                        currentLineErrorSeconds(5), 
                        currentPbitParityErroredSeconds(6), 
                        currentCbitParityErroredSeconds(7), 
                        currentPbitSeverelyErroredSeconds(8), 
                        currentLineSeverelyErroredSeconds(9), 
                        currentUnavailableSeconds(10), 
                        totalLineCodeViolation(11), totalPbitParity(12), 
                        totalCbitParity(13), 
                        totalSeverelyErroredFramingSecs(14), 
                        totalLineErrorSeconds(15), 
                        totalPbitParityErroredSeconds(16), 
                        totalCbitParityErroredSeconds(17), 
                        totalPbitSeverelyErroredSeconds(18), 
                        totalLineSeverelyErroredSeconds(19), 
                        totalUnavailableSeconds(20), 
                        currentCbitSeverelyErroredSeconds(21), 
                        currentPbitUnavailableSeconds(22), 
                        currentCbitUnavailableSeconds(23), 
                        totalCbitSeverelyErroredSeconds(24), 
                        totalPbitUnavailableSeconds(25), 
                        totalCbitUnavailableSeconds(26), 
                        currentFarEndCbitParity(27), 
                        currentFarEndCbitParityErroredSeconds(28), 
                        currentFarEndCbitSeverelyErroredSeconds(29), 
                        currentFarEndCbitParityUnavailableSeconds(30), 
                        totalFarEndCbitParity(31), 
                        totalFarEndCbitParityErroredSeconds(32), 
                        totalFarEndCbitSeverelyErroredSeconds(33), 
                        totalFarEndCbitParityUnavailableSeconds(34) }
    ACCESS          read-only
    STATUS          mandatory
    DESCRIPTION     
            "Type of threshold that was crossed which caused a threshold crossing trap"
    ::= { sonusDsx3MIBNotificationsObjects 3 }

sonusDs3LineState OBJECT-TYPE
    SYNTAX          INTEGER { green(1), red(2), rai(3), ais(4), 
                        hwfailure(5) }
    ACCESS          read-only
    STATUS          mandatory
    DESCRIPTION     
            "The type of Alarm or failure which caused DS3 to go out of service"
    ::= { sonusDsx3MIBNotificationsObjects 4 }

sonusDs3AdmnState OBJECT-TYPE
    SYNTAX          INTEGER { disabled(1), enabled(2), deleted(3), 
                        inservice(4), dryingUp(5) }
    ACCESS          read-only
    STATUS          mandatory
    DESCRIPTION     
            "The administrative state of the DS3."
    ::= { sonusDsx3MIBNotificationsObjects 5 }

sonusDsx3AdminChangeNotification TRAP-TYPE
    ENTERPRISE      sonusDsx3MIBNotifications
    VARIABLES       { sonusShelfIndex, sonusSlotIndex, sonusPortIndex, 
                      sonusDs3Index, sonusDs3AdmnState, 
                      sonusEventDescription, sonusEventClass, 
                      sonusEventLevel, sonusSequenceId, sonusEventTime }
--     STATUS          mandatory
    DESCRIPTION     
            "A sonusDsx3AdminChangeNotification trap indicates the DS3 administration 
             changes."
    ::= 1

sonusDsx3OutOfServiceNotification TRAP-TYPE
    ENTERPRISE      sonusDsx3MIBNotifications
    VARIABLES       { sonusShelfIndex, sonusSlotIndex, sonusPortIndex, 
                      sonusDs3Index, sonusDs3OutOfServiceReason, 
                      sonusDs3OutOfServiceType, sonusEventDescription, 
                      sonusEventClass, sonusEventLevel, sonusSequenceId, 
                      sonusEventTime }
--     STATUS          mandatory
    DESCRIPTION     
            "A sonusDsx3OutOfServiceNotification trap indicates that a DS3
             went out of service. The reason indicates the reason why and
             type indicates the type of failure."
    ::= 2

sonusDsx3LineStatusChangeNotification TRAP-TYPE
    ENTERPRISE      sonusDsx3MIBNotifications
    VARIABLES       { sonusShelfIndex, sonusSlotIndex, sonusPortIndex, 
                      sonusDs3Index, sonusDs3LineState, 
                      sonusEventDescription, sonusEventClass, 
                      sonusEventLevel, sonusSequenceId, sonusEventTime }
--     STATUS          mandatory
    DESCRIPTION     
            "A sonusDsx3LineStatusChangeNotification trap indicates the DS3 state changes. 
             It is used to notify DS3 Alarms states"
    ::= 4

END -- end of module SONUS-DS3-MIB.
