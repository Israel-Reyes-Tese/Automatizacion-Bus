--
-- This SMIv2 module has been generated by smidump 0.2-cvs. Do not edit.
--

SONUS-METAVAR-MIB DEFINITIONS ::= BEGIN

IMPORTS
    Counter32, Counter64, Gauge32, Integer32, IpAddress, MODULE-IDENTITY, 
    OBJECT-TYPE, Unsigned32
        FROM SNMPv2-SMI
    DateAndTime, RowStatus, TEXTUAL-CONVENTION, TruthValue
        FROM SNMPv2-TC
    sonusCommonSoftwarePlatformServicesMIBs
        FROM SONUS-SMI;

sonusMetaVarMIB MODULE-IDENTITY
    LAST-UPDATED    "201604140000Z"
    ORGANIZATION    
            "Ribbon Communications, Inc."
    CONTACT-INFO    
            "Customer Support        
             Ribbon Communications, Inc. 
             4 Technology Park Drive 
             Westford, MA 01886      
             USA                     
                                     
             Tel: 978-614-8100       
             Fax: 978-614-8609"
    DESCRIPTION     
            "The MIB Module for Meta Variables."
    REVISION        "201604140000Z"
    DESCRIPTION     
            "Auto generated MIB."
    ::= { sonusCommonSoftwarePlatformServicesMIBs 22 }


String ::= TEXTUAL-CONVENTION
    DISPLAY-HINT    "1t"
    STATUS          current
    DESCRIPTION     
            "xs:string"
    SYNTAX          OCTET STRING

sonusMetaVariableTable OBJECT-TYPE
    SYNTAX          SEQUENCE OF SonusMetaVariableEntry
    MAX-ACCESS      not-accessible
    STATUS          current
    DESCRIPTION     
            "
             Dynamic Meta variable name and value pair table in Cloud SBC configuration management.
             "
    ::= { sonusMetaVarMIB 1 }

sonusMetaVariableEntry OBJECT-TYPE
    SYNTAX          SonusMetaVariableEntry
    MAX-ACCESS      not-accessible
    STATUS          current
    DESCRIPTION     
            ""
    INDEX           { sonusMetaVariableCeName, sonusMetaVariableName }
    ::= { sonusMetaVariableTable 1 }

SonusMetaVariableEntry ::=
    SEQUENCE {
        sonusMetaVariableName           String,
        sonusMetaVariableValue          String,
        sonusMetaVariableCeName         String
    }

sonusMetaVariableName OBJECT-TYPE
    SYNTAX          String (SIZE(0..255))
    MAX-ACCESS      not-accessible
    STATUS          current
    DESCRIPTION     
            "
             The name of Meta Variable.
             "
    ::= { sonusMetaVariableEntry 1 }

sonusMetaVariableValue OBJECT-TYPE
    SYNTAX          String (SIZE(0..255))
    MAX-ACCESS      read-only
    STATUS          current
    DESCRIPTION     
            "
             The value of Meta Variable - string of 255 bytes
             "
    ::= { sonusMetaVariableEntry 2 }

sonusMetaVariableCeName OBJECT-TYPE
    SYNTAX          String (SIZE(0..255))
    MAX-ACCESS      not-accessible
    STATUS          current
    DESCRIPTION     
            "
             Identifies the instance.
             "
    ::= { sonusMetaVariableEntry 3 }

END -- end of module SONUS-METAVAR-MIB.
