--
-- This SMIv1 module has been generated by smidump 0.2-cvs. Do not edit.
--

SONUS-SS7-SERVICES-MIB DEFINITIONS ::= BEGIN

IMPORTS
    Ipv6Address
        FROM IPV6-TC
    OBJECT-TYPE
        FROM RFC-1212
    TRAP-TYPE
        FROM RFC-1215
    IpAddress
        FROM RFC1155-SMI
    RowStatus
        FROM SNMPv2-TC
    sonusEventClass, sonusEventDescription, sonusEventLevel, 
    sonusEventTime, sonusSequenceId
        FROM SONUS-COMMON-MIB
    sonusServicesMIBs
        FROM SONUS-SMI
    PointCode, SonusName, SonusNameReference, SonusPointCode, 
    SonusPointCodeFormat
        FROM SONUS-TC;

sonusSs7ServicesMIB OBJECT IDENTIFIER
    ::= { sonusServicesMIBs 3 }

-- sonusSs7ServicesMIB MODULE-IDENTITY
--     LAST-UPDATED    "201405140000Z"
--     ORGANIZATION    
--             "Sonus Networks, Inc."
--     CONTACT-INFO    
--             "   Customer Support    
--              Sonus Networks, Inc.
--              7 Technology Park Drive
--              Westford, MA 01886
--              USA
--              
--              Tel: 978-614-8100
--              Fax: 978-614-8609"
--     DESCRIPTION     
--             "The MIB Module for SS7 Gateway and SS7 Node Configuration."
--     ::= { sonusServicesMIBs 3 }


SonusSs7GatewayLinkSelection ::=
    INTEGER { primary(1), secondary(2), none(3), primaryAlt(4), 
                        secondaryAlt(5) }

-- SonusSs7GatewayLinkSelection ::= TEXTUAL-CONVENTION
--     STATUS          mandatory
--     DESCRIPTION     
--             "The SS7 Gateway link selection value."
--     SYNTAX          INTEGER
--                       { primary(1), secondary(2), none(3), 
--                         primaryAlt(4), secondaryAlt(5) }

sonusSs7ServicesMIBObjects OBJECT IDENTIFIER
    ::= { sonusSs7ServicesMIB 1 }

sonusSs7Gateway OBJECT IDENTIFIER
    ::= { sonusSs7ServicesMIBObjects 1 }

sonusSs7GatewayNextIndex OBJECT-TYPE
    SYNTAX          INTEGER
    ACCESS          read-only
    STATUS          mandatory
    DESCRIPTION     
            "The next valid index to use when creating an entry in
             the sonusSs7GatewayTable."
    ::= { sonusSs7Gateway 1 }

sonusSs7GatewayTable OBJECT-TYPE
    SYNTAX          SEQUENCE OF SonusSs7GatewayEntry
    ACCESS          not-accessible
    STATUS          mandatory
    DESCRIPTION     
            "This table specifies the SS7 Gateway list for the GSX9000 node."
    ::= { sonusSs7Gateway 2 }

sonusSs7GatewayEntry OBJECT-TYPE
    SYNTAX          SonusSs7GatewayEntry
    ACCESS          not-accessible
    STATUS          mandatory
    DESCRIPTION     
            ""
    INDEX           { sonusSs7GatewayIndex }
    ::= { sonusSs7GatewayTable 1 }

SonusSs7GatewayEntry ::=
    SEQUENCE {
        sonusSs7GatewayIndex            INTEGER,
        sonusSs7GatewayState            INTEGER,
        sonusSs7GatewayName             SonusName,
        sonusSs7GatewaySocketType       INTEGER,
        sonusSs7GatewayActiveHost       INTEGER,
        sonusSs7GatewayPriHostName      DisplayString,
        sonusSs7GatewayPriHostIpaddr    IpAddress,
        sonusSs7GatewayPriHostMode      INTEGER,
        sonusSs7GatewayPriHostOosDelayTimer   INTEGER,
        sonusSs7GatewaySecHostName      DisplayString,
        sonusSs7GatewaySecHostIpaddr    IpAddress,
        sonusSs7GatewaySecHostMode      INTEGER,
        sonusSs7GatewaySecHostOosDelayTimer   INTEGER,
        sonusSs7GatewayRowStatus        RowStatus,
        sonusSs7GatewayPriAltHostIpaddr IpAddress,
        sonusSs7GatewaySecAltHostIpaddr IpAddress,
        sonusSs7GatewayGwType           INTEGER,
        sonusSs7GatewayServerTcpPort    INTEGER,
        sonusSs7GatewayClientTcpPort    INTEGER,
        sonusSs7GatewayPriTaliTrafficControl    INTEGER,
        sonusSs7GatewayPriAltTaliTrafficControl       INTEGER,
        sonusSs7GatewaySecTaliTrafficControl    INTEGER,
        sonusSs7GatewaySecAltTaliTrafficControl       INTEGER,
        sonusSs7GatewayTimerTaliT1      INTEGER,
        sonusSs7GatewayTimerTaliT2      INTEGER,
        sonusSs7GatewayTimerTaliT3      INTEGER,
        sonusSs7GatewayTimerTaliT4      INTEGER,
        sonusSs7GatewayTaliSs7Type      INTEGER,
        sonusSs7GatewaySlsBits          INTEGER,
        sonusSs7GatewayTaliIsupNormalization    INTEGER,
        sonusSs7GatewayTaliPstnPresentation   INTEGER,
        sonusSs7GatewayTaliGroupCode    DisplayString,
        sonusSs7GatewayM3uaAckTimer     INTEGER,
        sonusSs7GatewayM3uaAuditTimer   INTEGER,
        sonusSs7GatewaySctpRtoInitial   INTEGER,
        sonusSs7GatewaySctpRtoMin       INTEGER,
        sonusSs7GatewaySctpRtoMax       INTEGER,
        sonusSs7GatewaySctpPathMaxRetrans INTEGER,
        sonusSs7GatewaySctpInitMaxRetrans INTEGER,
        sonusSs7GatewaySctpHeartBeatInterval    INTEGER,
        sonusSs7GatewayPriHostIp6addr   Ipv6Address,
        sonusSs7GatewayPriAltHostIp6addr Ipv6Address,
        sonusSs7GatewaySecHostIp6addr   Ipv6Address,
        sonusSs7GatewaySecAltHostIp6addr Ipv6Address,
        sonusSs7GatewayIpVersion        INTEGER,
        sonusSs7GatewayIpVersionSec     INTEGER
    }

sonusSs7GatewayIndex OBJECT-TYPE
    SYNTAX          INTEGER
    ACCESS          read-only
    STATUS          mandatory
    DESCRIPTION     
            "Identifies the target SS7 Gateway entry."
    ::= { sonusSs7GatewayEntry 1 }

sonusSs7GatewayState OBJECT-TYPE
    SYNTAX          INTEGER { disabled(1), enabled(2) }
    ACCESS          read-write
    STATUS          mandatory
    DESCRIPTION     
            "The administrative state of this SS7 Gateway entry."
    DEFVAL          { disabled }
    ::= { sonusSs7GatewayEntry 2 }

sonusSs7GatewayName OBJECT-TYPE
    SYNTAX          SonusName
    ACCESS          read-write
    STATUS          mandatory
    DESCRIPTION     
            "The name of this SS7 Gateway instance."
    ::= { sonusSs7GatewayEntry 3 }

sonusSs7GatewaySocketType OBJECT-TYPE
    SYNTAX          INTEGER { tcp(1) }
    ACCESS          read-write
    STATUS          mandatory
    DESCRIPTION     
            "Indicates the type of socket interface used by the GSX9000 node for
             connections to the SS7 Gateway platform."
    DEFVAL          { tcp }
    ::= { sonusSs7GatewayEntry 4 }

sonusSs7GatewayActiveHost OBJECT-TYPE
    SYNTAX          INTEGER { primary(1), secondary(2), none(3) }
    ACCESS          read-only
    STATUS          deprecated
    DESCRIPTION     
            "This status value has been replaced by sonusSs7GatewayNextHost and
             sonusSs7GatewaySelectHost."
    ::= { sonusSs7GatewayEntry 5 }

sonusSs7GatewayPriHostName OBJECT-TYPE
    SYNTAX          DisplayString (SIZE(1..39))
    ACCESS          read-write
    STATUS          mandatory
    DESCRIPTION     
            "The host name of the primary link to the SS7 Gateway platform."
    ::= { sonusSs7GatewayEntry 6 }

sonusSs7GatewayPriHostIpaddr OBJECT-TYPE
    SYNTAX          IpAddress
    ACCESS          read-write
    STATUS          mandatory
    DESCRIPTION     
            "Specifies the IP Address of the primary link to the SS7 Gateway platform."
    ::= { sonusSs7GatewayEntry 7 }

sonusSs7GatewayPriHostMode OBJECT-TYPE
    SYNTAX          INTEGER { inService(1), outOfService(2) }
    ACCESS          read-write
    STATUS          mandatory
    DESCRIPTION     
            "Specifies the service mode of the primary link to the SS7 Gateway platform."
    DEFVAL          { outOfService }
    ::= { sonusSs7GatewayEntry 8 }

sonusSs7GatewayPriHostOosDelayTimer OBJECT-TYPE
    SYNTAX          INTEGER (0..1440)
    ACCESS          read-write
    STATUS          mandatory
    DESCRIPTION     
            "This element is used to delay the action of taking the primary host link out of
             service for a specified number of minutes."
    DEFVAL          { 0 }
    ::= { sonusSs7GatewayEntry 9 }

sonusSs7GatewaySecHostName OBJECT-TYPE
    SYNTAX          DisplayString (SIZE(1..39))
    ACCESS          read-write
    STATUS          mandatory
    DESCRIPTION     
            "The host name of the secondary link to the SS7 Gateway platform."
    ::= { sonusSs7GatewayEntry 10 }

sonusSs7GatewaySecHostIpaddr OBJECT-TYPE
    SYNTAX          IpAddress
    ACCESS          read-write
    STATUS          mandatory
    DESCRIPTION     
            "Specifies the IP Address of the secondary link to the SS7 Gateway platform."
    ::= { sonusSs7GatewayEntry 11 }

sonusSs7GatewaySecHostMode OBJECT-TYPE
    SYNTAX          INTEGER { inService(1), outOfService(2) }
    ACCESS          read-write
    STATUS          mandatory
    DESCRIPTION     
            "Specifies the service mode of the secondary link to the SS7 Gateway platform."
    DEFVAL          { outOfService }
    ::= { sonusSs7GatewayEntry 12 }

sonusSs7GatewaySecHostOosDelayTimer OBJECT-TYPE
    SYNTAX          INTEGER (0..1440)
    ACCESS          read-write
    STATUS          mandatory
    DESCRIPTION     
            "This element is used to delay the action of taking the secondary host link out of
             service for a specified number of minutes."
    DEFVAL          { 0 }
    ::= { sonusSs7GatewayEntry 13 }

sonusSs7GatewayRowStatus OBJECT-TYPE
    SYNTAX          RowStatus
    ACCESS          read-write
    STATUS          mandatory
    DESCRIPTION     
            ""
    ::= { sonusSs7GatewayEntry 14 }

sonusSs7GatewayPriAltHostIpaddr OBJECT-TYPE
    SYNTAX          IpAddress
    ACCESS          read-write
    STATUS          mandatory
    DESCRIPTION     
            "Specifies the alternate IP Address of the primary link to the SS7 Gateway platform."
    ::= { sonusSs7GatewayEntry 15 }

sonusSs7GatewaySecAltHostIpaddr OBJECT-TYPE
    SYNTAX          IpAddress
    ACCESS          read-write
    STATUS          mandatory
    DESCRIPTION     
            "Specifies the alternate IP Address of the secondary link to the SS7 Gateway platform."
    ::= { sonusSs7GatewayEntry 16 }

sonusSs7GatewayGwType OBJECT-TYPE
    SYNTAX          INTEGER { tali(1), dgms(2), m3ua(3) }
    ACCESS          read-write
    STATUS          mandatory
    DESCRIPTION     
            "Gateway type is identified by the gateway protocol it uses"
    DEFVAL          { dgms }
    ::= { sonusSs7GatewayEntry 17 }

sonusSs7GatewayServerTcpPort OBJECT-TYPE
    SYNTAX          INTEGER (1024..65535)
    ACCESS          read-write
    STATUS          mandatory
    DESCRIPTION     
            "SCTP/TCP port for the server of M3UA association or TALI connection"
    ::= { sonusSs7GatewayEntry 18 }

sonusSs7GatewayClientTcpPort OBJECT-TYPE
    SYNTAX          INTEGER (0 | 1024..65535)
    ACCESS          read-write
    STATUS          mandatory
    DESCRIPTION     
            "SCTP/TCP port for the client of M3UA association or TALI connection.  When 0 is selected, it means that it is to be assigned by SCTP/TCP"
    DEFVAL          { 0 }
    ::= { sonusSs7GatewayEntry 19 }

sonusSs7GatewayPriTaliTrafficControl OBJECT-TYPE
    SYNTAX          INTEGER { allow(1), prohibit(2) }
    ACCESS          read-write
    STATUS          mandatory
    DESCRIPTION     
            "Control the ss7 traffic on the primary TALI connection"
    DEFVAL          { allow }
    ::= { sonusSs7GatewayEntry 20 }

sonusSs7GatewayPriAltTaliTrafficControl OBJECT-TYPE
    SYNTAX          INTEGER { allow(1), prohibit(2) }
    ACCESS          read-write
    STATUS          mandatory
    DESCRIPTION     
            "Control the ss7 traffic on the primary TALI connection"
    DEFVAL          { allow }
    ::= { sonusSs7GatewayEntry 21 }

sonusSs7GatewaySecTaliTrafficControl OBJECT-TYPE
    SYNTAX          INTEGER { allow(1), prohibit(2) }
    ACCESS          read-write
    STATUS          mandatory
    DESCRIPTION     
            "Control the ss7 traffic on the secondary TALI connection"
    DEFVAL          { allow }
    ::= { sonusSs7GatewayEntry 22 }

sonusSs7GatewaySecAltTaliTrafficControl OBJECT-TYPE
    SYNTAX          INTEGER { allow(1), prohibit(2) }
    ACCESS          read-write
    STATUS          mandatory
    DESCRIPTION     
            "Control the ss7 traffic on the secondary TALI connection"
    DEFVAL          { allow }
    ::= { sonusSs7GatewayEntry 23 }

sonusSs7GatewayTimerTaliT1 OBJECT-TYPE
    SYNTAX          INTEGER (100..60000)
    ACCESS          read-write
    STATUS          mandatory
    DESCRIPTION     
            "Send a TALI-TEST upon the expiry of T1 in millisecond."
    DEFVAL          { 4000 }
    ::= { sonusSs7GatewayEntry 24 }

sonusSs7GatewayTimerTaliT2 OBJECT-TYPE
    SYNTAX          INTEGER (100..60000)
    ACCESS          read-write
    STATUS          mandatory
    DESCRIPTION     
            "Guard timer in millisecond for the return of TALI-ALLO or 
             TALI-PROH in response to a TALI-TEST sent earlier."
    DEFVAL          { 3000 }
    ::= { sonusSs7GatewayEntry 25 }

sonusSs7GatewayTimerTaliT3 OBJECT-TYPE
    SYNTAX          INTEGER (100..60000)
    ACCESS          read-write
    STATUS          mandatory
    DESCRIPTION     
            "T3 in millisecond reprsents how long the near end can continue
             to process received messages after sending TALI-PROH."
    DEFVAL          { 5000 }
    ::= { sonusSs7GatewayEntry 26 }

sonusSs7GatewayTimerTaliT4 OBJECT-TYPE
    SYNTAX          INTEGER (100..60000)
    ACCESS          read-write
    STATUS          mandatory
    DESCRIPTION     
            "Send a TALI-MONI upon the expiry of T4 in millisecond."
    DEFVAL          { 10000 }
    ::= { sonusSs7GatewayEntry 27 }

sonusSs7GatewayTaliSs7Type OBJECT-TYPE
    SYNTAX          INTEGER { ansi(1), ituIntl(2), ituNatl(3), 
                        ituNatlGC(4) }
    ACCESS          read-write
    STATUS          mandatory
    DESCRIPTION     
            "SS7 protocol types used over TALI, where ituNatlGC for ITU-NATL with Group Code"
    DEFVAL          { ansi }
    ::= { sonusSs7GatewayEntry 28 }

sonusSs7GatewaySlsBits OBJECT-TYPE
    SYNTAX          INTEGER (4..8)
    ACCESS          read-write
    STATUS          mandatory
    DESCRIPTION     
            "The number of SLS bits to use"
    DEFVAL          { 5 }
    ::= { sonusSs7GatewayEntry 29 }

sonusSs7GatewayTaliIsupNormalization OBJECT-TYPE
    SYNTAX          INTEGER { norm(1), raw(2) }
    ACCESS          read-write
    STATUS          mandatory
    DESCRIPTION     
            "ISUP message format over TALI -- normalized or raw"
    DEFVAL          { raw }
    ::= { sonusSs7GatewayEntry 30 }

sonusSs7GatewayTaliPstnPresentation OBJECT-TYPE
    SYNTAX          INTEGER { q767(1), etsiIsup(2), ukIsup(3), grIsup(4) }
    ACCESS          read-write
    STATUS          mandatory
    DESCRIPTION     
            "ISUP types over TALI"
    DEFVAL          { etsiIsup }
    ::= { sonusSs7GatewayEntry 31 }

sonusSs7GatewayTaliGroupCode OBJECT-TYPE
    SYNTAX          DisplayString (SIZE(2))
    ACCESS          read-write
    STATUS          mandatory
    DESCRIPTION     
            "Group Code in ASCII"
    DEFVAL          { "aa" }
    ::= { sonusSs7GatewayEntry 32 }

sonusSs7GatewayM3uaAckTimer OBJECT-TYPE
    SYNTAX          INTEGER (100..60000)
    ACCESS          read-write
    STATUS          mandatory
    DESCRIPTION     
            "When the GSX sends an ASPUP/ASPDN/ASPAC/ASPIA message it starts a timer with this parameter value in ms.  If the ASP does not receive a response before the timer expires, the GSX MAY restart the timer and resend the message until it receives an Ack message."
    DEFVAL          { 2000 }
    ::= { sonusSs7GatewayEntry 33 }

sonusSs7GatewayM3uaAuditTimer OBJECT-TYPE
    SYNTAX          INTEGER (1000..60000)
    ACCESS          read-write
    STATUS          mandatory
    DESCRIPTION     
            "The DAUD message MAY be sent from the GSX to the SGX to audit the availability/congestion state of SS7 routes from the SG to one or more affected destinations after they have become unavailable/congested for an interval specified by this parameter in ms."
    DEFVAL          { 10000 }
    ::= { sonusSs7GatewayEntry 34 }

sonusSs7GatewaySctpRtoInitial OBJECT-TYPE
    SYNTAX          INTEGER (100..60000)
    ACCESS          read-write
    STATUS          mandatory
    DESCRIPTION     
            "An SCTP endpoint uses a retransmission timer to ensure data delivery in the absence of any feedback from its peer.  The duration of this timer is referred to as RTO (retransmission timeout).  Until an RTT (Round Trip Time) measurement has been made for a packet sent to the given destination transport address, set RTO to this protocol parameter in ms."
    DEFVAL          { 700 }
    ::= { sonusSs7GatewayEntry 35 }

sonusSs7GatewaySctpRtoMin OBJECT-TYPE
    SYNTAX          INTEGER (100..60000)
    ACCESS          read-write
    STATUS          mandatory
    DESCRIPTION     
            "An SCTP endpoint uses a retransmission timer to ensure data delivery in the absence of any feedback from its peer.  The duration of this timer is referred to as RTO (retransmission timeout).  Whenever RTO is computed, if it is less than RTO.Min seconds then it is rounded up to this protocol parameter iin ms."
    DEFVAL          { 600 }
    ::= { sonusSs7GatewayEntry 36 }

sonusSs7GatewaySctpRtoMax OBJECT-TYPE
    SYNTAX          INTEGER (100..180000)
    ACCESS          read-write
    STATUS          mandatory
    DESCRIPTION     
            "An SCTP endpoint uses a retransmission timer to ensure data delivery in the absence of any feedback from its peer.  The duration of this timer is referred to as RTO (retransmission timeout).  A maximum value may be placed on RTO provided it is at least sonusSs7GatewaySctpRtoMax ms."
    DEFVAL          { 800 }
    ::= { sonusSs7GatewayEntry 37 }

sonusSs7GatewaySctpPathMaxRetrans OBJECT-TYPE
    SYNTAX          INTEGER (1..20)
    ACCESS          read-write
    STATUS          mandatory
    DESCRIPTION     
            "Each time the T3-rtx timer expires on any address, or when a HEARTBEAT sent to an idle address is not acknowledged within a RTO, the error counter of that destination address will be incremented.  When the value in the error counter exceeds this protocol parameter that destination address, the endpoint should mark the destination transport address as inactive."
    DEFVAL          { 2 }
    ::= { sonusSs7GatewayEntry 38 }

sonusSs7GatewaySctpInitMaxRetrans OBJECT-TYPE
    SYNTAX          INTEGER (2..30)
    ACCESS          read-write
    STATUS          mandatory
    DESCRIPTION     
            "If the T1-init/T1-cookie timer expires, the endpoint MUST retransmit INIT/COOKIE ECHO and re-start the T1-init/T1-cookie timer without changing state.  This MUST be repeated up to Max.Init.Retransmits times.  After that, the endpoint MUST abort the initialization process and report the error to SCTP user."
    DEFVAL          { 5 }
    ::= { sonusSs7GatewayEntry 39 }

sonusSs7GatewaySctpHeartBeatInterval OBJECT-TYPE
    SYNTAX          INTEGER (50..60000)
    ACCESS          read-write
    STATUS          mandatory
    DESCRIPTION     
            "An SCTP endpoint shall monitor the reachability of the idle destination transport address(es) of its peer by sending a HEARTBEAT chunk periodically to the destination transport address(es).  This parameter, combined with other parameters determine how often in ms a HEARTBEAT should be sent when needed."
    DEFVAL          { 100 }
    ::= { sonusSs7GatewayEntry 40 }

sonusSs7GatewayPriHostIp6addr OBJECT-TYPE
    SYNTAX          Ipv6Address
    ACCESS          read-write
    STATUS          mandatory
    DESCRIPTION     
            "Specifies the IPV6Address of the primary link to the SS7 Gateway platform."
    ::= { sonusSs7GatewayEntry 41 }

sonusSs7GatewayPriAltHostIp6addr OBJECT-TYPE
    SYNTAX          Ipv6Address
    ACCESS          read-write
    STATUS          mandatory
    DESCRIPTION     
            "Specifies the alternate IPV6Address of the primary link to the SS7 Gateway platform."
    ::= { sonusSs7GatewayEntry 42 }

sonusSs7GatewaySecHostIp6addr OBJECT-TYPE
    SYNTAX          Ipv6Address
    ACCESS          read-write
    STATUS          mandatory
    DESCRIPTION     
            "Specifies the IPV6 Address of the secondary link to the SS7 Gateway platform."
    ::= { sonusSs7GatewayEntry 43 }

sonusSs7GatewaySecAltHostIp6addr OBJECT-TYPE
    SYNTAX          Ipv6Address
    ACCESS          read-write
    STATUS          mandatory
    DESCRIPTION     
            "Specifies the alternate IP Address of the secondary link to the SS7 Gateway platform."
    ::= { sonusSs7GatewayEntry 44 }

sonusSs7GatewayIpVersion OBJECT-TYPE
    SYNTAX          INTEGER { afInet(2), afInet6(24) }
    ACCESS          read-only
    STATUS          mandatory
    DESCRIPTION     
            "IP Address version of SS7 Gateway "
    ::= { sonusSs7GatewayEntry 45 }

sonusSs7GatewayIpVersionSec OBJECT-TYPE
    SYNTAX          INTEGER { afInet(2), afInet6(24) }
    ACCESS          read-only
    STATUS          mandatory
    DESCRIPTION     
            "IP Address version of SS7 Gateway "
    ::= { sonusSs7GatewayEntry 46 }

sonusSs7GatewayStatusTable OBJECT-TYPE
    SYNTAX          SEQUENCE OF SonusSs7GatewayStatusEntry
    ACCESS          not-accessible
    STATUS          mandatory
    DESCRIPTION     
            "Status Table of the SS7 Gateway for the GSX9000 node."
    ::= { sonusSs7Gateway 3 }

sonusSs7GatewayStatusEntry OBJECT-TYPE
    SYNTAX          SonusSs7GatewayStatusEntry
    ACCESS          not-accessible
    STATUS          mandatory
    DESCRIPTION     
            "List of SS7 Gateway status elements."
    INDEX           { sonusSs7GatewayStatusIndex }
    ::= { sonusSs7GatewayStatusTable 1 }

SonusSs7GatewayStatusEntry ::=
    SEQUENCE {
        sonusSs7GatewayStatusIndex      INTEGER,
        sonusSs7GatewayNextHost         SonusSs7GatewayLinkSelection,
        sonusSs7GatewaySelectHost       SonusSs7GatewayLinkSelection,
        sonusSs7GatewayPriTaliConnState INTEGER,
        sonusSs7GatewaySecTaliConnState INTEGER,
        sonusSs7GatewayPriAltTaliConnState  INTEGER,
        sonusSs7GatewaySecAltTaliConnState  INTEGER,
        sonusSs7GatewayPriNearEndTaliVersion    DisplayString,
        sonusSs7GatewayPriFarEndTaliVersion   DisplayString,
        sonusSs7GatewayPriAltNearEndTaliVersion       DisplayString,
        sonusSs7GatewayPriAltFarEndTaliVersion      DisplayString,
        sonusSs7GatewaySecNearEndTaliVersion    DisplayString,
        sonusSs7GatewaySecFarEndTaliVersion   DisplayString,
        sonusSs7GatewaySecAltNearEndTaliVersion       DisplayString,
        sonusSs7GatewaySecAltFarEndTaliVersion      DisplayString,
        sonusSs7GatewayPriAssocState    INTEGER,
        sonusSs7GatewaySecAssocState    INTEGER,
        sonusSs7GatewayPriAssocPrimaryPath  IpAddress,
        sonusSs7GatewaySecAssocPrimaryPath  IpAddress,
        sonusSs7GatewayPriAssocPrimaryV6Path    Ipv6Address,
        sonusSs7GatewaySecAssocPrimaryV6Path    Ipv6Address,
        sonusSs7GatewayPriPathIpVersion INTEGER,
        sonusSs7GatewaySecPathIpVersion INTEGER
    }

sonusSs7GatewayStatusIndex OBJECT-TYPE
    SYNTAX          INTEGER
    ACCESS          read-only
    STATUS          mandatory
    DESCRIPTION     
            "Identifies the SS7 Gateway status entry."
    ::= { sonusSs7GatewayStatusEntry 1 }

sonusSs7GatewayNextHost OBJECT-TYPE
    SYNTAX          SonusSs7GatewayLinkSelection
    ACCESS          read-only
    STATUS          mandatory
    DESCRIPTION     
            "Indicates which host link connection to the SS7 Gateway is next to be
             selected. If there is none, then this element is set to none."
    DEFVAL          { none }
    ::= { sonusSs7GatewayStatusEntry 2 }

sonusSs7GatewaySelectHost OBJECT-TYPE
    SYNTAX          SonusSs7GatewayLinkSelection
    ACCESS          read-only
    STATUS          mandatory
    DESCRIPTION     
            "Indicates which host link connection to the SS7 Gateway is selected
             to be tried. If there is none, then this element is set to none."
    DEFVAL          { none }
    ::= { sonusSs7GatewayStatusEntry 3 }

sonusSs7GatewayPriTaliConnState OBJECT-TYPE
    SYNTAX          INTEGER { oos(1), connecting(2), nepFep(3), 
                        nepFea(4), neaFep(5), neaFea(6) }
    ACCESS          read-only
    STATUS          mandatory
    DESCRIPTION     
            "TALI state of the primary connection for this SS7 gateway."
    DEFVAL          { oos }
    ::= { sonusSs7GatewayStatusEntry 4 }

sonusSs7GatewaySecTaliConnState OBJECT-TYPE
    SYNTAX          INTEGER { oos(1), connecting(2), nepFep(3), 
                        nepFea(4), neaFep(5), neaFea(6) }
    ACCESS          read-only
    STATUS          mandatory
    DESCRIPTION     
            "TALI state of the secondary connection for this SS7 gateway."
    DEFVAL          { oos }
    ::= { sonusSs7GatewayStatusEntry 5 }

sonusSs7GatewayPriAltTaliConnState OBJECT-TYPE
    SYNTAX          INTEGER { oos(1), connecting(2), nepFep(3), 
                        nepFea(4), neaFep(5), neaFea(6) }
    ACCESS          read-only
    STATUS          mandatory
    DESCRIPTION     
            "TALI state of the primary alt connection for this SS7 gateway."
    DEFVAL          { oos }
    ::= { sonusSs7GatewayStatusEntry 6 }

sonusSs7GatewaySecAltTaliConnState OBJECT-TYPE
    SYNTAX          INTEGER { oos(1), connecting(2), nepFep(3), 
                        nepFea(4), neaFep(5), neaFea(6) }
    ACCESS          read-only
    STATUS          mandatory
    DESCRIPTION     
            "TALI state of the secondary alt connection for this SS7 gateway."
    DEFVAL          { oos }
    ::= { sonusSs7GatewayStatusEntry 7 }

sonusSs7GatewayPriNearEndTaliVersion OBJECT-TYPE
    SYNTAX          DisplayString (SIZE(7))
    ACCESS          read-only
    STATUS          mandatory
    DESCRIPTION     
            "The protocol version at the near end of the TALI primary 
             conncection, or M3UA primary association"
    DEFVAL          { "001.000" }
    ::= { sonusSs7GatewayStatusEntry 8 }

sonusSs7GatewayPriFarEndTaliVersion OBJECT-TYPE
    SYNTAX          DisplayString (SIZE(7))
    ACCESS          read-only
    STATUS          mandatory
    DESCRIPTION     
            "The protocol version at the far end of the TALI primary 
             conncection, or M3UA primary association"
    DEFVAL          { "001.000" }
    ::= { sonusSs7GatewayStatusEntry 9 }

sonusSs7GatewayPriAltNearEndTaliVersion OBJECT-TYPE
    SYNTAX          DisplayString (SIZE(7))
    ACCESS          read-only
    STATUS          mandatory
    DESCRIPTION     
            "TALI protocol version at the near end of the pri-alt conn."
    DEFVAL          { "001.000" }
    ::= { sonusSs7GatewayStatusEntry 10 }

sonusSs7GatewayPriAltFarEndTaliVersion OBJECT-TYPE
    SYNTAX          DisplayString (SIZE(7))
    ACCESS          read-only
    STATUS          mandatory
    DESCRIPTION     
            "TALI protocol version at the far end of the pri-alt connection"
    DEFVAL          { "001.000" }
    ::= { sonusSs7GatewayStatusEntry 11 }

sonusSs7GatewaySecNearEndTaliVersion OBJECT-TYPE
    SYNTAX          DisplayString (SIZE(7))
    ACCESS          read-only
    STATUS          mandatory
    DESCRIPTION     
            "The protocol version at the near end of the TALI secondary 
             conncection, or M3UA secondary association"
    DEFVAL          { "001.000" }
    ::= { sonusSs7GatewayStatusEntry 12 }

sonusSs7GatewaySecFarEndTaliVersion OBJECT-TYPE
    SYNTAX          DisplayString (SIZE(7))
    ACCESS          read-only
    STATUS          mandatory
    DESCRIPTION     
            "The protocol version at the far end of the TALI secondary 
             conncection, or M3UA secondary association"
    DEFVAL          { "001.000" }
    ::= { sonusSs7GatewayStatusEntry 13 }

sonusSs7GatewaySecAltNearEndTaliVersion OBJECT-TYPE
    SYNTAX          DisplayString (SIZE(7))
    ACCESS          read-only
    STATUS          mandatory
    DESCRIPTION     
            "TALI protocol version at the near end of the sec-alt conn."
    DEFVAL          { "001.000" }
    ::= { sonusSs7GatewayStatusEntry 14 }

sonusSs7GatewaySecAltFarEndTaliVersion OBJECT-TYPE
    SYNTAX          DisplayString (SIZE(7))
    ACCESS          read-only
    STATUS          mandatory
    DESCRIPTION     
            "TALI protocol version at the far end of the sec-alt connection"
    DEFVAL          { "001.000" }
    ::= { sonusSs7GatewayStatusEntry 15 }

sonusSs7GatewayPriAssocState OBJECT-TYPE
    SYNTAX          INTEGER { oos(1), connecting(2), aspUpSent(3), 
                        aspUp(4), aspDnSent(5), aspDown(6) }
    ACCESS          read-only
    STATUS          mandatory
    DESCRIPTION     
            "The state of the primary association to this SS7 gateway."
    DEFVAL          { oos }
    ::= { sonusSs7GatewayStatusEntry 16 }

sonusSs7GatewaySecAssocState OBJECT-TYPE
    SYNTAX          INTEGER { oos(1), connecting(2), aspUpSent(3), 
                        aspUp(4), aspDnSent(5), aspDown(6) }
    ACCESS          read-only
    STATUS          mandatory
    DESCRIPTION     
            "The state of the secondary association to this SS7 gateway."
    DEFVAL          { oos }
    ::= { sonusSs7GatewayStatusEntry 17 }

sonusSs7GatewayPriAssocPrimaryPath OBJECT-TYPE
    SYNTAX          IpAddress
    ACCESS          read-only
    STATUS          mandatory
    DESCRIPTION     
            "Specifies the current primary path Address of the pri-association to the SS7 Gateway platform."
    ::= { sonusSs7GatewayStatusEntry 18 }

sonusSs7GatewaySecAssocPrimaryPath OBJECT-TYPE
    SYNTAX          IpAddress
    ACCESS          read-only
    STATUS          mandatory
    DESCRIPTION     
            "Specifies the current primary path Address of the sec-association to the SS7 Gateway platform."
    ::= { sonusSs7GatewayStatusEntry 19 }

sonusSs7GatewayPriAssocPrimaryV6Path OBJECT-TYPE
    SYNTAX          Ipv6Address
    ACCESS          read-only
    STATUS          mandatory
    DESCRIPTION     
            "Specifies the current primary path IPV6 Address of the pri-association to the SS7 Gateway platform."
    ::= { sonusSs7GatewayStatusEntry 20 }

sonusSs7GatewaySecAssocPrimaryV6Path OBJECT-TYPE
    SYNTAX          Ipv6Address
    ACCESS          read-only
    STATUS          mandatory
    DESCRIPTION     
            "Specifies the current primary path IPV6 Address of the sec-association to the SS7 Gateway platform."
    ::= { sonusSs7GatewayStatusEntry 21 }

sonusSs7GatewayPriPathIpVersion OBJECT-TYPE
    SYNTAX          INTEGER { afInet(2), afInet6(24) }
    ACCESS          read-only
    STATUS          mandatory
    DESCRIPTION     
            "IP Address version of SS7 Gateway "
    ::= { sonusSs7GatewayStatusEntry 22 }

sonusSs7GatewaySecPathIpVersion OBJECT-TYPE
    SYNTAX          INTEGER { afInet(2), afInet6(24) }
    ACCESS          read-only
    STATUS          mandatory
    DESCRIPTION     
            "IP Address version of SS7 Gateway "
    ::= { sonusSs7GatewayStatusEntry 23 }

sonusSs7GatewayPSStatusTable OBJECT-TYPE
    SYNTAX          SEQUENCE OF SonusSs7GatewayPSStatusEntry
    ACCESS          not-accessible
    STATUS          obsolete
    DESCRIPTION     
            "Status Table of the SS7 Gateway of a PRIMARY or SECONDARY for the
             GSX9000 node. This object is obsoleted as of GSX release 5.0.1 .
             This table, and sonusSs7GatewayLinkStatusTable are replaced by
             a single table sonusSs7NodeGatewayLinkStatusTable."
    ::= { sonusSs7Gateway 4 }

sonusSs7GatewayPSStatusEntry OBJECT-TYPE
    SYNTAX          SonusSs7GatewayPSStatusEntry
    ACCESS          not-accessible
    STATUS          obsolete
    DESCRIPTION     
            "List of SS7 Gateway status elements.
             This object is obsoleted as of GSX release 5.0.1"
    INDEX           { sonusSs7GatewayPSStatusIndex, 
                      sonusSs7GatewayPSStatusPSIndex }
    ::= { sonusSs7GatewayPSStatusTable 1 }

SonusSs7GatewayPSStatusEntry ::=
    SEQUENCE {
        sonusSs7GatewayPSStatusIndex    INTEGER,
        sonusSs7GatewayPSStatusPSIndex  INTEGER,
        sonusSs7GatewayPSStatusPrimaryCE INTEGER,
        sonusSs7GatewayPSStatusActiveLink INTEGER
    }

sonusSs7GatewayPSStatusIndex OBJECT-TYPE
    SYNTAX          INTEGER
    ACCESS          read-only
    STATUS          obsolete
    DESCRIPTION     
            "Identifies the SS7 Gateway status entry.
             This object is obsoleted as of GSX release 5.0.1"
    ::= { sonusSs7GatewayPSStatusEntry 1 }

sonusSs7GatewayPSStatusPSIndex OBJECT-TYPE
    SYNTAX          INTEGER { primary(0), secondary(1), primaryAlt(2), 
                        secondaryAlt(3) }
    ACCESS          read-only
    STATUS          obsolete
    DESCRIPTION     
            "Identifies the SS7 Gateway link status entry.
             This object is obsoleted as of GSX release 5.0.1"
    ::= { sonusSs7GatewayPSStatusEntry 2 }

sonusSs7GatewayPSStatusPrimaryCE OBJECT-TYPE
    SYNTAX          INTEGER
    ACCESS          read-only
    STATUS          obsolete
    DESCRIPTION     
            "Identifies the link Primary CE value.
             This object is obsoleted as of GSX release 5.0.1"
    ::= { sonusSs7GatewayPSStatusEntry 3 }

sonusSs7GatewayPSStatusActiveLink OBJECT-TYPE
    SYNTAX          INTEGER (0..16)
    ACCESS          read-only
    STATUS          obsolete
    DESCRIPTION     
            "Identifies the link active entry.
             This object is obsoleted as of GSX release 5.0.1"
    ::= { sonusSs7GatewayPSStatusEntry 4 }

sonusSs7GatewayLinkStatusTable OBJECT-TYPE
    SYNTAX          SEQUENCE OF SonusSs7GatewayLinkStatusEntry
    ACCESS          not-accessible
    STATUS          obsolete
    DESCRIPTION     
            "Link Status Table of a SS7 Gateway for the GSX9000 node.
             This table is obsoleted as of GSX release 5.0.1 . This 
             table is replaced by sonusSs7NodeGatewayLinkStatusTable. "
    ::= { sonusSs7Gateway 5 }

sonusSs7GatewayLinkStatusEntry OBJECT-TYPE
    SYNTAX          SonusSs7GatewayLinkStatusEntry
    ACCESS          not-accessible
    STATUS          obsolete
    DESCRIPTION     
            "List of SS7 Gateway Link Status elements.This object
             is obsoleted as of GSX release 5.0.1 "
    INDEX           { sonusSs7GatewayStatusLinkIndex, 
                      sonusSs7GatewayStatusLinkPSIndex, 
                      sonusSs7GatewayStatusLinkHostIndex }
    ::= { sonusSs7GatewayLinkStatusTable 1 }

SonusSs7GatewayLinkStatusEntry ::=
    SEQUENCE {
        sonusSs7GatewayStatusLinkIndex  INTEGER,
        sonusSs7GatewayStatusLinkPSIndex INTEGER,
        sonusSs7GatewayStatusLinkHostIndex  INTEGER,
        sonusSs7GatewayStatusHostName   DisplayString,
        sonusSs7GatewayStatusHostIpaddr IpAddress,
        sonusSs7GatewayStatusHostState  INTEGER,
        sonusSs7GatewayStatusHostCE     INTEGER
    }

sonusSs7GatewayStatusLinkIndex OBJECT-TYPE
    SYNTAX          INTEGER
    ACCESS          read-only
    STATUS          obsolete
    DESCRIPTION     
            "Identifies the SS7 Gateway status link entry gateway
             index.This object is obsoleted as of GSX release 5.0.1"
    ::= { sonusSs7GatewayLinkStatusEntry 1 }

sonusSs7GatewayStatusLinkPSIndex OBJECT-TYPE
    SYNTAX          INTEGER { primary(1), secondary(2), primaryAlt(3), 
                        secondaryAlt(4) }
    ACCESS          read-only
    STATUS          obsolete
    DESCRIPTION     
            "Identifies the SS7 Gateway status link entry primary or secondary index.
             This object is obsoleted as of GSX release 5.0.1"
    ::= { sonusSs7GatewayLinkStatusEntry 2 }

sonusSs7GatewayStatusLinkHostIndex OBJECT-TYPE
    SYNTAX          INTEGER
    ACCESS          read-only
    STATUS          obsolete
    DESCRIPTION     
            "Identifies the SS7 Gateway host status link entry index.
             This object is obsoleted as of GSX release 5.0.1"
    ::= { sonusSs7GatewayLinkStatusEntry 3 }

sonusSs7GatewayStatusHostName OBJECT-TYPE
    SYNTAX          DisplayString (SIZE(1..39))
    ACCESS          read-only
    STATUS          obsolete
    DESCRIPTION     
            "The host name of the Link link to the SS7 Gateway platform.
             This object is obsoleted as of GSX release 5.0.1"
    ::= { sonusSs7GatewayLinkStatusEntry 4 }

sonusSs7GatewayStatusHostIpaddr OBJECT-TYPE
    SYNTAX          IpAddress
    ACCESS          read-only
    STATUS          obsolete
    DESCRIPTION     
            "Specifies the IP Address of the link to the SS7 Gateway platform.
             This object is obsoleted as of GSX release 5.0.1"
    ::= { sonusSs7GatewayLinkStatusEntry 5 }

sonusSs7GatewayStatusHostState OBJECT-TYPE
    SYNTAX          INTEGER { empty(1), init(2), available(3), broken(4) }
    ACCESS          read-only
    STATUS          obsolete
    DESCRIPTION     
            "The state of host link to the SS7 Gateway platform.
             This object is obsoleted as of GSX release 5.0.1"
    ::= { sonusSs7GatewayLinkStatusEntry 6 }

sonusSs7GatewayStatusHostCE OBJECT-TYPE
    SYNTAX          INTEGER
    ACCESS          read-only
    STATUS          obsolete
    DESCRIPTION     
            "The CE of host link to the SS7 Gateway platform.
             This object is obsoleted as of GSX release 5.0.1"
    ::= { sonusSs7GatewayLinkStatusEntry 7 }

sonusSs7NodeStatusTable OBJECT-TYPE
    SYNTAX          SEQUENCE OF SonusSs7NodeStatusEntry
    ACCESS          not-accessible
    STATUS          mandatory
    DESCRIPTION     
            "Status Table of the SS7 Node for the GSX9000 node."
    ::= { sonusSs7Gateway 6 }

sonusSs7NodeStatusEntry OBJECT-TYPE
    SYNTAX          SonusSs7NodeStatusEntry
    ACCESS          not-accessible
    STATUS          mandatory
    DESCRIPTION     
            "List of SS7 Node status elements."
    INDEX           { sonusSs7NodeStatusIndex }
    ::= { sonusSs7NodeStatusTable 1 }

SonusSs7NodeStatusEntry ::=
    SEQUENCE {
        sonusSs7NodeStatusIndex         INTEGER,
        sonusSs7NodeStatIsup            INTEGER,
        sonusSs7NodeStatMtp             INTEGER,
        sonusSs7NodeStatGatewayName     DisplayString,
        sonusSs7NodeStatPrimaryCe       INTEGER,
        sonusSs7NodeStatGatewaySocketType INTEGER,
        sonusSs7NodeStatAltGatewayName  DisplayString
    }

sonusSs7NodeStatusIndex OBJECT-TYPE
    SYNTAX          INTEGER
    ACCESS          read-only
    STATUS          mandatory
    DESCRIPTION     
            "Identifies the SS7 Node status entry."
    ::= { sonusSs7NodeStatusEntry 1 }

sonusSs7NodeStatIsup OBJECT-TYPE
    SYNTAX          INTEGER { offline(1), active(2), initializing(3), 
                        failed(4), disabled(5), congested(6) }
    ACCESS          read-only
    STATUS          mandatory
    DESCRIPTION     
            "Specifies the operating status of the ISUP service within this SS7 Node."
    DEFVAL          { offline }
    ::= { sonusSs7NodeStatusEntry 2 }

sonusSs7NodeStatMtp OBJECT-TYPE
    SYNTAX          INTEGER { paused(1), resumed(2) }
    ACCESS          read-only
    STATUS          mandatory
    DESCRIPTION     
            "Specifies the current MTP status for this SS7 Node."
    DEFVAL          { paused }
    ::= { sonusSs7NodeStatusEntry 3 }

sonusSs7NodeStatGatewayName OBJECT-TYPE
    SYNTAX          DisplayString (SIZE(1..23))
    ACCESS          read-only
    STATUS          mandatory
    DESCRIPTION     
            "The name of the SS7 Gateway to which this SS7 Node is assigned."
    ::= { sonusSs7NodeStatusEntry 4 }

sonusSs7NodeStatPrimaryCe OBJECT-TYPE
    SYNTAX          INTEGER { ce0(1), ce1(2), none(3) }
    ACCESS          read-only
    STATUS          mandatory
    DESCRIPTION     
            "Identifies the CE on which primary copy of SGX is running currently"
    DEFVAL          { none }
    ::= { sonusSs7NodeStatusEntry 5 }

sonusSs7NodeStatGatewaySocketType OBJECT-TYPE
    SYNTAX          INTEGER { none(1), tcp(2), udp(3) }
    ACCESS          read-only
    STATUS          mandatory
    DESCRIPTION     
            "Identifies the transport protocol used to talk to SGX"
    DEFVAL          { none }
    ::= { sonusSs7NodeStatusEntry 6 }

sonusSs7NodeStatAltGatewayName OBJECT-TYPE
    SYNTAX          DisplayString (SIZE(1..23))
    ACCESS          read-only
    STATUS          mandatory
    DESCRIPTION     
            "The name of the SS7 alternate gateway to which this SS7 
             Node is assigned in the case of geographic redundancy."
    ::= { sonusSs7NodeStatusEntry 7 }

sonusSs7NodeGatewayLinkStatusTable OBJECT-TYPE
    SYNTAX          SEQUENCE OF SonusSs7NodeGatewayLinkStatusEntry
    ACCESS          not-accessible
    STATUS          mandatory
    DESCRIPTION     
            "Link Status Table of a SS7 Node Gateway for the GSX9000 node."
    ::= { sonusSs7Gateway 7 }

sonusSs7NodeGatewayLinkStatusEntry OBJECT-TYPE
    SYNTAX          SonusSs7NodeGatewayLinkStatusEntry
    ACCESS          not-accessible
    STATUS          mandatory
    DESCRIPTION     
            "List of SS7 Node Gateway Host Link Status elements."
    INDEX           { sonusSs7NodeGatewayLinkStatNodeIndex, 
                      sonusSs7NodeGatewayLinkStatMnsIndex, 
                      sonusSs7NodeGatewayLinkStatHostIndex }
    ::= { sonusSs7NodeGatewayLinkStatusTable 1 }

SonusSs7NodeGatewayLinkStatusEntry ::=
    SEQUENCE {
        sonusSs7NodeGatewayLinkStatNodeIndex    INTEGER,
        sonusSs7NodeGatewayLinkStatMnsIndex   INTEGER,
        sonusSs7NodeGatewayLinkStatHostIndex    INTEGER,
        sonusSs7NodeGatewayLinkStatHostName   DisplayString,
        sonusSs7NodeGatewayLinkStatHostIpaddr     IpAddress,
        sonusSs7NodeGatewayLinkStatHostState    INTEGER,
        sonusSs7NodeGatewayLinkStatHostCE INTEGER,
        sonusSs7NodeGatewayLinkStatHostLinkStatus         INTEGER
    }

sonusSs7NodeGatewayLinkStatNodeIndex OBJECT-TYPE
    SYNTAX          INTEGER
    ACCESS          read-only
    STATUS          mandatory
    DESCRIPTION     
            "This index identifies the node, for which status of
             the IP links towards SS7 Gateway are to be dsiplayed. "
    ::= { sonusSs7NodeGatewayLinkStatusEntry 1 }

sonusSs7NodeGatewayLinkStatMnsIndex OBJECT-TYPE
    SYNTAX          INTEGER (1..2)
    ACCESS          read-only
    STATUS          mandatory
    DESCRIPTION     
            "This element identifies the Active or, Standby MNS
             index, for which link status informations are to be obtained."
    ::= { sonusSs7NodeGatewayLinkStatusEntry 2 }

sonusSs7NodeGatewayLinkStatHostIndex OBJECT-TYPE
    SYNTAX          INTEGER (1..16)
    ACCESS          read-only
    STATUS          mandatory
    DESCRIPTION     
            "This element represents the index into host entry table, 
             from where the state and status infromation are to be gathered."
    ::= { sonusSs7NodeGatewayLinkStatusEntry 3 }

sonusSs7NodeGatewayLinkStatHostName OBJECT-TYPE
    SYNTAX          DisplayString (SIZE(1..39))
    ACCESS          read-only
    STATUS          mandatory
    DESCRIPTION     
            "The host name of this host link to the SS7 Gateway platform."
    ::= { sonusSs7NodeGatewayLinkStatusEntry 4 }

sonusSs7NodeGatewayLinkStatHostIpaddr OBJECT-TYPE
    SYNTAX          IpAddress
    ACCESS          read-only
    STATUS          mandatory
    DESCRIPTION     
            "This element specifies the IP Address of the host link to the SS7 Gateway."
    ::= { sonusSs7NodeGatewayLinkStatusEntry 5 }

sonusSs7NodeGatewayLinkStatHostState OBJECT-TYPE
    SYNTAX          INTEGER { available(1), unavailable(2) }
    ACCESS          read-only
    STATUS          mandatory
    DESCRIPTION     
            " The element specifies the state of SS7 Gateway  and the state
             of this host link. If the either link, or, SS7 gateway to which the
             link is connected to, goes down, the state becomes un-available.  "
    ::= { sonusSs7NodeGatewayLinkStatusEntry 6 }

sonusSs7NodeGatewayLinkStatHostCE OBJECT-TYPE
    SYNTAX          INTEGER
    ACCESS          read-only
    STATUS          mandatory
    DESCRIPTION     
            "This element specifies the name of the CE to which 
             this host link is connected to. "
    ::= { sonusSs7NodeGatewayLinkStatusEntry 7 }

sonusSs7NodeGatewayLinkStatHostLinkStatus OBJECT-TYPE
    SYNTAX          INTEGER { unequipped(1), active(2), standby(3) }
    ACCESS          read-only
    STATUS          mandatory
    DESCRIPTION     
            "This element specifies whether this link towards SS7 Gateway 
             is currently carrying or, chosen to carry, the data traffic. "
    DEFVAL          { unequipped }
    ::= { sonusSs7NodeGatewayLinkStatusEntry 8 }

sonusSs7Node OBJECT IDENTIFIER
    ::= { sonusSs7ServicesMIBObjects 2 }

sonusSs7NodeNextIndex OBJECT-TYPE
    SYNTAX          INTEGER
    ACCESS          read-only
    STATUS          mandatory
    DESCRIPTION     
            "The next valid index to use when creating an entry in
             the sonusSs7NodeTable."
    ::= { sonusSs7Node 1 }

sonusSs7NodeTable OBJECT-TYPE
    SYNTAX          SEQUENCE OF SonusSs7NodeEntry
    ACCESS          not-accessible
    STATUS          mandatory
    DESCRIPTION     
            "This table specifies the SS7 Node list for the GSX9000 node."
    ::= { sonusSs7Node 2 }

sonusSs7NodeEntry OBJECT-TYPE
    SYNTAX          SonusSs7NodeEntry
    ACCESS          not-accessible
    STATUS          mandatory
    DESCRIPTION     
            ""
    INDEX           { sonusSs7NodeIndex }
    ::= { sonusSs7NodeTable 1 }

SonusSs7NodeEntry ::=
    SEQUENCE {
        sonusSs7NodeIndex               INTEGER,
        sonusSs7NodeState               INTEGER,
        sonusSs7NodeName                SonusName,
        sonusSs7NodePointCode           PointCode,
        sonusSs7NodeServices            INTEGER,
        sonusSs7NodeProtocol            INTEGER,
        sonusSs7NodeTcapSsn             INTEGER,
        sonusSs7NodeIsupStatus          INTEGER,
        sonusSs7NodeTcapStatus          INTEGER,
        sonusSs7NodeMtpStatus           INTEGER,
        sonusSs7NodeGatewayAssignment   DisplayString,
        sonusSs7NodeNativePointCode     INTEGER,
        sonusSs7NodeMode                INTEGER,
        sonusSs7NodeConnCntrl           INTEGER,
        sonusSs7NodeRowStatus           RowStatus,
        sonusSs7NodeStdPointCode        SonusPointCode,
        sonusSs7NodePointCodeSize       INTEGER,
        sonusSs7NodePointCodeFormatType SonusPointCodeFormat,
        sonusSs7NodeServerProtocol      INTEGER,
        sonusSs7NodeHandShakeInterval   INTEGER,
        sonusSs7NodeTimerT1             INTEGER,
        sonusSs7NodeTimerT2             INTEGER,
        sonusSs7NodeTimerT3             INTEGER,
        sonusSs7NodeTimerT4             INTEGER,
        sonusSs7NodeTimerT5             INTEGER,
        sonusSs7NodeTimerT6             INTEGER,
        sonusSs7NodeTimerT7             INTEGER,
        sonusSs7NodeTimerT8             INTEGER,
        sonusSs7NodeTimerT9             INTEGER,
        sonusSs7NodeTimerT10            INTEGER,
        sonusSs7NodeTimerT11            INTEGER,
        sonusSs7NodeTimerT12            INTEGER,
        sonusSs7NodeTimerT13            INTEGER,
        sonusSs7NodeTimerT14            INTEGER,
        sonusSs7NodeTimerT15            INTEGER,
        sonusSs7NodeTimerT16            INTEGER,
        sonusSs7NodeTimerT17            INTEGER,
        sonusSs7NodeTimerT18            INTEGER,
        sonusSs7NodeTimerT19            INTEGER,
        sonusSs7NodeTimerT20            INTEGER,
        sonusSs7NodeTimerT21            INTEGER,
        sonusSs7NodeTimerT22            INTEGER,
        sonusSs7NodeTimerT23            INTEGER,
        sonusSs7NodeTimerT24            INTEGER,
        sonusSs7NodeTimerT25            INTEGER,
        sonusSs7NodeTimerT26            INTEGER,
        sonusSs7NodeTimerT27            INTEGER,
        sonusSs7NodeTimerT28            INTEGER,
        sonusSs7NodeTimerT29            INTEGER,
        sonusSs7NodeTimerT30            INTEGER,
        sonusSs7NodeTimerT31            INTEGER,
        sonusSs7NodeTimerT32            INTEGER,
        sonusSs7NodeTimerT33            INTEGER,
        sonusSs7NodeTimerT34            INTEGER,
        sonusSs7NodeTimerT35            INTEGER,
        sonusSs7NodeTimerT36            INTEGER,
        sonusSs7NodeTimerT37            INTEGER,
        sonusSs7NodeTimerT38            INTEGER,
        sonusSs7NodeTimerT39            INTEGER,
        sonusSs7NodeTimerT40            INTEGER,
        sonusSs7NodeTimerTAcc           INTEGER,
        sonusSs7NodeTimerTCcr           INTEGER,
        sonusSs7NodeTimerTCcrr          INTEGER,
        sonusSs7NodeTimerTCgb           INTEGER,
        sonusSs7NodeTimerTCra           INTEGER,
        sonusSs7NodeTimerTCrm           INTEGER,
        sonusSs7NodeTimerTCvt           INTEGER,
        sonusSs7NodeTimerTExm           INTEGER,
        sonusSs7NodeTimerTGrs           INTEGER,
        sonusSs7NodeTimerTHga           INTEGER,
        sonusSs7NodeTimerTScga          INTEGER,
        sonusSs7NodeTimerTScgad         INTEGER,
        sonusSs7NodeApplProfileName     DisplayString,
        sonusSs7NodeNetworkInd          INTEGER,
        sonusSs7NodeSlsBits             INTEGER,
        sonusSs7NodeTimerTA             INTEGER,
        sonusSs7NodeTimerTBlom          INTEGER,
        sonusSs7NodeTimerTCotd          INTEGER,
        sonusSs7NodeTimerTCotl          INTEGER,
        sonusSs7NodeTimerTSus           INTEGER,
        sonusSs7NodeTimerT6Trans        INTEGER,
        sonusSs7NodeTimerT6Term         INTEGER,
        sonusSs7NodeTimerT9Trans        INTEGER,
        sonusSs7NodeTimerT9Int          INTEGER,
        sonusSs7NodeTimerT9Orig         INTEGER,
        sonusSs7NodeTimerT8a            INTEGER,
        sonusSs7NodeTimerT12a           INTEGER,
        sonusSs7NodeTimerT1a            INTEGER,
        sonusSs7NodeTimerT1b            INTEGER,
        sonusSs7NodeTimerT1c            INTEGER,
        sonusSs7NodeTimerT1d            INTEGER,
        sonusSs7NodeIsupVariant         INTEGER,
        sonusSs7NodeTeardownCalls       INTEGER,
        sonusSs7NodeNetAppearance       Gauge,
        sonusSs7NodeTimerTECSR          INTEGER,
        sonusSs7NodeMtp3MgmtName        DisplayString,
        sonusSs7NodeAltGateway          DisplayString,
        sonusSs7NodeTimerTSusImmediateRel INTEGER,
        sonusSs7NodeIsupUcic            INTEGER,
        sonusSs7NodeTimerSuppressCircuitTraps     INTEGER,
        sonusSs7NodeGenerateNCR         INTEGER,
        sonusSs7NodeGeoRedundancy       INTEGER,
        sonusSs7NodeTimerT42            INTEGER,
        sonusSs7NodeTimerT43            INTEGER,
        sonusSs7NodeTimerTreass         INTEGER,
        sonusSs7NodeTimerTCRGA          INTEGER,
        sonusSs7NodeNifGroupName        SonusNameReference,
        sonusSs7NodeNetworkAccess       INTEGER,
        sonusSs7NodeGatewayPriority     INTEGER,
        sonusSs7NodeGateway1Assignment  DisplayString,
        sonusSs7NodeGateway1Priority    INTEGER,
        sonusSs7NodeAltGatewayPriority  INTEGER,
        sonusSs7NodeSgx4000             INTEGER,
        sonusSs7NodeSlsRotation         INTEGER
    }

sonusSs7NodeIndex OBJECT-TYPE
    SYNTAX          INTEGER
    ACCESS          read-only
    STATUS          mandatory
    DESCRIPTION     
            "Identifies the target SS7 Node entry."
    ::= { sonusSs7NodeEntry 1 }

sonusSs7NodeState OBJECT-TYPE
    SYNTAX          INTEGER { disabled(1), enabled(2) }
    ACCESS          read-write
    STATUS          mandatory
    DESCRIPTION     
            "The administrative state of this SS7 Node entry."
    DEFVAL          { disabled }
    ::= { sonusSs7NodeEntry 2 }

sonusSs7NodeName OBJECT-TYPE
    SYNTAX          SonusName
    ACCESS          read-write
    STATUS          mandatory
    DESCRIPTION     
            "The name of this SS7 Node instance."
    ::= { sonusSs7NodeEntry 3 }

sonusSs7NodePointCode OBJECT-TYPE
    SYNTAX          PointCode
    ACCESS          read-write
    STATUS          mandatory
    DESCRIPTION     
            "The SS7 point code assigned to this SS7 Node entry."
    ::= { sonusSs7NodeEntry 4 }

sonusSs7NodeServices OBJECT-TYPE
    SYNTAX          INTEGER { isupOnly(1), tcapOnly(2), isupAndTcap(3), 
                        biccOnly(4) }
    ACCESS          read-write
    STATUS          mandatory
    DESCRIPTION     
            "The type of SS7 services (ISUP, TCAP, or both) supported by this SS7 Node entry. 
             As of GSX release 3.02.00, isupOnly is now the only vaild option for this entry."
    DEFVAL          { isupOnly }
    ::= { sonusSs7NodeEntry 5 }

sonusSs7NodeProtocol OBJECT-TYPE
    SYNTAX          INTEGER { ansi(1), itu(2), etsi(3), japan(4), bt7(5), 
                        china(6) }
    ACCESS          read-write
    STATUS          mandatory
    DESCRIPTION     
            "The SS7 protocol type supported by this SS7 Node entry."
    DEFVAL          { ansi }
    ::= { sonusSs7NodeEntry 6 }

sonusSs7NodeTcapSsn OBJECT-TYPE
    SYNTAX          INTEGER
    ACCESS          read-write
    STATUS          obsolete
    DESCRIPTION     
            "If Tcap is supported by this SS7 Node, specifies the Sub System Number for
             this node entry.
             This object is obsoleted as of GSX release 3.02.00."
    DEFVAL          { 0 }
    ::= { sonusSs7NodeEntry 7 }

sonusSs7NodeIsupStatus OBJECT-TYPE
    SYNTAX          INTEGER { offline(1), active(2), initializing(3), 
                        failed(4), disabled(5), congested(6) }
    ACCESS          read-only
    STATUS          deprecated
    DESCRIPTION     
            "This status value has been replaced by sonusSs7NodeStatIsup"
    ::= { sonusSs7NodeEntry 8 }

sonusSs7NodeTcapStatus OBJECT-TYPE
    SYNTAX          INTEGER { offline(1), active(2), initializing(3), 
                        failed(4), disabled(5), congested(6) }
    ACCESS          read-only
    STATUS          obsolete
    DESCRIPTION     
            "Specifies the operating status of the TCAP service within this SS7 Node. 
             This object is obsoleted as of GSX release 3.02.00."
    DEFVAL          { offline }
    ::= { sonusSs7NodeEntry 9 }

sonusSs7NodeMtpStatus OBJECT-TYPE
    SYNTAX          INTEGER { paused(1), resumed(2) }
    ACCESS          read-only
    STATUS          deprecated
    DESCRIPTION     
            "This status value has been replaced by sonusSs7NodeStatMtp"
    ::= { sonusSs7NodeEntry 10 }

sonusSs7NodeGatewayAssignment OBJECT-TYPE
    SYNTAX          DisplayString (SIZE(1..23))
    ACCESS          read-write
    STATUS          mandatory
    DESCRIPTION     
            "The name of the SS7 Gateway to which this SS7 Node is assigned."
    ::= { sonusSs7NodeEntry 11 }

sonusSs7NodeNativePointCode OBJECT-TYPE
    SYNTAX          INTEGER
    ACCESS          read-only
    STATUS          mandatory
    DESCRIPTION     
            "The native point code of the SS7 node. e.g. For ITU the 
             point code is in 3 bit 8 bit 3 bit format adding up to 14 bits whereas
             ANSI uses a 8bit 8bit 8bit format adding up to 24 bits."
    DEFVAL          { 0 }
    ::= { sonusSs7NodeEntry 12 }

sonusSs7NodeMode OBJECT-TYPE
    SYNTAX          INTEGER { inService(1), outOfService(2) }
    ACCESS          read-write
    STATUS          mandatory
    DESCRIPTION     
            "Specifies the service mode for this SS7 Node."
    DEFVAL          { outOfService }
    ::= { sonusSs7NodeEntry 13 }

sonusSs7NodeConnCntrl OBJECT-TYPE
    SYNTAX          INTEGER { always(1), asNeeded(2) }
    ACCESS          read-write
    STATUS          mandatory
    DESCRIPTION     
            "Specifies when the Node will establish an ISUP connection with the SS7 Gateway. 
             This parameter is used to minimize unnecessary connections to the SS7 Gateway 
             for ISUP services, allowing the GSX to only establish the ISUP connections that 
             are required by ISUP circuits on a particular shelf. When set to always, 
             the ISUP service connection will be established when the node is enabled. When 
             set to asNeeded, the ISUP service connection will be established only if there 
             are ISUP circuits assigned to this node. This parameter only applies to ISUP 
             service registration."
    DEFVAL          { asNeeded }
    ::= { sonusSs7NodeEntry 14 }

sonusSs7NodeRowStatus OBJECT-TYPE
    SYNTAX          RowStatus
    ACCESS          read-write
    STATUS          mandatory
    DESCRIPTION     
            ""
    ::= { sonusSs7NodeEntry 15 }

sonusSs7NodeStdPointCode OBJECT-TYPE
    SYNTAX          SonusPointCode
    ACCESS          read-write
    STATUS          mandatory
    DESCRIPTION     
            "Octet string of the point code. This gives the actual representation
             the user entered."
    ::= { sonusSs7NodeEntry 16 }

sonusSs7NodePointCodeSize OBJECT-TYPE
    SYNTAX          INTEGER (1..32)
    ACCESS          read-write
    STATUS          mandatory
    DESCRIPTION     
            "Indicates the total number of bits in the point code."
    DEFVAL          { 24 }
    ::= { sonusSs7NodeEntry 17 }

sonusSs7NodePointCodeFormatType OBJECT-TYPE
    SYNTAX          SonusPointCodeFormat
    ACCESS          read-write
    STATUS          mandatory
    DESCRIPTION     
            "The Point Code format type being defined."
    ::= { sonusSs7NodeEntry 18 }

sonusSs7NodeServerProtocol OBJECT-TYPE
    SYNTAX          INTEGER { dgmsProp(1), dgmsRaw(2), tekTali(3), 
                        dgmsSuperRaw(4), m3ua(5), local(6), 
                        dgmsSuperRawM3ua(7) }
    ACCESS          read-write
    STATUS          mandatory
    DESCRIPTION     
            "The interface used between the SS7 gateway and the SS7 client
             on the GSX9000.  When local(6) is selected, the system is 
             directly connected to the SS7 network without via any SGX."
    DEFVAL          { dgmsSuperRaw }
    ::= { sonusSs7NodeEntry 19 }

sonusSs7NodeHandShakeInterval OBJECT-TYPE
    SYNTAX          INTEGER (1..255)
    ACCESS          read-write
    STATUS          mandatory
    DESCRIPTION     
            "HandShake interval between the client and the server in seconds."
    ::= { sonusSs7NodeEntry 20 }

sonusSs7NodeTimerT1 OBJECT-TYPE
    SYNTAX          INTEGER (2..180)
    ACCESS          read-write
    STATUS          mandatory
    DESCRIPTION     
            "The Timer T1 could be changed from its default using this entry in ISUP, or started when the
             Called Sub clears first in BT7. The valid ranges are 4 - 15 seconds for ANSI, 15 - 60 Seconds 
             for ITU, and 2 - 180 Seconds for BT7."
    DEFVAL          { 10 }
    ::= { sonusSs7NodeEntry 21 }

sonusSs7NodeTimerT2 OBJECT-TYPE
    SYNTAX          INTEGER (0..720)
    ACCESS          read-write
    STATUS          mandatory
    DESCRIPTION     
            "The Timer T2 could be changed from its default using this entry for ISUP, or waiting for receipt
             of Answer or Clear/Release in BT7. The valid value for ITU is 3 Minutes, and 60 - 720 Seconds for 
             BT7. This timer has no relevence in the ANSI network. "
    DEFVAL          { 180 }
    ::= { sonusSs7NodeEntry 22 }

sonusSs7NodeTimerT3 OBJECT-TYPE
    SYNTAX          INTEGER (1..300)
    ACCESS          read-write
    STATUS          mandatory
    DESCRIPTION     
            "The T3 timer is started on receipt of an Overload message in the ITU network, and to ensure 
             cleardown at the Terminating Node in the BT7 Network. . This has no relevence in the ANSI network. 
             The valid ITU recommended value is 120 Seconds, and 2 - 300 seconds for BT7 "
    DEFVAL          { 120 }
    ::= { sonusSs7NodeEntry 23 }

sonusSs7NodeTimerT4 OBJECT-TYPE
    SYNTAX          INTEGER (120..900)
    ACCESS          read-write
    STATUS          mandatory
    DESCRIPTION     
            "The Timer T4 could be changed from its default using this entry in ISUP, and to delay release
             for 120 seconds during Overload in BT7."
    DEFVAL          { 600 }
    ::= { sonusSs7NodeEntry 24 }

sonusSs7NodeTimerT5 OBJECT-TYPE
    SYNTAX          INTEGER (60..900)
    ACCESS          read-write
    STATUS          mandatory
    DESCRIPTION     
            "The T5 Timer is started when the release message is sent, and awaiting Answer for BT7. The valid values
             as per the specifications are 60 seconds for the ANSI, 300 to 900 seconds for ITU, 60 - 840 seconds for BT7."
    DEFVAL          { 60 }
    ::= { sonusSs7NodeEntry 25 }

sonusSs7NodeTimerT6 OBJECT-TYPE
    SYNTAX          INTEGER (1..120)
    ACCESS          read-write
    STATUS          mandatory
    DESCRIPTION     
            "The timer T6 is started when the suspend message is received at the originating
             exchange, and to determine end of dialing for BT7. 
             The valid range for this timer is 1 to 120 seconds for ISUP, and 1 - 6 seconds for BT7."
    DEFVAL          { 22 }
    ::= { sonusSs7NodeEntry 26 }

sonusSs7NodeTimerT7 OBJECT-TYPE
    SYNTAX          INTEGER (2..50)
    ACCESS          read-write
    STATUS          mandatory
    DESCRIPTION     
            "The Timer T7 could be changed from its default using this entry. Currently not used for BT7"
    DEFVAL          { 25 }
    ::= { sonusSs7NodeEntry 27 }

sonusSs7NodeTimerT8 OBJECT-TYPE
    SYNTAX          INTEGER (1..40)
    ACCESS          read-write
    STATUS          mandatory
    DESCRIPTION     
            "The T8 timer is timer to be started with continuity check has been indicated in the IAM for ISUP, and awaiting
             receipt of Blocking/UnBlocking in BT7. The valid range for ISUP is 10 to 15 seconds, and 1 - 40 seconds for BT7."
    DEFVAL          { 13 }
    ::= { sonusSs7NodeEntry 28 }

sonusSs7NodeTimerT9 OBJECT-TYPE
    SYNTAX          INTEGER (5..255)
    ACCESS          read-write
    STATUS          mandatory
    DESCRIPTION     
            "The Timer T9 started at the terminating exchange when after an ACM is returned to 
             the originating exchange, or awaiting backwards message in BT7. The valid range is
             120 to 255 seconds for ISUP, 5 to 30 for BT7."
    DEFVAL          { 220 }
    ::= { sonusSs7NodeEntry 29 }

sonusSs7NodeTimerT10 OBJECT-TYPE
    SYNTAX          INTEGER (1..360)
    ACCESS          read-write
    STATUS          mandatory
    DESCRIPTION     
            "The Timer T10 is started when the last digit is recived in interworking situations, and waiting for 
             forwards release in BT7. This timer has no relevence to ANSI. The valid range for ISUP is 4 -6 seconds, and
             1 - 40 seconds for BT7."
    ::= { sonusSs7NodeEntry 30 }

sonusSs7NodeTimerT11 OBJECT-TYPE
    SYNTAX          INTEGER (5..20)
    ACCESS          read-write
    STATUS          mandatory
    DESCRIPTION     
            "The Timer T11 is started when the latest address message is received in interworking 
             situations. Currently not used by BT7. The valid range is 5 to 20 seconds."
    DEFVAL          { 17 }
    ::= { sonusSs7NodeEntry 31 }

sonusSs7NodeTimerT12 OBJECT-TYPE
    SYNTAX          INTEGER (1..60)
    ACCESS          read-write
    STATUS          mandatory
    DESCRIPTION     
            "The Timer T12 is started when a blocking message is sent in ISUP, and awaiting Circuit free or Blocking
             messages in BT7.  The valid ranges are 4 to 15 seconds for ANSI, 15 to 60 seconds for ITU, and 1 - 60
             seconds for BT7."
    DEFVAL          { 10 }
    ::= { sonusSs7NodeEntry 32 }

sonusSs7NodeTimerT13 OBJECT-TYPE
    SYNTAX          INTEGER (60..900)
    ACCESS          read-write
    STATUS          mandatory
    DESCRIPTION     
            "The Timer T13 is started when the initial blocking messge is sent. The valid
             value for ANSI is 60 seconds and for ITU is between 300 and 900 seconds."
    DEFVAL          { 60 }
    ::= { sonusSs7NodeEntry 33 }

sonusSs7NodeTimerT14 OBJECT-TYPE
    SYNTAX          INTEGER (1..60)
    ACCESS          read-write
    STATUS          mandatory
    DESCRIPTION     
            "The Timer T14 is started when an unblocking message is sent in ISUP, and awaiting addition
             information in BT7. The valid values are 4 to 15 seconds for ANSI, 15 to 60 seconds for ITU, and
             1 - 40 seconds for BT7"
    DEFVAL          { 10 }
    ::= { sonusSs7NodeEntry 34 }

sonusSs7NodeTimerT15 OBJECT-TYPE
    SYNTAX          INTEGER (60..900)
    ACCESS          read-write
    STATUS          mandatory
    DESCRIPTION     
            "The Timer T15 is started when the initial unblocking message is sent, currently not used by
             BT7. The valid values are 60 seconds for ANSI and 300 to 900 seconds for ITU."
    DEFVAL          { 60 }
    ::= { sonusSs7NodeEntry 35 }

sonusSs7NodeTimerT16 OBJECT-TYPE
    SYNTAX          INTEGER (4..180)
    ACCESS          read-write
    STATUS          mandatory
    DESCRIPTION     
            "The Timer T16 is started when the reset circuit is started which was not due to expiry of
             T5 in ISUP, and prolonged call setup in BT7. The valid ranges are 4 to 15 seconds for ANSI, 
             		 15 to 60 seconds for ITU and 60 - 180 seconds for BT7."
    DEFVAL          { 10 }
    ::= { sonusSs7NodeEntry 36 }

sonusSs7NodeTimerT17 OBJECT-TYPE
    SYNTAX          INTEGER (5..900)
    ACCESS          read-write
    STATUS          mandatory
    DESCRIPTION     
            "The Timer T17 is started when initial reset message is sent in ISUP, and awaiting receipt of FAM/SAM 
             after sending a SAD in BT7. The valid values are 60 seconds for ANSI, 300 to 900 for ITU and 5 - 20 
             seconds for BT7."
    DEFVAL          { 60 }
    ::= { sonusSs7NodeEntry 37 }

sonusSs7NodeTimerT18 OBJECT-TYPE
    SYNTAX          INTEGER (4..180)
    ACCESS          read-write
    STATUS          mandatory
    DESCRIPTION     
            "The Timer T18 is started when circuit group blocking message is sent in ISUP, and waiting receipt of 
             FAM/SAM after sending SND for BT7. The valid values are 4 to 15 seconds for ANSI and 15 to 60 seconds 
             for ITU, and 5 - 180 seconds in BT7."
    DEFVAL          { 10 }
    ::= { sonusSs7NodeEntry 38 }

sonusSs7NodeTimerT19 OBJECT-TYPE
    SYNTAX          INTEGER (60..900)
    ACCESS          read-write
    STATUS          mandatory
    DESCRIPTION     
            "The Timer T19 is started when initial group blocking message is sent, currently not used by BT7. The 
             valid values are 60 seconds for ANSI and 300 to 900 seconds for ITU."
    DEFVAL          { 60 }
    ::= { sonusSs7NodeEntry 39 }

sonusSs7NodeTimerT20 OBJECT-TYPE
    SYNTAX          INTEGER (4..60)
    ACCESS          read-write
    STATUS          mandatory
    DESCRIPTION     
            "The Timer T20 is started when group unblocking message is sent. The valid ranges are
             4 to 15 seconds for ANSI and 15 to 60 seconds for ITU."
    DEFVAL          { 10 }
    ::= { sonusSs7NodeEntry 40 }

sonusSs7NodeTimerT21 OBJECT-TYPE
    SYNTAX          INTEGER (60..900)
    ACCESS          read-write
    STATUS          mandatory
    DESCRIPTION     
            "The Timer T21 is started when initial group blocking message is sent in ISUP, and to enable call 
             clear while waiting for Resume message in BT7. The valid values are 60 seconds for ANSI, 300 to 900 
             seconds for ITU, and 180 seconds for BT7."
    DEFVAL          { 60 }
    ::= { sonusSs7NodeEntry 41 }

sonusSs7NodeTimerT22 OBJECT-TYPE
    SYNTAX          INTEGER (4..60)
    ACCESS          read-write
    STATUS          mandatory
    DESCRIPTION     
            "The Timer T22 is started when circuit group reset message is sent. The valid values are
             4 to 15 seconds for ANSI and 15 to 60 seconds for ITU."
    DEFVAL          { 10 }
    ::= { sonusSs7NodeEntry 42 }

sonusSs7NodeTimerT23 OBJECT-TYPE
    SYNTAX          INTEGER (60..900)
    ACCESS          read-write
    STATUS          mandatory
    DESCRIPTION     
            "The Timer T23 is started when initial group reset message is sent. The valid values
             are 60 seconds for the ANSI and 300 to 900 seconds for the ITU."
    DEFVAL          { 60 }
    ::= { sonusSs7NodeEntry 43 }

sonusSs7NodeTimerT24 OBJECT-TYPE
    SYNTAX          INTEGER (1..2)
    ACCESS          read-write
    STATUS          mandatory
    DESCRIPTION     
            "The Timer T24 is started when check tone is sent. The value is less
             than 2 seconds."
    DEFVAL          { 1 }
    ::= { sonusSs7NodeEntry 44 }

sonusSs7NodeTimerT25 OBJECT-TYPE
    SYNTAX          INTEGER (1..20)
    ACCESS          read-write
    STATUS          mandatory
    DESCRIPTION     
            "The Timer T25 is started when initial continuity check failure is 
             detected. 
             		 For ANSI the valid range is 1 to 10 seconds - GR317 requires a range of 16 to 20 seconds."
    DEFVAL          { 5 }
    ::= { sonusSs7NodeEntry 45 }

sonusSs7NodeTimerT26 OBJECT-TYPE
    SYNTAX          INTEGER (60..180)
    ACCESS          read-write
    STATUS          mandatory
    DESCRIPTION     
            "The Timer T26 is started when a second or subsequent continuity failure is detected.
             The valid value are 60 to 180 seconds."
    DEFVAL          { 120 }
    ::= { sonusSs7NodeEntry 46 }

sonusSs7NodeTimerT27 OBJECT-TYPE
    SYNTAX          INTEGER (10..36000)
    ACCESS          read-write
    STATUS          mandatory
    DESCRIPTION     
            "The Timer T27 is started when a continuity fail message is recieved. The valid values are
             more than 180 seconds for ANSI and 240 seconds for ITU. "
    DEFVAL          { 240 }
    ::= { sonusSs7NodeEntry 47 }

sonusSs7NodeTimerT28 OBJECT-TYPE
    SYNTAX          INTEGER (5..12)
    ACCESS          read-write
    STATUS          mandatory
    DESCRIPTION     
            "The Timer T28 is started when Circuit Query Message is sent. The valid value is 10 seconds."
    DEFVAL          { 10 }
    ::= { sonusSs7NodeEntry 48 }

sonusSs7NodeTimerT29 OBJECT-TYPE
    SYNTAX          INTEGER (300..600)
    ACCESS          read-write
    STATUS          mandatory
    DESCRIPTION     
            "The Timer T29 is started when Congestion indication is received when T29
             is not running. The valid range is 300 to 600 milli second. This timer has
             no relevence for ANSI."
    ::= { sonusSs7NodeEntry 49 }

sonusSs7NodeTimerT30 OBJECT-TYPE
    SYNTAX          INTEGER (5..10)
    ACCESS          read-write
    STATUS          mandatory
    DESCRIPTION     
            "The Timer T30 is stared when congestion indication is recieved when T29 is not running. The valid 
             range is 5 to 10 seconds for the ITU. This timer has no relevence under ANSI."
    ::= { sonusSs7NodeEntry 50 }

sonusSs7NodeTimerT31 OBJECT-TYPE
    SYNTAX          INTEGER (360..65520)
    ACCESS          read-write
    STATUS          mandatory
    DESCRIPTION     
            "The Timer T31 is started on release of ISUP signalling connection based on
             CO SCCP. The value should be set to greater than 360 seconds"
    DEFVAL          { 420 }
    ::= { sonusSs7NodeEntry 51 }

sonusSs7NodeTimerT32 OBJECT-TYPE
    SYNTAX          INTEGER (3..5)
    ACCESS          read-write
    STATUS          mandatory
    DESCRIPTION     
            "The Timer T32 is started when the first end-to-end message is recived. Under ANSI this
             timer is started after the response to such a message is sent. The valid values are 3 
             to 5 seconds. "
    DEFVAL          { 4 }
    ::= { sonusSs7NodeEntry 52 }

sonusSs7NodeTimerT33 OBJECT-TYPE
    SYNTAX          INTEGER (5..15)
    ACCESS          read-write
    STATUS          mandatory
    DESCRIPTION     
            "The Timer T33 is started when Information Request Message is sent. The 
             valid range is 5 to 15 seconds."
    DEFVAL          { 14 }
    ::= { sonusSs7NodeEntry 53 }

sonusSs7NodeTimerT34 OBJECT-TYPE
    SYNTAX          INTEGER (2..15)
    ACCESS          read-write
    STATUS          mandatory
    DESCRIPTION     
            "The Timer T34 is started when Loop Back Acknowledgement is sent under ANSI.
             The Timer T34 is started when segmentation is received for IAM, ACM, CPG,
             ANM or CON under ITU. The valid range for ANSI is 10 to 15 seconds. The valid
             range for ITU is 2 to 4 seconds."
    ::= { sonusSs7NodeEntry 54 }

sonusSs7NodeTimerT35 OBJECT-TYPE
    SYNTAX          INTEGER (4..20)
    ACCESS          read-write
    STATUS          mandatory
    DESCRIPTION     
            "The Timer T35 is started when the last digit recieved is not an ST digit or
             the fixed number of digits have been recieved. This procedure is only valid
             for overlap hence ITU. This timer has no relevence in ANSI."
    DEFVAL          { 18 }
    ::= { sonusSs7NodeEntry 55 }

sonusSs7NodeTimerT36 OBJECT-TYPE
    SYNTAX          INTEGER (2..15)
    ACCESS          read-write
    STATUS          mandatory
    DESCRIPTION     
            "The Timer T36 is started when IAM is recived with a segmentation indication for ANSI.
             This timer is started when transit or incoming international exchange recieves Continuity check
             request message. The valid range for ANSI is 2 to 4 seconds and 10 to 15 
             seconds for ITU. "
    ::= { sonusSs7NodeEntry 56 }

sonusSs7NodeTimerT37 OBJECT-TYPE
    SYNTAX          INTEGER (2..30)
    ACCESS          read-write
    STATUS          mandatory
    DESCRIPTION     
            "The Timer T37 is started when User Part Availability test is started under ANSI. This
             timer is started when a request for and Echo control device is sent to another exchange
             under ITU. The valid value for ANSI is 30 seconds and for ITU is 2 to 4 seconds."
    ::= { sonusSs7NodeEntry 57 }

sonusSs7NodeTimerT38 OBJECT-TYPE
    SYNTAX          INTEGER (2..1800)
    ACCESS          read-write
    STATUS          mandatory
    DESCRIPTION     
            "The Timer T38 is started when a suspend message is sent to the preceding switch. This timer
             is only relevent under ITU."
    DEFVAL          { 30 }
    ::= { sonusSs7NodeEntry 58 }

sonusSs7NodeTimerT39 OBJECT-TYPE
    SYNTAX          INTEGER (1..65535)
    ACCESS          read-write
    STATUS          mandatory
    DESCRIPTION     
            "The Timer T39 is started when MCID request is sent. It is only relevent in the ITU."
    DEFVAL          { 9 }
    ::= { sonusSs7NodeEntry 59 }

sonusSs7NodeTimerT40 OBJECT-TYPE
    SYNTAX          INTEGER (1..65535)
    ACCESS          read-write
    STATUS          mandatory
    DESCRIPTION     
            "The Timer T40 could be changed from its default using this entry."
    ::= { sonusSs7NodeEntry 60 }

sonusSs7NodeTimerTAcc OBJECT-TYPE
    SYNTAX          INTEGER (3..8)
    ACCESS          read-write
    STATUS          mandatory
    DESCRIPTION     
            "Automatic Congestion Control Timer as per ANSI T1.113.4 - 1995. The value
             of the timer is 5 Seconds."
    DEFVAL          { 5 }
    ::= { sonusSs7NodeEntry 61 }

sonusSs7NodeTimerTCcr OBJECT-TYPE
    SYNTAX          INTEGER (1..3)
    ACCESS          read-write
    STATUS          mandatory
    DESCRIPTION     
            "Continuity Check Request Timer. The value As per ANSI T1.113.4 - 1995 is 2 Seconds."
    DEFVAL          { 2 }
    ::= { sonusSs7NodeEntry 62 }

sonusSs7NodeTimerTCcrr OBJECT-TYPE
    SYNTAX          INTEGER (10..31)
    ACCESS          read-write
    STATUS          mandatory
    DESCRIPTION     
            "Continuity Check Failed Recived. The value as per ANSI T1.113.4 - 1995 is 20 Seconds."
    DEFVAL          { 20 }
    ::= { sonusSs7NodeEntry 63 }

sonusSs7NodeTimerTCgb OBJECT-TYPE
    SYNTAX          INTEGER (3..8)
    ACCESS          read-write
    STATUS          mandatory
    DESCRIPTION     
            "Timer started on recipt of a Circuit Group Block Message. The value as per
             ANSI T1.113.4 - 1995 is 5 Seconds."
    DEFVAL          { 5 }
    ::= { sonusSs7NodeEntry 64 }

sonusSs7NodeTimerTCra OBJECT-TYPE
    SYNTAX          INTEGER (10..31)
    ACCESS          read-write
    STATUS          mandatory
    DESCRIPTION     
            "Timer started when Circuit Reservation Acknowledgment is sent. The time value
             as per ANSI T1.113.4 - 1995 is 20 seconds."
    DEFVAL          { 20 }
    ::= { sonusSs7NodeEntry 65 }

sonusSs7NodeTimerTCrm OBJECT-TYPE
    SYNTAX          INTEGER (3..4)
    ACCESS          read-write
    STATUS          mandatory
    DESCRIPTION     
            "This timer is started when the circuit reservation message is sent. The value 
             as per ANSI T1.113.4 - 1995 is 3 - 4 Seconds. The default is set to 4 seconds."
    DEFVAL          { 4 }
    ::= { sonusSs7NodeEntry 66 }

sonusSs7NodeTimerTCvt OBJECT-TYPE
    SYNTAX          INTEGER (5..12)
    ACCESS          read-write
    STATUS          mandatory
    DESCRIPTION     
            "The Timer T CVT is started when the Circuit Validation Test message
             is sent. This message is only valid for ANSI."
    DEFVAL          { 10 }
    ::= { sonusSs7NodeEntry 67 }

sonusSs7NodeTimerTExm OBJECT-TYPE
    SYNTAX          INTEGER (1..65535)
    ACCESS          read-write
    STATUS          mandatory
    DESCRIPTION     
            "The Timer Exm,d is started when IAM is sent to the succeeding network. This
             timer has no relevence in the ITU. This timer is in milliseconds"
    DEFVAL          { 600 }
    ::= { sonusSs7NodeEntry 68 }

sonusSs7NodeTimerTGrs OBJECT-TYPE
    SYNTAX          INTEGER (3..8)
    ACCESS          read-write
    STATUS          mandatory
    DESCRIPTION     
            "This timer is started when a circuit group reset message is received. 
             This timer is only relevent in the ANSI network. "
    DEFVAL          { 5 }
    ::= { sonusSs7NodeEntry 69 }

sonusSs7NodeTimerTHga OBJECT-TYPE
    SYNTAX          INTEGER (0..300)
    ACCESS          read-write
    STATUS          mandatory
    DESCRIPTION     
            "This timer is started on recognition of carrier loss. It is only relevent in ANSI
             network. The valid range is 0 to 300 seconds."
    DEFVAL          { 150 }
    ::= { sonusSs7NodeEntry 70 }

sonusSs7NodeTimerTScga OBJECT-TYPE
    SYNTAX          INTEGER (0..120)
    ACCESS          read-write
    STATUS          mandatory
    DESCRIPTION     
            "This timer is started when initial demand continuity check fails in the
             SCGA group. The valid range for this timer is 0 to 120 seconds."
    DEFVAL          { 60 }
    ::= { sonusSs7NodeEntry 71 }

sonusSs7NodeTimerTScgad OBJECT-TYPE
    SYNTAX          INTEGER (5..120)
    ACCESS          read-write
    STATUS          mandatory
    DESCRIPTION     
            "This timer is started failure of demand continuity check in the SCGA group."
    DEFVAL          { 65 }
    ::= { sonusSs7NodeEntry 72 }

sonusSs7NodeApplProfileName OBJECT-TYPE
    SYNTAX          DisplayString (SIZE(0..23))
    ACCESS          read-write
    STATUS          obsolete
    DESCRIPTION     
            "The SS7 Node Profile to be applied to the node. The values here are
             a snap shot only and might have changed since they were set. This 
             		 object is obsoleted as of GSX release 5.1"
    ::= { sonusSs7NodeEntry 73 }

sonusSs7NodeNetworkInd OBJECT-TYPE
    SYNTAX          INTEGER { intl0(1), intl1(2), natl0(3), natl1(4) }
    ACCESS          read-write
    STATUS          mandatory
    DESCRIPTION     
            "The setting of the Network Indicator used for this SS7 Node entry."
    DEFVAL          { natl0 }
    ::= { sonusSs7NodeEntry 74 }

sonusSs7NodeSlsBits OBJECT-TYPE
    SYNTAX          INTEGER (4..8)
    ACCESS          read-write
    STATUS          mandatory
    DESCRIPTION     
            "The number of SLS bits to use"
    DEFVAL          { 5 }
    ::= { sonusSs7NodeEntry 75 }

sonusSs7NodeTimerTA OBJECT-TYPE
    SYNTAX          INTEGER (0..1000)
    ACCESS          read-write
    STATUS          mandatory
    DESCRIPTION     
            "The Bellcore specific timer TA is the guard timer on outgoing SS7 circuit before
             idling. The value of this timer is 0 to 1000 milliseconds."
    DEFVAL          { 0 }
    ::= { sonusSs7NodeEntry 76 }

sonusSs7NodeTimerTBlom OBJECT-TYPE
    SYNTAX          INTEGER (240..360)
    ACCESS          read-write
    STATUS          mandatory
    DESCRIPTION     
            "The Bellcore specific timer TBlom is started when blocking a circuit due to a
             BLO, and after any call is released; used to notify maintenance."
    DEFVAL          { 300 }
    ::= { sonusSs7NodeEntry 77 }

sonusSs7NodeTimerTCotd OBJECT-TYPE
    SYNTAX          INTEGER (0..500)
    ACCESS          read-write
    STATUS          mandatory
    DESCRIPTION     
            "The Bellcore specific timer TCOTd is started when sending IAM requesting
             continuity check. The value of this timer is in milliseconds. It is given
             a default even though it does not exist in the ANSI T1 standards as experience
             shows it to improve system performance."
    DEFVAL          { 250 }
    ::= { sonusSs7NodeEntry 78 }

sonusSs7NodeTimerTCotl OBJECT-TYPE
    SYNTAX          INTEGER (240..300)
    ACCESS          read-write
    STATUS          mandatory
    DESCRIPTION     
            "The Bellcore specific timer TCOTl is started when receiving second COT coded
             failed, awaiting receipt of CCR."
    DEFVAL          { 250 }
    ::= { sonusSs7NodeEntry 79 }

sonusSs7NodeTimerTSus OBJECT-TYPE
    SYNTAX          INTEGER (0..16)
    ACCESS          read-write
    STATUS          mandatory
    DESCRIPTION     
            "The Bellcore specific timer TSUS is started when a SUS message is sent by the
             terminating switch, awaiting called party off-hook or REL."
    DEFVAL          { 15 }
    ::= { sonusSs7NodeEntry 80 }

sonusSs7NodeTimerT6Trans OBJECT-TYPE
    SYNTAX          INTEGER (0..1800)
    ACCESS          read-write
    STATUS          mandatory
    DESCRIPTION     
            "The T6Trans timer is started after a network initiated SUS is received at a
             transit exchange for ITU. The valid range is 2 to 1800."
    DEFVAL          { 1200 }
    ::= { sonusSs7NodeEntry 81 }

sonusSs7NodeTimerT6Term OBJECT-TYPE
    SYNTAX          INTEGER (2..180)
    ACCESS          read-write
    STATUS          mandatory
    DESCRIPTION     
            "The T6Term timer is started after a network initiated SUS is recevied at a
             terminating exchange for ITU. The valid range is 2 to 180."
    DEFVAL          { 140 }
    ::= { sonusSs7NodeEntry 82 }

sonusSs7NodeTimerT9Trans OBJECT-TYPE
    SYNTAX          INTEGER (90..900)
    ACCESS          read-write
    STATUS          mandatory
    DESCRIPTION     
            "The T9Trans timer is started after an ACM is received at a Transit exchange for ITU.
             The valid range 300 to 900."
    DEFVAL          { 600 }
    ::= { sonusSs7NodeEntry 83 }

sonusSs7NodeTimerT9Int OBJECT-TYPE
    SYNTAX          INTEGER (0..900)
    ACCESS          read-write
    STATUS          mandatory
    DESCRIPTION     
            "The T9Int timer is started after an ACM is received at an interworking or at an
             international exchange for ANSI, ITU or China. The valid ranges are:
             90 to 900 for ITU, China.
             0 (off), 120 to 240 for ANSI."
    DEFVAL          { 200 }
    ::= { sonusSs7NodeEntry 84 }

sonusSs7NodeTimerT9Orig OBJECT-TYPE
    SYNTAX          INTEGER (90..900)
    ACCESS          read-write
    STATUS          mandatory
    DESCRIPTION     
            "The T9Orig timer is started at the originating exchange after an ACM is received for ITU.
             The valid range is 90 to 900."
    DEFVAL          { 600 }
    ::= { sonusSs7NodeEntry 85 }

sonusSs7NodeTimerT8a OBJECT-TYPE
    SYNTAX          INTEGER (300..900)
    ACCESS          read-write
    STATUS          mandatory
    DESCRIPTION     
            "The BT7 specific timer T8a is started on non-receipt of Unblocking Acknowledgement, awaiting receipt of UBA."
    DEFVAL          { 360 }
    ::= { sonusSs7NodeEntry 86 }

sonusSs7NodeTimerT12a OBJECT-TYPE
    SYNTAX          INTEGER (300..900)
    ACCESS          read-write
    STATUS          mandatory
    DESCRIPTION     
            "The BT7 specific timer T12a is started when awaiting Circuit Free or Blocking Message. "
    DEFVAL          { 360 }
    ::= { sonusSs7NodeEntry 87 }

sonusSs7NodeTimerT1a OBJECT-TYPE
    SYNTAX          INTEGER (0..180)
    ACCESS          read-write
    STATUS          mandatory
    DESCRIPTION     
            "The Timer T1a could be changed from its default using this entry. The valid ranges are
             0 - 180 seconds for BT IUP."
    DEFVAL          { 0 }
    ::= { sonusSs7NodeEntry 88 }

sonusSs7NodeTimerT1b OBJECT-TYPE
    SYNTAX          INTEGER (0..120)
    ACCESS          read-write
    STATUS          mandatory
    DESCRIPTION     
            "The Timer T1b could be changed from its default using this entry. The valid ranges are
             0 - 120 seconds for BT IUP."
    DEFVAL          { 0 }
    ::= { sonusSs7NodeEntry 89 }

sonusSs7NodeTimerT1c OBJECT-TYPE
    SYNTAX          INTEGER (2..180)
    ACCESS          read-write
    STATUS          mandatory
    DESCRIPTION     
            "The Timer T1c could be changed from its default using this entry. The valid ranges are
             2 - 180 seconds for BT IUP."
    DEFVAL          { 180 }
    ::= { sonusSs7NodeEntry 90 }

sonusSs7NodeTimerT1d OBJECT-TYPE
    SYNTAX          INTEGER (5..86400)
    ACCESS          read-write
    STATUS          mandatory
    DESCRIPTION     
            "The Timer T1d could be changed from its default using this entry. The valid ranges are
             5 - 86400 seconds (24hrs) for BT IUP."
    DEFVAL          { 86400 }
    ::= { sonusSs7NodeEntry 91 }

sonusSs7NodeIsupVariant OBJECT-TYPE
    SYNTAX          INTEGER { standard(1), j7ttc(10) }
    ACCESS          read-write
    STATUS          obsolete
    DESCRIPTION     
            "The SS7 ISUP variant set during Client Initialisation. This object is obsoleted as of
             release GSX 7.1 "
    DEFVAL          { standard }
    ::= { sonusSs7NodeEntry 92 }

sonusSs7NodeTeardownCalls OBJECT-TYPE
    SYNTAX          INTEGER { disabled(1), enabled(2) }
    ACCESS          read-write
    STATUS          mandatory
    DESCRIPTION     
            "The Teardowncalls if enabled will tear down all
             activ calls when node becomes out of serivce. "
    DEFVAL          { disabled }
    ::= { sonusSs7NodeEntry 93 }

sonusSs7NodeNetAppearance OBJECT-TYPE
    SYNTAX          Gauge (0..4294967295)
    ACCESS          read-write
    STATUS          mandatory
    DESCRIPTION     
            "The Network Appearance is a M3UA local 
             reference shared by SG and AS (typically an 
             integer) that together with an Signaling Point 
             Code uniquely identifies an SS7 node by 
             indicating the specific SS7 network it belongs 
             to."
    DEFVAL          { 0 }
    ::= { sonusSs7NodeEntry 94 }

sonusSs7NodeTimerTECSR OBJECT-TYPE
    SYNTAX          INTEGER (0..60)
    ACCESS          read-write
    STATUS          mandatory
    DESCRIPTION     
            "The Timer ECSR (in seconds) is started for
             emergency calls when the ACM message is received,
             if an ANM message is not received before the timer 
             expires then a trap will fire."
    DEFVAL          { 30 }
    ::= { sonusSs7NodeEntry 95 }

sonusSs7NodeMtp3MgmtName OBJECT-TYPE
    SYNTAX          DisplayString (SIZE(0..23))
    ACCESS          read-write
    STATUS          mandatory
    DESCRIPTION     
            "The name of MTP3 MGMT that is used."
    ::= { sonusSs7NodeEntry 96 }

sonusSs7NodeAltGateway OBJECT-TYPE
    SYNTAX          DisplayString (SIZE(0..23))
    ACCESS          read-write
    STATUS          mandatory
    DESCRIPTION     
            "The name of the alternate SS7 gateway which forms a 
             geographic redundancy pair with sonusSs7NodeGatewayAssignment
             for this node."
    DEFVAL          { "" }
    ::= { sonusSs7NodeEntry 97 }

sonusSs7NodeTimerTSusImmediateRel OBJECT-TYPE
    SYNTAX          INTEGER (0..300)
    ACCESS          read-write
    STATUS          mandatory
    DESCRIPTION     
            "This timer (in seconds) is used to immediately
             release a call if B Party hang up first. The timer
             will determine how long the call will remain in
             speech before the call is released."
    DEFVAL          { 0 }
    ::= { sonusSs7NodeEntry 98 }

sonusSs7NodeIsupUcic OBJECT-TYPE
    SYNTAX          INTEGER { unsupported(1), supported(2) }
    ACCESS          read-write
    STATUS          mandatory
    DESCRIPTION     
            "UCIC if enabled will send a ISUP UCIC message
             on reception of an IAM, Circuit check request,
             Circuit supervision or Circuit group supervision message
             to an unequipped CIC. "
    DEFVAL          { unsupported }
    ::= { sonusSs7NodeEntry 100 }

sonusSs7NodeTimerSuppressCircuitTraps OBJECT-TYPE
    SYNTAX          INTEGER (0..600)
    ACCESS          read-write
    STATUS          mandatory
    DESCRIPTION     
            "This Timer is the time in seconds over which certain circuit related events
             and associated data will be counted. If any event data has been counted by 
             				 the end of the consolidation period then consolidation events will be raised
             				 causing SNMP traps to be generated containing the consolidated data. 
             				 The valid range is 0 to 600 seconds."
    DEFVAL          { 300 }
    ::= { sonusSs7NodeEntry 101 }

sonusSs7NodeGenerateNCR OBJECT-TYPE
    SYNTAX          INTEGER { disabled(1), enabled(2) }
    ACCESS          read-write
    STATUS          mandatory
    DESCRIPTION     
            "The Generate NCR if enabled will Generate the
             NCR parameter at the GSX."
    DEFVAL          { disabled }
    ::= { sonusSs7NodeEntry 102 }

sonusSs7NodeGeoRedundancy OBJECT-TYPE
    SYNTAX          INTEGER { disabled(1), enabled(2) }
    ACCESS          read-write
    STATUS          mandatory
    DESCRIPTION     
            "The Geographic Redundancy State of SS7 Node"
    DEFVAL          { disabled }
    ::= { sonusSs7NodeEntry 103 }

sonusSs7NodeTimerT42 OBJECT-TYPE
    SYNTAX          INTEGER (5..30)
    ACCESS          read-write
    STATUS          mandatory
    DESCRIPTION     
            "This timer is started when a modification is initiated during codec modification or mid-call
             codec negotiation procedures"
    DEFVAL          { 5 }
    ::= { sonusSs7NodeEntry 108 }

sonusSs7NodeTimerT43 OBJECT-TYPE
    SYNTAX          INTEGER (5..30)
    ACCESS          read-write
    STATUS          mandatory
    DESCRIPTION     
            "This timer is started when a mid-call codec negotiation is initiated"
    DEFVAL          { 5 }
    ::= { sonusSs7NodeEntry 109 }

sonusSs7NodeTimerTreass OBJECT-TYPE
    SYNTAX          INTEGER (10..18)
    ACCESS          read-write
    STATUS          mandatory
    DESCRIPTION     
            "This timer is started on receipt of APP indicating new sequence for reassembly"
    DEFVAL          { 15 }
    ::= { sonusSs7NodeEntry 110 }

sonusSs7NodeTimerTCRGA OBJECT-TYPE
    SYNTAX          INTEGER (6..15)
    ACCESS          read-write
    STATUS          mandatory
    DESCRIPTION     
            "The Timer TCRGA (in seconds) is started when sending
             CRGT. If a CRGA is not received before timer expires,
             an EventNotify will be displayed in the SYS logs."
    DEFVAL          { 10 }
    ::= { sonusSs7NodeEntry 111 }

sonusSs7NodeNifGroupName OBJECT-TYPE
    SYNTAX          SonusNameReference
    ACCESS          read-write
    STATUS          mandatory
    DESCRIPTION     
            "The NIF Group which this SS7 Node application port belongs to."
    ::= { sonusSs7NodeEntry 112 }

sonusSs7NodeNetworkAccess OBJECT-TYPE
    SYNTAX          INTEGER { none(1), nifgroup(2), anynif(3) }
    ACCESS          read-write
    STATUS          mandatory
    DESCRIPTION     
            "The Network access type of SS7 Node application. Option NONE is basically as good as disabled; NIFGROUP uses only the interfaces in the NIF group; ANYNIF would use any of the interfaces"
    DEFVAL          { nifgroup }
    ::= { sonusSs7NodeEntry 113 }

sonusSs7NodeGatewayPriority OBJECT-TYPE
    SYNTAX          INTEGER (1..2)
    ACCESS          read-write
    STATUS          mandatory
    DESCRIPTION     
            "The priority of the Gateway for carrying the messages"
    DEFVAL          { 1 }
    ::= { sonusSs7NodeEntry 114 }

sonusSs7NodeGateway1Assignment OBJECT-TYPE
    SYNTAX          DisplayString (SIZE(0..23))
    ACCESS          read-only
    STATUS          obsolete
    DESCRIPTION     
            "This field is obsolete. It is replaced by AltGateway field."
    DEFVAL          { "" }
    ::= { sonusSs7NodeEntry 115 }

sonusSs7NodeGateway1Priority OBJECT-TYPE
    SYNTAX          INTEGER (1..2)
    ACCESS          read-only
    STATUS          obsolete
    DESCRIPTION     
            "This field is obsolete.  It is replaced by AltGatewayPriority field."
    DEFVAL          { 1 }
    ::= { sonusSs7NodeEntry 116 }

sonusSs7NodeAltGatewayPriority OBJECT-TYPE
    SYNTAX          INTEGER (1..2)
    ACCESS          read-write
    STATUS          mandatory
    DESCRIPTION     
            "The priority of the Gateway for carrying the messages"
    DEFVAL          { 1 }
    ::= { sonusSs7NodeEntry 117 }

sonusSs7NodeSgx4000 OBJECT-TYPE
    SYNTAX          INTEGER { disabled(0), enabled(1) }
    ACCESS          read-write
    STATUS          mandatory
    DESCRIPTION     
            "Configuration Control to specify the connected SGX is either SGX4000 or SGX2000."
    DEFVAL          { disabled }
    ::= { sonusSs7NodeEntry 118 }

sonusSs7NodeSlsRotation OBJECT-TYPE
    SYNTAX          INTEGER { disabled(1), enabled(2) }
    ACCESS          read-write
    STATUS          mandatory
    DESCRIPTION     
            "The SlsRotation, if disabled, will bypass existing sls rotation code.
             This is only applicable to M3UA connections to the SGX.
             Having it set to enabled is the recommendation to maintain existing functionality."
    DEFVAL          { enabled }
    ::= { sonusSs7NodeEntry 119 }

sonusSs7NodeProfile OBJECT IDENTIFIER
    ::= { sonusSs7ServicesMIBObjects 3 }

sonusSs7NodeProfileNextIndex OBJECT-TYPE
    SYNTAX          INTEGER
    ACCESS          read-only
    STATUS          obsolete
    DESCRIPTION     
            "The next valid index to use when creating an entry in
             the sonusSs7NodeProfileTable. This object is
             obsoleted as of GSX release 5.1 "
    ::= { sonusSs7NodeProfile 1 }

sonusSs7NodeProfileTable OBJECT-TYPE
    SYNTAX          SEQUENCE OF SonusSs7NodeProfileEntry
    ACCESS          not-accessible
    STATUS          obsolete
    DESCRIPTION     
            "This table specifies the SS7 Node Profile list for
             the GSX9000 node. This table is obsoleted as of GSX
             release 5.1"
    ::= { sonusSs7NodeProfile 2 }

sonusSs7NodeProfileEntry OBJECT-TYPE
    SYNTAX          SonusSs7NodeProfileEntry
    ACCESS          not-accessible
    STATUS          obsolete
    DESCRIPTION     
            ""
    INDEX           { sonusSs7NodeProfileIndex }
    ::= { sonusSs7NodeProfileTable 1 }

SonusSs7NodeProfileEntry ::=
    SEQUENCE {
        sonusSs7NodeProfileIndex        INTEGER,
        sonusSs7NodeProfileName         SonusName,
        sonusSs7PointCodeSize           INTEGER,
        sonusSs7PointCodeFormatType     SonusPointCodeFormat,
        sonusSs7ServerProtocol          INTEGER,
        sonusSs7HandShakeInterval       INTEGER,
        sonusSs7TimerT1                 INTEGER,
        sonusSs7TimerT2                 INTEGER,
        sonusSs7TimerT3                 INTEGER,
        sonusSs7TimerT4                 INTEGER,
        sonusSs7TimerT5                 INTEGER,
        sonusSs7TimerT6                 INTEGER,
        sonusSs7TimerT7                 INTEGER,
        sonusSs7TimerT8                 INTEGER,
        sonusSs7TimerT9                 INTEGER,
        sonusSs7TimerT10                INTEGER,
        sonusSs7TimerT11                INTEGER,
        sonusSs7TimerT12                INTEGER,
        sonusSs7TimerT13                INTEGER,
        sonusSs7TimerT14                INTEGER,
        sonusSs7TimerT15                INTEGER,
        sonusSs7TimerT16                INTEGER,
        sonusSs7TimerT17                INTEGER,
        sonusSs7TimerT18                INTEGER,
        sonusSs7TimerT19                INTEGER,
        sonusSs7TimerT20                INTEGER,
        sonusSs7TimerT21                INTEGER,
        sonusSs7TimerT22                INTEGER,
        sonusSs7TimerT23                INTEGER,
        sonusSs7TimerT24                INTEGER,
        sonusSs7TimerT25                INTEGER,
        sonusSs7TimerT26                INTEGER,
        sonusSs7TimerT27                INTEGER,
        sonusSs7TimerT28                INTEGER,
        sonusSs7TimerT29                INTEGER,
        sonusSs7TimerT30                INTEGER,
        sonusSs7TimerT31                INTEGER,
        sonusSs7TimerT32                INTEGER,
        sonusSs7TimerT33                INTEGER,
        sonusSs7TimerT34                INTEGER,
        sonusSs7TimerT35                INTEGER,
        sonusSs7TimerT36                INTEGER,
        sonusSs7TimerT37                INTEGER,
        sonusSs7TimerT38                INTEGER,
        sonusSs7TimerT39                INTEGER,
        sonusSs7TimerT40                INTEGER,
        sonusSs7TimerTAcc               INTEGER,
        sonusSs7TimerTCcr               INTEGER,
        sonusSs7TimerTCcrr              INTEGER,
        sonusSs7TimerTCgb               INTEGER,
        sonusSs7TimerTCra               INTEGER,
        sonusSs7TimerTCrm               INTEGER,
        sonusSs7TimerTCvt               INTEGER,
        sonusSs7TimerTExm               INTEGER,
        sonusSs7TimerTGrs               INTEGER,
        sonusSs7TimerTHga               INTEGER,
        sonusSs7TimerTScga              INTEGER,
        sonusSs7TimerTScgad             INTEGER,
        sonusSs7NodeProfileState        INTEGER,
        sonusSs7NodeProfileRowStatus    RowStatus,
        sonusSs7NodeProfileNetworkInd   INTEGER,
        sonusSs7SlsBits                 INTEGER,
        sonusSs7TimerTA                 INTEGER,
        sonusSs7TimerTBlom              INTEGER,
        sonusSs7TimerTCotd              INTEGER,
        sonusSs7TimerTCotl              INTEGER,
        sonusSs7TimerTSus               INTEGER
    }

sonusSs7NodeProfileIndex OBJECT-TYPE
    SYNTAX          INTEGER
    ACCESS          read-only
    STATUS          obsolete
    DESCRIPTION     
            "Identifies the SS7 Node Profile entry. This object is
             obsoleted as of GSX release 5.1"
    ::= { sonusSs7NodeProfileEntry 1 }

sonusSs7NodeProfileName OBJECT-TYPE
    SYNTAX          SonusName
    ACCESS          read-write
    STATUS          obsolete
    DESCRIPTION     
            "The name of the Node Profile. This object is
             obsoleted as of GSX release 5.1"
    ::= { sonusSs7NodeProfileEntry 2 }

sonusSs7PointCodeSize OBJECT-TYPE
    SYNTAX          INTEGER (1..32)
    ACCESS          read-write
    STATUS          obsolete
    DESCRIPTION     
            "Indicates the total number of bits in the point code. This object is
             obsoleted as of GSX release 5.1"
    DEFVAL          { 24 }
    ::= { sonusSs7NodeProfileEntry 3 }

sonusSs7PointCodeFormatType OBJECT-TYPE
    SYNTAX          SonusPointCodeFormat
    ACCESS          read-write
    STATUS          obsolete
    DESCRIPTION     
            "The Point Code format type being defined.This object is
             obsoleted as of GSX release 5.1"
    ::= { sonusSs7NodeProfileEntry 4 }

sonusSs7ServerProtocol OBJECT-TYPE
    SYNTAX          INTEGER { dgmsProp(1), dgmsRaw(2), tekTali(3), 
                        dgmsSuperRaw(4), m3ua(5) }
    ACCESS          read-write
    STATUS          obsolete
    DESCRIPTION     
            "The interface used between the SS7 gateway and the SS7 client
             on the GSX9000.This object is obsoleted as of GSX release 5.1"
    DEFVAL          { dgmsProp }
    ::= { sonusSs7NodeProfileEntry 5 }

sonusSs7HandShakeInterval OBJECT-TYPE
    SYNTAX          INTEGER (1..255)
    ACCESS          read-write
    STATUS          obsolete
    DESCRIPTION     
            "HandShake interval between the client and the server in seconds.
             This object is obsoleted as of GSX release 5.1"
    ::= { sonusSs7NodeProfileEntry 6 }

sonusSs7TimerT1 OBJECT-TYPE
    SYNTAX          INTEGER (4..180)
    ACCESS          read-write
    STATUS          obsolete
    DESCRIPTION     
            "The Timer T1 could be changed from its default using this entry for ISUP, and when the Called
             Sub clears first awaiting reanswer in BT7. The valid ranges are 4 - 15 seconds for ANSI, 15 - 60 
             Seconds for ITU and 2 - 180 seconds for BT7. This object is obsoleted as of GSX release 5.1"
    DEFVAL          { 10 }
    ::= { sonusSs7NodeProfileEntry 7 }

sonusSs7TimerT2 OBJECT-TYPE
    SYNTAX          INTEGER (1..720)
    ACCESS          read-write
    STATUS          obsolete
    DESCRIPTION     
            "The Timer T2 could be changed from its default using this entry in ISUP, and waiting for Answer 
             Message in BT7. The valid value for ITU is 3 Minutes and 60 - 720 seconds for BT7. This timer 
             has no relevence in the ANSI network. This object is obsoleted as of GSX release 5.1 "
    DEFVAL          { 180 }
    ::= { sonusSs7NodeProfileEntry 8 }

sonusSs7TimerT3 OBJECT-TYPE
    SYNTAX          INTEGER (1..300)
    ACCESS          read-write
    STATUS          obsolete
    DESCRIPTION     
            "The T3 timer is started on receipt of an Overload message in the ITU network, and awaiting Called
             Sub Release forward or Re-Answer in BT7. This has no relevence in the ANSI network. The valid ITU 
             recommended value is 120 Seconds, and 300 seconds for BT7. This object is obsoleted as of GSX 
             release 5.1 "
    DEFVAL          { 120 }
    ::= { sonusSs7NodeProfileEntry 9 }

sonusSs7TimerT4 OBJECT-TYPE
    SYNTAX          INTEGER (120..900)
    ACCESS          read-write
    STATUS          obsolete
    DESCRIPTION     
            "The Timer T4 could be changed from its default using this entry in ISUP, and delaying release of
             Circuit for 2 minutes while exchange in Overload for BT7. This object is obsoleted as of GSX 
             release 5.1 "
    DEFVAL          { 600 }
    ::= { sonusSs7NodeProfileEntry 10 }

sonusSs7TimerT5 OBJECT-TYPE
    SYNTAX          INTEGER (60..900)
    ACCESS          read-write
    STATUS          obsolete
    DESCRIPTION     
            "The T5 Timer is started when the release message is sent in ISUP, and awaiting Answer in Terminating Node
             for BT7. The valid values as per the specifications are 60 seconds for the ANSI, 300 to 900 seconds for
             ITU, and 60 - 840 seconds for BT7. This object is obsoleted as of GSX release 5.1 "
    DEFVAL          { 60 }
    ::= { sonusSs7NodeProfileEntry 11 }

sonusSs7TimerT6 OBJECT-TYPE
    SYNTAX          INTEGER (1..32)
    ACCESS          read-write
    STATUS          obsolete
    DESCRIPTION     
            "The timer T6 is started when the suspend message is received in ISUP, or to determine end of dialing in BT7. 
             The valid ISUP range for this timer is 10 to 32 seconds, and 1 - 6 seconds in BT7. This object is obsoleted
             as of GSX release 5.1"
    DEFVAL          { 22 }
    ::= { sonusSs7NodeProfileEntry 12 }

sonusSs7TimerT7 OBJECT-TYPE
    SYNTAX          INTEGER (2..50)
    ACCESS          read-write
    STATUS          obsolete
    DESCRIPTION     
            "The Timer T7 could be changed from its default using this entry. Currently not used in BT7.
             This object is obsoleted as of GSX release 5.1 "
    DEFVAL          { 25 }
    ::= { sonusSs7NodeProfileEntry 13 }

sonusSs7TimerT8 OBJECT-TYPE
    SYNTAX          INTEGER (1..40)
    ACCESS          read-write
    STATUS          obsolete
    DESCRIPTION     
            "The T8 timer is timer to be started with continuity check has been indicated in the IAM for ISUP, and
             awaiting Blocking or UnBlocking message in BT7. The valid range is 10 to 15 seconds for ISUP, and 1 - 40
             seconds for BT7. This object is obsoleted as of GSX release 5.1 "
    DEFVAL          { 13 }
    ::= { sonusSs7NodeProfileEntry 14 }

sonusSs7TimerT9 OBJECT-TYPE
    SYNTAX          INTEGER (5..240)
    ACCESS          read-write
    STATUS          obsolete
    DESCRIPTION     
            "The Timer T9 started when outgoing international exchange recieves an ACM in ISUP, and awaiting backwards
             message in BT7. The valid range is 120 to 240 seconds for ISUP, and 5 - 30 seconds for BT7.This object 
             is obsoleted as of GSX release 5.1"
    DEFVAL          { 180 }
    ::= { sonusSs7NodeProfileEntry 15 }

sonusSs7TimerT10 OBJECT-TYPE
    SYNTAX          INTEGER (1..360)
    ACCESS          read-write
    STATUS          obsolete
    DESCRIPTION     
            "The Timer T10 is started when the last digit is recived in interworking situations for ISUP, and waiting for 
             forwards Release message in BT7. This timer has no relevence to ANSI. The valid range is 1 - 40 seconds
             for BT7. This object is obsoleted as of GSX release 5.1 "
    DEFVAL          { 300 }
    ::= { sonusSs7NodeProfileEntry 16 }

sonusSs7TimerT11 OBJECT-TYPE
    SYNTAX          INTEGER (15..20)
    ACCESS          read-write
    STATUS          obsolete
    DESCRIPTION     
            "The Timer T11 is started when the latest address message is received in interworking 
             situations. Currently not used by BT7.  The valid range is 15 to 20 seconds. This 
             object is obsoleted as of GSX release 5.1"
    DEFVAL          { 17 }
    ::= { sonusSs7NodeProfileEntry 17 }

sonusSs7TimerT12 OBJECT-TYPE
    SYNTAX          INTEGER (1..60)
    ACCESS          read-write
    STATUS          obsolete
    DESCRIPTION     
            "The Timer T12 is started when a blocking message is sent in ISUP, and awaiting Circuit Free or Blocking
             message for BT7. The valid ranges are 4 to 15 seconds for ANSI, 15 to 60 seconds for ITU, and 1 - 60
             seconds for BT7. This object is obsoleted as of GSX release 5.1"
    DEFVAL          { 10 }
    ::= { sonusSs7NodeProfileEntry 18 }

sonusSs7TimerT13 OBJECT-TYPE
    SYNTAX          INTEGER (60..900)
    ACCESS          read-write
    STATUS          obsolete
    DESCRIPTION     
            "The Timer T13 is started when the initial blocking messge is sent. Currently not used by BT7. 
             The valid value for ANSI is 60 seconds and for ITU is between 300 and 900 seconds. This object
             is obsoleted as of GSX release 5.1"
    DEFVAL          { 60 }
    ::= { sonusSs7NodeProfileEntry 19 }

sonusSs7TimerT14 OBJECT-TYPE
    SYNTAX          INTEGER (1..60)
    ACCESS          read-write
    STATUS          obsolete
    DESCRIPTION     
            "The Timer T14 is started when an unblocking message is sent in ISUP, and awaiting Additional
             information in BT7. The valid values are 4 to 15 seconds for ANSI, 15 to 60 seconds for ITU, and
             1 - 40 seconds for BT7. This object is obsoleted as of GSX release 5.1 "
    DEFVAL          { 10 }
    ::= { sonusSs7NodeProfileEntry 20 }

sonusSs7TimerT15 OBJECT-TYPE
    SYNTAX          INTEGER (60..900)
    ACCESS          read-write
    STATUS          obsolete
    DESCRIPTION     
            "The Timer T15 is started when the initial unblocking message is sent. Currently not used by BT7.
             The valid values are 60 seconds for ANSI and 300 to 900 seconds for ITU. This object is obsoleted
             as of GSX release 5.1 "
    DEFVAL          { 60 }
    ::= { sonusSs7NodeProfileEntry 21 }

sonusSs7TimerT16 OBJECT-TYPE
    SYNTAX          INTEGER (4..180)
    ACCESS          read-write
    STATUS          obsolete
    DESCRIPTION     
            "The Timer T16 is started when the reset circuit is started which was not due to expiry of
             T5 in ISUP, and prolonged call setup in BT7. The valid ranges are 4 to 15 seconds for ANSI, 15 to 
             		60 seconds for ITU, and 60 to 180 seconds for BT7. This object is obsoleted as of GSX release 5.1 "
    DEFVAL          { 10 }
    ::= { sonusSs7NodeProfileEntry 22 }

sonusSs7TimerT17 OBJECT-TYPE
    SYNTAX          INTEGER (5..900)
    ACCESS          read-write
    STATUS          obsolete
    DESCRIPTION     
            "The Timer T17 is started when initial reset message is sent in ISUP, and awaiting receipt of SAM/FAM
             after sending a SAD message. The valid values are 60 seconds for ANSI, 300 to 900 for ITU, and 5 to
             20 seconds for BT7. This object is obsoleted as of GSX release 5.1 "
    DEFVAL          { 60 }
    ::= { sonusSs7NodeProfileEntry 23 }

sonusSs7TimerT18 OBJECT-TYPE
    SYNTAX          INTEGER (4..180)
    ACCESS          read-write
    STATUS          obsolete
    DESCRIPTION     
            "The Timer T18 is started when circuit group blocking message is sent in ISUP, and awaiting receipt of
             SAM/FAM after sending a SND message. The valid values are 4 to 15 seconds for ANSI, 15 to 60 seconds 
             for ITU, and 5 to 180 seconds for BT7. This object is obsoleted as of GSX release 5.1"
    DEFVAL          { 10 }
    ::= { sonusSs7NodeProfileEntry 24 }

sonusSs7TimerT19 OBJECT-TYPE
    SYNTAX          INTEGER (60..900)
    ACCESS          read-write
    STATUS          obsolete
    DESCRIPTION     
            "The Timer T19 is started when initial group blocking message is sent. Currently not used by BT7.
             The valid values are 60 seconds for ANSI and 300 to 900 seconds for ITU. This object is obsoleted 
             as of GSX release 5.1"
    DEFVAL          { 60 }
    ::= { sonusSs7NodeProfileEntry 25 }

sonusSs7TimerT20 OBJECT-TYPE
    SYNTAX          INTEGER (4..60)
    ACCESS          read-write
    STATUS          obsolete
    DESCRIPTION     
            "The Timer T20 is started when group unblocking message is sent. Currently no used by BT7.
             The valid ranges are 4 to 15 seconds for ANSI and 15 to 60 seconds for ITU.This object is
             obsoleted as of GSX release 5.1"
    DEFVAL          { 10 }
    ::= { sonusSs7NodeProfileEntry 26 }

sonusSs7TimerT21 OBJECT-TYPE
    SYNTAX          INTEGER (60..900)
    ACCESS          read-write
    STATUS          obsolete
    DESCRIPTION     
            "The Timer T21 is started when initial group blocking message is sent in ISUP, and awaiting Resume in
             BT7. The valid values are 60 seconds for ANSI, 300 to 900 seconds for ITU, 180 seconds for BT7.This 
             object is obsoleted as of GSX release 5.1"
    DEFVAL          { 60 }
    ::= { sonusSs7NodeProfileEntry 27 }

sonusSs7TimerT22 OBJECT-TYPE
    SYNTAX          INTEGER (4..60)
    ACCESS          read-write
    STATUS          obsolete
    DESCRIPTION     
            "The Timer T22 is started when circuit group reset message is sent. The valid values are
             4 to 15 seconds for ANSI and 15 to 60 seconds for ITU. This object is obsoleted as of
             		 GSX release 5.1"
    DEFVAL          { 10 }
    ::= { sonusSs7NodeProfileEntry 28 }

sonusSs7TimerT23 OBJECT-TYPE
    SYNTAX          INTEGER (60..900)
    ACCESS          read-write
    STATUS          obsolete
    DESCRIPTION     
            "The Timer T23 is started when initial group reset message is sent. The valid values
             are 60 seconds for the ANSI and 300 to 900 seconds for the ITU. This object is
             		 obsoleted as of GSX release 5.1 "
    DEFVAL          { 60 }
    ::= { sonusSs7NodeProfileEntry 29 }

sonusSs7TimerT24 OBJECT-TYPE
    SYNTAX          INTEGER (1..2)
    ACCESS          read-write
    STATUS          obsolete
    DESCRIPTION     
            "The Timer T24 is started when check tone is sent. The value is less
             than 2 seconds. This object is obsoleted as of GSX release 5.1 "
    DEFVAL          { 1 }
    ::= { sonusSs7NodeProfileEntry 30 }

sonusSs7TimerT25 OBJECT-TYPE
    SYNTAX          INTEGER (1..20)
    ACCESS          read-write
    STATUS          obsolete
    DESCRIPTION     
            "The Timer T25 is started when initial continuity check failure is 
             detected. The valid range for ANSI is 1 to 10 seconds. For GR317 the valid range is 16 to 20 seconds.
             		 This object is obsoleted as of GSX release 5.1"
    DEFVAL          { 5 }
    ::= { sonusSs7NodeProfileEntry 31 }

sonusSs7TimerT26 OBJECT-TYPE
    SYNTAX          INTEGER (60..180)
    ACCESS          read-write
    STATUS          obsolete
    DESCRIPTION     
            "The Timer T26 is started when a second or subsequent continuity failure is detected.
             The valid value are 60 to 180 seconds. This object is obsoleted as of GSX release 5.1"
    DEFVAL          { 120 }
    ::= { sonusSs7NodeProfileEntry 32 }

sonusSs7TimerT27 OBJECT-TYPE
    SYNTAX          INTEGER (180..36000)
    ACCESS          read-write
    STATUS          obsolete
    DESCRIPTION     
            "The Timer T27 is started when a continuity fail message is recieved. The valid values are
             more than 180 seconds for ANSI and 240 seconds for ITU. This object is obsoleted as of
             		 GSX release 5.1"
    DEFVAL          { 240 }
    ::= { sonusSs7NodeProfileEntry 33 }

sonusSs7TimerT28 OBJECT-TYPE
    SYNTAX          INTEGER (5..12)
    ACCESS          read-write
    STATUS          obsolete
    DESCRIPTION     
            "The Timer T28 is started when Circuit Query Message is sent. The valid value is 10 seconds. 
             This object is obsoleted as of GSX release 5.1"
    DEFVAL          { 10 }
    ::= { sonusSs7NodeProfileEntry 34 }

sonusSs7TimerT29 OBJECT-TYPE
    SYNTAX          INTEGER (300..600)
    ACCESS          read-write
    STATUS          obsolete
    DESCRIPTION     
            "The Timer T29 is started when Congestion indication is received when T29
             is not running. The valid range is 300 to 600 milli second. This timer has
             no relevence for ANSI. This object is obsoleted as of GSX release 5.1"
    ::= { sonusSs7NodeProfileEntry 35 }

sonusSs7TimerT30 OBJECT-TYPE
    SYNTAX          INTEGER (5..10)
    ACCESS          read-write
    STATUS          obsolete
    DESCRIPTION     
            "The Timer T30 is stared when congestion indication is recieved when T29 is not running. The valid 
             range is 5 to 10 seconds for the ITU. This timer has no relevence under ANSI.This object is 
             		 obsoleted as of GSX release 5.1"
    ::= { sonusSs7NodeProfileEntry 36 }

sonusSs7TimerT31 OBJECT-TYPE
    SYNTAX          INTEGER (360..65520)
    ACCESS          read-write
    STATUS          obsolete
    DESCRIPTION     
            "The Timer T31 is started on release of ISUP signalling connection based on
             CO SCCP. The value should be set to greater than 360 seconds. This object 
             		 is obsoleted as of GSX release 5.1"
    DEFVAL          { 420 }
    ::= { sonusSs7NodeProfileEntry 37 }

sonusSs7TimerT32 OBJECT-TYPE
    SYNTAX          INTEGER (3..5)
    ACCESS          read-write
    STATUS          obsolete
    DESCRIPTION     
            "The Timer T32 is started when the first end-to-end message is recived. Under ANSI this
             timer is started after the response to such a message is sent. The valid values are 3 
             to 5 seconds. This object is obsoleted as of GSX release 5.1"
    DEFVAL          { 4 }
    ::= { sonusSs7NodeProfileEntry 38 }

sonusSs7TimerT33 OBJECT-TYPE
    SYNTAX          INTEGER (12..15)
    ACCESS          read-write
    STATUS          obsolete
    DESCRIPTION     
            "The Timer T33 is started when Information Request Message is sent. The 
             valid range is 12 to 15 seconds. This object is obsoleted as of GSX release 5.1"
    DEFVAL          { 14 }
    ::= { sonusSs7NodeProfileEntry 39 }

sonusSs7TimerT34 OBJECT-TYPE
    SYNTAX          INTEGER (2..15)
    ACCESS          read-write
    STATUS          obsolete
    DESCRIPTION     
            "The Timer T34 is started when Loop Back Acknowledgement is sent under ANSI.
             The Timer T34 is started when segmentation is received for IAM, ACM, CPG,
             ANM or CON under ITU. The valid range for ANSI is 10 to 15 seconds. The valid
             range for ITU is 2 to 4 seconds.This object is obsoleted as of GSX release 5.1"
    ::= { sonusSs7NodeProfileEntry 40 }

sonusSs7TimerT35 OBJECT-TYPE
    SYNTAX          INTEGER (4..20)
    ACCESS          read-write
    STATUS          obsolete
    DESCRIPTION     
            "The Timer T35 is started when the last digit recieved is not an ST digit or
             the fixed number of digits have been recieved. This procedure is only valid
             for overlap hence ITU. This timer has no relevence in ANSI.This object is
             		 obsoleted as of GSX release 5.1"
    DEFVAL          { 18 }
    ::= { sonusSs7NodeProfileEntry 41 }

sonusSs7TimerT36 OBJECT-TYPE
    SYNTAX          INTEGER (2..15)
    ACCESS          read-write
    STATUS          obsolete
    DESCRIPTION     
            "The Timer T36 is started when IAM is recived with a segmentation indication for ANSI.
             This timer is started when transit or incoming international exchange recieves Continuity check
             request message. The valid range for ANSI is 2 to 4 seconds and 10 to 15 
             seconds for ITU. This object is obsoleted as of GSX release 5.1"
    ::= { sonusSs7NodeProfileEntry 42 }

sonusSs7TimerT37 OBJECT-TYPE
    SYNTAX          INTEGER (2..30)
    ACCESS          read-write
    STATUS          obsolete
    DESCRIPTION     
            "The Timer T37 is started when User Part Availability test is started under ANSI. This
             timer is started when a request for and Echo control device is sent to another exchange
             under ITU. The valid value for ANSI is 30 seconds and for ITU is 2 to 4 seconds. This
             		 object is obsoleted as of GSX release 5.1"
    ::= { sonusSs7NodeProfileEntry 43 }

sonusSs7TimerT38 OBJECT-TYPE
    SYNTAX          INTEGER (10..60)
    ACCESS          read-write
    STATUS          obsolete
    DESCRIPTION     
            "The Timer T38 is started when a suspend message is sent to the preceding switch. This timer
             is only relevent under ITU. This object is obsoleted as of GSX release 5.1"
    DEFVAL          { 30 }
    ::= { sonusSs7NodeProfileEntry 44 }

sonusSs7TimerT39 OBJECT-TYPE
    SYNTAX          INTEGER (1..65535)
    ACCESS          read-write
    STATUS          obsolete
    DESCRIPTION     
            "The Timer T39 is started when MCID request is sent. It is only relevent in the ITU.
             This object is obsoleted as of GSX release 5.1"
    ::= { sonusSs7NodeProfileEntry 45 }

sonusSs7TimerT40 OBJECT-TYPE
    SYNTAX          INTEGER (1..65535)
    ACCESS          read-write
    STATUS          obsolete
    DESCRIPTION     
            "The Timer T40 could be changed from its default using this entry.This object is 
             obsoleted as of GSX release 5.1"
    ::= { sonusSs7NodeProfileEntry 46 }

sonusSs7TimerTAcc OBJECT-TYPE
    SYNTAX          INTEGER (3..8)
    ACCESS          read-write
    STATUS          obsolete
    DESCRIPTION     
            "Automatic Congestion Control Timer as per ANSI T1.113.4 - 1995. The value
             of the timer is 5 Seconds. This object is obsoleted as of GSX release 5.1"
    DEFVAL          { 5 }
    ::= { sonusSs7NodeProfileEntry 47 }

sonusSs7TimerTCcr OBJECT-TYPE
    SYNTAX          INTEGER (1..3)
    ACCESS          read-write
    STATUS          obsolete
    DESCRIPTION     
            "Continuity Check Request Timer. The value As per ANSI T1.113.4 - 1995 is 2 Seconds.
             This object is obsoleted as of GSX release 5.1"
    DEFVAL          { 2 }
    ::= { sonusSs7NodeProfileEntry 48 }

sonusSs7TimerTCcrr OBJECT-TYPE
    SYNTAX          INTEGER (16..31)
    ACCESS          read-write
    STATUS          obsolete
    DESCRIPTION     
            "Continuity Check Failed Recived. The value as per ANSI T1.113.4 - 1995 is 20 Seconds.
             This object is obsoleted as of GSX release 5.1"
    DEFVAL          { 20 }
    ::= { sonusSs7NodeProfileEntry 49 }

sonusSs7TimerTCgb OBJECT-TYPE
    SYNTAX          INTEGER (3..8)
    ACCESS          read-write
    STATUS          obsolete
    DESCRIPTION     
            "Timer started on recipt of a Circuit Group Block Message. The value as per
             ANSI T1.113.4 - 1995 is 5 Seconds. This object is obsoleted as of GSX release 5.1"
    DEFVAL          { 5 }
    ::= { sonusSs7NodeProfileEntry 50 }

sonusSs7TimerTCra OBJECT-TYPE
    SYNTAX          INTEGER (10..31)
    ACCESS          read-write
    STATUS          obsolete
    DESCRIPTION     
            "Timer started when Circuit Reservation Acknowledgment is sent. The time value
             as per ANSI T1.113.4 - 1995 is 20 seconds. This object is obsoleted as of GSX 
             release 5.1"
    DEFVAL          { 20 }
    ::= { sonusSs7NodeProfileEntry 51 }

sonusSs7TimerTCrm OBJECT-TYPE
    SYNTAX          INTEGER (3..4)
    ACCESS          read-write
    STATUS          obsolete
    DESCRIPTION     
            "This timer is started when the circuit reservation message is sent. The value 
             as per ANSI T1.113.4 - 1995 is 3 - 4 Seconds. The default is set to 4 seconds.
             This object is obsoleted as of GSX release 5.1"
    DEFVAL          { 4 }
    ::= { sonusSs7NodeProfileEntry 52 }

sonusSs7TimerTCvt OBJECT-TYPE
    SYNTAX          INTEGER (5..12)
    ACCESS          read-write
    STATUS          obsolete
    DESCRIPTION     
            "The Timer T CVT is started when the Circuit Validation Test message
             is sent. This message is only valid for ANSI. This object is obsoleted
             		 as of GSX release 5.1"
    DEFVAL          { 10 }
    ::= { sonusSs7NodeProfileEntry 53 }

sonusSs7TimerTExm OBJECT-TYPE
    SYNTAX          INTEGER (1..65535)
    ACCESS          read-write
    STATUS          obsolete
    DESCRIPTION     
            "The Timer Exm,d is started when IAM is sent to the succeeding network. This
             timer has no relevence in the ITU. This timer is in milliseconds. This object
             		 is obsoleted as of GSX release 5.1"
    ::= { sonusSs7NodeProfileEntry 54 }

sonusSs7TimerTGrs OBJECT-TYPE
    SYNTAX          INTEGER (3..8)
    ACCESS          read-write
    STATUS          obsolete
    DESCRIPTION     
            "This timer is started when a circuit group reset message is received. 
             This timer is only relevent in the ANSI network. This object is 
             		 obsoleted as of GSX release 5.1 "
    DEFVAL          { 5 }
    ::= { sonusSs7NodeProfileEntry 55 }

sonusSs7TimerTHga OBJECT-TYPE
    SYNTAX          INTEGER (0..300)
    ACCESS          read-write
    STATUS          obsolete
    DESCRIPTION     
            "This timer is started on recognition of carrier loss. It is only relevent in ANSI
             network. The valid range is 0 to 300 seconds. This object is obsoleted as of 
             		 GSX release 5.1"
    DEFVAL          { 150 }
    ::= { sonusSs7NodeProfileEntry 56 }

sonusSs7TimerTScga OBJECT-TYPE
    SYNTAX          INTEGER (0..120)
    ACCESS          read-write
    STATUS          obsolete
    DESCRIPTION     
            "This timer is started when initial demand continuity check fails in the
             SCGA group. The valid range for this timer is 0 to 120 seconds. This object 
             		 is obsoleted as of GSX release 5.1"
    DEFVAL          { 60 }
    ::= { sonusSs7NodeProfileEntry 57 }

sonusSs7TimerTScgad OBJECT-TYPE
    SYNTAX          INTEGER (5..120)
    ACCESS          read-write
    STATUS          obsolete
    DESCRIPTION     
            "This timer is started failure of demand continuity check in the SCGA group. 
             This object is obsoleted as of GSX release 5.1"
    DEFVAL          { 65 }
    ::= { sonusSs7NodeProfileEntry 58 }

sonusSs7NodeProfileState OBJECT-TYPE
    SYNTAX          INTEGER { disabled(1), enabled(2) }
    ACCESS          read-write
    STATUS          obsolete
    DESCRIPTION     
            "The administrative state of this object. This object is obsoleted as of GSX release 5.1"
    DEFVAL          { disabled }
    ::= { sonusSs7NodeProfileEntry 59 }

sonusSs7NodeProfileRowStatus OBJECT-TYPE
    SYNTAX          RowStatus
    ACCESS          read-write
    STATUS          obsolete
    DESCRIPTION     
            " This object is obsoleted as of GSX release 5.1 "
    ::= { sonusSs7NodeProfileEntry 60 }

sonusSs7NodeProfileNetworkInd OBJECT-TYPE
    SYNTAX          INTEGER { intl0(1), intl1(2), natl0(3), natl1(4) }
    ACCESS          read-write
    STATUS          obsolete
    DESCRIPTION     
            "The setting of the Network Indicator used for this SS7 Node entry.
             This object is obsoleted as of GSX release 5.1 "
    DEFVAL          { natl0 }
    ::= { sonusSs7NodeProfileEntry 61 }

sonusSs7SlsBits OBJECT-TYPE
    SYNTAX          INTEGER (4..8)
    ACCESS          read-write
    STATUS          obsolete
    DESCRIPTION     
            "The number of SLS bits to use. This object is obsoleted as of GSX release 5.1"
    DEFVAL          { 5 }
    ::= { sonusSs7NodeProfileEntry 62 }

sonusSs7TimerTA OBJECT-TYPE
    SYNTAX          INTEGER (0..1000)
    ACCESS          read-write
    STATUS          obsolete
    DESCRIPTION     
            "The Bellcore specific timer TA is started when a RLC message is sent by the switch.
             The value of this timer is 0 to 1000 milliseconds. This object is obsoleted as of 
             GSX release 5.1"
    DEFVAL          { 500 }
    ::= { sonusSs7NodeProfileEntry 63 }

sonusSs7TimerTBlom OBJECT-TYPE
    SYNTAX          INTEGER (240..360)
    ACCESS          read-write
    STATUS          obsolete
    DESCRIPTION     
            "The Bellcore specific timer TBlom is started when blocking a circuit due to a
             BLO, and after any call is released; used to notify maintenance. This object 
             is obsoleted as of GSX release 5.1"
    DEFVAL          { 300 }
    ::= { sonusSs7NodeProfileEntry 64 }

sonusSs7TimerTCotd OBJECT-TYPE
    SYNTAX          INTEGER (0..500)
    ACCESS          read-write
    STATUS          obsolete
    DESCRIPTION     
            "The Bellcore specific timer TCOTd is started when sending IAM requesting
             continuity check. The value of this timer is in milliseconds. This object
             is obsoleted as of GSX release 5.1"
    DEFVAL          { 250 }
    ::= { sonusSs7NodeProfileEntry 65 }

sonusSs7TimerTCotl OBJECT-TYPE
    SYNTAX          INTEGER (240..300)
    ACCESS          read-write
    STATUS          obsolete
    DESCRIPTION     
            "The Bellcore specific timer TCOTl is started when receiving second COT
             coded failed, awaiting receipt of CCR. This object is obsoleted as of 
             GSX release 5.1"
    DEFVAL          { 300 }
    ::= { sonusSs7NodeProfileEntry 66 }

sonusSs7TimerTSus OBJECT-TYPE
    SYNTAX          INTEGER (14..16)
    ACCESS          read-write
    STATUS          obsolete
    DESCRIPTION     
            "The Bellcore specific timer TSUS is started when a SUS message is sent by the
             terminating switch, awaiting called party off-hook or REL. This object is 
             obsoleted as of GSX release 5.1"
    DEFVAL          { 15 }
    ::= { sonusSs7NodeProfileEntry 67 }

sonusSs7ServicesMIBNotifications OBJECT IDENTIFIER
    ::= { sonusSs7ServicesMIB 2 }

sonusSs7ServicesMIBNotificationsPrefix OBJECT IDENTIFIER
    ::= { sonusSs7ServicesMIBNotifications 0 }

sonusSs7ServicesMIBNotificationsObjects OBJECT IDENTIFIER
    ::= { sonusSs7ServicesMIBNotifications 1 }

sonusSs7NodeServiceType OBJECT-TYPE
    SYNTAX          DisplayString (SIZE(1..6))
    ACCESS          read-only
    STATUS          mandatory
    DESCRIPTION     
            "The type of service supported by this SS7 node connection (ISUP or TCAP)."
    ::= { sonusSs7ServicesMIBNotificationsObjects 1 }

sonusSs7NodeStateChangeReason OBJECT-TYPE
    SYNTAX          DisplayString (SIZE(1..101))
    ACCESS          read-only
    STATUS          mandatory
    DESCRIPTION     
            "The reason why this SS7 node connection has  changed state."
    ::= { sonusSs7ServicesMIBNotificationsObjects 2 }

sonusSs7NodeCurrentState OBJECT-TYPE
    SYNTAX          INTEGER { offline(1), active(2), initializing(3), 
                        failed(4), disabled(5), congested(6) }
    ACCESS          read-only
    STATUS          mandatory
    DESCRIPTION     
            "The current state of this SS7 node connection."
    ::= { sonusSs7ServicesMIBNotificationsObjects 3 }

sonusSs7NodeAffectedPointCode OBJECT-TYPE
    SYNTAX          PointCode
    ACCESS          read-only
    STATUS          mandatory
    DESCRIPTION     
            "The SS7 point code affected by this MTP state change."
    ::= { sonusSs7ServicesMIBNotificationsObjects 4 }

sonusSs7NodeACCObject OBJECT-TYPE
    SYNTAX          INTEGER { sonusSs7NodeTimerTAcc(1) }
    ACCESS          read-only
    STATUS          mandatory
    DESCRIPTION     
            "This object is a bit mask that indicates what ACC
             object in the SS7 Node table has changed."
    ::= { sonusSs7ServicesMIBNotificationsObjects 5 }

sonusSs7NodeServerProtocolChangeReason OBJECT-TYPE
    SYNTAX          DisplayString (SIZE(1..101))
    ACCESS          read-only
    STATUS          mandatory
    DESCRIPTION     
            "The reason why SS7 Node server protocol is changed to SUPERRAW "
    ::= { sonusSs7ServicesMIBNotificationsObjects 6 }

sonusSs7NodeConnectionEstablishedNotification TRAP-TYPE
    ENTERPRISE      sonusSs7ServicesMIBNotifications
    VARIABLES       { sonusSs7NodeName, sonusSs7NodeGatewayAssignment, 
                      sonusSs7NodeServiceType, sonusEventDescription, 
                      sonusEventClass, sonusEventLevel, sonusSequenceId, 
                      sonusEventTime }
--     STATUS          mandatory
    DESCRIPTION     
            "This trap indicates that a connection has been established to the
             specified SS7 gateway. Information provided by this trap includes
             the name of the connected SS7 node, the name of the SS7 gateway 
             on which the node resides, and the type of SS7 service that has been
             established (ISUP or TCAP)."
    ::= 1

sonusSs7NodeConnectionFailedNotification TRAP-TYPE
    ENTERPRISE      sonusSs7ServicesMIBNotifications
    VARIABLES       { sonusSs7NodeName, sonusSs7NodeGatewayAssignment, 
                      sonusSs7NodeServiceType, 
                      sonusSs7NodeStateChangeReason, 
                      sonusEventDescription, sonusEventClass, 
                      sonusEventLevel, sonusSequenceId, sonusEventTime }
--     STATUS          mandatory
    DESCRIPTION     
            "This trap indicates that an established connection to an SS7 gateway
             has failed. Information provided by this trap includes the name of the
             failed SS7 node, the name of the SS7 gateway on which the node resides,
             the type of SS7 service affected by this failure, and the reason why
             the connection has failed."
    ::= 2

sonusSs7NodeConnectionStateChangeNotification TRAP-TYPE
    ENTERPRISE      sonusSs7ServicesMIBNotifications
    VARIABLES       { sonusSs7NodeName, sonusSs7NodeGatewayAssignment, 
                      sonusSs7NodeServiceType, sonusSs7NodeCurrentState, 
                      sonusSs7NodeStateChangeReason, 
                      sonusEventDescription, sonusEventClass, 
                      sonusEventLevel, sonusSequenceId, sonusEventTime }
--     STATUS          mandatory
    DESCRIPTION     
            "This trap indicates that an established connection to an SS7 gateway
             has changed state. Information provided by this trap includes the name 
             of the affected SS7 node, the name of the SS7 gateway on which the node 
             resides, the type of SS7 service affected by this failure, the new state
             of the node, and the reason for the state change."
    ::= 3

sonusSs7NodeMtpStateChangeNotification TRAP-TYPE
    ENTERPRISE      sonusSs7ServicesMIBNotifications
    VARIABLES       { sonusSs7NodeName, sonusSs7NodeGatewayAssignment, 
                      sonusSs7NodeServiceType, sonusSs7NodeMtpStatus, 
                      sonusSs7NodeAffectedPointCode, 
                      sonusEventDescription, sonusEventClass, 
                      sonusEventLevel, sonusSequenceId, sonusEventTime }
--     STATUS          mandatory
    DESCRIPTION     
            "This trap indicates that a MTP state change event has been received from the
             SS7 gateway, affecting the specified destination (or remote) point 
             code (DPC). Information provided by this trap includes the name 
             of the affected SS7 node, the name of the SS7 gateway on which the node 
             resides, the updated MTP state, and the DPC affected by this event."
    ::= 4

sonusSs7NodeACCConfNotification TRAP-TYPE
    ENTERPRISE      sonusSs7ServicesMIBNotifications
    VARIABLES       { sonusSs7NodeName, sonusSs7NodeACCObject, 
                      sonusEventDescription, sonusEventClass, 
                      sonusEventLevel, sonusSequenceId, sonusEventTime }
--     STATUS          mandatory
    DESCRIPTION     
            "This trap indicates that a ACC Control 
             configuration object in  
             the SS7 node table has changed.  The  
             sonusSs7nodeACCObject parameter indicates what  
             object or objects have changed."
    ::= 5

sonusSs7NodeServerProtocolChangedToSuperRaw TRAP-TYPE
    ENTERPRISE      sonusSs7ServicesMIBNotifications
    VARIABLES       { sonusSs7NodeName, 
                      sonusSs7NodeServerProtocolChangeReason, 
                      sonusEventDescription, sonusEventClass, 
                      sonusEventLevel, sonusSequenceId, sonusEventTime }
--     STATUS          mandatory
    DESCRIPTION     
            "This trap indicates that SS7 Node's server protocol
             is forced to SUPERRAW, since PROP/ RAW modes are not
             supported in this GSX Release."
    ::= 6

sonusSs7NodeFailedCriticalNotification TRAP-TYPE
    ENTERPRISE      sonusSs7ServicesMIBNotifications
    VARIABLES       { sonusSs7NodeName, sonusSs7NodeGatewayAssignment, 
                      sonusSs7NodeServiceType, 
                      sonusSs7NodeStateChangeReason, 
                      sonusEventDescription, sonusEventClass, 
                      sonusEventLevel, sonusSequenceId, sonusEventTime }
--     STATUS          mandatory
    DESCRIPTION     
            "This critical trap indicates that a established connection to an SS7 gateway
             has failed. Information provided by this trap includes the name of the
             failed SS7 node, the name of the SS7 gateway on which the node resides,
             the type of SS7 service affected by this failure, and the reason why
             the connection has failed."
    ::= 7

sonusSs7NodeConnectivityChangeNotification TRAP-TYPE
    ENTERPRISE      sonusSs7ServicesMIBNotifications
    VARIABLES       { sonusSs7NodeName, sonusSs7NodeServiceType, 
                      sonusEventDescription, sonusEventClass, 
                      sonusEventLevel, sonusSequenceId, sonusEventTime }
--     STATUS          mandatory
    DESCRIPTION     
            "This trap indicates the connectivity of the named SS7 node 
             to the SS7 network has changed.  The new state can be either 
             CONNECTED or DISCONNECTED."
    ::= 8

sonusSs7NodeRpcStateChangeNotification TRAP-TYPE
    ENTERPRISE      sonusSs7ServicesMIBNotifications
    VARIABLES       { sonusSs7NodeName, sonusSs7NodeServiceType, 
                      sonusSs7NodeMtpStatus, 
                      sonusSs7NodeAffectedPointCode, 
                      sonusEventDescription, sonusEventClass, 
                      sonusEventLevel, sonusSequenceId, sonusEventTime }
--     STATUS          mandatory
    DESCRIPTION     
            "This trap indicates that the state of the named remote point 
             code in relation to the named node has changed.  The new state 
             can be one of PAUSE, RESUME, CONGESTED, or UPU"
    ::= 9

sonusSs7NodeRoutingKeyOverriddenNotification TRAP-TYPE
    ENTERPRISE      sonusSs7ServicesMIBNotifications
    VARIABLES       { sonusSs7NodeName, sonusSs7NodeAffectedPointCode, 
                      sonusEventDescription, sonusEventClass, 
                      sonusEventLevel, sonusSequenceId, sonusEventTime }
--     STATUS          mandatory
    DESCRIPTION     
            "This trap indicates that the active status of an M3UA 
             routing key between the named node and the remote point 
             code of this chassis has been overridden."
    ::= 10

sonusSs7StandbyNullPointerNotification TRAP-TYPE
    ENTERPRISE      sonusSs7ServicesMIBNotifications
    VARIABLES       { sonusEventDescription, sonusEventClass, 
                      sonusEventLevel, sonusSequenceId, sonusEventTime }
--     STATUS          mandatory
    DESCRIPTION     
            "This trap indicates that either the pNode or pConnMgmt pointer in the
             standby SS7FE is NULL.  This trap will be generated
             either when the Standby Node is going to Active state or
             when the Standby Node receives Redundancy messages from
             Active Node."
    ::= 11

END -- end of module SONUS-SS7-SERVICES-MIB.
