--
-- This SMIv1 module has been generated by smidump 0.2-cvs. Do not edit.
--

SONUS-SBX-TRAP-MIB DEFINITIONS ::= BEGIN

IMPORTS
    Ipv6Address
        FROM IPV6-TC
    OBJECT-TYPE
        FROM RFC-1212
    TRAP-TYPE
        FROM RFC-1215
    Counter, IpAddress
        FROM RFC1155-SMI
    DisplayString
        FROM SNMPv2-TC
    SonusAdminState, SonusGMTTime, SonusName, SonusNameReference
        FROM SONUS-COMMON-TC
    sonusAlarmDescription, sonusAlarmLevel, sonusAlarmNodeID, 
    sonusAlarmSequenceId, sonusAlarmTime
        FROM SONUS-COMMON-TRAP-MIB
    sonusSBX5000NotificationMIBs
        FROM SONUS-SMI;

sonusSbxTraps OBJECT IDENTIFIER
    ::= { sonusSBX5000NotificationMIBs 1 }

-- sonusSbxTraps MODULE-IDENTITY
--     LAST-UPDATED    "201504040000Z"
--     ORGANIZATION    
--             "Sonus Networks, Inc."
--     CONTACT-INFO    
--             "   Customer Support     
--              Sonus Networks, Inc. 
--              7 Technology Park Drive 
--                  Westford, MA 01886 
--              USA 
--              
--              Tel: 978-614-8100 
--                  Fax: 978-614-8609"
--     DESCRIPTION     
--             "The MIB Module for SBC notifications"
--     REVISION        "200911100000Z"
--     DESCRIPTION     
--             "Last revision."
--     ::= { sonusSBX5000NotificationMIBs 1 }


sonusSipSignallingMIBNotifications OBJECT IDENTIFIER
    ::= { sonusSbxTraps 1 }

sonusSipSignallingMIBNotificationsPrefix OBJECT IDENTIFIER
    ::= { sonusSipSignallingMIBNotifications 0 }

sonusSipSignallingMIBNotificationsObjects OBJECT IDENTIFIER
    ::= { sonusSipSignallingMIBNotifications 1 }

sonusSipTgName OBJECT-TYPE
    SYNTAX          SonusNameReference
    ACCESS          read-only
    STATUS          mandatory
    DESCRIPTION     
            "Name of the SIP service group."
    ::= { sonusSipSignallingMIBNotificationsObjects 1 }

sonusSipSigPortIpAddress OBJECT-TYPE
    SYNTAX          IpAddress
    ACCESS          read-only
    STATUS          mandatory
    DESCRIPTION     
            "
             IP Address of the Sip Signalling Port - mandatory parameter. 
             "
    ::= { sonusSipSignallingMIBNotificationsObjects 2 }

sonusSipSigPortNum OBJECT-TYPE
    SYNTAX          INTEGER (1..65535)
    ACCESS          read-only
    STATUS          mandatory
    DESCRIPTION     
            "
             UDP/TCP port number of SIP Signalling Port (default is 5060).
             "
    ::= { sonusSipSignallingMIBNotificationsObjects 3 }

sonusSipArsStatSigZoneId OBJECT-TYPE
    SYNTAX          Gauge
    ACCESS          read-only
    STATUS          mandatory
    DESCRIPTION     
            "The Id of the Signaling Zone where address reachability service status
             is being shown."
    ::= { sonusSipSignallingMIBNotificationsObjects 4 }

sonusSipArsStatEndpointIpAddress OBJECT-TYPE
    SYNTAX          IpAddress
    ACCESS          read-only
    STATUS          mandatory
    DESCRIPTION     
            "
             Blacklisted endpoint's IP Address. 
             "
    ::= { sonusSipSignallingMIBNotificationsObjects 5 }

sonusSipArsStatEndpointIpPortNum OBJECT-TYPE
    SYNTAX          INTEGER (0..65535)
    ACCESS          read-only
    STATUS          mandatory
    DESCRIPTION     
            "
             Blacklisted endpoint's UDP port number.
             "
    ::= { sonusSipSignallingMIBNotificationsObjects 6 }

sonusSipArsStatSigPortNum OBJECT-TYPE
    SYNTAX          Gauge
    ACCESS          read-only
    STATUS          mandatory
    DESCRIPTION     
            "A signaling port in the signaling zone showing status."
    ::= { sonusSipSignallingMIBNotificationsObjects 7 }

sonusSipArsStatEndpointOwnerId OBJECT-TYPE
    SYNTAX          Gauge (1..65535)
    ACCESS          read-only
    STATUS          mandatory
    DESCRIPTION     
            "Blacklisted endpoints owner id. This is identifies the slot that originally  blacklisted the endpoint."
    ::= { sonusSipSignallingMIBNotificationsObjects 8 }

sonusSipArsEndpointRecoveryAll OBJECT-TYPE
    SYNTAX          INTEGER { none(0), oneSigZone(1), allSigZone(2), 
                        allinOneSlot(3) }
    ACCESS          read-only
    STATUS          mandatory
    DESCRIPTION     
            "The flag for recovering a group of endpoints: all endpoints in one signaling
             zone or all endpoints in all signaling zones."
    ::= { sonusSipSignallingMIBNotificationsObjects 9 }

sonusSipSigProto OBJECT-TYPE
    SYNTAX          DisplayString
    ACCESS          read-only
    STATUS          mandatory
    DESCRIPTION     
            " The signaling transport protocol."
    ::= { sonusSipSignallingMIBNotificationsObjects 10 }

sonusPingPeerIpAddress OBJECT-TYPE
    SYNTAX          IpAddress
    ACCESS          read-only
    STATUS          mandatory
    DESCRIPTION     
            "IP Address of the SIP Peer."
    ::= { sonusSipSignallingMIBNotificationsObjects 11 }

sonusPingPeerPortNum OBJECT-TYPE
    SYNTAX          INTEGER (0..65535)
    ACCESS          read-only
    STATUS          mandatory
    DESCRIPTION     
            "UDP/TCP port number of SIP Peer."
    ::= { sonusSipSignallingMIBNotificationsObjects 12 }

sonusPingPeerZoneId OBJECT-TYPE
    SYNTAX          Gauge
    ACCESS          read-only
    STATUS          mandatory
    DESCRIPTION     
            "The Id of the Signaling Zone where OPTIONS is received from the SIP Peer."
    ::= { sonusSipSignallingMIBNotificationsObjects 13 }

sonusSipAorSigZoneId OBJECT-TYPE
    SYNTAX          Gauge
    ACCESS          read-only
    STATUS          mandatory
    DESCRIPTION     
            "The Id of the Signaling Zone"
    ::= { sonusSipSignallingMIBNotificationsObjects 14 }

sonusSurrRegPeerIpAddress OBJECT-TYPE
    SYNTAX          IpAddress
    ACCESS          read-only
    STATUS          mandatory
    DESCRIPTION     
            "IP Address of the SurrReg Peer."
    ::= { sonusSipSignallingMIBNotificationsObjects 15 }

sonusSurrRegPeerPortNum OBJECT-TYPE
    SYNTAX          INTEGER (1..65535)
    ACCESS          read-only
    STATUS          mandatory
    DESCRIPTION     
            "port number of SurrReg Peer."
    ::= { sonusSipSignallingMIBNotificationsObjects 16 }

sonusSurrRegPeerZoneId OBJECT-TYPE
    SYNTAX          Gauge
    ACCESS          read-only
    STATUS          mandatory
    DESCRIPTION     
            "The Id of the Signaling Zone where Surrogate Registration enabled for Sip Peer."
    ::= { sonusSipSignallingMIBNotificationsObjects 17 }

sonusSipArsStatEndpointIpAddressV6 OBJECT-TYPE
    SYNTAX          Ipv6Address
    ACCESS          read-only
    STATUS          mandatory
    DESCRIPTION     
            "Blacklisted endpoint's IP Address."
    ::= { sonusSipSignallingMIBNotificationsObjects 18 }

sonusSipSigPortIpAddressV6 OBJECT-TYPE
    SYNTAX          Ipv6Address
    ACCESS          read-only
    STATUS          mandatory
    DESCRIPTION     
            "IP Address of the Sip Signalling Port - mandatory parameter."
    ::= { sonusSipSignallingMIBNotificationsObjects 19 }

sonusPingPeerIpAddressV6 OBJECT-TYPE
    SYNTAX          Ipv6Address
    ACCESS          read-only
    STATUS          mandatory
    DESCRIPTION     
            "IP Address of the SIP Peer."
    ::= { sonusSipSignallingMIBNotificationsObjects 20 }

sonusSurrRegPeerIpAddressV6 OBJECT-TYPE
    SYNTAX          Ipv6Address
    ACCESS          read-only
    STATUS          mandatory
    DESCRIPTION     
            "IP Address of the SIP Peer."
    ::= { sonusSipSignallingMIBNotificationsObjects 21 }

sonusPingPeerFqdn OBJECT-TYPE
    SYNTAX          DisplayString
    ACCESS          read-only
    STATUS          mandatory
    DESCRIPTION     
            "The Fully Qualified Domain Name of the SIP Peer."
    ::= { sonusSipSignallingMIBNotificationsObjects 22 }

sonusSurrRegMethodName OBJECT-TYPE
    SYNTAX          DisplayString
    ACCESS          read-only
    STATUS          mandatory
    DESCRIPTION     
            "METHOD for which Surrogate Endpoint Authentication is failed."
    ::= { sonusSipSignallingMIBNotificationsObjects 23 }

sonusSurrRegPeerName OBJECT-TYPE
    SYNTAX          DisplayString
    ACCESS          read-only
    STATUS          mandatory
    DESCRIPTION     
            "Peer Name of Surrogate Endpoint for which Authentication is failed."
    ::= { sonusSipSignallingMIBNotificationsObjects 24 }

sonusSurrRegUserPart OBJECT-TYPE
    SYNTAX          DisplayString
    ACCESS          read-only
    STATUS          mandatory
    DESCRIPTION     
            "UserPart of Surrogate Endpoint for which Authentication is failed."
    ::= { sonusSipSignallingMIBNotificationsObjects 25 }

sonusCertReCheckSocketId OBJECT-TYPE
    SYNTAX          Gauge
    ACCESS          read-only
    STATUS          mandatory
    DESCRIPTION     
            "The socketId of the session failing certificate recheck."
    ::= { sonusSipSignallingMIBNotificationsObjects 26 }

sonusCertReCheckName OBJECT-TYPE
    SYNTAX          DisplayString (SIZE(1..101))
    ACCESS          read-only
    STATUS          mandatory
    DESCRIPTION     
            "The name of the certificate failing recheck."
    ::= { sonusSipSignallingMIBNotificationsObjects 27 }

sonusRecorderIpAddress OBJECT-TYPE
    SYNTAX          IpAddress
    ACCESS          read-only
    STATUS          mandatory
    DESCRIPTION     
            "IP Address of the Recording Server."
    ::= { sonusSipSignallingMIBNotificationsObjects 28 }

sonusRecorderIpAddressV6 OBJECT-TYPE
    SYNTAX          Ipv6Address
    ACCESS          read-only
    STATUS          mandatory
    DESCRIPTION     
            "IP V6 Address of the Recording Server."
    ::= { sonusSipSignallingMIBNotificationsObjects 29 }

sonusRecorderPortNum OBJECT-TYPE
    SYNTAX          INTEGER (1..65535)
    ACCESS          read-only
    STATUS          mandatory
    DESCRIPTION     
            "Port number of Recording Server."
    ::= { sonusSipSignallingMIBNotificationsObjects 30 }

sonusRecCallGCID OBJECT-TYPE
    SYNTAX          Gauge
    ACCESS          read-only
    STATUS          mandatory
    DESCRIPTION     
            "The GCID of the call being recorded."
    ::= { sonusSipSignallingMIBNotificationsObjects 31 }

sonusRecorderTrunkName OBJECT-TYPE
    SYNTAX          SonusNameReference
    ACCESS          read-only
    STATUS          mandatory
    DESCRIPTION     
            "Name of the trunk group where recorder is configured."
    ::= { sonusSipSignallingMIBNotificationsObjects 32 }

sonusRecordingCallLeg OBJECT-TYPE
    SYNTAX          SonusNameReference
    ACCESS          read-only
    STATUS          mandatory
    DESCRIPTION     
            "The call leg in communication session being recorded."
    ::= { sonusSipSignallingMIBNotificationsObjects 33 }

sonusNonRouteInviteRequestUri OBJECT-TYPE
    SYNTAX          DisplayString
    ACCESS          read-only
    STATUS          mandatory
    DESCRIPTION     
            "
             reqUri of the non-routed invite. 
             "
    ::= { sonusSipSignallingMIBNotificationsObjects 34 }

sonusNonRouteInviteSourceIpAddress OBJECT-TYPE
    SYNTAX          DisplayString
    ACCESS          read-only
    STATUS          mandatory
    DESCRIPTION     
            "
             Source Ip Address where the non-routed invite was originated from.
             "
    ::= { sonusSipSignallingMIBNotificationsObjects 35 }

sonusNonRouteInviteSourceIpPortNum OBJECT-TYPE
    SYNTAX          INTEGER (1..65535)
    ACCESS          read-only
    STATUS          mandatory
    DESCRIPTION     
            "
             Source port number of the invite where non-routed invite was originated from.
             "
    ::= { sonusSipSignallingMIBNotificationsObjects 36 }

sonusTgTrunkGroupName OBJECT-TYPE
    SYNTAX          DisplayString
    ACCESS          read-only
    STATUS          mandatory
    DESCRIPTION     
            "The trunk group name."
    ::= { sonusSipSignallingMIBNotificationsObjects 37 }

sonusDropSipMsgFromUnknowSrcAddress OBJECT-TYPE
    SYNTAX          DisplayString
    ACCESS          read-only
    STATUS          mandatory
    DESCRIPTION     
            "
             Unknown source Ip address where sip message is originated from.
             "
    ::= { sonusSipSignallingMIBNotificationsObjects 38 }

sonusDropSipMsgFromUnknowSrcMsgType OBJECT-TYPE
    SYNTAX          DisplayString
    ACCESS          read-only
    STATUS          mandatory
    DESCRIPTION     
            "
             SIP message type for which SIP message is being dropped.
             "
    ::= { sonusSipSignallingMIBNotificationsObjects 39 }

sonusSipIceGcid OBJECT-TYPE
    SYNTAX          Gauge
    ACCESS          read-only
    STATUS          mandatory
    DESCRIPTION     
            "
             The GCID of the call for which the STUN message is processed for.
             "
    ::= { sonusSipSignallingMIBNotificationsObjects 40 }

sonusSipIceRemoteIpAddress OBJECT-TYPE
    SYNTAX          IpAddress
    ACCESS          read-only
    STATUS          mandatory
    DESCRIPTION     
            "STUN Remote IP Address."
    ::= { sonusSipSignallingMIBNotificationsObjects 41 }

sonusSipIceRemotePort OBJECT-TYPE
    SYNTAX          INTEGER (1..65535)
    ACCESS          read-only
    STATUS          mandatory
    DESCRIPTION     
            "
             STUN Remote Port number.
             "
    ::= { sonusSipSignallingMIBNotificationsObjects 42 }

sonusSipIceLocalIpAddress OBJECT-TYPE
    SYNTAX          IpAddress
    ACCESS          read-only
    STATUS          mandatory
    DESCRIPTION     
            "
             STUN Local IP Address. 
             "
    ::= { sonusSipSignallingMIBNotificationsObjects 43 }

sonusSipIceLocalPort OBJECT-TYPE
    SYNTAX          INTEGER (1..65535)
    ACCESS          read-only
    STATUS          mandatory
    DESCRIPTION     
            "
             STUN Local Port number.
             "
    ::= { sonusSipSignallingMIBNotificationsObjects 44 }

sonusSipIceFailReason OBJECT-TYPE
    SYNTAX          DisplayString
    ACCESS          read-only
    STATUS          mandatory
    DESCRIPTION     
            "
             STUN message validation reason.
             "
    ::= { sonusSipSignallingMIBNotificationsObjects 45 }

sonusEmergencyMessageRejected OBJECT-TYPE
    SYNTAX          DisplayString
    ACCESS          read-only
    STATUS          mandatory
    DESCRIPTION     
            "
             Emergency Message Rejected.
             "
    ::= { sonusSipSignallingMIBNotificationsObjects 46 }

sonusRPHNamespace OBJECT-TYPE
    SYNTAX          DisplayString
    ACCESS          read-only
    STATUS          mandatory
    DESCRIPTION     
            "
             RPH namespace for which the emergency Message Rejected.
             "
    ::= { sonusSipSignallingMIBNotificationsObjects 47 }

sonusRPHPriority OBJECT-TYPE
    SYNTAX          DisplayString
    ACCESS          read-only
    STATUS          mandatory
    DESCRIPTION     
            "
             Rph priority value for which emergency Message Rejected.
             "
    ::= { sonusSipSignallingMIBNotificationsObjects 48 }

sonusPrefixedNumber OBJECT-TYPE
    SYNTAX          DisplayString
    ACCESS          read-only
    STATUS          mandatory
    DESCRIPTION     
            "
             Prefixed Number for which emergency Message Rejected.
             "
    ::= { sonusSipSignallingMIBNotificationsObjects 49 }

sonusSubscriptionId OBJECT-TYPE
    SYNTAX          Gauge
    ACCESS          read-only
    STATUS          mandatory
    DESCRIPTION     
            "The subscription id of current subscription."
    ::= { sonusSipSignallingMIBNotificationsObjects 50 }

sonusZoneIdName OBJECT-TYPE
    SYNTAX          DisplayString
    ACCESS          read-only
    STATUS          mandatory
    DESCRIPTION     
            "
             Zone Name for which emergency Message Rejected.
             "
    ::= { sonusSipSignallingMIBNotificationsObjects 51 }

sonusTrunkGroupName OBJECT-TYPE
    SYNTAX          DisplayString
    ACCESS          read-only
    STATUS          mandatory
    DESCRIPTION     
            "
             Tg Name for which emergency Message Rejected.
             "
    ::= { sonusSipSignallingMIBNotificationsObjects 52 }

sonusPolicerName OBJECT-TYPE
    SYNTAX          DisplayString
    ACCESS          read-only
    STATUS          mandatory
    DESCRIPTION     
            "
             Policer which rejects the emergency Message.
             "
    ::= { sonusSipSignallingMIBNotificationsObjects 53 }

sonusSipIceLocalIpV6Address OBJECT-TYPE
    SYNTAX          Ipv6Address
    ACCESS          read-only
    STATUS          mandatory
    DESCRIPTION     
            "
             STUN Local IP V6 Address. 
             "
    ::= { sonusSipSignallingMIBNotificationsObjects 54 }

sonusSipIceRemoteIpV6Address OBJECT-TYPE
    SYNTAX          Ipv6Address
    ACCESS          read-only
    STATUS          mandatory
    DESCRIPTION     
            "
             STUN Remote IP V6 Address. 
             "
    ::= { sonusSipSignallingMIBNotificationsObjects 55 }

sonusRecNumStreamsConfigured OBJECT-TYPE
    SYNTAX          Gauge
    ACCESS          read-only
    STATUS          mandatory
    DESCRIPTION     
            "Number of recording streams configured for this gcid"
    ::= { sonusSipSignallingMIBNotificationsObjects 56 }

sonusRecInitFailureReason OBJECT-TYPE
    SYNTAX          DisplayString
    ACCESS          read-only
    STATUS          mandatory
    DESCRIPTION     
            "Reason for failure to initiate SIPREC recording "
    ::= { sonusSipSignallingMIBNotificationsObjects 57 }

sonusMonIpAddress OBJECT-TYPE
    SYNTAX          IpAddress
    ACCESS          read-only
    STATUS          mandatory
    DESCRIPTION     
            "IP Address of the Monitoring Server."
    ::= { sonusSipSignallingMIBNotificationsObjects 58 }

sonusMonPortNum OBJECT-TYPE
    SYNTAX          INTEGER (1..65535)
    ACCESS          read-only
    STATUS          mandatory
    DESCRIPTION     
            "UDP/TCP port number of the Monitoring Server. "
    ::= { sonusSipSignallingMIBNotificationsObjects 59 }

sonusMonIpAddressV6 OBJECT-TYPE
    SYNTAX          Ipv6Address
    ACCESS          read-only
    STATUS          mandatory
    DESCRIPTION     
            "IP Address of the Monitoring Server."
    ::= { sonusSipSignallingMIBNotificationsObjects 60 }

sonusMsbcIpAddress OBJECT-TYPE
    SYNTAX          IpAddress
    ACCESS          read-only
    STATUS          mandatory
    DESCRIPTION     
            "IP Address of the MSBC."
    ::= { sonusSipSignallingMIBNotificationsObjects 61 }

sonusMsbcIpAddressV6 OBJECT-TYPE
    SYNTAX          Ipv6Address
    ACCESS          read-only
    STATUS          mandatory
    DESCRIPTION     
            "IP Address of the MSBC."
    ::= { sonusSipSignallingMIBNotificationsObjects 62 }

sonusSipArsStatSigZoneName OBJECT-TYPE
    SYNTAX          DisplayString (SIZE(1..63))
    ACCESS          read-only
    STATUS          mandatory
    DESCRIPTION     
            "The name of the ARS Zone"
    ::= { sonusSipSignallingMIBNotificationsObjects 63 }

sonusPingPeerZoneName OBJECT-TYPE
    SYNTAX          DisplayString (SIZE(1..63))
    ACCESS          read-only
    STATUS          mandatory
    DESCRIPTION     
            "The name of the Peer Zone"
    ::= { sonusSipSignallingMIBNotificationsObjects 64 }

sonusPingPeerName OBJECT-TYPE
    SYNTAX          DisplayString (SIZE(1..63))
    ACCESS          read-only
    STATUS          mandatory
    DESCRIPTION     
            "The name of the Peer"
    ::= { sonusSipSignallingMIBNotificationsObjects 65 }

sonusH323SignallingMIBNotifications OBJECT IDENTIFIER
    ::= { sonusSbxTraps 2 }

sonusH323SignallingMIBNotificationsPrefix OBJECT IDENTIFIER
    ::= { sonusH323SignallingMIBNotifications 0 }

sonusH323SignallingMIBNotificationsObjects OBJECT IDENTIFIER
    ::= { sonusH323SignallingMIBNotifications 1 }

sonusH323TrunkGrpName OBJECT-TYPE
    SYNTAX          SonusNameReference
    ACCESS          read-only
    STATUS          mandatory
    DESCRIPTION     
            "Name of the H323 trunk group."
    ::= { sonusH323SignallingMIBNotificationsObjects 1 }

sonusSoftswitchClientServicesMIBNotifications OBJECT IDENTIFIER
    ::= { sonusSbxTraps 3 }

sonusSoftswitchClientServicesMIBNotificationsPrefix OBJECT IDENTIFIER
    ::= { sonusSoftswitchClientServicesMIBNotifications 0 }

sonusSoftswitchClientServicesMIBNotificationsObjects OBJECT IDENTIFIER
    ::= { sonusSoftswitchClientServicesMIBNotifications 1 }

sonusPscsPolicyServerName OBJECT-TYPE
    SYNTAX          SonusName
    ACCESS          read-only
    STATUS          mandatory
    DESCRIPTION     
            "The name of this Softswitch."
    ::= { sonusSoftswitchClientServicesMIBNotificationsObjects 1 }

sonusPscsTranErrorReason OBJECT-TYPE
    SYNTAX          INTEGER { noSoftswitchAvailable(1), 
                        transactionTimeout(2), invalidParameters(3), 
                        receiveError(4), transmitError(5), 
                        encodeApiError(6), decodeApiError(7), 
                        noMatchingReplyCbFound(8) }
    ACCESS          read-only
    STATUS          mandatory
    DESCRIPTION     
            "The reason why a transaction has failed."
    ::= { sonusSoftswitchClientServicesMIBNotificationsObjects 2 }

sonusPscsRejectIndReason OBJECT-TYPE
    SYNTAX          INTEGER { notRegistered(1), unknownGateway(2), 
                        errorAVPContent(3), errorMsgContent(4), 
                        maxClientAccount(5), miscRegFailure(6) }
    ACCESS          read-only
    STATUS          mandatory
    DESCRIPTION     
            "The reason why a reject ind received."
    ::= { sonusSoftswitchClientServicesMIBNotificationsObjects 3 }

sonusPscsCalledNumber OBJECT-TYPE
    SYNTAX          DisplayString
    ACCESS          read-only
    STATUS          mandatory
    DESCRIPTION     
            "Destination number."
    ::= { sonusSoftswitchClientServicesMIBNotificationsObjects 4 }

sonusPscsCallingNumber OBJECT-TYPE
    SYNTAX          DisplayString
    ACCESS          read-only
    STATUS          mandatory
    DESCRIPTION     
            "Originating number."
    ::= { sonusSoftswitchClientServicesMIBNotificationsObjects 5 }

sonusPscsCarrierCode OBJECT-TYPE
    SYNTAX          DisplayString
    ACCESS          read-only
    STATUS          mandatory
    DESCRIPTION     
            "Carrier code."
    ::= { sonusSoftswitchClientServicesMIBNotificationsObjects 6 }

sonusPscsRouteFailureReason OBJECT-TYPE
    SYNTAX          INTEGER { routeNotFound(1), noServiceConfigured(2), 
                        databaseError(3) }
    ACCESS          read-only
    STATUS          mandatory
    DESCRIPTION     
            "The reason why a route look up has failed."
    ::= { sonusSoftswitchClientServicesMIBNotificationsObjects 7 }

sonusPscsGapNumber OBJECT-TYPE
    SYNTAX          DisplayString
    ACCESS          read-only
    STATUS          mandatory
    DESCRIPTION     
            "Gap number. Valid only in the case of LNP number translation."
    ::= { sonusSoftswitchClientServicesMIBNotificationsObjects 8 }

sonusPscsOperState OBJECT-TYPE
    SYNTAX          INTEGER { active(1), standby(2), congested(3), 
                        down(4), dryingup(5), alternate(6), test(7) }
    ACCESS          read-only
    STATUS          mandatory
    DESCRIPTION     
            "Operational state of the Softswitch"
    ::= { sonusSoftswitchClientServicesMIBNotificationsObjects 9 }

sonusPscsOutOfServiceReason OBJECT-TYPE
    SYNTAX          INTEGER { configured(1), connectionLoss(2), 
                        noConnection(3), nodeNameChang(4), 
                        incompatibleVersion(5) }
    ACCESS          read-only
    STATUS          mandatory
    DESCRIPTION     
            "The reason why the softswitch is out of service"
    ::= { sonusSoftswitchClientServicesMIBNotificationsObjects 10 }

sonusPscsInServiceReason OBJECT-TYPE
    SYNTAX          INTEGER { configured(1), successfulReConnect(2), 
                        automatic(3) }
    ACCESS          read-only
    STATUS          mandatory
    DESCRIPTION     
            "The reason why a softswitch is in service"
    ::= { sonusSoftswitchClientServicesMIBNotificationsObjects 11 }

sonusNodeResourcesMIBNotifications OBJECT IDENTIFIER
    ::= { sonusSbxTraps 4 }

sonusNodeResourcesMIBNotificationsPrefix OBJECT IDENTIFIER
    ::= { sonusNodeResourcesMIBNotifications 0 }

sonusNodeResourcesMIBNotificationsObjects OBJECT IDENTIFIER
    ::= { sonusNodeResourcesMIBNotifications 1 }

sonusCallAdmissionChangeReason OBJECT-TYPE
    SYNTAX          DisplayString (SIZE(1..101))
    ACCESS          read-only
    STATUS          mandatory
    DESCRIPTION     
            "The reason why the call admission control state has changes."
    ::= { sonusNodeResourcesMIBNotificationsObjects 1 }

sonusFeatureName OBJECT-TYPE
    SYNTAX          DisplayString (SIZE(1..31))
    ACCESS          read-only
    STATUS          mandatory
    DESCRIPTION     
            "Name of the feature in the context."
    ::= { sonusNodeResourcesMIBNotificationsObjects 2 }

sonusFeatureState OBJECT-TYPE
    SYNTAX          SonusAdminState
    ACCESS          read-only
    STATUS          mandatory
    DESCRIPTION     
            "State of the feature in context"
    ::= { sonusNodeResourcesMIBNotificationsObjects 3 }

sonusCallTraceCalledNumber OBJECT-TYPE
    SYNTAX          DisplayString (SIZE(0..30))
    ACCESS          read-write
    STATUS          mandatory
    DESCRIPTION     
            "The called number being traced."
    ::= { sonusNodeResourcesMIBNotificationsObjects 4 }

sonusActiveCallOrigCalledNum OBJECT-TYPE
    SYNTAX          DisplayString (SIZE(0..30))
    ACCESS          read-only
    STATUS          mandatory
    DESCRIPTION     
            "If an address translation has been performed on the called party number, 
             this entry contains the original, untranslated number."
    ::= { sonusNodeResourcesMIBNotificationsObjects 5 }

sonusCallTraceCallingNumber OBJECT-TYPE
    SYNTAX          DisplayString (SIZE(0..30))
    ACCESS          read-only
    STATUS          mandatory
    DESCRIPTION     
            "The calling number being traced."
    ::= { sonusNodeResourcesMIBNotificationsObjects 6 }

sonusActiveCallIngressPstnTrunk OBJECT-TYPE
    SYNTAX          DisplayString (SIZE(0..23))
    ACCESS          read-only
    STATUS          mandatory
    DESCRIPTION     
            "For calls originating from the PSTN (circuit) side, specifies the trunk
             group name to which the Ingress Pstn Channel belongs."
    ::= { sonusNodeResourcesMIBNotificationsObjects 7 }

sonusNodeResourceIsupCircuit OBJECT-TYPE
    SYNTAX          INTEGER (0..16383)
    ACCESS          read-only
    STATUS          mandatory
    DESCRIPTION     
            "Base circuit identity code (CIC) for the circuit."
    ::= { sonusNodeResourcesMIBNotificationsObjects 8 }

sonusActiveCallCallingNum OBJECT-TYPE
    SYNTAX          DisplayString (SIZE(0..30))
    ACCESS          read-only
    STATUS          mandatory
    DESCRIPTION     
            "The E.164 number representing the Calling Party's telephone number."
    ::= { sonusNodeResourcesMIBNotificationsObjects 9 }

sonusActiveCallCalledNum OBJECT-TYPE
    SYNTAX          DisplayString (SIZE(0..30))
    ACCESS          read-only
    STATUS          mandatory
    DESCRIPTION     
            "The E.164 number representing the Called Party's telephone number."
    ::= { sonusNodeResourcesMIBNotificationsObjects 10 }

sonusNumCallFailureNoDspExceedThreshold OBJECT-TYPE
    SYNTAX          Gauge
    ACCESS          read-only
    STATUS          mandatory
    DESCRIPTION     
            "The number of times call failure due to lack of DSP resource exceeded threshold since last trap notification."
    ::= { sonusNodeResourcesMIBNotificationsObjects 11 }

sonusNumDspAvailabilityG729CrossThreshold OBJECT-TYPE
    SYNTAX          Gauge
    ACCESS          read-only
    STATUS          mandatory
    DESCRIPTION     
            "The number of times the availability of G729 DSP resource crossed threshold since last trap notification."
    ::= { sonusNodeResourcesMIBNotificationsObjects 12 }

sonusNumDspAvailabilityG726CrossThreshold OBJECT-TYPE
    SYNTAX          Gauge
    ACCESS          read-only
    STATUS          mandatory
    DESCRIPTION     
            "The number of times the availability of G726 DSP resource crossed threshold since last trap notification."
    ::= { sonusNodeResourcesMIBNotificationsObjects 13 }

sonusNumDspAvailabilityG711PacketCrossThreshold OBJECT-TYPE
    SYNTAX          Gauge
    ACCESS          read-only
    STATUS          mandatory
    DESCRIPTION     
            "The number of times the availability of G711 Packet DSP resource crossed threshold since last trap notification."
    ::= { sonusNodeResourcesMIBNotificationsObjects 14 }

sonusNrmaCallGcid OBJECT-TYPE
    SYNTAX          Gauge
    ACCESS          read-only
    STATUS          mandatory
    DESCRIPTION     
            "The GCID of the call for which trap notification is generated."
    ::= { sonusNodeResourcesMIBNotificationsObjects 15 }

sonusJSrcServerName OBJECT-TYPE
    SYNTAX          DisplayString (SIZE(1..255))
    ACCESS          read-only
    STATUS          mandatory
    DESCRIPTION     
            "The JSRC Server name for which the trap notification is generated."
    ::= { sonusNodeResourcesMIBNotificationsObjects 16 }

sonusOverloadLevel OBJECT-TYPE
    SYNTAX          INTEGER { noOverload(0), levelOne(1), levelTwo(2), 
                        levelThree(3) }
    ACCESS          read-only
    STATUS          mandatory
    DESCRIPTION     
            "The overload level."
    ::= { sonusNodeResourcesMIBNotificationsObjects 17 }

sonusCallTraceDisableReason OBJECT-TYPE
    SYNTAX          DisplayString (SIZE(0..100))
    ACCESS          read-write
    STATUS          mandatory
    DESCRIPTION     
            "The reason for callTrace to be disabled."
    ::= { sonusNodeResourcesMIBNotificationsObjects 18 }

sonusCallCount OBJECT-TYPE
    SYNTAX          Gauge
    ACCESS          read-only
    STATUS          mandatory
    DESCRIPTION     
            "The number of currently active calls on the system."
    ::= { sonusNodeResourcesMIBNotificationsObjects 19 }

sonusRegCount OBJECT-TYPE
    SYNTAX          Gauge
    ACCESS          read-only
    STATUS          mandatory
    DESCRIPTION     
            "The number of currently active registrations on the system."
    ::= { sonusNodeResourcesMIBNotificationsObjects 20 }

sonusRelayCount OBJECT-TYPE
    SYNTAX          Gauge
    ACCESS          read-only
    STATUS          mandatory
    DESCRIPTION     
            "The number of currently active relay control blocks on the system."
    ::= { sonusNodeResourcesMIBNotificationsObjects 21 }

sonusNrmaToneType OBJECT-TYPE
    SYNTAX          Gauge
    ACCESS          read-only
    STATUS          mandatory
    DESCRIPTION     
            "The toneType for announcementBasedTone play failed."
    ::= { sonusNodeResourcesMIBNotificationsObjects 22 }

sonusNrmaCodecType OBJECT-TYPE
    SYNTAX          Gauge
    ACCESS          read-only
    STATUS          mandatory
    DESCRIPTION     
            "The codecType for announcementBasedTone play failed."
    ::= { sonusNodeResourcesMIBNotificationsObjects 23 }

sonusNrmaCodecAttr OBJECT-TYPE
    SYNTAX          Gauge
    ACCESS          read-only
    STATUS          mandatory
    DESCRIPTION     
            "The codec attrib for announcementBasedTone play failed."
    ::= { sonusNodeResourcesMIBNotificationsObjects 24 }

sonusScmInstanceId OBJECT-TYPE
    SYNTAX          Gauge
    ACCESS          read-only
    STATUS          mandatory
    DESCRIPTION     
            "The SCM instance ID that performed decryption"
    ::= { sonusNodeResourcesMIBNotificationsObjects 25 }

sonusDecryptModuleId OBJECT-TYPE
    SYNTAX          Gauge
    ACCESS          read-only
    STATUS          mandatory
    DESCRIPTION     
            "The identity of an module that performed decryption"
    ::= { sonusNodeResourcesMIBNotificationsObjects 26 }

sonusMrfpRealmId OBJECT-TYPE
    SYNTAX          DisplayString
    ACCESS          read-only
    STATUS          mandatory
    DESCRIPTION     
            "The identity of an realm"
    ::= { sonusNodeResourcesMIBNotificationsObjects 27 }

sonusTrunkGroupResourcesMIBNotifications OBJECT IDENTIFIER
    ::= { sonusSbxTraps 5 }

sonusTrunkGroupResourcesMIBNotificationsPrefix OBJECT IDENTIFIER
    ::= { sonusTrunkGroupResourcesMIBNotifications 0 }

sonusTrunkGroupResourcesMIBNotificationsObjects OBJECT IDENTIFIER
    ::= { sonusTrunkGroupResourcesMIBNotifications 1 }

sonusTrunkOutOfServiceReason OBJECT-TYPE
    SYNTAX          INTEGER { configured(1), allResourcesBlocked(2) }
    ACCESS          read-only
    STATUS          mandatory
    DESCRIPTION     
            "The reason why the Trunk Group is out of service."
    ::= { sonusTrunkGroupResourcesMIBNotificationsObjects 1 }

sonusTrunkGroupTCObject OBJECT-TYPE
    SYNTAX          INTEGER { sonusTgTCInboundReserved(1), 
                        sonusTgTCCirResvState(2), 
                        sonusTgTCPriorityCallReserve(3), 
                        sonusTgTCIncomingCallReserve(4), 
                        sonusTgTCOutgoingCallReserve(5), 
                        sonusTgTCSilcState(6), 
                        sonusTgTCSilcMC1Percent(7), 
                        sonusTgTCSilcMC2Percent(8) }
    ACCESS          read-only
    STATUS          mandatory
    DESCRIPTION     
            "This object is a bit mask that indicates what traffic
             control object in the trunk group table has changed."
    ::= { sonusTrunkGroupResourcesMIBNotificationsObjects 2 }

sonusTrunkGroupManCon OBJECT-TYPE
    SYNTAX          OCTET STRING
--                       { skip(0), cant(1), canf(2), irr(3), sirr(4), 
--                         orr(5), sorr(6) }
    ACCESS          read-only
    STATUS          mandatory
    DESCRIPTION     
            "This object is a bit mask that indicates what 
             manual trunk group controls were active in the
             last 30 seconds."
    ::= { sonusTrunkGroupResourcesMIBNotificationsObjects 3 }

sonusTrunkGroupAutoCon OBJECT-TYPE
    SYNTAX          OCTET STRING
--                       { acc(0), str(1), silc(2), dre(3), pod(4), 
--                         gwAcc(5), callPolicing(6), regPolicing(7) }
    ACCESS          read-only
    STATUS          mandatory
    DESCRIPTION     
            "This object is a bit mask that indicates what 
             automatic trunk group controls were active in 
             the last 30 seconds."
    ::= { sonusTrunkGroupResourcesMIBNotificationsObjects 4 }

sonusHpcLimitCallAttemptsDenied OBJECT-TYPE
    SYNTAX          Gauge
    ACCESS          read-only
    STATUS          mandatory
    DESCRIPTION     
            "The number of HPC call attempts that have been denied because of 
             exceeding the HPC limit associated with the trap since the last 
             instance of the trap"
    ::= { sonusTrunkGroupResourcesMIBNotificationsObjects 5 }

sonusTgName OBJECT-TYPE
    SYNTAX          SonusName
    ACCESS          read-only
    STATUS          mandatory
    DESCRIPTION     
            "The name of the trunk group.  The trunk group name must be present when the
             instance is created.  A trunk group can be renamed by setting sonusTgName
             in an existing instance.  When sonusTgName is set in an existing instance,
             the prior value of this object is placed in sonusTgAlternateName.  The new
             name will placed in sonusIsupsgServiceGroupTG from sonusIsupsg.mib, 
             sonusIsdnsgServiceGroupTrunkGroup from sonusIsdnsg.mib, and 
             sonusCassgServiceGroupTG from sonusCassg.mib.  Both the name in sonusTgName and 
             sonusTgAlternateName will be accepted for routing requests.  No other
             trunk group table instance can use the name in sonusTgName or 
             sonusTgAlternateName."
    ::= { sonusTrunkGroupResourcesMIBNotificationsObjects 6 }

sonusTgAdditionalData OBJECT-TYPE
    SYNTAX          DisplayString (SIZE(1..63))
    ACCESS          read-write
    STATUS          deprecated
    DESCRIPTION     
            "Any additional data related to the trunk group. The data can be used to
             configure any meta data related to trunk group e.g. customer name.
             The Trunk Group related traps should carry this data so as to make the
                  traps more descriptive of the Trunk Group."
    ::= { sonusTrunkGroupResourcesMIBNotificationsObjects 7 }

sonusCurrentKpiValue OBJECT-TYPE
    SYNTAX          Gauge
    ACCESS          read-only
    STATUS          mandatory
    DESCRIPTION     
            "The current KPI value for the trunk group"
    ::= { sonusTrunkGroupResourcesMIBNotificationsObjects 8 }

sonusKpi OBJECT-TYPE
    SYNTAX          DisplayString (SIZE(1..63))
    ACCESS          read-write
    STATUS          mandatory
    DESCRIPTION     
            "The QOS KPI whose status is being reported."
    ::= { sonusTrunkGroupResourcesMIBNotificationsObjects 9 }

sonusAddressContextName OBJECT-TYPE
    SYNTAX          DisplayString (SIZE(1..63))
    ACCESS          read-write
    STATUS          mandatory
    DESCRIPTION     
            "The name of the address contest to which the TG belongs."
    ::= { sonusTrunkGroupResourcesMIBNotificationsObjects 10 }

sonusZoneName OBJECT-TYPE
    SYNTAX          DisplayString (SIZE(1..63))
    ACCESS          read-write
    STATUS          mandatory
    DESCRIPTION     
            "The name of the Zone to which the TG belongs."
    ::= { sonusTrunkGroupResourcesMIBNotificationsObjects 11 }

sonusCacLimitType OBJECT-TYPE
    SYNTAX          DisplayString (SIZE(1..63))
    ACCESS          read-write
    STATUS          mandatory
    DESCRIPTION     
            "Type of the cac limit which is exhausted."
    ::= { sonusTrunkGroupResourcesMIBNotificationsObjects 12 }

sonusTrunkGroupManCon3 OBJECT-TYPE
    SYNTAX          DisplayString (SIZE(1..63))
    ACCESS          read-only
    STATUS          mandatory
    DESCRIPTION     
            "This string is a concatenation of  
             manual trunk group controls that were active in the
             last 30 seconds."
    ::= { sonusTrunkGroupResourcesMIBNotificationsObjects 13 }

sonusTrunkGroupAutoCon3 OBJECT-TYPE
    SYNTAX          DisplayString (SIZE(1..63))
    ACCESS          read-only
    STATUS          mandatory
    DESCRIPTION     
            "This string is a concatenation of 
             automatic trunk group controls that were active in 
             the last 30 seconds."
    ::= { sonusTrunkGroupResourcesMIBNotificationsObjects 14 }

sonusAccountingMIBNotifications OBJECT IDENTIFIER
    ::= { sonusSbxTraps 6 }

sonusAccountingMIBNotificationsPrefix OBJECT IDENTIFIER
    ::= { sonusAccountingMIBNotifications 0 }

sonusAccountingMIBNotificationsObjects OBJECT IDENTIFIER
    ::= { sonusAccountingMIBNotifications 1 }

sonusAcctOutOfServiceReason OBJECT-TYPE
    SYNTAX          INTEGER { configChange(1), eventLoggingError(2) }
    ACCESS          read-only
    STATUS          mandatory
    DESCRIPTION     
            "The Reason for Call Accounting for the Node being
             Out-of-Service."
    ::= { sonusAccountingMIBNotificationsObjects 1 }

sonusAcctGcid OBJECT-TYPE
    SYNTAX          INTEGER
    ACCESS          read-only
    STATUS          mandatory
    DESCRIPTION     
            "GCID associated with the call which generated the trap.
             Corresponds to INTERMEDIATE accounting record, field 65."
    ::= { sonusAccountingMIBNotificationsObjects 2 }

sonusAcctOrigTrunkgroupType OBJECT-TYPE
    SYNTAX          INTEGER
    ACCESS          read-only
    STATUS          mandatory
    DESCRIPTION     
            "This value represents the originating trunk type as specified
             by customer. This field is associated with the corresponding
             field of trunk group screen on PSX.
             Corresponds to INTERMEDIATE accounting record, field 135."
    ::= { sonusAccountingMIBNotificationsObjects 3 }

sonusAcctIngressCep OBJECT-TYPE
    SYNTAX          DisplayString (SIZE(0..128))
    ACCESS          read-only
    STATUS          mandatory
    DESCRIPTION     
            "Ingress Circuit End Point.
             If ingress is PSTN, then CEP string contains the following:
             <Shelf>:<Slot>:<Port>:<Ds0>:<Cic>:<LPC>:<RPC>
             If ingress is IP, then CEP string containst the following:
             <Local IP Address>:<Port>/<Remote IP Address>:<Port>
             Corresponds to INTERMEDIATE accounting record, fields 32 & 33."
    ::= { sonusAccountingMIBNotificationsObjects 4 }

sonusAcctTermTrunkgroupType OBJECT-TYPE
    SYNTAX          INTEGER
    ACCESS          read-only
    STATUS          mandatory
    DESCRIPTION     
            "This value represents the terminating trunk type as specified
             by customer. This field is associated with the corresponding
             field of trunk group screen on PSX.
             Corresponds to INTERMEDIATE accounting record, field 136."
    ::= { sonusAccountingMIBNotificationsObjects 5 }

sonusAcctEgressCep OBJECT-TYPE
    SYNTAX          DisplayString (SIZE(0..128))
    ACCESS          read-only
    STATUS          mandatory
    DESCRIPTION     
            "Egress Circuit End Point.
             If egress is PSTN, then CEP string contains the following:
             <Shelf>:<Slot>:<Port>:<Ds0>:<Cic>:<LPC>:<RPC>
             If egress is IP, then CEP string containst the following:
             <Local IP Address>:<Port>/<Remote IP Address>:<Port>
              Corresponds to INTERMEDIATE accounting record, fields 34 & 35."
    ::= { sonusAccountingMIBNotificationsObjects 6 }

sonusAcctCallingPartyNumber OBJECT-TYPE
    SYNTAX          DisplayString (SIZE(0..31))
    ACCESS          read-only
    STATUS          mandatory
    DESCRIPTION     
            "Calling Party Number associated with the call which generated the trap.
             Corresponds to INTERMEDIATE accounting record, field 17."
    ::= { sonusAccountingMIBNotificationsObjects 7 }

sonusAcctCalledPartyNumber OBJECT-TYPE
    SYNTAX          DisplayString (SIZE(0..31))
    ACCESS          read-only
    STATUS          mandatory
    DESCRIPTION     
            "Called Party Number associated with the call which generated the trap.
             Corresponds to INTERMEDIATE accounting record, field 18."
    ::= { sonusAccountingMIBNotificationsObjects 8 }

sonusSelCdrReqRspTimeout OBJECT-TYPE
    SYNTAX          Gauge
    ACCESS          read-only
    STATUS          mandatory
    DESCRIPTION     
            ""
    ::= { sonusAccountingMIBNotificationsObjects 9 }

sonusAcctGenerationMode OBJECT-TYPE
    SYNTAX          INTEGER { origination(1), destination(2), 
                        allcalls(3), none(4) }
    ACCESS          read-only
    STATUS          mandatory
    DESCRIPTION     
            "This configures the accounting generation mode for the node"
    ::= { sonusAccountingMIBNotificationsObjects 10 }

sonusAcctLogDestination OBJECT-TYPE
    SYNTAX          INTEGER { nfs(1), streaming(2) }
    ACCESS          read-only
    STATUS          mandatory
    DESCRIPTION     
            "The accounting log destination "
    ::= { sonusAccountingMIBNotificationsObjects 11 }

sonusAcctIntAcctState OBJECT-TYPE
    SYNTAX          SonusAdminState
    ACCESS          read-only
    STATUS          mandatory
    DESCRIPTION     
            "This administrative Intermediate Accounting state"
    ::= { sonusAccountingMIBNotificationsObjects 12 }

sonusAcctIntAcctInterval OBJECT-TYPE
    SYNTAX          INTEGER (5..86400)
    ACCESS          read-only
    STATUS          mandatory
    DESCRIPTION     
            "The Intermediate Accounting Interval in seconds"
    ::= { sonusAccountingMIBNotificationsObjects 13 }

sonusSelCdrSequenceNumber OBJECT-TYPE
    SYNTAX          Counter
    ACCESS          read-only
    STATUS          mandatory
    DESCRIPTION     
            "The sequence number of the GSX selectable CDR configuration of GSX-  
             DSI CDR streaming."
    ::= { sonusAccountingMIBNotificationsObjects 14 }

sonusSelCdrUpdateStatus OBJECT-TYPE
    SYNTAX          INTEGER { success(0), subsetStart(1), subsetStop(2), 
                        subsetStartStop(3), subsetAttempt(4), 
                        subsetStartAttempt(5), subsetStopAttempt(6), 
                        subsetStartStopAttempt(7), subsetIntermediate(8), 
                        subsetStartIntermediate(9), 
                        subsetStopIntermediate(10), 
                        subsetStartStopInter(11), subsetAttemptInter(12), 
                        subsetStartAttemptInter(13), 
                        subsetStopAttemptInter(14), 
                        subsetStartStopAtmpIntr(15) }
    ACCESS          read-only
    STATUS          mandatory
    DESCRIPTION     
            "This field contains the update status of the selectable CDR configuration.
             
             Value 0 indicates GSX accepts all selectable CDR configurations 
             provisioned by DSI.
             
             Value 1 indicates GSX partially accepted the selectable CDR configuration 
             of START record type, and fully accepted all other configuration updates 
             on STOP, ATTEMPT and INTERMEDIATE record types.
             
             Value 2 indicates GSX partially accepted the selectable CDR configuration 
             on STOP record type, and fully accepted all other configuration updates 
             on START, ATTEMPT and INTERMEDIATE record types.
             
             Value 3 indicates GSX partially accepted the selectable CDR configuration 
             on START and STOP record types, and fully accepted all other configuration
             update on ATTEMPT and INTERMEDIATE record types.
             .. etc. "
    ::= { sonusAccountingMIBNotificationsObjects 15 }

sonusAcctIntAcctMode OBJECT-TYPE
    SYNTAX          INTEGER { interval(1), telcordia(2) }
    ACCESS          read-only
    STATUS          mandatory
    DESCRIPTION     
            "This configures the intermediate record generation mode for
             the node.
             
             In INTERVAL(1) mode, intermediate records are generated
             a periodic intervals following call establishment.  This
             interval is defined by sonusAcctIntAcctInterval.
             
             In TELCORDIA(2) mode, intermediate records are geneated once
             per day for calls whose duration exceeds 24 hours.  The 
             scheduled generated time is defined by
             sonusAcctTelcoridaGenTime."
    ::= { sonusAccountingMIBNotificationsObjects 16 }

sonusAcctIntLongDurGenTime OBJECT-TYPE
    SYNTAX          SonusGMTTime
    ACCESS          read-only
    STATUS          mandatory
    DESCRIPTION     
            "Octet string that identifies the GMT time to generate Telcordia
             Long Duration accounting records.  At the scheduled time an
             intermediate accounting record will be generated for all calls
             whose duration exceeds 24 hours.  Duration is measured from
             Service Established time to the current time.
             
                octet  contents      range
                -----  --------      -----
                  1    hour          0..23
                  2    minute        0..59
                  3    seconds       0..60
                  4    deci-seconds  0..9
             
             For example, 23:59:59.9 GMT is represented as 0x173B3B09.
             
             Note: this object is only applicable when sonusAcctIntAcctMode
                   is set to telcordia(2)."
    ::= { sonusAccountingMIBNotificationsObjects 17 }

sonusCommonCallProcessMIBNotifications OBJECT IDENTIFIER
    ::= { sonusSbxTraps 7 }

sonusCommonCallProcessMIBNotificationsPrefix OBJECT IDENTIFIER
    ::= { sonusCommonCallProcessMIBNotifications 0 }

sonusCommonCallProcessMIBNotificationsObjects OBJECT IDENTIFIER
    ::= { sonusCommonCallProcessMIBNotifications 1 }

sonusIngressTgName OBJECT-TYPE
    SYNTAX          DisplayString (SIZE(0..23))
    ACCESS          read-only
    STATUS          mandatory
    DESCRIPTION     
            "Name of the ingress trunk group."
    ::= { sonusCommonCallProcessMIBNotificationsObjects 1 }

sonusIngressCep OBJECT-TYPE
    SYNTAX          DisplayString (SIZE(0..128))
    ACCESS          read-only
    STATUS          mandatory
    DESCRIPTION     
            "Ingress circuit end point information, this could be PSTN or IP formatted."
    ::= { sonusCommonCallProcessMIBNotificationsObjects 2 }

sonusEgressTgName OBJECT-TYPE
    SYNTAX          DisplayString (SIZE(0..23))
    ACCESS          read-only
    STATUS          mandatory
    DESCRIPTION     
            "Name of the egress trunk group."
    ::= { sonusCommonCallProcessMIBNotificationsObjects 3 }

sonusEgressCep OBJECT-TYPE
    SYNTAX          DisplayString (SIZE(0..128))
    ACCESS          read-only
    STATUS          mandatory
    DESCRIPTION     
            "Egress circuit end point information, this could be PSTN or IP formatted."
    ::= { sonusCommonCallProcessMIBNotificationsObjects 4 }

sonusCalledNumber OBJECT-TYPE
    SYNTAX          DisplayString (SIZE(0..30))
    ACCESS          read-only
    STATUS          mandatory
    DESCRIPTION     
            "Called Party Number."
    ::= { sonusCommonCallProcessMIBNotificationsObjects 5 }

sonusCallingNumber OBJECT-TYPE
    SYNTAX          DisplayString (SIZE(0..30))
    ACCESS          read-only
    STATUS          mandatory
    DESCRIPTION     
            "Calling Party Number."
    ::= { sonusCommonCallProcessMIBNotificationsObjects 6 }

sonusLdcStatus OBJECT-TYPE
    SYNTAX          DisplayString (SIZE(0..13))
    ACCESS          read-only
    STATUS          mandatory
    DESCRIPTION     
            "Is the LDC call to be disconnected or remain active."
    ::= { sonusCommonCallProcessMIBNotificationsObjects 7 }

sonusCep OBJECT-TYPE
    SYNTAX          DisplayString (SIZE(0..96))
    ACCESS          read-only
    STATUS          mandatory
    DESCRIPTION     
            "Circuit end point information, this could be PSTN or IP formatted."
    ::= { sonusCommonCallProcessMIBNotificationsObjects 8 }

sonusStaticCallGcid OBJECT-TYPE
    SYNTAX          INTEGER
    ACCESS          read-write
    STATUS          mandatory
    DESCRIPTION     
            "The call identifier for a call to be deleted"
    ::= { sonusCommonCallProcessMIBNotificationsObjects 9 }

sonusCommonMIBNotifications OBJECT IDENTIFIER
    ::= { sonusSbxTraps 8 }

sonusCommonMIBNotificationsPrefix OBJECT IDENTIFIER
    ::= { sonusCommonMIBNotifications 0 }

sonusCommonMIBNotificationsObjects OBJECT IDENTIFIER
    ::= { sonusCommonMIBNotifications 1 }

sonusNetMgmtClientName OBJECT-TYPE
    SYNTAX          SonusName
    ACCESS          read-only
    STATUS          mandatory
    DESCRIPTION     
            "The name of this administrative management client."
    ::= { sonusCommonMIBNotificationsObjects 1 }

sonusNetMgmtInformReqDiscards OBJECT-TYPE
    SYNTAX          INTEGER (0..100)
    ACCESS          read-only
    STATUS          mandatory
    DESCRIPTION     
            "The number of InformRequest PDUs that were discarded
             for a Management Client."
    ::= { sonusCommonMIBNotificationsObjects 2 }

sonusIpmMIBNotifications OBJECT IDENTIFIER
    ::= { sonusSbxTraps 9 }

sonusIpmMIBNotificationsPrefix OBJECT IDENTIFIER
    ::= { sonusIpmMIBNotifications 0 }

sonusIpmMIBNotificationsObjects OBJECT IDENTIFIER
    ::= { sonusIpmMIBNotifications 1 }

sonusPolicerTypeStr OBJECT-TYPE
    SYNTAX          DisplayString (SIZE(1..32))
    ACCESS          read-only
    STATUS          mandatory
    DESCRIPTION     
            "The policer type whose alarm state has changed."
    ::= { sonusIpmMIBNotificationsObjects 1 }

sonusPolicerLevelStr OBJECT-TYPE
    SYNTAX          DisplayString (SIZE(1..12))
    ACCESS          read-only
    STATUS          mandatory
    DESCRIPTION     
            "The previous policer alarm level reported when the alarm 
             state has changed."
    ::= { sonusIpmMIBNotificationsObjects 2 }

sonusDBLAddressContextName OBJECT-TYPE
    SYNTAX          DisplayString (SIZE(1..32))
    ACCESS          read-only
    STATUS          mandatory
    DESCRIPTION     
            "AddressContext name."
    ::= { sonusIpmMIBNotificationsObjects 3 }

sonusDBLEndPointInfo OBJECT-TYPE
    SYNTAX          DisplayString (SIZE(1..63))
    ACCESS          read-only
    STATUS          mandatory
    DESCRIPTION     
            "Endpoint information"
    ::= { sonusIpmMIBNotificationsObjects 4 }

sonusDBLAction OBJECT-TYPE
    SYNTAX          DisplayString (SIZE(1..32))
    ACCESS          read-only
    STATUS          mandatory
    DESCRIPTION     
            "Action type"
    ::= { sonusIpmMIBNotificationsObjects 5 }

sonusDBLDuration OBJECT-TYPE
    SYNTAX          Gauge
    ACCESS          read-only
    STATUS          mandatory
    DESCRIPTION     
            "Endpoint action duration"
    ::= { sonusIpmMIBNotificationsObjects 6 }

sonusDBLCriteria OBJECT-TYPE
    SYNTAX          DisplayString (SIZE(1..255))
    ACCESS          read-only
    STATUS          mandatory
    DESCRIPTION     
            "Criteria information"
    ::= { sonusIpmMIBNotificationsObjects 7 }

sonusDBLProfileRuleInfo OBJECT-TYPE
    SYNTAX          DisplayString (SIZE(1..63))
    ACCESS          read-only
    STATUS          mandatory
    DESCRIPTION     
            "Profile and rule information"
    ::= { sonusIpmMIBNotificationsObjects 8 }

sonusDBLEventName OBJECT-TYPE
    SYNTAX          DisplayString (SIZE(1..63))
    ACCESS          read-only
    STATUS          mandatory
    DESCRIPTION     
            "DBL Event Name"
    ::= { sonusIpmMIBNotificationsObjects 9 }

sonusSbxNotifications OBJECT IDENTIFIER
    ::= { sonusSbxTraps 10 }

sonusSbxNotificationPrefix OBJECT IDENTIFIER
    ::= { sonusSbxNotifications 2 }

sonusSbxNotificationObjects OBJECT IDENTIFIER
    ::= { sonusSbxNotifications 3 }

sonusNrsMIBNotifications OBJECT IDENTIFIER
    ::= { sonusSbxTraps 11 }

sonusNrsMIBNotificationsPrefix OBJECT IDENTIFIER
    ::= { sonusNrsMIBNotifications 0 }

sonusNrsMIBNotificationsObjects OBJECT IDENTIFIER
    ::= { sonusNrsMIBNotifications 1 }

sonusNrsAddressContextName OBJECT-TYPE
    SYNTAX          DisplayString (SIZE(1..24))
    ACCESS          read-only
    STATUS          mandatory
    DESCRIPTION     
            "The name of the address context."
    ::= { sonusNrsMIBNotificationsObjects 1 }

sonusNrsIpInterfaceGroupName OBJECT-TYPE
    SYNTAX          DisplayString (SIZE(1..24))
    ACCESS          read-only
    STATUS          mandatory
    DESCRIPTION     
            "The name of the IP interface group."
    ::= { sonusNrsMIBNotificationsObjects 2 }

sonusNrsIpInterfaceName OBJECT-TYPE
    SYNTAX          DisplayString (SIZE(1..24))
    ACCESS          read-only
    STATUS          mandatory
    DESCRIPTION     
            "The name of the IP interface."
    ::= { sonusNrsMIBNotificationsObjects 3 }

sonusNrsPortName OBJECT-TYPE
    SYNTAX          DisplayString (SIZE(1..24))
    ACCESS          read-only
    STATUS          mandatory
    DESCRIPTION     
            "The name of the port."
    ::= { sonusNrsMIBNotificationsObjects 4 }

sonusNrsCeName OBJECT-TYPE
    SYNTAX          DisplayString (SIZE(1..255))
    ACCESS          read-only
    STATUS          mandatory
    DESCRIPTION     
            "The name of the compute element."
    ::= { sonusNrsMIBNotificationsObjects 5 }

sonusNrsIpAddress OBJECT-TYPE
    SYNTAX          IpAddress
    ACCESS          read-only
    STATUS          mandatory
    DESCRIPTION     
            "
             IP Address. 
             "
    ::= { sonusNrsMIBNotificationsObjects 6 }

sonusNrsIpAddressV6 OBJECT-TYPE
    SYNTAX          Ipv6Address
    ACCESS          read-only
    STATUS          mandatory
    DESCRIPTION     
            "IP Address."
    ::= { sonusNrsMIBNotificationsObjects 7 }

sonusNrsInvalidSfpReason OBJECT-TYPE
    SYNTAX          DisplayString
    ACCESS          read-only
    STATUS          mandatory
    DESCRIPTION     
            "
             Reason SFP is invalid. 
             "
    ::= { sonusNrsMIBNotificationsObjects 8 }

sonusNifPort OBJECT-TYPE
    SYNTAX          INTEGER (1..65535)
    ACCESS          read-only
    STATUS          mandatory
    DESCRIPTION     
            "
             The port ID. 
             "
    ::= { sonusNrsMIBNotificationsObjects 9 }

sonusNifIndex OBJECT-TYPE
    SYNTAX          INTEGER (1..65535)
    ACCESS          read-only
    STATUS          mandatory
    DESCRIPTION     
            "
             The ifIndex of the interface. 
             "
    ::= { sonusNrsMIBNotificationsObjects 10 }

sonusBgfMIBNotifications OBJECT IDENTIFIER
    ::= { sonusSbxTraps 12 }

sonusBgfMIBNotificationsPrefix OBJECT IDENTIFIER
    ::= { sonusBgfMIBNotifications 0 }

sonusBgfMIBNotificationsObjects OBJECT IDENTIFIER
    ::= { sonusBgfMIBNotifications 1 }

sonusH248SigRemoteIpAddr OBJECT-TYPE
    SYNTAX          DisplayString
    ACCESS          read-only
    STATUS          mandatory
    DESCRIPTION     
            "IP address of the SPDF."
    ::= { sonusBgfMIBNotificationsObjects 1 }

sonusH248SigLocalIpAddr OBJECT-TYPE
    SYNTAX          DisplayString
    ACCESS          read-only
    STATUS          mandatory
    DESCRIPTION     
            "IP address of the VBGF."
    ::= { sonusBgfMIBNotificationsObjects 2 }

sonusH248SigScMethod OBJECT-TYPE
    SYNTAX          DisplayString
    ACCESS          read-only
    STATUS          mandatory
    DESCRIPTION     
            "Service Change method."
    ::= { sonusBgfMIBNotificationsObjects 3 }

sonusH248SigMid OBJECT-TYPE
    SYNTAX          DisplayString
    ACCESS          read-only
    STATUS          mandatory
    DESCRIPTION     
            "MID of SPDF."
    ::= { sonusBgfMIBNotificationsObjects 4 }

sonusH248SigStatus OBJECT-TYPE
    SYNTAX          DisplayString
    ACCESS          read-only
    STATUS          mandatory
    DESCRIPTION     
            "Service change disconnected transmission status."
    ::= { sonusBgfMIBNotificationsObjects 5 }

sonusH248SpdfName OBJECT-TYPE
    SYNTAX          DisplayString
    ACCESS          read-only
    STATUS          mandatory
    DESCRIPTION     
            "SPDF Name."
    ::= { sonusBgfMIBNotificationsObjects 6 }

sonusH248FeatureName OBJECT-TYPE
    SYNTAX          DisplayString
    ACCESS          read-only
    STATUS          deprecated
    DESCRIPTION     
            " Feature Name."
    ::= { sonusBgfMIBNotificationsObjects 7 }

sonusH248Version OBJECT-TYPE
    SYNTAX          INTEGER (1..3)
    ACCESS          read-only
    STATUS          deprecated
    DESCRIPTION     
            " H248 Version Number"
    ::= { sonusBgfMIBNotificationsObjects 8 }

sonusH248SigPortIpAddress OBJECT-TYPE
    SYNTAX          IpAddress
    ACCESS          read-only
    STATUS          mandatory
    DESCRIPTION     
            "
             IP Address of the H248 Signalling Port - mandatory parameter. 
             "
    ::= { sonusBgfMIBNotificationsObjects 9 }

sonusH248SigPortNum OBJECT-TYPE
    SYNTAX          INTEGER (1..65535)
    ACCESS          read-only
    STATUS          mandatory
    DESCRIPTION     
            "
             UDP/TCP port number of H248 Signalling Port (default is 2944).
             "
    ::= { sonusBgfMIBNotificationsObjects 10 }

sonusH248SigProto OBJECT-TYPE
    SYNTAX          DisplayString
    ACCESS          read-only
    STATUS          mandatory
    DESCRIPTION     
            " The signaling transport protocol."
    ::= { sonusBgfMIBNotificationsObjects 11 }

sonusGatewaySignallingMIBNotifications OBJECT IDENTIFIER
    ::= { sonusSbxTraps 13 }

sonusGatewaySignallingMIBNotificationsPrefix OBJECT IDENTIFIER
    ::= { sonusGatewaySignallingMIBNotifications 0 }

sonusGatewaySignallingMIBNotificationsObjects OBJECT IDENTIFIER
    ::= { sonusGatewaySignallingMIBNotifications 1 }

sonusGwRemoteGwName OBJECT-TYPE
    SYNTAX          DisplayString (SIZE(0..23))
    ACCESS          read-only
    STATUS          deprecated
    DESCRIPTION     
            "Name of the remote Gateway."
    ::= { sonusGatewaySignallingMIBNotificationsObjects 1 }

sonusGwCloseReasonCode OBJECT-TYPE
    SYNTAX          INTEGER { administratorInitiatedClose(1), 
                        closeRequestReceivedFromRemote(2), 
                        remoteNotResponding(3), internalError(4), 
                        configError(5), recvCallSigReqFromUnknownGw(6), 
                        socketErrNetworkDown(7), 
                        socketErrNetworkUnreachable(8), 
                        socketErrNetworkReset(9), 
                        socketErrSoftwareConnectionAbort(10), 
                        socketErrConnectionResetByPeer(11), 
                        socketErrNoBufferSpaceAvail(12), 
                        socketErrAlreadyConnected(13), 
                        socketErrNotConnected(14), 
                        socketErrCantSendAfterShutdown(15), 
                        socketErrTooManyReferences(16), 
                        socketErrConnectionTimedOut(17), 
                        socketErrUnknown(18), 
                        recvDuplicateLinkOpenReq(19), 
                        socketErrExceptionEvent(20), 
                        linkXmtCongestion(21), 
                        openNackReceivedFromRemote(22), idleTimeout(23) }
    ACCESS          read-only
    STATUS          mandatory
    DESCRIPTION     
            "Reason for close of Call Signaling Link."
    ::= { sonusGatewaySignallingMIBNotificationsObjects 2 }

sonusGwRemoteGwAddr OBJECT-TYPE
    SYNTAX          IpAddress
    ACCESS          read-only
    STATUS          mandatory
    DESCRIPTION     
            "Ip Address of the remote Gateway."
    ::= { sonusGatewaySignallingMIBNotificationsObjects 3 }

sonusGwSigTgName OBJECT-TYPE
    SYNTAX          SonusNameReference
    ACCESS          read-only
    STATUS          mandatory
    DESCRIPTION     
            "Name of the Gateway trunk group."
    ::= { sonusGatewaySignallingMIBNotificationsObjects 4 }

sonusGwRemoteGw6Addr OBJECT-TYPE
    SYNTAX          Ipv6Address
    ACCESS          read-only
    STATUS          mandatory
    DESCRIPTION     
            "Ipv6 Address of the remote Gateway."
    ::= { sonusGatewaySignallingMIBNotificationsObjects 5 }

sonusOrcaLicenseMIBNotifications OBJECT IDENTIFIER
    ::= { sonusSbxTraps 14 }

sonusOrcaLicenseMIBNotificationsPrefix OBJECT IDENTIFIER
    ::= { sonusOrcaLicenseMIBNotifications 0 }

sonusOrcaLicenseMIBNotificationsObjects OBJECT IDENTIFIER
    ::= { sonusOrcaLicenseMIBNotifications 1 }

sonusSessLicenseLimit OBJECT-TYPE
    SYNTAX          Gauge
    ACCESS          read-only
    STATUS          mandatory
    DESCRIPTION     
            "Licensed session limit"
    ::= { sonusOrcaLicenseMIBNotificationsObjects 1 }

sonusConcurrentCalls OBJECT-TYPE
    SYNTAX          Gauge
    ACCESS          read-only
    STATUS          mandatory
    DESCRIPTION     
            "Concurrent calls"
    ::= { sonusOrcaLicenseMIBNotificationsObjects 2 }

sonusSessionsThreshold OBJECT-TYPE
    SYNTAX          Gauge
    ACCESS          read-only
    STATUS          mandatory
    DESCRIPTION     
            "Sessions threshold"
    ::= { sonusOrcaLicenseMIBNotificationsObjects 3 }

sonusAlarmName OBJECT-TYPE
    SYNTAX          DisplayString
    ACCESS          read-only
    STATUS          mandatory
    DESCRIPTION     
            "License Name."
    ::= { sonusOrcaLicenseMIBNotificationsObjects 4 }

sonusAlarmReason OBJECT-TYPE
    SYNTAX          DisplayString
    ACCESS          read-only
    STATUS          mandatory
    DESCRIPTION     
            "call admission is suspended."
    ::= { sonusOrcaLicenseMIBNotificationsObjects 5 }

sonusActiveSessionCount OBJECT-TYPE
    SYNTAX          Gauge
    ACCESS          read-only
    STATUS          mandatory
    DESCRIPTION     
            "Active Sessions count "
    ::= { sonusOrcaLicenseMIBNotificationsObjects 6 }

sonusDatabaseMIBNotifications OBJECT IDENTIFIER
    ::= { sonusSbxTraps 15 }

sonusDatabaseMIBNotificationsPrefix OBJECT IDENTIFIER
    ::= { sonusDatabaseMIBNotifications 0 }

sonusDatabaseMIBNotificationsObjects OBJECT IDENTIFIER
    ::= { sonusDatabaseMIBNotifications 1 }

sonusSbxSystemName OBJECT-TYPE
    SYNTAX          DisplayString
    ACCESS          read-only
    STATUS          mandatory
    DESCRIPTION     
            "
             Name of the system
             "
    ::= { sonusDatabaseMIBNotificationsObjects 1 }

sonusSbxServerName OBJECT-TYPE
    SYNTAX          DisplayString
    ACCESS          read-only
    STATUS          mandatory
    DESCRIPTION     
            "
             Name of the server
             "
    ::= { sonusDatabaseMIBNotificationsObjects 2 }

sonusSbxPeerServerName OBJECT-TYPE
    SYNTAX          DisplayString
    ACCESS          read-only
    STATUS          mandatory
    DESCRIPTION     
            "
             Name of the peer server
             "
    ::= { sonusDatabaseMIBNotificationsObjects 3 }

sonusSbxRedundencyRole OBJECT-TYPE
    SYNTAX          DisplayString
    ACCESS          read-only
    STATUS          mandatory
    DESCRIPTION     
            "
             Redundency role of the server.
             "
    ::= { sonusDatabaseMIBNotificationsObjects 4 }

sonusResourceMIBNotifications OBJECT IDENTIFIER
    ::= { sonusSbxTraps 16 }

sonusResourceMIBNotificationsPrefix OBJECT IDENTIFIER
    ::= { sonusResourceMIBNotifications 0 }

sonusResourceMIBNotificationsObjects OBJECT IDENTIFIER
    ::= { sonusResourceMIBNotifications 1 }

sonusResource OBJECT-TYPE
    SYNTAX          DisplayString
    ACCESS          read-only
    STATUS          mandatory
    DESCRIPTION     
            "
             Concurrent calls or bandwidth.
             "
    ::= { sonusResourceMIBNotificationsObjects 1 }

sonusEntityType OBJECT-TYPE
    SYNTAX          DisplayString
    ACCESS          read-only
    STATUS          mandatory
    DESCRIPTION     
            "
             Zone, TrunkGroup, IPPeer.
             "
    ::= { sonusResourceMIBNotificationsObjects 2 }

sonusEntityName OBJECT-TYPE
    SYNTAX          DisplayString
    ACCESS          read-only
    STATUS          mandatory
    DESCRIPTION     
            "
             Zone, TrunkGroup, IPPeer name.
             "
    ::= { sonusResourceMIBNotificationsObjects 3 }

sonusSharedCacLimitPoolProfileId OBJECT-TYPE
    SYNTAX          DisplayString
    ACCESS          read-only
    STATUS          mandatory
    DESCRIPTION     
            "
             Concurrent calls or bandwidthShared Cac Limit Pool Profile Id.
             "
    ::= { sonusResourceMIBNotificationsObjects 4 }

sonusResourceUsage OBJECT-TYPE
    SYNTAX          Gauge
    ACCESS          read-only
    STATUS          mandatory
    DESCRIPTION     
            "
             Resource Usage.
             "
    ::= { sonusResourceMIBNotificationsObjects 5 }

sonusResourceLimit OBJECT-TYPE
    SYNTAX          Gauge
    ACCESS          read-only
    STATUS          mandatory
    DESCRIPTION     
            "
             Resource Limit.
             "
    ::= { sonusResourceMIBNotificationsObjects 6 }

sonusResourceThreshold OBJECT-TYPE
    SYNTAX          Gauge
    ACCESS          read-only
    STATUS          mandatory
    DESCRIPTION     
            "
             Resource Usage.
             "
    ::= { sonusResourceMIBNotificationsObjects 7 }

sonusPeerResourcesMIBNotifications OBJECT IDENTIFIER
    ::= { sonusSbxTraps 17 }

sonusPeerResourcesMIBNotificationsPrefix OBJECT IDENTIFIER
    ::= { sonusPeerResourcesMIBNotifications 0 }

sonusPeerResourcesMIBNotificationsObjects OBJECT IDENTIFIER
    ::= { sonusPeerResourcesMIBNotifications 1 }

sonusPeerName OBJECT-TYPE
    SYNTAX          DisplayString
    ACCESS          read-only
    STATUS          mandatory
    DESCRIPTION     
            "
             Name of the IP PEER
             "
    ::= { sonusPeerResourcesMIBNotificationsObjects 1 }

sonusInterceptManagerMIBNotifications OBJECT IDENTIFIER
    ::= { sonusSbxTraps 18 }

sonusInterceptManagerMIBNotificationsPrefix OBJECT IDENTIFIER
    ::= { sonusInterceptManagerMIBNotifications 0 }

sonusInterceptManagerMIBNotificationsObjects OBJECT IDENTIFIER
    ::= { sonusInterceptManagerMIBNotifications 1 }

sonusImStatusPriOperState OBJECT-TYPE
    SYNTAX          INTEGER { inService(1), outOfService(2), standBy(3) }
    ACCESS          read-only
    STATUS          mandatory
    DESCRIPTION     
            " Current operational state of the primary call data channel."
    ::= { sonusInterceptManagerMIBNotificationsObjects 1 }

sonusImStatusSecOperState OBJECT-TYPE
    SYNTAX          INTEGER { inService(1), outOfService(2), standBy(3) }
    ACCESS          read-only
    STATUS          mandatory
    DESCRIPTION     
            " Current operational state of the Secondary call data channel."
    ::= { sonusInterceptManagerMIBNotificationsObjects 2 }

sonusImMediationServerName OBJECT-TYPE
    SYNTAX          DisplayString
    ACCESS          read-only
    STATUS          mandatory
    DESCRIPTION     
            "Mediation Server Name"
    ::= { sonusInterceptManagerMIBNotificationsObjects 3 }

sonusImMediationServerState OBJECT-TYPE
    SYNTAX          SonusAdminState
    ACCESS          read-only
    STATUS          mandatory
    DESCRIPTION     
            "This administrative state of the Mediation Server"
    ::= { sonusInterceptManagerMIBNotificationsObjects 4 }

sonusImMediationServerInterceptMediaType OBJECT-TYPE
    SYNTAX          DisplayString
    ACCESS          read-only
    STATUS          mandatory
    DESCRIPTION     
            "Mediation Server Entity - Signaling or Media"
    ::= { sonusInterceptManagerMIBNotificationsObjects 5 }

sonusMtrmMIBNotifications OBJECT IDENTIFIER
    ::= { sonusSbxTraps 19 }

sonusMtrmMIBNotificationsPrefix OBJECT IDENTIFIER
    ::= { sonusMtrmMIBNotifications 0 }

sonusMtrmMIBNotificationsObjects OBJECT IDENTIFIER
    ::= { sonusMtrmMIBNotifications 1 }

sonusMtrmPortIndex OBJECT-TYPE
    SYNTAX          Gauge
    ACCESS          read-only
    STATUS          mandatory
    DESCRIPTION     
            "This the MTRM connection port Index."
    ::= { sonusMtrmMIBNotificationsObjects 1 }

sonusMtrmServerAddr OBJECT-TYPE
    SYNTAX          IpAddress
    ACCESS          read-only
    STATUS          mandatory
    DESCRIPTION     
            "This the MTRM Server address"
    ::= { sonusMtrmMIBNotificationsObjects 2 }

sonusSecurityMIBNotifications OBJECT IDENTIFIER
    ::= { sonusSbxTraps 20 }

sonusSecurityMIBNotificationsPrefix OBJECT IDENTIFIER
    ::= { sonusSecurityMIBNotifications 0 }

sonusSecurityMIBNotificationsObjects OBJECT IDENTIFIER
    ::= { sonusSecurityMIBNotifications 1 }

sonusSecurityOcspUrlName OBJECT-TYPE
    SYNTAX          DisplayString (SIZE(1..254))
    ACCESS          read-only
    STATUS          mandatory
    DESCRIPTION     
            "OCSP responder URL."
    ::= { sonusSecurityMIBNotificationsObjects 1 }

sonusSecurityOcspResponseStatus OBJECT-TYPE
    SYNTAX          INTEGER { successful(0), malformedRequest(1), 
                        internalError(2), tryLater(3), sigRequired(5), 
                        unauthorized(6) }
    ACCESS          read-only
    STATUS          mandatory
    DESCRIPTION     
            "OCSP responseStatus indicating the processing status."
    ::= { sonusSecurityMIBNotificationsObjects 2 }

sonusVnfmUrlName OBJECT-TYPE
    SYNTAX          DisplayString (SIZE(1..254))
    ACCESS          read-only
    STATUS          mandatory
    DESCRIPTION     
            "VNFM  URL."
    ::= { sonusSecurityMIBNotificationsObjects 3 }

sonusLvmMIBNotifications OBJECT IDENTIFIER
    ::= { sonusSbxTraps 21 }

sonusLvmMIBNotificationsPrefix OBJECT IDENTIFIER
    ::= { sonusLvmMIBNotifications 0 }

sonusLvmMIBNotificationsObjects OBJECT IDENTIFIER
    ::= { sonusLvmMIBNotifications 1 }

sonusLvmPortSwitchReason OBJECT-TYPE
    SYNTAX          DisplayString
    ACCESS          read-only
    STATUS          mandatory
    DESCRIPTION     
            "Reason for switch"
    ::= { sonusLvmMIBNotificationsObjects 1 }

sonusLvmLinkDetectionGroupName OBJECT-TYPE
    SYNTAX          DisplayString (SIZE(1..24))
    ACCESS          read-only
    STATUS          mandatory
    DESCRIPTION     
            "The name of the link detection group."
    ::= { sonusLvmMIBNotificationsObjects 2 }

sonusLvmPortRedundancyGroupName OBJECT-TYPE
    SYNTAX          DisplayString (SIZE(1..24))
    ACCESS          read-only
    STATUS          mandatory
    DESCRIPTION     
            "The name of the port redundancy group."
    ::= { sonusLvmMIBNotificationsObjects 3 }

sonusDiamMIBNotifications OBJECT IDENTIFIER
    ::= { sonusSbxTraps 22 }

sonusDiamMIBNotificationsPrefix OBJECT IDENTIFIER
    ::= { sonusDiamMIBNotifications 0 }

sonusDiamMIBNotificationsObjects OBJECT IDENTIFIER
    ::= { sonusDiamMIBNotifications 1 }

sonusRfAccountingServerName OBJECT-TYPE
    SYNTAX          DisplayString
    ACCESS          read-only
    STATUS          deprecated
    DESCRIPTION     
            "Rf Accounting Server Name."
    ::= { sonusDiamMIBNotificationsObjects 1 }

sonusDiamPeerName OBJECT-TYPE
    SYNTAX          DisplayString
    ACCESS          read-only
    STATUS          mandatory
    DESCRIPTION     
            "Diameter Peer Name."
    ::= { sonusDiamMIBNotificationsObjects 2 }

sonusDiamPeerIpAddress OBJECT-TYPE
    SYNTAX          DisplayString
    ACCESS          read-only
    STATUS          mandatory
    DESCRIPTION     
            "
             Diameter Peer Ip Address.
             "
    ::= { sonusDiamMIBNotificationsObjects 3 }

sonusDnsMIBNotifications OBJECT IDENTIFIER
    ::= { sonusSbxTraps 23 }

sonusDnsMIBNotificationsPrefix OBJECT IDENTIFIER
    ::= { sonusDnsMIBNotifications 0 }

sonusDnsMIBNotificationsObjects OBJECT IDENTIFIER
    ::= { sonusDnsMIBNotifications 1 }

sonusDnsServerIp OBJECT-TYPE
    SYNTAX          DisplayString
    ACCESS          read-only
    STATUS          mandatory
    DESCRIPTION     
            "
             IP Address of the Dns server address  - mandatory parameter.
             "
    ::= { sonusDnsMIBNotificationsObjects 1 }

sonusDnsServerPortNum OBJECT-TYPE
    SYNTAX          INTEGER (1..65535)
    ACCESS          read-only
    STATUS          mandatory
    DESCRIPTION     
            "
             transport port number of the Dns server   - mandatory parameter.
             "
    ::= { sonusDnsMIBNotificationsObjects 2 }

sonusDnsServerTransport OBJECT-TYPE
    SYNTAX          DisplayString
    ACCESS          read-only
    STATUS          mandatory
    DESCRIPTION     
            "
             transport used to connect to  Dns server   - mandatory parameter.
             "
    ::= { sonusDnsMIBNotificationsObjects 3 }

sonusDnsIpAddr OBJECT-TYPE
    SYNTAX          IpAddress
    ACCESS          read-only
    STATUS          mandatory
    DESCRIPTION     
            "
             IP Address of the Dns server address.
             "
    ::= { sonusDnsMIBNotificationsObjects 4 }

sonusDnsServerZoneId OBJECT-TYPE
    SYNTAX          DisplayString
    ACCESS          read-only
    STATUS          mandatory
    DESCRIPTION     
            "
             DNS ZONE Name of the Dns zone.
             "
    ::= { sonusDnsMIBNotificationsObjects 5 }

sonusDomainName OBJECT-TYPE
    SYNTAX          DisplayString
    ACCESS          read-only
    STATUS          obsolete
    DESCRIPTION     
            "
             Domain Name for which the Query is been done.
             "
    ::= { sonusDnsMIBNotificationsObjects 6 }

sonusRecordType OBJECT-TYPE
    SYNTAX          DisplayString
    ACCESS          read-only
    STATUS          obsolete
    DESCRIPTION     
            "
             RecordType of the FQDN.
             "
    ::= { sonusDnsMIBNotificationsObjects 7 }

sonusRcodeError OBJECT-TYPE
    SYNTAX          DisplayString
    ACCESS          read-only
    STATUS          mandatory
    DESCRIPTION     
            "
             RCODE ERROR format received.
             "
    ::= { sonusDnsMIBNotificationsObjects 8 }

sonusDnsIpV6Addr OBJECT-TYPE
    SYNTAX          Ipv6Address
    ACCESS          read-only
    STATUS          mandatory
    DESCRIPTION     
            "Ipv6 Address of the Dns Server."
    ::= { sonusDnsMIBNotificationsObjects 9 }

sonusDnsServerType OBJECT-TYPE
    SYNTAX          DisplayString
    ACCESS          read-only
    STATUS          mandatory
    DESCRIPTION     
            "
             Server Type: Named server or configured server.
             "
    ::= { sonusDnsMIBNotificationsObjects 10 }

sonusEdnsMIBNotifications OBJECT IDENTIFIER
    ::= { sonusSbxTraps 24 }

sonusEdnsMIBNotificationsPrefix OBJECT IDENTIFIER
    ::= { sonusEdnsMIBNotifications 0 }

sonusEdnsMIBNotificationsObjects OBJECT IDENTIFIER
    ::= { sonusEdnsMIBNotifications 1 }

sonusEdnsServerIp OBJECT-TYPE
    SYNTAX          IpAddress
    ACCESS          read-only
    STATUS          mandatory
    DESCRIPTION     
            "
             IP Address of the Dns server address  - mandatory parameter.
             "
    ::= { sonusEdnsMIBNotificationsObjects 1 }

sonusDsbcSignallingMIBNotifications OBJECT IDENTIFIER
    ::= { sonusSbxTraps 25 }

sonusDsbcSignallingMIBNotificationsPrefix OBJECT IDENTIFIER
    ::= { sonusDsbcSignallingMIBNotifications 0 }

sonusDsbcSignallingMIBNotificationsObjects OBJECT IDENTIFIER
    ::= { sonusDsbcSignallingMIBNotifications 1 }

sonusDsbcCloseReasonCode OBJECT-TYPE
    SYNTAX          INTEGER { administratorInitiatedClose(1), 
                        closeRequestReceivedFromRemote(2), 
                        remoteNotResponding(3), internalError(4), 
                        configError(5), recvCallSigReqFromUnknownDsbc(6), 
                        socketErrNetworkDown(7), 
                        socketErrNetworkUnreachable(8), 
                        socketErrNetworkReset(9), 
                        socketErrSoftwareConnectionAbort(10), 
                        socketErrConnectionResetByPeer(11), 
                        socketErrNoBufferSpaceAvail(12), 
                        socketErrAlreadyConnected(13), 
                        socketErrNotConnected(14), 
                        socketErrCantSendAfterShutdown(15), 
                        socketErrTooManyReferences(16), 
                        socketErrConnectionTimedOut(17), 
                        socketErrUnknown(18), 
                        recvDuplicateLinkOpenReq(19), 
                        socketErrExceptionEvent(20), 
                        linkXmtCongestion(21), 
                        openNackReceivedFromRemote(22), idleTimeout(23) }
    ACCESS          read-only
    STATUS          mandatory
    DESCRIPTION     
            "Reason for close of Control Channel Link."
    ::= { sonusDsbcSignallingMIBNotificationsObjects 1 }

sonusDsbcRemoteDsbcAddr OBJECT-TYPE
    SYNTAX          IpAddress
    ACCESS          read-only
    STATUS          mandatory
    DESCRIPTION     
            "Ip Address of the remote Dsbc."
    ::= { sonusDsbcSignallingMIBNotificationsObjects 2 }

sonusDsbcRemoteDsbc6Addr OBJECT-TYPE
    SYNTAX          Ipv6Address
    ACCESS          read-only
    STATUS          mandatory
    DESCRIPTION     
            "Ipv6 Address of the remote Dsbc."
    ::= { sonusDsbcSignallingMIBNotificationsObjects 3 }

sonusDsbcClusterFqdn OBJECT-TYPE
    SYNTAX          DisplayString
    ACCESS          read-only
    STATUS          mandatory
    DESCRIPTION     
            "The Fully Qualified Domain Name of the Cluster."
    ::= { sonusDsbcSignallingMIBNotificationsObjects 4 }

sonusDsbcClusterType OBJECT-TYPE
    SYNTAX          DisplayString
    ACCESS          read-only
    STATUS          mandatory
    DESCRIPTION     
            "Cluster Type, policer or dsp."
    ::= { sonusDsbcSignallingMIBNotificationsObjects 5 }

sonusDsbcCallsReleasedReasonCode OBJECT-TYPE
    SYNTAX          Gauge
    ACCESS          read-only
    STATUS          mandatory
    DESCRIPTION     
            "Reason code for call release due to fault."
    ::= { sonusDsbcSignallingMIBNotificationsObjects 6 }

sonusDsbcCallsReleasedCount OBJECT-TYPE
    SYNTAX          Gauge
    ACCESS          read-only
    STATUS          mandatory
    DESCRIPTION     
            "Released call count due to fault."
    ::= { sonusDsbcSignallingMIBNotificationsObjects 7 }

sonusDsbcAllocFailuresCount OBJECT-TYPE
    SYNTAX          Gauge
    ACCESS          read-only
    STATUS          mandatory
    DESCRIPTION     
            "Released call count due to fault."
    ::= { sonusDsbcSignallingMIBNotificationsObjects 8 }

sonusThresholdCrossingCodec OBJECT-TYPE
    SYNTAX          DisplayString
    ACCESS          read-only
    STATUS          mandatory
    DESCRIPTION     
            "Codec/s crossing the channel capacity threshold on GPU device"
    ::= { sonusDsbcSignallingMIBNotificationsObjects 9 }

sonusTrafficProfileActivationMsg OBJECT-TYPE
    SYNTAX          DisplayString
    ACCESS          read-only
    STATUS          mandatory
    DESCRIPTION     
            "Reason of success/failure upon activation of a traffic profile."
    ::= { sonusDsbcSignallingMIBNotificationsObjects 10 }

sonusTrafficProfileActivationStatus OBJECT-TYPE
    SYNTAX          DisplayString
    ACCESS          read-only
    STATUS          mandatory
    DESCRIPTION     
            "Status (success/failure) of activation of a traffic profile."
    ::= { sonusDsbcSignallingMIBNotificationsObjects 11 }

sonusConfigProfileActivationMsg OBJECT-TYPE
    SYNTAX          DisplayString
    ACCESS          read-only
    STATUS          mandatory
    DESCRIPTION     
            "Reason of success/failure upon activation of a Config profile."
    ::= { sonusDsbcSignallingMIBNotificationsObjects 12 }

sonusConfigProfileActivationStatus OBJECT-TYPE
    SYNTAX          DisplayString
    ACCESS          read-only
    STATUS          mandatory
    DESCRIPTION     
            "Status (success/failure) of activation of a Config profile."
    ::= { sonusDsbcSignallingMIBNotificationsObjects 13 }

sonusCacMIBNotifications OBJECT IDENTIFIER
    ::= { sonusSbxTraps 26 }

sonusCacMIBNotificationsPrefix OBJECT IDENTIFIER
    ::= { sonusCacMIBNotifications 0 }

sonusCacMIBNotificationsObjects OBJECT IDENTIFIER
    ::= { sonusCacMIBNotifications 1 }

sonusCacSrcIp OBJECT-TYPE
    SYNTAX          IpAddress
    ACCESS          read-only
    STATUS          mandatory
    DESCRIPTION     
            " IP Address of end point  - mandatory parameter. "
    ::= { sonusCacMIBNotificationsObjects 1 }

sonusCcsMIBNotifications OBJECT IDENTIFIER
    ::= { sonusSbxTraps 27 }

sonusCcsMIBNotificationsPrefix OBJECT IDENTIFIER
    ::= { sonusCcsMIBNotifications 0 }

sonusCcsMIBNotificationsObjects OBJECT IDENTIFIER
    ::= { sonusCcsMIBNotifications 1 }

sonusOodMIBNotifications OBJECT IDENTIFIER
    ::= { sonusSbxTraps 28 }

sonusOodMIBNotificationsPrefix OBJECT IDENTIFIER
    ::= { sonusOodMIBNotifications 0 }

sonusOodMIBNotificationsObjects OBJECT IDENTIFIER
    ::= { sonusOodMIBNotifications 1 }

sonusActiveOodRate OBJECT-TYPE
    SYNTAX          Gauge
    ACCESS          read-only
    STATUS          mandatory
    DESCRIPTION     
            "Active OOD Message Rate"
    ::= { sonusOodMIBNotificationsObjects 1 }

sonusOodRateLimit OBJECT-TYPE
    SYNTAX          Gauge
    ACCESS          read-only
    STATUS          mandatory
    DESCRIPTION     
            "Configured OOD Message Rate Limit"
    ::= { sonusOodMIBNotificationsObjects 2 }

sonusOamMIBNotifications OBJECT IDENTIFIER
    ::= { sonusSbxTraps 29 }

sonusOamMIBNotificationsPrefix OBJECT IDENTIFIER
    ::= { sonusOamMIBNotifications 0 }

sonusOamMIBNotificationsObjects OBJECT IDENTIFIER
    ::= { sonusOamMIBNotifications 1 }

sonusManagedNodeCeName OBJECT-TYPE
    SYNTAX          DisplayString
    ACCESS          read-only
    STATUS          mandatory
    DESCRIPTION     
            "Managed node compute element name"
    ::= { sonusOamMIBNotificationsObjects 1 }

sonusHpcCallLimitMIBNotifications OBJECT IDENTIFIER
    ::= { sonusSbxTraps 30 }

sonusHpcCallLimitMIBNotificationsPrefix OBJECT IDENTIFIER
    ::= { sonusHpcCallLimitMIBNotifications 0 }

sonusHpcCallLimitMIBNotificationsObjects OBJECT IDENTIFIER
    ::= { sonusHpcCallLimitMIBNotifications 1 }

sonusHpcCallLimitEntityName OBJECT-TYPE
    SYNTAX          DisplayString
    ACCESS          read-only
    STATUS          mandatory
    DESCRIPTION     
            "Zone, TrunkGroup, IPPeer name"
    ::= { sonusHpcCallLimitMIBNotificationsObjects 1 }

sonusHpcCallLimitDeniedAttempts OBJECT-TYPE
    SYNTAX          Gauge
    ACCESS          read-only
    STATUS          mandatory
    DESCRIPTION     
            "Number of calls denied being reported."
    ::= { sonusHpcCallLimitMIBNotificationsObjects 2 }

sonusHpcCallNoLicenseMIBNotifications OBJECT IDENTIFIER
    ::= { sonusSbxTraps 31 }

sonusHpcCallNoLicenseMIBNotificationsPrefix OBJECT IDENTIFIER
    ::= { sonusHpcCallNoLicenseMIBNotifications 0 }

sonusHpcCallNoLicenseMIBNotificationsObjects OBJECT IDENTIFIER
    ::= { sonusHpcCallNoLicenseMIBNotifications 1 }

sonusSlbMIBNotifications OBJECT IDENTIFIER
    ::= { sonusSbxTraps 32 }

sonusSlbMIBNotificationsPrefix OBJECT IDENTIFIER
    ::= { sonusSlbMIBNotifications 0 }

sonusSlbMIBNotificationsObjects OBJECT IDENTIFIER
    ::= { sonusSlbMIBNotifications 1 }

sonusVnfId OBJECT-TYPE
    SYNTAX          DisplayString
    ACCESS          read-only
    STATUS          mandatory
    DESCRIPTION     
            "VNF Identifier"
    ::= { sonusSlbMIBNotificationsObjects 1 }

sonusVnfcInstanceId OBJECT-TYPE
    SYNTAX          Gauge
    ACCESS          read-only
    STATUS          mandatory
    DESCRIPTION     
            "VNFC Instance Identifier"
    ::= { sonusSlbMIBNotificationsObjects 2 }

sonusSlbIpAddress OBJECT-TYPE
    SYNTAX          IpAddress
    ACCESS          read-only
    STATUS          mandatory
    DESCRIPTION     
            "Ip Address of the SLB."
    ::= { sonusSlbMIBNotificationsObjects 3 }

sonusSlbIpv6Address OBJECT-TYPE
    SYNTAX          Ipv6Address
    ACCESS          read-only
    STATUS          mandatory
    DESCRIPTION     
            "Ipv6 Address of the SLB."
    ::= { sonusSlbMIBNotificationsObjects 4 }

sonusCurrentGlobalLossRatio OBJECT-TYPE
    SYNTAX          Gauge
    ACCESS          read-only
    STATUS          mandatory
    DESCRIPTION     
            "Current Global Loss Ratio"
    ::= { sonusSlbMIBNotificationsObjects 5 }

sonusGlobalLossRatioLimit OBJECT-TYPE
    SYNTAX          Gauge
    ACCESS          read-only
    STATUS          mandatory
    DESCRIPTION     
            "Configured Global Los Ratio Limit"
    ::= { sonusSlbMIBNotificationsObjects 6 }

sonusSlbName OBJECT-TYPE
    SYNTAX          DisplayString
    ACCESS          read-only
    STATUS          mandatory
    DESCRIPTION     
            "SLB Name"
    ::= { sonusSlbMIBNotificationsObjects 7 }

sonusCurrentGlobalUtilization OBJECT-TYPE
    SYNTAX          Gauge
    ACCESS          read-only
    STATUS          mandatory
    DESCRIPTION     
            "Current Global Utilization"
    ::= { sonusSlbMIBNotificationsObjects 8 }

sonusGlobalUtilizationLimit OBJECT-TYPE
    SYNTAX          Gauge
    ACCESS          read-only
    STATUS          mandatory
    DESCRIPTION     
            "Configured Global Utilization Limit"
    ::= { sonusSlbMIBNotificationsObjects 9 }

sonusMicroServiceMIBNotifications OBJECT IDENTIFIER
    ::= { sonusSbxTraps 33 }

sonusMicroServiceMIBNotificationsPrefix OBJECT IDENTIFIER
    ::= { sonusMicroServiceMIBNotifications 0 }

sonusMicroServiceMIBNotificationsObjects OBJECT IDENTIFIER
    ::= { sonusMicroServiceMIBNotifications 1 }

sonusMicroServiceName OBJECT-TYPE
    SYNTAX          DisplayString
    ACCESS          read-only
    STATUS          mandatory
    DESCRIPTION     
            "Name of the micro-service."
    ::= { sonusMicroServiceMIBNotificationsObjects 1 }

sonusBfdMIBNotifications OBJECT IDENTIFIER
    ::= { sonusSbxTraps 34 }

sonusBfdMIBNotificationsPrefix OBJECT IDENTIFIER
    ::= { sonusBfdMIBNotifications 0 }

sonusBfdMIBNotificationsObjects OBJECT IDENTIFIER
    ::= { sonusBfdMIBNotifications 1 }

sonusBfdLinkId OBJECT-TYPE
    SYNTAX          INTEGER (0..65535)
    ACCESS          read-only
    STATUS          mandatory
    DESCRIPTION     
            "link ID to identify bfd session."
    ::= { sonusBfdMIBNotificationsObjects 1 }

sonusH248NoRtpMIBNotifications OBJECT IDENTIFIER
    ::= { sonusSbxTraps 35 }

sonusH248NoRtpMIBNotificationsPrefix OBJECT IDENTIFIER
    ::= { sonusH248NoRtpMIBNotifications 0 }

sonusH248NoRtpMIBNotificationsObjects OBJECT IDENTIFIER
    ::= { sonusH248NoRtpMIBNotifications 1 }

sonusH248VmgName OBJECT-TYPE
    SYNTAX          DisplayString (SIZE(1..24))
    ACCESS          read-only
    STATUS          mandatory
    DESCRIPTION     
            "The name of the VMG."
    ::= { sonusH248NoRtpMIBNotificationsObjects 1 }

sonusH248TermThreshold OBJECT-TYPE
    SYNTAX          Gauge
    ACCESS          read-only
    STATUS          mandatory
    DESCRIPTION     
            "No RTP Alarm Set Threshold"
    ::= { sonusH248NoRtpMIBNotificationsObjects 2 }

sonusH248NoRtpTerminations OBJECT-TYPE
    SYNTAX          Gauge
    ACCESS          read-only
    STATUS          mandatory
    DESCRIPTION     
            "Total Number of No RTP Terminations"
    ::= { sonusH248NoRtpMIBNotificationsObjects 3 }

sonusH248ClearThreshold OBJECT-TYPE
    SYNTAX          Gauge
    ACCESS          read-only
    STATUS          mandatory
    DESCRIPTION     
            "No RTP Alarm Clear Threshold"
    ::= { sonusH248NoRtpMIBNotificationsObjects 4 }

sonusH248MinimumRtpTerminations OBJECT-TYPE
    SYNTAX          Gauge
    ACCESS          read-only
    STATUS          mandatory
    DESCRIPTION     
            "Minimum Number of RTP Terminations Required"
    ::= { sonusH248NoRtpMIBNotificationsObjects 5 }

sonusH248TotalRtpTerminations OBJECT-TYPE
    SYNTAX          Gauge
    ACCESS          read-only
    STATUS          mandatory
    DESCRIPTION     
            "Total RTP Terminations on VMG"
    ::= { sonusH248NoRtpMIBNotificationsObjects 6 }

sonusPortMIBNotifications OBJECT IDENTIFIER
    ::= { sonusSbxTraps 36 }

sonusPortMIBNotificationsPrefix OBJECT IDENTIFIER
    ::= { sonusPortMIBNotifications 0 }

sonusPortMIBNotificationsObjects OBJECT IDENTIFIER
    ::= { sonusPortMIBNotifications 1 }

sonusEthernetPortName OBJECT-TYPE
    SYNTAX          DisplayString (SIZE(1..24))
    ACCESS          read-only
    STATUS          mandatory
    DESCRIPTION     
            "The name of the port."
    ::= { sonusPortMIBNotificationsObjects 1 }

sonusEthernetPortBwUsageThreshold OBJECT-TYPE
    SYNTAX          Gauge
    ACCESS          read-only
    STATUS          mandatory
    DESCRIPTION     
            "Packet Port BW Usage Set Threshold"
    ::= { sonusPortMIBNotificationsObjects 2 }

sonusEthernetPortBwUsage OBJECT-TYPE
    SYNTAX          Gauge
    ACCESS          read-only
    STATUS          mandatory
    DESCRIPTION     
            "BW Usage on Packet Port"
    ::= { sonusPortMIBNotificationsObjects 3 }

sonusEthernetPortBwUsageClearThreshold OBJECT-TYPE
    SYNTAX          Gauge
    ACCESS          read-only
    STATUS          mandatory
    DESCRIPTION     
            "Packet Port BW Usage Clear Threshold"
    ::= { sonusPortMIBNotificationsObjects 4 }

sonusSbxSipCallSigPortOpenNotification TRAP-TYPE
    ENTERPRISE      sonusSipSignallingMIBNotifications
    VARIABLES       { sonusAlarmNodeID, sonusAlarmLevel, 
                      sonusAlarmSequenceId, sonusAlarmTime, 
                      sonusAlarmDescription, sonusSipSigPortIpAddress, 
                      sonusSipSigPortNum, sonusSipSigProto }
--     STATUS          mandatory
    DESCRIPTION     
            "This trap indicates that a call signaling port is opened."
    ::= 1

sonusSbxSipCallSigPortCloseNotification TRAP-TYPE
    ENTERPRISE      sonusSipSignallingMIBNotifications
    VARIABLES       { sonusAlarmNodeID, sonusAlarmLevel, 
                      sonusAlarmSequenceId, sonusAlarmTime, 
                      sonusAlarmDescription, sonusSipSigPortIpAddress, 
                      sonusSipSigPortNum, sonusSipSigProto }
--     STATUS          mandatory
    DESCRIPTION     
            "This trap indicates that a call signaling port is closed."
    ::= 2

sonusSbxSipTrunkGroupInServiceNotification TRAP-TYPE
    ENTERPRISE      sonusSipSignallingMIBNotifications
    VARIABLES       { sonusAlarmNodeID, sonusAlarmLevel, 
                      sonusAlarmSequenceId, sonusAlarmTime, 
                      sonusAlarmDescription, sonusSipTgName }
--     STATUS          mandatory
    DESCRIPTION     
            "This trap indicates that the SIP Trunk Group was put
             into service by maintenance staff."
    ::= 3

sonusSbxSipTrunkGroupOutOfServiceNotification TRAP-TYPE
    ENTERPRISE      sonusSipSignallingMIBNotifications
    VARIABLES       { sonusAlarmNodeID, sonusAlarmLevel, 
                      sonusAlarmSequenceId, sonusAlarmTime, 
                      sonusAlarmDescription, sonusSipTgName }
--     STATUS          mandatory
    DESCRIPTION     
            "This trap indicates that the SIP Trunk Group was taken
             out of service by maintenance staff."
    ::= 4

sonusSbxSipRegistrantPortChangeNotification TRAP-TYPE
    ENTERPRISE      sonusSipSignallingMIBNotifications
    VARIABLES       { sonusAlarmNodeID, sonusAlarmLevel, 
                      sonusAlarmSequenceId, sonusAlarmTime, 
                      sonusAlarmDescription }
--     STATUS          mandatory
    DESCRIPTION     
            "This trap indicates that at least one SIP registrant
             has a source port number that changed over two or more
             consecutive REGISTER refreshes, possibly indicating that
             the registrant was unreachable from the SBC for a time."
    ::= 5

sonusSbxArsEndPointBlacklistedNotification TRAP-TYPE
    ENTERPRISE      sonusSipSignallingMIBNotifications
    VARIABLES       { sonusAlarmNodeID, sonusAlarmLevel, 
                      sonusAlarmSequenceId, sonusAlarmTime, 
                      sonusAlarmDescription, 
                      sonusSipArsStatEndpointIpAddress, 
                      sonusSipArsStatEndpointIpPortNum, 
                      sonusSipArsStatSigZoneId, 
                      sonusSipArsStatSigPortNum, 
                      sonusSipArsStatEndpointOwnerId }
--     STATUS          deprecated
    DESCRIPTION     
            "This trap is replaced by sonusSbxArsEndPointBlacklistedNotification2"
    ::= 6

sonusSbxArsEndPointRecoveredNotification TRAP-TYPE
    ENTERPRISE      sonusSipSignallingMIBNotifications
    VARIABLES       { sonusAlarmNodeID, sonusAlarmLevel, 
                      sonusAlarmSequenceId, sonusAlarmTime, 
                      sonusAlarmDescription, 
                      sonusSipArsStatEndpointIpAddress, 
                      sonusSipArsStatEndpointIpPortNum, 
                      sonusSipArsStatSigZoneId, 
                      sonusSipArsStatSigPortNum, 
                      sonusSipArsStatEndpointOwnerId }
--     STATUS          deprecated
    DESCRIPTION     
            "This trap is replaced by sonusSbxArsEndPointRecoveredNotification2"
    ::= 7

sonusSbxArsEndPointsRecoveredNotification TRAP-TYPE
    ENTERPRISE      sonusSipSignallingMIBNotifications
    VARIABLES       { sonusAlarmNodeID, sonusAlarmLevel, 
                      sonusAlarmSequenceId, sonusAlarmTime, 
                      sonusAlarmDescription, sonusSipArsStatSigZoneId, 
                      sonusSipArsEndpointRecoveryAll }
--     STATUS          deprecated
    DESCRIPTION     
            "This trap is replaced by sonusSbxArsEndPointsRecoveredNotification2"
    ::= 8

sonusSbxSipTgRegLimitReachedNotification TRAP-TYPE
    ENTERPRISE      sonusSipSignallingMIBNotifications
    VARIABLES       { sonusAlarmNodeID, sonusAlarmLevel, 
                      sonusAlarmSequenceId, sonusAlarmTime, 
                      sonusAlarmDescription, sonusSipTgName }
--     STATUS          mandatory
    DESCRIPTION     
            "This trap indicates that a Trunk Group's max registration limit
             has reached due to received registrations on ingress OR implicit or child registrations."
    ::= 9

sonusSbxPathCheckPingStateUpNotification TRAP-TYPE
    ENTERPRISE      sonusSipSignallingMIBNotifications
    VARIABLES       { sonusAlarmNodeID, sonusAlarmLevel, 
                      sonusAlarmSequenceId, sonusAlarmTime, 
                      sonusAlarmDescription, sonusPingPeerIpAddress, 
                      sonusPingPeerPortNum, sonusPingPeerZoneId }
--     STATUS          deprecated
    DESCRIPTION     
            "This trap is replaced by sonusSbxPathCheckPingStateUpNotification2"
    ::= 10

sonusSbxPathCheckPingStateDownNotification TRAP-TYPE
    ENTERPRISE      sonusSipSignallingMIBNotifications
    VARIABLES       { sonusAlarmNodeID, sonusAlarmLevel, 
                      sonusAlarmSequenceId, sonusAlarmTime, 
                      sonusAlarmDescription, sonusPingPeerIpAddress, 
                      sonusPingPeerPortNum, sonusPingPeerZoneId }
--     STATUS          deprecated
    DESCRIPTION     
            "This trap is replaced by sonusSbxPathCheckPingStateDownNotification2"
    ::= 11

sonusSbxPathCheckRemoteAdminStateUpNotification TRAP-TYPE
    ENTERPRISE      sonusSipSignallingMIBNotifications
    VARIABLES       { sonusAlarmNodeID, sonusAlarmLevel, 
                      sonusAlarmSequenceId, sonusAlarmTime, 
                      sonusAlarmDescription, sonusPingPeerIpAddress, 
                      sonusPingPeerPortNum, sonusPingPeerZoneId }
--     STATUS          deprecated
    DESCRIPTION     
            "This trap is replaced by sonusSbxPathCheckRemoteAdminStateUpNotification2"
    ::= 12

sonusSbxPathCheckRemoteAdminStateDownNotification TRAP-TYPE
    ENTERPRISE      sonusSipSignallingMIBNotifications
    VARIABLES       { sonusAlarmNodeID, sonusAlarmLevel, 
                      sonusAlarmSequenceId, sonusAlarmTime, 
                      sonusAlarmDescription, sonusPingPeerIpAddress, 
                      sonusPingPeerPortNum, sonusPingPeerZoneId }
--     STATUS          deprecated
    DESCRIPTION     
            "This trap is replaced by sonusSbxPathCheckRemoteAdminStateDownNotification2"
    ::= 13

sonusSbxPathCheckLocalAdminStateUpNotification TRAP-TYPE
    ENTERPRISE      sonusSipSignallingMIBNotifications
    VARIABLES       { sonusAlarmNodeID, sonusAlarmLevel, 
                      sonusAlarmSequenceId, sonusAlarmTime, 
                      sonusAlarmDescription, sonusPingPeerIpAddress, 
                      sonusPingPeerPortNum, sonusPingPeerZoneId }
--     STATUS          deprecated
    DESCRIPTION     
            "This trap is replaced by sonusSbxPathCheckLocalAdminStateUpNotification2"
    ::= 14

sonusSbxPathCheckLocalAdminStateDownNotification TRAP-TYPE
    ENTERPRISE      sonusSipSignallingMIBNotifications
    VARIABLES       { sonusAlarmNodeID, sonusAlarmLevel, 
                      sonusAlarmSequenceId, sonusAlarmTime, 
                      sonusAlarmDescription, sonusPingPeerIpAddress, 
                      sonusPingPeerPortNum, sonusPingPeerZoneId }
--     STATUS          deprecated
    DESCRIPTION     
            "The trap is replaced by sonusSbxPathCheckLocalAdminStateDownNotification2"
    ::= 15

sonusSbxSipMultipleContactsPerAorSigPortExhaustedNotification TRAP-TYPE
    ENTERPRISE      sonusSipSignallingMIBNotifications
    VARIABLES       { sonusAlarmNodeID, sonusAlarmLevel, 
                      sonusAlarmSequenceId, sonusAlarmTime, 
                      sonusAlarmDescription, sonusSipAorSigZoneId }
--     STATUS          mandatory
    DESCRIPTION     
            "This trap indicates that  an AOR registering from multiple
             contact address is reusing a signlaing port on trunk group the towards the 
             registrar. This trap is generated once per zone"
    ::= 16

sonusSbxSurrRegRegistrationSuccessNotification TRAP-TYPE
    ENTERPRISE      sonusSipSignallingMIBNotifications
    VARIABLES       { sonusAlarmNodeID, sonusAlarmLevel, 
                      sonusAlarmSequenceId, sonusAlarmTime, 
                      sonusAlarmDescription, sonusSurrRegPeerIpAddress, 
                      sonusSurrRegPeerPortNum, sonusSurrRegPeerZoneId, 
                      sonusSurrRegUserPart }
--     STATUS          mandatory
    DESCRIPTION     
            "This trap indicates that the surrogate registration for the AOR succeeded"
    ::= 17

sonusSbxSurrRegRegistrationFailedNotification TRAP-TYPE
    ENTERPRISE      sonusSipSignallingMIBNotifications
    VARIABLES       { sonusAlarmNodeID, sonusAlarmLevel, 
                      sonusAlarmSequenceId, sonusAlarmTime, 
                      sonusAlarmDescription, sonusSurrRegPeerIpAddress, 
                      sonusSurrRegPeerPortNum, sonusSurrRegPeerZoneId, 
                      sonusSurrRegUserPart }
--     STATUS          mandatory
    DESCRIPTION     
            "This trap indicates that the surrogate registration for the AOR failed"
    ::= 18

sonusSbxArsEndPointBlacklistedNotificationV6 TRAP-TYPE
    ENTERPRISE      sonusSipSignallingMIBNotifications
    VARIABLES       { sonusAlarmNodeID, sonusAlarmLevel, 
                      sonusAlarmSequenceId, sonusAlarmTime, 
                      sonusAlarmDescription, 
                      sonusSipArsStatEndpointIpAddressV6, 
                      sonusSipArsStatEndpointIpPortNum, 
                      sonusSipArsStatSigZoneId, 
                      sonusSipArsStatSigPortNum, 
                      sonusSipArsStatEndpointOwnerId }
--     STATUS          deprecated
    DESCRIPTION     
            "This trap is replaced by sonusSbxArsEndPointBlacklistedNotification2V6"
    ::= 19

sonusSbxArsEndPointRecoveredNotificationV6 TRAP-TYPE
    ENTERPRISE      sonusSipSignallingMIBNotifications
    VARIABLES       { sonusAlarmNodeID, sonusAlarmLevel, 
                      sonusAlarmSequenceId, sonusAlarmTime, 
                      sonusAlarmDescription, 
                      sonusSipArsStatEndpointIpAddressV6, 
                      sonusSipArsStatEndpointIpPortNum, 
                      sonusSipArsStatSigZoneId, 
                      sonusSipArsStatSigPortNum, 
                      sonusSipArsStatEndpointOwnerId }
--     STATUS          deprecated
    DESCRIPTION     
            "This trap is replaced by sonusSbxArsEndPointRecoveredNotification2V6"
    ::= 20

sonusSbxSipCallSigPortOpenNotificationV6 TRAP-TYPE
    ENTERPRISE      sonusSipSignallingMIBNotifications
    VARIABLES       { sonusAlarmNodeID, sonusAlarmLevel, 
                      sonusAlarmSequenceId, sonusAlarmTime, 
                      sonusAlarmDescription, sonusSipSigPortIpAddressV6, 
                      sonusSipSigPortNum, sonusSipSigProto }
--     STATUS          mandatory
    DESCRIPTION     
            "This trap indicates that a call signaling port is opened."
    ::= 21

sonusSbxPathCheckLocalAdminStateUpNotificationV6 TRAP-TYPE
    ENTERPRISE      sonusSipSignallingMIBNotifications
    VARIABLES       { sonusAlarmNodeID, sonusAlarmLevel, 
                      sonusAlarmSequenceId, sonusAlarmTime, 
                      sonusAlarmDescription, sonusPingPeerIpAddressV6, 
                      sonusPingPeerPortNum, sonusPingPeerZoneId }
--     STATUS          deprecated
    DESCRIPTION     
            "This trap is replaced by sonusSbxPathCheckLocalAdminStateUpNotification2V6"
    ::= 22

sonusSbxPathCheckLocalAdminStateDownNotificationV6 TRAP-TYPE
    ENTERPRISE      sonusSipSignallingMIBNotifications
    VARIABLES       { sonusAlarmNodeID, sonusAlarmLevel, 
                      sonusAlarmSequenceId, sonusAlarmTime, 
                      sonusAlarmDescription, sonusPingPeerIpAddressV6, 
                      sonusPingPeerPortNum, sonusPingPeerZoneId }
--     STATUS          deprecated
    DESCRIPTION     
            "This trap is replaced by sonusSbxPathCheckLocalAdminStateDownNotification2V6"
    ::= 23

sonusSbxPathCheckPingStateUpNotificationV6 TRAP-TYPE
    ENTERPRISE      sonusSipSignallingMIBNotifications
    VARIABLES       { sonusAlarmNodeID, sonusAlarmLevel, 
                      sonusAlarmSequenceId, sonusAlarmTime, 
                      sonusAlarmDescription, sonusPingPeerIpAddressV6, 
                      sonusPingPeerPortNum, sonusPingPeerZoneId }
--     STATUS          deprecated
    DESCRIPTION     
            "This trap is replaced by sonusSbxPathCheckPingStateUpNotification2V6"
    ::= 24

sonusSbxPathCheckPingStateDownNotificationV6 TRAP-TYPE
    ENTERPRISE      sonusSipSignallingMIBNotifications
    VARIABLES       { sonusAlarmNodeID, sonusAlarmLevel, 
                      sonusAlarmSequenceId, sonusAlarmTime, 
                      sonusAlarmDescription, sonusPingPeerIpAddressV6, 
                      sonusPingPeerPortNum, sonusPingPeerZoneId }
--     STATUS          deprecated
    DESCRIPTION     
            "This trap is replaced by sonusSbxPathCheckPingStateDownNotification2V6"
    ::= 25

sonusSbxSipCallSigPortCloseNotificationV6 TRAP-TYPE
    ENTERPRISE      sonusSipSignallingMIBNotifications
    VARIABLES       { sonusAlarmNodeID, sonusAlarmLevel, 
                      sonusAlarmSequenceId, sonusAlarmTime, 
                      sonusAlarmDescription, sonusSipSigPortIpAddressV6, 
                      sonusSipSigPortNum, sonusSipSigProto }
--     STATUS          mandatory
    DESCRIPTION     
            "This trap indicates that a call signaling port is closed."
    ::= 26

sonusSbxPathCheckRemoteAdminStateUpNotificationV6 TRAP-TYPE
    ENTERPRISE      sonusSipSignallingMIBNotifications
    VARIABLES       { sonusAlarmNodeID, sonusAlarmLevel, 
                      sonusAlarmSequenceId, sonusAlarmTime, 
                      sonusAlarmDescription, sonusPingPeerIpAddressV6, 
                      sonusPingPeerPortNum, sonusPingPeerZoneId }
--     STATUS          deprecated
    DESCRIPTION     
            "This trap is replaced by sonusSbxPathCheckRemoteAdminStateUpNotification2V6"
    ::= 27

sonusSbxPathCheckRemoteAdminStateDownNotificationV6 TRAP-TYPE
    ENTERPRISE      sonusSipSignallingMIBNotifications
    VARIABLES       { sonusAlarmNodeID, sonusAlarmLevel, 
                      sonusAlarmSequenceId, sonusAlarmTime, 
                      sonusAlarmDescription, sonusPingPeerIpAddressV6, 
                      sonusPingPeerPortNum, sonusPingPeerZoneId }
--     STATUS          deprecated
    DESCRIPTION     
            "This trap is replaced by sonusSbxPathCheckRemoteAdminStateDownNotification2V6"
    ::= 28

sonusSbxSurrRegRegistrationSuccessNotificationV6 TRAP-TYPE
    ENTERPRISE      sonusSipSignallingMIBNotifications
    VARIABLES       { sonusAlarmNodeID, sonusAlarmLevel, 
                      sonusAlarmSequenceId, sonusAlarmTime, 
                      sonusAlarmDescription, sonusSurrRegPeerIpAddressV6, 
                      sonusSurrRegPeerPortNum, sonusSurrRegPeerZoneId }
--     STATUS          mandatory
    DESCRIPTION     
            "This trap indicates that the surrogate registration for the peer succeeded"
    ::= 29

sonusSbxSurrRegRegistrationFailedNotificationV6 TRAP-TYPE
    ENTERPRISE      sonusSipSignallingMIBNotifications
    VARIABLES       { sonusAlarmNodeID, sonusAlarmLevel, 
                      sonusAlarmSequenceId, sonusAlarmTime, 
                      sonusAlarmDescription, sonusSurrRegPeerIpAddressV6, 
                      sonusSurrRegPeerPortNum, sonusSurrRegPeerZoneId }
--     STATUS          mandatory
    DESCRIPTION     
            "This trap indicates that the surrogate registration for the peer failed"
    ::= 30

sonusSbxPathCheckFqdnPeerUpNotification TRAP-TYPE
    ENTERPRISE      sonusSipSignallingMIBNotifications
    VARIABLES       { sonusAlarmNodeID, sonusAlarmLevel, 
                      sonusAlarmSequenceId, sonusAlarmTime, 
                      sonusAlarmDescription, sonusPingPeerFqdn, 
                      sonusPingPeerPortNum, sonusPingPeerZoneId }
--     STATUS          deprecated
    DESCRIPTION     
            "This trap is replaced by sonusSbxPathCheckFqdnPeerUpNotification2"
    ::= 31

sonusSbxPathCheckFqdnPeerDownNotification TRAP-TYPE
    ENTERPRISE      sonusSipSignallingMIBNotifications
    VARIABLES       { sonusAlarmNodeID, sonusAlarmLevel, 
                      sonusAlarmSequenceId, sonusAlarmTime, 
                      sonusAlarmDescription, sonusPingPeerFqdn, 
                      sonusPingPeerPortNum, sonusPingPeerZoneId }
--     STATUS          deprecated
    DESCRIPTION     
            "This trap is replaced by sonusSbxPathCheckFqdnPeerDownNotification2"
    ::= 32

sonusSbxPathCheckFqdnPeerIpEndpointUpNotification TRAP-TYPE
    ENTERPRISE      sonusSipSignallingMIBNotifications
    VARIABLES       { sonusAlarmNodeID, sonusAlarmLevel, 
                      sonusAlarmSequenceId, sonusAlarmTime, 
                      sonusAlarmDescription, sonusPingPeerIpAddress, 
                      sonusPingPeerPortNum, sonusPingPeerFqdn, 
                      sonusPingPeerZoneId }
--     STATUS          deprecated
    DESCRIPTION     
            "This trap is replaced by sonusSbxPathCheckFqdnPeerIpEndpointUpNotification2"
    ::= 33

sonusSbxPathCheckFqdnPeerIpEndpointDownNotification TRAP-TYPE
    ENTERPRISE      sonusSipSignallingMIBNotifications
    VARIABLES       { sonusAlarmNodeID, sonusAlarmLevel, 
                      sonusAlarmSequenceId, sonusAlarmTime, 
                      sonusAlarmDescription, sonusPingPeerIpAddress, 
                      sonusPingPeerPortNum, sonusPingPeerFqdn, 
                      sonusPingPeerZoneId }
--     STATUS          deprecated
    DESCRIPTION     
            "This trap is replaced by sonusSbxPathCheckFqdnPeerIpEndpointDownNotification2"
    ::= 34

sonusSbxFailedCertificateReCheck TRAP-TYPE
    ENTERPRISE      sonusSipSignallingMIBNotifications
    VARIABLES       { sonusAlarmNodeID, sonusAlarmLevel, 
                      sonusAlarmSequenceId, sonusAlarmTime, 
                      sonusAlarmDescription, sonusCertReCheckSocketId, 
                      sonusCertReCheckName }
--     STATUS          mandatory
    DESCRIPTION     
            "This trap indicates that certificate recheck for long lived session failed."
    ::= 36

sonusSbxSurrRegAuthenticationFailedNotification TRAP-TYPE
    ENTERPRISE      sonusSipSignallingMIBNotifications
    VARIABLES       { sonusAlarmNodeID, sonusAlarmLevel, 
                      sonusAlarmSequenceId, sonusAlarmTime, 
                      sonusAlarmDescription, sonusSurrRegMethodName, 
                      sonusSurrRegPeerName, sonusSurrRegUserPart, 
                      sonusSurrRegPeerIpAddress, sonusSurrRegPeerPortNum, 
                      sonusSurrRegPeerZoneId }
--     STATUS          mandatory
    DESCRIPTION     
            "This alarm indicates that the authentication failed for surrogate endpoint"
    ::= 37

sonusSbxSurrRegAuthenticationClearNotification TRAP-TYPE
    ENTERPRISE      sonusSipSignallingMIBNotifications
    VARIABLES       { sonusAlarmNodeID, sonusAlarmLevel, 
                      sonusAlarmSequenceId, sonusAlarmTime, 
                      sonusAlarmDescription, sonusSurrRegPeerName, 
                      sonusSurrRegUserPart, sonusSurrRegPeerIpAddress, 
                      sonusSurrRegPeerPortNum, sonusSurrRegPeerZoneId }
--     STATUS          mandatory
    DESCRIPTION     
            "This trap indicates that the surrogate registration for the peer succeeded"
    ::= 38

sonusSbxPathCheckFqdnPeerIpV6EndpointUpNotification TRAP-TYPE
    ENTERPRISE      sonusSipSignallingMIBNotifications
    VARIABLES       { sonusAlarmNodeID, sonusAlarmLevel, 
                      sonusAlarmSequenceId, sonusAlarmTime, 
                      sonusAlarmDescription, sonusPingPeerIpAddressV6, 
                      sonusPingPeerPortNum, sonusPingPeerFqdn, 
                      sonusPingPeerZoneId }
--     STATUS          deprecated
    DESCRIPTION     
            "This trap is replaced by sonusSbxPathCheckFqdnPeerIpV6EndpointUpNotification2"
    ::= 39

sonusSbxPathCheckFqdnPeerIpV6EndpointDownNotification TRAP-TYPE
    ENTERPRISE      sonusSipSignallingMIBNotifications
    VARIABLES       { sonusAlarmNodeID, sonusAlarmLevel, 
                      sonusAlarmSequenceId, sonusAlarmTime, 
                      sonusAlarmDescription, sonusPingPeerIpAddressV6, 
                      sonusPingPeerPortNum, sonusPingPeerFqdn, 
                      sonusPingPeerZoneId }
--     STATUS          deprecated
    DESCRIPTION     
            "This trap is replaced by sonusSbxPathCheckFqdnPeerIpV6EndpointDownNotification2"
    ::= 40

sonusSbxSipRecRecordingFailedNotification TRAP-TYPE
    ENTERPRISE      sonusSipSignallingMIBNotifications
    VARIABLES       { sonusAlarmNodeID, sonusAlarmLevel, 
                      sonusAlarmSequenceId, sonusAlarmTime, 
                      sonusAlarmDescription, sonusRecorderIpAddress, 
                      sonusRecorderPortNum, sonusRecCallGCID, 
                      sonusRecorderTrunkName, sonusRecordingCallLeg }
--     STATUS          mandatory
    DESCRIPTION     
            "This trap indicates that SIPRec recording failed"
    ::= 41

sonusSbxSipRecRecordingFailedNotificationV6 TRAP-TYPE
    ENTERPRISE      sonusSipSignallingMIBNotifications
    VARIABLES       { sonusAlarmNodeID, sonusAlarmLevel, 
                      sonusAlarmSequenceId, sonusAlarmTime, 
                      sonusAlarmDescription, sonusRecorderIpAddressV6, 
                      sonusRecorderPortNum, sonusRecCallGCID, 
                      sonusRecorderTrunkName, sonusRecordingCallLeg }
--     STATUS          mandatory
    DESCRIPTION     
            "This trap indicates that SIPRec recording failed"
    ::= 42

sonusSbxSipSignallingRecordingRejectedServerUnavailable TRAP-TYPE
    ENTERPRISE      sonusSipSignallingMIBNotifications
    VARIABLES       { sonusAlarmNodeID, sonusAlarmLevel, 
                      sonusAlarmSequenceId, sonusAlarmTime, 
                      sonusAlarmDescription, sonusRecorderIpAddress, 
                      sonusRecorderPortNum, sonusRecCallGCID, 
                      sonusRecorderTrunkName, sonusRecordingCallLeg }
--     STATUS          mandatory
    DESCRIPTION     
            "This trap indicates that recording request is rejected due to the unavailability of the recording server"
    ::= 43

sonusSbxSipSignallingRecordingRejectedServerUnavailableV6 TRAP-TYPE
    ENTERPRISE      sonusSipSignallingMIBNotifications
    VARIABLES       { sonusAlarmNodeID, sonusAlarmLevel, 
                      sonusAlarmSequenceId, sonusAlarmTime, 
                      sonusAlarmDescription, sonusRecorderIpAddressV6, 
                      sonusRecorderPortNum, sonusRecCallGCID, 
                      sonusRecorderTrunkName, sonusRecordingCallLeg }
--     STATUS          mandatory
    DESCRIPTION     
            "This trap indicates that recording request is rejected due to the unavailability of the recording server"
    ::= 44

sonusSbxSIPRecLicenseNotAvailable TRAP-TYPE
    ENTERPRISE      sonusSipSignallingMIBNotifications
    VARIABLES       { sonusAlarmNodeID, sonusAlarmLevel, 
                      sonusAlarmSequenceId, sonusAlarmTime, 
                      sonusAlarmDescription }
--     STATUS          mandatory
    DESCRIPTION     
            "The License is not enabled for SIPRec Feature"
    ::= 45

sonusSbxSuppressNonRouteInviteResponseNotification TRAP-TYPE
    ENTERPRISE      sonusSipSignallingMIBNotifications
    VARIABLES       { sonusAlarmNodeID, sonusAlarmLevel, 
                      sonusAlarmSequenceId, sonusAlarmTime, 
                      sonusAlarmDescription, 
                      sonusNonRouteInviteRequestUri, 
                      sonusNonRouteInviteSourceIpAddress, 
                      sonusNonRouteInviteSourceIpPortNum }
--     STATUS          mandatory
    DESCRIPTION     
            "Non-routed incoming invite has been silently dropped."
    ::= 46

sonusSbxTgAuthenticationClearNotification TRAP-TYPE
    ENTERPRISE      sonusSipSignallingMIBNotifications
    VARIABLES       { sonusAlarmNodeID, sonusAlarmLevel, 
                      sonusAlarmSequenceId, sonusAlarmTime, 
                      sonusAlarmDescription, sonusTgTrunkGroupName }
--     STATUS          mandatory
    DESCRIPTION     
            "This trap indicates that IPTG authentication on the trunkgroup succeeded"
    ::= 47

sonusSbxTgAuthenticationFailedNotification TRAP-TYPE
    ENTERPRISE      sonusSipSignallingMIBNotifications
    VARIABLES       { sonusAlarmNodeID, sonusAlarmLevel, 
                      sonusAlarmSequenceId, sonusAlarmTime, 
                      sonusAlarmDescription, sonusTgTrunkGroupName }
--     STATUS          mandatory
    DESCRIPTION     
            "This trap indicates that authentication on the trunkgroup failed"
    ::= 48

sonusSbxDropSipMessageFromUnknownSourceNotification TRAP-TYPE
    ENTERPRISE      sonusSipSignallingMIBNotifications
    VARIABLES       { sonusAlarmNodeID, sonusAlarmLevel, 
                      sonusAlarmSequenceId, sonusAlarmTime, 
                      sonusAlarmDescription, 
                      sonusDropSipMsgFromUnknowSrcAddress, 
                      sonusDropSipMsgFromUnknowSrcMsgType }
--     STATUS          mandatory
    DESCRIPTION     
            "SIP message from unknown source has been silently dropped."
    ::= 49

sonusSbxSipSignalingPortRangeRegistrationFailedNotification TRAP-TYPE
    ENTERPRISE      sonusSipSignallingMIBNotifications
    VARIABLES       { sonusAlarmNodeID, sonusAlarmLevel, 
                      sonusAlarmSequenceId, sonusAlarmTime, 
                      sonusAlarmDescription, sonusAddressContextName, 
                      sonusZoneName, sonusRecorderTrunkName }
--     STATUS          mandatory
    DESCRIPTION     
            "This trap indicates that registration is rejected due to the unavailability of the ports."
    ::= 50

sonusSbxIceStunMsgValidationFailNotification TRAP-TYPE
    ENTERPRISE      sonusSipSignallingMIBNotifications
    VARIABLES       { sonusAlarmNodeID, sonusAlarmLevel, 
                      sonusAlarmSequenceId, sonusAlarmTime, 
                      sonusAlarmDescription, sonusSipIceGcid, 
                      sonusSipIceRemoteIpAddress, sonusSipIceRemotePort, 
                      sonusSipIceLocalIpAddress, sonusSipIceLocalPort, 
                      sonusSipIceFailReason }
--     STATUS          mandatory
    DESCRIPTION     
            "This trap indicates that validation has failed for the first
             STUN messages for that call leg, indicating failure reason"
    ::= 51

sonusSbxDialogTransparencyMisConfiguredNotification TRAP-TYPE
    ENTERPRISE      sonusSipSignallingMIBNotifications
    VARIABLES       { sonusAlarmNodeID, sonusAlarmLevel, 
                      sonusAlarmSequenceId, sonusAlarmTime, 
                      sonusAlarmDescription, sonusZoneName }
--     STATUS          mandatory
    DESCRIPTION     
            "This Trap is generated when one of ingress or egress dialog transparency flag is enabled and not both."
    ::= 52

sonusSbxSubscriptionToRegEventPackageFailedNotification TRAP-TYPE
    ENTERPRISE      sonusSipSignallingMIBNotifications
    VARIABLES       { sonusAlarmNodeID, sonusAlarmLevel, 
                      sonusAlarmSequenceId, sonusAlarmTime, 
                      sonusAlarmDescription, sonusSubscriptionId }
--     STATUS          mandatory
    DESCRIPTION     
            "This trap indicates that the subscription to reg-event package failed"
    ::= 53

sonusEmergencyMessageRejectedNotification TRAP-TYPE
    ENTERPRISE      sonusSipSignallingMIBNotifications
    VARIABLES       { sonusAlarmNodeID, sonusAlarmLevel, 
                      sonusAlarmSequenceId, sonusAlarmTime, 
                      sonusAlarmDescription, 
                      sonusEmergencyMessageRejected, sonusRPHNamespace, 
                      sonusRPHPriority, sonusPrefixedNumber, 
                      sonusZoneIdName, sonusTrunkGroupName, 
                      sonusPolicerName }
--     STATUS          obsolete
    DESCRIPTION     
            "This trap indicates that Non-Invite OOD emergency message is rejected"
    ::= 54

sonusSbxIceTimerExpiryNotification TRAP-TYPE
    ENTERPRISE      sonusSipSignallingMIBNotifications
    VARIABLES       { sonusAlarmNodeID, sonusAlarmLevel, 
                      sonusAlarmSequenceId, sonusAlarmTime, 
                      sonusAlarmDescription, sonusSipIceGcid, 
                      sonusSipIceLocalIpAddress, sonusSipIceLocalPort, 
                      sonusSipIceFailReason }
--     STATUS          mandatory
    DESCRIPTION     
            "This trap indicates that timer expired for waiting stun request/response
             for that call leg, indicating failure reason"
    ::= 55

sonusSbxIceStunMsgValidationFailNotificationV6 TRAP-TYPE
    ENTERPRISE      sonusSipSignallingMIBNotifications
    VARIABLES       { sonusAlarmNodeID, sonusAlarmLevel, 
                      sonusAlarmSequenceId, sonusAlarmTime, 
                      sonusAlarmDescription, sonusSipIceGcid, 
                      sonusSipIceRemoteIpV6Address, 
                      sonusSipIceRemotePort, sonusSipIceLocalIpV6Address, 
                      sonusSipIceLocalPort, sonusSipIceFailReason }
--     STATUS          mandatory
    DESCRIPTION     
            "This trap indicates that validation has failed for the first
             STUN messages for that call leg, indicating failure reason"
    ::= 56

sonusSbxIceTimerExpiryNotificationV6 TRAP-TYPE
    ENTERPRISE      sonusSipSignallingMIBNotifications
    VARIABLES       { sonusAlarmNodeID, sonusAlarmLevel, 
                      sonusAlarmSequenceId, sonusAlarmTime, 
                      sonusAlarmDescription, sonusSipIceGcid, 
                      sonusSipIceLocalIpV6Address, sonusSipIceLocalPort, 
                      sonusSipIceFailReason }
--     STATUS          mandatory
    DESCRIPTION     
            "This trap indicates that timer expired for waiting stun request/response
             for that call leg, indicating failure reason"
    ::= 57

sonusEmergencyMessageRejectNotification TRAP-TYPE
    ENTERPRISE      sonusSipSignallingMIBNotifications
    VARIABLES       { sonusAlarmNodeID, sonusAlarmLevel, 
                      sonusAlarmSequenceId, sonusAlarmTime, 
                      sonusAlarmDescription, 
                      sonusEmergencyMessageRejected, sonusRPHNamespace, 
                      sonusRPHPriority, sonusPrefixedNumber, 
                      sonusZoneIdName, sonusTrunkGroupName, 
                      sonusPolicerName }
--     STATUS          mandatory
    DESCRIPTION     
            "This trap indicates that Non-Invite OOD emergency message is rejected"
    ::= 58

sonusSbxSipRecSrsSelectionFailedNotification TRAP-TYPE
    ENTERPRISE      sonusSipSignallingMIBNotifications
    VARIABLES       { sonusAlarmNodeID, sonusAlarmLevel, 
                      sonusAlarmSequenceId, sonusAlarmTime, 
                      sonusAlarmDescription, sonusRecCallGCID, 
                      sonusRecorderTrunkName, sonusRecordingCallLeg, 
                      sonusRecNumStreamsConfigured, 
                      sonusRecInitFailureReason }
--     STATUS          mandatory
    DESCRIPTION     
            "This trap indicates that SIPRec recording initiation failed"
    ::= 59

sonusSbxSiprecLicenseUnavailableNotification TRAP-TYPE
    ENTERPRISE      sonusSipSignallingMIBNotifications
    VARIABLES       { sonusAlarmNodeID, sonusAlarmLevel, 
                      sonusAlarmSequenceId, sonusAlarmTime, 
                      sonusAlarmDescription, sonusRecorderIpAddress, 
                      sonusRecorderPortNum, sonusRecCallGCID, 
                      sonusRecorderTrunkName, sonusRecordingCallLeg }
--     STATUS          mandatory
    DESCRIPTION     
            "This trap indicates that SIPRec recording failed due to lack of license"
    ::= 60

sonusSbxPDCSLicenseUnavailableNotification TRAP-TYPE
    ENTERPRISE      sonusSipSignallingMIBNotifications
    VARIABLES       { sonusAlarmNodeID, sonusAlarmLevel, 
                      sonusAlarmSequenceId, sonusAlarmTime, 
                      sonusAlarmDescription, sonusRecCallGCID }
--     STATUS          mandatory
    DESCRIPTION     
            "This trap indicates that PDCS header interception failed due to lack of license"
    ::= 61

sonusSbxSipSmMonServerTcpConnFailureNotification TRAP-TYPE
    ENTERPRISE      sonusSipSignallingMIBNotifications
    VARIABLES       { sonusAlarmNodeID, sonusAlarmLevel, 
                      sonusAlarmSequenceId, sonusAlarmTime, 
                      sonusAlarmDescription, sonusMonIpAddress, 
                      sonusMonPortNum }
--     STATUS          mandatory
    DESCRIPTION     
            "This trap indicates that TCP connection towards monitoring server failed"
    ::= 62

sonusSbxSipSmMonServerTcpConnFailureNotificationV6 TRAP-TYPE
    ENTERPRISE      sonusSipSignallingMIBNotifications
    VARIABLES       { sonusAlarmNodeID, sonusAlarmLevel, 
                      sonusAlarmSequenceId, sonusAlarmTime, 
                      sonusAlarmDescription, sonusMonIpAddressV6, 
                      sonusMonPortNum }
--     STATUS          mandatory
    DESCRIPTION     
            "This trap indicates that TCP connection towards monitoring server failed"
    ::= 63

sonusSbxLocalSurvivabilityModeActiveNotification TRAP-TYPE
    ENTERPRISE      sonusSipSignallingMIBNotifications
    VARIABLES       { sonusAlarmNodeID, sonusAlarmLevel, 
                      sonusAlarmSequenceId, sonusAlarmTime, 
                      sonusAlarmDescription, 
                      sonusSipArsStatEndpointIpAddress, 
                      sonusSipArsStatEndpointIpPortNum, 
                      sonusSipArsStatSigZoneId, 
                      sonusSipArsStatSigPortNum }
--     STATUS          mandatory
    DESCRIPTION     
            "This trap indicates that local survivability mode is active for a SIP server 
             of the specified ip address, port, sig zone"
    ::= 64

sonusSbxLocalSurvivabilityModeActiveNotificationV6 TRAP-TYPE
    ENTERPRISE      sonusSipSignallingMIBNotifications
    VARIABLES       { sonusAlarmNodeID, sonusAlarmLevel, 
                      sonusAlarmSequenceId, sonusAlarmTime, 
                      sonusAlarmDescription, 
                      sonusSipArsStatEndpointIpAddressV6, 
                      sonusSipArsStatEndpointIpPortNum, 
                      sonusSipArsStatSigZoneId, 
                      sonusSipArsStatSigPortNum }
--     STATUS          mandatory
    DESCRIPTION     
            "This trap indicates that local survivability mode is active for a SIP server 
             of the specified V6 ip address, port, sig zone"
    ::= 65

sonusSbxLocalSurvivabilityModeClearNotification TRAP-TYPE
    ENTERPRISE      sonusSipSignallingMIBNotifications
    VARIABLES       { sonusAlarmNodeID, sonusAlarmLevel, 
                      sonusAlarmSequenceId, sonusAlarmTime, 
                      sonusAlarmDescription, 
                      sonusSipArsStatEndpointIpAddress, 
                      sonusSipArsStatEndpointIpPortNum, 
                      sonusSipArsStatSigZoneId, 
                      sonusSipArsStatSigPortNum }
--     STATUS          mandatory
    DESCRIPTION     
            "This trap indicates that local survivability mode is cleared for a SIP server 
             of the specified ip address, port, sig zone"
    ::= 66

sonusSbxLocalSurvivabilityModeClearNotificationV6 TRAP-TYPE
    ENTERPRISE      sonusSipSignallingMIBNotifications
    VARIABLES       { sonusAlarmNodeID, sonusAlarmLevel, 
                      sonusAlarmSequenceId, sonusAlarmTime, 
                      sonusAlarmDescription, 
                      sonusSipArsStatEndpointIpAddressV6, 
                      sonusSipArsStatEndpointIpPortNum, 
                      sonusSipArsStatSigZoneId, 
                      sonusSipArsStatSigPortNum }
--     STATUS          mandatory
    DESCRIPTION     
            "This trap indicates that local survivability mode is cleared for a SIP server 
             of the specified V6 ip address, port, sig zone"
    ::= 67

sonusSbxSipSmDropLargeSipPduOverUdpNotification TRAP-TYPE
    ENTERPRISE      sonusSipSignallingMIBNotifications
    VARIABLES       { sonusAlarmNodeID, sonusAlarmLevel, 
                      sonusAlarmSequenceId, sonusAlarmTime, 
                      sonusAlarmDescription, sonusMonIpAddress, 
                      sonusMonPortNum }
--     STATUS          mandatory
    DESCRIPTION     
            "This trap indicates that we drop large sip pdu over UDP."
    ::= 68

sonusSbxSipSmDropLargeSipPduOverUdpNotificationV6 TRAP-TYPE
    ENTERPRISE      sonusSipSignallingMIBNotifications
    VARIABLES       { sonusAlarmNodeID, sonusAlarmLevel, 
                      sonusAlarmSequenceId, sonusAlarmTime, 
                      sonusAlarmDescription, sonusMonIpAddressV6, 
                      sonusMonPortNum }
--     STATUS          mandatory
    DESCRIPTION     
            "This trap indicates that we drop large sip pdu over UDP."
    ::= 69

sonusSbxLbsLocalNodeIsLeaderLackOfCommuncationNotification TRAP-TYPE
    ENTERPRISE      sonusSipSignallingMIBNotifications
    VARIABLES       { sonusAlarmNodeID, sonusAlarmLevel, 
                      sonusAlarmSequenceId, sonusAlarmTime, 
                      sonusAlarmDescription, sonusMsbcIpAddress }
--     STATUS          mandatory
    DESCRIPTION     
            "This trap indicates that Local Node Elected as Leader due to lack of communication with other instances in a cluster."
    ::= 70

sonusSbxLbsLocalNodeIsLeaderLackOfCommuncationNotificationV6 TRAP-TYPE
    ENTERPRISE      sonusSipSignallingMIBNotifications
    VARIABLES       { sonusAlarmNodeID, sonusAlarmLevel, 
                      sonusAlarmSequenceId, sonusAlarmTime, 
                      sonusAlarmDescription, sonusMsbcIpAddressV6 }
--     STATUS          mandatory
    DESCRIPTION     
            "This trap indicates that Local Node Elected as Leader due to lack of communication with other instances in a cluster."
    ::= 71

sonusSbxArsEndPointBlacklistedNotification2 TRAP-TYPE
    ENTERPRISE      sonusSipSignallingMIBNotifications
    VARIABLES       { sonusAlarmNodeID, sonusAlarmLevel, 
                      sonusAlarmSequenceId, sonusAlarmTime, 
                      sonusAlarmDescription, 
                      sonusSipArsStatEndpointIpAddress, 
                      sonusSipArsStatEndpointIpPortNum, 
                      sonusSipArsStatSigZoneId, 
                      sonusSipArsStatSigPortNum, 
                      sonusSipArsStatEndpointOwnerId, 
                      sonusSipArsStatSigZoneName }
--     STATUS          mandatory
    DESCRIPTION     
            "This trap indicates that  one SIP endpoint of the
             specified ip address, port, sig zone has been blacklisted
             by the ARS service. This indicates the endpoint is unreachable"
    ::= 72

sonusSbxArsEndPointRecoveredNotification2 TRAP-TYPE
    ENTERPRISE      sonusSipSignallingMIBNotifications
    VARIABLES       { sonusAlarmNodeID, sonusAlarmLevel, 
                      sonusAlarmSequenceId, sonusAlarmTime, 
                      sonusAlarmDescription, 
                      sonusSipArsStatEndpointIpAddress, 
                      sonusSipArsStatEndpointIpPortNum, 
                      sonusSipArsStatSigZoneId, 
                      sonusSipArsStatSigPortNum, 
                      sonusSipArsStatEndpointOwnerId, 
                      sonusSipArsStatSigZoneName }
--     STATUS          mandatory
    DESCRIPTION     
            "This trap indicates that  one SIP endpoint of the specified ip address,
             port, sig zone has been recovered from  blacklisting by the ARS service.
             This indicates the endpoint is now reachable"
    ::= 73

sonusSbxArsEndPointsRecoveredNotification2 TRAP-TYPE
    ENTERPRISE      sonusSipSignallingMIBNotifications
    VARIABLES       { sonusAlarmNodeID, sonusAlarmLevel, 
                      sonusAlarmSequenceId, sonusAlarmTime, 
                      sonusAlarmDescription, sonusSipArsStatSigZoneId, 
                      sonusSipArsEndpointRecoveryAll, 
                      sonusSipArsStatSigZoneName }
--     STATUS          mandatory
    DESCRIPTION     
            "This trap indicates that  all SIP endpoints in the specified zone,
             OR all the zones has been recovered from  blacklisting by the ARS service.
             This indicates these endpoints are  now reachable"
    ::= 74

sonusSbxArsEndPointBlacklistedNotification2V6 TRAP-TYPE
    ENTERPRISE      sonusSipSignallingMIBNotifications
    VARIABLES       { sonusAlarmNodeID, sonusAlarmLevel, 
                      sonusAlarmSequenceId, sonusAlarmTime, 
                      sonusAlarmDescription, 
                      sonusSipArsStatEndpointIpAddressV6, 
                      sonusSipArsStatEndpointIpPortNum, 
                      sonusSipArsStatSigZoneId, 
                      sonusSipArsStatSigPortNum, 
                      sonusSipArsStatEndpointOwnerId, 
                      sonusSipArsStatSigZoneName }
--     STATUS          mandatory
    DESCRIPTION     
            "This trap indicates that  one SIP endpoint of the
             specified ip address, port, sig zone has been blacklisted
             by the ARS service. This indicates the endpoint is unreachable"
    ::= 75

sonusSbxArsEndPointRecoveredNotification2V6 TRAP-TYPE
    ENTERPRISE      sonusSipSignallingMIBNotifications
    VARIABLES       { sonusAlarmNodeID, sonusAlarmLevel, 
                      sonusAlarmSequenceId, sonusAlarmTime, 
                      sonusAlarmDescription, 
                      sonusSipArsStatEndpointIpAddressV6, 
                      sonusSipArsStatEndpointIpPortNum, 
                      sonusSipArsStatSigZoneId, 
                      sonusSipArsStatSigPortNum, 
                      sonusSipArsStatEndpointOwnerId, 
                      sonusSipArsStatSigZoneName }
--     STATUS          mandatory
    DESCRIPTION     
            "This trap indicates that  one SIP endpoint of the specified ip address,
             port, sig zone has been recovered from  blacklisting by the ARS service.
             This indicates the endpoint is now reachable"
    ::= 76

sonusSbxPathCheckPingStateUpNotification2 TRAP-TYPE
    ENTERPRISE      sonusSipSignallingMIBNotifications
    VARIABLES       { sonusAlarmNodeID, sonusAlarmLevel, 
                      sonusAlarmSequenceId, sonusAlarmTime, 
                      sonusAlarmDescription, sonusPingPeerIpAddress, 
                      sonusPingPeerPortNum, sonusPingPeerZoneId, 
                      sonusPingPeerZoneName, sonusPingPeerName }
--     STATUS          mandatory
    DESCRIPTION     
            "This trap indicates that the peer's ping state is up."
    ::= 77

sonusSbxPathCheckPingStateDownNotification2 TRAP-TYPE
    ENTERPRISE      sonusSipSignallingMIBNotifications
    VARIABLES       { sonusAlarmNodeID, sonusAlarmLevel, 
                      sonusAlarmSequenceId, sonusAlarmTime, 
                      sonusAlarmDescription, sonusPingPeerIpAddress, 
                      sonusPingPeerPortNum, sonusPingPeerZoneId, 
                      sonusPingPeerZoneName, sonusPingPeerName }
--     STATUS          mandatory
    DESCRIPTION     
            "This trap indicates that the peer's ping state is down."
    ::= 78

sonusSbxPathCheckRemoteAdminStateUpNotification2 TRAP-TYPE
    ENTERPRISE      sonusSipSignallingMIBNotifications
    VARIABLES       { sonusAlarmNodeID, sonusAlarmLevel, 
                      sonusAlarmSequenceId, sonusAlarmTime, 
                      sonusAlarmDescription, sonusPingPeerIpAddress, 
                      sonusPingPeerPortNum, sonusPingPeerZoneId, 
                      sonusPingPeerZoneName, sonusPingPeerName }
--     STATUS          mandatory
    DESCRIPTION     
            "This trap indicates that the peer's remote admin state is up."
    ::= 79

sonusSbxPathCheckRemoteAdminStateDownNotification2 TRAP-TYPE
    ENTERPRISE      sonusSipSignallingMIBNotifications
    VARIABLES       { sonusAlarmNodeID, sonusAlarmLevel, 
                      sonusAlarmSequenceId, sonusAlarmTime, 
                      sonusAlarmDescription, sonusPingPeerIpAddress, 
                      sonusPingPeerPortNum, sonusPingPeerZoneId, 
                      sonusPingPeerZoneName, sonusPingPeerName }
--     STATUS          mandatory
    DESCRIPTION     
            "This trap indicates that the peer's remote admin state is down."
    ::= 80

sonusSbxPathCheckLocalAdminStateUpNotification2 TRAP-TYPE
    ENTERPRISE      sonusSipSignallingMIBNotifications
    VARIABLES       { sonusAlarmNodeID, sonusAlarmLevel, 
                      sonusAlarmSequenceId, sonusAlarmTime, 
                      sonusAlarmDescription, sonusPingPeerIpAddress, 
                      sonusPingPeerPortNum, sonusPingPeerZoneId, 
                      sonusPingPeerZoneName, sonusPingPeerName }
--     STATUS          mandatory
    DESCRIPTION     
            "This trap indicates that the peer's local admin state is up."
    ::= 81

sonusSbxPathCheckLocalAdminStateDownNotification2 TRAP-TYPE
    ENTERPRISE      sonusSipSignallingMIBNotifications
    VARIABLES       { sonusAlarmNodeID, sonusAlarmLevel, 
                      sonusAlarmSequenceId, sonusAlarmTime, 
                      sonusAlarmDescription, sonusPingPeerIpAddress, 
                      sonusPingPeerPortNum, sonusPingPeerZoneId, 
                      sonusPingPeerZoneName, sonusPingPeerName }
--     STATUS          mandatory
    DESCRIPTION     
            "This trap indicates that the peer's local admin state is down."
    ::= 82

sonusSbxPathCheckLocalAdminStateUpNotification2V6 TRAP-TYPE
    ENTERPRISE      sonusSipSignallingMIBNotifications
    VARIABLES       { sonusAlarmNodeID, sonusAlarmLevel, 
                      sonusAlarmSequenceId, sonusAlarmTime, 
                      sonusAlarmDescription, sonusPingPeerIpAddressV6, 
                      sonusPingPeerPortNum, sonusPingPeerZoneId, 
                      sonusPingPeerZoneName, sonusPingPeerName }
--     STATUS          mandatory
    DESCRIPTION     
            "This trap indicates that the peer's local admin state is up."
    ::= 83

sonusSbxPathCheckLocalAdminStateDownNotification2V6 TRAP-TYPE
    ENTERPRISE      sonusSipSignallingMIBNotifications
    VARIABLES       { sonusAlarmNodeID, sonusAlarmLevel, 
                      sonusAlarmSequenceId, sonusAlarmTime, 
                      sonusAlarmDescription, sonusPingPeerIpAddressV6, 
                      sonusPingPeerPortNum, sonusPingPeerZoneId, 
                      sonusPingPeerZoneName, sonusPingPeerName }
--     STATUS          mandatory
    DESCRIPTION     
            "This trap indicates that the peer's local admin state is down."
    ::= 84

sonusSbxPathCheckPingStateUpNotification2V6 TRAP-TYPE
    ENTERPRISE      sonusSipSignallingMIBNotifications
    VARIABLES       { sonusAlarmNodeID, sonusAlarmLevel, 
                      sonusAlarmSequenceId, sonusAlarmTime, 
                      sonusAlarmDescription, sonusPingPeerIpAddressV6, 
                      sonusPingPeerPortNum, sonusPingPeerZoneId, 
                      sonusPingPeerZoneName, sonusPingPeerName }
--     STATUS          mandatory
    DESCRIPTION     
            "This trap indicates that the peer's ping state is up."
    ::= 85

sonusSbxPathCheckPingStateDownNotification2V6 TRAP-TYPE
    ENTERPRISE      sonusSipSignallingMIBNotifications
    VARIABLES       { sonusAlarmNodeID, sonusAlarmLevel, 
                      sonusAlarmSequenceId, sonusAlarmTime, 
                      sonusAlarmDescription, sonusPingPeerIpAddressV6, 
                      sonusPingPeerPortNum, sonusPingPeerZoneId, 
                      sonusPingPeerZoneName, sonusPingPeerName }
--     STATUS          mandatory
    DESCRIPTION     
            "This trap indicates that the peer's ping state is down."
    ::= 86

sonusSbxPathCheckRemoteAdminStateUpNotification2V6 TRAP-TYPE
    ENTERPRISE      sonusSipSignallingMIBNotifications
    VARIABLES       { sonusAlarmNodeID, sonusAlarmLevel, 
                      sonusAlarmSequenceId, sonusAlarmTime, 
                      sonusAlarmDescription, sonusPingPeerIpAddressV6, 
                      sonusPingPeerPortNum, sonusPingPeerZoneId, 
                      sonusPingPeerZoneName, sonusPingPeerName }
--     STATUS          mandatory
    DESCRIPTION     
            "This trap indicates that the peer's remote admin state is up."
    ::= 87

sonusSbxPathCheckRemoteAdminStateDownNotification2V6 TRAP-TYPE
    ENTERPRISE      sonusSipSignallingMIBNotifications
    VARIABLES       { sonusAlarmNodeID, sonusAlarmLevel, 
                      sonusAlarmSequenceId, sonusAlarmTime, 
                      sonusAlarmDescription, sonusPingPeerIpAddressV6, 
                      sonusPingPeerPortNum, sonusPingPeerZoneId, 
                      sonusPingPeerZoneName, sonusPingPeerName }
--     STATUS          mandatory
    DESCRIPTION     
            "This trap indicates that the peer's remote admin state is down."
    ::= 88

sonusSbxPathCheckFqdnPeerUpNotification2 TRAP-TYPE
    ENTERPRISE      sonusSipSignallingMIBNotifications
    VARIABLES       { sonusAlarmNodeID, sonusAlarmLevel, 
                      sonusAlarmSequenceId, sonusAlarmTime, 
                      sonusAlarmDescription, sonusPingPeerFqdn, 
                      sonusPingPeerPortNum, sonusPingPeerZoneId, 
                      sonusPingPeerZoneName, sonusPingPeerName }
--     STATUS          mandatory
    DESCRIPTION     
            "This trap indicates that the specified SIP peer is available to receive calls."
    ::= 89

sonusSbxPathCheckFqdnPeerDownNotification2 TRAP-TYPE
    ENTERPRISE      sonusSipSignallingMIBNotifications
    VARIABLES       { sonusAlarmNodeID, sonusAlarmLevel, 
                      sonusAlarmSequenceId, sonusAlarmTime, 
                      sonusAlarmDescription, sonusPingPeerFqdn, 
                      sonusPingPeerPortNum, sonusPingPeerZoneId, 
                      sonusPingPeerZoneName, sonusPingPeerName }
--     STATUS          mandatory
    DESCRIPTION     
            "This trap indicates that the specified SIP peer is unavailable to receive calls."
    ::= 90

sonusSbxPathCheckFqdnPeerIpEndpointUpNotification2 TRAP-TYPE
    ENTERPRISE      sonusSipSignallingMIBNotifications
    VARIABLES       { sonusAlarmNodeID, sonusAlarmLevel, 
                      sonusAlarmSequenceId, sonusAlarmTime, 
                      sonusAlarmDescription, sonusPingPeerIpAddress, 
                      sonusPingPeerPortNum, sonusPingPeerFqdn, 
                      sonusPingPeerZoneId, sonusPingPeerZoneName, 
                      sonusPingPeerName }
--     STATUS          mandatory
    DESCRIPTION     
            "This trap indicates that the specified IP end-point belonging to the SIP Peer is 
             available to receive calls."
    ::= 91

sonusSbxPathCheckFqdnPeerIpEndpointDownNotification2 TRAP-TYPE
    ENTERPRISE      sonusSipSignallingMIBNotifications
    VARIABLES       { sonusAlarmNodeID, sonusAlarmLevel, 
                      sonusAlarmSequenceId, sonusAlarmTime, 
                      sonusAlarmDescription, sonusPingPeerIpAddress, 
                      sonusPingPeerPortNum, sonusPingPeerFqdn, 
                      sonusPingPeerZoneId, sonusPingPeerZoneName, 
                      sonusPingPeerName }
--     STATUS          mandatory
    DESCRIPTION     
            "This trap indicates that the specified IP end-point belonging to the SIP Peer is 
             unavailable to receive calls."
    ::= 92

sonusSbxPathCheckFqdnPeerIpV6EndpointUpNotification2 TRAP-TYPE
    ENTERPRISE      sonusSipSignallingMIBNotifications
    VARIABLES       { sonusAlarmNodeID, sonusAlarmLevel, 
                      sonusAlarmSequenceId, sonusAlarmTime, 
                      sonusAlarmDescription, sonusPingPeerIpAddressV6, 
                      sonusPingPeerPortNum, sonusPingPeerFqdn, 
                      sonusPingPeerZoneId, sonusPingPeerZoneName, 
                      sonusPingPeerName }
--     STATUS          mandatory
    DESCRIPTION     
            "This trap indicates that the specified IPV6 end-point belonging to the SIP Peer is 
             available to receive calls."
    ::= 93

sonusSbxPathCheckFqdnPeerIpV6EndpointDownNotification2 TRAP-TYPE
    ENTERPRISE      sonusSipSignallingMIBNotifications
    VARIABLES       { sonusAlarmNodeID, sonusAlarmLevel, 
                      sonusAlarmSequenceId, sonusAlarmTime, 
                      sonusAlarmDescription, sonusPingPeerIpAddressV6, 
                      sonusPingPeerPortNum, sonusPingPeerFqdn, 
                      sonusPingPeerZoneId, sonusPingPeerZoneName, 
                      sonusPingPeerName }
--     STATUS          mandatory
    DESCRIPTION     
            "This trap indicates that the specified IPV6 end-point belonging to the SIP Peer is 
             unavailable to receive calls."
    ::= 94

sonusSbxH323TrunkGroupInServiceNotification TRAP-TYPE
    ENTERPRISE      sonusH323SignallingMIBNotifications
    VARIABLES       { sonusAlarmNodeID, sonusAlarmLevel, 
                      sonusAlarmSequenceId, sonusAlarmTime, 
                      sonusAlarmDescription, sonusH323TrunkGrpName }
--     STATUS          mandatory
    DESCRIPTION     
            "This trap indicates that the H323 Trunk Group was put
             into service by maintenance staff."
    ::= 1

sonusSbxH323TrunkGroupOutOfServiceNotification TRAP-TYPE
    ENTERPRISE      sonusH323SignallingMIBNotifications
    VARIABLES       { sonusAlarmNodeID, sonusAlarmLevel, 
                      sonusAlarmSequenceId, sonusAlarmTime, 
                      sonusAlarmDescription, sonusH323TrunkGrpName }
--     STATUS          mandatory
    DESCRIPTION     
            "This trap indicates that the H323 Trunk Group was taken
             out of service by maintenance staff."
    ::= 2

sonusSbxSscsRouteFailureWithoutGapNotification TRAP-TYPE
    ENTERPRISE      sonusSoftswitchClientServicesMIBNotifications
    VARIABLES       { sonusAlarmNodeID, sonusAlarmLevel, 
                      sonusAlarmSequenceId, sonusAlarmTime, 
                      sonusAlarmDescription, sonusH323TrunkGrpName, 
                      sonusPscsPolicyServerName, 
                      sonusPscsRouteFailureReason, sonusPscsCalledNumber, 
                      sonusPscsCallingNumber, sonusPscsCarrierCode }
--     STATUS          deprecated
    DESCRIPTION     
            "This trap has been replaced by sonusSbxSscsRouteFailureWithoutGapNotification2."
    ::= 1

sonusSbxSscsRouteFailureNotification TRAP-TYPE
    ENTERPRISE      sonusSoftswitchClientServicesMIBNotifications
    VARIABLES       { sonusAlarmNodeID, sonusAlarmLevel, 
                      sonusAlarmSequenceId, sonusAlarmTime, 
                      sonusAlarmDescription, sonusPscsPolicyServerName, 
                      sonusPscsRouteFailureReason, sonusPscsCalledNumber, 
                      sonusPscsCallingNumber, sonusPscsCarrierCode, 
                      sonusPscsGapNumber }
--     STATUS          mandatory
    DESCRIPTION     
            "This trap indicates a route look up has failed."
    ::= 2

sonusSbxSscsTransErrorNotification TRAP-TYPE
    ENTERPRISE      sonusSoftswitchClientServicesMIBNotifications
    VARIABLES       { sonusAlarmNodeID, sonusAlarmLevel, 
                      sonusAlarmSequenceId, sonusAlarmTime, 
                      sonusAlarmDescription, sonusPscsPolicyServerName, 
                      sonusPscsTranErrorReason }
--     STATUS          mandatory
    DESCRIPTION     
            "This trap indicates a softswitch has a transaction error."
    ::= 3

sonusSbxSscsRejectIndNotification TRAP-TYPE
    ENTERPRISE      sonusSoftswitchClientServicesMIBNotifications
    VARIABLES       { sonusAlarmNodeID, sonusAlarmLevel, 
                      sonusAlarmSequenceId, sonusAlarmTime, 
                      sonusAlarmDescription, sonusPscsPolicyServerName, 
                      sonusPscsRejectIndReason }
--     STATUS          mandatory
    DESCRIPTION     
            "This trap indicates a reject indication has been received."
    ::= 4

sonusSbxSscsOutOfServiceNotification TRAP-TYPE
    ENTERPRISE      sonusSoftswitchClientServicesMIBNotifications
    VARIABLES       { sonusAlarmNodeID, sonusAlarmLevel, 
                      sonusAlarmSequenceId, sonusAlarmTime, 
                      sonusAlarmDescription, sonusPscsPolicyServerName, 
                      sonusPscsOutOfServiceReason }
--     STATUS          mandatory
    DESCRIPTION     
            "This trap indicates a softswitch is now out of service."
    ::= 5

sonusSbxSscsInServiceNotification TRAP-TYPE
    ENTERPRISE      sonusSoftswitchClientServicesMIBNotifications
    VARIABLES       { sonusAlarmNodeID, sonusAlarmLevel, 
                      sonusAlarmSequenceId, sonusAlarmTime, 
                      sonusAlarmDescription, sonusPscsPolicyServerName, 
                      sonusPscsOperState, sonusPscsInServiceReason }
--     STATUS          mandatory
    DESCRIPTION     
            "This trap indicates a softswitch is now in service"
    ::= 6

sonusSbxSscsRouteFailureWithoutGapNotification2 TRAP-TYPE
    ENTERPRISE      sonusSoftswitchClientServicesMIBNotifications
    VARIABLES       { sonusAlarmNodeID, sonusAlarmLevel, 
                      sonusAlarmSequenceId, sonusAlarmTime, 
                      sonusAlarmDescription, sonusPscsPolicyServerName, 
                      sonusPscsRouteFailureReason, sonusPscsCalledNumber, 
                      sonusPscsCallingNumber, sonusPscsCarrierCode }
--     STATUS          mandatory
    DESCRIPTION     
            "This trap indicates a route look up has failed with out GAP."
    ::= 7

sonusSbxNodeResourcesCallAdmissionSuspendedNotification TRAP-TYPE
    ENTERPRISE      sonusNodeResourcesMIBNotifications
    VARIABLES       { sonusAlarmNodeID, sonusAlarmLevel, 
                      sonusAlarmSequenceId, sonusAlarmTime, 
                      sonusAlarmDescription, 
                      sonusCallAdmissionChangeReason }
--     STATUS          mandatory
    DESCRIPTION     
            "This trap indicates that call admission into the SBC has been
             suspended. Information provided by this trap includes the reason
             why call admission has been suspended."
    ::= 1

sonusSbxNodeResourcesCallAdmissionEnabledNotification TRAP-TYPE
    ENTERPRISE      sonusNodeResourcesMIBNotifications
    VARIABLES       { sonusAlarmNodeID, sonusAlarmLevel, 
                      sonusAlarmSequenceId, sonusAlarmTime, 
                      sonusAlarmDescription, 
                      sonusCallAdmissionChangeReason }
--     STATUS          mandatory
    DESCRIPTION     
            "This trap indicates that call admission into the SBC has been
             enabled. Information provided by this trap includes the reason
             why call admission has been enabled."
    ::= 2

sonusSbxNodeResourcesCallTraceHitNotification TRAP-TYPE
    ENTERPRISE      sonusNodeResourcesMIBNotifications
    VARIABLES       { sonusAlarmNodeID, sonusAlarmLevel, 
                      sonusAlarmSequenceId, sonusAlarmTime, 
                      sonusAlarmDescription, sonusCallTraceCalledNumber, 
                      sonusCallTraceCallingNumber }
--     STATUS          mandatory
    DESCRIPTION     
            "This trap indicates that call trace filter had a hit.
             Information provided by this trap includes the called number
             and the calling number."
    ::= 3

sonusSbxNodeResourcesCallTraceHitGAPNotification TRAP-TYPE
    ENTERPRISE      sonusNodeResourcesMIBNotifications
    VARIABLES       { sonusAlarmNodeID, sonusAlarmLevel, 
                      sonusAlarmSequenceId, sonusAlarmTime, 
                      sonusAlarmDescription, sonusCallTraceCalledNumber, 
                      sonusCallTraceCallingNumber, 
                      sonusActiveCallOrigCalledNum }
--     STATUS          mandatory
    DESCRIPTION     
            "This trap indicates that call trace filter had a hit.
             Information provided by this trap includes the called number,
             the calling number, and the original called number (in GAP)."
    ::= 4

sonusSbxNodeResEmerCallNoRouteNotification TRAP-TYPE
    ENTERPRISE      sonusNodeResourcesMIBNotifications
    VARIABLES       { sonusAlarmNodeID, sonusAlarmLevel, 
                      sonusAlarmSequenceId, sonusAlarmTime, 
                      sonusAlarmDescription, 
                      sonusActiveCallIngressPstnTrunk, 
                      sonusNodeResourceIsupCircuit, 
                      sonusActiveCallCallingNum, 
                      sonusActiveCallCalledNum, 
                      sonusActiveCallOrigCalledNum }
--     STATUS          mandatory
    DESCRIPTION     
            "This trap indicates that an emergency call was placed
             that failed to route."
    ::= 5

sonusSbxNodeResourcesMaxIpCallLimitSetNotification TRAP-TYPE
    ENTERPRISE      sonusNodeResourcesMIBNotifications
    VARIABLES       { sonusAlarmNodeID, sonusAlarmLevel, 
                      sonusAlarmSequenceId, sonusAlarmTime, 
                      sonusAlarmDescription }
--     STATUS          mandatory
    DESCRIPTION     
            "This trap indicates that MAX IP call Limit set."
    ::= 6

sonusSbxNodeResourcesMaxIpCallLimitClearNotification TRAP-TYPE
    ENTERPRISE      sonusNodeResourcesMIBNotifications
    VARIABLES       { sonusAlarmNodeID, sonusAlarmLevel, 
                      sonusAlarmSequenceId, sonusAlarmTime, 
                      sonusAlarmDescription }
--     STATUS          mandatory
    DESCRIPTION     
            "This trap indicates that MAX IP call Limit cleared."
    ::= 7

sonusSbxNodeResourcesMaxSysCallLimitSetNotification TRAP-TYPE
    ENTERPRISE      sonusNodeResourcesMIBNotifications
    VARIABLES       { sonusAlarmNodeID, sonusAlarmLevel, 
                      sonusAlarmSequenceId, sonusAlarmTime, 
                      sonusAlarmDescription }
--     STATUS          mandatory
    DESCRIPTION     
            "This trap indicates that MAX System call limit set."
    ::= 8

sonusSbxNodeResourcesMaxSysCallLimitClearNotification TRAP-TYPE
    ENTERPRISE      sonusNodeResourcesMIBNotifications
    VARIABLES       { sonusAlarmNodeID, sonusAlarmLevel, 
                      sonusAlarmSequenceId, sonusAlarmTime, 
                      sonusAlarmDescription }
--     STATUS          mandatory
    DESCRIPTION     
            "This trap indicates that MAX system call limit cleared."
    ::= 9

sonusSbxNodeResourcesFeatureKeyStateChangeNotification TRAP-TYPE
    ENTERPRISE      sonusNodeResourcesMIBNotifications
    VARIABLES       { sonusAlarmNodeID, sonusAlarmLevel, 
                      sonusAlarmSequenceId, sonusAlarmTime, 
                      sonusAlarmDescription, sonusFeatureName, 
                      sonusFeatureState }
--     STATUS          mandatory
    DESCRIPTION     
            "This trap indicates that there is change in feature key state."
    ::= 10

sonusSbxCallFailureNoDspExceedThresholdNotification TRAP-TYPE
    ENTERPRISE      sonusNodeResourcesMIBNotifications
    VARIABLES       { sonusAlarmNodeID, sonusAlarmLevel, 
                      sonusAlarmSequenceId, sonusAlarmTime, 
                      sonusAlarmDescription, 
                      sonusNumCallFailureNoDspExceedThreshold }
--     STATUS          mandatory
    DESCRIPTION     
            "This trap indicates that number of call failure due to lack of DSP resource exceed the threshold."
    ::= 11

sonusSbxDspAvailG729OnSetCrossThresholdNotification TRAP-TYPE
    ENTERPRISE      sonusNodeResourcesMIBNotifications
    VARIABLES       { sonusAlarmNodeID, sonusAlarmLevel, 
                      sonusAlarmSequenceId, sonusAlarmTime, 
                      sonusAlarmDescription, 
                      sonusNumDspAvailabilityG729CrossThreshold }
--     STATUS          mandatory
    DESCRIPTION     
            "This trap indicates that the Availability of type G729 DSP Cross the threshold downward."
    ::= 12

sonusSbxDspAvailG726OnSetCrossThresholdNotification TRAP-TYPE
    ENTERPRISE      sonusNodeResourcesMIBNotifications
    VARIABLES       { sonusAlarmNodeID, sonusAlarmLevel, 
                      sonusAlarmSequenceId, sonusAlarmTime, 
                      sonusAlarmDescription, 
                      sonusNumDspAvailabilityG726CrossThreshold }
--     STATUS          mandatory
    DESCRIPTION     
            "This trap indicates that the Availability of type G726 DSP Cross the threshold downward."
    ::= 13

sonusSbxDspAvailG711OnSetCrossThresholdNotification TRAP-TYPE
    ENTERPRISE      sonusNodeResourcesMIBNotifications
    VARIABLES       { sonusAlarmNodeID, sonusAlarmLevel, 
                      sonusAlarmSequenceId, sonusAlarmTime, 
                      sonusAlarmDescription, 
                      sonusNumDspAvailabilityG711PacketCrossThreshold }
--     STATUS          mandatory
    DESCRIPTION     
            "This trap indicates that the Availability of type G711 Packet DSP Cross the threshold downward."
    ::= 14

sonusSbxDspAvailG729AbateCrossThresholdNotification TRAP-TYPE
    ENTERPRISE      sonusNodeResourcesMIBNotifications
    VARIABLES       { sonusAlarmNodeID, sonusAlarmLevel, 
                      sonusAlarmSequenceId, sonusAlarmTime, 
                      sonusAlarmDescription, 
                      sonusNumDspAvailabilityG729CrossThreshold }
--     STATUS          mandatory
    DESCRIPTION     
            "This trap indicates that the Availability of type G729 DSP Cross the threshold downward."
    ::= 15

sonusSbxDspAvailG726AbateCrossThresholdNotification TRAP-TYPE
    ENTERPRISE      sonusNodeResourcesMIBNotifications
    VARIABLES       { sonusAlarmNodeID, sonusAlarmLevel, 
                      sonusAlarmSequenceId, sonusAlarmTime, 
                      sonusAlarmDescription, 
                      sonusNumDspAvailabilityG726CrossThreshold }
--     STATUS          mandatory
    DESCRIPTION     
            "This trap indicates that the Availability of type G726 DSP Cross the threshold downward."
    ::= 16

sonusSbxDspAvailG711PacketAbateCrossThresholdNotification TRAP-TYPE
    ENTERPRISE      sonusNodeResourcesMIBNotifications
    VARIABLES       { sonusAlarmNodeID, sonusAlarmLevel, 
                      sonusAlarmSequenceId, sonusAlarmTime, 
                      sonusAlarmDescription, 
                      sonusNumDspAvailabilityG711PacketCrossThreshold }
--     STATUS          mandatory
    DESCRIPTION     
            "This trap indicates that the Availability of type G711 DSP Cross the threshold downward."
    ::= 17

sonusSbxNodeResourcesPacketLossThresholdExceededNotification TRAP-TYPE
    ENTERPRISE      sonusNodeResourcesMIBNotifications
    VARIABLES       { sonusAlarmNodeID, sonusAlarmLevel, 
                      sonusAlarmSequenceId, sonusAlarmTime, 
                      sonusAlarmDescription, sonusNrmaCallGcid }
--     STATUS          mandatory
    DESCRIPTION     
            "This trap indicates that the packet loss has exceeded the threshold level."
    ::= 18

sonusSbxNodeResourcesPacketLossThresholdClearNotification TRAP-TYPE
    ENTERPRISE      sonusNodeResourcesMIBNotifications
    VARIABLES       { sonusAlarmNodeID, sonusAlarmLevel, 
                      sonusAlarmSequenceId, sonusAlarmTime, 
                      sonusAlarmDescription, sonusNrmaCallGcid }
--     STATUS          mandatory
    DESCRIPTION     
            "This trap indicates that the packet loss is below the threshold level."
    ::= 19

sonusSbxNodeResourcesNoPacketsReceivedNotification TRAP-TYPE
    ENTERPRISE      sonusNodeResourcesMIBNotifications
    VARIABLES       { sonusAlarmNodeID, sonusAlarmLevel, 
                      sonusAlarmSequenceId, sonusAlarmTime, 
                      sonusAlarmDescription, sonusNrmaCallGcid }
--     STATUS          mandatory
    DESCRIPTION     
            "This trap indicates that no RTP or RTCP packets were received from peer."
    ::= 20

sonusSbxNodeResourcesNoPacketsReceivedClearNotification TRAP-TYPE
    ENTERPRISE      sonusNodeResourcesMIBNotifications
    VARIABLES       { sonusAlarmNodeID, sonusAlarmLevel, 
                      sonusAlarmSequenceId, sonusAlarmTime, 
                      sonusAlarmDescription, sonusNrmaCallGcid }
--     STATUS          mandatory
    DESCRIPTION     
            "This trap indicates that the peer has resumed sending RTP or RTCP packets."
    ::= 21

sonusSbxPadThresholdNotification TRAP-TYPE
    ENTERPRISE      sonusNodeResourcesMIBNotifications
    VARIABLES       { sonusAlarmNodeID, sonusAlarmLevel, 
                      sonusAlarmSequenceId, sonusAlarmTime, 
                      sonusAlarmDescription }
--     STATUS          mandatory
    DESCRIPTION     
            "This trap indicates that the compression DSP resource usage has crossed the threshold value."
    ::= 22

sonusSbxPadThresholdNotificationClear TRAP-TYPE
    ENTERPRISE      sonusNodeResourcesMIBNotifications
    VARIABLES       { sonusAlarmNodeID, sonusAlarmLevel, 
                      sonusAlarmSequenceId, sonusAlarmTime, 
                      sonusAlarmDescription }
--     STATUS          mandatory
    DESCRIPTION     
            "This trap indicates that the compression DSP resource usage has dropped below the threshold value."
    ::= 23

sonusSbxMediaProfileDspReconfigurationNotification TRAP-TYPE
    ENTERPRISE      sonusNodeResourcesMIBNotifications
    VARIABLES       { sonusAlarmNodeID, sonusAlarmLevel, 
                      sonusAlarmSequenceId, sonusAlarmTime, 
                      sonusAlarmDescription }
--     STATUS          mandatory
    DESCRIPTION     
            "This trap indicates that the mediaProfile config has been modified and DSP reconfiguration initiated and in progress."
    ::= 24

sonusSbxMediaProfileDspReconfigurationNotificationClear TRAP-TYPE
    ENTERPRISE      sonusNodeResourcesMIBNotifications
    VARIABLES       { sonusAlarmNodeID, sonusAlarmLevel, 
                      sonusAlarmSequenceId, sonusAlarmTime, 
                      sonusAlarmDescription }
--     STATUS          mandatory
    DESCRIPTION     
            "This trap indicates that the mediaProfile and DSP reconfiguration is complete."
    ::= 25

sonusJsrcServerStateUpNotification TRAP-TYPE
    ENTERPRISE      sonusNodeResourcesMIBNotifications
    VARIABLES       { sonusAlarmNodeID, sonusAlarmLevel, 
                      sonusAlarmSequenceId, sonusAlarmTime, 
                      sonusAlarmDescription, sonusJSrcServerName }
--     STATUS          mandatory
    DESCRIPTION     
            "This trap indicates that the JSRC Server is up."
    ::= 26

sonusJsrcServerStateDownNotification TRAP-TYPE
    ENTERPRISE      sonusNodeResourcesMIBNotifications
    VARIABLES       { sonusAlarmNodeID, sonusAlarmLevel, 
                      sonusAlarmSequenceId, sonusAlarmTime, 
                      sonusAlarmDescription, sonusJSrcServerName }
--     STATUS          mandatory
    DESCRIPTION     
            "This trap indicates that the JSRC Server is down."
    ::= 27

sonusSbxNodeMachineCongestionNotification TRAP-TYPE
    ENTERPRISE      sonusNodeResourcesMIBNotifications
    VARIABLES       { sonusAlarmNodeID, sonusAlarmLevel, 
                      sonusAlarmSequenceId, sonusAlarmTime, 
                      sonusAlarmDescription, sonusOverloadLevel }
--     STATUS          mandatory
    DESCRIPTION     
            "The sonusSbxNodeMachineCongestionNotification indicates
             SBX Machine congestion level changes."
    ::= 28

sonusSbxNodeResourceCallTraceDisabledNotification TRAP-TYPE
    ENTERPRISE      sonusNodeResourcesMIBNotifications
    VARIABLES       { sonusAlarmNodeID, sonusAlarmLevel, 
                      sonusAlarmSequenceId, sonusAlarmTime, 
                      sonusAlarmDescription, sonusCallTraceDisableReason }
--     STATUS          mandatory
    DESCRIPTION     
            "This trap indicates that call trace is disabled/inactive."
    ::= 29

sonusSbxNodeResourceCallTraceActiveNotification TRAP-TYPE
    ENTERPRISE      sonusNodeResourcesMIBNotifications
    VARIABLES       { sonusAlarmNodeID, sonusAlarmLevel, 
                      sonusAlarmSequenceId, sonusAlarmTime, 
                      sonusAlarmDescription }
--     STATUS          mandatory
    DESCRIPTION     
            "This trap indicates that call trace started."
    ::= 30

sonusSbxNodeResourcesMaxTcpMediaSessLimitSetNotification TRAP-TYPE
    ENTERPRISE      sonusNodeResourcesMIBNotifications
    VARIABLES       { sonusAlarmNodeID, sonusAlarmLevel, 
                      sonusAlarmSequenceId, sonusAlarmTime, 
                      sonusAlarmDescription }
--     STATUS          mandatory
    DESCRIPTION     
            "This trap indicates that TCP media sessions has reached higher threshold."
    ::= 31

sonusSbxNodeResourcesMaxTcpMediaSessLimitClearNotification TRAP-TYPE
    ENTERPRISE      sonusNodeResourcesMIBNotifications
    VARIABLES       { sonusAlarmNodeID, sonusAlarmLevel, 
                      sonusAlarmSequenceId, sonusAlarmTime, 
                      sonusAlarmDescription }
--     STATUS          mandatory
    DESCRIPTION     
            "This trap indicates that the TCP media sessions has dropped below lower threshold."
    ::= 32

sonusSbxNodeResourcesSysACLLimitNotification TRAP-TYPE
    ENTERPRISE      sonusNodeResourcesMIBNotifications
    VARIABLES       { sonusAlarmNodeID, sonusAlarmLevel, 
                      sonusAlarmSequenceId, sonusAlarmTime, 
                      sonusAlarmDescription }
--     STATUS          mandatory
    DESCRIPTION     
            "This trap indicates that there was an error creating system ACL for TCP media session possibly due to reaching maximum ACL limits."
    ::= 33

sonusSbxNodeResourcesMediaPortRangeExhaustionNotification TRAP-TYPE
    ENTERPRISE      sonusNodeResourcesMIBNotifications
    VARIABLES       { sonusAlarmNodeID, sonusAlarmLevel, 
                      sonusAlarmSequenceId, sonusAlarmTime, 
                      sonusAlarmDescription, sonusTgName }
--     STATUS          mandatory
    DESCRIPTION     
            "The media port range has been exhausted."
    ::= 34

sonusSbxNodeResourcesMediaPortRangeExhaustionClearedNotfication TRAP-TYPE
    ENTERPRISE      sonusNodeResourcesMIBNotifications
    VARIABLES       { sonusAlarmNodeID, sonusAlarmLevel, 
                      sonusAlarmSequenceId, sonusAlarmTime, 
                      sonusAlarmDescription, sonusTgName }
--     STATUS          mandatory
    DESCRIPTION     
            "The media port range is no longer exhausted."
    ::= 35

sonusSbxNodeResourcesTcpPortRangeExhaustionNotification TRAP-TYPE
    ENTERPRISE      sonusNodeResourcesMIBNotifications
    VARIABLES       { sonusAlarmNodeID, sonusAlarmLevel, 
                      sonusAlarmSequenceId, sonusAlarmTime, 
                      sonusAlarmDescription, sonusTgName }
--     STATUS          mandatory
    DESCRIPTION     
            "The TCP port range has been exhausted."
    ::= 36

sonusSbxNodeResourcesTcpPortRangeExhaustionClearedNotification TRAP-TYPE
    ENTERPRISE      sonusNodeResourcesMIBNotifications
    VARIABLES       { sonusAlarmNodeID, sonusAlarmLevel, 
                      sonusAlarmSequenceId, sonusAlarmTime, 
                      sonusAlarmDescription, sonusTgName }
--     STATUS          mandatory
    DESCRIPTION     
            "The TCP port range is no longer exhausted."
    ::= 37

sonusSbxSingleDspReloadAndCoreDumpNotification TRAP-TYPE
    ENTERPRISE      sonusNodeResourcesMIBNotifications
    VARIABLES       { sonusAlarmNodeID, sonusAlarmLevel, 
                      sonusAlarmSequenceId, sonusAlarmTime, 
                      sonusAlarmDescription }
--     STATUS          mandatory
    DESCRIPTION     
            "This trap indicates completion of single Dsp Reload and Core-Dump process."
    ::= 38

sonusSbxNodeMemoryCongestionNotification TRAP-TYPE
    ENTERPRISE      sonusNodeResourcesMIBNotifications
    VARIABLES       { sonusAlarmNodeID, sonusAlarmLevel, 
                      sonusAlarmSequenceId, sonusAlarmTime, 
                      sonusAlarmDescription, sonusCallCount, 
                      sonusRegCount, sonusRelayCount }
--     STATUS          mandatory
    DESCRIPTION     
            "This trap indicates that the machine's memory is congested."
    ::= 39

sonusSbxNodeMemoryCongestionClearNotification TRAP-TYPE
    ENTERPRISE      sonusNodeResourcesMIBNotifications
    VARIABLES       { sonusAlarmNodeID, sonusAlarmLevel, 
                      sonusAlarmSequenceId, sonusAlarmTime, 
                      sonusAlarmDescription, sonusCallCount, 
                      sonusRegCount, sonusRelayCount }
--     STATUS          mandatory
    DESCRIPTION     
            "This trap indicates that the machine's memory is no longer congested."
    ::= 40

sonusSbxNodeResourceCallTraceSignalingDisabledNotification TRAP-TYPE
    ENTERPRISE      sonusNodeResourcesMIBNotifications
    VARIABLES       { sonusAlarmNodeID, sonusAlarmLevel, 
                      sonusAlarmSequenceId, sonusAlarmTime, 
                      sonusAlarmDescription, sonusCallTraceDisableReason }
--     STATUS          mandatory
    DESCRIPTION     
            "This trap indicates that signaling packet capture is disabled/inactive."
    ::= 41

sonusSbxNodeResourceCallTraceSignalingEnabledNotification TRAP-TYPE
    ENTERPRISE      sonusNodeResourcesMIBNotifications
    VARIABLES       { sonusAlarmNodeID, sonusAlarmLevel, 
                      sonusAlarmSequenceId, sonusAlarmTime, 
                      sonusAlarmDescription }
--     STATUS          mandatory
    DESCRIPTION     
            "This trap indicates that signaling packet capture started."
    ::= 42

sonusSbxDspFpgaVersionCheckFailureNotification TRAP-TYPE
    ENTERPRISE      sonusNodeResourcesMIBNotifications
    VARIABLES       { sonusAlarmNodeID, sonusAlarmLevel, 
                      sonusAlarmSequenceId, sonusAlarmTime, 
                      sonusAlarmDescription }
--     STATUS          mandatory
    DESCRIPTION     
            "This trap indicates DSP FPGA version check failure."
    ::= 43

sonusSbxNodeOutOfServiceNotification TRAP-TYPE
    ENTERPRISE      sonusNodeResourcesMIBNotifications
    VARIABLES       { sonusAlarmNodeID, sonusAlarmLevel, 
                      sonusAlarmSequenceId, sonusAlarmTime, 
                      sonusAlarmDescription }
--     STATUS          mandatory
    DESCRIPTION     
            "This trap indicates that this node has been administratively removed from processing calls."
    ::= 44

sonusSbxToneAnnouncementFailedNotification TRAP-TYPE
    ENTERPRISE      sonusNodeResourcesMIBNotifications
    VARIABLES       { sonusAlarmNodeID, sonusAlarmLevel, 
                      sonusAlarmSequenceId, sonusAlarmTime, 
                      sonusAlarmDescription, sonusNrmaToneType, 
                      sonusNrmaCodecType, sonusNrmaCodecAttr }
--     STATUS          mandatory
    DESCRIPTION     
            "This trap indicates that tone playing failed when we are playing compressed tone using file."
    ::= 45

sonusLiCryptoFailureNotification TRAP-TYPE
    ENTERPRISE      sonusNodeResourcesMIBNotifications
    VARIABLES       { sonusAlarmNodeID, sonusAlarmLevel, 
                      sonusAlarmSequenceId, sonusAlarmTime, 
                      sonusAlarmDescription, sonusScmInstanceId, 
                      sonusDecryptModuleId }
--     STATUS          mandatory
    DESCRIPTION     
            "Decryption failed"
    ::= 46

sonusLiCryptoSuccessNotification TRAP-TYPE
    ENTERPRISE      sonusNodeResourcesMIBNotifications
    VARIABLES       { sonusAlarmNodeID, sonusAlarmLevel, 
                      sonusAlarmSequenceId, sonusAlarmTime, 
                      sonusAlarmDescription, sonusScmInstanceId, 
                      sonusDecryptModuleId }
--     STATUS          mandatory
    DESCRIPTION     
            "Decryption successful"
    ::= 47

sonusSbxNodeInServiceNotification TRAP-TYPE
    ENTERPRISE      sonusNodeResourcesMIBNotifications
    VARIABLES       { sonusAlarmNodeID, sonusAlarmLevel, 
                      sonusAlarmSequenceId, sonusAlarmTime, 
                      sonusAlarmDescription }
--     STATUS          mandatory
    DESCRIPTION     
            "This trap indicates that this node has been administratively placed in service for processing calls."
    ::= 48

sonusSbxDspCardOrDeviceFailureNotification TRAP-TYPE
    ENTERPRISE      sonusNodeResourcesMIBNotifications
    VARIABLES       { sonusAlarmNodeID, sonusAlarmLevel, 
                      sonusAlarmSequenceId, sonusAlarmTime, 
                      sonusAlarmDescription }
--     STATUS          mandatory
    DESCRIPTION     
            "This trap indicates and identifies a fatal DSP device or card failure."
    ::= 49

sonusSbxDspCardOrDeviceFailureNotificationClear TRAP-TYPE
    ENTERPRISE      sonusNodeResourcesMIBNotifications
    VARIABLES       { sonusAlarmNodeID, sonusAlarmLevel, 
                      sonusAlarmSequenceId, sonusAlarmTime, 
                      sonusAlarmDescription }
--     STATUS          mandatory
    DESCRIPTION     
            "This trap indicates that a DSP device or card failure has cleared."
    ::= 50

sonusSbxGpuCodecThresholdNotification TRAP-TYPE
    ENTERPRISE      sonusNodeResourcesMIBNotifications
    VARIABLES       { sonusAlarmNodeID, sonusAlarmLevel, 
                      sonusAlarmSequenceId, sonusAlarmTime, 
                      sonusAlarmDescription, sonusThresholdCrossingCodec }
--     STATUS          mandatory
    DESCRIPTION     
            "This trap indicates that the compression DSP resource usage for certain GPU supported codecs has crossed the threshold value."
    ::= 51

sonusSbxGpuCodecThresholdNotificationClear TRAP-TYPE
    ENTERPRISE      sonusNodeResourcesMIBNotifications
    VARIABLES       { sonusAlarmNodeID, sonusAlarmLevel, 
                      sonusAlarmSequenceId, sonusAlarmTime, 
                      sonusAlarmDescription, sonusThresholdCrossingCodec }
--     STATUS          mandatory
    DESCRIPTION     
            "This trap indicates that the compression DSP resource usage for GPU supported codec has dropped below the threshold value."
    ::= 52

sonusSbxMediaOverFlowPacketsNotification TRAP-TYPE
    ENTERPRISE      sonusNodeResourcesMIBNotifications
    VARIABLES       { sonusAlarmNodeID, sonusAlarmLevel, 
                      sonusAlarmSequenceId, sonusAlarmTime, 
                      sonusAlarmDescription }
--     STATUS          mandatory
    DESCRIPTION     
            "This trap indicates that over flow packets or Non-Confirming packets were found for one or more calls during X interval defined in system policing."
    ::= 53

sonusSbxMediaOverFlowPacketsCleared TRAP-TYPE
    ENTERPRISE      sonusNodeResourcesMIBNotifications
    VARIABLES       { sonusAlarmNodeID, sonusAlarmLevel, 
                      sonusAlarmSequenceId, sonusAlarmTime, 
                      sonusAlarmDescription }
--     STATUS          mandatory
    DESCRIPTION     
            "This trap indicates that there are no more over flow packets or Non-Confirming packets for calls during X interval defined in system policing."
    ::= 54

sonusTrafficProfileActivationNotification TRAP-TYPE
    ENTERPRISE      sonusNodeResourcesMIBNotifications
    VARIABLES       { sonusAlarmNodeID, sonusAlarmLevel, 
                      sonusAlarmSequenceId, sonusAlarmTime, 
                      sonusAlarmDescription, 
                      sonusTrafficProfileActivationMsg, 
                      sonusTrafficProfileActivationStatus }
--     STATUS          mandatory
    DESCRIPTION     
            "This trap indicates that there was an attempt to activate a traffic profile on a SWe/Cloud instance from OAM."
    ::= 55

sonusConfigProfileActivationNotification TRAP-TYPE
    ENTERPRISE      sonusNodeResourcesMIBNotifications
    VARIABLES       { sonusAlarmNodeID, sonusAlarmLevel, 
                      sonusAlarmSequenceId, sonusAlarmTime, 
                      sonusAlarmDescription, 
                      sonusConfigProfileActivationMsg, 
                      sonusConfigProfileActivationStatus }
--     STATUS          mandatory
    DESCRIPTION     
            "This trap indicates that there was an attempt to activate a Config profile on a SWe/Cloud instance from OAM."
    ::= 56

sonusMrfpRealmMediaPortRangeThresholdExceededNotification TRAP-TYPE
    ENTERPRISE      sonusNodeResourcesMIBNotifications
    VARIABLES       { sonusAlarmNodeID, sonusAlarmLevel, 
                      sonusAlarmSequenceId, sonusAlarmTime, 
                      sonusAlarmDescription, sonusMrfpRealmId }
--     STATUS          mandatory
    DESCRIPTION     
            "The realm media port usage has exceeded threshold."
    ::= 57

sonusMrfpRealmMediaPortRangeThresholdExceededClearedNotfication TRAP-TYPE
    ENTERPRISE      sonusNodeResourcesMIBNotifications
    VARIABLES       { sonusAlarmNodeID, sonusAlarmLevel, 
                      sonusAlarmSequenceId, sonusAlarmTime, 
                      sonusAlarmDescription, sonusMrfpRealmId }
--     STATUS          mandatory
    DESCRIPTION     
            "The realm media port range is back under threshold."
    ::= 58

sonusSbxTrunkGroupTrafficControlConfChanged TRAP-TYPE
    ENTERPRISE      sonusTrunkGroupResourcesMIBNotifications
    VARIABLES       { sonusAlarmNodeID, sonusAlarmLevel, 
                      sonusAlarmSequenceId, sonusAlarmTime, 
                      sonusAlarmDescription, sonusTgName, 
                      sonusTrunkGroupTCObject, sonusTgAdditionalData }
--     STATUS          deprecated
    DESCRIPTION     
            "This trap has been replaced by sonusSbxTrunkGroupTrafficControlConfChanged2."
    ::= 1

sonusSbxTrunkGroupManualControlActive TRAP-TYPE
    ENTERPRISE      sonusTrunkGroupResourcesMIBNotifications
    VARIABLES       { sonusAlarmNodeID, sonusAlarmLevel, 
                      sonusAlarmSequenceId, sonusAlarmTime, 
                      sonusAlarmDescription, sonusTgName, 
                      sonusTrunkGroupManCon, sonusTgAdditionalData }
--     STATUS          deprecated
    DESCRIPTION     
            "This trap has been replaced by sonusSbxTrunkGroupManualControlActive2."
    ::= 2

sonusSbxTrunkGroupAutomaticControlActive TRAP-TYPE
    ENTERPRISE      sonusTrunkGroupResourcesMIBNotifications
    VARIABLES       { sonusAlarmNodeID, sonusAlarmLevel, 
                      sonusAlarmSequenceId, sonusAlarmTime, 
                      sonusAlarmDescription, sonusTgName, 
                      sonusTrunkGroupAutoCon, sonusTgAdditionalData }
--     STATUS          deprecated
    DESCRIPTION     
            "This trap has been replaced by sonusSbxTrunkGroupAutomaticControlActive2."
    ::= 3

sonusSbxTrunkGroupOutOfResourcesNotification TRAP-TYPE
    ENTERPRISE      sonusTrunkGroupResourcesMIBNotifications
    VARIABLES       { sonusAlarmNodeID, sonusAlarmLevel, 
                      sonusAlarmSequenceId, sonusAlarmTime, 
                      sonusAlarmDescription, sonusTgName, 
                      sonusCacLimitType, sonusTgAdditionalData }
--     STATUS          deprecated
    DESCRIPTION     
            "This trap has been replaced by sonusSbxTrunkGroupOutOfResourcesNotification2."
    ::= 4

sonusSbxTrunkGroupKpiClearedThresholdNotification TRAP-TYPE
    ENTERPRISE      sonusTrunkGroupResourcesMIBNotifications
    VARIABLES       { sonusAlarmNodeID, sonusAlarmLevel, 
                      sonusAlarmSequenceId, sonusAlarmTime, 
                      sonusAlarmDescription, sonusTgName, 
                      sonusAddressContextName, sonusZoneName, sonusKpi, 
                      sonusCurrentKpiValue }
--     STATUS          mandatory
    DESCRIPTION     
            "This trap indicates that bad QOS KPI condition in the trunk
             group got cleared."
    ::= 5

sonusSbxTrunkGroupKpiMajorThresholdNotification TRAP-TYPE
    ENTERPRISE      sonusTrunkGroupResourcesMIBNotifications
    VARIABLES       { sonusAlarmNodeID, sonusAlarmLevel, 
                      sonusAlarmSequenceId, sonusAlarmTime, 
                      sonusAlarmDescription, sonusTgName, 
                      sonusAddressContextName, sonusZoneName, sonusKpi, 
                      sonusCurrentKpiValue }
--     STATUS          mandatory
    DESCRIPTION     
            "This trap indicates that major QOS KPI condition in the trunk"
    ::= 6

sonusSbxTrunkGroupKpiCriticalThresholdNotification TRAP-TYPE
    ENTERPRISE      sonusTrunkGroupResourcesMIBNotifications
    VARIABLES       { sonusAlarmNodeID, sonusAlarmLevel, 
                      sonusAlarmSequenceId, sonusAlarmTime, 
                      sonusAlarmDescription, sonusTgName, 
                      sonusAddressContextName, sonusZoneName, sonusKpi, 
                      sonusCurrentKpiValue }
--     STATUS          mandatory
    DESCRIPTION     
            "This trap indicates that critical QOS KPI condition in the TG"
    ::= 7

sonusSbxTrunkGroupKpiCriticalThresholdClearedNotification TRAP-TYPE
    ENTERPRISE      sonusTrunkGroupResourcesMIBNotifications
    VARIABLES       { sonusAlarmNodeID, sonusAlarmLevel, 
                      sonusAlarmSequenceId, sonusAlarmTime, 
                      sonusAlarmDescription, sonusTgName, 
                      sonusAddressContextName, sonusZoneName, sonusKpi, 
                      sonusCurrentKpiValue }
--     STATUS          mandatory
    DESCRIPTION     
            "This trap indicates that critical QOS KPI condition in the TG got cleared"
    ::= 8

sonusSbxTrunkGroupTrafficControlConfChanged2 TRAP-TYPE
    ENTERPRISE      sonusTrunkGroupResourcesMIBNotifications
    VARIABLES       { sonusAlarmNodeID, sonusAlarmLevel, 
                      sonusAlarmSequenceId, sonusAlarmTime, 
                      sonusAlarmDescription, sonusTgName, 
                      sonusTrunkGroupTCObject }
--     STATUS          mandatory
    DESCRIPTION     
            "This trap indicates that a traffic control
             configuration object in 
             the trunk group table has changed.  The 
             sonusTrunkGroupTCObject parameter indicates what 
             object or objects have changed."
    ::= 9

sonusSbxTrunkGroupManualControlActive2 TRAP-TYPE
    ENTERPRISE      sonusTrunkGroupResourcesMIBNotifications
    VARIABLES       { sonusAlarmNodeID, sonusAlarmLevel, 
                      sonusAlarmSequenceId, sonusAlarmTime, 
                      sonusAlarmDescription, sonusTgName, 
                      sonusTrunkGroupManCon }
--     STATUS          deprecated
    DESCRIPTION     
            "This trap has been replaced by sonusSbxTrunkGroupManualControlActive3."
    ::= 10

sonusSbxTrunkGroupAutomaticControlActive2 TRAP-TYPE
    ENTERPRISE      sonusTrunkGroupResourcesMIBNotifications
    VARIABLES       { sonusAlarmNodeID, sonusAlarmLevel, 
                      sonusAlarmSequenceId, sonusAlarmTime, 
                      sonusAlarmDescription, sonusTgName, 
                      sonusTrunkGroupAutoCon }
--     STATUS          deprecated
    DESCRIPTION     
            "This trap has been replaced by sonusSbxTrunkGroupManualControlActive3."
    ::= 11

sonusSbxTrunkGroupOutOfResourcesNotification2 TRAP-TYPE
    ENTERPRISE      sonusTrunkGroupResourcesMIBNotifications
    VARIABLES       { sonusAlarmNodeID, sonusAlarmLevel, 
                      sonusAlarmSequenceId, sonusAlarmTime, 
                      sonusAlarmDescription, sonusTgName, 
                      sonusCacLimitType }
--     STATUS          mandatory
    DESCRIPTION     
            "This trap indicates a Trunk Group is out of resources."
    ::= 12

sonusSbxTrunkGroupManualControlActive3 TRAP-TYPE
    ENTERPRISE      sonusTrunkGroupResourcesMIBNotifications
    VARIABLES       { sonusAlarmNodeID, sonusAlarmLevel, 
                      sonusAlarmSequenceId, sonusAlarmTime, 
                      sonusAlarmDescription, sonusTgName, 
                      sonusTrunkGroupManCon3 }
--     STATUS          mandatory
    DESCRIPTION     
            "This trap indicates that a manual traffic control 
             was active within the last 30 seconds.  The 
             sonusTrunkGroupManualControl parameter indicates what 
             manual control was active."
    ::= 13

sonusSbxTrunkGroupAutomaticControlActive3 TRAP-TYPE
    ENTERPRISE      sonusTrunkGroupResourcesMIBNotifications
    VARIABLES       { sonusAlarmNodeID, sonusAlarmLevel, 
                      sonusAlarmSequenceId, sonusAlarmTime, 
                      sonusAlarmDescription, sonusTgName, 
                      sonusTrunkGroupAutoCon3 }
--     STATUS          mandatory
    DESCRIPTION     
            "This trap indicates that an automatic traffic control 
             was active within the last 30 seconds.  The 
             sonusTrunkGroupAutomaticControl parameter indicates 
             what automatic control was active."
    ::= 14

sonusSbxCallAccountingInServiceNotification TRAP-TYPE
    ENTERPRISE      sonusAccountingMIBNotifications
    VARIABLES       { sonusAlarmNodeID, sonusAlarmLevel, 
                      sonusAlarmSequenceId, sonusAlarmTime, 
                      sonusAlarmDescription, sonusAcctGenerationMode, 
                      sonusAcctLogDestination, sonusAcctIntAcctState, 
                      sonusAcctIntAcctInterval, sonusAcctIntAcctMode, 
                      sonusAcctIntLongDurGenTime }
--     STATUS          mandatory
    DESCRIPTION     
            "This Trap is Generated when a change is made to the Accounting 
             Configuration for the Node, and the resultant configuration
             state of accounting for the node is that it is enabled/in-service"
    ::= 1

sonusSbxCallAccountingOutOfServiceNotification TRAP-TYPE
    ENTERPRISE      sonusAccountingMIBNotifications
    VARIABLES       { sonusAlarmNodeID, sonusAlarmLevel, 
                      sonusAlarmSequenceId, sonusAlarmTime, 
                      sonusAlarmDescription, sonusAcctOutOfServiceReason }
--     STATUS          mandatory
    DESCRIPTION     
            "This Trap is Generated when Accounting Records are no
             longer being generated on the Node. It could be either
             because of a change to the Accounting Configuration
             or because of errors in the logging mechanism such as file logging
             errors. When the reason specified for accounting outofservice
             is event logging error, then the SYS event logs on the Node
             should be examined to obtain further information about the
             event logging failure"
    ::= 2

sonusSbxAccountingIntermediateRecordNotification TRAP-TYPE
    ENTERPRISE      sonusAccountingMIBNotifications
    VARIABLES       { sonusAlarmNodeID, sonusAlarmLevel, 
                      sonusAlarmSequenceId, sonusAlarmTime, 
                      sonusAlarmDescription, sonusAcctGcid, 
                      sonusAcctOrigTrunkgroupType, sonusAcctIngressCep, 
                      sonusAcctTermTrunkgroupType, sonusAcctEgressCep, 
                      sonusAcctCallingPartyNumber, 
                      sonusAcctCalledPartyNumber }
--     STATUS          mandatory
    DESCRIPTION     
            "This Trap is Generated when an INTERMEDIATE accounting
             record is generated."
    ::= 3

sonusSbxSelCdrConfUpdateNotification TRAP-TYPE
    ENTERPRISE      sonusAccountingMIBNotifications
    VARIABLES       { sonusAlarmNodeID, sonusAlarmLevel, 
                      sonusAlarmSequenceId, sonusAlarmTime, 
                      sonusAlarmDescription, sonusSelCdrSequenceNumber, 
                      sonusSelCdrUpdateStatus }
--     STATUS          deprecated
    DESCRIPTION     
            "This Trap indicates that SBC receives
             selectable CDR configuration from DSI
             stream server. The variable sonusSelCdrConfSeqNum
             indicates the new sequence number of selectable CDR
             configuration received. The variable
             sonusSelCdrConfUpdateStatus indicates
             the accept status of the configuration updates."
    ::= 4

sonusSbxSelCdrConfigReqRspTimeoutNotification TRAP-TYPE
    ENTERPRISE      sonusAccountingMIBNotifications
    VARIABLES       { sonusAlarmNodeID, sonusAlarmLevel, 
                      sonusAlarmSequenceId, sonusAlarmTime, 
                      sonusAlarmDescription, sonusSelCdrReqRspTimeout, 
                      sonusSelCdrSequenceNumber }
--     STATUS          deprecated
    DESCRIPTION     
            "This trap indicates that SBC requests DSI for current selectable
             CDR configuration due to previous CDR streaming link outage or LSWU,
             but didn\222t receive the configuration updates from DSI after three 
             	    retries.
             
             The variable sonusSelCdrConfSeqNum indicates the last selectable CDR
             Configuration received, the variable sonusSelCdrReqRspTimeout
             indicates the duration of three retries."
    ::= 5

sonusSbxCallProcAnswerSupervisionTimeout TRAP-TYPE
    ENTERPRISE      sonusCommonCallProcessMIBNotifications
    VARIABLES       { sonusAlarmNodeID, sonusAlarmLevel, 
                      sonusAlarmSequenceId, sonusAlarmTime, 
                      sonusAlarmDescription, sonusIngressTgName, 
                      sonusIngressCep, sonusEgressTgName, sonusEgressCep, 
                      sonusCalledNumber, sonusCallingNumber }
--     STATUS          mandatory
    DESCRIPTION     
            "The answer supervision timer has expired, indicating that 
             answer message has not been received from the called party.
             This trap is used to inform maintenance personnel of the
             situation so they can decide whether executive action is 
             required to tear the call down."
    ::= 1

sonusSbxCallProcLongDurationCallTimeout TRAP-TYPE
    ENTERPRISE      sonusCommonCallProcessMIBNotifications
    VARIABLES       { sonusAlarmNodeID, sonusAlarmLevel, 
                      sonusAlarmSequenceId, sonusAlarmTime, 
                      sonusAlarmDescription, sonusTgName, sonusCep, 
                      sonusStaticCallGcid, sonusCalledNumber, 
                      sonusCallingNumber, sonusLdcStatus }
--     STATUS          mandatory
    DESCRIPTION     
            "This trap is used to inform that the long duration call 
             timer has expired. The call has been active for the 
             configured timeout period and the appropriate
             action has been taken."
    ::= 2

sonusSbxNetMgmtClientInformReqQueueFlushedNotification TRAP-TYPE
    ENTERPRISE      sonusCommonMIBNotifications
    VARIABLES       { sonusAlarmNodeID, sonusAlarmLevel, 
                      sonusAlarmSequenceId, sonusAlarmTime, 
                      sonusAlarmDescription, sonusNetMgmtClientName, 
                      sonusNetMgmtInformReqDiscards }
--     STATUS          mandatory
    DESCRIPTION     
            "The specified number of InformRequest PDUs destined to
             the specified Management Client were flushed from the
             InformRequest PDU queue because no Response PDUs were
             were received from the Management Client.
             
             This situtation could occur if the Management Client
             cannot quickly process and respond to InformRequest PDUs
             that it receives, or if communications is lost with the
             Management Client.
             
             If this situation occurs occasionally, it is recommended
             to increase the InformRequest PDU timeout and/or retry
             values (see sonusNetMgmtClientInformReqRspTimeout and
             sonusNetMgmtClientInformReqRetries.)
             
             If this situation occurs repeatedly, it is an indication
             that communications is lost with the Management Client,
             either because of network problems, or because the
             Management Client is no longer operational.
             
             It is recommended that this device be configured to
             send a Trap PDU, not an InformRequest PDU, for this
             Notification to all Management Clients, thus bypassing
             a problematic InformRequest PDU queue and allowing the
             situation to be quickly identified and resolved."
    ::= 1

sonusSbxNetMgmtClientInformReqQueueFullNotification TRAP-TYPE
    ENTERPRISE      sonusCommonMIBNotifications
    VARIABLES       { sonusAlarmNodeID, sonusAlarmLevel, 
                      sonusAlarmSequenceId, sonusAlarmTime, 
                      sonusAlarmDescription, sonusNetMgmtClientName, 
                      sonusNetMgmtInformReqDiscards }
--     STATUS          mandatory
    DESCRIPTION     
            "The specified number of InformRequest PDUs destined to
             the specified Management Client were discard because its
             InformRequest PDU queue was full.
             
             This situtation could occur if the Management Client
             cannot quickly process and respond to InformRequest PDUs
             that it receives, or if communications is lost with the
             Management Client.
             
             If this situation occurs occasionally, it is recommended
             to increase the InformRequest PDU queue size (see
             sonusNetMgmtClientInformReqMaxQueue.)
             
             If this situation occurs repeatedly, it is an indication
             that communications is lost with the Management Client,
             either because of network problems, or because the
             Management Client is no longer operational.
             
             It is recommended that this device be configured to
             send a Trap PDU, not an InformRequest PDU, for this
             Notification to all Management Clients, thus bypassing
             a problematic InformRequest PDU queue and allowing the
             situation to be quickly identified and resolved."
    ::= 2

sonusSbxNodePolicerMinorAlarmNotification TRAP-TYPE
    ENTERPRISE      sonusIpmMIBNotifications
    VARIABLES       { sonusAlarmNodeID, sonusAlarmLevel, 
                      sonusAlarmSequenceId, sonusAlarmTime, 
                      sonusAlarmDescription, sonusPolicerTypeStr, 
                      sonusPolicerLevelStr }
--     STATUS          mandatory
    DESCRIPTION     
            "The sonusNodePolicerMinorAlarmNotification indicates
             a system policer minor level alarm."
    ::= 1

sonusSbxNodePolicerMajorAlarmNotification TRAP-TYPE
    ENTERPRISE      sonusIpmMIBNotifications
    VARIABLES       { sonusAlarmNodeID, sonusAlarmLevel, 
                      sonusAlarmSequenceId, sonusAlarmTime, 
                      sonusAlarmDescription, sonusPolicerTypeStr, 
                      sonusPolicerLevelStr }
--     STATUS          mandatory
    DESCRIPTION     
            "The sonusNodePolicerMajorAlarmNotification indicates
             a system policer major level alarm."
    ::= 2

sonusSbxNodePolicerClearAlarmNotification TRAP-TYPE
    ENTERPRISE      sonusIpmMIBNotifications
    VARIABLES       { sonusAlarmNodeID, sonusAlarmLevel, 
                      sonusAlarmSequenceId, sonusAlarmTime, 
                      sonusAlarmDescription, sonusPolicerTypeStr }
--     STATUS          mandatory
    DESCRIPTION     
            "The sonusNodePolicerClearAlarmNotification indicates
             a system policer alarm clear."
    ::= 3

sonusSbxDBLActionMajorNotification TRAP-TYPE
    ENTERPRISE      sonusIpmMIBNotifications
    VARIABLES       { sonusAlarmNodeID, sonusAlarmLevel, 
                      sonusAlarmSequenceId, sonusAlarmTime, 
                      sonusAlarmDescription, sonusDBLAddressContextName }
--     STATUS          mandatory
    DESCRIPTION     
            "The sonusSbxDBLActionMajorNotification indicates
             there are one or more DBL entries in the system"
    ::= 4

sonusSbxDBLClearActionMajorNotification TRAP-TYPE
    ENTERPRISE      sonusIpmMIBNotifications
    VARIABLES       { sonusAlarmNodeID, sonusAlarmLevel, 
                      sonusAlarmSequenceId, sonusAlarmTime, 
                      sonusAlarmDescription, sonusDBLAddressContextName }
--     STATUS          mandatory
    DESCRIPTION     
            "The sonusSbxDBLClearActionMajorNotification notifies 
             that there are no DBL entries in the system"
    ::= 5

sonusSbxDBLEnhActionSetNotification TRAP-TYPE
    ENTERPRISE      sonusIpmMIBNotifications
    VARIABLES       { sonusAlarmNodeID, sonusAlarmLevel, 
                      sonusAlarmSequenceId, sonusAlarmTime, 
                      sonusAlarmDescription, sonusDBLAddressContextName, 
                      sonusDBLEndPointInfo, sonusDBLAction, 
                      sonusDBLDuration, sonusDBLCriteria, 
                      sonusDBLProfileRuleInfo }
--     STATUS          mandatory
    DESCRIPTION     
            "The sonusSbxDBLEnhActionSetNotification indicates
             that action has been taken on the endpoint due to
             enhanced DBL enforcements"
    ::= 6

sonusSbxDBLEnhActionClearNotification TRAP-TYPE
    ENTERPRISE      sonusIpmMIBNotifications
    VARIABLES       { sonusAlarmNodeID, sonusAlarmLevel, 
                      sonusAlarmSequenceId, sonusAlarmTime, 
                      sonusAlarmDescription, sonusDBLAddressContextName, 
                      sonusDBLEndPointInfo, sonusDBLAction, 
                      sonusDBLDuration, sonusDBLCriteria, 
                      sonusDBLProfileRuleInfo }
--     STATUS          mandatory
    DESCRIPTION     
            "The sonusSbxDBLEnhActionClearNotification notifies 
             that action which had been taken on the endpoint is now
             cleared"
    ::= 7

sonusSbxDBLActionEndpointInfoNotification TRAP-TYPE
    ENTERPRISE      sonusIpmMIBNotifications
    VARIABLES       { sonusAlarmNodeID, sonusAlarmLevel, 
                      sonusAlarmSequenceId, sonusAlarmTime, 
                      sonusAlarmDescription, sonusDBLAddressContextName, 
                      sonusDBLEndPointInfo, sonusDBLEventName, 
                      sonusDBLAction, sonusDBLDuration, 
                      sonusDBLProfileRuleInfo }
--     STATUS          mandatory
    DESCRIPTION     
            "The sonusSbxDBLActionEndpointInfoNotification indicates 
             that action has been taken on the endpoint due to 
             the DBL enforcements."
    ::= 8

sonusSbxDBLClearActionEndpointInfoNotification TRAP-TYPE
    ENTERPRISE      sonusIpmMIBNotifications
    VARIABLES       { sonusAlarmNodeID, sonusAlarmLevel, 
                      sonusAlarmSequenceId, sonusAlarmTime, 
                      sonusAlarmDescription, sonusDBLAddressContextName, 
                      sonusDBLEndPointInfo, sonusDBLEventName, 
                      sonusDBLAction, sonusDBLDuration, 
                      sonusDBLProfileRuleInfo }
--     STATUS          mandatory
    DESCRIPTION     
            "The sonusSbxDBLClearActionEndpointInfoNotification notifies 
             that action which had been taken on the endpoint is now cleared"
    ::= 9

sonusSbxNrsIpInterfaceOOSNotification TRAP-TYPE
    ENTERPRISE      sonusNrsMIBNotifications
    VARIABLES       { sonusAlarmNodeID, sonusAlarmLevel, 
                      sonusAlarmSequenceId, sonusAlarmTime, 
                      sonusAlarmDescription, sonusNrsAddressContextName, 
                      sonusNrsIpInterfaceGroupName, 
                      sonusNrsIpInterfaceName }
--     STATUS          mandatory
    DESCRIPTION     
            "The IP Interface is out of service."
    ::= 1

sonusSbxNrsIpInterfaceISNotification TRAP-TYPE
    ENTERPRISE      sonusNrsMIBNotifications
    VARIABLES       { sonusAlarmNodeID, sonusAlarmLevel, 
                      sonusAlarmSequenceId, sonusAlarmTime, 
                      sonusAlarmDescription, sonusNrsAddressContextName, 
                      sonusNrsIpInterfaceGroupName, 
                      sonusNrsIpInterfaceName }
--     STATUS          mandatory
    DESCRIPTION     
            "The IP Interface is in service."
    ::= 2

sonusSbxNrsIpInterfaceAdminDisabledNotification TRAP-TYPE
    ENTERPRISE      sonusNrsMIBNotifications
    VARIABLES       { sonusAlarmNodeID, sonusAlarmLevel, 
                      sonusAlarmSequenceId, sonusAlarmTime, 
                      sonusAlarmDescription, sonusNrsAddressContextName, 
                      sonusNrsIpInterfaceGroupName, 
                      sonusNrsIpInterfaceName }
--     STATUS          mandatory
    DESCRIPTION     
            "The IP Interface was administratively disabled."
    ::= 3

sonusSbxNrsIpInterfaceAdminEnabledNotification TRAP-TYPE
    ENTERPRISE      sonusNrsMIBNotifications
    VARIABLES       { sonusAlarmNodeID, sonusAlarmLevel, 
                      sonusAlarmSequenceId, sonusAlarmTime, 
                      sonusAlarmDescription, sonusNrsAddressContextName, 
                      sonusNrsIpInterfaceGroupName, 
                      sonusNrsIpInterfaceName }
--     STATUS          mandatory
    DESCRIPTION     
            "The IP Interface was administratively enabled"
    ::= 4

sonusSbxNrsIpInterfaceAdminOOSNotification TRAP-TYPE
    ENTERPRISE      sonusNrsMIBNotifications
    VARIABLES       { sonusAlarmNodeID, sonusAlarmLevel, 
                      sonusAlarmSequenceId, sonusAlarmTime, 
                      sonusAlarmDescription, sonusNrsAddressContextName, 
                      sonusNrsIpInterfaceGroupName, 
                      sonusNrsIpInterfaceName }
--     STATUS          mandatory
    DESCRIPTION     
            "The IP Interface was administratively placed out of service."
    ::= 5

sonusSbxNrsIpInterfaceAdminISNotification TRAP-TYPE
    ENTERPRISE      sonusNrsMIBNotifications
    VARIABLES       { sonusAlarmNodeID, sonusAlarmLevel, 
                      sonusAlarmSequenceId, sonusAlarmTime, 
                      sonusAlarmDescription, sonusNrsAddressContextName, 
                      sonusNrsIpInterfaceGroupName, 
                      sonusNrsIpInterfaceName }
--     STATUS          mandatory
    DESCRIPTION     
            "The IP Interface was administratively placed in service."
    ::= 6

sonusSbxNrsIpInterfaceAdminDeletedNotification TRAP-TYPE
    ENTERPRISE      sonusNrsMIBNotifications
    VARIABLES       { sonusAlarmNodeID, sonusAlarmLevel, 
                      sonusAlarmSequenceId, sonusAlarmTime, 
                      sonusAlarmDescription, sonusNrsAddressContextName, 
                      sonusNrsIpInterfaceGroupName, 
                      sonusNrsIpInterfaceName }
--     STATUS          obsolete
    DESCRIPTION     
            "The IP Interface was administratively deleted"
    ::= 7

sonusSbxNrsMgmtIpInterfaceAdminDisabledNotification TRAP-TYPE
    ENTERPRISE      sonusNrsMIBNotifications
    VARIABLES       { sonusAlarmNodeID, sonusAlarmLevel, 
                      sonusAlarmSequenceId, sonusAlarmTime, 
                      sonusAlarmDescription, sonusNrsAddressContextName, 
                      sonusNrsIpInterfaceGroupName, 
                      sonusNrsIpInterfaceName }
--     STATUS          mandatory
    DESCRIPTION     
            "The Management IP Interface was administratively disabled."
    ::= 8

sonusSbxNrsMgmtIpInterfaceAdminEnabledNotification TRAP-TYPE
    ENTERPRISE      sonusNrsMIBNotifications
    VARIABLES       { sonusAlarmNodeID, sonusAlarmLevel, 
                      sonusAlarmSequenceId, sonusAlarmTime, 
                      sonusAlarmDescription, sonusNrsAddressContextName, 
                      sonusNrsIpInterfaceGroupName, 
                      sonusNrsIpInterfaceName }
--     STATUS          mandatory
    DESCRIPTION     
            "The Management IP Interface was administratively enabled."
    ::= 9

sonusSbxNrsMgmtPortAdminDisabledNotification TRAP-TYPE
    ENTERPRISE      sonusNrsMIBNotifications
    VARIABLES       { sonusAlarmNodeID, sonusAlarmLevel, 
                      sonusAlarmSequenceId, sonusAlarmTime, 
                      sonusAlarmDescription, sonusNrsCeName, 
                      sonusNrsPortName }
--     STATUS          mandatory
    DESCRIPTION     
            "The Management Port was administratively disabled."
    ::= 10

sonusSbxNrsMgmtPortAdminEnabledNotification TRAP-TYPE
    ENTERPRISE      sonusNrsMIBNotifications
    VARIABLES       { sonusAlarmNodeID, sonusAlarmLevel, 
                      sonusAlarmSequenceId, sonusAlarmTime, 
                      sonusAlarmDescription, sonusNrsCeName, 
                      sonusNrsPortName }
--     STATUS          mandatory
    DESCRIPTION     
            "The Management Port was administratively enabled."
    ::= 11

sonusSbxNrsMgmtPortIpInterfaceDeletedNotification TRAP-TYPE
    ENTERPRISE      sonusNrsMIBNotifications
    VARIABLES       { sonusAlarmNodeID, sonusAlarmLevel, 
                      sonusAlarmSequenceId, sonusAlarmTime, 
                      sonusAlarmDescription, sonusNrsAddressContextName, 
                      sonusNrsIpInterfaceGroupName, 
                      sonusNrsIpInterfaceName }
--     STATUS          obsolete
    DESCRIPTION     
            "The Management Port was administratively deleted."
    ::= 12

sonusSbxNrsPacketPortDownNotification TRAP-TYPE
    ENTERPRISE      sonusNrsMIBNotifications
    VARIABLES       { sonusAlarmNodeID, sonusAlarmLevel, 
                      sonusAlarmSequenceId, sonusAlarmTime, 
                      sonusAlarmDescription, sonusNrsCeName, 
                      sonusNrsPortName }
--     STATUS          mandatory
    DESCRIPTION     
            "The packet port is down."
    ::= 13

sonusSbxNrsPacketPortUpNotification TRAP-TYPE
    ENTERPRISE      sonusNrsMIBNotifications
    VARIABLES       { sonusAlarmNodeID, sonusAlarmLevel, 
                      sonusAlarmSequenceId, sonusAlarmTime, 
                      sonusAlarmDescription, sonusNrsCeName, 
                      sonusNrsPortName }
--     STATUS          mandatory
    DESCRIPTION     
            "The packet port is up."
    ::= 14

sonusSbxNrsMgmtPortDownNotification TRAP-TYPE
    ENTERPRISE      sonusNrsMIBNotifications
    VARIABLES       { sonusAlarmNodeID, sonusAlarmLevel, 
                      sonusAlarmSequenceId, sonusAlarmTime, 
                      sonusAlarmDescription, sonusNrsCeName, 
                      sonusNrsPortName }
--     STATUS          mandatory
    DESCRIPTION     
            "The Management IP Interface is down."
    ::= 15

sonusSbxNrsMgmtPortUpNotification TRAP-TYPE
    ENTERPRISE      sonusNrsMIBNotifications
    VARIABLES       { sonusAlarmNodeID, sonusAlarmLevel, 
                      sonusAlarmSequenceId, sonusAlarmTime, 
                      sonusAlarmDescription, sonusNrsCeName, 
                      sonusNrsPortName }
--     STATUS          mandatory
    DESCRIPTION     
            "The Management IP Interface is up"
    ::= 16

sonusSbxNrsIpInterfaceLinkMonitorDownNotification TRAP-TYPE
    ENTERPRISE      sonusNrsMIBNotifications
    VARIABLES       { sonusAlarmNodeID, sonusAlarmLevel, 
                      sonusAlarmSequenceId, sonusAlarmTime, 
                      sonusAlarmDescription, sonusNrsAddressContextName, 
                      sonusNrsIpInterfaceName, sonusNrsIpAddress }
--     STATUS          mandatory
    DESCRIPTION     
            "The destination IP Interface is down."
    ::= 17

sonusSbxNrsIpInterfaceLinkMonitorUpNotification TRAP-TYPE
    ENTERPRISE      sonusNrsMIBNotifications
    VARIABLES       { sonusAlarmNodeID, sonusAlarmLevel, 
                      sonusAlarmSequenceId, sonusAlarmTime, 
                      sonusAlarmDescription, sonusNrsAddressContextName, 
                      sonusNrsIpInterfaceName, sonusNrsIpAddress }
--     STATUS          mandatory
    DESCRIPTION     
            "The destination IP Interface is up."
    ::= 18

sonusSbxNrsLogMgmtIpInterfaceAdminEnabledNotification TRAP-TYPE
    ENTERPRISE      sonusNrsMIBNotifications
    VARIABLES       { sonusAlarmNodeID, sonusAlarmLevel, 
                      sonusAlarmSequenceId, sonusAlarmTime, 
                      sonusAlarmDescription, sonusNrsIpInterfaceName }
--     STATUS          mandatory
    DESCRIPTION     
            "The Logical Management IP Interface was administratively enabled."
    ::= 19

sonusSbxNrsLogMgmtIpInterfaceAdminDisabledNotification TRAP-TYPE
    ENTERPRISE      sonusNrsMIBNotifications
    VARIABLES       { sonusAlarmNodeID, sonusAlarmLevel, 
                      sonusAlarmSequenceId, sonusAlarmTime, 
                      sonusAlarmDescription, sonusNrsIpInterfaceName }
--     STATUS          mandatory
    DESCRIPTION     
            "The Logical Management Port was administratively disabled."
    ::= 20

sonusSbxNrsIpInterfaceLinkMonitorDownNotificationV6 TRAP-TYPE
    ENTERPRISE      sonusNrsMIBNotifications
    VARIABLES       { sonusAlarmNodeID, sonusAlarmLevel, 
                      sonusAlarmSequenceId, sonusAlarmTime, 
                      sonusAlarmDescription, sonusNrsAddressContextName, 
                      sonusNrsIpInterfaceName, sonusNrsIpAddressV6 }
--     STATUS          mandatory
    DESCRIPTION     
            "The destination IP Interface is down."
    ::= 21

sonusSbxNrsIpInterfaceLinkMonitorUpNotificationV6 TRAP-TYPE
    ENTERPRISE      sonusNrsMIBNotifications
    VARIABLES       { sonusAlarmNodeID, sonusAlarmLevel, 
                      sonusAlarmSequenceId, sonusAlarmTime, 
                      sonusAlarmDescription, sonusNrsAddressContextName, 
                      sonusNrsIpInterfaceName, sonusNrsIpAddressV6 }
--     STATUS          mandatory
    DESCRIPTION     
            "The destination IP Interface is up."
    ::= 22

sonusSbxNrsMediaPortDownNoLicenseNotification TRAP-TYPE
    ENTERPRISE      sonusNrsMIBNotifications
    VARIABLES       { sonusAlarmNodeID, sonusAlarmLevel, 
                      sonusAlarmSequenceId, sonusAlarmTime, 
                      sonusAlarmDescription, sonusNrsCeName, 
                      sonusNrsPortName }
--     STATUS          mandatory
    DESCRIPTION     
            "The media port is down due to no license present."
    ::= 23

sonusSbxNrsMediaPortDownNoLicenseClearedNotification TRAP-TYPE
    ENTERPRISE      sonusNrsMIBNotifications
    VARIABLES       { sonusAlarmNodeID, sonusAlarmLevel, 
                      sonusAlarmSequenceId, sonusAlarmTime, 
                      sonusAlarmDescription, sonusNrsCeName, 
                      sonusNrsPortName }
--     STATUS          mandatory
    DESCRIPTION     
            "The media port is no longer down due to no license present."
    ::= 24

sonusSbxNrsMediaPortInvalidSfpNotification TRAP-TYPE
    ENTERPRISE      sonusNrsMIBNotifications
    VARIABLES       { sonusAlarmNodeID, sonusAlarmLevel, 
                      sonusAlarmSequenceId, sonusAlarmTime, 
                      sonusAlarmDescription, sonusNrsCeName, 
                      sonusNrsPortName, sonusNrsInvalidSfpReason }
--     STATUS          mandatory
    DESCRIPTION     
            "An invalid SFP is plugged in to the port."
    ::= 25

sonusSbxNrsMediaPortInvalidSfpClearedNotification TRAP-TYPE
    ENTERPRISE      sonusNrsMIBNotifications
    VARIABLES       { sonusAlarmNodeID, sonusAlarmLevel, 
                      sonusAlarmSequenceId, sonusAlarmTime, 
                      sonusAlarmDescription, sonusNrsCeName, 
                      sonusNrsPortName, sonusNrsInvalidSfpReason }
--     STATUS          mandatory
    DESCRIPTION     
            "An invalid SFP is no longer plugged into the port."
    ::= 26

sonusNrsNifHighWatermarkNotification TRAP-TYPE
    ENTERPRISE      sonusNrsMIBNotifications
    VARIABLES       { sonusAlarmNodeID, sonusAlarmLevel, 
                      sonusAlarmSequenceId, sonusAlarmTime, 
                      sonusAlarmDescription, sonusNifPort, sonusNifIndex, 
                      sonusNrsPortName }
--     STATUS          mandatory
    DESCRIPTION     
            "This trap indicates that a NIF's high watermark has been reached 
             the first time since the NIF's low watermark has beend reached."
    ::= 27

sonusNrsNifLowWatermarkNotification TRAP-TYPE
    ENTERPRISE      sonusNrsMIBNotifications
    VARIABLES       { sonusAlarmNodeID, sonusAlarmLevel, 
                      sonusAlarmSequenceId, sonusAlarmTime, 
                      sonusAlarmDescription, sonusNifPort, sonusNifIndex, 
                      sonusNrsPortName }
--     STATUS          mandatory
    DESCRIPTION     
            "This trap indicates that a NIF's low watermark has been reached
             the first time since the NIF's high watermark has been reached."
    ::= 28

sonusH248ScDisconnectedTxNotification TRAP-TYPE
    ENTERPRISE      sonusBgfMIBNotifications
    VARIABLES       { sonusAlarmNodeID, sonusAlarmLevel, 
                      sonusAlarmSequenceId, sonusAlarmTime, 
                      sonusAlarmDescription, sonusH248SigRemoteIpAddr, 
                      sonusH248SigLocalIpAddr, sonusH248SigScMethod, 
                      sonusH248SigMid }
--     STATUS          mandatory
    DESCRIPTION     
            "This trap indicates the Service change Disconnected is
             transmitted."
    ::= 1

sonusH248ScHandoffTxNotification TRAP-TYPE
    ENTERPRISE      sonusBgfMIBNotifications
    VARIABLES       { sonusAlarmNodeID, sonusAlarmLevel, 
                      sonusAlarmSequenceId, sonusAlarmTime, 
                      sonusAlarmDescription, sonusH248SigRemoteIpAddr, 
                      sonusH248SigLocalIpAddr, sonusH248SigScMethod, 
                      sonusH248SigMid }
--     STATUS          deprecated
    DESCRIPTION     
            "This trap indicates the Service change Handoff is
             transmitted."
    ::= 2

sonusH248ScFailoverTxStatusNotification TRAP-TYPE
    ENTERPRISE      sonusBgfMIBNotifications
    VARIABLES       { sonusAlarmNodeID, sonusAlarmLevel, 
                      sonusAlarmSequenceId, sonusAlarmTime, 
                      sonusAlarmDescription, sonusH248SigRemoteIpAddr, 
                      sonusH248SigLocalIpAddr, sonusH248SigScMethod, 
                      sonusH248SigMid, sonusH248SigStatus }
--     STATUS          mandatory
    DESCRIPTION     
            "This trap indicates the Service change Failover 
             transmitted status."
    ::= 3

sonusH248ScFailoverTxNotification TRAP-TYPE
    ENTERPRISE      sonusBgfMIBNotifications
    VARIABLES       { sonusAlarmNodeID, sonusAlarmLevel, 
                      sonusAlarmSequenceId, sonusAlarmTime, 
                      sonusAlarmDescription, sonusH248SigRemoteIpAddr, 
                      sonusH248SigLocalIpAddr, sonusH248SigScMethod, 
                      sonusH248SigMid }
--     STATUS          mandatory
    DESCRIPTION     
            "This trap indicates the Service change Failover is
             transmitted. "
    ::= 4

sonusH248ScHandoffRxNotification TRAP-TYPE
    ENTERPRISE      sonusBgfMIBNotifications
    VARIABLES       { sonusAlarmNodeID, sonusAlarmLevel, 
                      sonusAlarmSequenceId, sonusAlarmTime, 
                      sonusAlarmDescription, sonusH248SigLocalIpAddr, 
                      sonusH248SigScMethod, sonusH248SigMid, 
                      sonusH248SigMid }
--     STATUS          mandatory
    DESCRIPTION     
            "This trap indicates the Service change Handoff 
             is received. "
    ::= 5

sonusH248ScRestartRxNotification TRAP-TYPE
    ENTERPRISE      sonusBgfMIBNotifications
    VARIABLES       { sonusAlarmNodeID, sonusAlarmLevel, 
                      sonusAlarmSequenceId, sonusAlarmTime, 
                      sonusAlarmDescription, sonusH248SigLocalIpAddr, 
                      sonusH248SigScMethod, sonusH248SigMid }
--     STATUS          deprecated
    DESCRIPTION     
            "This trap indicates the Service change Restart 
             is received. "
    ::= 6

sonusH248ScVerNotSupportedNotification TRAP-TYPE
    ENTERPRISE      sonusBgfMIBNotifications
    VARIABLES       { sonusAlarmNodeID, sonusAlarmLevel, 
                      sonusAlarmSequenceId, sonusAlarmTime, 
                      sonusAlarmDescription, sonusH248SigRemoteIpAddr, 
                      sonusH248SigLocalIpAddr, sonusH248SigMid, 
                      sonusH248SpdfName, sonusH248Version }
--     STATUS          deprecated
    DESCRIPTION     
            "This trap indicates the unsuccessful version
             negotiation. "
    ::= 7

sonusH248ScVerNegotiatedNotification TRAP-TYPE
    ENTERPRISE      sonusBgfMIBNotifications
    VARIABLES       { sonusAlarmNodeID, sonusAlarmLevel, 
                      sonusAlarmSequenceId, sonusAlarmTime, 
                      sonusAlarmDescription, sonusH248SigRemoteIpAddr, 
                      sonusH248SigLocalIpAddr, sonusH248SigMid, 
                      sonusH248SpdfName, sonusH248Version }
--     STATUS          deprecated
    DESCRIPTION     
            "This trap indicates the successful version
             negotiation. "
    ::= 8

sonusH248FeatureLicenseExpiryNotification TRAP-TYPE
    ENTERPRISE      sonusBgfMIBNotifications
    VARIABLES       { sonusAlarmNodeID, sonusAlarmLevel, 
                      sonusAlarmSequenceId, sonusAlarmTime, 
                      sonusAlarmDescription, sonusH248FeatureName }
--     STATUS          deprecated
    DESCRIPTION     
            "This trap indicates License expiry 
             notification. "
    ::= 9

sonusH248FeatureLicenseLimitNotification TRAP-TYPE
    ENTERPRISE      sonusBgfMIBNotifications
    VARIABLES       { sonusAlarmNodeID, sonusAlarmLevel, 
                      sonusAlarmSequenceId, sonusAlarmTime, 
                      sonusAlarmDescription, sonusH248FeatureName }
--     STATUS          deprecated
    DESCRIPTION     
            "This trap indicates License Limit is reached
             notification. "
    ::= 10

sonusH248FeatureDisabledNotification TRAP-TYPE
    ENTERPRISE      sonusBgfMIBNotifications
    VARIABLES       { sonusAlarmNodeID, sonusAlarmLevel, 
                      sonusAlarmSequenceId, sonusAlarmTime, 
                      sonusAlarmDescription, sonusH248FeatureName }
--     STATUS          deprecated
    DESCRIPTION     
            "This trap indicates License is Disabled for Feature. "
    ::= 11

sonusH248FeatureEnableNotification TRAP-TYPE
    ENTERPRISE      sonusBgfMIBNotifications
    VARIABLES       { sonusAlarmNodeID, sonusAlarmLevel, 
                      sonusAlarmSequenceId, sonusAlarmTime, 
                      sonusAlarmDescription, sonusH248FeatureName }
--     STATUS          deprecated
    DESCRIPTION     
            "This trap indicates License is Enabled for Feature. "
    ::= 12

sonusH248SigPortOpenNotification TRAP-TYPE
    ENTERPRISE      sonusBgfMIBNotifications
    VARIABLES       { sonusAlarmNodeID, sonusAlarmLevel, 
                      sonusAlarmSequenceId, sonusAlarmTime, 
                      sonusAlarmDescription, sonusH248SigPortIpAddress, 
                      sonusH248SigPortNum, sonusH248SigProto }
--     STATUS          mandatory
    DESCRIPTION     
            "This trap indicates that a H248 signaling port is opened."
    ::= 13

sonusH248SigPortCloseNotification TRAP-TYPE
    ENTERPRISE      sonusBgfMIBNotifications
    VARIABLES       { sonusAlarmNodeID, sonusAlarmLevel, 
                      sonusAlarmSequenceId, sonusAlarmTime, 
                      sonusAlarmDescription, sonusH248SigPortIpAddress, 
                      sonusH248SigPortNum, sonusH248SigProto }
--     STATUS          mandatory
    DESCRIPTION     
            "This trap indicates that a call signaling port is closed."
    ::= 14

sonusH248ScNotificationClear TRAP-TYPE
    ENTERPRISE      sonusBgfMIBNotifications
    VARIABLES       { sonusAlarmNodeID, sonusAlarmLevel, 
                      sonusAlarmSequenceId, sonusAlarmTime, 
                      sonusAlarmDescription, sonusH248SigRemoteIpAddr, 
                      sonusH248SigLocalIpAddr, sonusH248SigScMethod, 
                      sonusH248SigMid }
--     STATUS          mandatory
    DESCRIPTION     
            "This trap indicates the Service change is cleared."
    ::= 15

sonusSbxGwSigChanOpenNotification TRAP-TYPE
    ENTERPRISE      sonusGatewaySignallingMIBNotifications
    VARIABLES       { sonusAlarmNodeID, sonusAlarmLevel, 
                      sonusAlarmSequenceId, sonusAlarmTime, 
                      sonusAlarmDescription, sonusGwRemoteGwAddr }
--     STATUS          mandatory
    DESCRIPTION     
            "This trap indicates that a Call Signaling Link to a Remote Gateway has been sucessfully opened."
    ::= 1

sonusSbxGwSigChanCloseNotification TRAP-TYPE
    ENTERPRISE      sonusGatewaySignallingMIBNotifications
    VARIABLES       { sonusAlarmNodeID, sonusAlarmLevel, 
                      sonusAlarmSequenceId, sonusAlarmTime, 
                      sonusAlarmDescription, sonusGwRemoteGwAddr, 
                      sonusGwCloseReasonCode }
--     STATUS          mandatory
    DESCRIPTION     
            "This trap indicates that a Call Signaling Link to a Remote Gateway has been closed."
    ::= 2

sonusSbxGwSigChanOpenAttemptNotification TRAP-TYPE
    ENTERPRISE      sonusGatewaySignallingMIBNotifications
    VARIABLES       { sonusAlarmNodeID, sonusAlarmLevel, 
                      sonusAlarmSequenceId, sonusAlarmTime, 
                      sonusAlarmDescription, sonusGwRemoteGwAddr }
--     STATUS          mandatory
    DESCRIPTION     
            "This trap indicates that a request to Open a Call Signaling Link has been sent to a Remote Gateway."
    ::= 3

sonusSbxGwSigChanRetryTimerExpiredNotification TRAP-TYPE
    ENTERPRISE      sonusGatewaySignallingMIBNotifications
    VARIABLES       { sonusAlarmNodeID, sonusAlarmLevel, 
                      sonusAlarmSequenceId, sonusAlarmTime, 
                      sonusAlarmDescription, sonusGwRemoteGwAddr }
--     STATUS          mandatory
    DESCRIPTION     
            "This trap indicates that attempts to recover a Call Signaling Link to a Remote GW have failed."
    ::= 4

sonusSbxGwTrunkGroupInServiceNotification TRAP-TYPE
    ENTERPRISE      sonusGatewaySignallingMIBNotifications
    VARIABLES       { sonusAlarmNodeID, sonusAlarmLevel, 
                      sonusAlarmSequenceId, sonusAlarmTime, 
                      sonusAlarmDescription, sonusGwSigTgName }
--     STATUS          mandatory
    DESCRIPTION     
            "This trap indicates that the Gateway Trunk Group was put
             into service by maintenance staff."
    ::= 5

sonusSbxGwSigTrunkGroupOutOfServiceNotification TRAP-TYPE
    ENTERPRISE      sonusGatewaySignallingMIBNotifications
    VARIABLES       { sonusAlarmNodeID, sonusAlarmLevel, 
                      sonusAlarmSequenceId, sonusAlarmTime, 
                      sonusAlarmDescription, sonusGwSigTgName }
--     STATUS          mandatory
    DESCRIPTION     
            "This trap indicates that the Gateway Trunk Group was taken
             out of service by maintenance staff."
    ::= 6

sonusSbxGwSigChanOpenNotificationV6 TRAP-TYPE
    ENTERPRISE      sonusGatewaySignallingMIBNotifications
    VARIABLES       { sonusAlarmNodeID, sonusAlarmLevel, 
                      sonusAlarmSequenceId, sonusAlarmTime, 
                      sonusAlarmDescription, sonusGwRemoteGw6Addr }
--     STATUS          mandatory
    DESCRIPTION     
            "This trap indicates that a Call Signaling IPV6 Link to a Remote Gateway has been sucessfully opened."
    ::= 7

sonusSbxGwSigChanOpenAttemptNotificationV6 TRAP-TYPE
    ENTERPRISE      sonusGatewaySignallingMIBNotifications
    VARIABLES       { sonusAlarmNodeID, sonusAlarmLevel, 
                      sonusAlarmSequenceId, sonusAlarmTime, 
                      sonusAlarmDescription, sonusGwRemoteGw6Addr }
--     STATUS          mandatory
    DESCRIPTION     
            "This trap indicates that a request to Open a Call Signaling IPV6 Link has been sent to a Remote Gateway."
    ::= 8

sonusSbxGwSigChanRetryTimerExpiredNotificationV6 TRAP-TYPE
    ENTERPRISE      sonusGatewaySignallingMIBNotifications
    VARIABLES       { sonusAlarmNodeID, sonusAlarmLevel, 
                      sonusAlarmSequenceId, sonusAlarmTime, 
                      sonusAlarmDescription, sonusGwRemoteGw6Addr }
--     STATUS          mandatory
    DESCRIPTION     
            "This trap indicates that attempts to recover a Call Signaling IPV6 Link to a Remote GW have failed."
    ::= 9

sonusSbxGwSigChanCloseNotificationV6 TRAP-TYPE
    ENTERPRISE      sonusGatewaySignallingMIBNotifications
    VARIABLES       { sonusAlarmNodeID, sonusAlarmLevel, 
                      sonusAlarmSequenceId, sonusAlarmTime, 
                      sonusAlarmDescription, sonusGwRemoteGw6Addr, 
                      sonusGwCloseReasonCode }
--     STATUS          mandatory
    DESCRIPTION     
            "This trap indicates that a IPV6 Call Signaling Link to a Remote Gateway has been closed."
    ::= 10

sonusSbxCallRejectsDueToSessionLicenseNotification TRAP-TYPE
    ENTERPRISE      sonusOrcaLicenseMIBNotifications
    VARIABLES       { sonusAlarmNodeID, sonusAlarmLevel, 
                      sonusAlarmSequenceId, sonusAlarmTime, 
                      sonusAlarmDescription, sonusSessLicenseLimit }
--     STATUS          mandatory
    DESCRIPTION     
            "This Trap is generated when either pass-through or
             transcoded sessions fail to setup due to the lack of a 
             valid session license or if the total number of active 
             sessions has reached the session license limits thereby 
             unable to complete newer calls."
    ::= 1

sonusSbxCallRejectsDueToSessionLicenseClearNotification TRAP-TYPE
    ENTERPRISE      sonusOrcaLicenseMIBNotifications
    VARIABLES       { sonusAlarmNodeID, sonusAlarmLevel, 
                      sonusAlarmSequenceId, sonusAlarmTime, 
                      sonusAlarmDescription, sonusSessLicenseLimit }
--     STATUS          mandatory
    DESCRIPTION     
            "This Trap is not actually raised, but used to fool the alarm framework.
             If an application raises this trap, the comment has to be revisited"
    ::= 2

sonusSbxLicensedSessionsThresholdReachedNotification TRAP-TYPE
    ENTERPRISE      sonusOrcaLicenseMIBNotifications
    VARIABLES       { sonusAlarmNodeID, sonusAlarmLevel, 
                      sonusAlarmSequenceId, sonusAlarmTime, 
                      sonusAlarmDescription, sonusConcurrentCalls, 
                      sonusSessLicenseLimit, sonusSessionsThreshold }
--     STATUS          mandatory
    DESCRIPTION     
            "This trap indicates the licensed sessions notification threshold has been reached or exceeded."
    ::= 3

sonusSbxCallRejectsDueToNotAbleToAcquireAdvancedERELicense TRAP-TYPE
    ENTERPRISE      sonusOrcaLicenseMIBNotifications
    VARIABLES       { sonusAlarmNodeID, sonusAlarmLevel, 
                      sonusAlarmSequenceId, sonusAlarmTime, 
                      sonusAlarmDescription, sonusAlarmName, 
                      sonusAlarmReason }
--     STATUS          deprecated
    DESCRIPTION     
            "This Trap is generated when the system is unable to proceed to call 
             processing due to the inability to acquire an Advanced ERE license.
             ."
    ::= 4

sonusSbxAcquiredAdvancedERELicenseNotification TRAP-TYPE
    ENTERPRISE      sonusOrcaLicenseMIBNotifications
    VARIABLES       { sonusAlarmNodeID, sonusAlarmLevel, 
                      sonusAlarmSequenceId, sonusAlarmTime, 
                      sonusAlarmDescription, sonusAlarmName, 
                      sonusAlarmReason }
--     STATUS          deprecated
    DESCRIPTION     
            "This is clearing as SBX aquired an Advanced ERE license."
    ::= 5

sonusSbxMinimumLicenseCountThresholdNotReached TRAP-TYPE
    ENTERPRISE      sonusOrcaLicenseMIBNotifications
    VARIABLES       { sonusAlarmNodeID, sonusAlarmLevel, 
                      sonusAlarmSequenceId, sonusAlarmTime, 
                      sonusAlarmDescription, sonusAlarmName, 
                      sonusSessionsThreshold, sonusSessLicenseLimit }
--     STATUS          mandatory
    DESCRIPTION     
            "This Trap is generated when when the SBC-POL-RTU license is configured with a 
             minimum threshold (this will match the SBC-RTU minimum license count) that cannot 
             be returned by the site license server."
    ::= 6

sonusSbxClearMinimumLicenseCountThresholdNotReached TRAP-TYPE
    ENTERPRISE      sonusOrcaLicenseMIBNotifications
    VARIABLES       { sonusAlarmNodeID, sonusAlarmLevel, 
                      sonusAlarmSequenceId, sonusAlarmTime, 
                      sonusAlarmDescription, sonusAlarmName, 
                      sonusSessionsThreshold, sonusSessLicenseLimit }
--     STATUS          mandatory
    DESCRIPTION     
            "Clear the trap ."
    ::= 7

sonusSbxMaximumLicenseCountThresholdExceeded TRAP-TYPE
    ENTERPRISE      sonusOrcaLicenseMIBNotifications
    VARIABLES       { sonusAlarmNodeID, sonusAlarmLevel, 
                      sonusAlarmSequenceId, sonusAlarmTime, 
                      sonusAlarmDescription, sonusAlarmName, 
                      sonusSessionsThreshold, sonusSessLicenseLimit }
--     STATUS          mandatory
    DESCRIPTION     
            "This Trap is generated when when the SBC-POL-RTU license is configured with a maximum 
             threshold (this will match the SBC-RTU maximum license count) that is lower than the 
             current license count returned by the site license server.when the SBC-POL-RTU license 
             is configured with a maximum threshold (this will match the SBC-RTU maximum license count) 
             that is lower than the current license count returned by the site license server."
    ::= 8

sonusSbxClearMaximumLicenseCountThresholdExceeded TRAP-TYPE
    ENTERPRISE      sonusOrcaLicenseMIBNotifications
    VARIABLES       { sonusAlarmNodeID, sonusAlarmLevel, 
                      sonusAlarmSequenceId, sonusAlarmTime, 
                      sonusAlarmDescription, sonusAlarmName, 
                      sonusSessionsThreshold, sonusSessLicenseLimit }
--     STATUS          mandatory
    DESCRIPTION     
            "Clear the trap ."
    ::= 9

sonusSbxLicensedEncryptSessionsThresholdReachedNotification TRAP-TYPE
    ENTERPRISE      sonusOrcaLicenseMIBNotifications
    VARIABLES       { sonusAlarmNodeID, sonusAlarmLevel, 
                      sonusAlarmSequenceId, sonusAlarmTime, 
                      sonusAlarmDescription, sonusSessionsThreshold, 
                      sonusActiveSessionCount, sonusSessLicenseLimit }
--     STATUS          deprecated
    DESCRIPTION     
            "This trap is only applicable when the SBC is using local licenses.
             configured threshold is reached for ENCRYPT sessions."
    ::= 10

sonusSbxServiceDeniedDueToUnavailableLicenseNotification TRAP-TYPE
    ENTERPRISE      sonusOrcaLicenseMIBNotifications
    VARIABLES       { sonusAlarmNodeID, sonusAlarmLevel, 
                      sonusAlarmSequenceId, sonusAlarmTime, 
                      sonusAlarmDescription, sonusAlarmName, 
                      sonusActiveSessionCount }
--     STATUS          deprecated
    DESCRIPTION     
            "A licensed service has been denied due to lack of licenses.
             This trap is only applicable when the SBC is using Local/Network licenses."
    ::= 11

sonusSbxLicensedSrtpSessionsThresholdReachedNotification TRAP-TYPE
    ENTERPRISE      sonusOrcaLicenseMIBNotifications
    VARIABLES       { sonusAlarmNodeID, sonusAlarmLevel, 
                      sonusAlarmSequenceId, sonusAlarmTime, 
                      sonusAlarmDescription, sonusSessionsThreshold, 
                      sonusActiveSessionCount, sonusSessLicenseLimit }
--     STATUS          deprecated
    DESCRIPTION     
            "This trap is fired when configured threshold is reached for SRTP session
             only in LOCAL mode."
    ::= 12

sonusSbxLicensedVideoSessionsThresholdReachedNotification TRAP-TYPE
    ENTERPRISE      sonusOrcaLicenseMIBNotifications
    VARIABLES       { sonusAlarmNodeID, sonusAlarmLevel, 
                      sonusAlarmSequenceId, sonusAlarmTime, 
                      sonusAlarmDescription, sonusSessionsThreshold, 
                      sonusActiveSessionCount, sonusSessLicenseLimit }
--     STATUS          deprecated
    DESCRIPTION     
            "This trap is fired when configured threshold is reached for VIDEO session
             only in LOCAL mode."
    ::= 13

sonusSbxLicensedAmrNbSessionsThresholdReachedNotification TRAP-TYPE
    ENTERPRISE      sonusOrcaLicenseMIBNotifications
    VARIABLES       { sonusAlarmNodeID, sonusAlarmLevel, 
                      sonusAlarmSequenceId, sonusAlarmTime, 
                      sonusAlarmDescription, sonusSessionsThreshold, 
                      sonusActiveSessionCount, sonusSessLicenseLimit }
--     STATUS          mandatory
    DESCRIPTION     
            "This trap is only applicable when the SBC is using local licenses and
             configured threshold is reached for AMRNB sessions."
    ::= 14

sonusSbxLicensedAmrWbSessionsThresholdReachedNotification TRAP-TYPE
    ENTERPRISE      sonusOrcaLicenseMIBNotifications
    VARIABLES       { sonusAlarmNodeID, sonusAlarmLevel, 
                      sonusAlarmSequenceId, sonusAlarmTime, 
                      sonusAlarmDescription, sonusSessionsThreshold, 
                      sonusActiveSessionCount, sonusSessLicenseLimit }
--     STATUS          mandatory
    DESCRIPTION     
            "This trap is only applicable when the SBC is using local licenses and
             configured threshold is reached for AMRWB sessions."
    ::= 15

sonusSbxLicensedEvrcSessionsThresholdReachedNotification TRAP-TYPE
    ENTERPRISE      sonusOrcaLicenseMIBNotifications
    VARIABLES       { sonusAlarmNodeID, sonusAlarmLevel, 
                      sonusAlarmSequenceId, sonusAlarmTime, 
                      sonusAlarmDescription, sonusSessionsThreshold, 
                      sonusActiveSessionCount, sonusSessLicenseLimit }
--     STATUS          mandatory
    DESCRIPTION     
            "This trap is only applicable when the SBC is using local licenses and
             configured threshold is reached for EVRC sessions."
    ::= 16

sonusSbxLicensedNiceRecThresholdReachedNotification TRAP-TYPE
    ENTERPRISE      sonusOrcaLicenseMIBNotifications
    VARIABLES       { sonusAlarmNodeID, sonusAlarmLevel, 
                      sonusAlarmSequenceId, sonusAlarmTime, 
                      sonusAlarmDescription, sonusSessionsThreshold, 
                      sonusActiveSessionCount, sonusSessLicenseLimit }
--     STATUS          deprecated
    DESCRIPTION     
            "This trap is only applicable when the SBC is using local licenses and
             configured threshold is reached for Nice Rec  sessions."
    ::= 17

sonusSbxLicensedSipRecThresholdReachedNotification TRAP-TYPE
    ENTERPRISE      sonusOrcaLicenseMIBNotifications
    VARIABLES       { sonusAlarmNodeID, sonusAlarmLevel, 
                      sonusAlarmSequenceId, sonusAlarmTime, 
                      sonusAlarmDescription, sonusSessionsThreshold, 
                      sonusActiveSessionCount, sonusSessLicenseLimit }
--     STATUS          deprecated
    DESCRIPTION     
            "This trap is only applicable when the SBC is using local licenses and
             configured threshold is reached for SIPREC sessions."
    ::= 18

sonusSbxLicensedVdspThresholdReachedNotification TRAP-TYPE
    ENTERPRISE      sonusOrcaLicenseMIBNotifications
    VARIABLES       { sonusAlarmNodeID, sonusAlarmLevel, 
                      sonusAlarmSequenceId, sonusAlarmTime, 
                      sonusAlarmDescription, sonusSessionsThreshold, 
                      sonusActiveSessionCount, sonusSessLicenseLimit }
--     STATUS          mandatory
    DESCRIPTION     
            "This trap is only applicable when the SBC is using local licenses and
             configured threshold is reached for VDSP sessions."
    ::= 19

sonusSbxLicensedMrfSessionsThresholdReachedNotification TRAP-TYPE
    ENTERPRISE      sonusOrcaLicenseMIBNotifications
    VARIABLES       { sonusAlarmNodeID, sonusAlarmLevel, 
                      sonusAlarmSequenceId, sonusAlarmTime, 
                      sonusAlarmDescription, sonusSessionsThreshold, 
                      sonusActiveSessionCount, sonusSessLicenseLimit }
--     STATUS          deprecated
    DESCRIPTION     
            "This trap is only applicable when the SBC is using local licenses and
             configured threshold is reached for MRF sessions."
    ::= 20

sonusSbxMandatoryLicenseUnavailable TRAP-TYPE
    ENTERPRISE      sonusOrcaLicenseMIBNotifications
    VARIABLES       { sonusAlarmNodeID, sonusAlarmLevel, 
                      sonusAlarmSequenceId, sonusAlarmTime, 
                      sonusAlarmDescription, sonusAlarmName }
--     STATUS          mandatory
    DESCRIPTION     
            "This Alarm is generated when Mandatory licenses are specified in the RLT but 
             the SLS was unable to return at least 1 license of each mandatory license specified.
             Mandatory Licenses : SBC-RTU, SWE-INSTANCE,SBC-PSX-RTU,SBC-POL-RTU.
             ."
    ::= 21

sonusSbxMandatoryLicenseAvailable TRAP-TYPE
    ENTERPRISE      sonusOrcaLicenseMIBNotifications
    VARIABLES       { sonusAlarmNodeID, sonusAlarmLevel, 
                      sonusAlarmSequenceId, sonusAlarmTime, 
                      sonusAlarmDescription, sonusAlarmName }
--     STATUS          mandatory
    DESCRIPTION     
            "Mandatory license successfully retrieved from the license server.
             Mandatory Licenses : SBC-RTU, SWE-INSTANCE,SBC-PSX-RTU,SBC-POL-RTU."
    ::= 22

sonusSbxServiceLicenseUnavailable TRAP-TYPE
    ENTERPRISE      sonusOrcaLicenseMIBNotifications
    VARIABLES       { sonusAlarmNodeID, sonusAlarmLevel, 
                      sonusAlarmSequenceId, sonusAlarmTime, 
                      sonusAlarmDescription, sonusAlarmName }
--     STATUS          mandatory
    DESCRIPTION     
            "This Alarm is generated when Service licenses are specified in the RLT but 
             the SLS was unable to return at least 1 license of each mandatory license specified.
             ."
    ::= 23

sonusSbxServiceLicenseAvailable TRAP-TYPE
    ENTERPRISE      sonusOrcaLicenseMIBNotifications
    VARIABLES       { sonusAlarmNodeID, sonusAlarmLevel, 
                      sonusAlarmSequenceId, sonusAlarmTime, 
                      sonusAlarmDescription, sonusAlarmName }
--     STATUS          mandatory
    DESCRIPTION     
            "The licensed service functionality will be Allowed."
    ::= 24

sonusSbxLicensedServiceDeniedDueToLicenseLimit TRAP-TYPE
    ENTERPRISE      sonusOrcaLicenseMIBNotifications
    VARIABLES       { sonusAlarmNodeID, sonusAlarmLevel, 
                      sonusAlarmSequenceId, sonusAlarmTime, 
                      sonusAlarmDescription, sonusAlarmName, 
                      sonusActiveSessionCount }
--     STATUS          mandatory
    DESCRIPTION     
            "A licensed service has been denied due to lack of licenses.
             This trap is only applicable when the SBC is using Local/Network licenses."
    ::= 25

sonusSbxLicensedEvsSessionsThresholdReachedNotification TRAP-TYPE
    ENTERPRISE      sonusOrcaLicenseMIBNotifications
    VARIABLES       { sonusAlarmNodeID, sonusAlarmLevel, 
                      sonusAlarmSequenceId, sonusAlarmTime, 
                      sonusAlarmDescription, sonusSessionsThreshold, 
                      sonusActiveSessionCount, sonusSessLicenseLimit }
--     STATUS          mandatory
    DESCRIPTION     
            "This trap is only applicable when the SBC is using local licenses and
             configured threshold is reached for EVS sessions."
    ::= 28

sonusSbxCallRejectsDueToSlbSessionLicenseNotification TRAP-TYPE
    ENTERPRISE      sonusOrcaLicenseMIBNotifications
    VARIABLES       { sonusAlarmNodeID, sonusAlarmLevel, 
                      sonusAlarmSequenceId, sonusAlarmTime, 
                      sonusAlarmDescription, sonusSessLicenseLimit }
--     STATUS          mandatory
    DESCRIPTION     
            "This Trap is generated when either pass-through or
             transcoded sessions fail to setup due to the lack of a 
             valid slb session license or if the total number of active 
             slb sessions has reached the slb session license limits thereby 
             unable to complete newer calls."
    ::= 29

sonusSbxLicensedSlbSessionsThresholdReachedNotification TRAP-TYPE
    ENTERPRISE      sonusOrcaLicenseMIBNotifications
    VARIABLES       { sonusAlarmNodeID, sonusAlarmLevel, 
                      sonusAlarmSequenceId, sonusAlarmTime, 
                      sonusAlarmDescription, sonusConcurrentCalls, 
                      sonusSessLicenseLimit, sonusSessionsThreshold }
--     STATUS          mandatory
    DESCRIPTION     
            "This trap indicates the licensed slb sessions notification threshold has been reached or exceeded."
    ::= 30

sonusSbxFeatureLicenseUnavailable TRAP-TYPE
    ENTERPRISE      sonusOrcaLicenseMIBNotifications
    VARIABLES       { sonusAlarmNodeID, sonusAlarmLevel, 
                      sonusAlarmSequenceId, sonusAlarmTime, 
                      sonusAlarmDescription, sonusAlarmName }
--     STATUS          mandatory
    DESCRIPTION     
            "This alarm is generated when the mandatory feature license is not available.
             ."
    ::= 31

sonusSbxFeatureLicenseAvailable TRAP-TYPE
    ENTERPRISE      sonusOrcaLicenseMIBNotifications
    VARIABLES       { sonusAlarmNodeID, sonusAlarmLevel, 
                      sonusAlarmSequenceId, sonusAlarmTime, 
                      sonusAlarmDescription, sonusAlarmName }
--     STATUS          mandatory
    DESCRIPTION     
            "This alarm is generated when the feature license becomes available."
    ::= 32

sonusDatabaseConfigPolicyDataOutOfSyncNotification TRAP-TYPE
    ENTERPRISE      sonusDatabaseMIBNotifications
    VARIABLES       { sonusAlarmNodeID, sonusAlarmLevel, 
                      sonusAlarmSequenceId, sonusAlarmTime, 
                      sonusAlarmDescription, sonusSbxSystemName, 
                      sonusSbxServerName, sonusSbxRedundencyRole }
--     STATUS          mandatory
    DESCRIPTION     
            "This trap indicates that the config policy databases on the active are out of sync and manual action is required."
    ::= 1

sonusDatabaseConfigPolicyDataInSyncNotification TRAP-TYPE
    ENTERPRISE      sonusDatabaseMIBNotifications
    VARIABLES       { sonusAlarmNodeID, sonusAlarmLevel, 
                      sonusAlarmSequenceId, sonusAlarmTime, 
                      sonusAlarmDescription, sonusSbxSystemName, 
                      sonusSbxServerName, sonusSbxRedundencyRole }
--     STATUS          mandatory
    DESCRIPTION     
            "This trap indicates that the config policy databases on the active are in sync."
    ::= 2

sonusDatabasePolicyDataOutOfSyncNotification TRAP-TYPE
    ENTERPRISE      sonusDatabaseMIBNotifications
    VARIABLES       { sonusAlarmNodeID, sonusAlarmLevel, 
                      sonusAlarmSequenceId, sonusAlarmTime, 
                      sonusAlarmDescription, sonusSbxSystemName, 
                      sonusSbxServerName, sonusSbxPeerServerName }
--     STATUS          mandatory
    DESCRIPTION     
            "This trap indicates that the policy databases on active and standby are out of sync and manual action is required."
    ::= 3

sonusDatabasePolicyDataInSyncNotification TRAP-TYPE
    ENTERPRISE      sonusDatabaseMIBNotifications
    VARIABLES       { sonusAlarmNodeID, sonusAlarmLevel, 
                      sonusAlarmSequenceId, sonusAlarmTime, 
                      sonusAlarmDescription, sonusSbxSystemName, 
                      sonusSbxServerName, sonusSbxPeerServerName }
--     STATUS          mandatory
    DESCRIPTION     
            "This trap indicates that the policy databases on active and standby are in sync."
    ::= 4

sonusSbxResourceThresholdReachedNotification TRAP-TYPE
    ENTERPRISE      sonusResourceMIBNotifications
    VARIABLES       { sonusAlarmNodeID, sonusAlarmLevel, 
                      sonusAlarmSequenceId, sonusAlarmTime, 
                      sonusAlarmDescription, sonusResource, 
                      sonusEntityType, sonusEntityName, 
                      sonusSharedCacLimitPoolProfileId, 
                      sonusResourceUsage, sonusResourceLimit, 
                      sonusResourceThreshold }
--     STATUS          mandatory
    DESCRIPTION     
            "This trap indicates the resource usage notification threshold has been reached or exceeded."
    ::= 1

sonusSbxIpPeerKpiCriticalThresholdNotification TRAP-TYPE
    ENTERPRISE      sonusPeerResourcesMIBNotifications
    VARIABLES       { sonusAlarmNodeID, sonusAlarmLevel, 
                      sonusAlarmSequenceId, sonusAlarmTime, 
                      sonusAlarmDescription, sonusPeerName, 
                      sonusZoneName, sonusKpi, sonusCurrentKpiValue }
--     STATUS          mandatory
    DESCRIPTION     
            "This IP peer has been put to Temporary OOS and shall not be chosen for Routing"
    ::= 1

sonusSbxIpPeerKpiCriticalThresholdClearedNotification TRAP-TYPE
    ENTERPRISE      sonusPeerResourcesMIBNotifications
    VARIABLES       { sonusAlarmNodeID, sonusAlarmLevel, 
                      sonusAlarmSequenceId, sonusAlarmTime, 
                      sonusAlarmDescription, sonusPeerName, 
                      sonusZoneName, sonusKpi, sonusCurrentKpiValue }
--     STATUS          mandatory
    DESCRIPTION     
            "This trap indicates that critical QOS KPI condition in the IP PEER got cleared"
    ::= 2

sonusSbxImPriOperStateChange TRAP-TYPE
    ENTERPRISE      sonusInterceptManagerMIBNotifications
    VARIABLES       { sonusAlarmNodeID, sonusAlarmLevel, 
                      sonusAlarmSequenceId, sonusAlarmTime, 
                      sonusAlarmDescription, sonusImStatusPriOperState }
--     STATUS          mandatory
    DESCRIPTION     
            "This trap indicates the intercept manager primary operational state has changed."
    ::= 1

sonusSbxImSecOperStateChange TRAP-TYPE
    ENTERPRISE      sonusInterceptManagerMIBNotifications
    VARIABLES       { sonusAlarmNodeID, sonusAlarmLevel, 
                      sonusAlarmSequenceId, sonusAlarmTime, 
                      sonusAlarmDescription, sonusImStatusSecOperState }
--     STATUS          mandatory
    DESCRIPTION     
            "This trap indicates the intercept manager secondary operational state has changed."
    ::= 2

sonusSbxImMediationServerTcpLinkDown TRAP-TYPE
    ENTERPRISE      sonusInterceptManagerMIBNotifications
    VARIABLES       { sonusAlarmNodeID, sonusAlarmLevel, 
                      sonusAlarmSequenceId, sonusAlarmTime, 
                      sonusAlarmDescription, sonusImMediationServerName, 
                      sonusImMediationServerState, 
                      sonusImMediationServerInterceptMediaType }
--     STATUS          mandatory
    DESCRIPTION     
            "TCP link towards Mediation Server is down"
    ::= 3

sonusSbxImMediationServerTcpLinkUp TRAP-TYPE
    ENTERPRISE      sonusInterceptManagerMIBNotifications
    VARIABLES       { sonusAlarmNodeID, sonusAlarmLevel, 
                      sonusAlarmSequenceId, sonusAlarmTime, 
                      sonusAlarmDescription, sonusImMediationServerName, 
                      sonusImMediationServerState, 
                      sonusImMediationServerInterceptMediaType }
--     STATUS          mandatory
    DESCRIPTION     
            "TCP link towards Mediation Server is established."
    ::= 4

sonusSbxImMediationServerX2MsgBufferFull TRAP-TYPE
    ENTERPRISE      sonusInterceptManagerMIBNotifications
    VARIABLES       { sonusAlarmNodeID, sonusAlarmLevel, 
                      sonusAlarmSequenceId, sonusAlarmTime, 
                      sonusAlarmDescription, sonusImMediationServerName }
--     STATUS          mandatory
    DESCRIPTION     
            "Mediation server or diameter realm X2 Message Buffer is Full"
    ::= 5

sonusSbxImMediationServerX2MsgBufferAvailable TRAP-TYPE
    ENTERPRISE      sonusInterceptManagerMIBNotifications
    VARIABLES       { sonusAlarmNodeID, sonusAlarmLevel, 
                      sonusAlarmSequenceId, sonusAlarmTime, 
                      sonusAlarmDescription, sonusImMediationServerName }
--     STATUS          mandatory
    DESCRIPTION     
            "Mediation server or diameter realm X2 Message Buffer is available"
    ::= 6

sonusSbxMtrmPortAvailNotification TRAP-TYPE
    ENTERPRISE      sonusMtrmMIBNotifications
    VARIABLES       { sonusAlarmNodeID, sonusAlarmLevel, 
                      sonusAlarmSequenceId, sonusAlarmTime, 
                      sonusAlarmDescription, sonusMtrmPortIndex }
--     STATUS          mandatory
    DESCRIPTION     
            "This trap indicates that MTRM peer connection is available."
    ::= 1

sonusSbxMtrmPortUnAvailNotification TRAP-TYPE
    ENTERPRISE      sonusMtrmMIBNotifications
    VARIABLES       { sonusAlarmNodeID, sonusAlarmLevel, 
                      sonusAlarmSequenceId, sonusAlarmTime, 
                      sonusAlarmDescription, sonusMtrmPortIndex }
--     STATUS          mandatory
    DESCRIPTION     
            "This trap indicates that MTRM peer connection is unavailable."
    ::= 2

sonusSbxMtrmPortSwitchoverNotification TRAP-TYPE
    ENTERPRISE      sonusMtrmMIBNotifications
    VARIABLES       { sonusAlarmNodeID, sonusAlarmLevel, 
                      sonusAlarmSequenceId, sonusAlarmTime, 
                      sonusAlarmDescription, sonusMtrmPortIndex }
--     STATUS          mandatory
    DESCRIPTION     
            "This trap indicates that MTRM client connection is now switched to secondary server."
    ::= 3

sonusOcspConnectionFailed TRAP-TYPE
    ENTERPRISE      sonusSecurityMIBNotifications
    VARIABLES       { sonusAlarmNodeID, sonusAlarmLevel, 
                      sonusAlarmSequenceId, sonusAlarmTime, 
                      sonusAlarmDescription, sonusSecurityOcspUrlName }
--     STATUS          mandatory
    DESCRIPTION     
            "TCP connection to a OCSP Responder cannot be established."
    ::= 1

sonusInvalidOcspResponseReceived TRAP-TYPE
    ENTERPRISE      sonusSecurityMIBNotifications
    VARIABLES       { sonusAlarmNodeID, sonusAlarmLevel, 
                      sonusAlarmSequenceId, sonusAlarmTime, 
                      sonusAlarmDescription, sonusSecurityOcspUrlName }
--     STATUS          mandatory
    DESCRIPTION     
            "An invalid OCSP response was received."
    ::= 2

sonusNoValidOcspResponseReceived TRAP-TYPE
    ENTERPRISE      sonusSecurityMIBNotifications
    VARIABLES       { sonusAlarmNodeID, sonusAlarmLevel, 
                      sonusAlarmSequenceId, sonusAlarmTime, 
                      sonusAlarmDescription, sonusSecurityOcspUrlName }
--     STATUS          mandatory
    DESCRIPTION     
            "No Valid OCSP response was received upon the expiry of the OCSP response timer."
    ::= 3

sonusOcspResponseUnknown TRAP-TYPE
    ENTERPRISE      sonusSecurityMIBNotifications
    VARIABLES       { sonusAlarmNodeID, sonusAlarmLevel, 
                      sonusAlarmSequenceId, sonusAlarmTime, 
                      sonusAlarmDescription, sonusSecurityOcspUrlName, 
                      sonusSecurityOcspResponseStatus }
--     STATUS          mandatory
    DESCRIPTION     
            "A valid OCSP response was received with certificate status unknown."
    ::= 4

sonusOcspExceptionResponse TRAP-TYPE
    ENTERPRISE      sonusSecurityMIBNotifications
    VARIABLES       { sonusAlarmNodeID, sonusAlarmLevel, 
                      sonusAlarmSequenceId, sonusAlarmTime, 
                      sonusAlarmDescription, sonusSecurityOcspUrlName, 
                      sonusSecurityOcspResponseStatus }
--     STATUS          mandatory
    DESCRIPTION     
            "An exception OCSP response was received from OCSP responder - malformedRequest, internalError, tryLater, sigRequired, unauthorized"
    ::= 5

sonusVnfmConnectionFailed TRAP-TYPE
    ENTERPRISE      sonusSecurityMIBNotifications
    VARIABLES       { sonusAlarmNodeID, sonusAlarmLevel, 
                      sonusAlarmSequenceId, sonusAlarmTime, 
                      sonusAlarmDescription, sonusVnfmUrlName }
--     STATUS          mandatory
    DESCRIPTION     
            "SBC connection to VNFM cannot be established."
    ::= 6

sonusVnfmConnectionSucceeded TRAP-TYPE
    ENTERPRISE      sonusSecurityMIBNotifications
    VARIABLES       { sonusAlarmNodeID, sonusAlarmLevel, 
                      sonusAlarmSequenceId, sonusAlarmTime, 
                      sonusAlarmDescription, sonusVnfmUrlName }
--     STATUS          mandatory
    DESCRIPTION     
            "SBC connection to VNFM is recovered."
    ::= 7

sonusSbxLvmPhyPacketPortDownNotification TRAP-TYPE
    ENTERPRISE      sonusLvmMIBNotifications
    VARIABLES       { sonusAlarmNodeID, sonusAlarmLevel, 
                      sonusAlarmSequenceId, sonusAlarmTime, 
                      sonusAlarmDescription, sonusNrsCeName, 
                      sonusNrsPortName }
--     STATUS          mandatory
    DESCRIPTION     
            "The physical packet port is down."
    ::= 1

sonusSbxLvmPhyPacketPortUpNotification TRAP-TYPE
    ENTERPRISE      sonusLvmMIBNotifications
    VARIABLES       { sonusAlarmNodeID, sonusAlarmLevel, 
                      sonusAlarmSequenceId, sonusAlarmTime, 
                      sonusAlarmDescription, sonusNrsCeName, 
                      sonusNrsPortName }
--     STATUS          mandatory
    DESCRIPTION     
            "The physical packet port is up."
    ::= 2

sonusSbxLvmPrimaryPhyPacketPortActiveNotification TRAP-TYPE
    ENTERPRISE      sonusLvmMIBNotifications
    VARIABLES       { sonusAlarmNodeID, sonusAlarmLevel, 
                      sonusAlarmSequenceId, sonusAlarmTime, 
                      sonusAlarmDescription, sonusNrsCeName, 
                      sonusNrsPortName, sonusLvmPortSwitchReason }
--     STATUS          mandatory
    DESCRIPTION     
            "The primary physical packet port is made ACTIVE."
    ::= 3

sonusSbxLvmSecondaryPhyPacketPortActiveNotification TRAP-TYPE
    ENTERPRISE      sonusLvmMIBNotifications
    VARIABLES       { sonusAlarmNodeID, sonusAlarmLevel, 
                      sonusAlarmSequenceId, sonusAlarmTime, 
                      sonusAlarmDescription, sonusNrsCeName, 
                      sonusNrsPortName, sonusLvmPortSwitchReason }
--     STATUS          mandatory
    DESCRIPTION     
            "The secondary physical packet port is made ACTIVE."
    ::= 4

sonusSbxLvmLinkDetectionGroupFailedNotification TRAP-TYPE
    ENTERPRISE      sonusLvmMIBNotifications
    VARIABLES       { sonusAlarmNodeID, sonusAlarmLevel, 
                      sonusAlarmSequenceId, sonusAlarmTime, 
                      sonusAlarmDescription, sonusNrsCeName, 
                      sonusNrsAddressContextName, 
                      sonusLvmLinkDetectionGroupName }
--     STATUS          mandatory
    DESCRIPTION     
            "The link detection group has failed."
    ::= 5

sonusSbxLvmLinkDetectionGroupRestoredNotification TRAP-TYPE
    ENTERPRISE      sonusLvmMIBNotifications
    VARIABLES       { sonusAlarmNodeID, sonusAlarmLevel, 
                      sonusAlarmSequenceId, sonusAlarmTime, 
                      sonusAlarmDescription, sonusNrsCeName, 
                      sonusNrsAddressContextName, 
                      sonusLvmLinkDetectionGroupName }
--     STATUS          mandatory
    DESCRIPTION     
            "The link detection group has been restored."
    ::= 6

sonusSbxLvmLinkDetectionGroupSwitchoverNotification TRAP-TYPE
    ENTERPRISE      sonusLvmMIBNotifications
    VARIABLES       { sonusAlarmNodeID, sonusAlarmLevel, 
                      sonusAlarmSequenceId, sonusAlarmTime, 
                      sonusAlarmDescription, sonusNrsCeName, 
                      sonusNrsAddressContextName, 
                      sonusLvmLinkDetectionGroupName }
--     STATUS          mandatory
    DESCRIPTION     
            "The link detection group has triggered a CE switchover."
    ::= 7

sonusSbxLvmPrgLinkFailureToggleNotification TRAP-TYPE
    ENTERPRISE      sonusLvmMIBNotifications
    VARIABLES       { sonusAlarmNodeID, sonusAlarmLevel, 
                      sonusAlarmSequenceId, sonusAlarmTime, 
                      sonusAlarmDescription, sonusNrsCeName, 
                      sonusLvmPortRedundancyGroupName }
--     STATUS          mandatory
    DESCRIPTION     
            "Port Redundancy Group detected link failure toggling."
    ::= 8

sonusSbxLvmPrgLinkFailureToggleClearedNotification TRAP-TYPE
    ENTERPRISE      sonusLvmMIBNotifications
    VARIABLES       { sonusAlarmNodeID, sonusAlarmLevel, 
                      sonusAlarmSequenceId, sonusAlarmTime, 
                      sonusAlarmDescription, sonusNrsCeName, 
                      sonusLvmPortRedundancyGroupName }
--     STATUS          mandatory
    DESCRIPTION     
            "Port Redundancy Group cleared link failure toggling."
    ::= 9

sonusSbxLvmPrgSwitchoverToRecoverLinksNotification TRAP-TYPE
    ENTERPRISE      sonusLvmMIBNotifications
    VARIABLES       { sonusAlarmNodeID, sonusAlarmLevel, 
                      sonusAlarmSequenceId, sonusAlarmTime, 
                      sonusAlarmDescription }
--     STATUS          mandatory
    DESCRIPTION     
            "Initiating CE switchover as the system is unable to recover from port toggling."
    ::= 10

sonusSbxDiamConnectionToRfAccountingServerGoesDown TRAP-TYPE
    ENTERPRISE      sonusDiamMIBNotifications
    VARIABLES       { sonusAlarmNodeID, sonusAlarmLevel, 
                      sonusAlarmSequenceId, sonusAlarmTime, 
                      sonusAlarmDescription, sonusRfAccountingServerName }
--     STATUS          deprecated
    DESCRIPTION     
            "This trap has been replaced by sonusSbxDiamPeerConnectionDown."
    ::= 1

sonusSbxDiamConnectionToRfAccountingServerGoesUp TRAP-TYPE
    ENTERPRISE      sonusDiamMIBNotifications
    VARIABLES       { sonusAlarmNodeID, sonusAlarmLevel, 
                      sonusAlarmSequenceId, sonusAlarmTime, 
                      sonusAlarmDescription, sonusRfAccountingServerName }
--     STATUS          deprecated
    DESCRIPTION     
            "This trap has been replaced by sonusSbxDiamPeerConnectionUp"
    ::= 2

sonusSbxDiamPeerConnectionDown TRAP-TYPE
    ENTERPRISE      sonusDiamMIBNotifications
    VARIABLES       { sonusAlarmNodeID, sonusAlarmLevel, 
                      sonusAlarmSequenceId, sonusAlarmTime, 
                      sonusAlarmDescription, sonusDiamPeerName, 
                      sonusDiamPeerIpAddress }
--     STATUS          mandatory
    DESCRIPTION     
            "Diameter Peer Connection is detected as lost or broken."
    ::= 3

sonusSbxDiamPeerConnectionUp TRAP-TYPE
    ENTERPRISE      sonusDiamMIBNotifications
    VARIABLES       { sonusAlarmNodeID, sonusAlarmLevel, 
                      sonusAlarmSequenceId, sonusAlarmTime, 
                      sonusAlarmDescription, sonusDiamPeerName, 
                      sonusDiamPeerIpAddress }
--     STATUS          mandatory
    DESCRIPTION     
            "Diameter Peer Connection is established."
    ::= 4

sonusSbxDnsServerBlacklistedNotification TRAP-TYPE
    ENTERPRISE      sonusDnsMIBNotifications
    VARIABLES       { sonusAlarmNodeID, sonusAlarmLevel, 
                      sonusAlarmSequenceId, sonusAlarmTime, 
                      sonusAlarmDescription, sonusDnsServerIp, 
                      sonusDnsServerPortNum, sonusDnsServerTransport }
--     STATUS          mandatory
    DESCRIPTION     
            "This alarms is raised when dns server consistently failed to send response 
             to sbx dns request . Dns Server will be moved to Blacklisting state "
    ::= 1

sonusSbxDnsServerRecoveredNotification TRAP-TYPE
    ENTERPRISE      sonusDnsMIBNotifications
    VARIABLES       { sonusAlarmNodeID, sonusAlarmLevel, 
                      sonusAlarmSequenceId, sonusAlarmTime, 
                      sonusAlarmDescription, sonusDnsServerIp, 
                      sonusDnsServerPortNum, sonusDnsServerTransport }
--     STATUS          mandatory
    DESCRIPTION     
            "This alarms is raised when sbx  recoverd from blacklisted state "
    ::= 2

sonusSbxRcodeErrorOnDnsQuery TRAP-TYPE
    ENTERPRISE      sonusDnsMIBNotifications
    VARIABLES       { sonusAlarmNodeID, sonusAlarmLevel, 
                      sonusAlarmSequenceId, sonusAlarmTime, 
                      sonusAlarmDescription, sonusDnsServerZoneId, 
                      sonusDnsIpAddr, sonusRcodeError, 
                      sonusDnsServerType }
--     STATUS          mandatory
    DESCRIPTION     
            "The DNS Server has encountered an RCODE error"
    ::= 3

sonusSbxRcodeErrorClearNotification TRAP-TYPE
    ENTERPRISE      sonusDnsMIBNotifications
    VARIABLES       { sonusAlarmNodeID, sonusAlarmLevel, 
                      sonusAlarmSequenceId, sonusAlarmTime, 
                      sonusAlarmDescription, sonusDnsIpAddr }
--     STATUS          mandatory
    DESCRIPTION     
            "RCODE Alarm Monitor interval expired for DNS server "
    ::= 4

sonusSbxRcodeErrorOnDnsQueryV6 TRAP-TYPE
    ENTERPRISE      sonusDnsMIBNotifications
    VARIABLES       { sonusAlarmNodeID, sonusAlarmLevel, 
                      sonusAlarmSequenceId, sonusAlarmTime, 
                      sonusAlarmDescription, sonusDnsServerZoneId, 
                      sonusDnsIpV6Addr, sonusRcodeError, 
                      sonusDnsServerType }
--     STATUS          mandatory
    DESCRIPTION     
            "The DNS Server has encountered an RCODE error"
    ::= 5

sonusSbxRcodeErrorClearNotificationV6 TRAP-TYPE
    ENTERPRISE      sonusDnsMIBNotifications
    VARIABLES       { sonusAlarmNodeID, sonusAlarmLevel, 
                      sonusAlarmSequenceId, sonusAlarmTime, 
                      sonusAlarmDescription, sonusDnsIpV6Addr }
--     STATUS          mandatory
    DESCRIPTION     
            "RCODE Alarm Monitor interval expired for DNS server "
    ::= 6

sonusSbxDnsServerEdnsFailureNotification TRAP-TYPE
    ENTERPRISE      sonusEdnsMIBNotifications
    VARIABLES       { sonusAlarmNodeID, sonusAlarmLevel, 
                      sonusAlarmSequenceId, sonusAlarmTime, 
                      sonusAlarmDescription, sonusEdnsServerIp }
--     STATUS          mandatory
    DESCRIPTION     
            "This alarms is raised when dns server consistently sends negative response
             to sbx edns request . Dns Server will be moved to the edns unsupported state "
    ::= 1

sonusSbxDsbcControlChanOpenNotification TRAP-TYPE
    ENTERPRISE      sonusDsbcSignallingMIBNotifications
    VARIABLES       { sonusAlarmNodeID, sonusAlarmLevel, 
                      sonusAlarmSequenceId, sonusAlarmTime, 
                      sonusAlarmDescription, sonusDsbcRemoteDsbcAddr }
--     STATUS          mandatory
    DESCRIPTION     
            "This trap indicates that a Control Channel Link to a Remote DSBC node has been sucessfully opened."
    ::= 1

sonusSbxDsbcControlChanCloseNotification TRAP-TYPE
    ENTERPRISE      sonusDsbcSignallingMIBNotifications
    VARIABLES       { sonusAlarmNodeID, sonusAlarmLevel, 
                      sonusAlarmSequenceId, sonusAlarmTime, 
                      sonusAlarmDescription, sonusDsbcRemoteDsbcAddr, 
                      sonusDsbcCloseReasonCode }
--     STATUS          mandatory
    DESCRIPTION     
            "This trap indicates that a Control Channel Link to a Remote DSBC node has been closed."
    ::= 2

sonusSbxDsbcControlChanOpenAttemptNotification TRAP-TYPE
    ENTERPRISE      sonusDsbcSignallingMIBNotifications
    VARIABLES       { sonusAlarmNodeID, sonusAlarmLevel, 
                      sonusAlarmSequenceId, sonusAlarmTime, 
                      sonusAlarmDescription, sonusDsbcRemoteDsbcAddr }
--     STATUS          mandatory
    DESCRIPTION     
            "This trap indicates that a request to Open a Control Channel Link has been sent to a Remote Dsbc."
    ::= 3

sonusSbxDsbcControlChanRetryTimerExpiredNotification TRAP-TYPE
    ENTERPRISE      sonusDsbcSignallingMIBNotifications
    VARIABLES       { sonusAlarmNodeID, sonusAlarmLevel, 
                      sonusAlarmSequenceId, sonusAlarmTime, 
                      sonusAlarmDescription, sonusDsbcRemoteDsbcAddr }
--     STATUS          mandatory
    DESCRIPTION     
            "This trap indicates that attempts to recover a Control Channel Link to a Remote DSBC node have failed."
    ::= 4

sonusSbxDsbcControlChanOpenNotificationV6 TRAP-TYPE
    ENTERPRISE      sonusDsbcSignallingMIBNotifications
    VARIABLES       { sonusAlarmNodeID, sonusAlarmLevel, 
                      sonusAlarmSequenceId, sonusAlarmTime, 
                      sonusAlarmDescription, sonusDsbcRemoteDsbc6Addr }
--     STATUS          mandatory
    DESCRIPTION     
            "This trap indicates that a Call Signaling IPV6 Link to a Remote DSBC node has been sucessfully opened."
    ::= 5

sonusSbxDsbcControlChanOpenAttemptNotificationV6 TRAP-TYPE
    ENTERPRISE      sonusDsbcSignallingMIBNotifications
    VARIABLES       { sonusAlarmNodeID, sonusAlarmLevel, 
                      sonusAlarmSequenceId, sonusAlarmTime, 
                      sonusAlarmDescription, sonusDsbcRemoteDsbc6Addr }
--     STATUS          mandatory
    DESCRIPTION     
            "This trap indicates that a request to Open a Call Signaling IPV6 Link has been sent to a Remote Dsbc."
    ::= 6

sonusSbxDsbcControlChanRetryTimerExpiredNotificationV6 TRAP-TYPE
    ENTERPRISE      sonusDsbcSignallingMIBNotifications
    VARIABLES       { sonusAlarmNodeID, sonusAlarmLevel, 
                      sonusAlarmSequenceId, sonusAlarmTime, 
                      sonusAlarmDescription, sonusDsbcRemoteDsbc6Addr }
--     STATUS          mandatory
    DESCRIPTION     
            "This trap indicates that attempts to recover a Call Signaling IPV6 Link to a Remote DSBC node have failed."
    ::= 7

sonusSbxDsbcControlChanCloseNotificationV6 TRAP-TYPE
    ENTERPRISE      sonusDsbcSignallingMIBNotifications
    VARIABLES       { sonusAlarmNodeID, sonusAlarmLevel, 
                      sonusAlarmSequenceId, sonusAlarmTime, 
                      sonusAlarmDescription, sonusDsbcRemoteDsbc6Addr, 
                      sonusDsbcCloseReasonCode }
--     STATUS          mandatory
    DESCRIPTION     
            "This trap indicates that a IPV6 Control Channel Link to a Remote DSBC node has been closed."
    ::= 8

sonusSbxDsbcClusterFqdnResolutionFailure TRAP-TYPE
    ENTERPRISE      sonusDsbcSignallingMIBNotifications
    VARIABLES       { sonusAlarmNodeID, sonusAlarmLevel, 
                      sonusAlarmSequenceId, sonusAlarmTime, 
                      sonusAlarmDescription, sonusDsbcClusterFqdn, 
                      sonusDsbcClusterType }
--     STATUS          mandatory
    DESCRIPTION     
            "This trap indicates that all FQDN resolution attempts have failed for this cluster."
    ::= 9

sonusSbxDsbcClusterFqdnResolutionSuccess TRAP-TYPE
    ENTERPRISE      sonusDsbcSignallingMIBNotifications
    VARIABLES       { sonusAlarmNodeID, sonusAlarmLevel, 
                      sonusAlarmSequenceId, sonusAlarmTime, 
                      sonusAlarmDescription, sonusDsbcClusterFqdn, 
                      sonusDsbcClusterType }
--     STATUS          mandatory
    DESCRIPTION     
            "This trap indicates that FQDN resolution has succeeded for this cluster."
    ::= 10

sonusSbxDsbcClusterAllSeedNodesUnreachable TRAP-TYPE
    ENTERPRISE      sonusDsbcSignallingMIBNotifications
    VARIABLES       { sonusAlarmNodeID, sonusAlarmLevel, 
                      sonusAlarmSequenceId, sonusAlarmTime, 
                      sonusAlarmDescription, sonusDsbcClusterFqdn, 
                      sonusDsbcClusterType }
--     STATUS          mandatory
    DESCRIPTION     
            "This trap indicates that all seed nodes for this cluster FQDN are unreachable."
    ::= 11

sonusSbxDsbcClusterLeaderDiscoveryInProgress TRAP-TYPE
    ENTERPRISE      sonusDsbcSignallingMIBNotifications
    VARIABLES       { sonusAlarmNodeID, sonusAlarmLevel, 
                      sonusAlarmSequenceId, sonusAlarmTime, 
                      sonusAlarmDescription, sonusDsbcClusterFqdn, 
                      sonusDsbcClusterType, sonusDsbcRemoteDsbcAddr }
--     STATUS          mandatory
    DESCRIPTION     
            "This trap indicates that a seed node for this cluster has been reached and leader discovery is in progress."
    ::= 12

sonusSbxDsbcClusterLeaderDiscoveryInProgressV6 TRAP-TYPE
    ENTERPRISE      sonusDsbcSignallingMIBNotifications
    VARIABLES       { sonusAlarmNodeID, sonusAlarmLevel, 
                      sonusAlarmSequenceId, sonusAlarmTime, 
                      sonusAlarmDescription, sonusDsbcClusterFqdn, 
                      sonusDsbcClusterType, sonusDsbcRemoteDsbc6Addr }
--     STATUS          mandatory
    DESCRIPTION     
            "This trap indicates that a seed node for this cluster has been reached and leader discovery is in progress."
    ::= 13

sonusSbxDsbcClusterLeaderRetrievalCompleted TRAP-TYPE
    ENTERPRISE      sonusDsbcSignallingMIBNotifications
    VARIABLES       { sonusAlarmNodeID, sonusAlarmLevel, 
                      sonusAlarmSequenceId, sonusAlarmTime, 
                      sonusAlarmDescription, sonusDsbcClusterFqdn, 
                      sonusDsbcClusterType, sonusDsbcRemoteDsbcAddr }
--     STATUS          mandatory
    DESCRIPTION     
            "This trap indicates that a seed node for this cluster has been reached and leader retrieval is completed."
    ::= 14

sonusSbxDsbcClusterLeaderRetrievalCompletedV6 TRAP-TYPE
    ENTERPRISE      sonusDsbcSignallingMIBNotifications
    VARIABLES       { sonusAlarmNodeID, sonusAlarmLevel, 
                      sonusAlarmSequenceId, sonusAlarmTime, 
                      sonusAlarmDescription, sonusDsbcClusterFqdn, 
                      sonusDsbcClusterType, sonusDsbcRemoteDsbc6Addr }
--     STATUS          mandatory
    DESCRIPTION     
            "This trap indicates that a seed node for this cluster has been reached and leader retrieval is completed."
    ::= 15

sonusSbxDsbcFaultCallsReleased TRAP-TYPE
    ENTERPRISE      sonusDsbcSignallingMIBNotifications
    VARIABLES       { sonusAlarmNodeID, sonusAlarmLevel, 
                      sonusAlarmSequenceId, sonusAlarmTime, 
                      sonusAlarmDescription, 
                      sonusDsbcCallsReleasedReasonCode, 
                      sonusDsbcCallsReleasedCount, 
                      sonusDsbcRemoteDsbcAddr }
--     STATUS          mandatory
    DESCRIPTION     
            "This trap indicates that a D-SBC network fault has resulted in calls being dropped."
    ::= 16

sonusSbxDsbcFaultCallsReleasedClear TRAP-TYPE
    ENTERPRISE      sonusDsbcSignallingMIBNotifications
    VARIABLES       { sonusAlarmNodeID, sonusAlarmLevel, 
                      sonusAlarmSequenceId, sonusAlarmTime, 
                      sonusAlarmDescription, 
                      sonusDsbcCallsReleasedReasonCode, 
                      sonusDsbcRemoteDsbcAddr }
--     STATUS          mandatory
    DESCRIPTION     
            "This trap clears the D-SBC network fault call drop trap."
    ::= 17

sonusSbxDsbcFaultCallsReleasedV6 TRAP-TYPE
    ENTERPRISE      sonusDsbcSignallingMIBNotifications
    VARIABLES       { sonusAlarmNodeID, sonusAlarmLevel, 
                      sonusAlarmSequenceId, sonusAlarmTime, 
                      sonusAlarmDescription, 
                      sonusDsbcCallsReleasedReasonCode, 
                      sonusDsbcCallsReleasedCount, 
                      sonusDsbcRemoteDsbc6Addr }
--     STATUS          mandatory
    DESCRIPTION     
            "This trap indicates that a D-SBC network fault has resulted in calls being dropped."
    ::= 18

sonusSbxDsbcFaultCallsReleasedClearV6 TRAP-TYPE
    ENTERPRISE      sonusDsbcSignallingMIBNotifications
    VARIABLES       { sonusAlarmNodeID, sonusAlarmLevel, 
                      sonusAlarmSequenceId, sonusAlarmTime, 
                      sonusAlarmDescription, 
                      sonusDsbcCallsReleasedReasonCode, 
                      sonusDsbcRemoteDsbc6Addr }
--     STATUS          mandatory
    DESCRIPTION     
            "This trap clears the D-SBC network fault call drop trap."
    ::= 19

sonusSbxDsbcNodeCongested TRAP-TYPE
    ENTERPRISE      sonusDsbcSignallingMIBNotifications
    VARIABLES       { sonusAlarmNodeID, sonusAlarmLevel, 
                      sonusAlarmSequenceId, sonusAlarmTime, 
                      sonusAlarmDescription, sonusDsbcRemoteDsbcAddr }
--     STATUS          mandatory
    DESCRIPTION     
            "This trap indicates that the D-SBC node has reported congestion failure."
    ::= 20

sonusSbxDsbcNodeCongestedClear TRAP-TYPE
    ENTERPRISE      sonusDsbcSignallingMIBNotifications
    VARIABLES       { sonusAlarmNodeID, sonusAlarmLevel, 
                      sonusAlarmSequenceId, sonusAlarmTime, 
                      sonusAlarmDescription, sonusDsbcRemoteDsbcAddr }
--     STATUS          mandatory
    DESCRIPTION     
            "This trap indicates that the D-SBC node congestion condition has been cleared."
    ::= 21

sonusSbxDsbcNodeCongestedV6 TRAP-TYPE
    ENTERPRISE      sonusDsbcSignallingMIBNotifications
    VARIABLES       { sonusAlarmNodeID, sonusAlarmLevel, 
                      sonusAlarmSequenceId, sonusAlarmTime, 
                      sonusAlarmDescription, sonusDsbcRemoteDsbc6Addr }
--     STATUS          mandatory
    DESCRIPTION     
            "This trap indicates that a D-SBC node has reported congestion failure."
    ::= 22

sonusSbxDsbcNodeCongestedClearV6 TRAP-TYPE
    ENTERPRISE      sonusDsbcSignallingMIBNotifications
    VARIABLES       { sonusAlarmNodeID, sonusAlarmLevel, 
                      sonusAlarmSequenceId, sonusAlarmTime, 
                      sonusAlarmDescription, sonusDsbcRemoteDsbc6Addr }
--     STATUS          mandatory
    DESCRIPTION     
            "This trap indicates that the D-SBC node congestion condition has been cleared."
    ::= 23

sonusSbxDsbcNodeAllocationFailure TRAP-TYPE
    ENTERPRISE      sonusDsbcSignallingMIBNotifications
    VARIABLES       { sonusAlarmNodeID, sonusAlarmLevel, 
                      sonusAlarmSequenceId, sonusAlarmTime, 
                      sonusAlarmDescription, sonusDsbcAllocFailuresCount, 
                      sonusDsbcRemoteDsbcAddr }
--     STATUS          mandatory
    DESCRIPTION     
            "This trap indicates that the M-SBC node has reported allocation failure(s)."
    ::= 24

sonusSbxDsbcNodeAllocationFailureClear TRAP-TYPE
    ENTERPRISE      sonusDsbcSignallingMIBNotifications
    VARIABLES       { sonusAlarmNodeID, sonusAlarmLevel, 
                      sonusAlarmSequenceId, sonusAlarmTime, 
                      sonusAlarmDescription, sonusDsbcAllocFailuresCount, 
                      sonusDsbcRemoteDsbcAddr }
--     STATUS          mandatory
    DESCRIPTION     
            "This trap indicates that the M-SBC node allocation failure condition has been cleared."
    ::= 25

sonusSbxDsbcNodeAllocationFailureV6 TRAP-TYPE
    ENTERPRISE      sonusDsbcSignallingMIBNotifications
    VARIABLES       { sonusAlarmNodeID, sonusAlarmLevel, 
                      sonusAlarmSequenceId, sonusAlarmTime, 
                      sonusAlarmDescription, sonusDsbcAllocFailuresCount, 
                      sonusDsbcRemoteDsbc6Addr }
--     STATUS          mandatory
    DESCRIPTION     
            "This trap indicates that the M-SBC node has reported allocation failure(s)."
    ::= 26

sonusSbxDsbcNodeAllocationFailureClearV6 TRAP-TYPE
    ENTERPRISE      sonusDsbcSignallingMIBNotifications
    VARIABLES       { sonusAlarmNodeID, sonusAlarmLevel, 
                      sonusAlarmSequenceId, sonusAlarmTime, 
                      sonusAlarmDescription, sonusDsbcAllocFailuresCount, 
                      sonusDsbcRemoteDsbc6Addr }
--     STATUS          mandatory
    DESCRIPTION     
            "This trap indicates that the M-SBC node allocation failure condition has been cleared."
    ::= 27

sonusSbxCallRejectedDueToNonRegCacMaxLimitReachedNotification TRAP-TYPE
    ENTERPRISE      sonusCacMIBNotifications
    VARIABLES       { sonusAlarmNodeID, sonusAlarmLevel, 
                      sonusAlarmSequenceId, sonusAlarmTime, 
                      sonusAlarmDescription, sonusCacSrcIp }
--     STATUS          mandatory
    DESCRIPTION     
            "This alarms is raised when call gets rejected due to maximum cac limit is
             reached and all CACs have active sessions."
    ::= 1

sonusSbxCcsClusterDownNotification TRAP-TYPE
    ENTERPRISE      sonusCcsMIBNotifications
    VARIABLES       { sonusAlarmNodeID, sonusAlarmLevel, 
                      sonusAlarmSequenceId, sonusAlarmTime, 
                      sonusAlarmDescription, sonusNrsCeName }
--     STATUS          mandatory
    DESCRIPTION     
            "The cluster is down."
    ::= 1

sonusSbxCcsClusterUpNotification TRAP-TYPE
    ENTERPRISE      sonusCcsMIBNotifications
    VARIABLES       { sonusAlarmNodeID, sonusAlarmLevel, 
                      sonusAlarmSequenceId, sonusAlarmTime, 
                      sonusAlarmDescription, sonusNrsCeName }
--     STATUS          mandatory
    DESCRIPTION     
            "The cluster is up."
    ::= 2

sonusSbxLicensedOodRateLimitReachedNotification TRAP-TYPE
    ENTERPRISE      sonusOodMIBNotifications
    VARIABLES       { sonusAlarmNodeID, sonusAlarmLevel, 
                      sonusAlarmSequenceId, sonusAlarmTime, 
                      sonusAlarmDescription, sonusAlarmName, 
                      sonusActiveOodRate, sonusOodRateLimit }
--     STATUS          mandatory
    DESCRIPTION     
            "This trap indicates the licensed sessions notification threshold has been reached or exceeded."
    ::= 1

sonusSbxLicensedOodRateLimitClearNotification TRAP-TYPE
    ENTERPRISE      sonusOodMIBNotifications
    VARIABLES       { sonusAlarmNodeID, sonusAlarmLevel, 
                      sonusAlarmSequenceId, sonusAlarmTime, 
                      sonusAlarmDescription, sonusAlarmName, 
                      sonusActiveOodRate, sonusOodRateLimit }
--     STATUS          mandatory
    DESCRIPTION     
            "This trap indicates the licensed sessions notification threshold has been cleared under 90% limit."
    ::= 2

sonusSbxManagedNodeUnableToReceiveConfigUpdates TRAP-TYPE
    ENTERPRISE      sonusOamMIBNotifications
    VARIABLES       { sonusAlarmNodeID, sonusAlarmLevel, 
                      sonusAlarmSequenceId, sonusAlarmTime, 
                      sonusAlarmDescription, sonusManagedNodeCeName }
--     STATUS          mandatory
    DESCRIPTION     
            "Managed node is unable to receive config update/revert requests (i.e., managed node is unable to access config update/revert requests on OAM node)."
    ::= 1

sonusSbxManagedNodeAbleToReceiveConfigUpdates TRAP-TYPE
    ENTERPRISE      sonusOamMIBNotifications
    VARIABLES       { sonusAlarmNodeID, sonusAlarmLevel, 
                      sonusAlarmSequenceId, sonusAlarmTime, 
                      sonusAlarmDescription, sonusManagedNodeCeName }
--     STATUS          mandatory
    DESCRIPTION     
            "Managed node is able to receive config update/revert requests (i.e., managed node is able to access config update/revert requests on OAM node)."
    ::= 2

sonusSbxManagedNodeConfigChangeListApplyFailed TRAP-TYPE
    ENTERPRISE      sonusOamMIBNotifications
    VARIABLES       { sonusAlarmNodeID, sonusAlarmLevel, 
                      sonusAlarmSequenceId, sonusAlarmTime, 
                      sonusAlarmDescription, sonusManagedNodeCeName }
--     STATUS          mandatory
    DESCRIPTION     
            "Managed node failed to apply the config changes by replaying the config change list."
    ::= 3

sonusSbxManagedNodeConfigChangeListApplySucceeded TRAP-TYPE
    ENTERPRISE      sonusOamMIBNotifications
    VARIABLES       { sonusAlarmNodeID, sonusAlarmLevel, 
                      sonusAlarmSequenceId, sonusAlarmTime, 
                      sonusAlarmDescription, sonusManagedNodeCeName }
--     STATUS          mandatory
    DESCRIPTION     
            "Managed node successfully  applied the config changes by replaying the config change list."
    ::= 4

sonusHpcLimitHighIngressCallRateNotification TRAP-TYPE
    ENTERPRISE      sonusHpcCallLimitMIBNotifications
    VARIABLES       { sonusAlarmNodeID, sonusAlarmLevel, 
                      sonusAlarmSequenceId, sonusAlarmTime, 
                      sonusAlarmDescription, sonusHpcCallLimitEntityName, 
                      sonusHpcCallLimitDeniedAttempts }
--     STATUS          mandatory
    DESCRIPTION     
            "This trap indicates a HPC Call Rate Limit has been exceeded and reports the number of denied attempts."
    ::= 1

sonusHpcLimitHighSimultaneousCallsNotification TRAP-TYPE
    ENTERPRISE      sonusHpcCallLimitMIBNotifications
    VARIABLES       { sonusAlarmNodeID, sonusAlarmLevel, 
                      sonusAlarmSequenceId, sonusAlarmTime, 
                      sonusAlarmDescription, sonusHpcCallLimitEntityName, 
                      sonusHpcCallLimitDeniedAttempts }
--     STATUS          mandatory
    DESCRIPTION     
            "This trap indicates a HPC Simultaneous Call Limit has been exceeded and reports the number of denied attempts."
    ::= 2

sonusHpcCallNoLicenseNotification TRAP-TYPE
    ENTERPRISE      sonusHpcCallNoLicenseMIBNotifications
    VARIABLES       { sonusAlarmNodeID, sonusAlarmLevel, 
                      sonusAlarmSequenceId, sonusAlarmTime, 
                      sonusAlarmDescription }
--     STATUS          mandatory
    DESCRIPTION     
            "This trap indicates a HPC Call occurred without a valid license"
    ::= 1

sonusSlbSbcRegistrationNotification TRAP-TYPE
    ENTERPRISE      sonusSlbMIBNotifications
    VARIABLES       { sonusAlarmNodeID, sonusAlarmLevel, 
                      sonusAlarmSequenceId, sonusAlarmTime, 
                      sonusAlarmDescription, sonusVnfId, 
                      sonusVnfcInstanceId }
--     STATUS          mandatory
    DESCRIPTION     
            "An SBC has registered with the SLB."
    ::= 1

sonusSlbSbcConnectionUpNotification TRAP-TYPE
    ENTERPRISE      sonusSlbMIBNotifications
    VARIABLES       { sonusAlarmNodeID, sonusAlarmLevel, 
                      sonusAlarmSequenceId, sonusAlarmTime, 
                      sonusAlarmDescription, sonusVnfId, 
                      sonusVnfcInstanceId }
--     STATUS          mandatory
    DESCRIPTION     
            "The control channel connection between the SLB and a registered SBC is up."
    ::= 2

sonusSlbSbcConnectionDownNotification TRAP-TYPE
    ENTERPRISE      sonusSlbMIBNotifications
    VARIABLES       { sonusAlarmNodeID, sonusAlarmLevel, 
                      sonusAlarmSequenceId, sonusAlarmTime, 
                      sonusAlarmDescription, sonusVnfId, 
                      sonusVnfcInstanceId }
--     STATUS          mandatory
    DESCRIPTION     
            "The control channel connection between the SLB and a registered SBC is down."
    ::= 3

sonusSlbSbcsUnreachableNotification TRAP-TYPE
    ENTERPRISE      sonusSlbMIBNotifications
    VARIABLES       { sonusAlarmNodeID, sonusAlarmLevel, 
                      sonusAlarmSequenceId, sonusAlarmTime, 
                      sonusAlarmDescription, sonusSipSigPortNum }
--     STATUS          mandatory
    DESCRIPTION     
            "The SLB is unable to forward a SIP message because all registered SBCs that could process that message are unreachable."
    ::= 4

sonusSbxSlbConnectionUpNotification TRAP-TYPE
    ENTERPRISE      sonusSlbMIBNotifications
    VARIABLES       { sonusAlarmNodeID, sonusAlarmLevel, 
                      sonusAlarmSequenceId, sonusAlarmTime, 
                      sonusAlarmDescription, sonusSlbIpAddress }
--     STATUS          mandatory
    DESCRIPTION     
            "The SBC has successfully connected and registered with the SLB."
    ::= 5

sonusSbxSlbConnectionDownNotification TRAP-TYPE
    ENTERPRISE      sonusSlbMIBNotifications
    VARIABLES       { sonusAlarmNodeID, sonusAlarmLevel, 
                      sonusAlarmSequenceId, sonusAlarmTime, 
                      sonusAlarmDescription, sonusSlbIpAddress }
--     STATUS          mandatory
    DESCRIPTION     
            "The SBC's control channel connection with the SLB has gone down."
    ::= 6

sonusSbxSlbConnectionUpNotificationV6 TRAP-TYPE
    ENTERPRISE      sonusSlbMIBNotifications
    VARIABLES       { sonusAlarmNodeID, sonusAlarmLevel, 
                      sonusAlarmSequenceId, sonusAlarmTime, 
                      sonusAlarmDescription, sonusSlbIpv6Address }
--     STATUS          mandatory
    DESCRIPTION     
            "The SBC has successfully connected and registered with the SLB."
    ::= 7

sonusSbxSlbConnectionDownNotificationV6 TRAP-TYPE
    ENTERPRISE      sonusSlbMIBNotifications
    VARIABLES       { sonusAlarmNodeID, sonusAlarmLevel, 
                      sonusAlarmSequenceId, sonusAlarmTime, 
                      sonusAlarmDescription, sonusSlbIpv6Address }
--     STATUS          mandatory
    DESCRIPTION     
            "The SBC's control channel connection with the SLB has gone down."
    ::= 8

sonusSbxSlbGlobalLossRatioThresholdReachedNotification TRAP-TYPE
    ENTERPRISE      sonusSlbMIBNotifications
    VARIABLES       { sonusAlarmNodeID, sonusAlarmLevel, 
                      sonusAlarmSequenceId, sonusAlarmTime, 
                      sonusAlarmDescription, sonusCurrentGlobalLossRatio, 
                      sonusGlobalLossRatioLimit }
--     STATUS          mandatory
    DESCRIPTION     
            "This trap indicates the global loss ratio threshold for SLB has been reached or exceeded."
    ::= 9

sonusSbcSlbConnectionEstablishedNotification TRAP-TYPE
    ENTERPRISE      sonusSlbMIBNotifications
    VARIABLES       { sonusAlarmNodeID, sonusAlarmLevel, 
                      sonusAlarmSequenceId, sonusAlarmTime, 
                      sonusAlarmDescription, sonusSlbName, 
                      sonusSlbIpAddress }
--     STATUS          mandatory
    DESCRIPTION     
            "The connection between SBC and SLB is established."
    ::= 10

sonusSbcSlbConnectionNotEstablishedNotification TRAP-TYPE
    ENTERPRISE      sonusSlbMIBNotifications
    VARIABLES       { sonusAlarmNodeID, sonusAlarmLevel, 
                      sonusAlarmSequenceId, sonusAlarmTime, 
                      sonusAlarmDescription, sonusSlbName, 
                      sonusSlbIpAddress }
--     STATUS          mandatory
    DESCRIPTION     
            "The connection establishment between SBC and SLB failed"
    ::= 11

sonusSbxSlbGlobalLossRatioThresoldClearNotification TRAP-TYPE
    ENTERPRISE      sonusSlbMIBNotifications
    VARIABLES       { sonusAlarmNodeID, sonusAlarmLevel, 
                      sonusAlarmSequenceId, sonusAlarmTime, 
                      sonusAlarmDescription, sonusCurrentGlobalLossRatio, 
                      sonusGlobalLossRatioLimit }
--     STATUS          mandatory
    DESCRIPTION     
            "This trap indicates the global loss ratio threshold has been cleared."
    ::= 12

sonusSbxSlbGlobalUtilizationThresholdReachedNotification TRAP-TYPE
    ENTERPRISE      sonusSlbMIBNotifications
    VARIABLES       { sonusAlarmNodeID, sonusAlarmLevel, 
                      sonusAlarmSequenceId, sonusAlarmTime, 
                      sonusAlarmDescription, 
                      sonusCurrentGlobalUtilization, 
                      sonusGlobalUtilizationLimit }
--     STATUS          mandatory
    DESCRIPTION     
            "This trap indicates the global utilization threshold for SLB has been reached or exceeded."
    ::= 13

sonusSbxSlbGlobalUtilizationThresholdClearNotification TRAP-TYPE
    ENTERPRISE      sonusSlbMIBNotifications
    VARIABLES       { sonusAlarmNodeID, sonusAlarmLevel, 
                      sonusAlarmSequenceId, sonusAlarmTime, 
                      sonusAlarmDescription, 
                      sonusCurrentGlobalUtilization, 
                      sonusGlobalUtilizationLimit }
--     STATUS          mandatory
    DESCRIPTION     
            "This trap indicates the global utilization threshold has been cleared."
    ::= 14

sonusMicroServiceConnectionFailed TRAP-TYPE
    ENTERPRISE      sonusMicroServiceMIBNotifications
    VARIABLES       { sonusAlarmNodeID, sonusAlarmLevel, 
                      sonusAlarmSequenceId, sonusAlarmTime, 
                      sonusAlarmDescription, sonusMicroServiceName }
--     STATUS          mandatory
    DESCRIPTION     
            "The connection to the specified micro-service is lost."
    ::= 1

sonusMicroServiceConnectionSucceeded TRAP-TYPE
    ENTERPRISE      sonusMicroServiceMIBNotifications
    VARIABLES       { sonusAlarmNodeID, sonusAlarmLevel, 
                      sonusAlarmSequenceId, sonusAlarmTime, 
                      sonusAlarmDescription, sonusMicroServiceName }
--     STATUS          mandatory
    DESCRIPTION     
            "The connection to the specified micro-service is restored."
    ::= 2

sonusBfdSessionDown TRAP-TYPE
    ENTERPRISE      sonusBfdMIBNotifications
    VARIABLES       { sonusAlarmNodeID, sonusAlarmLevel, 
                      sonusAlarmSequenceId, sonusAlarmTime, 
                      sonusAlarmDescription, sonusBfdLinkId }
--     STATUS          mandatory
    DESCRIPTION     
            "BFD session for the specified linkId is DOWN"
    ::= 1

sonusBfdSessionUp TRAP-TYPE
    ENTERPRISE      sonusBfdMIBNotifications
    VARIABLES       { sonusAlarmNodeID, sonusAlarmLevel, 
                      sonusAlarmSequenceId, sonusAlarmTime, 
                      sonusAlarmDescription, sonusBfdLinkId }
--     STATUS          mandatory
    DESCRIPTION     
            "BFD session for the specified linkId is UP"
    ::= 2

sonusBfdSessionDelete TRAP-TYPE
    ENTERPRISE      sonusBfdMIBNotifications
    VARIABLES       { sonusAlarmNodeID, sonusAlarmLevel, 
                      sonusAlarmSequenceId, sonusAlarmTime, 
                      sonusAlarmDescription, sonusBfdLinkId }
--     STATUS          mandatory
    DESCRIPTION     
            "BFD session for the specified linkId is DELETED"
    ::= 3

sonusH248VMGtermNoRTPRcvdThresholdExceeded TRAP-TYPE
    ENTERPRISE      sonusH248NoRtpMIBNotifications
    VARIABLES       { sonusAlarmNodeID, sonusAlarmLevel, 
                      sonusAlarmSequenceId, sonusAlarmTime, 
                      sonusAlarmDescription, sonusH248VmgName, 
                      sonusH248TermThreshold, sonusH248NoRtpTerminations }
--     STATUS          mandatory
    DESCRIPTION     
            "This alarm is generated when the VMG is configured with a maximum threshold 
             specifying percentage of the total number of Terminations that never received 
             any RTP/RTCP during their session in the latest bin period, and that threshold 
             is exceeded"
    ::= 1

sonusH248ClearVMGtermNoRTPRcvdThresholdExceeded TRAP-TYPE
    ENTERPRISE      sonusH248NoRtpMIBNotifications
    VARIABLES       { sonusAlarmNodeID, sonusAlarmLevel, 
                      sonusAlarmSequenceId, sonusAlarmTime, 
                      sonusAlarmDescription, sonusH248VmgName, 
                      sonusH248ClearThreshold, 
                      sonusH248NoRtpTerminations, 
                      sonusH248MinimumRtpTerminations, 
                      sonusH248TotalRtpTerminations }
--     STATUS          mandatory
    DESCRIPTION     
            "This alarm is generated when the VMG is configured with a clear threshold 
             specifying percentage of the total number of Terminations that never received 
             any RTP/RTCP during their session in the latest bin period, and the latest 
             value goes under this threshold"
    ::= 2

sonusPacketPortBWusageThresholdExceeded TRAP-TYPE
    ENTERPRISE      sonusPortMIBNotifications
    VARIABLES       { sonusAlarmNodeID, sonusAlarmLevel, 
                      sonusAlarmSequenceId, sonusAlarmTime, 
                      sonusAlarmDescription, sonusEthernetPortName, 
                      sonusEthernetPortBwUsageThreshold, 
                      sonusEthernetPortBwUsage }
--     STATUS          mandatory
    DESCRIPTION     
            "This alarm is generated when the Bandwidth Usage exceeds a maximum threshold of 95%"
    ::= 1

sonusClearPacketPortclearThresholdExceeded TRAP-TYPE
    ENTERPRISE      sonusPortMIBNotifications
    VARIABLES       { sonusAlarmNodeID, sonusAlarmLevel, 
                      sonusAlarmSequenceId, sonusAlarmTime, 
                      sonusAlarmDescription, sonusEthernetPortName, 
                      sonusEthernetPortBwUsageClearThreshold, 
                      sonusEthernetPortBwUsage }
--     STATUS          mandatory
    DESCRIPTION     
            "This alarm is generated when the Bandwidth Usage returns back under a threshold of 90%"
    ::= 2

END -- end of module SONUS-SBX-TRAP-MIB.
