--
-- This SMIv2 module has been generated by smidump 0.2-cvs. Do not edit.
--

SONUS-SOFTSWITCH-SSREQ-MIB DEFINITIONS ::= BEGIN

IMPORTS
    MODULE-IDENTITY, NOTIFICATION-TYPE
        FROM SNMPv2-SMI
    sonusEventClass, sonusEventDescription, sonusEventLevel, 
    sonusEventTime
        FROM SONUS-COMMON-MIB
    sonusServicesMIBs
        FROM SONUS-SMI;

sonusSoftSwitchSsreqMIB MODULE-IDENTITY
    LAST-UPDATED    "200211040000Z"
    ORGANIZATION    
            "Sonus Networks, Inc."
    CONTACT-INFO    
            "   Customer Support    
             Sonus Networks, Inc.
             250 Apollo Drive
             Chelmsford, MA 01824
             USA
             
             Tel: 978-614-8100
             Fax: 978-614-8609"
    DESCRIPTION     
            "The MIB Module for SoftSwitch Ss Request Management."
    ::= { sonusServicesMIBs 19 }


sonusSoftSwitchSsreqMIBObjects OBJECT IDENTIFIER
    ::= { sonusSoftSwitchSsreqMIB 1 }

sonusSoftSwitchSsreqMIBNotifications OBJECT IDENTIFIER
    ::= { sonusSoftSwitchSsreqMIB 2 }

sonusSoftSwitchSsreqMIBNotificationsPrefix OBJECT IDENTIFIER
    ::= { sonusSoftSwitchSsreqMIBNotifications 0 }

sonusSoftSwitchSsreqMIBNotificationsObjects OBJECT IDENTIFIER
    ::= { sonusSoftSwitchSsreqMIBNotifications 1 }

sonusSoftSwitchSsreqDownNotification NOTIFICATION-TYPE
    OBJECTS         { sonusEventDescription, sonusEventClass, 
                      sonusEventLevel, sonusEventTime }
    STATUS          current
    DESCRIPTION     
            "Ss Request is down"
    ::= { sonusSoftSwitchSsreqMIBNotificationsPrefix 1 }

sonusSoftSwitchSsreqUpNotification NOTIFICATION-TYPE
    OBJECTS         { sonusEventDescription, sonusEventClass, 
                      sonusEventLevel, sonusEventTime }
    STATUS          current
    DESCRIPTION     
            "Ss Request is up"
    ::= { sonusSoftSwitchSsreqMIBNotificationsPrefix 2 }

END -- end of module SONUS-SOFTSWITCH-SSREQ-MIB.
