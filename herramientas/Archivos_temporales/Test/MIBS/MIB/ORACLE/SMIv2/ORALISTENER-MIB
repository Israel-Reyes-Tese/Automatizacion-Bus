--
-- This SMIv2 module has been generated by smidump 0.2-cvs. Do not edit.
--

ORALISTENER-MIB DEFINITIONS ::= BEGIN

IMPORTS
    Counter32, Gauge32, Integer32, NOTIFICATION-TYPE, OBJECT-TYPE, 
    TimeTicks, enterprises
        FROM SNMPv2-SMI
    DisplayString
        FROM SNMPv2-TC;

oracle OBJECT IDENTIFIER
    ::= { enterprises 111 }

oraListenerMIB OBJECT IDENTIFIER
    ::= { enterprises 111 5 }

oraListenerObjects OBJECT IDENTIFIER
    ::= { oraListenerMIB 1 }

oraListenerTable OBJECT-TYPE
    SYNTAX          SEQUENCE OF OraListenerEntry
    MAX-ACCESS      not-accessible
    STATUS          current
    DESCRIPTION     
            "The table of information about the generic network listeners 
             installed on a system."
    ::= { oraListenerObjects 1 }

oraListenerEntry OBJECT-TYPE
    SYNTAX          OraListenerEntry
    MAX-ACCESS      not-accessible
    STATUS          current
    DESCRIPTION     
            "An entry for a single generic network listener on the host."
    INDEX           { oraListenerIndex }
    ::= { oraListenerTable 1 }

OraListenerEntry ::=
    SEQUENCE {
        oraListenerIndex                Integer32,
        oraListenerName                 DisplayString,
        oraListenerVersion              DisplayString,
        oraListenerStartDate            DisplayString,
        oraListenerUptime               TimeTicks,
        oraListenerTraceLevel           INTEGER,
        oraListenerSecurityLevel        INTEGER,
        oraListenerParameterFile        DisplayString,
        oraListenerLogFile              DisplayString,
        oraListenerTraceFile            DisplayString,
        oraListenerState                INTEGER,
        oraListenerNumberOfServices     Integer32,
        oraListenerContact              DisplayString
    }

oraListenerIndex OBJECT-TYPE
    SYNTAX          Integer32
    MAX-ACCESS      read-only
    STATUS          current
    DESCRIPTION     
            "A numeric index, unique among all the generic listeners
             on this host."
    ::= { oraListenerEntry 1 }

oraListenerName OBJECT-TYPE
    SYNTAX          DisplayString
    MAX-ACCESS      read-only
    STATUS          current
    DESCRIPTION     
            "The name of this generic listener."
    ::= { oraListenerEntry 2 }

oraListenerVersion OBJECT-TYPE
    SYNTAX          DisplayString
    MAX-ACCESS      read-only
    STATUS          current
    DESCRIPTION     
            "The version number of this generic listener, in vendor specific
             format."
    ::= { oraListenerEntry 3 }

oraListenerStartDate OBJECT-TYPE
    SYNTAX          DisplayString
    MAX-ACCESS      read-only
    STATUS          current
    DESCRIPTION     
            "The date and time at which ths generic listener was started."
    ::= { oraListenerEntry 4 }

oraListenerUptime OBJECT-TYPE
    SYNTAX          TimeTicks
    MAX-ACCESS      read-only
    STATUS          current
    DESCRIPTION     
            "The value of sysUpTime at the time the generic listener
             was last started."
    ::= { oraListenerEntry 5 }

oraListenerTraceLevel OBJECT-TYPE
    SYNTAX          INTEGER { level1(1), level2(2), level3(3), user(4), 
                        level5(5), admin(6), level7(7), level8(8), 
                        level9(9), level10(10), level11(11), level12(12), 
                        level13(13), level14(14), level15(15), 
                        level16(16), off(17) }
    MAX-ACCESS      read-only
    STATUS          current
    DESCRIPTION     
            "indicates the level of detail the trace facility the generic
             listener records for events.  The greater the level is, the more
             detailed the level of tracing is."
    ::= { oraListenerEntry 6 }

oraListenerSecurityLevel OBJECT-TYPE
    SYNTAX          INTEGER { on(1), off(2) }
    MAX-ACCESS      read-only
    STATUS          current
    DESCRIPTION     
            "indicates whether the generic listener is password-protected
             or not.  If security is 'on', password is required to perform
             certain DBA tasks asgainst the listener using the listener
             control utility.  If security is 'off', password is not required."
    ::= { oraListenerEntry 7 }

oraListenerParameterFile OBJECT-TYPE
    SYNTAX          DisplayString
    MAX-ACCESS      read-only
    STATUS          current
    DESCRIPTION     
            "indicates the name of the file to which configuration
             information is stored.  Default is $ORACLE_HOME/network/admin/
             <listener_name>.ora."
    ::= { oraListenerEntry 8 }

oraListenerLogFile OBJECT-TYPE
    SYNTAX          DisplayString
    MAX-ACCESS      read-only
    STATUS          current
    DESCRIPTION     
            "indicates the directory in which to find the log file that is
             automatically generated for listener events.  Default is 
             operating system specific; on UNIX, for example, it is
             $ORACLE_HOME/network/log."
    ::= { oraListenerEntry 9 }

oraListenerTraceFile OBJECT-TYPE
    SYNTAX          DisplayString
    MAX-ACCESS      read-only
    STATUS          current
    DESCRIPTION     
            "indicates the name of the file to which trace information is
             written.  Default is $ORACLE_HOME/network/trace/<listener_name>.trc."
    ::= { oraListenerEntry 10 }

oraListenerState OBJECT-TYPE
    SYNTAX          INTEGER { up(1), down(2) }
    MAX-ACCESS      read-only
    STATUS          current
    DESCRIPTION     
            "indicates the current state of the generic listener.  'down'
             indicates that the generic listener is not available for any
             use, but is know to the agent.  'up' indicates that the generic
             listener is running and available for generic use.  This would
             be inspected by an agent on receipt of an oraListenerState trap."
    ::= { oraListenerEntry 11 }

oraListenerNumberOfServices OBJECT-TYPE
    SYNTAX          Integer32
    MAX-ACCESS      read-only
    STATUS          current
    DESCRIPTION     
            "indicates the number of different types services: dedicated
             sever, dispatcher, or prespawned shadow, configured with the
             generic listener."
    ::= { oraListenerEntry 12 }

oraListenerContact OBJECT-TYPE
    SYNTAX          DisplayString
    MAX-ACCESS      read-write
    STATUS          current
    DESCRIPTION     
            "The textual identification of the contact person for this
             managed listener, together with information on how to contact
             this person."
    ::= { oraListenerEntry 13 }

oraDedicatedSrvTable OBJECT-TYPE
    SYNTAX          SEQUENCE OF OraDedicatedSrvEntry
    MAX-ACCESS      not-accessible
    STATUS          current
    DESCRIPTION     
            "The table of the dedicated servers associated with an system
             identifier (SID) of the database."
    ::= { oraListenerObjects 2 }

oraDedicatedSrvEntry OBJECT-TYPE
    SYNTAX          OraDedicatedSrvEntry
    MAX-ACCESS      not-accessible
    STATUS          current
    DESCRIPTION     
            "An entry relating a dedicated server to a SID.
             The table is indexed first by oraSIDName, and then
             oraDedicatedSrvIndex so that all dedicated servers
             associated with a given SID can be found by SNMP
             traversal operations (get-next and get-bulk)."
    INDEX           { oraSIDName, oraDedicatedSrvIndex }
    ::= { oraDedicatedSrvTable 1 }

OraDedicatedSrvEntry ::=
    SEQUENCE {
        oraDedicatedSrvIndex            Integer32,
        oraDedicatedSrvEstablishedConnections     Counter32,
        oraDedicatedSrvRejectedConnections  Counter32
    }

oraDedicatedSrvIndex OBJECT-TYPE
    SYNTAX          Integer32
    MAX-ACCESS      read-only
    STATUS          current
    DESCRIPTION     
            "A numeric index, unique among all the dedicated servers."
    ::= { oraDedicatedSrvEntry 1 }

oraDedicatedSrvEstablishedConnections OBJECT-TYPE
    SYNTAX          Counter32
    MAX-ACCESS      read-only
    STATUS          current
    DESCRIPTION     
            "indicates how many incoming connection requests have been
             accepted by the dedicated server."
    ::= { oraDedicatedSrvEntry 2 }

oraDedicatedSrvRejectedConnections OBJECT-TYPE
    SYNTAX          Counter32
    MAX-ACCESS      read-only
    STATUS          current
    DESCRIPTION     
            "indicates how many incoming connection requests have been
             rejected by the dedicated server."
    ::= { oraDedicatedSrvEntry 3 }

oraDispatcherTable OBJECT-TYPE
    SYNTAX          SEQUENCE OF OraDispatcherEntry
    MAX-ACCESS      not-accessible
    STATUS          current
    DESCRIPTION     
            "The table of the dispatchers associated with an system
             identifier (SID) of the database."
    ::= { oraListenerObjects 3 }

oraDispatcherEntry OBJECT-TYPE
    SYNTAX          OraDispatcherEntry
    MAX-ACCESS      not-accessible
    STATUS          current
    DESCRIPTION     
            "An entry relating a dispatcher to a SID.  The
             table is indexed first by oraSIDName, and then
             oraDispatcherIndex so that all dispatchers associated
             with a given SID can be found by SNMP traversal
             operations (get-next and get-bulk)."
    INDEX           { oraSIDName, oraDispatcherIndex }
    ::= { oraDispatcherTable 1 }

OraDispatcherEntry ::=
    SEQUENCE {
        oraDispatcherIndex              Integer32,
        oraDispatcherEstablishedConnections   Counter32,
        oraDispatcherRejectedConnections Counter32,
        oraDispatcherCurrentConnections Gauge32,
        oraDispatcherMaximumConnections Integer32,
        oraDispatcherState              INTEGER,
        oraDispatcherProtocolInfo       DisplayString
    }

oraDispatcherIndex OBJECT-TYPE
    SYNTAX          Integer32
    MAX-ACCESS      read-only
    STATUS          current
    DESCRIPTION     
            "A numeric index, unique among all the dispatchers."
    ::= { oraDispatcherEntry 1 }

oraDispatcherEstablishedConnections OBJECT-TYPE
    SYNTAX          Counter32
    MAX-ACCESS      read-only
    STATUS          current
    DESCRIPTION     
            "indicates how many incoming connection requests have been 
             accepted by the dispatcher."
    ::= { oraDispatcherEntry 2 }

oraDispatcherRejectedConnections OBJECT-TYPE
    SYNTAX          Counter32
    MAX-ACCESS      read-only
    STATUS          current
    DESCRIPTION     
            "indicates how many incoming connection requests have been 
             rejected by the dispatcher."
    ::= { oraDispatcherEntry 3 }

oraDispatcherCurrentConnections OBJECT-TYPE
    SYNTAX          Gauge32
    MAX-ACCESS      read-only
    STATUS          current
    DESCRIPTION     
            "indicates the number of connection requests currently being
             redirected to the dispatcher."
    ::= { oraDispatcherEntry 4 }

oraDispatcherMaximumConnections OBJECT-TYPE
    SYNTAX          Integer32
    MAX-ACCESS      read-only
    STATUS          current
    DESCRIPTION     
            "indicates the greatest number of connection requests that
             will ever be accepted by the dispatcher."
    ::= { oraDispatcherEntry 5 }

oraDispatcherState OBJECT-TYPE
    SYNTAX          INTEGER { blocked(1), ready(2) }
    MAX-ACCESS      read-only
    STATUS          current
    DESCRIPTION     
            "indicates the current state of the dispatcher.  'blocked'
             indicates that the dispatcher is temporarily not accepting
             redirected connectioin requests.  'ready' indicates that 
             the dispacher is ready to accept any redirected conenction
             requests."
    ::= { oraDispatcherEntry 6 }

oraDispatcherProtocolInfo OBJECT-TYPE
    SYNTAX          DisplayString
    MAX-ACCESS      read-only
    STATUS          current
    DESCRIPTION     
            "indicates the protocol of the dispatcher listens on as well
             as protocol specific information.  The exact format will be
             vendor and host specific."
    ::= { oraDispatcherEntry 7 }

oraPrespawnedSrvTable OBJECT-TYPE
    SYNTAX          SEQUENCE OF OraPrespawnedSrvEntry
    MAX-ACCESS      not-accessible
    STATUS          current
    DESCRIPTION     
            "The table of the prespawned servers associated with a SID."
    ::= { oraListenerObjects 4 }

oraPrespawnedSrvEntry OBJECT-TYPE
    SYNTAX          OraPrespawnedSrvEntry
    MAX-ACCESS      not-accessible
    STATUS          current
    DESCRIPTION     
            "An entry relating a prespawned server to a SID.
             The table is indexed first by oraSIDName, and then
             oraPrespawnedSrvIndex so that all prespawned servers
             associated with a given SID can be found by SNMP
             traversal operations (get-next and get-bulk)."
    INDEX           { oraSIDName, oraPrespawnedSrvIndex }
    ::= { oraPrespawnedSrvTable 1 }

OraPrespawnedSrvEntry ::=
    SEQUENCE {
        oraPrespawnedSrvIndex           Integer32,
        oraPrespawnedSrvEstablishedConnections      Counter32,
        oraPrespawnedSrvRejectedConnections   Counter32,
        oraPrespawnedSrvCurrentConnections  Gauge32,
        oraPrespawnedSrvMaximumConnections  Integer32,
        oraPrespawnedSrvState           INTEGER,
        oraPrespawnedSrvProtocolInfo    DisplayString,
        oraPrespawnedSrvProcessorID     DisplayString
    }

oraPrespawnedSrvIndex OBJECT-TYPE
    SYNTAX          Integer32
    MAX-ACCESS      read-only
    STATUS          current
    DESCRIPTION     
            "A numeric index, unique among all the prespawned servers."
    ::= { oraPrespawnedSrvEntry 1 }

oraPrespawnedSrvEstablishedConnections OBJECT-TYPE
    SYNTAX          Counter32
    MAX-ACCESS      read-only
    STATUS          current
    DESCRIPTION     
            "indicates how many incoming connection requests have been 
             accepted by the prespawned server."
    ::= { oraPrespawnedSrvEntry 2 }

oraPrespawnedSrvRejectedConnections OBJECT-TYPE
    SYNTAX          Counter32
    MAX-ACCESS      read-only
    STATUS          current
    DESCRIPTION     
            "indicates how many incoming connection requests have been 
             rejected by the prespawned server."
    ::= { oraPrespawnedSrvEntry 3 }

oraPrespawnedSrvCurrentConnections OBJECT-TYPE
    SYNTAX          Gauge32
    MAX-ACCESS      read-only
    STATUS          current
    DESCRIPTION     
            "indicates the number of connection requests currently being
             redirected to the prespawned server."
    ::= { oraPrespawnedSrvEntry 4 }

oraPrespawnedSrvMaximumConnections OBJECT-TYPE
    SYNTAX          Integer32
    MAX-ACCESS      read-only
    STATUS          current
    DESCRIPTION     
            "indicates the greatest number of connection requests that
             will ever be accepted by the prespawned server."
    ::= { oraPrespawnedSrvEntry 5 }

oraPrespawnedSrvState OBJECT-TYPE
    SYNTAX          INTEGER { blocked(1), ready(2) }
    MAX-ACCESS      read-only
    STATUS          current
    DESCRIPTION     
            "indicates the current state of the prespawned server.  'blocked'
             indicates that the prespawned server is temporarily not
             accepting redirected connection requests.  'ready' indicates
             the prespawned server is ready to accept any redirected conenction
             requests."
    ::= { oraPrespawnedSrvEntry 6 }

oraPrespawnedSrvProtocolInfo OBJECT-TYPE
    SYNTAX          DisplayString
    MAX-ACCESS      read-only
    STATUS          current
    DESCRIPTION     
            "indicates the protocol of the prespawned server listens on as well
             as protocol specific information.  The exact format will be
             vendor and host specific."
    ::= { oraPrespawnedSrvEntry 7 }

oraPrespawnedSrvProcessorID OBJECT-TYPE
    SYNTAX          DisplayString
    MAX-ACCESS      read-only
    STATUS          current
    DESCRIPTION     
            "indicates the process ID of the prespawned server."
    ::= { oraPrespawnedSrvEntry 8 }

oraSIDTable OBJECT-TYPE
    SYNTAX          SEQUENCE OF OraSIDEntry
    MAX-ACCESS      not-accessible
    STATUS          current
    DESCRIPTION     
            "The table of information about the SIDs of the databases
             for whom the listener listens on.  The system identifier
              (SID) specifies the ORACLE System ID of the database server. "
    ::= { oraListenerObjects 5 }

oraSIDEntry OBJECT-TYPE
    SYNTAX          OraSIDEntry
    MAX-ACCESS      not-accessible
    STATUS          current
    DESCRIPTION     
            "An entry relating a SID to a generic listener."
    INDEX           { oraSIDName }
    ::= { oraSIDTable 1 }

OraSIDEntry ::=
    SEQUENCE {
        oraSIDListenerIndex             Integer32,
        oraSIDName                      DisplayString,
        oraSIDCurrentConnectedClients   Gauge32,
        oraSIDReservedConnections       Counter32
    }

oraSIDListenerIndex OBJECT-TYPE
    SYNTAX          Integer32
    MAX-ACCESS      read-only
    STATUS          current
    DESCRIPTION     
            "A numeric index, unique among all the generic listeners."
    ::= { oraSIDEntry 1 }

oraSIDName OBJECT-TYPE
    SYNTAX          DisplayString
    MAX-ACCESS      read-only
    STATUS          current
    DESCRIPTION     
            "The name of the SID.  There is a one-to-one correspondence
             between database and SID."
    ::= { oraSIDEntry 2 }

oraSIDCurrentConnectedClients OBJECT-TYPE
    SYNTAX          Gauge32
    MAX-ACCESS      read-only
    STATUS          current
    DESCRIPTION     
            "indicates the total number of currently connected clients
             thru this SID."
    ::= { oraSIDEntry 3 }

oraSIDReservedConnections OBJECT-TYPE
    SYNTAX          Counter32
    MAX-ACCESS      read-only
    STATUS          current
    DESCRIPTION     
            "indicates the total number of reserved connections for
             clients on this SID."
    ::= { oraSIDEntry 4 }

oraListenAddressTable OBJECT-TYPE
    SYNTAX          SEQUENCE OF OraListenAddressEntry
    MAX-ACCESS      not-accessible
    STATUS          current
    DESCRIPTION     
            "The table of information about the addresses that the listener
             is listening at."
    ::= { oraListenerObjects 6 }

oraListenAddressEntry OBJECT-TYPE
    SYNTAX          OraListenAddressEntry
    MAX-ACCESS      not-accessible
    STATUS          current
    DESCRIPTION     
            "An entry relating the listen addresses to a generic listener."
    INDEX           { oraListenerIndex, oraListenAddressIndex }
    ::= { oraListenAddressTable 1 }

OraListenAddressEntry ::=
    SEQUENCE {
        oraListenAddressIndex           Integer32,
        oraListenAddress                DisplayString
    }

oraListenAddressIndex OBJECT-TYPE
    SYNTAX          Integer32
    MAX-ACCESS      read-only
    STATUS          current
    DESCRIPTION     
            "A numeric index, unique among all the listen addresses."
    ::= { oraListenAddressEntry 1 }

oraListenAddress OBJECT-TYPE
    SYNTAX          DisplayString
    MAX-ACCESS      read-only
    STATUS          current
    DESCRIPTION     
            "The addresses to whom the listener is listening at."
    ::= { oraListenAddressEntry 2 }

oraListenerTraps OBJECT IDENTIFIER
    ::= { oraListenerMIB 2 }

oraListenerStateChange NOTIFICATION-TYPE
    OBJECTS         { oraListenerState }
    STATUS          current
    DESCRIPTION     
            "An rdbmsStateChange trap signifies that one of the generic
             listeners managed by this agent has changed its oraListenerState
             in a way that makes it less accessible for use."
    ::= { oraListenerTraps 0 1 }

END -- end of module ORALISTENER-MIB.
