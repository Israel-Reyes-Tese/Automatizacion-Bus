--
-- This SMIv2 module has been generated by smidump 0.2-cvs. Do not edit.
--

SM10-R3-MIB DEFINITIONS ::= BEGIN

IMPORTS
    InetAddress, InetAddressType
        FROM INET-ADDRESS-MIB
    MODULE-COMPLIANCE, NOTIFICATION-GROUP, OBJECT-GROUP
        FROM SNMPv2-CONF
    MODULE-IDENTITY, NOTIFICATION-TYPE, OBJECT-TYPE, enterprises
        FROM SNMPv2-SMI
    DisplayString
        FROM SNMPv2-TC;

sm10R3 MODULE-IDENTITY
    LAST-UPDATED    "201108051503Z"
    ORGANIZATION    
            "NetApp, Inc"
    CONTACT-INFO    
            "http://www.netapp.com/us/support/"
    DESCRIPTION     
            "SANtricity Storage Manager for E-Series Storage Systems"
    REVISION        "201108051503Z"
    DESCRIPTION     
            "This is the third revision of the sm10 MIB. This revision of the sm10
             MIB module has been converted to NetApp private enterprise number space."
    ::= { storageManager 500 }


netapp OBJECT IDENTIFIER
    ::= { enterprises 789 }

eSeriesStorageSystem OBJECT IDENTIFIER
    ::= { netapp 1123 }

storageManager OBJECT IDENTIFIER
    ::= { eSeriesStorageSystem 1 }

smConformance OBJECT IDENTIFIER
    ::= { storageManager 8 }

smCompliance OBJECT IDENTIFIER
    ::= { smConformance 1 }

smGroups OBJECT IDENTIFIER
    ::= { smConformance 2 }

sm10R3TrapBase OBJECT IDENTIFIER
    ::= { sm10R3 0 }

infoTable OBJECT-TYPE
    SYNTAX          SEQUENCE OF InfoEntry
    MAX-ACCESS      not-accessible
    STATUS          current
    DESCRIPTION     
            "Information for array traps."
    ::= { sm10R3 1 }

infoEntry OBJECT-TYPE
    SYNTAX          InfoEntry
    MAX-ACCESS      not-accessible
    STATUS          current
    DESCRIPTION     
            "The data for array traps."
    INDEX           { deviceHostIPType }
    ::= { infoTable 1 }

InfoEntry ::=
    SEQUENCE {
        deviceHostIPType                InetAddressType,
        deviceHostIPAddr                InetAddress,
        deviceHostName                  DisplayString,
        deviceUserLabel                 DisplayString,
        deviceErrorCode                 DisplayString,
        eventTime                       DisplayString,
        trapDescription                 DisplayString,
        componentType                   DisplayString,
        componentLocation               DisplayString
    }

deviceHostIPType OBJECT-TYPE
    SYNTAX          InetAddressType
    MAX-ACCESS      read-only
    STATUS          current
    DESCRIPTION     
            "Type of IP Address of the network-attached device or device host. 0 unknown, 1 ipv4, 2 ipv6"
    ::= { infoEntry 1 }

deviceHostIPAddr OBJECT-TYPE
    SYNTAX          InetAddress
    MAX-ACCESS      read-only
    STATUS          current
    DESCRIPTION     
            "IP Address of the network-attached device or device host."
    ::= { infoEntry 2 }

deviceHostName OBJECT-TYPE
    SYNTAX          DisplayString (SIZE(0..17))
    MAX-ACCESS      read-only
    STATUS          current
    DESCRIPTION     
            "The user label for the host of the device being reported on."
    ::= { infoEntry 3 }

deviceUserLabel OBJECT-TYPE
    SYNTAX          DisplayString (SIZE(0..30))
    MAX-ACCESS      read-only
    STATUS          current
    DESCRIPTION     
            "The user label for the device being reported on."
    ::= { infoEntry 4 }

deviceErrorCode OBJECT-TYPE
    SYNTAX          DisplayString (SIZE(0..19))
    MAX-ACCESS      read-only
    STATUS          current
    DESCRIPTION     
            "The error code as reported by the device or host."
    ::= { infoEntry 5 }

eventTime OBJECT-TYPE
    SYNTAX          DisplayString (SIZE(0..39))
    MAX-ACCESS      read-only
    STATUS          current
    DESCRIPTION     
            "The time at which the event happen on the device."
    ::= { infoEntry 6 }

trapDescription OBJECT-TYPE
    SYNTAX          DisplayString (SIZE(0..69))
    MAX-ACCESS      read-only
    STATUS          current
    DESCRIPTION     
            "A string to indicate the nature of the trap"
    ::= { infoEntry 7 }

componentType OBJECT-TYPE
    SYNTAX          DisplayString (SIZE(0..59))
    MAX-ACCESS      read-only
    STATUS          current
    DESCRIPTION     
            "A string to identify the failing component type"
    ::= { infoEntry 8 }

componentLocation OBJECT-TYPE
    SYNTAX          DisplayString (SIZE(0..39))
    MAX-ACCESS      read-only
    STATUS          current
    DESCRIPTION     
            "A string to identify the location of the failing component"
    ::= { infoEntry 9 }

storageServer OBJECT IDENTIFIER
    ::= { eSeriesStorageSystem 2 }

storageArrayCritical NOTIFICATION-TYPE
    OBJECTS         { deviceHostIPType, deviceHostIPAddr, deviceHostName, 
                      deviceUserLabel, deviceErrorCode, eventTime, 
                      trapDescription, componentType, componentLocation }
    STATUS          current
    DESCRIPTION     
            "This trap indicates an event where user-interaction is required immediately.
             Some example events are component failures or critical errors."
    ::= { sm10R3TrapBase 2 }

smObjectGroup OBJECT-GROUP
    OBJECTS         { deviceHostIPType, deviceHostIPAddr, deviceHostName, 
                      deviceUserLabel, deviceErrorCode, eventTime, 
                      trapDescription, componentType, componentLocation }
    STATUS          current
    DESCRIPTION     
            "A collection of objects that are current in this
             MIB."
    ::= { smGroups 1 }

smNotificationGroup NOTIFICATION-GROUP
    NOTIFICATIONS   { storageArrayCritical }
    STATUS          current
    DESCRIPTION     
            "A collection of notifications that are current in this
             MIB."
    ::= { smGroups 2 }

smGrpCompliance MODULE-COMPLIANCE
    STATUS          current
    DESCRIPTION     
            "The compliance statement for current SNMP entities in
             the NetApp E-Series Storage Systems SM10-R3 MIB."

    MODULE          -- this module

        MANDATORY-GROUPS    { smObjectGroup, smNotificationGroup }

    ::= { smCompliance 1 }

END -- end of module SM10-R3-MIB.
