--
-- This SMIv1 module has been generated by smidump 0.2-cvs. Do not edit.
--

SONUS-SOFTSWITCH-VNFM-ENGINE-MIB DEFINITIONS ::= BEGIN

IMPORTS
    TRAP-TYPE
        FROM RFC-1215
    sonusEventClass, sonusEventDescription, sonusEventLevel, 
    sonusEventTime
        FROM SONUS-COMMON-MIB
    sonusServicesMIBs
        FROM SONUS-SMI;

sonusSoftSwitchVNFMEngineMIB OBJECT IDENTIFIER
    ::= { sonusServicesMIBs 46 }

-- sonusSoftSwitchVNFMEngineMIB MODULE-IDENTITY
--     LAST-UPDATED    "201806010000Z"
--     ORGANIZATION    
--             "Sonus Networks, Inc."
--     CONTACT-INFO    
--             "   Customer Support    
--              Sonus Networks, Inc.
--              250 Apollo Drive
--              Chelmsford, MA 01824
--              USA
--              
--              Tel: 978-614-8100
--              Fax: 978-614-8609"
--     DESCRIPTION     
--             "The MIB Module for SoftSwitch VNFM Engine Management."
--     ::= { sonusServicesMIBs 46 }


sonusSoftSwitchVNFMEngineMIBObjects OBJECT IDENTIFIER
    ::= { sonusSoftSwitchVNFMEngineMIB 1 }

sonusSoftSwitchVNFMEngineMIBNotifications OBJECT IDENTIFIER
    ::= { sonusSoftSwitchVNFMEngineMIB 2 }

sonusSoftSwitchVNFMEngineMIBNotificationsPrefix OBJECT IDENTIFIER
    ::= { sonusSoftSwitchVNFMEngineMIBNotifications 0 }

sonusSoftSwitchVnfmUpNotification TRAP-TYPE
    ENTERPRISE      sonusSoftSwitchVNFMEngineMIBNotifications
    VARIABLES       { sonusEventDescription, sonusEventClass, 
                      sonusEventLevel, sonusEventTime }
--     STATUS          mandatory
    DESCRIPTION     
            "SoftSwitch VNFM Engine is up."
    ::= 1

sonusSoftSwitchVnfmDownNotification TRAP-TYPE
    ENTERPRISE      sonusSoftSwitchVNFMEngineMIBNotifications
    VARIABLES       { sonusEventDescription, sonusEventClass, 
                      sonusEventLevel, sonusEventTime }
--     STATUS          mandatory
    DESCRIPTION     
            "SoftSwitch VNFM Engine is down."
    ::= 2

sonusSoftSwitchVnfmHeartbeatLostNotification TRAP-TYPE
    ENTERPRISE      sonusSoftSwitchVNFMEngineMIBNotifications
    VARIABLES       { sonusEventDescription, sonusEventClass, 
                      sonusEventLevel, sonusEventTime }
--     STATUS          mandatory
    DESCRIPTION     
            "SoftSwitch VNFM Engine lost heartbeat to VNFM."
    ::= 3

sonusSoftSwitchVnfmHeartbeatRecoveredNotification TRAP-TYPE
    ENTERPRISE      sonusSoftSwitchVNFMEngineMIBNotifications
    VARIABLES       { sonusEventDescription, sonusEventClass, 
                      sonusEventLevel, sonusEventTime }
--     STATUS          mandatory
    DESCRIPTION     
            "SoftSwitch VNFM Engine recovered heartbeat to VNFM."
    ::= 4

END -- end of module SONUS-SOFTSWITCH-VNFM-ENGINE-MIB.
