--
-- This SMIv1 module has been generated by smidump 0.2-cvs. Do not edit.
--

SONUS-SOFTSWITCH-DIMA-MIB DEFINITIONS ::= BEGIN

IMPORTS
    OBJECT-TYPE
        FROM RFC-1212
    TRAP-TYPE
        FROM RFC-1215
    Counter
        FROM RFC1155-SMI
    sonusEventClass, sonusEventDescription, sonusEventLevel, 
    sonusEventTime
        FROM SONUS-COMMON-MIB
    sonusServicesMIBs
        FROM SONUS-SMI;

sonusSoftSwitchDIMAMIB OBJECT IDENTIFIER
    ::= { sonusServicesMIBs 31 }

-- sonusSoftSwitchDIMAMIB MODULE-IDENTITY
--     LAST-UPDATED    "200707100000Z"
--     ORGANIZATION    
--             "Sonus Networks, Inc."
--     CONTACT-INFO    
--             "   Customer Support    
--              Sonus Networks, Inc.
--              7 Technology Park Drive
--              Westford, MA 01886
--              USA
--              
--              Tel: 978-614-8100
--              Fax: 978-614-8609"
--     DESCRIPTION     
--             "The MIB Module for the Diameter Agent."
--     ::= { sonusServicesMIBs 31 }


sonusSoftSwitchDIMAMIBObjects OBJECT IDENTIFIER
    ::= { sonusSoftSwitchDIMAMIB 1 }

sonusSoftSwitchDIMAMIBNotifications OBJECT IDENTIFIER
    ::= { sonusSoftSwitchDIMAMIB 2 }

sonusSoftSwitchDIMAMIBNotificationsPrefix OBJECT IDENTIFIER
    ::= { sonusSoftSwitchDIMAMIBNotifications 0 }

sonusSoftSwitchDIMAMIBNotificationsObjects OBJECT IDENTIFIER
    ::= { sonusSoftSwitchDIMAMIBNotifications 1 }

sonusSoftSwitchDIMADiameterPeerName OBJECT-TYPE
    SYNTAX          OCTET STRING
    ACCESS          read-only
    STATUS          mandatory
    DESCRIPTION     
            "Diameter Peer Name."
    ::= { sonusSoftSwitchDIMAMIBNotificationsObjects 1 }

sonusSoftSwitchDIMAMIBCounters OBJECT IDENTIFIER
    ::= { sonusSoftSwitchDIMAMIB 3 }

sonusSoftSwitchDIMAStdDiameterMesgSent OBJECT-TYPE
    SYNTAX          Counter
    ACCESS          read-only
    STATUS          mandatory
    DESCRIPTION     
            "Number of messages sent to Standard Diameter Peers."
    ::= { sonusSoftSwitchDIMAMIBCounters 1 }

sonusSoftSwitchDIMAStdDiameterMesgRcvd OBJECT-TYPE
    SYNTAX          Counter
    ACCESS          read-only
    STATUS          mandatory
    DESCRIPTION     
            "Number of messages received from Standard Diameter Peers."
    ::= { sonusSoftSwitchDIMAMIBCounters 2 }

sonusSoftSwitchDIMAMesgSentToPES OBJECT-TYPE
    SYNTAX          Counter
    ACCESS          read-only
    STATUS          mandatory
    DESCRIPTION     
            "Number of messages sent to PES."
    ::= { sonusSoftSwitchDIMAMIBCounters 3 }

sonusSoftSwitchDIMAMesgRcvdFromPES OBJECT-TYPE
    SYNTAX          Counter
    ACCESS          read-only
    STATUS          mandatory
    DESCRIPTION     
            "Number of messages received from PES."
    ::= { sonusSoftSwitchDIMAMIBCounters 4 }

sonusSoftSwitchDIMAMesgSentToSCPA OBJECT-TYPE
    SYNTAX          Counter
    ACCESS          read-only
    STATUS          mandatory
    DESCRIPTION     
            "Number of messages sent to SCPA."
    ::= { sonusSoftSwitchDIMAMIBCounters 5 }

sonusSoftSwitchDIMAMesgRcvdFromSCPA OBJECT-TYPE
    SYNTAX          Counter
    ACCESS          read-only
    STATUS          mandatory
    DESCRIPTION     
            "Number of messages received from SCPA."
    ::= { sonusSoftSwitchDIMAMIBCounters 6 }

sonusSoftSwitchDIMADownNotification TRAP-TYPE
    ENTERPRISE      sonusSoftSwitchDIMAMIBNotifications
    VARIABLES       { sonusEventDescription, sonusEventClass, 
                      sonusEventLevel, sonusEventTime }
--     STATUS          mandatory
    DESCRIPTION     
            "DIMA shutdown event."
    ::= 1

sonusSoftSwitchDIMAUpNotification TRAP-TYPE
    ENTERPRISE      sonusSoftSwitchDIMAMIBNotifications
    VARIABLES       { sonusEventDescription, sonusEventClass, 
                      sonusEventLevel, sonusEventTime }
--     STATUS          mandatory
    DESCRIPTION     
            "DIMA startup event"
    ::= 2

sonusSoftSwitchDIMADiameterPeerOpenNotification TRAP-TYPE
    ENTERPRISE      sonusSoftSwitchDIMAMIBNotifications
    VARIABLES       { sonusSoftSwitchDIMADiameterPeerName, 
                      sonusEventDescription, sonusEventClass, 
                      sonusEventLevel, sonusEventTime }
--     STATUS          mandatory
    DESCRIPTION     
            "Connection to a Standard Diameter peer is opened."
    ::= 3

sonusSoftSwitchDIMADiameterPeerCloseNotification TRAP-TYPE
    ENTERPRISE      sonusSoftSwitchDIMAMIBNotifications
    VARIABLES       { sonusSoftSwitchDIMADiameterPeerName, 
                      sonusEventDescription, sonusEventClass, 
                      sonusEventLevel, sonusEventTime }
--     STATUS          mandatory
    DESCRIPTION     
            "Connection to a Standard Diameter peer is closed."
    ::= 4

END -- end of module SONUS-SOFTSWITCH-DIMA-MIB.
