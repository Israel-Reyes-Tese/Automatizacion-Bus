--
-- This SMIv2 module has been generated by smidump 0.2-cvs. Do not edit.
--

IFT-RAID-MIB DEFINITIONS ::= BEGIN

IMPORTS
    NOTIFICATION-TYPE, OBJECT-TYPE, enterprises
        FROM SNMPv2-SMI;

infortrend OBJECT IDENTIFIER
    ::= { enterprises 1714 }

iftRaid OBJECT IDENTIFIER
    ::= { infortrend 1 }

iftMgm OBJECT IDENTIFIER
    ::= { iftRaid 2 }

iftNpc OBJECT IDENTIFIER
    ::= { iftMgm 3 }

iftSnmpTrap OBJECT IDENTIFIER
    ::= { iftNpc 1 }

iftEventText OBJECT-TYPE
    SYNTAX          OCTET STRING
    MAX-ACCESS      read-only
    STATUS          current
    DESCRIPTION     
            "The description of the event"
    ::= { iftSnmpTrap 1 }

iftCtlrEventTrap NOTIFICATION-TYPE
    OBJECTS         { iftEventText }
    STATUS          current
    DESCRIPTION     
            "There is a controller event occurred"
    ::= { infortrend 0 1 }

END -- end of module IFT-RAID-MIB.
