--
-- This SMIv2 module has been generated by smidump 0.2-cvs. Do not edit.
--

SONUS-DSI-TRANSPORTER-MIB DEFINITIONS ::= BEGIN

IMPORTS
    MODULE-IDENTITY, NOTIFICATION-TYPE
        FROM SNMPv2-SMI
    sonusEventClass, sonusEventDescription, sonusEventLevel, 
    sonusEventTime
        FROM SONUS-COMMON-MIB
    sonusServicesMIBs
        FROM SONUS-SMI;

sonusDsiTransporterMIB MODULE-IDENTITY
    LAST-UPDATED    "200708180000Z"
    ORGANIZATION    
            "Sonus Networks, Inc."
    CONTACT-INFO    
            "   Customer Support    
             Sonus Networks, Inc.
             250 Apollo Drive
             Chelmsford, MA 01824
             USA
             
             Tel: 978-614-8100
             Fax: 978-614-8609"
    DESCRIPTION     
            "The MIB Module for DataStreamIntegrator (DSI) Transporter Management."
    ::= { sonusServicesMIBs 23 }


sonusDsiTransporterMIBObjects OBJECT IDENTIFIER
    ::= { sonusDsiTransporterMIB 1 }

sonusDsiTransporterMIBNotifications OBJECT IDENTIFIER
    ::= { sonusDsiTransporterMIB 2 }

sonusDsiTransporterMIBNotificationsPrefix OBJECT IDENTIFIER
    ::= { sonusDsiTransporterMIBNotifications 0 }

sonusDsiTransporterMIBNotificationsObjects OBJECT IDENTIFIER
    ::= { sonusDsiTransporterMIBNotifications 1 }

sonusDsiTransporterDownNotification NOTIFICATION-TYPE
    OBJECTS         { sonusEventDescription, sonusEventClass, 
                      sonusEventLevel, sonusEventTime }
    STATUS          current
    DESCRIPTION     
            "."
    ::= { sonusDsiTransporterMIBNotificationsPrefix 1 }

sonusDsiTransporterConnDownNotification NOTIFICATION-TYPE
    OBJECTS         { sonusEventDescription, sonusEventClass, 
                      sonusEventLevel, sonusEventTime }
    STATUS          current
    DESCRIPTION     
            "."
    ::= { sonusDsiTransporterMIBNotificationsPrefix 2 }

sonusDsiTransporterFtpDownNotification NOTIFICATION-TYPE
    OBJECTS         { sonusEventDescription, sonusEventClass, 
                      sonusEventLevel, sonusEventTime }
    STATUS          current
    DESCRIPTION     
            "."
    ::= { sonusDsiTransporterMIBNotificationsPrefix 3 }

sonusDsiTransporterFtpLoginFailedNotification NOTIFICATION-TYPE
    OBJECTS         { sonusEventDescription, sonusEventClass, 
                      sonusEventLevel, sonusEventTime }
    STATUS          current
    DESCRIPTION     
            "."
    ::= { sonusDsiTransporterMIBNotificationsPrefix 4 }

sonusDsiTransporterFtpTransferFailedNotification NOTIFICATION-TYPE
    OBJECTS         { sonusEventDescription, sonusEventClass, 
                      sonusEventLevel, sonusEventTime }
    STATUS          current
    DESCRIPTION     
            "."
    ::= { sonusDsiTransporterMIBNotificationsPrefix 5 }

sonusDsiTransporterIOOpenErrorNotification NOTIFICATION-TYPE
    OBJECTS         { sonusEventDescription, sonusEventClass, 
                      sonusEventLevel, sonusEventTime }
    STATUS          current
    DESCRIPTION     
            "."
    ::= { sonusDsiTransporterMIBNotificationsPrefix 6 }

sonusDsiTransporterIOReadErrorNotification NOTIFICATION-TYPE
    OBJECTS         { sonusEventDescription, sonusEventClass, 
                      sonusEventLevel, sonusEventTime }
    STATUS          current
    DESCRIPTION     
            "."
    ::= { sonusDsiTransporterMIBNotificationsPrefix 7 }

sonusDsiTransporterIOWriteErrorNotification NOTIFICATION-TYPE
    OBJECTS         { sonusEventDescription, sonusEventClass, 
                      sonusEventLevel, sonusEventTime }
    STATUS          current
    DESCRIPTION     
            "."
    ::= { sonusDsiTransporterMIBNotificationsPrefix 8 }

sonusDsiTransporterIORenameErrorNotification NOTIFICATION-TYPE
    OBJECTS         { sonusEventDescription, sonusEventClass, 
                      sonusEventLevel, sonusEventTime }
    STATUS          current
    DESCRIPTION     
            "."
    ::= { sonusDsiTransporterMIBNotificationsPrefix 9 }

sonusDsiTransporterIORemoveErrorNotification NOTIFICATION-TYPE
    OBJECTS         { sonusEventDescription, sonusEventClass, 
                      sonusEventLevel, sonusEventTime }
    STATUS          current
    DESCRIPTION     
            "."
    ::= { sonusDsiTransporterMIBNotificationsPrefix 10 }

sonusDsiTransporterCAMFileSeqErrorNotification NOTIFICATION-TYPE
    OBJECTS         { sonusEventDescription, sonusEventClass, 
                      sonusEventLevel, sonusEventTime }
    STATUS          current
    DESCRIPTION     
            "."
    ::= { sonusDsiTransporterMIBNotificationsPrefix 11 }

sonusDsiTransporterCAMFileSizeErrorNotification NOTIFICATION-TYPE
    OBJECTS         { sonusEventDescription, sonusEventClass, 
                      sonusEventLevel, sonusEventTime }
    STATUS          current
    DESCRIPTION     
            "."
    ::= { sonusDsiTransporterMIBNotificationsPrefix 12 }

sonusDsiTransporterCAMFileTimeErrorNotification NOTIFICATION-TYPE
    OBJECTS         { sonusEventDescription, sonusEventClass, 
                      sonusEventLevel, sonusEventTime }
    STATUS          current
    DESCRIPTION     
            "."
    ::= { sonusDsiTransporterMIBNotificationsPrefix 13 }

sonusDsiTransporterCAMFileDupRecordNotification NOTIFICATION-TYPE
    OBJECTS         { sonusEventDescription, sonusEventClass, 
                      sonusEventLevel, sonusEventTime }
    STATUS          current
    DESCRIPTION     
            "."
    ::= { sonusDsiTransporterMIBNotificationsPrefix 14 }

sonusDsiTransporterIOCloseErrorNotification NOTIFICATION-TYPE
    OBJECTS         { sonusEventDescription, sonusEventClass, 
                      sonusEventLevel, sonusEventTime }
    STATUS          current
    DESCRIPTION     
            "."
    ::= { sonusDsiTransporterMIBNotificationsPrefix 15 }

END -- end of module SONUS-DSI-TRANSPORTER-MIB.
