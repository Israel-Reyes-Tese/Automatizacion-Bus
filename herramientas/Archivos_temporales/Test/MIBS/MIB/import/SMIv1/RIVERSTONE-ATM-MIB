--
-- This SMIv1 module has been generated by smidump 0.2-cvs. Do not edit.
--

RIVERSTONE-ATM-MIB DEFINITIONS ::= BEGIN

IMPORTS
    AtmVcIdentifier, AtmVpIdentifier
        FROM ATM-TC-MIB
    dot1dTpFdbAddress
        FROM BRIDGE-MIB
    OBJECT-TYPE
        FROM RFC-1212
    Gauge
        FROM RFC1155-SMI
    riverstoneMibs
        FROM RIVERSTONE-SMI-MIB;

rsAtmMib OBJECT IDENTIFIER
    ::= { riverstoneMibs 16 }

-- rsAtmMib MODULE-IDENTITY
--     LAST-UPDATED    "200101310000Z"
--     ORGANIZATION    
--             "Riverstone Networks, Inc"
--     CONTACT-INFO    
--             "Riverstone Networks, Inc
--              5200 Great America Parkway
--              Santa Clara CA USA 95054
--              PHONE:+1 408.878.6500
--              EMAIL: nms-eng@riverstonenet.com
--              WEB: http://www.riverstonenet.com"
--     DESCRIPTION     
--             "This MIB module defines enterprise extensions to IETF Standard
--              MIB modules. rsAtmFdbObjects group defines a mapping 
--              from a MAC address to the ATM PVC on which it was learned.
--              
--              Copyright (C) Riverstone Networks, Inc 2001"
--     REVISION        "200101310000Z"
--     DESCRIPTION     
--             "Initial version of of Riverstone extensions to ATM Management."
--     ::= { riverstoneMibs 16 }


rsAtmFdbObjects OBJECT IDENTIFIER
    ::= { rsAtmMib 1 }

rsAtmFdbMacsLearned OBJECT-TYPE
    SYNTAX          Gauge
    ACCESS          read-only
    STATUS          mandatory
    DESCRIPTION     
            "Number of MAC addresses learned on ATM line cards system."
    ::= { rsAtmFdbObjects 1 }

rsAtmFdbTable OBJECT-TYPE
    SYNTAX          SEQUENCE OF RsAtmFdbEntry
    ACCESS          not-accessible
    STATUS          mandatory
    DESCRIPTION     
            "This table provides a mapping of a MAC address to the bridge port, 
             plus Virtual Path Identifier/Virtual Channel Identifier (VPI/VCI) 
             on which  it was learned. 
             
             A row will appear in this table for each row in dot1dTpFdbTable 
             that maps to a bridge port (dot1dBasePortNum) which is of type
             ATM ifType(37). Rows in this table share the same fate as rows
             in dot1dTpFdbTable."
    ::= { rsAtmFdbObjects 2 }

rsAtmFdbEntry OBJECT-TYPE
    SYNTAX          RsAtmFdbEntry
    ACCESS          not-accessible
    STATUS          mandatory
    DESCRIPTION     
            "An entry in the table shares the same fate as an entry 
             in dot1dTpFdbTable and uses the same indexing."
    INDEX           { dot1dTpFdbAddress }
    ::= { rsAtmFdbTable 1 }

RsAtmFdbEntry ::=
    SEQUENCE {
        rsAtmFdbVpi                     AtmVpIdentifier,
        rsAtmFdbVci                     AtmVcIdentifier
    }

rsAtmFdbVpi OBJECT-TYPE
    SYNTAX          AtmVpIdentifier
    ACCESS          read-only
    STATUS          mandatory
    DESCRIPTION     
            "The Virtual Path Identifier on which this MAC address was learned."
    ::= { rsAtmFdbEntry 1 }

rsAtmFdbVci OBJECT-TYPE
    SYNTAX          AtmVcIdentifier
    ACCESS          read-only
    STATUS          mandatory
    DESCRIPTION     
            "The Virtual Channel Identifier on which this MAC address was learned."
    ::= { rsAtmFdbEntry 2 }

rsAtmFdbConformance OBJECT IDENTIFIER
    ::= { rsAtmMib 10 }

rsAtmFdbGroups OBJECT IDENTIFIER
    ::= { rsAtmFdbConformance 1 }

rsAtmFdbCompliances OBJECT IDENTIFIER
    ::= { rsAtmFdbConformance 2 }

rsAtmFdbBaseGroup OBJECT IDENTIFIER
    ::= { rsAtmFdbGroups 1 }

-- rsAtmFdbBaseGroup OBJECT-GROUP
--     OBJECTS         { rsAtmFdbMacsLearned, rsAtmFdbVpi, rsAtmFdbVci }
--     STATUS          mandatory
--     DESCRIPTION     
--             "A collection of objects providing 
--              a mapping between a MAC address and
--              the ATM vpi/vci it was learned on."
--     ::= { rsAtmFdbGroups 1 }

rsAtmFdbMibCompliance OBJECT IDENTIFIER
    ::= { rsAtmFdbCompliances 1 }

-- rsAtmFdbMibCompliance MODULE-COMPLIANCE
--     STATUS          mandatory
--     DESCRIPTION     
--             "The compliance statement for device support of extension
--              to dot1dTpFdbTable for ATM interfaces."

--     MODULE          -- -- this module

--         MANDATORY-GROUPS    { rsAtmFdbBaseGroup }

--     ::= { rsAtmFdbCompliances 1 }

END -- end of module RIVERSTONE-ATM-MIB.
