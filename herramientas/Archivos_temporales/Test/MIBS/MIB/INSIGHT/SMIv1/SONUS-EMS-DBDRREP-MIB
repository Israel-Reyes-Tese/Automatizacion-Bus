--
-- This SMIv1 module has been generated by smidump 0.2-cvs. Do not edit.
--

SONUS-EMS-DBDRREP-MIB DEFINITIONS ::= BEGIN

IMPORTS
    OBJECT-TYPE
        FROM RFC-1212
    TRAP-TYPE
        FROM RFC-1215
    sonusEventClass, sonusEventDescription, sonusEventLevel, 
    sonusEventTime
        FROM SONUS-COMMON-MIB
    sonusEmsMIB
        FROM SONUS-EMS-MIB
    sonusHostID
        FROM SONUS-HOST-MIB;

sonusEmsDbDrRepMIB OBJECT IDENTIFIER
    ::= { sonusEmsMIB 4 }

-- sonusEmsDbDrRepMIB MODULE-IDENTITY
--     LAST-UPDATED    "200805060000Z"
--     ORGANIZATION    
--             "Sonus Networks, Inc."
--     CONTACT-INFO    
--             "   Customer Support    
--              Sonus Networks, Inc.
--              7 Technology Park Drive
--              Westford, MA 01886
--              USA
--              
--              Tel: 978-614-8100
--              Fax: 978-614-8609"
--     DESCRIPTION     
--             "The MIB Module for Sonus EMS Database Replication Management."
--     ::= { sonusEmsMIB 4 }


sonusEmsDbDrRepMIBObjects OBJECT IDENTIFIER
    ::= { sonusEmsDbDrRepMIB 1 }

sonusEmsDbDrRepMIBNotifications OBJECT IDENTIFIER
    ::= { sonusEmsDbDrRepMIB 2 }

sonusEmsDbDrRepMIBNotificationsPrefix OBJECT IDENTIFIER
    ::= { sonusEmsDbDrRepMIBNotifications 0 }

sonusEmsDbDrRepMIBNotificationsObjects OBJECT IDENTIFIER
    ::= { sonusEmsDbDrRepMIBNotifications 1 }

sonusEmsDbDrRepDRState OBJECT-TYPE
    SYNTAX          INTEGER { standalone(1), dr-source(2), dr-target(3) }
    ACCESS          read-only
    STATUS          mandatory
    DESCRIPTION     
            "Specifies the disaster recovery status of the source device."
    ::= { sonusEmsDbDrRepMIBNotificationsObjects 1 }

sonusEmsDbDrRepOutOfSyncReason OBJECT-TYPE
    SYNTAX          INTEGER { notReceivingArchiveLogs(1), 
                        noReplicationProgress(2), 
                        slowReplicationProgress(3) }
    ACCESS          read-only
    STATUS          mandatory
    DESCRIPTION     
            "Specifies why the databases are not in sync."
    ::= { sonusEmsDbDrRepMIBNotificationsObjects 2 }

sonusEmsDbDrErrorNotification TRAP-TYPE
    ENTERPRISE      sonusEmsDbDrRepMIBNotifications
    VARIABLES       { sonusEventDescription, sonusEventClass, 
                      sonusEventLevel, sonusEventTime, sonusHostID, 
                      sonusEmsDbDrRepDRState }
--     STATUS          mandatory
    DESCRIPTION     
            "Database error"
    ::= 1

sonusEmsDbDrRepOutOfSyncNotification TRAP-TYPE
    ENTERPRISE      sonusEmsDbDrRepMIBNotifications
    VARIABLES       { sonusEventDescription, sonusEventClass, 
                      sonusEventLevel, sonusEventTime, sonusHostID, 
                      sonusEmsDbDrRepDRState, 
                      sonusEmsDbDrRepOutOfSyncReason }
--     STATUS          mandatory
    DESCRIPTION     
            "Target is out of sync."
    ::= 2

sonusEmsDbDrRepConnectErrorNotification TRAP-TYPE
    ENTERPRISE      sonusEmsDbDrRepMIBNotifications
    VARIABLES       { sonusEventDescription, sonusEventClass, 
                      sonusEventLevel, sonusEventTime, sonusHostID, 
                      sonusEmsDbDrRepDRState }
--     STATUS          mandatory
    DESCRIPTION     
            "Error when attempting to connect to the DR peer."
    ::= 3

sonusEmsDbDrRepConnectFailNotification TRAP-TYPE
    ENTERPRISE      sonusEmsDbDrRepMIBNotifications
    VARIABLES       { sonusEventDescription, sonusEventClass, 
                      sonusEventLevel, sonusEventTime, sonusHostID, 
                      sonusEmsDbDrRepDRState }
--     STATUS          mandatory
    DESCRIPTION     
            "Failed to connect to the DR peer."
    ::= 4

END -- end of module SONUS-EMS-DBDRREP-MIB.
