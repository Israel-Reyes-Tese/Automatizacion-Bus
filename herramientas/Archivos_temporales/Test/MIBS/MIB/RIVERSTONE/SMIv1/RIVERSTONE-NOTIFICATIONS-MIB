--
-- This SMIv1 module has been generated by smidump 0.2-cvs. Do not edit.
--

RIVERSTONE-NOTIFICATIONS-MIB DEFINITIONS ::= BEGIN

IMPORTS
    entPhysicalDescr
        FROM ENTITY-MIB
    TRAP-TYPE
        FROM RFC-1215
    riverstoneMibs
        FROM RIVERSTONE-SMI-MIB;

rsNotificationsMib OBJECT IDENTIFIER
    ::= { riverstoneMibs 33 }

-- rsNotificationsMib MODULE-IDENTITY
--     LAST-UPDATED    "200306100000Z"
--     ORGANIZATION    
--             "Riverstone Networks, Inc"
--     CONTACT-INFO    
--             "Riverstone Networks, Inc
--              5200 Great America Parkway
--              Santa Clara CA USA 95054
--              PHONE:+1 408.878.6500
--              EMAIL: nms-eng@riverstonenet.com
--              WEB: http://www.riverstonenet.com"
--     DESCRIPTION     
--             "This module describes the set of notifications specific to the 
--              Devices from Riverstone Networks platform. This module represents
--              the total set of enterprise notifications, some are conditionally
--              mandatory depending on platform capabilities."
--     REVISION        "200306100000Z"
--     DESCRIPTION     
--             "Fixed a typo in the conformance section"
--     REVISION        "200203120000Z"
--     DESCRIPTION     
--             "Add two notifications for chassis that have switching fabrics. 
--              The first notification is switching fabric failure. The second 
--              notification is switching fabric failover. Add a
--              new notification group. Add a new module compliance."
--     REVISION        "200112070000Z"
--     DESCRIPTION     
--             "Inserted a sub-id 0 to conform to RFC 2576 Section 2.1.2(5)
--              and renamed rstone-traps-mib as rstone-notifications-mib."
--     REVISION        "200105010000Z"
--     DESCRIPTION     
--             "Created rstone-traps-mib."
--     ::= { riverstoneMibs 33 }


rsNotifications OBJECT IDENTIFIER
    ::= { rsNotificationsMib 1 }

rsNotificationControl OBJECT IDENTIFIER
    ::= { rsNotifications 1 }

rsEnvNotificationGroup OBJECT IDENTIFIER
    ::= { rsNotifications 2 }

rsEnvNotifications OBJECT IDENTIFIER
    ::= { rsEnvNotificationGroup 0 }

rsNotificationConformance OBJECT IDENTIFIER
    ::= { rsNotificationsMib 2 }

rsNotificationCompliances OBJECT IDENTIFIER
    ::= { rsNotificationConformance 1 }

rsEnvNotificationConfGroup OBJECT IDENTIFIER
    ::= { rsNotificationConformance 2 }

rsEnvirPowerSupplyFailed TRAP-TYPE
    ENTERPRISE      rsEnvNotificationGroup
    VARIABLES       { entPhysicalDescr }
--     STATUS          mandatory
    DESCRIPTION     
            "A power supply on the sending device has failed. The 
             entPhysicalDescr object identifies the failed supply."
    ::= 1

rsEnvirPowerSupplyRecovered TRAP-TYPE
    ENTERPRISE      rsEnvNotificationGroup
    VARIABLES       { entPhysicalDescr }
--     STATUS          mandatory
    DESCRIPTION     
            "A power supply on the sending device has recovered 
             after failure. The entPhysicalDescr object identifies 
             the recovered supply."
    ::= 2

rsEnvirFanFailed TRAP-TYPE
    ENTERPRISE      rsEnvNotificationGroup
    VARIABLES       { entPhysicalDescr }
--     STATUS          mandatory
    DESCRIPTION     
            "A Fan tray on the sending device has failed. The
             entPhysicalDescr object identifies the failed fan tray."
    ::= 3

rsEnvirFanRecovered TRAP-TYPE
    ENTERPRISE      rsEnvNotificationGroup
    VARIABLES       { entPhysicalDescr }
--     STATUS          mandatory
    DESCRIPTION     
            "A Fan tray on the sending device has recovered
             after failure. The entPhysicalDescr object identifies
             the recovered Fan tray."
    ::= 4

rsEnvirTempExceeded TRAP-TYPE
    ENTERPRISE      rsEnvNotificationGroup
    VARIABLES       { entPhysicalDescr }
--     STATUS          mandatory
    DESCRIPTION     
            "A temperature inside the chassis on the sending device has exceeded
             normal operating temperature. The entPhysicalDescr object
             identifies the chassis."
    ::= 5

rsEnvirTempNormal TRAP-TYPE
    ENTERPRISE      rsEnvNotificationGroup
    VARIABLES       { entPhysicalDescr }
--     STATUS          mandatory
    DESCRIPTION     
            "A temperature inside the chassis on the sending device has returned
             to normal operating temperature. The entPhysicalDescr
             object identifies the chassis."
    ::= 6

rsEnvirHotSwapIn TRAP-TYPE
    ENTERPRISE      rsEnvNotificationGroup
    VARIABLES       { entPhysicalDescr }
--     STATUS          mandatory
    DESCRIPTION     
            "A module has been inserted into the chassis. The object
             entPhysicalDescr identifies the module. The module can be a card
             for the main bay or a switching fabric in the switching fabric
             bay."
    ::= 7

rsEnvirHotSwapOut TRAP-TYPE
    ENTERPRISE      rsEnvNotificationGroup
    VARIABLES       { entPhysicalDescr }
--     STATUS          mandatory
    DESCRIPTION     
            "A module has been turned off or removed from the chassis. The
             object entPhysicalDescr identifies the module. The module can be 
             a card for the main bay or a switching fabric in the switching 
             fabric."
    ::= 8

rsEnvirBackupControlModuleOnline TRAP-TYPE
    ENTERPRISE      rsEnvNotificationGroup
    VARIABLES       { entPhysicalDescr }
--     STATUS          mandatory
    DESCRIPTION     
            "A backup control module that was in standby mode has taken over 
             for a failed primary control module. The objec entPhysicalDescr 
             identifies the now active control module."
    ::= 9

rsEnvirSwitchingFabricFailure TRAP-TYPE
    ENTERPRISE      rsEnvNotificationGroup
    VARIABLES       { entPhysicalDescr }
--     STATUS          mandatory
    DESCRIPTION     
            "The primary switching fabric that was in standby mode has failed.
             The object entPhysicalDescr identifies the failed switching 
             fabric. If there is a backup switching fabric and if it comes up
             ok, rsEnvirSwitchingFabricFailover would be sent after this one."
    ::= 10

rsEnvirSwitchingFabricFailover TRAP-TYPE
    ENTERPRISE      rsEnvNotificationGroup
    VARIABLES       { entPhysicalDescr }
--     STATUS          mandatory
    DESCRIPTION     
            "A backup switching fabric that was in standby mode has taken over 
             for a failed primary switching fabric. The object entPhysicalDescr 
             identifies the now active switching fabric. This would be sent 
             after sending rsEnvirSwitchingFabricFailure."
    ::= 11

rsNotificationConfGroupV10 OBJECT IDENTIFIER
    ::= { rsEnvNotificationConfGroup 1 }

-- rsNotificationConfGroupV10 NOTIFICATION-GROUP
--     NOTIFICATIONS   { rsEnvirPowerSupplyFailed, 
--                       rsEnvirPowerSupplyRecovered, rsEnvirFanFailed, 
--                       rsEnvirFanRecovered, rsEnvirTempExceeded, 
--                       rsEnvirTempNormal, rsEnvirHotSwapIn, 
--                       rsEnvirHotSwapOut, 
--                       rsEnvirBackupControlModuleOnline }
--     STATUS          mandatory
--     DESCRIPTION     
--             "A base set of notifications for chassis based devices."
--     ::= { rsEnvNotificationConfGroup 1 }

rsNotificationSwitchingFabric OBJECT IDENTIFIER
    ::= { rsEnvNotificationConfGroup 2 }

-- rsNotificationSwitchingFabric NOTIFICATION-GROUP
--     NOTIFICATIONS   { rsEnvirSwitchingFabricFailure, 
--                       rsEnvirSwitchingFabricFailover }
--     STATUS          mandatory
--     DESCRIPTION     
--             "A set of switching fabric notifications."
--     ::= { rsEnvNotificationConfGroup 2 }

rsNotificationComplianceV10 OBJECT IDENTIFIER
    ::= { rsNotificationCompliances 1 }

-- rsNotificationComplianceV10 MODULE-COMPLIANCE
--     STATUS          obsolete
--     DESCRIPTION     
--             "The compliance statement for the RIVERSTONE-NOTIFICATIONS-MIB."

--     MODULE          -- -- this module

--         MANDATORY-GROUPS    { rsNotificationConfGroupV10 }

--     ::= { rsNotificationCompliances 1 }

rsNotificationComplianceV11 OBJECT IDENTIFIER
    ::= { rsNotificationCompliances 2 }

-- rsNotificationComplianceV11 MODULE-COMPLIANCE
--     STATUS          mandatory
--     DESCRIPTION     
--             "Add compliance that includes the two new notifications."

--     MODULE          -- -- this module

--         MANDATORY-GROUPS    { rsNotificationConfGroupV10 }

--         GROUP       rsNotificationSwitchingFabric
--         DESCRIPTION 
--             "This group is mandatory for all devices that have redundant 
--              switching fabrics."

--     ::= { rsNotificationCompliances 2 }

END -- end of module RIVERSTONE-NOTIFICATIONS-MIB.
