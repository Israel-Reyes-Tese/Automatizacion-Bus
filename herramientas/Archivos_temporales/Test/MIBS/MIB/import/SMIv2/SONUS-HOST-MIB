--
-- This SMIv2 module has been generated by smidump 0.2-cvs. Do not edit.
--

SONUS-HOST-MIB DEFINITIONS ::= BEGIN

IMPORTS
    Counter64, Integer32, MODULE-IDENTITY, NOTIFICATION-TYPE, 
    OBJECT-TYPE, Unsigned32
        FROM SNMPv2-SMI
    DisplayString
        FROM SNMPv2-TC
    sonusEventClass, sonusEventDescription, sonusEventLevel, 
    sonusEventTime
        FROM SONUS-COMMON-MIB
    sonusSystemMIBs
        FROM SONUS-SMI;

sonusHostMIB MODULE-IDENTITY
    LAST-UPDATED    "200811210000Z"
    ORGANIZATION    
            "Sonus Networks, Inc."
    CONTACT-INFO    
            "   Customer Support    
             Sonus Networks, Inc.
             250 Apollo Drive
             Chelmsford, MA 01824
             USA
             
             Tel: 978-614-8100
             Fax: 978-614-8609"
    DESCRIPTION     
            "The MIB Module for application host monitoring related objects."
    ::= { sonusSystemMIBs 12 }


sonusHostMIBObjects OBJECT IDENTIFIER
    ::= { sonusHostMIB 1 }

sonusHostNotifications OBJECT IDENTIFIER
    ::= { sonusHostMIB 2 }

sonusHostNotificationsPrefix OBJECT IDENTIFIER
    ::= { sonusHostNotifications 0 }

sonusHostResourceObjects OBJECT IDENTIFIER
    ::= { sonusHostMIB 3 }

sonusHostCpuID OBJECT-TYPE
    SYNTAX          DisplayString
    MAX-ACCESS      read-only
    STATUS          current
    DESCRIPTION     
            "CPU identifier."
    ::= { sonusHostResourceObjects 1 }

sonusHostExecName OBJECT-TYPE
    SYNTAX          DisplayString
    MAX-ACCESS      read-only
    STATUS          current
    DESCRIPTION     
            "Executable name."
    ::= { sonusHostResourceObjects 2 }

sonusHostFileSystemPath OBJECT-TYPE
    SYNTAX          DisplayString
    MAX-ACCESS      read-only
    STATUS          current
    DESCRIPTION     
            "File system path name."
    ::= { sonusHostResourceObjects 3 }

sonusHostProcessID OBJECT-TYPE
    SYNTAX          Unsigned32
    MAX-ACCESS      read-only
    STATUS          current
    DESCRIPTION     
            "Process ID."
    ::= { sonusHostResourceObjects 4 }

sonusHostManagementObjects OBJECT IDENTIFIER
    ::= { sonusHostMIB 4 }

sonusHostClrSet OBJECT-TYPE
    SYNTAX          INTEGER { clear(0), set(1) }
    MAX-ACCESS      read-only
    STATUS          current
    DESCRIPTION     
            "Alarm clear and set flag for an event."
    ::= { sonusHostManagementObjects 1 }

sonusHostExpectedInstanceCount OBJECT-TYPE
    SYNTAX          Unsigned32
    MAX-ACCESS      read-only
    STATUS          current
    DESCRIPTION     
            "Expected number of application instances."
    ::= { sonusHostManagementObjects 2 }

sonusHostSampleInstanceCount OBJECT-TYPE
    SYNTAX          Unsigned32
    MAX-ACCESS      read-only
    STATUS          current
    DESCRIPTION     
            "Actual number of application instance from 
             sampling poll."
    ::= { sonusHostManagementObjects 3 }

sonusHostThresholdTriggerValue OBJECT-TYPE
    SYNTAX          Counter64
    MAX-ACCESS      read-only
    STATUS          current
    DESCRIPTION     
            "Threshold trigger value."
    ::= { sonusHostManagementObjects 4 }

sonusHostThresholdSampleValue OBJECT-TYPE
    SYNTAX          Counter64
    MAX-ACCESS      read-only
    STATUS          current
    DESCRIPTION     
            "Actual sampling value that trigger a threshold-crossing event."
    ::= { sonusHostManagementObjects 5 }

sonusHostThresholdName OBJECT-TYPE
    SYNTAX          DisplayString
    MAX-ACCESS      read-only
    STATUS          current
    DESCRIPTION     
            "Threshold name configured for a threshold-crossing notification."
    ::= { sonusHostManagementObjects 6 }

sonusHostID OBJECT-TYPE
    SYNTAX          OCTET STRING (SIZE(1..32))
    MAX-ACCESS      read-only
    STATUS          current
    DESCRIPTION     
            "The unique id or serial number for this host. The serial number is an ASCII representation of the hardware-specific serial number of the physical machine. It may contain non-numeric characters."
    ::= { sonusHostManagementObjects 7 }

sonusHostDiskDevName OBJECT-TYPE
    SYNTAX          OCTET STRING (SIZE(1..32))
    MAX-ACCESS      read-only
    STATUS          current
    DESCRIPTION     
            "Disk device name in descriptive format. Example: cXtYdZ"
    ::= { sonusHostManagementObjects 8 }

sonusHostDiskErrorCount OBJECT-TYPE
    SYNTAX          Unsigned32
    MAX-ACCESS      read-only
    STATUS          current
    DESCRIPTION     
            "Error count representing the difference between last and present polled value."
    ::= { sonusHostManagementObjects 9 }

sonusHostResourceUsageStats OBJECT IDENTIFIER
    ::= { sonusHostMIB 5 }

sonusHostCpuAvgUsage OBJECT-TYPE
    SYNTAX          Integer32
    MAX-ACCESS      read-only
    STATUS          current
    DESCRIPTION     
            "CPU usage as percentage.  Total CPU time is the sum of 4 values: user time, kernel time, IO-wait time, and idle time.  Each time value is calculated by taking the difference between present and the previous samples.  The sampling period is 5 seconds.  Usage is calculated using this formula: (user time+kernel time)/(user time+kernel time+IO-wait time+idle time)*100.  The value is round up to an integer. The calculation is performed for each CPU, and the usage value is the average."
    ::= { sonusHostResourceUsageStats 1 }

sonusHostMemUsage OBJECT-TYPE
    SYNTAX          Integer32
    MAX-ACCESS      read-only
    STATUS          current
    DESCRIPTION     
            "Host physical memory usage as percentage.  Usage value is calculated by dividing total in-use memory by total physical memory in the system.  Usage value is represented in percentage and round up to an integer.  Sampling period is 5 seconds.  "
    ::= { sonusHostResourceUsageStats 2 }

sonusHostSwapSpaceUsage OBJECT-TYPE
    SYNTAX          Integer32
    MAX-ACCESS      read-only
    STATUS          current
    DESCRIPTION     
            "Host swap space usage as percentage.  Usage value is calculated by dividing total in-use swap space by total available swap space.  Usage value is represented in percentage and it is round up to an integer.  Sampling period is 5 seconds. "
    ::= { sonusHostResourceUsageStats 3 }

sonusHostFsUsageTable OBJECT-TYPE
    SYNTAX          SEQUENCE OF SonusFileSystemUsageEntry
    MAX-ACCESS      not-accessible
    STATUS          current
    DESCRIPTION     
            "Host File System Usage Table."
    ::= { sonusHostResourceUsageStats 4 }

sonusFileSystemUsageEntry OBJECT-TYPE
    SYNTAX          SonusFileSystemUsageEntry
    MAX-ACCESS      not-accessible
    STATUS          current
    DESCRIPTION     
            "File System Usage table entry."
    INDEX           { sonusHostFileSystemPathName }
    ::= { sonusHostFsUsageTable 1 }

SonusFileSystemUsageEntry ::=
    SEQUENCE {
        sonusHostFileSystemPathName     DisplayString,
        sonusHostFileSystemUsage        Integer32
    }

sonusHostFileSystemPathName OBJECT-TYPE
    SYNTAX          DisplayString
    MAX-ACCESS      read-only
    STATUS          current
    DESCRIPTION     
            "File System Path Name."
    ::= { sonusFileSystemUsageEntry 1 }

sonusHostFileSystemUsage OBJECT-TYPE
    SYNTAX          Integer32
    MAX-ACCESS      read-only
    STATUS          current
    DESCRIPTION     
            "File System Usage as percentage.  Usage value is calculated by dividing disk space in use by total available space in a file system.  Usage value is represented in percentage and round up to an integer.  Sampling period is 60 seconds."
    ::= { sonusFileSystemUsageEntry 2 }

sonusHostApplResUsageTable OBJECT-TYPE
    SYNTAX          SEQUENCE OF SonusApplResUsageEntry
    MAX-ACCESS      not-accessible
    STATUS          current
    DESCRIPTION     
            "Host application resource usage Table."
    ::= { sonusHostResourceUsageStats 5 }

sonusApplResUsageEntry OBJECT-TYPE
    SYNTAX          SonusApplResUsageEntry
    MAX-ACCESS      not-accessible
    STATUS          current
    DESCRIPTION     
            "File System Usage table entry."
    INDEX           { sonusHostApplPID }
    ::= { sonusHostApplResUsageTable 1 }

SonusApplResUsageEntry ::=
    SEQUENCE {
        sonusHostApplPID                Unsigned32,
        sonusHostApplExecName           DisplayString,
        sonusHostApplCpuUsage           Integer32,
        sonusHostApplMemSize            Unsigned32,
        sonusHostApplVMSize             Unsigned32
    }

sonusHostApplPID OBJECT-TYPE
    SYNTAX          Unsigned32
    MAX-ACCESS      read-only
    STATUS          current
    DESCRIPTION     
            "Application process ID (PID)."
    ::= { sonusApplResUsageEntry 1 }

sonusHostApplExecName OBJECT-TYPE
    SYNTAX          DisplayString
    MAX-ACCESS      read-only
    STATUS          current
    DESCRIPTION     
            "Application executable name."
    ::= { sonusApplResUsageEntry 2 }

sonusHostApplCpuUsage OBJECT-TYPE
    SYNTAX          Integer32
    MAX-ACCESS      read-only
    STATUS          current
    DESCRIPTION     
            "Application CPU usage as percentage.  Usage value is round up to an integer.  CPU usage is collected from the process table in operating system kernel. Sampling period is 30 seconds. "
    ::= { sonusApplResUsageEntry 3 }

sonusHostApplMemSize OBJECT-TYPE
    SYNTAX          Unsigned32
    MAX-ACCESS      read-only
    STATUS          current
    DESCRIPTION     
            "Application physical memory size in kbytes.  Usage value is collected from process table in operating system kernel.  Sampling period is 30 seconds."
    ::= { sonusApplResUsageEntry 4 }

sonusHostApplVMSize OBJECT-TYPE
    SYNTAX          Unsigned32
    MAX-ACCESS      read-only
    STATUS          current
    DESCRIPTION     
            "Application virtual memory usage size in kbytes.  Usage value is collected from process table in operating system kernel.  Sampling period is 30 seconds."
    ::= { sonusApplResUsageEntry 5 }

sonusHostCpuUsageRisingThresholdNotification NOTIFICATION-TYPE
    OBJECTS         { sonusHostCpuID, sonusHostThresholdTriggerValue, 
                      sonusHostThresholdSampleValue, sonusEventTime, 
                      sonusEventDescription, sonusEventClass, 
                      sonusEventLevel, sonusHostClrSet, 
                      sonusHostThresholdName, sonusHostID }
    STATUS          current
    DESCRIPTION     
            "Reports a CPU usage exceeds a predefind 
             threshold value."
    ::= { sonusHostNotificationsPrefix 1 }

sonusHostCpuUsageFallingThresholdNotification NOTIFICATION-TYPE
    OBJECTS         { sonusHostCpuID, sonusHostThresholdTriggerValue, 
                      sonusHostThresholdSampleValue, sonusEventTime, 
                      sonusEventDescription, sonusEventClass, 
                      sonusEventLevel, sonusHostClrSet, 
                      sonusHostThresholdName, sonusHostID }
    STATUS          current
    DESCRIPTION     
            "Reports a CPU usage falls below a predefind 
             threshold value."
    ::= { sonusHostNotificationsPrefix 2 }

sonusHostCpuAvgUsageRisingThresholdNotification NOTIFICATION-TYPE
    OBJECTS         { sonusHostThresholdTriggerValue, 
                      sonusHostThresholdSampleValue, sonusEventTime, 
                      sonusEventDescription, sonusEventClass, 
                      sonusEventLevel, sonusHostClrSet, 
                      sonusHostThresholdName, sonusHostID }
    STATUS          current
    DESCRIPTION     
            "Report average CPU usage exceeds a threshold 
             value."
    ::= { sonusHostNotificationsPrefix 3 }

sonusHostCpuAvgUsageFallingThresholdNotification NOTIFICATION-TYPE
    OBJECTS         { sonusHostThresholdTriggerValue, 
                      sonusHostThresholdSampleValue, sonusEventTime, 
                      sonusEventDescription, sonusEventClass, 
                      sonusEventLevel, sonusHostClrSet, 
                      sonusHostThresholdName, sonusHostID }
    STATUS          current
    DESCRIPTION     
            "Report average CPU usage falls below a threshold 
             value."
    ::= { sonusHostNotificationsPrefix 4 }

sonusHostFsUsageRisingThresholdNotification NOTIFICATION-TYPE
    OBJECTS         { sonusHostFileSystemPath, 
                      sonusHostThresholdTriggerValue, 
                      sonusHostThresholdSampleValue, sonusEventTime, 
                      sonusEventDescription, sonusEventClass, 
                      sonusEventLevel, sonusHostClrSet, 
                      sonusHostThresholdName, sonusHostID }
    STATUS          current
    DESCRIPTION     
            "Reports usage of a file system exceeds a predefined
             threshold value."
    ::= { sonusHostNotificationsPrefix 5 }

sonusHostFsUsageFallingThresholdNotification NOTIFICATION-TYPE
    OBJECTS         { sonusHostFileSystemPath, 
                      sonusHostThresholdTriggerValue, 
                      sonusHostThresholdSampleValue, sonusEventTime, 
                      sonusEventDescription, sonusEventClass, 
                      sonusEventLevel, sonusHostClrSet, 
                      sonusHostThresholdName, sonusHostID }
    STATUS          current
    DESCRIPTION     
            "Reports usage of a file system falls below 
             a predefined threshold value."
    ::= { sonusHostNotificationsPrefix 6 }

sonusHostMemUsageRisingThrshldNotification NOTIFICATION-TYPE
    OBJECTS         { sonusHostThresholdTriggerValue, 
                      sonusHostThresholdSampleValue, sonusEventTime, 
                      sonusEventDescription, sonusEventClass, 
                      sonusEventLevel, sonusHostClrSet, 
                      sonusHostThresholdName, sonusHostID }
    STATUS          current
    DESCRIPTION     
            "Reports memory usage of the host exceeds a 
             given threshold value."
    ::= { sonusHostNotificationsPrefix 7 }

sonusHostMemUsageFallingThrshldNotification NOTIFICATION-TYPE
    OBJECTS         { sonusHostThresholdTriggerValue, 
                      sonusHostThresholdSampleValue, sonusEventTime, 
                      sonusEventDescription, sonusEventClass, 
                      sonusEventLevel, sonusHostClrSet, 
                      sonusHostThresholdName, sonusHostID }
    STATUS          current
    DESCRIPTION     
            "Reports memory usage of the host falls below a
             given threshold value."
    ::= { sonusHostNotificationsPrefix 8 }

sonusHostSwapUsageRisingThresholdNotification NOTIFICATION-TYPE
    OBJECTS         { sonusHostThresholdTriggerValue, 
                      sonusHostThresholdSampleValue, sonusEventTime, 
                      sonusEventDescription, sonusEventClass, 
                      sonusEventLevel, sonusHostClrSet, 
                      sonusHostThresholdName, sonusHostID }
    STATUS          current
    DESCRIPTION     
            "Reports the swap space usage exceeds a given 
             threshold."
    ::= { sonusHostNotificationsPrefix 9 }

sonusHostSwapUsageFallingThresholdNotification NOTIFICATION-TYPE
    OBJECTS         { sonusHostThresholdTriggerValue, 
                      sonusHostThresholdSampleValue, sonusEventTime, 
                      sonusEventDescription, sonusEventClass, 
                      sonusEventLevel, sonusHostClrSet, 
                      sonusHostThresholdName, sonusHostID }
    STATUS          current
    DESCRIPTION     
            "Reports the swap space usage exceeds a given 
             threshold."
    ::= { sonusHostNotificationsPrefix 10 }

sonusHostApplicationRuntimeErrorNotification NOTIFICATION-TYPE
    OBJECTS         { sonusHostExecName, sonusHostExpectedInstanceCount, 
                      sonusHostSampleInstanceCount, sonusEventTime, 
                      sonusEventDescription, sonusEventClass, 
                      sonusEventLevel, sonusHostID }
    STATUS          current
    DESCRIPTION     
            "Reports runtime errors occur by detecting
             the number of application running instances 
             does not match the expected number."
    ::= { sonusHostNotificationsPrefix 11 }

sonusHostApplicationRuntimeErrorRecoverNotification NOTIFICATION-TYPE
    OBJECTS         { sonusHostExecName, sonusHostExpectedInstanceCount, 
                      sonusHostSampleInstanceCount, sonusEventTime, 
                      sonusEventDescription, sonusEventClass, 
                      sonusEventLevel, sonusHostID }
    STATUS          current
    DESCRIPTION     
            "Informs the runtime errors report previously 
             is recovered."
    ::= { sonusHostNotificationsPrefix 12 }

sonusHostApplicationExitNotification NOTIFICATION-TYPE
    OBJECTS         { sonusHostExecName, sonusHostProcessID, 
                      sonusEventTime, sonusEventDescription, 
                      sonusEventClass, sonusEventLevel, sonusHostID }
    STATUS          current
    DESCRIPTION     
            "Reports a previously running application 
             exits."
    ::= { sonusHostNotificationsPrefix 13 }

sonusHostApplicationStartupNotification NOTIFICATION-TYPE
    OBJECTS         { sonusHostExecName, sonusHostProcessID, 
                      sonusEventTime, sonusEventDescription, 
                      sonusEventClass, sonusEventLevel, sonusHostID }
    STATUS          current
    DESCRIPTION     
            "Informs an application just starts up."
    ::= { sonusHostNotificationsPrefix 14 }

sonusHostApplCpuUsageRisingThresholdNotification NOTIFICATION-TYPE
    OBJECTS         { sonusHostExecName, sonusHostThresholdTriggerValue, 
                      sonusHostThresholdSampleValue, sonusHostProcessID, 
                      sonusEventTime, sonusEventDescription, 
                      sonusEventClass, sonusEventLevel, sonusHostClrSet, 
                      sonusHostThresholdName, sonusHostID }
    STATUS          current
    DESCRIPTION     
            "Reports an application's instance usage exceeds 
             a given threhold value."
    ::= { sonusHostNotificationsPrefix 15 }

sonusHostApplCpuUsageFallingThresholdNotification NOTIFICATION-TYPE
    OBJECTS         { sonusHostExecName, sonusHostThresholdTriggerValue, 
                      sonusHostThresholdSampleValue, sonusHostProcessID, 
                      sonusEventTime, sonusEventDescription, 
                      sonusEventClass, sonusEventLevel, sonusHostClrSet, 
                      sonusHostThresholdName, sonusHostID }
    STATUS          current
    DESCRIPTION     
            "Reports an application's instance usage falling 
             a given threhold value."
    ::= { sonusHostNotificationsPrefix 16 }

sonusHostApplMemUsageRisingThresholdNotification NOTIFICATION-TYPE
    OBJECTS         { sonusHostExecName, sonusHostThresholdTriggerValue, 
                      sonusHostThresholdSampleValue, sonusHostProcessID, 
                      sonusEventTime, sonusEventDescription, 
                      sonusEventClass, sonusEventLevel, sonusHostClrSet, 
                      sonusHostThresholdName, sonusHostID }
    STATUS          current
    DESCRIPTION     
            "Reports an application instance's memory usage
             exceeds a given threshold value."
    ::= { sonusHostNotificationsPrefix 17 }

sonusHostApplMemUsageFallingThresholdNotification NOTIFICATION-TYPE
    OBJECTS         { sonusHostExecName, sonusHostThresholdTriggerValue, 
                      sonusHostThresholdSampleValue, sonusHostProcessID, 
                      sonusEventTime, sonusEventDescription, 
                      sonusEventClass, sonusEventLevel, sonusHostClrSet, 
                      sonusHostThresholdName, sonusHostID }
    STATUS          current
    DESCRIPTION     
            "Reports an application instance's memory usage
             falls below a given threshold value."
    ::= { sonusHostNotificationsPrefix 18 }

sonusHostDiskMonSoftErrorNotification NOTIFICATION-TYPE
    OBJECTS         { sonusEventTime, sonusEventDescription, 
                      sonusEventClass, sonusEventLevel, sonusHostID, 
                      sonusHostDiskDevName, sonusHostDiskErrorCount }
    STATUS          current
    DESCRIPTION     
            "Reports that the soft error count for the disk 
             identified by sonusHostDiskDevName has increased by 
             the value of sonusHostDiskErrorCount since the  
             last poll."
    ::= { sonusHostNotificationsPrefix 19 }

sonusHostDiskMonHardErrorNotification NOTIFICATION-TYPE
    OBJECTS         { sonusEventTime, sonusEventDescription, 
                      sonusEventClass, sonusEventLevel, sonusHostID, 
                      sonusHostDiskDevName, sonusHostDiskErrorCount }
    STATUS          current
    DESCRIPTION     
            "Reports that the soft error count for the disk 
             identified by sonusHostDiskDevName has increased by 
             the value of sonusHostDiskErrorCount since the  
             last poll."
    ::= { sonusHostNotificationsPrefix 20 }

sonusHostDiskMonTransportErrorNotification NOTIFICATION-TYPE
    OBJECTS         { sonusEventTime, sonusEventDescription, 
                      sonusEventClass, sonusEventLevel, sonusHostID, 
                      sonusHostDiskDevName, sonusHostDiskErrorCount }
    STATUS          current
    DESCRIPTION     
            "Reports that the transport error count for the disk 
             identified by sonusHostDiskDevName has increased by 
             the value of sonusHostDiskErrorCount since the  
             last poll."
    ::= { sonusHostNotificationsPrefix 21 }

sonusHostDiskMonSMARTErrorNotification NOTIFICATION-TYPE
    OBJECTS         { sonusEventTime, sonusEventDescription, 
                      sonusEventClass, sonusEventLevel, sonusHostID }
    STATUS          current
    DESCRIPTION     
            "SMARTmon error was reported.  Detailed error is specified in sonusEventDescription."
    ::= { sonusHostNotificationsPrefix 22 }

sonusHostDiskMonSMARTWarnNotification NOTIFICATION-TYPE
    OBJECTS         { sonusEventTime, sonusEventDescription, 
                      sonusEventClass, sonusEventLevel, sonusHostID }
    STATUS          current
    DESCRIPTION     
            "SMARTmon warning was reported.  Detailed message is specified in sonusEventDescription."
    ::= { sonusHostNotificationsPrefix 23 }

END -- end of module SONUS-HOST-MIB.
