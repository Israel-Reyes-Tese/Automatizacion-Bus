MIB-EMS-IPASOLINK-IX-COMMON1000-MIB DEFINITIONS ::= BEGIN
    
    IMPORTS
        OBJECT-TYPE
            FROM RFC-1212
        IpAddress, Opaque
            FROM RFC1155-SMI
        enterprises
            FROM SNMPv2-SMI;
    
    -- 1.3.6.1.4.1.119
    nec OBJECT IDENTIFIER
        ::= { enterprises 119 }
    
    -- 1.3.6.1.4.1.119.2
    nec-mib OBJECT IDENTIFIER
        ::= { nec 2 }
    
    -- 1.3.6.1.4.1.119.2.3
    necProductDepend OBJECT IDENTIFIER
        ::= { nec-mib 3 }
    
    -- 1.3.6.1.4.1.119.2.3.69
    radioEquipment OBJECT IDENTIFIER
        ::= { necProductDepend 69 }
    
    -- 1.3.6.1.4.1.119.2.3.69.203
    commonPnms OBJECT IDENTIFIER
        ::= { radioEquipment 203 }
    
    -- 1.3.6.1.4.1.119.2.3.69.203.507
    ipasolinkIx OBJECT IDENTIFIER
        ::= { commonPnms 507 }
    
    -- 1.3.6.1.4.1.119.2.3.69.203.507.5
    system5 OBJECT IDENTIFIER
        ::= { ipasolinkIx 5 }
    
    -- 1.3.6.1.4.1.119.2.3.69.203.507.501
    pasoNeoIpe-common OBJECT IDENTIFIER
        ::= { ipasolinkIx 501 }
    
    -- 1.3.6.1.4.1.119.2.3.69.203.507.501.3
    alarmStatusGroup OBJECT IDENTIFIER
        ::= { pasoNeoIpe-common 3 }
    
    -- 1.3.6.1.4.1.119.2.3.69.203.507.501.3.35
    asMainCtrlGroup OBJECT IDENTIFIER
        ::= { alarmStatusGroup 35 }
    
    -- 1.3.6.1.4.1.119.2.3.69.203.507.501.3.35.1
    asMainCtrlGroupTable OBJECT-TYPE
        SYNTAX      SEQUENCE OF AsMainCtrlGroupEntry
        ACCESS      not-accessible
        STATUS      mandatory
        DESCRIPTION
            "Main card group object for iPASO1000."
        ::= { asMainCtrlGroup 1 }
    
    -- 1.3.6.1.4.1.119.2.3.69.203.507.501.3.35.1.1
    asMainCtrlGroupEntry OBJECT-TYPE
        SYNTAX      AsMainCtrlGroupEntry
        ACCESS      not-accessible
        STATUS      mandatory
        DESCRIPTION
            ""
        INDEX       { asMainCtrlGroupNEAddress, asMainCtrlGroupIndex }
        ::= { asMainCtrlGroupTable 1 }
    
    AsMainCtrlGroupEntry ::= SEQUENCE {
        asMainCtrlGroupIndex        INTEGER,
        asMainCtrlGroupNEAddress    IpAddress,
        ctrlGroupStartupStatus      INTEGER
    }
    
    -- 1.3.6.1.4.1.119.2.3.69.203.507.501.3.35.1.1.1
    asMainCtrlGroupIndex OBJECT-TYPE
        SYNTAX      INTEGER (1)
        ACCESS      not-accessible
        STATUS      mandatory
        DESCRIPTION
            ""
        ::= { asMainCtrlGroupEntry 1 }
    
    -- 1.3.6.1.4.1.119.2.3.69.203.507.501.3.35.1.1.2
    asMainCtrlGroupNEAddress OBJECT-TYPE
        SYNTAX      IpAddress
        ACCESS      not-accessible
        STATUS      mandatory
        DESCRIPTION
            ""
        ::= { asMainCtrlGroupEntry 2 }
    
    -- 1.3.6.1.4.1.119.2.3.69.203.507.501.3.35.1.1.23
    ctrlGroupStartupStatus OBJECT-TYPE
        SYNTAX      INTEGER { powerOn(1), cpuReset(2), deviceReset(3) }
        ACCESS      read-only
        STATUS      mandatory
        DESCRIPTION
            "Main Card Startup Status."
        ::= { asMainCtrlGroupEntry 23 }
    
    -- 1.3.6.1.4.1.119.2.3.69.203.507.507
    pasoNeoIpe-ix OBJECT IDENTIFIER
        ::= { ipasolinkIx 507 }
    
END -- end of module MIB-EMS-IPASOLINK-IX-COMMON1000-MIB.
