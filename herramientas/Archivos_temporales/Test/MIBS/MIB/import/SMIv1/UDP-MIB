--
-- This SMIv1 module has been generated by smidump 0.2-cvs. Do not edit.
--

UDP-MIB DEFINITIONS ::= BEGIN

IMPORTS
    OBJECT-TYPE
        FROM RFC-1212
    Counter, IpAddress
        FROM RFC1155-SMI
    mib-2
        FROM RFC1213-MIB;

udpMIB OBJECT IDENTIFIER
    ::= { mib-2 50 }

-- udpMIB MODULE-IDENTITY
--     LAST-UPDATED    "199411010000Z"
--     ORGANIZATION    
--             "IETF SNMPv2 Working Group"
--     CONTACT-INFO    
--             "        Keith McCloghrie
--              
--              Postal: Cisco Systems, Inc.
--                      170 West Tasman Drive
--                      San Jose, CA  95134-1706
--                      US
--              
--              Phone:  +1 408 526 5260
--              Email:  kzm@cisco.com"
--     DESCRIPTION     
--             "The MIB module for managing UDP implementations."
--     REVISION        "199103310000Z"
--     DESCRIPTION     
--             "The initial revision of this MIB module was part of MIB-
--              II."
--     ::= { mib-2 50 }


udp OBJECT IDENTIFIER
    ::= { mib-2 7 }

udpInDatagrams OBJECT-TYPE
    SYNTAX          Counter
    ACCESS          read-only
    STATUS          mandatory
    DESCRIPTION     
            "The total number of UDP datagrams delivered to UDP users."
    ::= { udp 1 }

udpNoPorts OBJECT-TYPE
    SYNTAX          Counter
    ACCESS          read-only
    STATUS          mandatory
    DESCRIPTION     
            "The total number of received UDP datagrams for which there
             was no application at the destination port."
    ::= { udp 2 }

udpInErrors OBJECT-TYPE
    SYNTAX          Counter
    ACCESS          read-only
    STATUS          mandatory
    DESCRIPTION     
            "The number of received UDP datagrams that could not be
             delivered for reasons other than the lack of an application
             at the destination port."
    ::= { udp 3 }

udpOutDatagrams OBJECT-TYPE
    SYNTAX          Counter
    ACCESS          read-only
    STATUS          mandatory
    DESCRIPTION     
            "The total number of UDP datagrams sent from this entity."
    ::= { udp 4 }

udpTable OBJECT-TYPE
    SYNTAX          SEQUENCE OF UdpEntry
    ACCESS          not-accessible
    STATUS          mandatory
    DESCRIPTION     
            "A table containing UDP listener information."
    ::= { udp 5 }

udpEntry OBJECT-TYPE
    SYNTAX          UdpEntry
    ACCESS          not-accessible
    STATUS          mandatory
    DESCRIPTION     
            "Information about a particular current UDP listener."
    INDEX           { udpLocalAddress, udpLocalPort }
    ::= { udpTable 1 }

UdpEntry ::=
    SEQUENCE {
        udpLocalAddress                 IpAddress,
        udpLocalPort                    INTEGER
    }

udpLocalAddress OBJECT-TYPE
    SYNTAX          IpAddress
    ACCESS          read-only
    STATUS          mandatory
    DESCRIPTION     
            "The local IP address for this UDP listener.  In the case of
             a UDP listener which is willing to accept datagrams for any
             IP interface associated with the node, the value 0.0.0.0 is
             used."
    ::= { udpEntry 1 }

udpLocalPort OBJECT-TYPE
    SYNTAX          INTEGER (0..65535)
    ACCESS          read-only
    STATUS          mandatory
    DESCRIPTION     
            "The local port number for this UDP listener."
    ::= { udpEntry 2 }

udpMIBConformance OBJECT IDENTIFIER
    ::= { udpMIB 2 }

udpMIBCompliances OBJECT IDENTIFIER
    ::= { udpMIBConformance 1 }

udpMIBGroups OBJECT IDENTIFIER
    ::= { udpMIBConformance 2 }

udpGroup OBJECT IDENTIFIER
    ::= { udpMIBGroups 1 }

-- udpGroup OBJECT-GROUP
--     OBJECTS         { udpInDatagrams, udpNoPorts, udpInErrors, 
--                       udpOutDatagrams, udpLocalAddress, udpLocalPort }
--     STATUS          mandatory
--     DESCRIPTION     
--             "The udp group of objects providing for management of UDP
--              entities."
--     ::= { udpMIBGroups 1 }

udpMIBCompliance OBJECT IDENTIFIER
    ::= { udpMIBCompliances 1 }

-- udpMIBCompliance MODULE-COMPLIANCE
--     STATUS          mandatory
--     DESCRIPTION     
--             "The compliance statement for SNMPv2 entities which
--              implement UDP."

--     MODULE          -- -- this module

--         MANDATORY-GROUPS    { udpGroup }

--     ::= { udpMIBCompliances 1 }

END -- end of module UDP-MIB.
