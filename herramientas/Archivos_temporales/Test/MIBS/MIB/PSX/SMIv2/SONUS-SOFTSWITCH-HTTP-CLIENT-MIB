--
-- This SMIv2 module has been generated by smidump 0.2-cvs. Do not edit.
--

SONUS-SOFTSWITCH-HTTP-CLIENT-MIB DEFINITIONS ::= BEGIN

IMPORTS
    InetAddress, InetAddressType
        FROM INET-ADDRESS-MIB
    Counter32, Gauge32, Integer32, IpAddress, MODULE-IDENTITY, 
    NOTIFICATION-TYPE, OBJECT-TYPE, TimeTicks
        FROM SNMPv2-SMI
    DisplayString
        FROM SNMPv2-TC
    sonusEventClass, sonusEventDescription, sonusEventLevel, 
    sonusEventTime
        FROM SONUS-COMMON-MIB
    sonusServicesMIBs
        FROM SONUS-SMI;

sonusSoftSwitchHTTPClientMIB MODULE-IDENTITY
    LAST-UPDATED    "201807030000Z"
    ORGANIZATION    
            "Sonus Networks, Inc."
    CONTACT-INFO    
            "   Customer Support    
             Sonus Networks, Inc.
             250 Apollo Drive
             Chelmsford, MA 01824
             USA
             
             Tel: 978-614-8100
             Fax: 978-614-8609"
    DESCRIPTION     
            "The MIB Module for SoftSwitch HTTP Client Management."
    ::= { sonusServicesMIBs 43 }


sonusSoftSwitchHTTPClientMIBObjects OBJECT IDENTIFIER
    ::= { sonusSoftSwitchHTTPClientMIB 1 }

sonusSoftSwitchHTTPClientStatistics OBJECT IDENTIFIER
    ::= { sonusSoftSwitchHTTPClientMIBObjects 1 }

sonusSoftSwitchHTTPClientSigningCounters OBJECT IDENTIFIER
    ::= { sonusSoftSwitchHTTPClientStatistics 1 }

sonusSoftSwitchHTTPSigningQuerySentCounters OBJECT-TYPE
    SYNTAX          Counter32
    MAX-ACCESS      read-only
    STATUS          current
    DESCRIPTION     
            "This counter keeps track of the number of Signing requests 
             which are sent from HTTP Client Process."
    ::= { sonusSoftSwitchHTTPClientSigningCounters 1 }

sonusSoftSwitchHTTPSigningRspCounters OBJECT-TYPE
    SYNTAX          Counter32
    MAX-ACCESS      read-only
    STATUS          current
    DESCRIPTION     
            "This counter keeps track of the number of Signing responses 
             which have been received by HTTP Client process."
    ::= { sonusSoftSwitchHTTPClientSigningCounters 2 }

sonusSoftSwitchHTTPSigningInvalidInputCounters OBJECT-TYPE
    SYNTAX          Counter32
    MAX-ACCESS      read-only
    STATUS          current
    DESCRIPTION     
            "This counter keeps track of the number of signing requests 
             which failed due to invalid input."
    ::= { sonusSoftSwitchHTTPClientSigningCounters 3 }

sonusSoftSwitchHTTPSigningQueryTimeOutCounters OBJECT-TYPE
    SYNTAX          Counter32
    MAX-ACCESS      read-only
    STATUS          current
    DESCRIPTION     
            "This counter keeps track of the number of signing requests 
             which have timeout for response."
    ::= { sonusSoftSwitchHTTPClientSigningCounters 4 }

sonusSoftSwitchHTTPSigningQueryRetryCounters OBJECT-TYPE
    SYNTAX          Counter32
    MAX-ACCESS      read-only
    STATUS          current
    DESCRIPTION     
            "This counter keeps track of the number of Signing requests
             which are retried from HTTP Client Process."
    ::= { sonusSoftSwitchHTTPClientSigningCounters 5 }

sonusSoftSwitchHTTPClientVerificationCounters OBJECT IDENTIFIER
    ::= { sonusSoftSwitchHTTPClientStatistics 2 }

sonusSoftSwitchHTTPVerificationQuerySentCounters OBJECT-TYPE
    SYNTAX          Counter32
    MAX-ACCESS      read-only
    STATUS          current
    DESCRIPTION     
            "This counter keeps track of the number of Verification requests
             which are sent from HTTP Client Process."
    ::= { sonusSoftSwitchHTTPClientVerificationCounters 1 }

sonusSoftSwitchHTTPVerificationRspCounters OBJECT-TYPE
    SYNTAX          Counter32
    MAX-ACCESS      read-only
    STATUS          current
    DESCRIPTION     
            "This counter keeps track of the number of Verification responses
             which have been received by HTTP Client process."
    ::= { sonusSoftSwitchHTTPClientVerificationCounters 2 }

sonusSoftSwitchHTTPVerificationInvalidInputCounters OBJECT-TYPE
    SYNTAX          Counter32
    MAX-ACCESS      read-only
    STATUS          current
    DESCRIPTION     
            "This counter keeps track of the number of Verification requests
             which failed due to invalid input."
    ::= { sonusSoftSwitchHTTPClientVerificationCounters 3 }

sonusSoftSwitchHTTPVerificationQueryTimeOutCounters OBJECT-TYPE
    SYNTAX          Counter32
    MAX-ACCESS      read-only
    STATUS          current
    DESCRIPTION     
            "This counter keeps track of the number of Verification requests
             which have timeout for response."
    ::= { sonusSoftSwitchHTTPClientVerificationCounters 4 }

sonusSoftSwitchHTTPVerificationQueryRetryCounters OBJECT-TYPE
    SYNTAX          Counter32
    MAX-ACCESS      read-only
    STATUS          current
    DESCRIPTION     
            "This counter keeps track of the number of Verification requests
             which are retried from HTTP Client Process."
    ::= { sonusSoftSwitchHTTPClientVerificationCounters 5 }

sonusSoftSwitchHTTPClientSigningFailureCounters OBJECT IDENTIFIER
    ::= { sonusSoftSwitchHTTPClientStatistics 3 }

sonusSoftSwitchHTTPSigningFailureE3Counters OBJECT-TYPE
    SYNTAX          Counter32
    MAX-ACCESS      read-only
    STATUS          current
    DESCRIPTION     
            "This counter keeps track of the number of E3 error 
             received from signing server."
    ::= { sonusSoftSwitchHTTPClientSigningFailureCounters 1 }

sonusSoftSwitchHTTPSigningFailureX1Counters OBJECT-TYPE
    SYNTAX          Counter32
    MAX-ACCESS      read-only
    STATUS          current
    DESCRIPTION     
            "This counter keeps track of the number of X1 error 
             received from signing server."
    ::= { sonusSoftSwitchHTTPClientSigningFailureCounters 2 }

sonusSoftSwitchHTTPSigningFailureX2Counters OBJECT-TYPE
    SYNTAX          Counter32
    MAX-ACCESS      read-only
    STATUS          current
    DESCRIPTION     
            "This counter keeps track of the number of X2 error 
             received from signing server."
    ::= { sonusSoftSwitchHTTPClientSigningFailureCounters 3 }

sonusSoftSwitchHTTPSigningFailureX3Counters OBJECT-TYPE
    SYNTAX          Counter32
    MAX-ACCESS      read-only
    STATUS          current
    DESCRIPTION     
            "This counter keeps track of the number of X3 error 
             received from signing server."
    ::= { sonusSoftSwitchHTTPClientSigningFailureCounters 4 }

sonusSoftSwitchHTTPSigningFailureX4Counters OBJECT-TYPE
    SYNTAX          Counter32
    MAX-ACCESS      read-only
    STATUS          current
    DESCRIPTION     
            "This counter keeps track of the number of X4 error 
             received from signing server."
    ::= { sonusSoftSwitchHTTPClientSigningFailureCounters 5 }

sonusSoftSwitchHTTPSigningFailure400Counters OBJECT-TYPE
    SYNTAX          Counter32
    MAX-ACCESS      read-only
    STATUS          current
    DESCRIPTION     
            "This counter keeps track of the number of 400 error
             received from signing server."
    ::= { sonusSoftSwitchHTTPClientSigningFailureCounters 6 }

sonusSoftSwitchHTTPSigningFailure500Counters OBJECT-TYPE
    SYNTAX          Counter32
    MAX-ACCESS      read-only
    STATUS          current
    DESCRIPTION     
            "This counter keeps track of the number of 500 error 
             received from signing server."
    ::= { sonusSoftSwitchHTTPClientSigningFailureCounters 7 }

sonusSoftSwitchHTTPSigningFailure503Counters OBJECT-TYPE
    SYNTAX          Counter32
    MAX-ACCESS      read-only
    STATUS          current
    DESCRIPTION     
            "This counter keeps track of the number of 503 error 
             received from signing server."
    ::= { sonusSoftSwitchHTTPClientSigningFailureCounters 8 }

sonusSoftSwitchHTTPSigningFailure405Counters OBJECT-TYPE
    SYNTAX          Counter32
    MAX-ACCESS      read-only
    STATUS          current
    DESCRIPTION     
            "This counter keeps track of the number of 405 error
             received from signing server."
    ::= { sonusSoftSwitchHTTPClientSigningFailureCounters 9 }

sonusSoftSwitchHTTPSigningFailure406Counters OBJECT-TYPE
    SYNTAX          Counter32
    MAX-ACCESS      read-only
    STATUS          current
    DESCRIPTION     
            "This counter keeps track of the number of 406 error
             received from signing server."
    ::= { sonusSoftSwitchHTTPClientSigningFailureCounters 10 }

sonusSoftSwitchHTTPSigningFailure411Counters OBJECT-TYPE
    SYNTAX          Counter32
    MAX-ACCESS      read-only
    STATUS          current
    DESCRIPTION     
            "This counter keeps track of the number of 411 error
             received from signing server."
    ::= { sonusSoftSwitchHTTPClientSigningFailureCounters 11 }

sonusSoftSwitchHTTPSigningFailure415Counters OBJECT-TYPE
    SYNTAX          Counter32
    MAX-ACCESS      read-only
    STATUS          current
    DESCRIPTION     
            "This counter keeps track of the number of 415 error
             received from signing server."
    ::= { sonusSoftSwitchHTTPClientSigningFailureCounters 12 }

sonusSoftSwitchHTTPSigningFailureSVC4000Counters OBJECT-TYPE
    SYNTAX          Counter32
    MAX-ACCESS      read-only
    STATUS          current
    DESCRIPTION     
            "This counter keeps track of the number of service exception 4000 error
             received from signing server."
    ::= { sonusSoftSwitchHTTPClientSigningFailureCounters 13 }

sonusSoftSwitchHTTPSigningFailureSVC4001Counters OBJECT-TYPE
    SYNTAX          Counter32
    MAX-ACCESS      read-only
    STATUS          current
    DESCRIPTION     
            "This counter keeps track of the number of service exception 4001 error
             received from signing server."
    ::= { sonusSoftSwitchHTTPClientSigningFailureCounters 14 }

sonusSoftSwitchHTTPSigningFailureSVC4002Counters OBJECT-TYPE
    SYNTAX          Counter32
    MAX-ACCESS      read-only
    STATUS          current
    DESCRIPTION     
            "This counter keeps track of the number of service exception 4002 error
             received from signing server."
    ::= { sonusSoftSwitchHTTPClientSigningFailureCounters 15 }

sonusSoftSwitchHTTPSigningFailureSVC4003Counters OBJECT-TYPE
    SYNTAX          Counter32
    MAX-ACCESS      read-only
    STATUS          current
    DESCRIPTION     
            "This counter keeps track of the number of service exception 4003 error
             received from signing server."
    ::= { sonusSoftSwitchHTTPClientSigningFailureCounters 16 }

sonusSoftSwitchHTTPSigningFailureSVC4004Counters OBJECT-TYPE
    SYNTAX          Counter32
    MAX-ACCESS      read-only
    STATUS          current
    DESCRIPTION     
            "This counter keeps track of the number of service exception 4004 error
             received from signing server."
    ::= { sonusSoftSwitchHTTPClientSigningFailureCounters 17 }

sonusSoftSwitchHTTPSigningFailureSVC4005Counters OBJECT-TYPE
    SYNTAX          Counter32
    MAX-ACCESS      read-only
    STATUS          current
    DESCRIPTION     
            "This counter keeps track of the number of service exception 4005 error
             received from signing server."
    ::= { sonusSoftSwitchHTTPClientSigningFailureCounters 18 }

sonusSoftSwitchHTTPSigningFailureSVC4006Counters OBJECT-TYPE
    SYNTAX          Counter32
    MAX-ACCESS      read-only
    STATUS          current
    DESCRIPTION     
            "This counter keeps track of the number of service exception 4006 error
             received from signing server."
    ::= { sonusSoftSwitchHTTPClientSigningFailureCounters 19 }

sonusSoftSwitchHTTPSigningFailureSVC4007Counters OBJECT-TYPE
    SYNTAX          Counter32
    MAX-ACCESS      read-only
    STATUS          current
    DESCRIPTION     
            "This counter keeps track of the number of service exception 4007 error
             received from signing server."
    ::= { sonusSoftSwitchHTTPClientSigningFailureCounters 20 }

sonusSoftSwitchHTTPSigningFailurePOL4050Counters OBJECT-TYPE
    SYNTAX          Counter32
    MAX-ACCESS      read-only
    STATUS          current
    DESCRIPTION     
            "This counter keeps track of the number of policy exception 4050 error
             received from signing server."
    ::= { sonusSoftSwitchHTTPClientSigningFailureCounters 21 }

sonusSoftSwitchHTTPSigningFailurePOL5000Counters OBJECT-TYPE
    SYNTAX          Counter32
    MAX-ACCESS      read-only
    STATUS          current
    DESCRIPTION     
            "This counter keeps track of the number of policy exception 5000 error
             received from signing server."
    ::= { sonusSoftSwitchHTTPClientSigningFailureCounters 22 }

sonusSoftSwitchHTTPSigningFailure404Counters OBJECT-TYPE
    SYNTAX          Counter32
    MAX-ACCESS      read-only
    STATUS          current
    DESCRIPTION     
            "This counter keeps track of the number of 404 error
             received from signing server."
    ::= { sonusSoftSwitchHTTPClientSigningFailureCounters 23 }

sonusSoftSwitchHTTPClientVerificationFailureCounters OBJECT IDENTIFIER
    ::= { sonusSoftSwitchHTTPClientStatistics 4 }

sonusSoftSwitchHTTPVerificationFailureE3Counters OBJECT-TYPE
    SYNTAX          Counter32
    MAX-ACCESS      read-only
    STATUS          current
    DESCRIPTION     
            "This counter keeps track of the number of E3 error
             received from verification server."
    ::= { sonusSoftSwitchHTTPClientVerificationFailureCounters 1 }

sonusSoftSwitchHTTPVerificationFailureE4Counters OBJECT-TYPE
    SYNTAX          Counter32
    MAX-ACCESS      read-only
    STATUS          current
    DESCRIPTION     
            "This counter keeps track of the number of E4 error
             received from verification server."
    ::= { sonusSoftSwitchHTTPClientVerificationFailureCounters 2 }

sonusSoftSwitchHTTPVerificationFailureE5Counters OBJECT-TYPE
    SYNTAX          Counter32
    MAX-ACCESS      read-only
    STATUS          current
    DESCRIPTION     
            "This counter keeps track of the number of E5 error
             received from verification server."
    ::= { sonusSoftSwitchHTTPClientVerificationFailureCounters 3 }

sonusSoftSwitchHTTPVerificationFailureE6Counters OBJECT-TYPE
    SYNTAX          Counter32
    MAX-ACCESS      read-only
    STATUS          current
    DESCRIPTION     
            "This counter keeps track of the number of E6 error
             received from verification server."
    ::= { sonusSoftSwitchHTTPClientVerificationFailureCounters 4 }

sonusSoftSwitchHTTPVerificationFailureE7Counters OBJECT-TYPE
    SYNTAX          Counter32
    MAX-ACCESS      read-only
    STATUS          current
    DESCRIPTION     
            "This counter keeps track of the number of E7 error
             received from verification server."
    ::= { sonusSoftSwitchHTTPClientVerificationFailureCounters 5 }

sonusSoftSwitchHTTPVerificationFailureE8Counters OBJECT-TYPE
    SYNTAX          Counter32
    MAX-ACCESS      read-only
    STATUS          current
    DESCRIPTION     
            "This counter keeps track of the number of E8 error
             received from verification server."
    ::= { sonusSoftSwitchHTTPClientVerificationFailureCounters 6 }

sonusSoftSwitchHTTPVerificationFailureE9Counters OBJECT-TYPE
    SYNTAX          Counter32
    MAX-ACCESS      read-only
    STATUS          current
    DESCRIPTION     
            "This counter keeps track of the number of E9 error
             received from verification server."
    ::= { sonusSoftSwitchHTTPClientVerificationFailureCounters 7 }

sonusSoftSwitchHTTPVerificationFailureE10Counters OBJECT-TYPE
    SYNTAX          Counter32
    MAX-ACCESS      read-only
    STATUS          current
    DESCRIPTION     
            "This counter keeps track of the number of E10 error
             received from verification server."
    ::= { sonusSoftSwitchHTTPClientVerificationFailureCounters 8 }

sonusSoftSwitchHTTPVerificationFailureE11Counters OBJECT-TYPE
    SYNTAX          Counter32
    MAX-ACCESS      read-only
    STATUS          current
    DESCRIPTION     
            "This counter keeps track of the number of E11 error
             received from verification server."
    ::= { sonusSoftSwitchHTTPClientVerificationFailureCounters 9 }

sonusSoftSwitchHTTPVerificationFailureE12Counters OBJECT-TYPE
    SYNTAX          Counter32
    MAX-ACCESS      read-only
    STATUS          current
    DESCRIPTION     
            "This counter keeps track of the number of E12 error
             received from verification server."
    ::= { sonusSoftSwitchHTTPClientVerificationFailureCounters 10 }

sonusSoftSwitchHTTPVerificationFailureE13Counters OBJECT-TYPE
    SYNTAX          Counter32
    MAX-ACCESS      read-only
    STATUS          current
    DESCRIPTION     
            "This counter keeps track of the number of E13 error
             received from verification server."
    ::= { sonusSoftSwitchHTTPClientVerificationFailureCounters 11 }

sonusSoftSwitchHTTPVerificationFailureE14Counters OBJECT-TYPE
    SYNTAX          Counter32
    MAX-ACCESS      read-only
    STATUS          current
    DESCRIPTION     
            "This counter keeps track of the number of E14 error
             received from verification server."
    ::= { sonusSoftSwitchHTTPClientVerificationFailureCounters 12 }

sonusSoftSwitchHTTPVerificationFailureE15Counters OBJECT-TYPE
    SYNTAX          Counter32
    MAX-ACCESS      read-only
    STATUS          current
    DESCRIPTION     
            "This counter keeps track of the number of E15 error
             received from verification server."
    ::= { sonusSoftSwitchHTTPClientVerificationFailureCounters 13 }

sonusSoftSwitchHTTPVerificationFailureE16Counters OBJECT-TYPE
    SYNTAX          Counter32
    MAX-ACCESS      read-only
    STATUS          current
    DESCRIPTION     
            "This counter keeps track of the number of E16 error
             received from verification server."
    ::= { sonusSoftSwitchHTTPClientVerificationFailureCounters 14 }

sonusSoftSwitchHTTPVerificationFailureE17Counters OBJECT-TYPE
    SYNTAX          Counter32
    MAX-ACCESS      read-only
    STATUS          current
    DESCRIPTION     
            "This counter keeps track of the number of E17 error
             received from verification server."
    ::= { sonusSoftSwitchHTTPClientVerificationFailureCounters 15 }

sonusSoftSwitchHTTPVerificationFailureE18Counters OBJECT-TYPE
    SYNTAX          Counter32
    MAX-ACCESS      read-only
    STATUS          current
    DESCRIPTION     
            "This counter keeps track of the number of E18 error
             received from verification server."
    ::= { sonusSoftSwitchHTTPClientVerificationFailureCounters 16 }

sonusSoftSwitchHTTPVerificationFailureE19Counters OBJECT-TYPE
    SYNTAX          Counter32
    MAX-ACCESS      read-only
    STATUS          current
    DESCRIPTION     
            "This counter keeps track of the number of E19 error
             received from verification server."
    ::= { sonusSoftSwitchHTTPClientVerificationFailureCounters 17 }

sonusSoftSwitchHTTPVerificationFailureE20Counters OBJECT-TYPE
    SYNTAX          Counter32
    MAX-ACCESS      read-only
    STATUS          current
    DESCRIPTION     
            "This counter keeps track of the number of E20 error
             received from verification server."
    ::= { sonusSoftSwitchHTTPClientVerificationFailureCounters 18 }

sonusSoftSwitchHTTPVerificationFailureE21Counters OBJECT-TYPE
    SYNTAX          Counter32
    MAX-ACCESS      read-only
    STATUS          current
    DESCRIPTION     
            "This counter keeps track of the number of E21 error
             received from verification server."
    ::= { sonusSoftSwitchHTTPClientVerificationFailureCounters 19 }

sonusSoftSwitchHTTPVerificationFailureE22Counters OBJECT-TYPE
    SYNTAX          Counter32
    MAX-ACCESS      read-only
    STATUS          current
    DESCRIPTION     
            "This counter keeps track of the number of E22 error
             received from verification server."
    ::= { sonusSoftSwitchHTTPClientVerificationFailureCounters 20 }

sonusSoftSwitchHTTPVerificationFailureE23Counters OBJECT-TYPE
    SYNTAX          Counter32
    MAX-ACCESS      read-only
    STATUS          current
    DESCRIPTION     
            "This counter keeps track of the number of E23 error
             received from verification server."
    ::= { sonusSoftSwitchHTTPClientVerificationFailureCounters 21 }

sonusSoftSwitchHTTPVerificationFailureX1Counters OBJECT-TYPE
    SYNTAX          Counter32
    MAX-ACCESS      read-only
    STATUS          current
    DESCRIPTION     
            "This counter keeps track of the number of X1 error
             received from verification server."
    ::= { sonusSoftSwitchHTTPClientVerificationFailureCounters 22 }

sonusSoftSwitchHTTPVerificationFailureX2Counters OBJECT-TYPE
    SYNTAX          Counter32
    MAX-ACCESS      read-only
    STATUS          current
    DESCRIPTION     
            "This counter keeps track of the number of X2 error
             received from verification server."
    ::= { sonusSoftSwitchHTTPClientVerificationFailureCounters 23 }

sonusSoftSwitchHTTPVerificationFailureX3Counters OBJECT-TYPE
    SYNTAX          Counter32
    MAX-ACCESS      read-only
    STATUS          current
    DESCRIPTION     
            "This counter keeps track of the number of X3 error
             received from verification server."
    ::= { sonusSoftSwitchHTTPClientVerificationFailureCounters 24 }

sonusSoftSwitchHTTPVerificationFailureX4Counters OBJECT-TYPE
    SYNTAX          Counter32
    MAX-ACCESS      read-only
    STATUS          current
    DESCRIPTION     
            "This counter keeps track of the number of X4 error
             received from verification server."
    ::= { sonusSoftSwitchHTTPClientVerificationFailureCounters 25 }

sonusSoftSwitchHTTPVerificationFailure400Counters OBJECT-TYPE
    SYNTAX          Counter32
    MAX-ACCESS      read-only
    STATUS          current
    DESCRIPTION     
            "This counter keeps track of the number of 400 error
             received from verification server."
    ::= { sonusSoftSwitchHTTPClientVerificationFailureCounters 26 }

sonusSoftSwitchHTTPVerificationFailure500Counters OBJECT-TYPE
    SYNTAX          Counter32
    MAX-ACCESS      read-only
    STATUS          current
    DESCRIPTION     
            "This counter keeps track of the number of 500 error
             received from verification server."
    ::= { sonusSoftSwitchHTTPClientVerificationFailureCounters 27 }

sonusSoftSwitchHTTPVerificationFailure503Counters OBJECT-TYPE
    SYNTAX          Counter32
    MAX-ACCESS      read-only
    STATUS          current
    DESCRIPTION     
            "This counter keeps track of the number of 503 error
             received from verification server."
    ::= { sonusSoftSwitchHTTPClientVerificationFailureCounters 28 }

sonusSoftSwitchHTTPVerificationFailure405Counters OBJECT-TYPE
    SYNTAX          Counter32
    MAX-ACCESS      read-only
    STATUS          current
    DESCRIPTION     
            "This counter keeps track of the number of 405 error
             received from verification server."
    ::= { sonusSoftSwitchHTTPClientVerificationFailureCounters 29 }

sonusSoftSwitchHTTPVerificationFailure406Counters OBJECT-TYPE
    SYNTAX          Counter32
    MAX-ACCESS      read-only
    STATUS          current
    DESCRIPTION     
            "This counter keeps track of the number of 406 error
             received from verification server."
    ::= { sonusSoftSwitchHTTPClientVerificationFailureCounters 30 }

sonusSoftSwitchHTTPVerificationFailure411Counters OBJECT-TYPE
    SYNTAX          Counter32
    MAX-ACCESS      read-only
    STATUS          current
    DESCRIPTION     
            "This counter keeps track of the number of 411 error
             received from verification server."
    ::= { sonusSoftSwitchHTTPClientVerificationFailureCounters 31 }

sonusSoftSwitchHTTPVerificationFailure415Counters OBJECT-TYPE
    SYNTAX          Counter32
    MAX-ACCESS      read-only
    STATUS          current
    DESCRIPTION     
            "This counter keeps track of the number of 415 error
             received from verification server."
    ::= { sonusSoftSwitchHTTPClientVerificationFailureCounters 32 }

sonusSoftSwitchHTTPVerificationFailureSVC4000Counters OBJECT-TYPE
    SYNTAX          Counter32
    MAX-ACCESS      read-only
    STATUS          current
    DESCRIPTION     
            "This counter keeps track of the number of service exception 4000 error
             received from verification server."
    ::= { sonusSoftSwitchHTTPClientVerificationFailureCounters 33 }

sonusSoftSwitchHTTPVerificationFailureSVC4001Counters OBJECT-TYPE
    SYNTAX          Counter32
    MAX-ACCESS      read-only
    STATUS          current
    DESCRIPTION     
            "This counter keeps track of the number of service exception 4001 error
             received from verification server."
    ::= { sonusSoftSwitchHTTPClientVerificationFailureCounters 34 }

sonusSoftSwitchHTTPVerificationFailureSVC4002Counters OBJECT-TYPE
    SYNTAX          Counter32
    MAX-ACCESS      read-only
    STATUS          current
    DESCRIPTION     
            "This counter keeps track of the number of service exception 4002 error
             received from verification server."
    ::= { sonusSoftSwitchHTTPClientVerificationFailureCounters 35 }

sonusSoftSwitchHTTPVerificationFailureSVC4003Counters OBJECT-TYPE
    SYNTAX          Counter32
    MAX-ACCESS      read-only
    STATUS          current
    DESCRIPTION     
            "This counter keeps track of the number of service exception 4003 error
             received from verification server."
    ::= { sonusSoftSwitchHTTPClientVerificationFailureCounters 36 }

sonusSoftSwitchHTTPVerificationFailureSVC4004Counters OBJECT-TYPE
    SYNTAX          Counter32
    MAX-ACCESS      read-only
    STATUS          current
    DESCRIPTION     
            "This counter keeps track of the number of service exception 4004 error
             received from verification server."
    ::= { sonusSoftSwitchHTTPClientVerificationFailureCounters 37 }

sonusSoftSwitchHTTPVerificationFailureSVC4005Counters OBJECT-TYPE
    SYNTAX          Counter32
    MAX-ACCESS      read-only
    STATUS          current
    DESCRIPTION     
            "This counter keeps track of the number of service exception 4005 error
             received from verification server."
    ::= { sonusSoftSwitchHTTPClientVerificationFailureCounters 38 }

sonusSoftSwitchHTTPVerificationFailureSVC4006Counters OBJECT-TYPE
    SYNTAX          Counter32
    MAX-ACCESS      read-only
    STATUS          current
    DESCRIPTION     
            "This counter keeps track of the number of service exception 4006 error
             received from verification server."
    ::= { sonusSoftSwitchHTTPClientVerificationFailureCounters 39 }

sonusSoftSwitchHTTPVerificationFailureSVC4007Counters OBJECT-TYPE
    SYNTAX          Counter32
    MAX-ACCESS      read-only
    STATUS          current
    DESCRIPTION     
            "This counter keeps track of the number of service exception 4007 error
             received from verification server."
    ::= { sonusSoftSwitchHTTPClientVerificationFailureCounters 40 }

sonusSoftSwitchHTTPVerificationFailurePOL4050Counters OBJECT-TYPE
    SYNTAX          Counter32
    MAX-ACCESS      read-only
    STATUS          current
    DESCRIPTION     
            "This counter keeps track of the number of policy exception 4050 error
             received from verification server."
    ::= { sonusSoftSwitchHTTPClientVerificationFailureCounters 41 }

sonusSoftSwitchHTTPVerificationFailurePOL5000Counters OBJECT-TYPE
    SYNTAX          Counter32
    MAX-ACCESS      read-only
    STATUS          current
    DESCRIPTION     
            "This counter keeps track of the number of policy exception 5000 error
             received from verification server."
    ::= { sonusSoftSwitchHTTPClientVerificationFailureCounters 42 }

sonusSoftSwitchHTTPVerificationFailure404Counters OBJECT-TYPE
    SYNTAX          Counter32
    MAX-ACCESS      read-only
    STATUS          current
    DESCRIPTION     
            "This counter keeps track of the number of 404 error
             received from verification server."
    ::= { sonusSoftSwitchHTTPClientVerificationFailureCounters 43 }

sonusSoftSwitchHTTPClientInternalCounters OBJECT IDENTIFIER
    ::= { sonusSoftSwitchHTTPClientStatistics 5 }

sonusSoftSwitchHTTPNoConnectionAvailableCounters OBJECT-TYPE
    SYNTAX          Counter32
    MAX-ACCESS      read-only
    STATUS          current
    DESCRIPTION     
            "This counter keeps track of the number of errors with no connection available."
    ::= { sonusSoftSwitchHTTPClientInternalCounters 1 }

sonusSoftSwitchHTTPJsonErrorCounters OBJECT-TYPE
    SYNTAX          Counter32
    MAX-ACCESS      read-only
    STATUS          current
    DESCRIPTION     
            "This counter keeps track of the number of JSON Error."
    ::= { sonusSoftSwitchHTTPClientInternalCounters 2 }

sonusSoftSwitchHTTPCurlErrorCounters OBJECT-TYPE
    SYNTAX          Counter32
    MAX-ACCESS      read-only
    STATUS          current
    DESCRIPTION     
            "This counter keeps track of the number of HTTP Error."
    ::= { sonusSoftSwitchHTTPClientInternalCounters 3 }

sonusSoftSwitchHTTPMaxRetriesExhaustedCounters OBJECT-TYPE
    SYNTAX          Counter32
    MAX-ACCESS      read-only
    STATUS          current
    DESCRIPTION     
            "This counter keeps track of the number of failures due to Max Retries Exhausted."
    ::= { sonusSoftSwitchHTTPClientInternalCounters 4 }

sonusSoftSwitchHTTPGeneralFailureCounters OBJECT-TYPE
    SYNTAX          Counter32
    MAX-ACCESS      read-only
    STATUS          current
    DESCRIPTION     
            "This counter keeps track of the number of General Failure."
    ::= { sonusSoftSwitchHTTPClientInternalCounters 5 }

sonusSoftSwitchPerFqdnCounters OBJECT IDENTIFIER
    ::= { sonusSoftSwitchHTTPClientStatistics 6 }

sonusSoftSwitchPerFqdnCountersTable OBJECT-TYPE
    SYNTAX          SEQUENCE OF SonusSoftSwitchFqdnCountersEntry
    MAX-ACCESS      not-accessible
    STATUS          current
    DESCRIPTION     
            "FQDN Counters PER FQDN Server"
    ::= { sonusSoftSwitchPerFqdnCounters 1 }

sonusSoftSwitchFqdnCountersEntry OBJECT-TYPE
    SYNTAX          SonusSoftSwitchFqdnCountersEntry
    MAX-ACCESS      not-accessible
    STATUS          current
    DESCRIPTION     
            "An entry of Traffic counters related to FQDN Servers"
    INDEX           { sonusSoftSwitchPerFqdnCountersFqdnName }
    ::= { sonusSoftSwitchPerFqdnCountersTable 1 }

SonusSoftSwitchFqdnCountersEntry ::=
    SEQUENCE {
        sonusSoftSwitchPerFqdnCountersFqdnName      DisplayString,
        sonusSoftSwitchPerFqdnCountersRequestsSent          Counter32,
        sonusSoftSwitchPerFqdnCountersResponsesRcvd           Counter32,
        sonusSoftSwitchPerFqdnCounters400Rcvd     Counter32,
        sonusSoftSwitchPerFqdnCounters500Rcvd     Counter32,
        sonusSoftSwitchPerFqdnCounters503Rcvd     Counter32,
        sonusSoftSwitchPerFqdnCountersTimeouts      Counter32,
        sonusSoftSwitchPerFqdnCountersNoConnAvailable             Counter32,
        sonusSoftSwitchPerFqdnCountersJsonErr     Counter32,
        sonusSoftSwitchPerFqdnCountersHttpErr     Counter32,
        sonusSoftSwitchPerFqdnCountersMaxRetryExhausted               Counter32,
        sonusSoftSwitchPerFqdnCountersGenFailure        Counter32,
        sonusSoftSwitchPerFqdnCounters403Rcvd     Counter32
    }

sonusSoftSwitchPerFqdnCountersFqdnName OBJECT-TYPE
    SYNTAX          DisplayString
    MAX-ACCESS      read-only
    STATUS          current
    DESCRIPTION     
            "FQDN Name."
    ::= { sonusSoftSwitchFqdnCountersEntry 1 }

sonusSoftSwitchPerFqdnCountersRequestsSent OBJECT-TYPE
    SYNTAX          Counter32
    MAX-ACCESS      read-only
    STATUS          current
    DESCRIPTION     
            "This counter keeps track of the number of requests
             which have been sent by the http process counted for each Fqdn"
    ::= { sonusSoftSwitchFqdnCountersEntry 2 }

sonusSoftSwitchPerFqdnCountersResponsesRcvd OBJECT-TYPE
    SYNTAX          Counter32
    MAX-ACCESS      read-only
    STATUS          current
    DESCRIPTION     
            "This counter keeps track of the number of responses
             which have been received by the http process counted for each Fqdn "
    ::= { sonusSoftSwitchFqdnCountersEntry 3 }

sonusSoftSwitchPerFqdnCounters400Rcvd OBJECT-TYPE
    SYNTAX          Counter32
    MAX-ACCESS      read-only
    STATUS          current
    DESCRIPTION     
            "This counter keeps track of the number of 400 responses
             which have been received by the http process counted for each Fqdn "
    ::= { sonusSoftSwitchFqdnCountersEntry 4 }

sonusSoftSwitchPerFqdnCounters500Rcvd OBJECT-TYPE
    SYNTAX          Counter32
    MAX-ACCESS      read-only
    STATUS          current
    DESCRIPTION     
            "This counter keeps track of the number of 500 responses
             which have been received by the http process counted for each Fqdn "
    ::= { sonusSoftSwitchFqdnCountersEntry 5 }

sonusSoftSwitchPerFqdnCounters503Rcvd OBJECT-TYPE
    SYNTAX          Counter32
    MAX-ACCESS      read-only
    STATUS          current
    DESCRIPTION     
            "This counter keeps track of the number of 503 responses
             which have been received by the http process counted for each Fqdn "
    ::= { sonusSoftSwitchFqdnCountersEntry 6 }

sonusSoftSwitchPerFqdnCountersTimeouts OBJECT-TYPE
    SYNTAX          Counter32
    MAX-ACCESS      read-only
    STATUS          current
    DESCRIPTION     
            "This counter keeps track of the number of Timeouts "
    ::= { sonusSoftSwitchFqdnCountersEntry 7 }

sonusSoftSwitchPerFqdnCountersNoConnAvailable OBJECT-TYPE
    SYNTAX          Counter32
    MAX-ACCESS      read-only
    STATUS          current
    DESCRIPTION     
            "This counter keeps track of the number of No Connections Available "
    ::= { sonusSoftSwitchFqdnCountersEntry 8 }

sonusSoftSwitchPerFqdnCountersJsonErr OBJECT-TYPE
    SYNTAX          Counter32
    MAX-ACCESS      read-only
    STATUS          current
    DESCRIPTION     
            "This counter keeps track of the number of JSON Error "
    ::= { sonusSoftSwitchFqdnCountersEntry 9 }

sonusSoftSwitchPerFqdnCountersHttpErr OBJECT-TYPE
    SYNTAX          Counter32
    MAX-ACCESS      read-only
    STATUS          current
    DESCRIPTION     
            "This counter keeps track of the number of HTTP Error "
    ::= { sonusSoftSwitchFqdnCountersEntry 10 }

sonusSoftSwitchPerFqdnCountersMaxRetryExhausted OBJECT-TYPE
    SYNTAX          Counter32
    MAX-ACCESS      read-only
    STATUS          current
    DESCRIPTION     
            "This counter keeps track of the number of Failures due to Max Retry Exhausted "
    ::= { sonusSoftSwitchFqdnCountersEntry 11 }

sonusSoftSwitchPerFqdnCountersGenFailure OBJECT-TYPE
    SYNTAX          Counter32
    MAX-ACCESS      read-only
    STATUS          current
    DESCRIPTION     
            "This counter keeps track of the number of General Failures"
    ::= { sonusSoftSwitchFqdnCountersEntry 12 }

sonusSoftSwitchPerFqdnCounters403Rcvd OBJECT-TYPE
    SYNTAX          Counter32
    MAX-ACCESS      read-only
    STATUS          current
    DESCRIPTION     
            "This counter keeps track of the number of 403 responses
             which have been received by the http process counted for each Fqdn "
    ::= { sonusSoftSwitchFqdnCountersEntry 13 }

sonusSoftSwitchHTTPClientPerServerIpCounters OBJECT IDENTIFIER
    ::= { sonusSoftSwitchHTTPClientStatistics 7 }

sonusSoftSwitchHTTPClientPerIpCountersTable OBJECT-TYPE
    SYNTAX          SEQUENCE OF SonusSoftSwitchHTTPClientPerIpCountersEntry
    MAX-ACCESS      not-accessible
    STATUS          current
    DESCRIPTION     
            "HTTP Client counters per IP"
    ::= { sonusSoftSwitchHTTPClientPerServerIpCounters 1 }

sonusSoftSwitchHTTPClientPerIpCountersEntry OBJECT-TYPE
    SYNTAX          SonusSoftSwitchHTTPClientPerIpCountersEntry
    MAX-ACCESS      not-accessible
    STATUS          current
    DESCRIPTION     
            "An entry of Traffic counters related to Stir IP Servers"
    INDEX           { sonusSoftSwitchHTTPClientPerIpCountersIpAddrType, 
                      sonusSoftSwitchHTTPClientPerIpCountersIpAddr, 
                      sonusSoftSwitchHTTPClientPerIpCountersIpPort }
    ::= { sonusSoftSwitchHTTPClientPerIpCountersTable 1 }

SonusSoftSwitchHTTPClientPerIpCountersEntry ::=
    SEQUENCE {
        sonusSoftSwitchHTTPClientPerIpCountersIpAddrType                InetAddressType,
        sonusSoftSwitchHTTPClientPerIpCountersIpAddr            InetAddress,
        sonusSoftSwitchHTTPClientPerIpCountersIpPort            Integer32,
        sonusSoftSwitchHTTPClientPerIpCountersMaxConnTime                 Gauge32,
        sonusSoftSwitchHTTPClientPerIpCountersMinConnTime                 Gauge32,
        sonusSoftSwitchHTTPClientPerIpCountersAvgConnTime                 Gauge32,
        sonusSoftSwitchHTTPClientPerIpCountersMaxRespTime                 Gauge32,
        sonusSoftSwitchHTTPClientPerIpCountersMinRespTime                 Gauge32,
        sonusSoftSwitchHTTPClientPerIpCountersAvgRespTime                 Gauge32
    }

sonusSoftSwitchHTTPClientPerIpCountersIpAddrType OBJECT-TYPE
    SYNTAX          InetAddressType
    MAX-ACCESS      read-only
    STATUS          current
    DESCRIPTION     
            "The Server IP address Type."
    ::= { sonusSoftSwitchHTTPClientPerIpCountersEntry 1 }

sonusSoftSwitchHTTPClientPerIpCountersIpAddr OBJECT-TYPE
    SYNTAX          InetAddress
    MAX-ACCESS      read-only
    STATUS          current
    DESCRIPTION     
            " IP address of STIR Server"
    ::= { sonusSoftSwitchHTTPClientPerIpCountersEntry 2 }

sonusSoftSwitchHTTPClientPerIpCountersIpPort OBJECT-TYPE
    SYNTAX          Integer32
    MAX-ACCESS      read-only
    STATUS          current
    DESCRIPTION     
            "The Port on which server is listening."
    ::= { sonusSoftSwitchHTTPClientPerIpCountersEntry 3 }

sonusSoftSwitchHTTPClientPerIpCountersMaxConnTime OBJECT-TYPE
    SYNTAX          Gauge32
    MAX-ACCESS      read-only
    STATUS          current
    DESCRIPTION     
            "This counter keeps track of the maximum time taken to establish a connection."
    ::= { sonusSoftSwitchHTTPClientPerIpCountersEntry 4 }

sonusSoftSwitchHTTPClientPerIpCountersMinConnTime OBJECT-TYPE
    SYNTAX          Gauge32
    MAX-ACCESS      read-only
    STATUS          current
    DESCRIPTION     
            "This counter keeps track of the minimum time taken to establish a connection."
    ::= { sonusSoftSwitchHTTPClientPerIpCountersEntry 5 }

sonusSoftSwitchHTTPClientPerIpCountersAvgConnTime OBJECT-TYPE
    SYNTAX          Gauge32
    MAX-ACCESS      read-only
    STATUS          current
    DESCRIPTION     
            "This counter keeps track of the average time taken to establish a connection."
    ::= { sonusSoftSwitchHTTPClientPerIpCountersEntry 6 }

sonusSoftSwitchHTTPClientPerIpCountersMaxRespTime OBJECT-TYPE
    SYNTAX          Gauge32
    MAX-ACCESS      read-only
    STATUS          current
    DESCRIPTION     
            "This counter keeps track of the maximum time taken for the server response."
    ::= { sonusSoftSwitchHTTPClientPerIpCountersEntry 7 }

sonusSoftSwitchHTTPClientPerIpCountersMinRespTime OBJECT-TYPE
    SYNTAX          Gauge32
    MAX-ACCESS      read-only
    STATUS          current
    DESCRIPTION     
            "This counter keeps track of the minimum time taken for the server response."
    ::= { sonusSoftSwitchHTTPClientPerIpCountersEntry 8 }

sonusSoftSwitchHTTPClientPerIpCountersAvgRespTime OBJECT-TYPE
    SYNTAX          Gauge32
    MAX-ACCESS      read-only
    STATUS          current
    DESCRIPTION     
            "This counter keeps track of the average time taken for the server response."
    ::= { sonusSoftSwitchHTTPClientPerIpCountersEntry 9 }

sonusSoftSwitchHTTPPerSvrTypeSignVerCounters OBJECT IDENTIFIER
    ::= { sonusSoftSwitchHTTPClientStatistics 8 }

sonusSoftSwitchHTTPPerSvrTypeSignVerCountersTable OBJECT-TYPE
    SYNTAX          SEQUENCE OF SonusSoftSwitchHTTPPerSvrTypeSignVerCountersEntry
    MAX-ACCESS      not-accessible
    STATUS          current
    DESCRIPTION     
            "HTTP Client Signing Verification Counters Per Server Type"
    ::= { sonusSoftSwitchHTTPPerSvrTypeSignVerCounters 1 }

sonusSoftSwitchHTTPPerSvrTypeSignVerCountersEntry OBJECT-TYPE
    SYNTAX          SonusSoftSwitchHTTPPerSvrTypeSignVerCountersEntry
    MAX-ACCESS      not-accessible
    STATUS          current
    DESCRIPTION     
            "An entry of Traffic counters related to FQDN Servers"
    INDEX           { 
                      sonusSoftSwitchHTTPPerSvrTypeSignVerCountersSignVerServerName }
    ::= { sonusSoftSwitchHTTPPerSvrTypeSignVerCountersTable 1 }

SonusSoftSwitchHTTPPerSvrTypeSignVerCountersEntry ::=
    SEQUENCE {
        sonusSoftSwitchHTTPPerSvrTypeSignVerCountersSignVerServerName                             DisplayString,
        sonusSoftSwitchHTTPPerSvrTypeSignVerCountersSigningQuerySent                            Counter32,
        sonusSoftSwitchHTTPPerSvrTypeSignVerCountersSigningRsp                      Counter32,
        sonusSoftSwitchHTTPPerSvrTypeSignVerCountersSigningInvalidInput                               Counter32,
        sonusSoftSwitchHTTPPerSvrTypeSignVerCountersSigningQueryTimeOut                               Counter32,
        sonusSoftSwitchHTTPPerSvrTypeSignVerCountersSigningQueryRetry                             Counter32,
        sonusSoftSwitchHTTPPerSvrTypeSignVerCountersVerQuerySent                        Counter32,
        sonusSoftSwitchHTTPPerSvrTypeSignVerCountersVerificationRsp                           Counter32,
        sonusSoftSwitchHTTPPerSvrTypeSignVerCountersVerInvalidInput                           Counter32,
        sonusSoftSwitchHTTPPerSvrTypeSignVerCountersVerQueryTimeOut                           Counter32,
        sonusSoftSwitchHTTPPerSvrTypeSignVerCountersVerQueryRetry                         Counter32
    }

sonusSoftSwitchHTTPPerSvrTypeSignVerCountersSignVerServerName OBJECT-TYPE
    SYNTAX          DisplayString
    MAX-ACCESS      read-only
    STATUS          current
    DESCRIPTION     
            "Server Type Name."
    ::= { sonusSoftSwitchHTTPPerSvrTypeSignVerCountersEntry 1 }

sonusSoftSwitchHTTPPerSvrTypeSignVerCountersSigningQuerySent OBJECT-TYPE
    SYNTAX          Counter32
    MAX-ACCESS      read-only
    STATUS          current
    DESCRIPTION     
            "This counter keeps track of the number of Signing requests 
             which are sent from HTTP Client Process Per Server Type."
    ::= { sonusSoftSwitchHTTPPerSvrTypeSignVerCountersEntry 2 }

sonusSoftSwitchHTTPPerSvrTypeSignVerCountersSigningRsp OBJECT-TYPE
    SYNTAX          Counter32
    MAX-ACCESS      read-only
    STATUS          current
    DESCRIPTION     
            "This counter keeps track of the number of Signing responses 
             which have been received by HTTP Client process Per Server Type."
    ::= { sonusSoftSwitchHTTPPerSvrTypeSignVerCountersEntry 3 }

sonusSoftSwitchHTTPPerSvrTypeSignVerCountersSigningInvalidInput OBJECT-TYPE
    SYNTAX          Counter32
    MAX-ACCESS      read-only
    STATUS          current
    DESCRIPTION     
            "This counter keeps track of the number of signing requests 
             which failed due to invalid input Per Server Type."
    ::= { sonusSoftSwitchHTTPPerSvrTypeSignVerCountersEntry 4 }

sonusSoftSwitchHTTPPerSvrTypeSignVerCountersSigningQueryTimeOut OBJECT-TYPE
    SYNTAX          Counter32
    MAX-ACCESS      read-only
    STATUS          current
    DESCRIPTION     
            "This counter keeps track of the number of signing requests 
             which have timeout for response Per Server Type."
    ::= { sonusSoftSwitchHTTPPerSvrTypeSignVerCountersEntry 5 }

sonusSoftSwitchHTTPPerSvrTypeSignVerCountersSigningQueryRetry OBJECT-TYPE
    SYNTAX          Counter32
    MAX-ACCESS      read-only
    STATUS          current
    DESCRIPTION     
            "This counter keeps track of the number of Signing requests
             which are retried from HTTP Client Process Per Server Type."
    ::= { sonusSoftSwitchHTTPPerSvrTypeSignVerCountersEntry 6 }

sonusSoftSwitchHTTPPerSvrTypeSignVerCountersVerQuerySent OBJECT-TYPE
    SYNTAX          Counter32
    MAX-ACCESS      read-only
    STATUS          current
    DESCRIPTION     
            "This counter keeps track of the number of Verification requests
             which are sent from HTTP Client Process."
    ::= { sonusSoftSwitchHTTPPerSvrTypeSignVerCountersEntry 7 }

sonusSoftSwitchHTTPPerSvrTypeSignVerCountersVerificationRsp OBJECT-TYPE
    SYNTAX          Counter32
    MAX-ACCESS      read-only
    STATUS          current
    DESCRIPTION     
            "This counter keeps track of the number of Verification responses
             which have been received by HTTP Client process."
    ::= { sonusSoftSwitchHTTPPerSvrTypeSignVerCountersEntry 8 }

sonusSoftSwitchHTTPPerSvrTypeSignVerCountersVerInvalidInput OBJECT-TYPE
    SYNTAX          Counter32
    MAX-ACCESS      read-only
    STATUS          current
    DESCRIPTION     
            "This counter keeps track of the number of Verification requests
             which failed due to invalid input."
    ::= { sonusSoftSwitchHTTPPerSvrTypeSignVerCountersEntry 9 }

sonusSoftSwitchHTTPPerSvrTypeSignVerCountersVerQueryTimeOut OBJECT-TYPE
    SYNTAX          Counter32
    MAX-ACCESS      read-only
    STATUS          current
    DESCRIPTION     
            "This counter keeps track of the number of Verification requests
             which have timeout for response."
    ::= { sonusSoftSwitchHTTPPerSvrTypeSignVerCountersEntry 10 }

sonusSoftSwitchHTTPPerSvrTypeSignVerCountersVerQueryRetry OBJECT-TYPE
    SYNTAX          Counter32
    MAX-ACCESS      read-only
    STATUS          current
    DESCRIPTION     
            "This counter keeps track of the number of Verification requests
             which are retried from HTTP Client Process."
    ::= { sonusSoftSwitchHTTPPerSvrTypeSignVerCountersEntry 11 }

sonusSoftSwitchHTTPPerSvrTypeFailureCounters OBJECT IDENTIFIER
    ::= { sonusSoftSwitchHTTPClientStatistics 9 }

sonusSoftSwitchHTTPPerSvrTypeFailureCountersTable OBJECT-TYPE
    SYNTAX          SEQUENCE OF SonusSoftSwitchHTTPPerSvrTypeFailureCountersEntry
    MAX-ACCESS      not-accessible
    STATUS          current
    DESCRIPTION     
            "HTTP Client Signing-Verification Failure Counters PER Server Type"
    ::= { sonusSoftSwitchHTTPPerSvrTypeFailureCounters 1 }

sonusSoftSwitchHTTPPerSvrTypeFailureCountersEntry OBJECT-TYPE
    SYNTAX          SonusSoftSwitchHTTPPerSvrTypeFailureCountersEntry
    MAX-ACCESS      not-accessible
    STATUS          current
    DESCRIPTION     
            "An entry of Traffic counters related to HTTP Client Verification Counters Per Server Type"
    INDEX           { 
                      sonusSoftSwitchHTTPPerSvrTypeFailureCountersServerName }
    ::= { sonusSoftSwitchHTTPPerSvrTypeFailureCountersTable 1 }

SonusSoftSwitchHTTPPerSvrTypeFailureCountersEntry ::=
    SEQUENCE {
        sonusSoftSwitchHTTPPerSvrTypeFailureCountersServerName                      DisplayString,
        sonusSoftSwitchHTTPPerSvrTypeFailureCountersSignFailureE3                         Counter32,
        sonusSoftSwitchHTTPPerSvrTypeFailureCountersSignFailureX1                         Counter32,
        sonusSoftSwitchHTTPPerSvrTypeFailureCountersSignFailureX2                         Counter32,
        sonusSoftSwitchHTTPPerSvrTypeFailureCountersSignFailureX3                         Counter32,
        sonusSoftSwitchHTTPPerSvrTypeFailureCountersSignFailureX4                         Counter32,
        sonusSoftSwitchHTTPPerSvrTypeFailureCountersSignFailure400                          Counter32,
        sonusSoftSwitchHTTPPerSvrTypeFailureCountersSignFailure404                          Counter32,
        sonusSoftSwitchHTTPPerSvrTypeFailureCountersSignFailure405                          Counter32,
        sonusSoftSwitchHTTPPerSvrTypeFailureCountersSignFailure406                          Counter32,
        sonusSoftSwitchHTTPPerSvrTypeFailureCountersSignFailure411                          Counter32,
        sonusSoftSwitchHTTPPerSvrTypeFailureCountersSignFailure415                          Counter32,
        sonusSoftSwitchHTTPPerSvrTypeFailureCountersSignFailure500                          Counter32,
        sonusSoftSwitchHTTPPerSvrTypeFailureCountersSignFailure503                          Counter32,
        sonusSoftSwitchHTTPPerSvrTypeFailureCountersSignFailureSVC4000                              Counter32,
        sonusSoftSwitchHTTPPerSvrTypeFailureCountersSignFailureSVC4001                              Counter32,
        sonusSoftSwitchHTTPPerSvrTypeFailureCountersSignFailureSVC4002                              Counter32,
        sonusSoftSwitchHTTPPerSvrTypeFailureCountersSignFailureSVC4003                              Counter32,
        sonusSoftSwitchHTTPPerSvrTypeFailureCountersSignFailureSVC4004                              Counter32,
        sonusSoftSwitchHTTPPerSvrTypeFailureCountersSignFailureSVC4005                              Counter32,
        sonusSoftSwitchHTTPPerSvrTypeFailureCountersSignFailureSVC4006                              Counter32,
        sonusSoftSwitchHTTPPerSvrTypeFailureCountersSignFailureSVC4007                              Counter32,
        sonusSoftSwitchHTTPPerSvrTypeFailureCountersSignFailurePOL4050                              Counter32,
        sonusSoftSwitchHTTPPerSvrTypeFailureCountersSignFailurePOL5000                              Counter32,
        sonusSoftSwitchHTTPPerSvrTypeFailureCountersVerFailureE3                        Counter32,
        sonusSoftSwitchHTTPPerSvrTypeFailureCountersVerFailureE4                        Counter32,
        sonusSoftSwitchHTTPPerSvrTypeFailureCountersVerFailureE5                        Counter32,
        sonusSoftSwitchHTTPPerSvrTypeFailureCountersVerFailureE6                        Counter32,
        sonusSoftSwitchHTTPPerSvrTypeFailureCountersVerFailureE7                        Counter32,
        sonusSoftSwitchHTTPPerSvrTypeFailureCountersVerFailureE8                        Counter32,
        sonusSoftSwitchHTTPPerSvrTypeFailureCountersVerFailureE9                        Counter32,
        sonusSoftSwitchHTTPPerSvrTypeFailureCountersVerFailureE10                         Counter32,
        sonusSoftSwitchHTTPPerSvrTypeFailureCountersVerFailureE11                         Counter32,
        sonusSoftSwitchHTTPPerSvrTypeFailureCountersVerFailureE12                         Counter32,
        sonusSoftSwitchHTTPPerSvrTypeFailureCountersVerFailureE13                         Counter32,
        sonusSoftSwitchHTTPPerSvrTypeFailureCountersVerFailureE14                         Counter32,
        sonusSoftSwitchHTTPPerSvrTypeFailureCountersVerFailureE15                         Counter32,
        sonusSoftSwitchHTTPPerSvrTypeFailureCountersVerFailureE16                         Counter32,
        sonusSoftSwitchHTTPPerSvrTypeFailureCountersVerFailureE17                         Counter32,
        sonusSoftSwitchHTTPPerSvrTypeFailureCountersVerFailureE18                         Counter32,
        sonusSoftSwitchHTTPPerSvrTypeFailureCountersVerFailureE19                         Counter32,
        sonusSoftSwitchHTTPPerSvrTypeFailureCountersVerFailureE20                         Counter32,
        sonusSoftSwitchHTTPPerSvrTypeFailureCountersVerFailureE21                         Counter32,
        sonusSoftSwitchHTTPPerSvrTypeFailureCountersVerFailureE22                         Counter32,
        sonusSoftSwitchHTTPPerSvrTypeFailureCountersVerFailureE23                         Counter32,
        sonusSoftSwitchHTTPPerSvrTypeFailureCountersVerFailureX1                        Counter32,
        sonusSoftSwitchHTTPPerSvrTypeFailureCountersVerFailureX2                        Counter32,
        sonusSoftSwitchHTTPPerSvrTypeFailureCountersVerFailureX3                        Counter32,
        sonusSoftSwitchHTTPPerSvrTypeFailureCountersVerFailureX4                        Counter32,
        sonusSoftSwitchHTTPPerSvrTypeFailureCountersVerFailure400                         Counter32,
        sonusSoftSwitchHTTPPerSvrTypeFailureCountersVerFailure404                         Counter32,
        sonusSoftSwitchHTTPPerSvrTypeFailureCountersVerFailure405                         Counter32,
        sonusSoftSwitchHTTPPerSvrTypeFailureCountersVerFailure406                         Counter32,
        sonusSoftSwitchHTTPPerSvrTypeFailureCountersVerFailure411                         Counter32,
        sonusSoftSwitchHTTPPerSvrTypeFailureCountersVerFailure415                         Counter32,
        sonusSoftSwitchHTTPPerSvrTypeFailureCountersVerFailure500                         Counter32,
        sonusSoftSwitchHTTPPerSvrTypeFailureCountersVerFailure503                         Counter32,
        sonusSoftSwitchHTTPPerSvrTypeFailureCountersVerFailureSVC4000                             Counter32,
        sonusSoftSwitchHTTPPerSvrTypeFailureCountersVerFailureSVC4001                             Counter32,
        sonusSoftSwitchHTTPPerSvrTypeFailureCountersVerFailureSVC4002                             Counter32,
        sonusSoftSwitchHTTPPerSvrTypeFailureCountersVerFailureSVC4003                             Counter32,
        sonusSoftSwitchHTTPPerSvrTypeFailureCountersVerFailureSVC4004                             Counter32,
        sonusSoftSwitchHTTPPerSvrTypeFailureCountersVerFailureSVC4005                             Counter32,
        sonusSoftSwitchHTTPPerSvrTypeFailureCountersVerFailureSVC4006                             Counter32,
        sonusSoftSwitchHTTPPerSvrTypeFailureCountersVerFailureSVC4007                             Counter32,
        sonusSoftSwitchHTTPPerSvrTypeFailureCountersVerFailurePOL4050                             Counter32,
        sonusSoftSwitchHTTPPerSvrTypeFailureCountersVerFailurePOL5000                             Counter32
    }

sonusSoftSwitchHTTPPerSvrTypeFailureCountersServerName OBJECT-TYPE
    SYNTAX          DisplayString
    MAX-ACCESS      read-only
    STATUS          current
    DESCRIPTION     
            "Server Type Name."
    ::= { sonusSoftSwitchHTTPPerSvrTypeFailureCountersEntry 1 }

sonusSoftSwitchHTTPPerSvrTypeFailureCountersSignFailureE3 OBJECT-TYPE
    SYNTAX          Counter32
    MAX-ACCESS      read-only
    STATUS          current
    DESCRIPTION     
            "This counter keeps track of the number of E3 error 
             received from signing server per server type."
    ::= { sonusSoftSwitchHTTPPerSvrTypeFailureCountersEntry 2 }

sonusSoftSwitchHTTPPerSvrTypeFailureCountersSignFailureX1 OBJECT-TYPE
    SYNTAX          Counter32
    MAX-ACCESS      read-only
    STATUS          current
    DESCRIPTION     
            "This counter keeps track of the number of X1 error 
             received from signing server per server type."
    ::= { sonusSoftSwitchHTTPPerSvrTypeFailureCountersEntry 3 }

sonusSoftSwitchHTTPPerSvrTypeFailureCountersSignFailureX2 OBJECT-TYPE
    SYNTAX          Counter32
    MAX-ACCESS      read-only
    STATUS          current
    DESCRIPTION     
            "This counter keeps track of the number of X2 error 
             received from signing server per server type."
    ::= { sonusSoftSwitchHTTPPerSvrTypeFailureCountersEntry 4 }

sonusSoftSwitchHTTPPerSvrTypeFailureCountersSignFailureX3 OBJECT-TYPE
    SYNTAX          Counter32
    MAX-ACCESS      read-only
    STATUS          current
    DESCRIPTION     
            "This counter keeps track of the number of X3 error 
             received from signing server per server type."
    ::= { sonusSoftSwitchHTTPPerSvrTypeFailureCountersEntry 5 }

sonusSoftSwitchHTTPPerSvrTypeFailureCountersSignFailureX4 OBJECT-TYPE
    SYNTAX          Counter32
    MAX-ACCESS      read-only
    STATUS          current
    DESCRIPTION     
            "This counter keeps track of the number of X4 error 
             received from signing server per server type."
    ::= { sonusSoftSwitchHTTPPerSvrTypeFailureCountersEntry 6 }

sonusSoftSwitchHTTPPerSvrTypeFailureCountersSignFailure400 OBJECT-TYPE
    SYNTAX          Counter32
    MAX-ACCESS      read-only
    STATUS          current
    DESCRIPTION     
            "This counter keeps track of the number of 400 error
             received from signing server per server type."
    ::= { sonusSoftSwitchHTTPPerSvrTypeFailureCountersEntry 7 }

sonusSoftSwitchHTTPPerSvrTypeFailureCountersSignFailure404 OBJECT-TYPE
    SYNTAX          Counter32
    MAX-ACCESS      read-only
    STATUS          current
    DESCRIPTION     
            "This counter keeps track of the number of 404 error
             received from signing server per server type."
    ::= { sonusSoftSwitchHTTPPerSvrTypeFailureCountersEntry 8 }

sonusSoftSwitchHTTPPerSvrTypeFailureCountersSignFailure405 OBJECT-TYPE
    SYNTAX          Counter32
    MAX-ACCESS      read-only
    STATUS          current
    DESCRIPTION     
            "This counter keeps track of the number of 405 error
             received from signing server per server type."
    ::= { sonusSoftSwitchHTTPPerSvrTypeFailureCountersEntry 9 }

sonusSoftSwitchHTTPPerSvrTypeFailureCountersSignFailure406 OBJECT-TYPE
    SYNTAX          Counter32
    MAX-ACCESS      read-only
    STATUS          current
    DESCRIPTION     
            "This counter keeps track of the number of 406 error
             received from signing server per server type."
    ::= { sonusSoftSwitchHTTPPerSvrTypeFailureCountersEntry 10 }

sonusSoftSwitchHTTPPerSvrTypeFailureCountersSignFailure411 OBJECT-TYPE
    SYNTAX          Counter32
    MAX-ACCESS      read-only
    STATUS          current
    DESCRIPTION     
            "This counter keeps track of the number of 411 error
             received from signing server per server type."
    ::= { sonusSoftSwitchHTTPPerSvrTypeFailureCountersEntry 11 }

sonusSoftSwitchHTTPPerSvrTypeFailureCountersSignFailure415 OBJECT-TYPE
    SYNTAX          Counter32
    MAX-ACCESS      read-only
    STATUS          current
    DESCRIPTION     
            "This counter keeps track of the number of 415 error
             received from signing server per server type."
    ::= { sonusSoftSwitchHTTPPerSvrTypeFailureCountersEntry 12 }

sonusSoftSwitchHTTPPerSvrTypeFailureCountersSignFailure500 OBJECT-TYPE
    SYNTAX          Counter32
    MAX-ACCESS      read-only
    STATUS          current
    DESCRIPTION     
            "This counter keeps track of the number of 500 error 
             received from signing server per server type."
    ::= { sonusSoftSwitchHTTPPerSvrTypeFailureCountersEntry 13 }

sonusSoftSwitchHTTPPerSvrTypeFailureCountersSignFailure503 OBJECT-TYPE
    SYNTAX          Counter32
    MAX-ACCESS      read-only
    STATUS          current
    DESCRIPTION     
            "This counter keeps track of the number of 503 error 
             received from signing server per server type."
    ::= { sonusSoftSwitchHTTPPerSvrTypeFailureCountersEntry 14 }

sonusSoftSwitchHTTPPerSvrTypeFailureCountersSignFailureSVC4000 OBJECT-TYPE
    SYNTAX          Counter32
    MAX-ACCESS      read-only
    STATUS          current
    DESCRIPTION     
            "This counter keeps track of the number of service exception 4000 error
             received from signing server per server type."
    ::= { sonusSoftSwitchHTTPPerSvrTypeFailureCountersEntry 15 }

sonusSoftSwitchHTTPPerSvrTypeFailureCountersSignFailureSVC4001 OBJECT-TYPE
    SYNTAX          Counter32
    MAX-ACCESS      read-only
    STATUS          current
    DESCRIPTION     
            "This counter keeps track of the number of service exception 4001 error
             received from signing server per server type."
    ::= { sonusSoftSwitchHTTPPerSvrTypeFailureCountersEntry 16 }

sonusSoftSwitchHTTPPerSvrTypeFailureCountersSignFailureSVC4002 OBJECT-TYPE
    SYNTAX          Counter32
    MAX-ACCESS      read-only
    STATUS          current
    DESCRIPTION     
            "This counter keeps track of the number of service exception 4002 error
             received from signing server per server type."
    ::= { sonusSoftSwitchHTTPPerSvrTypeFailureCountersEntry 17 }

sonusSoftSwitchHTTPPerSvrTypeFailureCountersSignFailureSVC4003 OBJECT-TYPE
    SYNTAX          Counter32
    MAX-ACCESS      read-only
    STATUS          current
    DESCRIPTION     
            "This counter keeps track of the number of service exception 4003 error
             received from signing server per server type."
    ::= { sonusSoftSwitchHTTPPerSvrTypeFailureCountersEntry 18 }

sonusSoftSwitchHTTPPerSvrTypeFailureCountersSignFailureSVC4004 OBJECT-TYPE
    SYNTAX          Counter32
    MAX-ACCESS      read-only
    STATUS          current
    DESCRIPTION     
            "This counter keeps track of the number of service exception 4004 error
             received from signing server per server type."
    ::= { sonusSoftSwitchHTTPPerSvrTypeFailureCountersEntry 19 }

sonusSoftSwitchHTTPPerSvrTypeFailureCountersSignFailureSVC4005 OBJECT-TYPE
    SYNTAX          Counter32
    MAX-ACCESS      read-only
    STATUS          current
    DESCRIPTION     
            "This counter keeps track of the number of service exception 4005 error
             received from signing server per server type."
    ::= { sonusSoftSwitchHTTPPerSvrTypeFailureCountersEntry 20 }

sonusSoftSwitchHTTPPerSvrTypeFailureCountersSignFailureSVC4006 OBJECT-TYPE
    SYNTAX          Counter32
    MAX-ACCESS      read-only
    STATUS          current
    DESCRIPTION     
            "This counter keeps track of the number of service exception 4006 error
             received from signing server per server type."
    ::= { sonusSoftSwitchHTTPPerSvrTypeFailureCountersEntry 21 }

sonusSoftSwitchHTTPPerSvrTypeFailureCountersSignFailureSVC4007 OBJECT-TYPE
    SYNTAX          Counter32
    MAX-ACCESS      read-only
    STATUS          current
    DESCRIPTION     
            "This counter keeps track of the number of service exception 4007 error
             received from signing server per server type."
    ::= { sonusSoftSwitchHTTPPerSvrTypeFailureCountersEntry 22 }

sonusSoftSwitchHTTPPerSvrTypeFailureCountersSignFailurePOL4050 OBJECT-TYPE
    SYNTAX          Counter32
    MAX-ACCESS      read-only
    STATUS          current
    DESCRIPTION     
            "This counter keeps track of the number of policy exception 4050 error
             received from signing server per server type."
    ::= { sonusSoftSwitchHTTPPerSvrTypeFailureCountersEntry 23 }

sonusSoftSwitchHTTPPerSvrTypeFailureCountersSignFailurePOL5000 OBJECT-TYPE
    SYNTAX          Counter32
    MAX-ACCESS      read-only
    STATUS          current
    DESCRIPTION     
            "This counter keeps track of the number of policy exception 5000 error
             received from signing server per server type."
    ::= { sonusSoftSwitchHTTPPerSvrTypeFailureCountersEntry 24 }

sonusSoftSwitchHTTPPerSvrTypeFailureCountersVerFailureE3 OBJECT-TYPE
    SYNTAX          Counter32
    MAX-ACCESS      read-only
    STATUS          current
    DESCRIPTION     
            "This counter keeps track of the number of E3 error
             received from verification server per server type."
    ::= { sonusSoftSwitchHTTPPerSvrTypeFailureCountersEntry 25 }

sonusSoftSwitchHTTPPerSvrTypeFailureCountersVerFailureE4 OBJECT-TYPE
    SYNTAX          Counter32
    MAX-ACCESS      read-only
    STATUS          current
    DESCRIPTION     
            "This counter keeps track of the number of E4 error
             received from verification server per server type."
    ::= { sonusSoftSwitchHTTPPerSvrTypeFailureCountersEntry 26 }

sonusSoftSwitchHTTPPerSvrTypeFailureCountersVerFailureE5 OBJECT-TYPE
    SYNTAX          Counter32
    MAX-ACCESS      read-only
    STATUS          current
    DESCRIPTION     
            "This counter keeps track of the number of E5 error
             received from verification server per server type."
    ::= { sonusSoftSwitchHTTPPerSvrTypeFailureCountersEntry 27 }

sonusSoftSwitchHTTPPerSvrTypeFailureCountersVerFailureE6 OBJECT-TYPE
    SYNTAX          Counter32
    MAX-ACCESS      read-only
    STATUS          current
    DESCRIPTION     
            "This counter keeps track of the number of E6 error
             received from verification server per server type."
    ::= { sonusSoftSwitchHTTPPerSvrTypeFailureCountersEntry 28 }

sonusSoftSwitchHTTPPerSvrTypeFailureCountersVerFailureE7 OBJECT-TYPE
    SYNTAX          Counter32
    MAX-ACCESS      read-only
    STATUS          current
    DESCRIPTION     
            "This counter keeps track of the number of E7 error
             received from verification server per server type."
    ::= { sonusSoftSwitchHTTPPerSvrTypeFailureCountersEntry 29 }

sonusSoftSwitchHTTPPerSvrTypeFailureCountersVerFailureE8 OBJECT-TYPE
    SYNTAX          Counter32
    MAX-ACCESS      read-only
    STATUS          current
    DESCRIPTION     
            "This counter keeps track of the number of E8 error
             received from verification server per server type."
    ::= { sonusSoftSwitchHTTPPerSvrTypeFailureCountersEntry 30 }

sonusSoftSwitchHTTPPerSvrTypeFailureCountersVerFailureE9 OBJECT-TYPE
    SYNTAX          Counter32
    MAX-ACCESS      read-only
    STATUS          current
    DESCRIPTION     
            "This counter keeps track of the number of E9 error
             received from verification server per server type."
    ::= { sonusSoftSwitchHTTPPerSvrTypeFailureCountersEntry 31 }

sonusSoftSwitchHTTPPerSvrTypeFailureCountersVerFailureE10 OBJECT-TYPE
    SYNTAX          Counter32
    MAX-ACCESS      read-only
    STATUS          current
    DESCRIPTION     
            "This counter keeps track of the number of E10 error
             received from verification server per server type."
    ::= { sonusSoftSwitchHTTPPerSvrTypeFailureCountersEntry 32 }

sonusSoftSwitchHTTPPerSvrTypeFailureCountersVerFailureE11 OBJECT-TYPE
    SYNTAX          Counter32
    MAX-ACCESS      read-only
    STATUS          current
    DESCRIPTION     
            "This counter keeps track of the number of E11 error
             received from verification server per server type."
    ::= { sonusSoftSwitchHTTPPerSvrTypeFailureCountersEntry 33 }

sonusSoftSwitchHTTPPerSvrTypeFailureCountersVerFailureE12 OBJECT-TYPE
    SYNTAX          Counter32
    MAX-ACCESS      read-only
    STATUS          current
    DESCRIPTION     
            "This counter keeps track of the number of E12 error
             received from verification server per server type."
    ::= { sonusSoftSwitchHTTPPerSvrTypeFailureCountersEntry 34 }

sonusSoftSwitchHTTPPerSvrTypeFailureCountersVerFailureE13 OBJECT-TYPE
    SYNTAX          Counter32
    MAX-ACCESS      read-only
    STATUS          current
    DESCRIPTION     
            "This counter keeps track of the number of E13 error
             received from verification server per server type."
    ::= { sonusSoftSwitchHTTPPerSvrTypeFailureCountersEntry 35 }

sonusSoftSwitchHTTPPerSvrTypeFailureCountersVerFailureE14 OBJECT-TYPE
    SYNTAX          Counter32
    MAX-ACCESS      read-only
    STATUS          current
    DESCRIPTION     
            "This counter keeps track of the number of E14 error
             received from verification server per server type ."
    ::= { sonusSoftSwitchHTTPPerSvrTypeFailureCountersEntry 36 }

sonusSoftSwitchHTTPPerSvrTypeFailureCountersVerFailureE15 OBJECT-TYPE
    SYNTAX          Counter32
    MAX-ACCESS      read-only
    STATUS          current
    DESCRIPTION     
            "This counter keeps track of the number of E15 error
             received from verification server per server type."
    ::= { sonusSoftSwitchHTTPPerSvrTypeFailureCountersEntry 37 }

sonusSoftSwitchHTTPPerSvrTypeFailureCountersVerFailureE16 OBJECT-TYPE
    SYNTAX          Counter32
    MAX-ACCESS      read-only
    STATUS          current
    DESCRIPTION     
            "This counter keeps track of the number of E16 error
             received from verification server per server type."
    ::= { sonusSoftSwitchHTTPPerSvrTypeFailureCountersEntry 38 }

sonusSoftSwitchHTTPPerSvrTypeFailureCountersVerFailureE17 OBJECT-TYPE
    SYNTAX          Counter32
    MAX-ACCESS      read-only
    STATUS          current
    DESCRIPTION     
            "This counter keeps track of the number of E17 error
             received from verification server per server type."
    ::= { sonusSoftSwitchHTTPPerSvrTypeFailureCountersEntry 39 }

sonusSoftSwitchHTTPPerSvrTypeFailureCountersVerFailureE18 OBJECT-TYPE
    SYNTAX          Counter32
    MAX-ACCESS      read-only
    STATUS          current
    DESCRIPTION     
            "This counter keeps track of the number of E18 error
             received from verification server per server type."
    ::= { sonusSoftSwitchHTTPPerSvrTypeFailureCountersEntry 40 }

sonusSoftSwitchHTTPPerSvrTypeFailureCountersVerFailureE19 OBJECT-TYPE
    SYNTAX          Counter32
    MAX-ACCESS      read-only
    STATUS          current
    DESCRIPTION     
            "This counter keeps track of the number of E19 error
             received from verification server per server type."
    ::= { sonusSoftSwitchHTTPPerSvrTypeFailureCountersEntry 41 }

sonusSoftSwitchHTTPPerSvrTypeFailureCountersVerFailureE20 OBJECT-TYPE
    SYNTAX          Counter32
    MAX-ACCESS      read-only
    STATUS          current
    DESCRIPTION     
            "This counter keeps track of the number of E20 error
             received from verification server per server type."
    ::= { sonusSoftSwitchHTTPPerSvrTypeFailureCountersEntry 42 }

sonusSoftSwitchHTTPPerSvrTypeFailureCountersVerFailureE21 OBJECT-TYPE
    SYNTAX          Counter32
    MAX-ACCESS      read-only
    STATUS          current
    DESCRIPTION     
            "This counter keeps track of the number of E21 error
             received from verification server per server type."
    ::= { sonusSoftSwitchHTTPPerSvrTypeFailureCountersEntry 43 }

sonusSoftSwitchHTTPPerSvrTypeFailureCountersVerFailureE22 OBJECT-TYPE
    SYNTAX          Counter32
    MAX-ACCESS      read-only
    STATUS          current
    DESCRIPTION     
            "This counter keeps track of the number of E22 error
             received from verification server per server type."
    ::= { sonusSoftSwitchHTTPPerSvrTypeFailureCountersEntry 44 }

sonusSoftSwitchHTTPPerSvrTypeFailureCountersVerFailureE23 OBJECT-TYPE
    SYNTAX          Counter32
    MAX-ACCESS      read-only
    STATUS          current
    DESCRIPTION     
            "This counter keeps track of the number of E23 error
             received from verification server per server type."
    ::= { sonusSoftSwitchHTTPPerSvrTypeFailureCountersEntry 45 }

sonusSoftSwitchHTTPPerSvrTypeFailureCountersVerFailureX1 OBJECT-TYPE
    SYNTAX          Counter32
    MAX-ACCESS      read-only
    STATUS          current
    DESCRIPTION     
            "This counter keeps track of the number of X1 error
             received from verification server per server type."
    ::= { sonusSoftSwitchHTTPPerSvrTypeFailureCountersEntry 46 }

sonusSoftSwitchHTTPPerSvrTypeFailureCountersVerFailureX2 OBJECT-TYPE
    SYNTAX          Counter32
    MAX-ACCESS      read-only
    STATUS          current
    DESCRIPTION     
            "This counter keeps track of the number of X2 error
             received from verification server per server type."
    ::= { sonusSoftSwitchHTTPPerSvrTypeFailureCountersEntry 47 }

sonusSoftSwitchHTTPPerSvrTypeFailureCountersVerFailureX3 OBJECT-TYPE
    SYNTAX          Counter32
    MAX-ACCESS      read-only
    STATUS          current
    DESCRIPTION     
            "This counter keeps track of the number of X3 error
             received from verification server per server type."
    ::= { sonusSoftSwitchHTTPPerSvrTypeFailureCountersEntry 48 }

sonusSoftSwitchHTTPPerSvrTypeFailureCountersVerFailureX4 OBJECT-TYPE
    SYNTAX          Counter32
    MAX-ACCESS      read-only
    STATUS          current
    DESCRIPTION     
            "This counter keeps track of the number of X4 error
             received from verification server per server type."
    ::= { sonusSoftSwitchHTTPPerSvrTypeFailureCountersEntry 49 }

sonusSoftSwitchHTTPPerSvrTypeFailureCountersVerFailure400 OBJECT-TYPE
    SYNTAX          Counter32
    MAX-ACCESS      read-only
    STATUS          current
    DESCRIPTION     
            "This counter keeps track of the number of 400 error
             received from verification server per server type."
    ::= { sonusSoftSwitchHTTPPerSvrTypeFailureCountersEntry 50 }

sonusSoftSwitchHTTPPerSvrTypeFailureCountersVerFailure404 OBJECT-TYPE
    SYNTAX          Counter32
    MAX-ACCESS      read-only
    STATUS          current
    DESCRIPTION     
            "This counter keeps track of the number of 404 error
             received from verification server per server type."
    ::= { sonusSoftSwitchHTTPPerSvrTypeFailureCountersEntry 51 }

sonusSoftSwitchHTTPPerSvrTypeFailureCountersVerFailure405 OBJECT-TYPE
    SYNTAX          Counter32
    MAX-ACCESS      read-only
    STATUS          current
    DESCRIPTION     
            "This counter keeps track of the number of 405 error
             received from verification server per server type."
    ::= { sonusSoftSwitchHTTPPerSvrTypeFailureCountersEntry 52 }

sonusSoftSwitchHTTPPerSvrTypeFailureCountersVerFailure406 OBJECT-TYPE
    SYNTAX          Counter32
    MAX-ACCESS      read-only
    STATUS          current
    DESCRIPTION     
            "This counter keeps track of the number of 406 error
             received from verification server per server type."
    ::= { sonusSoftSwitchHTTPPerSvrTypeFailureCountersEntry 53 }

sonusSoftSwitchHTTPPerSvrTypeFailureCountersVerFailure411 OBJECT-TYPE
    SYNTAX          Counter32
    MAX-ACCESS      read-only
    STATUS          current
    DESCRIPTION     
            "This counter keeps track of the number of 411 error
             received from verification server per server type."
    ::= { sonusSoftSwitchHTTPPerSvrTypeFailureCountersEntry 54 }

sonusSoftSwitchHTTPPerSvrTypeFailureCountersVerFailure415 OBJECT-TYPE
    SYNTAX          Counter32
    MAX-ACCESS      read-only
    STATUS          current
    DESCRIPTION     
            "This counter keeps track of the number of 415 error
             received from verification server per server type."
    ::= { sonusSoftSwitchHTTPPerSvrTypeFailureCountersEntry 55 }

sonusSoftSwitchHTTPPerSvrTypeFailureCountersVerFailure500 OBJECT-TYPE
    SYNTAX          Counter32
    MAX-ACCESS      read-only
    STATUS          current
    DESCRIPTION     
            "This counter keeps track of the number of 500 error
             received from verification server per server type."
    ::= { sonusSoftSwitchHTTPPerSvrTypeFailureCountersEntry 56 }

sonusSoftSwitchHTTPPerSvrTypeFailureCountersVerFailure503 OBJECT-TYPE
    SYNTAX          Counter32
    MAX-ACCESS      read-only
    STATUS          current
    DESCRIPTION     
            "This counter keeps track of the number of 503 error
             received from verification server per server type."
    ::= { sonusSoftSwitchHTTPPerSvrTypeFailureCountersEntry 57 }

sonusSoftSwitchHTTPPerSvrTypeFailureCountersVerFailureSVC4000 OBJECT-TYPE
    SYNTAX          Counter32
    MAX-ACCESS      read-only
    STATUS          current
    DESCRIPTION     
            "This counter keeps track of the number of service exception 4000 error
             received from verification server per server type."
    ::= { sonusSoftSwitchHTTPPerSvrTypeFailureCountersEntry 58 }

sonusSoftSwitchHTTPPerSvrTypeFailureCountersVerFailureSVC4001 OBJECT-TYPE
    SYNTAX          Counter32
    MAX-ACCESS      read-only
    STATUS          current
    DESCRIPTION     
            "This counter keeps track of the number of service exception 4001 error
             received from verification server per server type."
    ::= { sonusSoftSwitchHTTPPerSvrTypeFailureCountersEntry 59 }

sonusSoftSwitchHTTPPerSvrTypeFailureCountersVerFailureSVC4002 OBJECT-TYPE
    SYNTAX          Counter32
    MAX-ACCESS      read-only
    STATUS          current
    DESCRIPTION     
            "This counter keeps track of the number of service exception 4002 error
             received from verification server per server type."
    ::= { sonusSoftSwitchHTTPPerSvrTypeFailureCountersEntry 60 }

sonusSoftSwitchHTTPPerSvrTypeFailureCountersVerFailureSVC4003 OBJECT-TYPE
    SYNTAX          Counter32
    MAX-ACCESS      read-only
    STATUS          current
    DESCRIPTION     
            "This counter keeps track of the number of service exception 4003 error
             received from verification server per server type."
    ::= { sonusSoftSwitchHTTPPerSvrTypeFailureCountersEntry 61 }

sonusSoftSwitchHTTPPerSvrTypeFailureCountersVerFailureSVC4004 OBJECT-TYPE
    SYNTAX          Counter32
    MAX-ACCESS      read-only
    STATUS          current
    DESCRIPTION     
            "This counter keeps track of the number of service exception 4004 error
             received from verification server per server type."
    ::= { sonusSoftSwitchHTTPPerSvrTypeFailureCountersEntry 62 }

sonusSoftSwitchHTTPPerSvrTypeFailureCountersVerFailureSVC4005 OBJECT-TYPE
    SYNTAX          Counter32
    MAX-ACCESS      read-only
    STATUS          current
    DESCRIPTION     
            "This counter keeps track of the number of service exception 4005 error
             received from verification server per server type."
    ::= { sonusSoftSwitchHTTPPerSvrTypeFailureCountersEntry 63 }

sonusSoftSwitchHTTPPerSvrTypeFailureCountersVerFailureSVC4006 OBJECT-TYPE
    SYNTAX          Counter32
    MAX-ACCESS      read-only
    STATUS          current
    DESCRIPTION     
            "This counter keeps track of the number of service exception 4006 error
             received from verification server per server type."
    ::= { sonusSoftSwitchHTTPPerSvrTypeFailureCountersEntry 64 }

sonusSoftSwitchHTTPPerSvrTypeFailureCountersVerFailureSVC4007 OBJECT-TYPE
    SYNTAX          Counter32
    MAX-ACCESS      read-only
    STATUS          current
    DESCRIPTION     
            "This counter keeps track of the number of service exception 4007 error
             received from verification server per server type."
    ::= { sonusSoftSwitchHTTPPerSvrTypeFailureCountersEntry 65 }

sonusSoftSwitchHTTPPerSvrTypeFailureCountersVerFailurePOL4050 OBJECT-TYPE
    SYNTAX          Counter32
    MAX-ACCESS      read-only
    STATUS          current
    DESCRIPTION     
            "This counter keeps track of the number of policy exception 4050 error
             received from verification server per server type."
    ::= { sonusSoftSwitchHTTPPerSvrTypeFailureCountersEntry 66 }

sonusSoftSwitchHTTPPerSvrTypeFailureCountersVerFailurePOL5000 OBJECT-TYPE
    SYNTAX          Counter32
    MAX-ACCESS      read-only
    STATUS          current
    DESCRIPTION     
            "This counter keeps track of the number of policy exception 5000 error
             received from verification server per server type."
    ::= { sonusSoftSwitchHTTPPerSvrTypeFailureCountersEntry 67 }

sonusSoftSwitchHTTPPerSvrTypeInternalCounters OBJECT IDENTIFIER
    ::= { sonusSoftSwitchHTTPClientStatistics 10 }

sonusSoftSwitchHTTPPerSvrTypeInternalCountersTable OBJECT-TYPE
    SYNTAX          SEQUENCE OF SonusSoftSwitchHTTPPerSvrTypeInternalCountersEntry
    MAX-ACCESS      not-accessible
    STATUS          current
    DESCRIPTION     
            "HTTP Client Internal Counters Per Server Type"
    ::= { sonusSoftSwitchHTTPPerSvrTypeInternalCounters 1 }

sonusSoftSwitchHTTPPerSvrTypeInternalCountersEntry OBJECT-TYPE
    SYNTAX          SonusSoftSwitchHTTPPerSvrTypeInternalCountersEntry
    MAX-ACCESS      not-accessible
    STATUS          current
    DESCRIPTION     
            "An entry of Traffic counters related to HTTPC Client Servers"
    INDEX           { 
                      sonusSoftSwitchHTTPPerSvrTypeInternalCountersServerName }
    ::= { sonusSoftSwitchHTTPPerSvrTypeInternalCountersTable 1 }

SonusSoftSwitchHTTPPerSvrTypeInternalCountersEntry ::=
    SEQUENCE {
        sonusSoftSwitchHTTPPerSvrTypeInternalCountersServerName                       DisplayString,
        sonusSoftSwitchHTTPPerSvrTypeInternalCountersNoConnAvailable                            Counter32,
        sonusSoftSwitchHTTPPerSvrTypeInternalCountersJsonError                      Counter32,
        sonusSoftSwitchHTTPPerSvrTypeInternalCountersCurlError                      Counter32,
        sonusSoftSwitchHTTPPerSvrTypeInternalCountersMaxRetriesExhausted                                Counter32,
        sonusSoftSwitchHTTPPerSvrTypeInternalCountersGeneralFailure                           Counter32
    }

sonusSoftSwitchHTTPPerSvrTypeInternalCountersServerName OBJECT-TYPE
    SYNTAX          DisplayString
    MAX-ACCESS      read-only
    STATUS          current
    DESCRIPTION     
            "Server Type Name."
    ::= { sonusSoftSwitchHTTPPerSvrTypeInternalCountersEntry 1 }

sonusSoftSwitchHTTPPerSvrTypeInternalCountersNoConnAvailable OBJECT-TYPE
    SYNTAX          Counter32
    MAX-ACCESS      read-only
    STATUS          current
    DESCRIPTION     
            "This counter keeps track of the number of errors with no connection available Per Server Type."
    ::= { sonusSoftSwitchHTTPPerSvrTypeInternalCountersEntry 2 }

sonusSoftSwitchHTTPPerSvrTypeInternalCountersJsonError OBJECT-TYPE
    SYNTAX          Counter32
    MAX-ACCESS      read-only
    STATUS          current
    DESCRIPTION     
            "This counter keeps track of the number of JSON Error Per Server Type."
    ::= { sonusSoftSwitchHTTPPerSvrTypeInternalCountersEntry 3 }

sonusSoftSwitchHTTPPerSvrTypeInternalCountersCurlError OBJECT-TYPE
    SYNTAX          Counter32
    MAX-ACCESS      read-only
    STATUS          current
    DESCRIPTION     
            "This counter keeps track of the number of HTTP Error Per Server Type."
    ::= { sonusSoftSwitchHTTPPerSvrTypeInternalCountersEntry 4 }

sonusSoftSwitchHTTPPerSvrTypeInternalCountersMaxRetriesExhausted OBJECT-TYPE
    SYNTAX          Counter32
    MAX-ACCESS      read-only
    STATUS          current
    DESCRIPTION     
            "This counter keeps track of the number of failures due to Max Retries Exhausted Per Server Type."
    ::= { sonusSoftSwitchHTTPPerSvrTypeInternalCountersEntry 5 }

sonusSoftSwitchHTTPPerSvrTypeInternalCountersGeneralFailure OBJECT-TYPE
    SYNTAX          Counter32
    MAX-ACCESS      read-only
    STATUS          current
    DESCRIPTION     
            "This counter keeps track of the number of General Failure Per Server Type."
    ::= { sonusSoftSwitchHTTPPerSvrTypeInternalCountersEntry 6 }

sonusSoftSwitchHTTPClientRESTServiceCounters OBJECT IDENTIFIER
    ::= { sonusSoftSwitchHTTPClientStatistics 11 }

sonusSoftSwitchHTTPRESTServiceQuerySentCounters OBJECT-TYPE
    SYNTAX          Counter32
    MAX-ACCESS      read-only
    STATUS          current
    DESCRIPTION     
            "This counter keeps track of the number of REST Service requests
             which are sent from HTTP Client Process."
    ::= { sonusSoftSwitchHTTPClientRESTServiceCounters 1 }

sonusSoftSwitchHTTPRESTServiceRspCounters OBJECT-TYPE
    SYNTAX          Counter32
    MAX-ACCESS      read-only
    STATUS          current
    DESCRIPTION     
            "This counter keeps track of the number of REST Service responses
             which have been received by HTTP Client process."
    ::= { sonusSoftSwitchHTTPClientRESTServiceCounters 2 }

sonusSoftSwitchHTTPRESTServiceQueryTimeOutCounters OBJECT-TYPE
    SYNTAX          Counter32
    MAX-ACCESS      read-only
    STATUS          current
    DESCRIPTION     
            "This counter keeps track of the number of REST Service requests
             which have timeout for response."
    ::= { sonusSoftSwitchHTTPClientRESTServiceCounters 3 }

sonusSoftSwitchHTTPRESTServiceQueryRetryCounters OBJECT-TYPE
    SYNTAX          Counter32
    MAX-ACCESS      read-only
    STATUS          current
    DESCRIPTION     
            "This counter keeps track of the number of REST Service requests
             which are retried from HTTP Client Process."
    ::= { sonusSoftSwitchHTTPClientRESTServiceCounters 4 }

sonusSoftSwitchHTTPClientRESTServiceFailureCounters OBJECT IDENTIFIER
    ::= { sonusSoftSwitchHTTPClientStatistics 12 }

sonusSoftSwitchHTTPRESTServiceFailure400Counters OBJECT-TYPE
    SYNTAX          Counter32
    MAX-ACCESS      read-only
    STATUS          current
    DESCRIPTION     
            "This counter keeps track of the number of 400 error
             received from REST Service server."
    ::= { sonusSoftSwitchHTTPClientRESTServiceFailureCounters 1 }

sonusSoftSwitchHTTPRESTServiceFailure403Counters OBJECT-TYPE
    SYNTAX          Counter32
    MAX-ACCESS      read-only
    STATUS          current
    DESCRIPTION     
            "This counter keeps track of the number of 403 error
             received from REST Service server."
    ::= { sonusSoftSwitchHTTPClientRESTServiceFailureCounters 2 }

sonusSoftSwitchHTTPRESTServiceFailure500Counters OBJECT-TYPE
    SYNTAX          Counter32
    MAX-ACCESS      read-only
    STATUS          current
    DESCRIPTION     
            "This counter keeps track of the number of 500 error
             received from REST Service server."
    ::= { sonusSoftSwitchHTTPClientRESTServiceFailureCounters 3 }

sonusSoftSwitchHTTPRESTServiceFailure503Counters OBJECT-TYPE
    SYNTAX          Counter32
    MAX-ACCESS      read-only
    STATUS          current
    DESCRIPTION     
            "This counter keeps track of the number of 503 error
             received from REST Service server."
    ::= { sonusSoftSwitchHTTPClientRESTServiceFailureCounters 4 }

sonusSoftSwitchHTTPClientMIBNotifications OBJECT IDENTIFIER
    ::= { sonusSoftSwitchHTTPClientMIB 2 }

sonusSoftSwitchHTTPClientMIBNotificationsPrefix OBJECT IDENTIFIER
    ::= { sonusSoftSwitchHTTPClientMIBNotifications 0 }

sonusSoftSwitchHTTPClientUpNotification NOTIFICATION-TYPE
    OBJECTS         { sonusEventDescription, sonusEventClass, 
                      sonusEventLevel, sonusEventTime }
    STATUS          current
    DESCRIPTION     
            "SoftSwitch HTTP Client is up."
    ::= { sonusSoftSwitchHTTPClientMIBNotificationsPrefix 1 }

sonusSoftSwitchHTTPClientDownNotification NOTIFICATION-TYPE
    OBJECTS         { sonusEventDescription, sonusEventClass, 
                      sonusEventLevel, sonusEventTime }
    STATUS          current
    DESCRIPTION     
            "SoftSwitch HTTP Client is down."
    ::= { sonusSoftSwitchHTTPClientMIBNotificationsPrefix 2 }

sonusSoftSwitchHTTPClientDnsServiceUpNotification NOTIFICATION-TYPE
    OBJECTS         { sonusEventDescription, sonusEventClass, 
                      sonusEventLevel, sonusEventTime }
    STATUS          current
    DESCRIPTION     
            "SoftSwitch HTTPC-DNS communication is up."
    ::= { sonusSoftSwitchHTTPClientMIBNotificationsPrefix 3 }

sonusSoftSwitchHTTPClientDnsServiceDownNotification NOTIFICATION-TYPE
    OBJECTS         { sonusEventDescription, sonusEventClass, 
                      sonusEventLevel, sonusEventTime }
    STATUS          current
    DESCRIPTION     
            "SoftSwitch HTTPC-DNS communication is down."
    ::= { sonusSoftSwitchHTTPClientMIBNotificationsPrefix 4 }

sonusSoftSwitchHTTPPeerConnectionBlacklisted NOTIFICATION-TYPE
    OBJECTS         { sonusEventDescription, sonusEventClass, 
                      sonusEventLevel, sonusEventTime }
    STATUS          current
    DESCRIPTION     
            "SVS SERVER connection Blacklisted."
    ::= { sonusSoftSwitchHTTPClientMIBNotificationsPrefix 5 }

sonusSoftSwitchHTTPPeerConnectionRecovered NOTIFICATION-TYPE
    OBJECTS         { sonusEventDescription, sonusEventClass, 
                      sonusEventLevel, sonusEventTime }
    STATUS          current
    DESCRIPTION     
            "SVS SERVER connection Recovered from Blacklist."
    ::= { sonusSoftSwitchHTTPClientMIBNotificationsPrefix 6 }

sonusSoftSwitchServerConnectionFailureNotification NOTIFICATION-TYPE
    OBJECTS         { sonusEventDescription, sonusEventClass, 
                      sonusEventLevel, sonusEventTime }
    STATUS          current
    DESCRIPTION     
            "SVS SERVER connection failure."
    ::= { sonusSoftSwitchHTTPClientMIBNotificationsPrefix 7 }

sonusSoftSwitchHttpConnectionFailureNotification NOTIFICATION-TYPE
    OBJECTS         { sonusEventDescription, sonusEventClass, 
                      sonusEventLevel, sonusEventTime }
    STATUS          current
    DESCRIPTION     
            "Connection establishment failed to Http server."
    ::= { sonusSoftSwitchHTTPClientMIBNotificationsPrefix 8 }

sonusSoftSwitchHttpSTIServersNotConfigured NOTIFICATION-TYPE
    OBJECTS         { sonusEventDescription, sonusEventClass, 
                      sonusEventLevel, sonusEventTime }
    STATUS          current
    DESCRIPTION     
            "STI Servers are not configured."
    ::= { sonusSoftSwitchHTTPClientMIBNotificationsPrefix 9 }

sonusSoftSwitchHttpThreadKeepAliveFailedNotification NOTIFICATION-TYPE
    OBJECTS         { sonusEventDescription, sonusEventClass, 
                      sonusEventLevel, sonusEventTime }
    STATUS          current
    DESCRIPTION     
            "Indicates that the one of the threads of HTTP process failed to send keepalive message."
    ::= { sonusSoftSwitchHTTPClientMIBNotificationsPrefix 10 }

END -- end of module SONUS-SOFTSWITCH-HTTP-CLIENT-MIB.
