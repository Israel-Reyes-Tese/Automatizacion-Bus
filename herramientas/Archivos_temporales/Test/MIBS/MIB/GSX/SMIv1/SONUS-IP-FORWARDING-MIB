--
-- This SMIv1 module has been generated by smidump 0.2-cvs. Do not edit.
--

SONUS-IP-FORWARDING-MIB DEFINITIONS ::= BEGIN

IMPORTS
    Ipv6Address
        FROM IPV6-TC
    OBJECT-TYPE
        FROM RFC-1212
    Gauge, IpAddress
        FROM RFC1155-SMI
    RowStatus
        FROM SNMPv2-TC
    sonusPacketMIBs
        FROM SONUS-SMI
    SonusShelfIndex, SonusSlotIndex
        FROM SONUS-TC;

sonusIpForwardingMIB OBJECT IDENTIFIER
    ::= { sonusPacketMIBs 3 }

-- sonusIpForwardingMIB MODULE-IDENTITY
--     LAST-UPDATED    "201207140000Z"
--     ORGANIZATION    
--             "Sonus Networks, Inc."
--     CONTACT-INFO    
--             "   Customer Support    
--              Sonus Networks, Inc.
--              7 Technology Park Drive
--              Westford, MA 01886
--              USA
--              
--              Tel: 978-614-8100
--              Fax: 978-614-8609"
--     DESCRIPTION     
--             "The MIB Module for IP Forwarding management."
--     ::= { sonusPacketMIBs 3 }


sonusIpForwardGeneralGroupTable OBJECT-TYPE
    SYNTAX          SEQUENCE OF SonusIpForwardGeneralGroupEntry
    ACCESS          not-accessible
    STATUS          mandatory
    DESCRIPTION     
            "The collection of IP Forward General Group information
             for the specified instance."
    ::= { sonusIpForwardingMIB 1 }

sonusIpForwardGeneralGroupEntry OBJECT-TYPE
    SYNTAX          SonusIpForwardGeneralGroupEntry
    ACCESS          not-accessible
    STATUS          mandatory
    DESCRIPTION     
            "The collection of IP Forward General Group information
             for the specified instance."
    INDEX           { sonusIpForwardGeneralGroupShelf, 
                      sonusIpForwardGeneralGroupSlot, 
                      sonusIpForwardGeneralGroupInstance }
    ::= { sonusIpForwardGeneralGroupTable 1 }

SonusIpForwardGeneralGroupEntry ::=
    SEQUENCE {
        sonusIpCidrRouteNumber          Gauge,
        sonusIpForwardGeneralGroupShelf SonusShelfIndex,
        sonusIpForwardGeneralGroupSlot  SonusSlotIndex,
        sonusIpForwardGeneralGroupInstance  INTEGER
    }

sonusIpCidrRouteNumber OBJECT-TYPE
    SYNTAX          Gauge
    ACCESS          read-only
    STATUS          mandatory
    DESCRIPTION     
            "The number of current ipCidrRouteTable entries
             that are not invalid."
    ::= { sonusIpForwardGeneralGroupEntry 3 }

sonusIpForwardGeneralGroupShelf OBJECT-TYPE
    SYNTAX          SonusShelfIndex
    ACCESS          read-only
    STATUS          mandatory
    DESCRIPTION     
            "A 32-bit integer identifying the shelf
             that the IP Forward General Group table applies to"
    ::= { sonusIpForwardGeneralGroupEntry 4 }

sonusIpForwardGeneralGroupSlot OBJECT-TYPE
    SYNTAX          SonusSlotIndex
    ACCESS          read-only
    STATUS          mandatory
    DESCRIPTION     
            "A 32-bit integer identifying the slot
             that the IP Forward General Group table applies to"
    ::= { sonusIpForwardGeneralGroupEntry 5 }

sonusIpForwardGeneralGroupInstance OBJECT-TYPE
    SYNTAX          INTEGER
    ACCESS          read-only
    STATUS          mandatory
    DESCRIPTION     
            "A 32-bit integer identifying the instance
             that the IP Forward General Group table applies to"
    ::= { sonusIpForwardGeneralGroupEntry 6 }

sonusIpCidrRouteTable OBJECT-TYPE
    SYNTAX          SEQUENCE OF SonusIpCidrRouteEntry
    ACCESS          not-accessible
    STATUS          mandatory
    DESCRIPTION     
            "This entity's IP Routing table."
--     REFERENCE       
--             "RFC 1213 Section 6.6, The IP Group"
    ::= { sonusIpForwardingMIB 2 }

sonusIpCidrRouteEntry OBJECT-TYPE
    SYNTAX          SonusIpCidrRouteEntry
    ACCESS          not-accessible
    STATUS          mandatory
    DESCRIPTION     
            "A particular route to  a  particular  destina-
             tion, under a particular policy."
    INDEX           { sonusIpCidrIpversion, sonusIpCidrRouteShelf, 
                      sonusIpCidrRouteSlot, sonusIpCidrRouteInstance, 
                      sonusIpCidrRouteDest, sonusIpCidrRouteMask, 
                      sonusIpCidrRouteTos, sonusIpCidrRouteNextHop, 
                      sonusIpv6CidrRouteDest, 
                      sonusIpv6CidrRoutePrefixLength, 
                      sonusIpv6CidrRouteNextHop }
    ::= { sonusIpCidrRouteTable 1 }

SonusIpCidrRouteEntry ::=
    SEQUENCE {
        sonusIpCidrRouteDest            IpAddress,
        sonusIpCidrRouteMask            IpAddress,
        sonusIpCidrRouteTos             INTEGER,
        sonusIpCidrRouteNextHop         IpAddress,
        sonusIpCidrRouteIfIndex         INTEGER,
        sonusIpCidrRouteType            INTEGER,
        sonusIpCidrRouteProto           INTEGER,
        sonusIpCidrRouteAge             INTEGER,
        sonusIpCidrRouteInfo            OBJECT IDENTIFIER,
        sonusIpCidrRouteNextHopAS       INTEGER,
        sonusIpCidrRouteMetric1         INTEGER,
        sonusIpCidrRouteMetric2         INTEGER,
        sonusIpCidrRouteMetric3         INTEGER,
        sonusIpCidrRouteMetric4         INTEGER,
        sonusIpCidrRouteMetric5         INTEGER,
        sonusIpCidrRouteStatus          RowStatus,
        sonusIpCidrRouteShelf           SonusShelfIndex,
        sonusIpCidrRouteSlot            SonusSlotIndex,
        sonusIpCidrRouteInstance        INTEGER,
        sonusIpv6CidrRouteDest          Ipv6Address,
        sonusIpv6CidrRoutePrefixLength  Ipv6Address,
        sonusIpv6CidrRouteNextHop       Ipv6Address,
        sonusIpCidrIpversion            INTEGER,
        sonusIpv6CidrPrefixlen          INTEGER
    }

sonusIpCidrRouteDest OBJECT-TYPE
    SYNTAX          IpAddress
    ACCESS          read-only
    STATUS          mandatory
    DESCRIPTION     
            "The destination IP address of this route.
             
             This object may not take a Multicast (Class  D)
             address value.
             
             Any assignment (implicit or  otherwise)  of  an
             instance  of  this  object to a value x must be
             rejected if the bitwise logical-AND of  x  with
             the  value of the corresponding instance of the
             ipCidrRouteMask object is not equal to x."
    ::= { sonusIpCidrRouteEntry 1 }

sonusIpCidrRouteMask OBJECT-TYPE
    SYNTAX          IpAddress
    ACCESS          read-only
    STATUS          mandatory
    DESCRIPTION     
            "Indicate the mask to be logical-ANDed with the
             destination  address  before  being compared to
             the value  in  the  ipCidrRouteDest  field.   For
             those  systems  that  do  not support arbitrary
             subnet masks, an agent constructs the value  of
             the  ipCidrRouteMask  by  reference to the IP Ad-
             dress Class.
             
             Any assignment (implicit or  otherwise)  of  an
             instance  of  this  object to a value x must be
             rejected if the bitwise logical-AND of  x  with
             the  value of the corresponding instance of the
             ipCidrRouteDest object is not equal to ipCidrRoute-
             Dest."
    ::= { sonusIpCidrRouteEntry 2 }

sonusIpCidrRouteTos OBJECT-TYPE
    SYNTAX          INTEGER
    ACCESS          read-only
    STATUS          mandatory
    DESCRIPTION     
            "The policy specifier is the IP TOS Field.  The encoding
             of IP TOS is as specified  by  the  following convention.
             Zero indicates the default path if no more  specific
             policy applies.
             
             +-----+-----+-----+-----+-----+-----+-----+-----+
             |                 |                       |     |
             |   PRECEDENCE    |    TYPE OF SERVICE    |  0  |
             |                 |                       |     |
             +-----+-----+-----+-----+-----+-----+-----+-----+
             
                      IP TOS                IP TOS
                 Field     Policy      Field     Policy
                 Contents    Code      Contents    Code
                 0 0 0 0  ==>   0      0 0 0 1  ==>   2
                 0 0 1 0  ==>   4      0 0 1 1  ==>   6
                 0 1 0 0  ==>   8      0 1 0 1  ==>  10
                 0 1 1 0  ==>  12      0 1 1 1  ==>  14
                 1 0 0 0  ==>  16      1 0 0 1  ==>  18
                 1 0 1 0  ==>  20      1 0 1 1  ==>  22
                 1 1 0 0  ==>  24      1 1 0 1  ==>  26
                 1 1 1 0  ==>  28      1 1 1 1  ==>  30"
    ::= { sonusIpCidrRouteEntry 3 }

sonusIpCidrRouteNextHop OBJECT-TYPE
    SYNTAX          IpAddress
    ACCESS          read-only
    STATUS          mandatory
    DESCRIPTION     
            "On remote routes, the address of the next sys-
             tem en route; Otherwise, 0.0.0.0."
    ::= { sonusIpCidrRouteEntry 4 }

sonusIpCidrRouteIfIndex OBJECT-TYPE
    SYNTAX          INTEGER
    ACCESS          read-only
    STATUS          mandatory
    DESCRIPTION     
            "The ifIndex value which identifies  the  local
             interface  through  which  the next hop of this
             route should be reached."
    DEFVAL          { 0 }
    ::= { sonusIpCidrRouteEntry 5 }

sonusIpCidrRouteType OBJECT-TYPE
    SYNTAX          INTEGER { other(1), reject(2), local(3), remote(4) }
    ACCESS          read-only
    STATUS          mandatory
    DESCRIPTION     
            "The type of route.  Note that local(3)  refers
             to  a route for which the next hop is the final
             destination; remote(4) refers to  a  route  for
             which  the  next  hop is not the final destina-
             tion.
             
             Routes which do not result in traffic forwarding or
             rejection should not be displayed even if the
             implementation keeps them stored internally.
             
             
             reject (2) refers to a route which, if matched, discards
             the message as unreachable. This is used in some
             protocols as a means of correctly aggregating routes."
    ::= { sonusIpCidrRouteEntry 6 }

sonusIpCidrRouteProto OBJECT-TYPE
    SYNTAX          INTEGER { other(1), local(2), netmgmt(3), icmp(4), 
                        egp(5), ggp(6), hello(7), rip(8), isIs(9), 
                        esIs(10), ciscoIgrp(11), bbnSpfIgp(12), ospf(13), 
                        bgp(14), idpr(15), ciscoEigrp(16) }
    ACCESS          read-only
    STATUS          mandatory
    DESCRIPTION     
            "The routing mechanism via which this route was
             learned.  Inclusion of values for gateway rout-
             ing protocols is not  intended  to  imply  that
             hosts should support those protocols."
    ::= { sonusIpCidrRouteEntry 7 }

sonusIpCidrRouteAge OBJECT-TYPE
    SYNTAX          INTEGER
    ACCESS          read-only
    STATUS          mandatory
    DESCRIPTION     
            "The number of seconds  since  this  route  was
             last  updated  or  otherwise  determined  to be
             correct.  Note that no semantics of  `too  old'
             can  be implied except through knowledge of the
             routing  protocol  by  which  the   route   was
             learned."
    DEFVAL          { 0 }
    ::= { sonusIpCidrRouteEntry 8 }

sonusIpCidrRouteInfo OBJECT-TYPE
    SYNTAX          OBJECT IDENTIFIER
    ACCESS          read-only
    STATUS          mandatory
    DESCRIPTION     
            "A reference to MIB definitions specific to the
             particular  routing protocol which is responsi-
             ble for this route, as determined by the  value
             specified  in the route's ipCidrRouteProto value.
             If this information is not present,  its  value
             should be set to the OBJECT IDENTIFIER { 0 0 },
             which is a syntactically valid object  identif-
             ier, and any implementation conforming to ASN.1
             and the Basic Encoding Rules must  be  able  to
             generate and recognize this value."
    ::= { sonusIpCidrRouteEntry 9 }

sonusIpCidrRouteNextHopAS OBJECT-TYPE
    SYNTAX          INTEGER
    ACCESS          read-only
    STATUS          mandatory
    DESCRIPTION     
            "The Autonomous System Number of the Next  Hop.
             The  semantics of this object are determined by
             the routing-protocol specified in  the  route's
             ipCidrRouteProto  value. When  this object is
             unknown or not relevant its value should be set
             to zero."
    DEFVAL          { 0 }
    ::= { sonusIpCidrRouteEntry 10 }

sonusIpCidrRouteMetric1 OBJECT-TYPE
    SYNTAX          INTEGER
    ACCESS          read-only
    STATUS          mandatory
    DESCRIPTION     
            "The primary routing  metric  for  this  route.
             The  semantics of this metric are determined by
             the routing-protocol specified in  the  route's
             ipCidrRouteProto  value.   If  this metric is not
             used, its value should be set to -1."
    DEFVAL          { -1 }
    ::= { sonusIpCidrRouteEntry 11 }

sonusIpCidrRouteMetric2 OBJECT-TYPE
    SYNTAX          INTEGER
    ACCESS          read-only
    STATUS          mandatory
    DESCRIPTION     
            "An alternate routing metric  for  this  route.
             The  semantics of this metric are determined by
             the routing-protocol specified in  the  route's
             ipCidrRouteProto  value.   If  this metric is not
             used, its value should be set to -1."
    DEFVAL          { -1 }
    ::= { sonusIpCidrRouteEntry 12 }

sonusIpCidrRouteMetric3 OBJECT-TYPE
    SYNTAX          INTEGER
    ACCESS          read-only
    STATUS          mandatory
    DESCRIPTION     
            "An alternate routing metric  for  this  route.
             The  semantics of this metric are determined by
             the routing-protocol specified in  the  route's
             ipCidrRouteProto  value.   If  this metric is not
             used, its value should be set to -1."
    DEFVAL          { -1 }
    ::= { sonusIpCidrRouteEntry 13 }

sonusIpCidrRouteMetric4 OBJECT-TYPE
    SYNTAX          INTEGER
    ACCESS          read-only
    STATUS          mandatory
    DESCRIPTION     
            "An alternate routing metric  for  this  route.
             The  semantics of this metric are determined by
             the routing-protocol specified in  the  route's
             ipCidrRouteProto  value.   If  this metric is not
             used, its value should be set to -1."
    DEFVAL          { -1 }
    ::= { sonusIpCidrRouteEntry 14 }

sonusIpCidrRouteMetric5 OBJECT-TYPE
    SYNTAX          INTEGER
    ACCESS          read-only
    STATUS          mandatory
    DESCRIPTION     
            "An alternate routing metric  for  this  route.
             The  semantics of this metric are determined by
             the routing-protocol specified in  the  route's
             ipCidrRouteProto  value.   If  this metric is not
             used, its value should be set to -1."
    DEFVAL          { -1 }
    ::= { sonusIpCidrRouteEntry 15 }

sonusIpCidrRouteStatus OBJECT-TYPE
    SYNTAX          RowStatus
    ACCESS          read-only
    STATUS          mandatory
    DESCRIPTION     
            "The row status variable, used according to
             row installation and removal conventions."
    ::= { sonusIpCidrRouteEntry 16 }

sonusIpCidrRouteShelf OBJECT-TYPE
    SYNTAX          SonusShelfIndex
    ACCESS          read-only
    STATUS          mandatory
    DESCRIPTION     
            "A 32-bit integer identifying the shelf
             that the IP CIDR Route table applies to"
    ::= { sonusIpCidrRouteEntry 17 }

sonusIpCidrRouteSlot OBJECT-TYPE
    SYNTAX          SonusSlotIndex
    ACCESS          read-only
    STATUS          mandatory
    DESCRIPTION     
            "A 32-bit integer identifying the slot
             that the IP CIDR Route table applies to"
    ::= { sonusIpCidrRouteEntry 18 }

sonusIpCidrRouteInstance OBJECT-TYPE
    SYNTAX          INTEGER
    ACCESS          read-only
    STATUS          mandatory
    DESCRIPTION     
            "A 32-bit integer identifying the instance
             that the IP CIDR Route table applies to"
    ::= { sonusIpCidrRouteEntry 19 }

sonusIpv6CidrRouteDest OBJECT-TYPE
    SYNTAX          Ipv6Address
    ACCESS          read-only
    STATUS          mandatory
    DESCRIPTION     
            "The IPv6 Address of this entry"
    ::= { sonusIpCidrRouteEntry 20 }

sonusIpv6CidrRoutePrefixLength OBJECT-TYPE
    SYNTAX          Ipv6Address
    ACCESS          read-only
    STATUS          mandatory
    DESCRIPTION     
            "Ipv6 Prefix Length"
    ::= { sonusIpCidrRouteEntry 21 }

sonusIpv6CidrRouteNextHop OBJECT-TYPE
    SYNTAX          Ipv6Address
    ACCESS          read-only
    STATUS          mandatory
    DESCRIPTION     
            "The next hop IPv6 Address of this entry"
    ::= { sonusIpCidrRouteEntry 22 }

sonusIpCidrIpversion OBJECT-TYPE
    SYNTAX          INTEGER { afInet(2), afInet6(24) }
    ACCESS          read-only
    STATUS          mandatory
    DESCRIPTION     
            "Ip address family"
    ::= { sonusIpCidrRouteEntry 23 }

sonusIpv6CidrPrefixlen OBJECT-TYPE
    SYNTAX          INTEGER
    ACCESS          read-only
    STATUS          mandatory
    DESCRIPTION     
            "Ipv6 Prefix length <0-128>"
    ::= { sonusIpCidrRouteEntry 24 }

sonusIpCidrAdminRouteTable OBJECT-TYPE
    SYNTAX          SEQUENCE OF SonusIpCidrAdminRouteEntry
    ACCESS          not-accessible
    STATUS          mandatory
    DESCRIPTION     
            "This entity's administratively configured IP Routing table."
    ::= { sonusIpForwardingMIB 3 }

sonusIpCidrAdminRouteEntry OBJECT-TYPE
    SYNTAX          SonusIpCidrAdminRouteEntry
    ACCESS          not-accessible
    STATUS          mandatory
    DESCRIPTION     
            "A particular route to  a  particular  destina-
             tion, under a particular policy."
    INDEX           { sonusIpCidrAdminRouteDest, 
                      sonusIpCidrAdminRouteMask, 
                      sonusIpCidrAdminRouteNextHop, 
                      sonusIpCidrAdminRouteIfIndex, 
                      sonusIpv6CidrAdminRouteDest, 
                      sonusIpv6CidrAdminPrefixLength, 
                      sonusIpv6CidrAdminRouteNextHop }
    ::= { sonusIpCidrAdminRouteTable 1 }

SonusIpCidrAdminRouteEntry ::=
    SEQUENCE {
        sonusIpCidrAdminRouteDest       IpAddress,
        sonusIpCidrAdminRouteMask       IpAddress,
        sonusIpCidrAdminRouteNextHop    IpAddress,
        sonusIpCidrAdminRouteIfIndex    INTEGER,
        sonusIpCidrAdminRouteStatus     RowStatus,
        sonusIpCidrAdminRoutePref       INTEGER,
        sonusIpv6CidrAdminRouteDest     Ipv6Address,
        sonusIpv6CidrAdminPrefixLength  INTEGER,
        sonusIpv6CidrAdminRouteNextHop  Ipv6Address,
        sonusIpv6CidrAdminRouteIpVersion INTEGER
    }

sonusIpCidrAdminRouteDest OBJECT-TYPE
    SYNTAX          IpAddress
    ACCESS          read-only
    STATUS          mandatory
    DESCRIPTION     
            "The destination IP address of this route.
             
             This object may not take a Multicast (Class  D)
             address value.
             
             Any assignment (implicit or  otherwise)  of  an
             instance  of  this  object to a value x must be
             rejected if the bitwise logical-AND of  x  with
             the  value of the corresponding instance of the
             ipCidrRouteMask object is not equal to x."
    ::= { sonusIpCidrAdminRouteEntry 1 }

sonusIpCidrAdminRouteMask OBJECT-TYPE
    SYNTAX          IpAddress
    ACCESS          read-only
    STATUS          mandatory
    DESCRIPTION     
            "Indicate the mask to be logical-ANDed with the
             destination  address  before  being compared to
             the value  in  the  ipCidrRouteDest  field.   For
             those  systems  that  do  not support arbitrary
             subnet masks, an agent constructs the value  of
             the  ipCidrRouteMask  by  reference to the IP Ad-
             dress Class.
             
             Any assignment (implicit or  otherwise)  of  an
             instance  of  this  object to a value x must be
             rejected if the bitwise logical-AND of  x  with
             the  value of the corresponding instance of the
             ipCidrRouteDest object is not equal to ipCidrRoute-
             Dest."
    ::= { sonusIpCidrAdminRouteEntry 2 }

sonusIpCidrAdminRouteNextHop OBJECT-TYPE
    SYNTAX          IpAddress
    ACCESS          read-only
    STATUS          mandatory
    DESCRIPTION     
            "On remote routes, the address of the next sys-
             tem en route; Otherwise, 0.0.0.0."
    ::= { sonusIpCidrAdminRouteEntry 3 }

sonusIpCidrAdminRouteIfIndex OBJECT-TYPE
    SYNTAX          INTEGER
    ACCESS          read-only
    STATUS          mandatory
    DESCRIPTION     
            "The interface  through  which  the next hop of this
             route should be reached."
    ::= { sonusIpCidrAdminRouteEntry 4 }

sonusIpCidrAdminRouteStatus OBJECT-TYPE
    SYNTAX          RowStatus
    ACCESS          read-write
    STATUS          mandatory
    DESCRIPTION     
            "The row status variable, used according to
             row installation and removal conventions."
    ::= { sonusIpCidrAdminRouteEntry 5 }

sonusIpCidrAdminRoutePref OBJECT-TYPE
    SYNTAX          INTEGER
    ACCESS          read-write
    STATUS          mandatory
    DESCRIPTION     
            "route preference value"
    ::= { sonusIpCidrAdminRouteEntry 6 }

sonusIpv6CidrAdminRouteDest OBJECT-TYPE
    SYNTAX          Ipv6Address
    ACCESS          read-only
    STATUS          mandatory
    DESCRIPTION     
            "The IPv6 Address of this entry"
    ::= { sonusIpCidrAdminRouteEntry 7 }

sonusIpv6CidrAdminPrefixLength OBJECT-TYPE
    SYNTAX          INTEGER (0..128)
    ACCESS          read-write
    STATUS          mandatory
    DESCRIPTION     
            "Ipv6 Prefix Length"
    ::= { sonusIpCidrAdminRouteEntry 8 }

sonusIpv6CidrAdminRouteNextHop OBJECT-TYPE
    SYNTAX          Ipv6Address
    ACCESS          read-only
    STATUS          mandatory
    DESCRIPTION     
            "The next hop IPv6 Address of this entry"
    ::= { sonusIpCidrAdminRouteEntry 9 }

sonusIpv6CidrAdminRouteIpVersion OBJECT-TYPE
    SYNTAX          INTEGER { afInet(2), afInet6(24) }
    ACCESS          read-only
    STATUS          mandatory
    DESCRIPTION     
            "Ip address family"
    ::= { sonusIpCidrAdminRouteEntry 10 }

sonusIpRouteTable OBJECT-TYPE
    SYNTAX          SEQUENCE OF SonusIpRouteEntry
    ACCESS          not-accessible
    STATUS          mandatory
    DESCRIPTION     
            "This entity's IP Routing table."
--     REFERENCE       
--             "RFC 1213 Section 6.6, The IP Group"
    ::= { sonusIpForwardingMIB 4 }

sonusIpRouteEntry OBJECT-TYPE
    SYNTAX          SonusIpRouteEntry
    ACCESS          not-accessible
    STATUS          mandatory
    DESCRIPTION     
            "A particular route to  a  particular  destina-
             tion, under a particular policy."
    INDEX           { sonusIpRouteversion, sonusIpRouteShelf, 
                      sonusIpRouteSlot, sonusIpRouteInstance, 
                      sonusIpRouteLocIndex }
    ::= { sonusIpRouteTable 1 }

SonusIpRouteEntry ::=
    SEQUENCE {
        sonusIpRouteShelf               SonusShelfIndex,
        sonusIpRouteSlot                SonusSlotIndex,
        sonusIpRouteInstance            INTEGER,
        sonusIpRouteDest                IpAddress,
        sonusIpRouteMask                IpAddress,
        sonusIpRouteNextHop             IpAddress,
        sonusIpRouteIfIndex             INTEGER,
        sonusIpRouteType                INTEGER,
        sonusIpRouteProto               INTEGER,
        sonusIpRoutePref                INTEGER,
        sonusIpRouteMetric              INTEGER,
        sonusIpRouteLocIndex            INTEGER,
        sonusIpRouteversion             INTEGER,
        sonusIpv6RouteDest              Ipv6Address,
        sonusIpv6RoutePrefixLength      INTEGER,
        sonusIpv6RouteNextHop           Ipv6Address
    }

sonusIpRouteShelf OBJECT-TYPE
    SYNTAX          SonusShelfIndex
    ACCESS          read-only
    STATUS          mandatory
    DESCRIPTION     
            "A 32-bit integer identifying the shelf
             that the IP Route table applies to"
    ::= { sonusIpRouteEntry 1 }

sonusIpRouteSlot OBJECT-TYPE
    SYNTAX          SonusSlotIndex
    ACCESS          read-only
    STATUS          mandatory
    DESCRIPTION     
            "A 32-bit integer identifying the slot
             that the IP Route table applies to"
    ::= { sonusIpRouteEntry 2 }

sonusIpRouteInstance OBJECT-TYPE
    SYNTAX          INTEGER
    ACCESS          read-only
    STATUS          mandatory
    DESCRIPTION     
            "A 32-bit integer identifying the instance
             that the IP Route table applies to"
    ::= { sonusIpRouteEntry 3 }

sonusIpRouteDest OBJECT-TYPE
    SYNTAX          IpAddress
    ACCESS          read-only
    STATUS          mandatory
    DESCRIPTION     
            "The destination IP address of this route.
             
             This object may not take a Multicast (Class  D)
             address value.
             
             Any assignment (implicit or  otherwise)  of  an
             instance  of  this  object to a value x must be
             rejected if the bitwise logical-AND of  x  with
             the  value of the coarresponding instance of the
             ipCidrRouteMask object is not equal to x."
    ::= { sonusIpRouteEntry 4 }

sonusIpRouteMask OBJECT-TYPE
    SYNTAX          IpAddress
    ACCESS          read-only
    STATUS          mandatory
    DESCRIPTION     
            "Indicate the mask to be logical-ANDed with the
             destination  address  before  being compared to
             the value  in  the  ipCidrRouteDest  field.   For
             those  systems  that  do  not support arbitrary
             subnet masks, an agent constructs the value  of
             the  ipCidrRouteMask  by  reference to the IP Ad-
             dress Class.
             
             Any assignment (implicit or  otherwise)  of  an
             instance  of  this  object to a value x must be
             rejected if the bitwise logical-AND of  x  with
             the  value of the corresponding instance of the
             ipCidrRouteDest object is not equal to ipCidrRoute-
             Dest."
    ::= { sonusIpRouteEntry 5 }

sonusIpRouteNextHop OBJECT-TYPE
    SYNTAX          IpAddress
    ACCESS          read-only
    STATUS          mandatory
    DESCRIPTION     
            "On remote routes, the address of the next sys-
             tem en route; Otherwise, 0.0.0.0."
    ::= { sonusIpRouteEntry 7 }

sonusIpRouteIfIndex OBJECT-TYPE
    SYNTAX          INTEGER
    ACCESS          read-only
    STATUS          mandatory
    DESCRIPTION     
            "The ifIndex value which identifies  the  local
             interface  through  which  the next hop of this
             route should be reached."
    ::= { sonusIpRouteEntry 8 }

sonusIpRouteType OBJECT-TYPE
    SYNTAX          INTEGER { other(1), reject(2), local(3), remote(4) }
    ACCESS          read-only
    STATUS          mandatory
    DESCRIPTION     
            "The type of route.  Note that local(3)  refers
             to  a route for which the next hop is the final
             destination; remote(4) refers to  a  route  for
             which  the  next  hop is not the final destina-
             tion.
             
             Routes which do not result in traffic forwarding or
             rejection should not be displayed even if the
             implementation keeps them stored internally.
             
             
             reject (2) refers to a route which, if matched, discards
             the message as unreachable. This is used in some
             protocols as a means of correctly aggregating routes."
    ::= { sonusIpRouteEntry 9 }

sonusIpRouteProto OBJECT-TYPE
    SYNTAX          INTEGER { other(1), local(2), netmgmt(3), icmp(4), 
                        egp(5), ggp(6), hello(7), rip(8), isIs(9), 
                        esIs(10), ciscoIgrp(11), bbnSpfIgp(12), ospf(13), 
                        bgp(14), idpr(15), ciscoEigrp(16) }
    ACCESS          read-only
    STATUS          mandatory
    DESCRIPTION     
            "The routing mechanism via which this route was
             learned.  Inclusion of values for gateway rout-
             ing protocols is not  intended  to  imply  that
             hosts should support those protocols."
    ::= { sonusIpRouteEntry 10 }

sonusIpRoutePref OBJECT-TYPE
    SYNTAX          INTEGER
    ACCESS          read-only
    STATUS          mandatory
    DESCRIPTION     
            "route preference value"
    ::= { sonusIpRouteEntry 11 }

sonusIpRouteMetric OBJECT-TYPE
    SYNTAX          INTEGER
    ACCESS          read-only
    STATUS          mandatory
    DESCRIPTION     
            "The primary routing  metric  for  this  route.
             The  semantics of this metric are determined by
             the routing-protocol specified in  the  route's
             ipCidrRouteProto  value.   If  this metric is not
             used, its value should be set to -1."
    ::= { sonusIpRouteEntry 12 }

sonusIpRouteLocIndex OBJECT-TYPE
    SYNTAX          INTEGER
    ACCESS          read-only
    STATUS          mandatory
    DESCRIPTION     
            "Positional index of the route entry in the routing
             table."
    ::= { sonusIpRouteEntry 13 }

sonusIpRouteversion OBJECT-TYPE
    SYNTAX          INTEGER { afInet(2), afInet6(24) }
    ACCESS          read-only
    STATUS          mandatory
    DESCRIPTION     
            "Ip address family"
    ::= { sonusIpRouteEntry 14 }

sonusIpv6RouteDest OBJECT-TYPE
    SYNTAX          Ipv6Address
    ACCESS          read-only
    STATUS          mandatory
    DESCRIPTION     
            "The IPv6 Address of this entry"
    ::= { sonusIpRouteEntry 15 }

sonusIpv6RoutePrefixLength OBJECT-TYPE
    SYNTAX          INTEGER (0..128)
    ACCESS          read-only
    STATUS          mandatory
    DESCRIPTION     
            "Ipv6 Prefix Length"
    ::= { sonusIpRouteEntry 16 }

sonusIpv6RouteNextHop OBJECT-TYPE
    SYNTAX          Ipv6Address
    ACCESS          read-only
    STATUS          mandatory
    DESCRIPTION     
            "The next hop IPv6 Address of this entry"
    ::= { sonusIpRouteEntry 17 }

END -- end of module SONUS-IP-FORWARDING-MIB.
