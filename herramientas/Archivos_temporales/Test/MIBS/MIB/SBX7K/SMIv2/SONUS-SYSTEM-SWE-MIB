--
-- This SMIv2 module has been generated by smidump 0.2-cvs. Do not edit.
--

SONUS-SYSTEM-SWE-MIB DEFINITIONS ::= BEGIN

IMPORTS
    Counter32, Counter64, Gauge32, Integer32, IpAddress, MODULE-IDENTITY, 
    OBJECT-TYPE, Unsigned32
        FROM SNMPv2-SMI
    DateAndTime, RowStatus, TEXTUAL-CONVENTION, TruthValue
        FROM SNMPv2-TC
    sonusCommonSoftwarePlatformServicesMIBs
        FROM SONUS-SMI;

sonusSystemSweMIB MODULE-IDENTITY
    LAST-UPDATED    "201705080000Z"
    ORGANIZATION    
            "Ribbon Communications, Inc."
    CONTACT-INFO    
            "Customer Support        
             Ribbon Communications, Inc. 
             4 Technology Park Drive 
             Westford, MA 01886      
             USA                     
                                     
             Tel: 978-614-8100       
             Fax: 978-614-8609"
    DESCRIPTION     
            "The MIB Module for tables related to SWE."
    REVISION        "201705080000Z"
    DESCRIPTION     
            "Auto generated MIB."
    ::= { sonusCommonSoftwarePlatformServicesMIBs 23 }


ConfdString ::= TEXTUAL-CONVENTION
    DISPLAY-HINT    "1t"
    STATUS          current
    DESCRIPTION     
            "xs: and confd: types mapped to strings"
    SYNTAX          OCTET STRING

String ::= TEXTUAL-CONVENTION
    DISPLAY-HINT    "1t"
    STATUS          current
    DESCRIPTION     
            "xs:string"
    SYNTAX          OCTET STRING

SonusSystemSWePPStype ::= TEXTUAL-CONVENTION
    DISPLAY-HINT    "1t"
    STATUS          current
    DESCRIPTION     
            "
             Value is in Mpps.
             "
    SYNTAX          OCTET STRING

SonusSystemSWebhcaType ::= TEXTUAL-CONVENTION
    DISPLAY-HINT    "1t"
    STATUS          current
    DESCRIPTION     
            "
             Value is of bhca per subscriber between 0.01 to 100.
             "
    SYNTAX          OCTET STRING

SonusSystemSWeActState ::= TEXTUAL-CONVENTION
    STATUS          current
    DESCRIPTION     
            "
             Activation States of Profile activation.
             "
    SYNTAX          INTEGER { active(1), inactive(2) }

SonusSystemSWeSupportedCodecType ::= TEXTUAL-CONVENTION
    STATUS          current
    DESCRIPTION     
            "
             Different types of supported Codecs in SWe.
             "
    SYNTAX          INTEGER { g711ss(1), g711(2), g729(3), g723(4), 
                        g726(5), g722(6), g7221(7), amr(8), amrwb(9), 
                        evrc(10), evrcb(11), efr(12), ilbc(13), opus(14), 
                        silk8(15), silk16(16), evs(17), t38(18), 
                        g7112g711(19) }

SonusSystemSWedryUpTime ::= TEXTUAL-CONVENTION
    STATUS          current
    DESCRIPTION     
            "
             Value of dryUpTime.
             "
    SYNTAX          Integer32 (0..1440)

SonusSystemSWeCHTType ::= TEXTUAL-CONVENTION
    STATUS          current
    DESCRIPTION     
            "
             Call Hold Time is in seconds from 10 to 10800.
             "
    SYNTAX          Integer32 (10..10800)

SonusPPSFactorType ::= TEXTUAL-CONVENTION
    DISPLAY-HINT    "1t"
    STATUS          current
    DESCRIPTION     
            "
             Value is of tx and rx PPS factor 1.0 to 100.
             "
    SYNTAX          OCTET STRING

SonusSystemSWePercentageFloatType ::= TEXTUAL-CONVENTION
    DISPLAY-HINT    "1t"
    STATUS          current
    DESCRIPTION     
            "
             Value is in percentage from 0.01 to 100.0
             "
    SYNTAX          OCTET STRING

SonusSystemSWeConfigProfileName ::= TEXTUAL-CONVENTION
    STATUS          current
    DESCRIPTION     
            "
             Lists names of all supported configuration provisioning profiles in SWe.
             "
    SYNTAX          INTEGER { small(0), large(1), extrasmall(2) }

SonusSystemSWePercentageType ::= TEXTUAL-CONVENTION
    STATUS          current
    DESCRIPTION     
            "
             Value is in percentage from 0 to 100.
             "
    SYNTAX          Integer32 (0..100)

SonusSystemSWePtime ::= TEXTUAL-CONVENTION
    STATUS          current
    DESCRIPTION     
            "
             Values for packetization time for G711 calls.
             "
    SYNTAX          INTEGER { p10(10), p20(20), p30(30), p40(40), 
                        p50(50), p60(60), p80(80), p100(100) }

CostFactorType ::= TEXTUAL-CONVENTION
    DISPLAY-HINT    "1t"
    STATUS          current
    DESCRIPTION     
            "
             Value is of signaling and media cost factor 0.0001 to 100.
             "
    SYNTAX          OCTET STRING

SonusSystemSWeActionType ::= TEXTUAL-CONVENTION
    STATUS          current
    DESCRIPTION     
            "
             Types of Action Type during activation.
             "
    SYNTAX          INTEGER { dryUp(1), forced(2) }

SonusSystemSWeMaxVMBandwidth ::= TEXTUAL-CONVENTION
    STATUS          current
    DESCRIPTION     
            "
             Max VM bandwidth required(in Gbps).
             Enter a value in range (1-10). "
    SYNTAX          Unsigned32 (1..10)

SonusSystemSWeProfileName ::= TEXTUAL-CONVENTION
    DISPLAY-HINT    "1t"
    STATUS          current
    DESCRIPTION     
            "
             This data type is used to model textual information taken
             from the NVT ASCII character set.  The sonusSystemSWeProfileName type is used
             to label Sonus Named objects. The characters #%^&(){}<>,/\;`[]=!$'*?|~
             and SPACE are not allowed.
             "
    SYNTAX          OCTET STRING (SIZE(0..40))

SonusSystemSWeIndexType ::= TEXTUAL-CONVENTION
    DISPLAY-HINT    "1t"
    STATUS          current
    DESCRIPTION     
            "
             Value is of override index between 0.2 to 10.
             "
    SYNTAX          OCTET STRING

SonusSystemSWeRegInterval ::= TEXTUAL-CONVENTION
    STATUS          current
    DESCRIPTION     
            "
             Interval is in seconds from 15 to 86400.
             "
    SYNTAX          Unsigned32 (15..86400)

sonusSweProcessorCoreCapacity OBJECT IDENTIFIER
    ::= { sonusSystemSweMIB 2 }

sonusSweProcessorCoreCapacityCryptoIndex OBJECT-TYPE
    SYNTAX          Unsigned32
    MAX-ACCESS      read-only
    STATUS          current
    DESCRIPTION     
            "
             Crypto index calculated by the startup scripts.
             "
    ::= { sonusSweProcessorCoreCapacity 1 }

sonusSweProcessorCoreCapacityPassthroughIndex OBJECT-TYPE
    SYNTAX          Unsigned32
    MAX-ACCESS      read-only
    STATUS          current
    DESCRIPTION     
            "
             Passthrough index calculated by the startup scripts.
             "
    ::= { sonusSweProcessorCoreCapacity 2 }

sonusSweProcessorCoreCapacitySignalingIndex OBJECT-TYPE
    SYNTAX          Unsigned32
    MAX-ACCESS      read-only
    STATUS          current
    DESCRIPTION     
            "
             Signaling index calculated by the startup scripts.
             "
    ::= { sonusSweProcessorCoreCapacity 3 }

sonusSweProcessorCoreCapacityTranscodeIndex OBJECT-TYPE
    SYNTAX          Unsigned32
    MAX-ACCESS      read-only
    STATUS          current
    DESCRIPTION     
            "
             Transcode index calculated by the startup scripts.
             "
    ::= { sonusSweProcessorCoreCapacity 4 }

sonusSweCapacityEstimationTable OBJECT-TYPE
    SYNTAX          SEQUENCE OF SonusSweCapacityEstimationEntry
    MAX-ACCESS      not-accessible
    STATUS          current
    DESCRIPTION     
            "
             This table stores the populated SWe capacity for different custom traffic profiles created.
             "
    ::= { sonusSystemSweMIB 3 }

sonusSweCapacityEstimationEntry OBJECT-TYPE
    SYNTAX          SonusSweCapacityEstimationEntry
    MAX-ACCESS      not-accessible
    STATUS          current
    DESCRIPTION     
            ""
    INDEX           { sonusSweCapacityEstimationName }
    ::= { sonusSweCapacityEstimationTable 1 }

SonusSweCapacityEstimationEntry ::=
    SEQUENCE {
        sonusSweCapacityEstimationName  SonusSystemSWeProfileName,
        sonusSweCapacityEstimationEstimatedSessionCapacity                  Unsigned32,
        sonusSweCapacityEstimationEstimatedNumSubscribers                 Unsigned32,
        sonusSweCapacityEstimationEstimatedCps      Unsigned32,
        sonusSweCapacityEstimationEstimatedRegistrationCapacity                       Unsigned32,
        sonusSweCapacityEstimationEstimatedRefreshRegisterCapacity                          Unsigned32,
        sonusSweCapacityEstimationEstimatedProtectedLinkBandwidth                         Unsigned32,
        sonusSweCapacityEstimationEstimatedProtectedPPS               SonusSystemSWePPStype,
        sonusSweCapacityEstimationMaxPassthroughSessions                Unsigned32,
        sonusSweCapacityEstimationMaxCryptoSessions           Unsigned32,
        sonusSweCapacityEstimationEstimatedTxPPS        SonusSystemSWePPStype,
        sonusSweCapacityEstimationEstimatedRxPPS        SonusSystemSWePPStype
    }

sonusSweCapacityEstimationName OBJECT-TYPE
    SYNTAX          SonusSystemSWeProfileName
    MAX-ACCESS      not-accessible
    STATUS          current
    DESCRIPTION     
            "
             Name of the profile referenced from sweTrafficProfiles.
             "
    ::= { sonusSweCapacityEstimationEntry 1 }

sonusSweCapacityEstimationEstimatedSessionCapacity OBJECT-TYPE
    SYNTAX          Unsigned32
    MAX-ACCESS      read-only
    STATUS          current
    DESCRIPTION     
            "
             Estimated number of sessions supported in the System.
             "
    ::= { sonusSweCapacityEstimationEntry 2 }

sonusSweCapacityEstimationEstimatedNumSubscribers OBJECT-TYPE
    SYNTAX          Unsigned32
    MAX-ACCESS      read-only
    STATUS          current
    DESCRIPTION     
            "
             Estimated number of subscribers supported in the System.
             "
    ::= { sonusSweCapacityEstimationEntry 3 }

sonusSweCapacityEstimationEstimatedCps OBJECT-TYPE
    SYNTAX          Unsigned32
    MAX-ACCESS      read-only
    STATUS          current
    DESCRIPTION     
            "
             Estimated maximum CPS supported in this System.
             "
    ::= { sonusSweCapacityEstimationEntry 4 }

sonusSweCapacityEstimationEstimatedRegistrationCapacity OBJECT-TYPE
    SYNTAX          Unsigned32
    MAX-ACCESS      read-only
    STATUS          current
    DESCRIPTION     
            "
             Estimated maximum Registrations/sec supported in this System.
             "
    ::= { sonusSweCapacityEstimationEntry 5 }

sonusSweCapacityEstimationEstimatedRefreshRegisterCapacity OBJECT-TYPE
    SYNTAX          Unsigned32
    MAX-ACCESS      read-only
    STATUS          current
    DESCRIPTION     
            "
             Estimated maximum Refresh Registrations/sec supported in this System.
             "
    ::= { sonusSweCapacityEstimationEntry 6 }

sonusSweCapacityEstimationEstimatedProtectedLinkBandwidth OBJECT-TYPE
    SYNTAX          Unsigned32
    MAX-ACCESS      read-only
    STATUS          obsolete
    DESCRIPTION     
            "
             Estimated maximum Link Bandwidth supported in this System.
             "
    ::= { sonusSweCapacityEstimationEntry 7 }

sonusSweCapacityEstimationEstimatedProtectedPPS OBJECT-TYPE
    SYNTAX          SonusSystemSWePPStype
    MAX-ACCESS      read-only
    STATUS          current
    DESCRIPTION     
            "
             Estimated maximum protected PPS supported in this System in Mpps.
             "
    ::= { sonusSweCapacityEstimationEntry 8 }

sonusSweCapacityEstimationMaxPassthroughSessions OBJECT-TYPE
    SYNTAX          Unsigned32
    MAX-ACCESS      read-only
    STATUS          current
    DESCRIPTION     
            "
             Estimated maximum pass thru calls supported in this System.
             "
    ::= { sonusSweCapacityEstimationEntry 9 }

sonusSweCapacityEstimationMaxCryptoSessions OBJECT-TYPE
    SYNTAX          Unsigned32
    MAX-ACCESS      read-only
    STATUS          current
    DESCRIPTION     
            "
             Estimated maximum transcoded calls supported in this System.
             "
    ::= { sonusSweCapacityEstimationEntry 10 }

sonusSweCapacityEstimationEstimatedTxPPS OBJECT-TYPE
    SYNTAX          SonusSystemSWePPStype
    MAX-ACCESS      read-only
    STATUS          current
    DESCRIPTION     
            "
             Estimated TX PPS supported in this System in Mpps.
             "
    ::= { sonusSweCapacityEstimationEntry 11 }

sonusSweCapacityEstimationEstimatedRxPPS OBJECT-TYPE
    SYNTAX          SonusSystemSWePPStype
    MAX-ACCESS      read-only
    STATUS          current
    DESCRIPTION     
            "
             Estimated RX PPS supported in this System in Mpps.
             "
    ::= { sonusSweCapacityEstimationEntry 12 }

END -- end of module SONUS-SYSTEM-SWE-MIB.
