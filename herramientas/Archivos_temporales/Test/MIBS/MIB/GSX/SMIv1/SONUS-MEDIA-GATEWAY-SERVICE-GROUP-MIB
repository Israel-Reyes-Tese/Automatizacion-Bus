--
-- This SMIv1 module has been generated by smidump 0.2-cvs. Do not edit.
--

SONUS-MEDIA-GATEWAY-SERVICE-GROUP-MIB DEFINITIONS ::= BEGIN

IMPORTS
    OBJECT-TYPE
        FROM RFC-1212
    IpAddress
        FROM RFC1155-SMI
    DisplayString, RowStatus
        FROM SNMPv2-TC
    sonusSignallingMIBs
        FROM SONUS-SMI
    SonusBoolean, SonusName, SonusNameReference, SonusShelfIndex, 
    SonusSlotIndex, SonusSupportFlag
        FROM SONUS-TC;

sonusMediaGatewayServiceGroupMIB OBJECT IDENTIFIER
    ::= { sonusSignallingMIBs 3 }

-- sonusMediaGatewayServiceGroupMIB MODULE-IDENTITY
--     LAST-UPDATED    "201105240000Z"
--     ORGANIZATION    
--             "Sonus Networks, Inc."
--     CONTACT-INFO    
--             "   Customer Support    
--              Sonus Networks, Inc.
--              7 Technology Park Drive
--              Westford, MA 01886
--              USA
--              
--              Tel: 978-614-8100
--              Fax: 978-614-8609"
--     DESCRIPTION     
--             "The MIB Module for Media Gateway Service Group management."
--     ::= { sonusSignallingMIBs 3 }


sonusMediaGatewayServiceGroupMIBObjects OBJECT IDENTIFIER
    ::= { sonusMediaGatewayServiceGroupMIB 1 }

sonusMgsgServiceGrp OBJECT IDENTIFIER
    ::= { sonusMediaGatewayServiceGroupMIBObjects 1 }

sonusMgsgServiceGrpNextIndex OBJECT-TYPE
    SYNTAX          Gauge
    ACCESS          read-only
    STATUS          mandatory
    DESCRIPTION     
            "The next valid index to use when creating a new sonusMgsgServiceGrpEntry"
    ::= { sonusMgsgServiceGrp 1 }

sonusMgsgServiceGrpTable OBJECT-TYPE
    SYNTAX          SEQUENCE OF SonusMgsgServiceGrpEntry
    ACCESS          not-accessible
    STATUS          mandatory
    DESCRIPTION     
            "This table contains information about each Media Gateway Service Group
             configured to be a member of the node. 
             A management entity may create rows for Service Group that are
             anticipated to be supported in the future."
    ::= { sonusMgsgServiceGrp 2 }

sonusMgsgServiceGrpEntry OBJECT-TYPE
    SYNTAX          SonusMgsgServiceGrpEntry
    ACCESS          not-accessible
    STATUS          mandatory
    DESCRIPTION     
            "This table describes the Media Gateway Service Groups that are configured as
             members of the Marlin Node."
    INDEX           { sonusMgsgServiceGrpListIndex }
    ::= { sonusMgsgServiceGrpTable 1 }

SonusMgsgServiceGrpEntry ::=
    SEQUENCE {
        sonusMgsgServiceGrpListIndex    Gauge,
        sonusMgsgServiceGrpName         SonusName,
        sonusMgsgServiceGrpAdminState   INTEGER,
        sonusMgsgServiceGrpControllerName SonusNameReference,
        sonusMgsgServiceGrpType         INTEGER,
        sonusMgsgServiceGrpMode         INTEGER,
        sonusMgsgServiceGrpAction       INTEGER,
        sonusMgsgServiceGrpTimeout      Gauge,
        sonusMgsgServiceGrpRowStatus    RowStatus,
        sonusMgsgServiceGrpTonePkgExtn  DisplayString,
        sonusMgsgServiceGrpH248DeviceName DisplayString,
        sonusMgsgServiceGrpCallAgentName SonusNameReference,
        sonusMgsgServiceGrpMgType       INTEGER,
        sonusMgsgServiceGrpG303PriorityDigitMap       DisplayString,
        sonusMgsgServiceGrpOffHookNotification      SonusSupportFlag
    }

sonusMgsgServiceGrpListIndex OBJECT-TYPE
    SYNTAX          Gauge
    ACCESS          read-only
    STATUS          mandatory
    DESCRIPTION     
            "The index of the Media Gateway Service Group entry."
    ::= { sonusMgsgServiceGrpEntry 1 }

sonusMgsgServiceGrpName OBJECT-TYPE
    SYNTAX          SonusName
    ACCESS          read-write
    STATUS          mandatory
    DESCRIPTION     
            "The name of the Media Gateway Service Group."
    ::= { sonusMgsgServiceGrpEntry 2 }

sonusMgsgServiceGrpAdminState OBJECT-TYPE
    SYNTAX          INTEGER { disabled(1), enabled(2) }
    ACCESS          read-write
    STATUS          mandatory
    DESCRIPTION     
            "The admin state of the Media Gateway Service Group."
    DEFVAL          { 1 }
    ::= { sonusMgsgServiceGrpEntry 3 }

sonusMgsgServiceGrpControllerName OBJECT-TYPE
    SYNTAX          SonusNameReference
    ACCESS          read-write
    STATUS          mandatory
    DESCRIPTION     
            "The Name of the Media Gateway Controller which controls this service group"
    ::= { sonusMgsgServiceGrpEntry 4 }

sonusMgsgServiceGrpType OBJECT-TYPE
    SYNTAX          INTEGER { ipdc(1), mgcp(2), h248(3) }
    ACCESS          read-write
    STATUS          mandatory
    DESCRIPTION     
            "The type(protocol) of media gateway control protocol
             Note: ipdc value is obsolete and can not be used"
    DEFVAL          { mgcp }
    ::= { sonusMgsgServiceGrpEntry 5 }

sonusMgsgServiceGrpMode OBJECT-TYPE
    SYNTAX          INTEGER { blocked(1), unblocked(2) }
    ACCESS          read-write
    STATUS          mandatory
    DESCRIPTION     
            "Whether the Service Group is in Blocked or Unblocked Mode"
    DEFVAL          { blocked }
    ::= { sonusMgsgServiceGrpEntry 6 }

sonusMgsgServiceGrpAction OBJECT-TYPE
    SYNTAX          INTEGER { dryup(1), force(2) }
    ACCESS          read-write
    STATUS          mandatory
    DESCRIPTION     
            "Indicates whether the service group is to be put in blocked immediately or 
             after a dry-up period"
    DEFVAL          { dryup }
    ::= { sonusMgsgServiceGrpEntry 7 }

sonusMgsgServiceGrpTimeout OBJECT-TYPE
    SYNTAX          Gauge (1..1440)
    ACCESS          read-write
    STATUS          mandatory
    DESCRIPTION     
            "The TimeOut Period for DryUp In Minutes"
    DEFVAL          { 60 }
    ::= { sonusMgsgServiceGrpEntry 8 }

sonusMgsgServiceGrpRowStatus OBJECT-TYPE
    SYNTAX          RowStatus
    ACCESS          read-write
    STATUS          mandatory
    DESCRIPTION     
            ""
    ::= { sonusMgsgServiceGrpEntry 9 }

sonusMgsgServiceGrpTonePkgExtn OBJECT-TYPE
    SYNTAX          DisplayString (SIZE(0..23))
    ACCESS          read-write
    STATUS          mandatory
    DESCRIPTION     
            "GSX Tone Package name extension."
    DEFVAL          { "mg" }
    ::= { sonusMgsgServiceGrpEntry 10 }

sonusMgsgServiceGrpH248DeviceName OBJECT-TYPE
    SYNTAX          DisplayString (SIZE(0..23))
    ACCESS          read-write
    STATUS          mandatory
    DESCRIPTION     
            "The name of the Virtual Media Gateway to which this service group
             belongs.  This name will be used as the Message Identifier (MID)
             		 when sending commands from this Service Group to an H.248 Media
             Gateway Controller (MGC).  If this field is not configured, then
             		 'sonusGatewayName' will be used as the MID.
             		 Note: This field is only applicable to H.248, not MGCP."
    ::= { sonusMgsgServiceGrpEntry 11 }

sonusMgsgServiceGrpCallAgentName OBJECT-TYPE
    SYNTAX          SonusNameReference
    ACCESS          read-write
    STATUS          mandatory
    DESCRIPTION     
            "The name of the Call Agent to which this service group belongs.
             When circuits belonging to this service group generate an H248
             message (i.e., NOTIFY or SERVICECHANGE), the configured call agent
             name determines which H.248 Media Gateway Controller (MGC) the
             message is sent to.
             		 Note: This field is only applicable to H.248, not MGCP."
    ::= { sonusMgsgServiceGrpEntry 12 }

sonusMgsgServiceGrpMgType OBJECT-TYPE
    SYNTAX          INTEGER { normal(1), gr303idt(2), bgf(3), ganc(4) }
    ACCESS          read-write
    STATUS          mandatory
    DESCRIPTION     
            "Media Gateway type - GR303-IDT, BGF, GANC based Media Gateway.
             Anything which is not listed above is normal"
    DEFVAL          { normal }
    ::= { sonusMgsgServiceGrpEntry 13 }

sonusMgsgServiceGrpG303PriorityDigitMap OBJECT-TYPE
    SYNTAX          DisplayString (SIZE(0..255))
    ACCESS          read-write
    STATUS          mandatory
    DESCRIPTION     
            "Stores the Priority Digit Map for GR303. This will be used in Overload feature during GR303 calls"
    DEFVAL          { "T:10,S:4,L:10,(911)" }
    ::= { sonusMgsgServiceGrpEntry 14 }

sonusMgsgServiceGrpOffHookNotification OBJECT-TYPE
    SYNTAX          SonusSupportFlag
    ACCESS          read-write
    STATUS          mandatory
    DESCRIPTION     
            "Controls the sending of off-hook notification along with dialed digits in overload scenarios"
    DEFVAL          { unsupported }
    ::= { sonusMgsgServiceGrpEntry 15 }

sonusMgsgServiceGrpStatTable OBJECT-TYPE
    SYNTAX          SEQUENCE OF SonusMgsgServiceGrpStatEntry
    ACCESS          not-accessible
    STATUS          mandatory
    DESCRIPTION     
            "This table contains status information about each MGSG service group
             in the Marlin Switch node.  "
    ::= { sonusMediaGatewayServiceGroupMIBObjects 2 }

sonusMgsgServiceGrpStatEntry OBJECT-TYPE
    SYNTAX          SonusMgsgServiceGrpStatEntry
    ACCESS          not-accessible
    STATUS          mandatory
    DESCRIPTION     
            "This table describes the status of MGSG Service Groups"
    INDEX           { sonusMgsgServiceGrpStatListIndex }
    ::= { sonusMgsgServiceGrpStatTable 1 }

SonusMgsgServiceGrpStatEntry ::=
    SEQUENCE {
        sonusMgsgServiceGrpStatListIndex Gauge,
        sonusMgsgServiceGrpStatName     SonusNameReference,
        sonusMgsgServiceGrpStatStatus   INTEGER
    }

sonusMgsgServiceGrpStatListIndex OBJECT-TYPE
    SYNTAX          Gauge
    ACCESS          read-only
    STATUS          mandatory
    DESCRIPTION     
            "The index of the MGSG Service Group."
    ::= { sonusMgsgServiceGrpStatEntry 1 }

sonusMgsgServiceGrpStatName OBJECT-TYPE
    SYNTAX          SonusNameReference
    ACCESS          read-only
    STATUS          mandatory
    DESCRIPTION     
            "The name of the MGSG Service Group."
    ::= { sonusMgsgServiceGrpStatEntry 2 }

sonusMgsgServiceGrpStatStatus OBJECT-TYPE
    SYNTAX          INTEGER { available(1), unavailable(2), blocked(3) }
    ACCESS          read-only
    STATUS          mandatory
    DESCRIPTION     
            "The state of the MGSG Service Group."
    ::= { sonusMgsgServiceGrpStatEntry 3 }

sonusMgsgCktTable OBJECT-TYPE
    SYNTAX          SEQUENCE OF SonusMgsgCktEntry
    ACCESS          not-accessible
    STATUS          mandatory
    DESCRIPTION     
            "The Mgsg Ckt table describes the ckts in a MGSG
             service Group."
    ::= { sonusMediaGatewayServiceGroupMIBObjects 3 }

sonusMgsgCktEntry OBJECT-TYPE
    SYNTAX          SonusMgsgCktEntry
    ACCESS          not-accessible
    STATUS          mandatory
    DESCRIPTION     
            "This is the admin table for MGSG Circuits"
    INDEX           { sonusMgsgCktShelfIndex, sonusMgsgCktSlotIndex, 
                      sonusMgsgCktDs1Index, sonusMgsgCktDs0Index }
    ::= { sonusMgsgCktTable 1 }

SonusMgsgCktEntry ::=
    SEQUENCE {
        sonusMgsgCktShelfIndex          SonusShelfIndex,
        sonusMgsgCktSlotIndex           SonusSlotIndex,
        sonusMgsgCktDs1Index            Gauge,
        sonusMgsgCktDs0Index            Gauge,
        sonusMgsgCktSrvGrpName          SonusNameReference,
        sonusMgsgCktMode                INTEGER,
        sonusMgsgCktAction              INTEGER,
        sonusMgsgCktTimeout             Gauge,
        sonusMgsgCktAdminState          INTEGER,
        sonusMgsgCktProfileName         SonusNameReference,
        sonusMgsgCktType                INTEGER,
        sonusMgsgCktDchanSwitchType     INTEGER,
        sonusMgsgCktRowStatus           RowStatus
    }

sonusMgsgCktShelfIndex OBJECT-TYPE
    SYNTAX          SonusShelfIndex
    ACCESS          read-only
    STATUS          mandatory
    DESCRIPTION     
            "The Shelf Index for this Ckt Table"
    ::= { sonusMgsgCktEntry 1 }

sonusMgsgCktSlotIndex OBJECT-TYPE
    SYNTAX          SonusSlotIndex
    ACCESS          read-only
    STATUS          mandatory
    DESCRIPTION     
            "The Slot Index for this Ckt Table"
    ::= { sonusMgsgCktEntry 2 }

sonusMgsgCktDs1Index OBJECT-TYPE
    SYNTAX          Gauge (1..28)
    ACCESS          read-only
    STATUS          mandatory
    DESCRIPTION     
            "The Ds1 Index for this Ckt Table"
    ::= { sonusMgsgCktEntry 3 }

sonusMgsgCktDs0Index OBJECT-TYPE
    SYNTAX          Gauge (1..32)
    ACCESS          read-only
    STATUS          mandatory
    DESCRIPTION     
            "Identifies the channel the ckt represents."
    ::= { sonusMgsgCktEntry 4 }

sonusMgsgCktSrvGrpName OBJECT-TYPE
    SYNTAX          SonusNameReference
    ACCESS          read-write
    STATUS          mandatory
    DESCRIPTION     
            "The name of the MGSG Service Group this ckt is under."
    ::= { sonusMgsgCktEntry 5 }

sonusMgsgCktMode OBJECT-TYPE
    SYNTAX          INTEGER { blocked(1), unblocked(2) }
    ACCESS          read-write
    STATUS          mandatory
    DESCRIPTION     
            "Whether the Circuit is in Blocked or Unblocked Mode"
    DEFVAL          { blocked }
    ::= { sonusMgsgCktEntry 6 }

sonusMgsgCktAction OBJECT-TYPE
    SYNTAX          INTEGER { dryup(1), force(2) }
    ACCESS          read-write
    STATUS          mandatory
    DESCRIPTION     
            "Indicates whether the circuit is to be put in blocked immediately or 
             after a dry-up period"
    DEFVAL          { dryup }
    ::= { sonusMgsgCktEntry 7 }

sonusMgsgCktTimeout OBJECT-TYPE
    SYNTAX          Gauge (1..1440)
    ACCESS          read-write
    STATUS          mandatory
    DESCRIPTION     
            "The TimeOut Period for DryUp In Minutes"
    DEFVAL          { 60 }
    ::= { sonusMgsgCktEntry 8 }

sonusMgsgCktAdminState OBJECT-TYPE
    SYNTAX          INTEGER { disabled(1), enabled(2) }
    ACCESS          read-write
    STATUS          mandatory
    DESCRIPTION     
            "The admin state of the MGSG Ckt."
    ::= { sonusMgsgCktEntry 9 }

sonusMgsgCktProfileName OBJECT-TYPE
    SYNTAX          SonusNameReference
    ACCESS          read-write
    STATUS          mandatory
    DESCRIPTION     
            "The ckt profile name assigned to the MGSG ckt."
    ::= { sonusMgsgCktEntry 10 }

sonusMgsgCktType OBJECT-TYPE
    SYNTAX          INTEGER { data(1), dchan-user(2), dchan-ntwk(3) }
    ACCESS          read-write
    STATUS          mandatory
    DESCRIPTION     
            "The type of the MGSG Ckt. (data or a D-channel)"
    DEFVAL          { 1 }
    ::= { sonusMgsgCktEntry 11 }

sonusMgsgCktDchanSwitchType OBJECT-TYPE
    SYNTAX          INTEGER { ni2(1), sw4ess(2), sw5esscust(3), dms(4), 
                        kdd(5), ntt(6), itu(7), net5(8), sw1tr6(9), 
                        ts014(10), vn(11) }
    ACCESS          read-write
    STATUS          mandatory
    DESCRIPTION     
            "For Ckts of type D-chan this describes the switch type that D-chan is connected to."
    DEFVAL          { itu }
    ::= { sonusMgsgCktEntry 12 }

sonusMgsgCktRowStatus OBJECT-TYPE
    SYNTAX          RowStatus
    ACCESS          read-write
    STATUS          mandatory
    DESCRIPTION     
            ""
    ::= { sonusMgsgCktEntry 13 }

sonusMgsgCktStatTable OBJECT-TYPE
    SYNTAX          SEQUENCE OF SonusMgsgCktStatEntry
    ACCESS          not-accessible
    STATUS          mandatory
    DESCRIPTION     
            "This table contains status information about each MGSG ckt 
             in the Marlin Switch node. ."
    ::= { sonusMediaGatewayServiceGroupMIBObjects 4 }

sonusMgsgCktStatEntry OBJECT-TYPE
    SYNTAX          SonusMgsgCktStatEntry
    ACCESS          not-accessible
    STATUS          mandatory
    DESCRIPTION     
            "This table describes the status of the configured MGSG ckts."
    INDEX           { sonusMgsgCktStatShelfIndex, 
                      sonusMgsgCktStatSlotIndex, 
                      sonusMgsgCktStatDs1Index, sonusMgsgCktStatDs0Index }
    ::= { sonusMgsgCktStatTable 1 }

SonusMgsgCktStatEntry ::=
    SEQUENCE {
        sonusMgsgCktStatShelfIndex      SonusShelfIndex,
        sonusMgsgCktStatSlotIndex       SonusSlotIndex,
        sonusMgsgCktStatDs1Index        Gauge,
        sonusMgsgCktStatDs0Index        Gauge,
        sonusMgsgCktStatSrvGrpName      SonusNameReference,
        sonusMgsgCktStatMgcState        INTEGER,
        sonusMgsgCktStatLocalHwState    INTEGER,
        sonusMgsgCktStatDryupInProgress SonusBoolean
    }

sonusMgsgCktStatShelfIndex OBJECT-TYPE
    SYNTAX          SonusShelfIndex
    ACCESS          read-only
    STATUS          mandatory
    DESCRIPTION     
            "The Shelf Index for this Ckt Table"
    ::= { sonusMgsgCktStatEntry 1 }

sonusMgsgCktStatSlotIndex OBJECT-TYPE
    SYNTAX          SonusSlotIndex
    ACCESS          read-only
    STATUS          mandatory
    DESCRIPTION     
            "The Slot Index for this Ckt Table"
    ::= { sonusMgsgCktStatEntry 2 }

sonusMgsgCktStatDs1Index OBJECT-TYPE
    SYNTAX          Gauge
    ACCESS          read-only
    STATUS          mandatory
    DESCRIPTION     
            "The Ds1 Index for this Ckt Table"
    ::= { sonusMgsgCktStatEntry 3 }

sonusMgsgCktStatDs0Index OBJECT-TYPE
    SYNTAX          Gauge
    ACCESS          read-only
    STATUS          mandatory
    DESCRIPTION     
            "Identifies the channel the ckt represents."
    ::= { sonusMgsgCktStatEntry 4 }

sonusMgsgCktStatSrvGrpName OBJECT-TYPE
    SYNTAX          SonusNameReference
    ACCESS          read-only
    STATUS          mandatory
    DESCRIPTION     
            "The name of the MGSG Service Group this ckt is under."
    ::= { sonusMgsgCktStatEntry 5 }

sonusMgsgCktStatMgcState OBJECT-TYPE
    SYNTAX          INTEGER { notPresent(1), outOfService(2), 
                        maintenance(3), blocked(4), loopback(5), idle(6), 
                        inUse(7), connected(8), disabled(9), 
                        dualToneLoop(10) }
    ACCESS          read-only
    STATUS          mandatory
    DESCRIPTION     
            "The state of MGSG ckt, as reported to the Media Gateway Controller "
    ::= { sonusMgsgCktStatEntry 6 }

sonusMgsgCktStatLocalHwState OBJECT-TYPE
    SYNTAX          INTEGER { available(1), unavailable(2) }
    ACCESS          read-only
    STATUS          mandatory
    DESCRIPTION     
            "The local state of the MGSG ckt from a hardware perspective"
    ::= { sonusMgsgCktStatEntry 7 }

sonusMgsgCktStatDryupInProgress OBJECT-TYPE
    SYNTAX          SonusBoolean
    ACCESS          read-only
    STATUS          mandatory
    DESCRIPTION     
            "This object indicates whether a dry-up is in progress or not on the circuit"
    ::= { sonusMgsgCktStatEntry 8 }

sonusMgsgInterfaceObjects OBJECT IDENTIFIER
    ::= { sonusMediaGatewayServiceGroupMIBObjects 5 }

sonusMgsgIntfTableObjects OBJECT IDENTIFIER
    ::= { sonusMgsgInterfaceObjects 1 }

sonusMgsgIntfTableNextIndex OBJECT-TYPE
    SYNTAX          Gauge
    ACCESS          read-only
    STATUS          mandatory
    DESCRIPTION     
            "The next valid index to use when creating a new sonusMgsgIntfTable"
    ::= { sonusMgsgIntfTableObjects 1 }

sonusMgsgIntfTableTable OBJECT-TYPE
    SYNTAX          SEQUENCE OF SonusMgsgIntfTableEntry
    ACCESS          not-accessible
    STATUS          mandatory
    DESCRIPTION     
            "This MIB table is used to create a name for a IP Term Interface table."
    ::= { sonusMgsgIntfTableObjects 2 }

sonusMgsgIntfTableEntry OBJECT-TYPE
    SYNTAX          SonusMgsgIntfTableEntry
    ACCESS          not-accessible
    STATUS          mandatory
    DESCRIPTION     
            "This MIB table is used to create a name for a IP Term Interface."
    INDEX           { sonusMgsgIntfTableIndex }
    ::= { sonusMgsgIntfTableTable 1 }

SonusMgsgIntfTableEntry ::=
    SEQUENCE {
        sonusMgsgIntfTableIndex         Gauge,
        sonusMgsgIntfTableName          SonusName,
        sonusMgsgIntfTableRowStatus     RowStatus,
        sonusMgsgIntfTableSlots         DisplayString,
        sonusMgsgIntfTableSrvGrpName    SonusNameReference,
        sonusMgsgIntfTableMode          INTEGER,
        sonusMgsgIntfTableAction        INTEGER,
        sonusMgsgIntfTableTimeout       Gauge,
        sonusMgsgIntfTableAdminState    INTEGER
    }

sonusMgsgIntfTableIndex OBJECT-TYPE
    SYNTAX          Gauge
    ACCESS          read-only
    STATUS          mandatory
    DESCRIPTION     
            "A unique index for this IP Term Interface name."
    ::= { sonusMgsgIntfTableEntry 1 }

sonusMgsgIntfTableName OBJECT-TYPE
    SYNTAX          SonusName
    ACCESS          read-write
    STATUS          mandatory
    DESCRIPTION     
            "The name of the IP Term Interface."
    ::= { sonusMgsgIntfTableEntry 2 }

sonusMgsgIntfTableRowStatus OBJECT-TYPE
    SYNTAX          RowStatus
    ACCESS          read-write
    STATUS          mandatory
    DESCRIPTION     
            "This is for SNMP use."
    ::= { sonusMgsgIntfTableEntry 3 }

sonusMgsgIntfTableSlots OBJECT-TYPE
    SYNTAX          DisplayString (SIZE(0..23))
    ACCESS          read-write
    STATUS          mandatory
    DESCRIPTION     
            "Slots for IP Term this interface."
    DEFVAL          { "all" }
    ::= { sonusMgsgIntfTableEntry 4 }

sonusMgsgIntfTableSrvGrpName OBJECT-TYPE
    SYNTAX          SonusNameReference
    ACCESS          read-write
    STATUS          mandatory
    DESCRIPTION     
            "The name of the MGSG Service Group for this IP Term Interface."
    ::= { sonusMgsgIntfTableEntry 5 }

sonusMgsgIntfTableMode OBJECT-TYPE
    SYNTAX          INTEGER { blocked(1), unblocked(2) }
    ACCESS          read-write
    STATUS          mandatory
    DESCRIPTION     
            "Interface Service Mode: Blocked or Unblocked"
    DEFVAL          { blocked }
    ::= { sonusMgsgIntfTableEntry 6 }

sonusMgsgIntfTableAction OBJECT-TYPE
    SYNTAX          INTEGER { dryup(1), force(2) }
    ACCESS          read-write
    STATUS          mandatory
    DESCRIPTION     
            "Select whether the interface is blocked immediately or after a dryup period"
    DEFVAL          { dryup }
    ::= { sonusMgsgIntfTableEntry 7 }

sonusMgsgIntfTableTimeout OBJECT-TYPE
    SYNTAX          Gauge (1..1440)
    ACCESS          read-write
    STATUS          mandatory
    DESCRIPTION     
            "The TimeOut Period for Interface DryUp In Minutes"
    DEFVAL          { 60 }
    ::= { sonusMgsgIntfTableEntry 8 }

sonusMgsgIntfTableAdminState OBJECT-TYPE
    SYNTAX          INTEGER { disabled(1), enabled(2) }
    ACCESS          read-write
    STATUS          mandatory
    DESCRIPTION     
            "The admin state of the Interface"
    ::= { sonusMgsgIntfTableEntry 9 }

sonusMgsgIntfStatTable OBJECT-TYPE
    SYNTAX          SEQUENCE OF SonusMgsgIntfStatEntry
    ACCESS          not-accessible
    STATUS          mandatory
    DESCRIPTION     
            "This table contains status information about each MGSG Interface."
    ::= { sonusMgsgIntfTableObjects 3 }

sonusMgsgIntfStatEntry OBJECT-TYPE
    SYNTAX          SonusMgsgIntfStatEntry
    ACCESS          not-accessible
    STATUS          mandatory
    DESCRIPTION     
            "This table describes the status of MGSG Interfaces."
    INDEX           { sonusMgsgIntfStatListIndex }
    ::= { sonusMgsgIntfStatTable 1 }

SonusMgsgIntfStatEntry ::=
    SEQUENCE {
        sonusMgsgIntfStatListIndex      Gauge,
        sonusMgsgIntfStatName           SonusNameReference,
        sonusMgsgIntfStatStatus         INTEGER,
        sonusMgsgIntfStatLocalHwState   INTEGER,
        sonusMgsgIntfStatDryupInProgress SonusBoolean
    }

sonusMgsgIntfStatListIndex OBJECT-TYPE
    SYNTAX          Gauge
    ACCESS          read-only
    STATUS          mandatory
    DESCRIPTION     
            "The index of the MGSG Interface."
    ::= { sonusMgsgIntfStatEntry 1 }

sonusMgsgIntfStatName OBJECT-TYPE
    SYNTAX          SonusNameReference
    ACCESS          read-only
    STATUS          mandatory
    DESCRIPTION     
            "The name of the MGSG Interface."
    ::= { sonusMgsgIntfStatEntry 2 }

sonusMgsgIntfStatStatus OBJECT-TYPE
    SYNTAX          INTEGER { available(1), unavailable(2), blocked(3) }
    ACCESS          read-only
    STATUS          mandatory
    DESCRIPTION     
            "The state of the MGSG Interface."
    ::= { sonusMgsgIntfStatEntry 3 }

sonusMgsgIntfStatLocalHwState OBJECT-TYPE
    SYNTAX          INTEGER { available(1), unavailable(2) }
    ACCESS          read-only
    STATUS          mandatory
    DESCRIPTION     
            "The local state of the Interface NIF hardware"
    ::= { sonusMgsgIntfStatEntry 4 }

sonusMgsgIntfStatDryupInProgress OBJECT-TYPE
    SYNTAX          SonusBoolean
    ACCESS          read-only
    STATUS          mandatory
    DESCRIPTION     
            "True when interface dryup is in progress"
    ::= { sonusMgsgIntfStatEntry 5 }

sonusMgsgIntfVlanObjects OBJECT IDENTIFIER
    ::= { sonusMgsgInterfaceObjects 2 }

sonusMgsgIntfVlanTable OBJECT-TYPE
    SYNTAX          SEQUENCE OF SonusMgsgIntfVlanEntry
    ACCESS          not-accessible
    STATUS          mandatory
    DESCRIPTION     
            "This MIB table is for IP Term Interface Entries."
    ::= { sonusMgsgIntfVlanObjects 1 }

sonusMgsgIntfVlanEntry OBJECT-TYPE
    SYNTAX          SonusMgsgIntfVlanEntry
    ACCESS          not-accessible
    STATUS          mandatory
    DESCRIPTION     
            "This MIB table is for IP Term Interface Entries."
    INDEX           { sonusMgsgIntfVlanTableIndex, 
                      sonusMgsgIntfVlanTagIndex }
    ::= { sonusMgsgIntfVlanTable 1 }

SonusMgsgIntfVlanEntry ::=
    SEQUENCE {
        sonusMgsgIntfVlanTableIndex     Gauge,
        sonusMgsgIntfVlanTagIndex       Gauge,
        sonusMgsgIntfVlanNifGrp         SonusNameReference,
        sonusMgsgIntfVlanRowStatus      RowStatus,
        sonusMgsgIntfName               DisplayString
    }

sonusMgsgIntfVlanTableIndex OBJECT-TYPE
    SYNTAX          Gauge
    ACCESS          read-only
    STATUS          mandatory
    DESCRIPTION     
            "Unique IP Term Interface index."
    ::= { sonusMgsgIntfVlanEntry 1 }

sonusMgsgIntfVlanTagIndex OBJECT-TYPE
    SYNTAX          Gauge
    ACCESS          read-only
    STATUS          mandatory
    DESCRIPTION     
            "VLAN tag index"
    ::= { sonusMgsgIntfVlanEntry 2 }

sonusMgsgIntfVlanNifGrp OBJECT-TYPE
    SYNTAX          SonusNameReference
    ACCESS          read-write
    STATUS          mandatory
    DESCRIPTION     
            "VLAN NIF Group."
    ::= { sonusMgsgIntfVlanEntry 3 }

sonusMgsgIntfVlanRowStatus OBJECT-TYPE
    SYNTAX          RowStatus
    ACCESS          read-write
    STATUS          mandatory
    DESCRIPTION     
            "This is for SNMP use."
    ::= { sonusMgsgIntfVlanEntry 4 }

sonusMgsgIntfName OBJECT-TYPE
    SYNTAX          DisplayString
    ACCESS          read-write
    STATUS          mandatory
    DESCRIPTION     
            "The name of the IP Term Interface to which this VLAN object is bound"
    ::= { sonusMgsgIntfVlanEntry 5 }

sonusMediaGatewayServiceGroupMIBNotifications OBJECT IDENTIFIER
    ::= { sonusMediaGatewayServiceGroupMIB 2 }

sonusMediaGatewayServiceGroupMIBNotificationsPrefix OBJECT IDENTIFIER
    ::= { sonusMediaGatewayServiceGroupMIBNotifications 0 }

sonusMediaGatewayServiceGroupMIBNotificationsObjects OBJECT IDENTIFIER
    ::= { sonusMediaGatewayServiceGroupMIBNotifications 1 }

END -- end of module SONUS-MEDIA-GATEWAY-SERVICE-GROUP-MIB.
