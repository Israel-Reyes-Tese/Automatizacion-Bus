--
-- This SMIv2 module has been generated by smidump 0.2-cvs. Do not edit.
--

SONUS-APS-MIB DEFINITIONS ::= BEGIN

IMPORTS
    apsChanStatusCurrent, apsChanStatusSwitchovers, 
    apsStatusChannelMismatches, apsStatusCurrent, apsStatusFEPLFs, 
    apsStatusModeMismatches, apsStatusPSBFs
        FROM APS-MIB
    InterfaceIndex
        FROM IF-MIB
    MODULE-COMPLIANCE, NOTIFICATION-GROUP, OBJECT-GROUP
        FROM SNMPv2-CONF
    Counter32, Gauge32, Integer32, MODULE-IDENTITY, NOTIFICATION-TYPE, 
    OBJECT-TYPE
        FROM SNMPv2-SMI
    RowStatus, TEXTUAL-CONVENTION, TimeStamp
        FROM SNMPv2-TC
    sonusEventClass, sonusEventDescription, sonusEventLevel, 
    sonusEventTime, sonusSequenceId
        FROM SONUS-COMMON-MIB
    sonusServicesMIBs
        FROM SONUS-SMI
    SonusName
        FROM SONUS-TC;

sonusApsMIB MODULE-IDENTITY
    LAST-UPDATED    "200703280000Z"
    ORGANIZATION    
            "Sonus Networks, Inc."
    CONTACT-INFO    
            "   Customer Support    
             Sonus Networks, Inc.
             7 Technology Park Drive
             Westford, MA 01886
             USA
             
             Tel: 978-614-8100
             Fax: 978-614-8609"
    DESCRIPTION     
            "This management information module supports the configuration and
             management of SONET linear APS groups.  The definitions and
             descriptions used in this mib have been derived from
             Synchronous Optical Network (SONET) Transport Systems:
             Common Generic Criteria, GR-253-CORE Revision 2, January 1999,
             section 5.3. The MIB is also consistent with the Multiplex
             Section Protection (MSP) protocol as specified in ITU-T
             Recommendation G.783, Characteristics of synchronous digital
             hierarchy (SDH) equipment function blocks, Annex A and B.
             "
    REVISION        "200105242300Z"
    DESCRIPTION     
            "Initial version of this MIB, published as RFC xxxx."
    ::= { sonusServicesMIBs 15 }


SonusApsK1K2 ::= TEXTUAL-CONVENTION
    STATUS          deprecated
    DESCRIPTION     
            "This Textual Convention describes an object that stores
             a SONET K1 and K2 byte APS protocol field.
             
             K1 is located in the first octet, K2 is located in
             the second octet. Bits are numbered from left to right.
             
             Bits 1-4 of the K1 byte indicate a request.
             
             1111  Lockout of Protection
             1110  Forced Switch
             1101  SF - High Priority
             1100  SF - Low Priority
             1011  SD - High Priority
             1010  SD - Low Priority
             1001  not used
             1000  Manual Switch
             0111  not used
             0110  Wait-to-Restore
             0101  not used
             0100  Exercise
             0011  not used
             0010  Reverse Request
             0001  Do Not Revert
             0000  No Request
             
             Bits 5-8 of the K1 byte indicate the channel associated with the
             request defined in bits 1-4.
             
             0000 is the Null channel.
             
             1-14 are working channels.
             15   is the extra traffic channel
             
             Bits 1-4 of the K2 byte indicate a channel. The channel is
             defined with the same syntax as K1 Bits 5-8.
             
             
             Bit 5 of the K2 byte indicates the
             architecture.
             
             0 if the architecture is 1+1
             1 if the architecture is 1:n
             
             Bits 6-8 of the K2 byte indicates the
             mode.
             
             000 - 011 are reserved for future use
             
             100  indicates the mode is unidirectional
             101  indicates the mode is bidirectional
             
             110  RDI-L
             
             111  AIS-L
             "
    REFERENCE       
            "This Textual Convention describes an object that stores
             a SONET K1 and K2 byte APS protocol field.
             
             K1 is located in the first octet, K2 is located in
             the second octet. Bits are numbered from left to right.
             
             Bits 1-4 of the K1 byte indicate a request.
             
             1111  Lockout of Protection
             1110  Forced Switch
             1101  SF - High Priority
             1100  SF - Low Priority
             1011  SD - High Priority
             1010  SD - Low Priority
             1001  not used
             1000  Manual Switch
             0111  not used
             0110  Wait-to-Restore
             0101  not used
             0100  Exercise
             0011  not used
             0010  Reverse Request
             0001  Do Not Revert
             0000  No Request
             
             Bits 5-8 of the K1 byte indicate the channel associated with the
             request defined in bits 1-4.
             
             0000 is the Null channel.
             
             1-14 are working channels.
             15   is the extra traffic channel
             
             Bits 1-4 of the K2 byte indicate a channel. The channel is
             defined with the same syntax as K1 Bits 5-8.
             
             
             Bit 5 of the K2 byte indicates the
             architecture.
             
             0 if the architecture is 1+1
             1 if the architecture is 1:n
             
             Bits 6-8 of the K2 byte indicates the
             mode.
             
             000 - 011 are reserved for future use
             
             100  indicates the mode is unidirectional
             101  indicates the mode is bidirectional
             
             110  RDI-L
             
             111  AIS-L
             "
    SYNTAX          OCTET STRING (SIZE(2))

SonusApsSwitchCommand ::= TEXTUAL-CONVENTION
    STATUS          deprecated
    DESCRIPTION     
            "An APS switch command allows a user to perform protection
             switch actions.
             
             The Switch command values are:
             
             noCmd
             
             This value should be returned by a read request when no switch
             command has been written to the object in question since
             initialization. This value may not be used in a write operation.
             
             clear
             
             Clears all of the switch commands listed below for the specified
             channel.
             
             lockoutOfProtection
             
             Prevents any of the working channels from switching to the protection
             line. The specified channel should be the protection channel.
             
             forcedSwitchWorkToProtect
             
             Switches the specified working channel to the protection line.
             
             forcedSwitchProtectToWork
             
             Switches the working channel back from the protection
             line to the working line. The specified channel should be
             the protection channel.
             
             manualSwitchWorkToProtect
             
             Switches the specified working channel to the protection line.
             
             manualSwitchProtectToWork
             
             Switches the working channel back from the protection
             line to the working line. The specified channel should be
             the protection channel.
             
             exercise
             
             Exercises the protocol for a protection switch of the specified
             channel by issuing an Exercise request for that channel and
             checking the response on the APS channel.
                     "
    SYNTAX          INTEGER { noCmd(1), clear(2), lockoutOfProtection(3), 
                        forcedSwitchWorkToProtect(4), 
                        forcedSwitchProtectToWork(5), 
                        manualSwitchWorkToProtect(6), 
                        manualSwitchProtectToWork(7), exercise(8) }

SonusApsControlCommand ::= TEXTUAL-CONVENTION
    STATUS          deprecated
    DESCRIPTION     
            "An APS control command applies only to LTE that support the
             1:n architecture and performs the following actions.
             
             
             The Control command values are:
             
             noCmd
             
             This value should be returned by a read request when no control
             command has been written to the object in question since
             initialization. This value may not be used in a write operation.
             
             lockoutWorkingChannel
             
             Prevents the specified working channel from switching to the protection
             line.
             
             clearLockoutWorkingChannel
             
             Clears the lockout a working channel command for the channel specified.
                     "
    SYNTAX          INTEGER { noCmd(1), lockoutWorkingChannel(2), 
                        clearLockoutWorkingChannel(3) }

sonusApsMIBObjects OBJECT IDENTIFIER
    ::= { sonusApsMIB 1 }

sonusApsConfig OBJECT IDENTIFIER
    ::= { sonusApsMIBObjects 1 }

sonusApsConfigGroups OBJECT-TYPE
    SYNTAX          Gauge32
    MAX-ACCESS      read-only
    STATUS          deprecated
    DESCRIPTION     
            "The count of APS groups. This count includes all rows in
             sonusApsConfigTable."
    ::= { sonusApsConfig 1 }

sonusApsConfigTable OBJECT-TYPE
    SYNTAX          SEQUENCE OF SonusApsConfigEntry
    MAX-ACCESS      not-accessible
    STATUS          deprecated
    DESCRIPTION     
            "This table is deprecated as of GSX release V06.00.00.
             It has been replaced by equivilant tabel in RFC3498
             
             This table lists the APS groups that have been configured
             on the system."
    ::= { sonusApsConfig 2 }

sonusApsConfigEntry OBJECT-TYPE
    SYNTAX          SonusApsConfigEntry
    MAX-ACCESS      not-accessible
    STATUS          deprecated
    DESCRIPTION     
            "A conceptual row in the sonusApsConfigTable."
    INDEX           { IMPLIED sonusApsConfigName }
    ::= { sonusApsConfigTable 1 }

SonusApsConfigEntry ::=
    SEQUENCE {
        sonusApsConfigName              SnmpAdminString,
        sonusApsConfigRowStatus         RowStatus,
        sonusApsConfigMode              INTEGER,
        sonusApsConfigRevert            INTEGER,
        sonusApsConfigDirection         INTEGER,
        sonusApsConfigExtraTraffic      INTEGER,
        sonusApsConfigSdBerThreshold    Integer32,
        sonusApsConfigSfBerThreshold    Integer32,
        sonusApsConfigWaitToRestore     Integer32,
        sonusApsConfigCreationTime      TimeStamp
    }

sonusApsConfigName OBJECT-TYPE
    SYNTAX          SnmpAdminString (SIZE(1..32))
    MAX-ACCESS      not-accessible
    STATUS          deprecated
    DESCRIPTION     
            "A textual name for the APS group."
    ::= { sonusApsConfigEntry 1 }

sonusApsConfigRowStatus OBJECT-TYPE
    SYNTAX          RowStatus
    MAX-ACCESS      read-create
    STATUS          deprecated
    DESCRIPTION     
            "The status of this APS group entry.
             
             An entry may not exist in the active state unless all
             objects in the entry have an appropriate value. Also,
             all associated apsChanConfigEntry rows must represent
             a set of consecutive channel numbers beginning with
             0 or 1, depending on the selected architecture.
             
             When set to notInService changes may be made to apsConfigMode,
             apsConfigRevert, apsConfigDirection, sonusApsConfigExtraTraffic,
             apsConfigSdBerThreshold, apsConfigSfBerThreshold,
             and apsConfigWaitToRestore. Also, associated apsChanConfigTable
             objects may be added, deleted and modified.
             "
    ::= { sonusApsConfigEntry 2 }

sonusApsConfigMode OBJECT-TYPE
    SYNTAX          INTEGER { onePlusOne(1), oneToN(2), 
                        onePlusOneCompatible(3), onePlusOneOptimized(4) }
    MAX-ACCESS      read-create
    STATUS          deprecated
    DESCRIPTION     
            "The architecture of the APS group.
             
             onePlusOne
             
             The 1+1 architecture permanently bridges the working
             line to the protection line.
             
             oneToN
             
             The 1:n architecture allows one protection channel to
             protect up to n working channels. When a fault is detected
             on one of the n working channels that channel is bridged
             over the protection channel.
             
             onePlusOneCompatible
             
             This refers to 1 + 1 bidirectional switching compatible with
             1:n bidirectional switching as specified in ITU-T
             Recommendation G.783 (04/97) section A.3.4.1. Since this
             mode necessitates bidirectional switching, apsConfigDirection
             must be set to bidirectional whenever onePlusOneCompatible is set.
             
             onePlusOneOptimized
             
             This refers to 1 + 1 bidirectional switching optimized
             for a network using predominantly 1 + 1 bidirectional
             switching as specified in ITU-T Recommendation G.783 (04/97)
             section B.1. Since this mode necessitates bidirectional
             switching, apsConfigDirection must be set to bidirectional
             whenever onePlusOneOptimized is set.
             
             This object may not be modified if the associated
             apsConfigRowStatus object is equal to active(1)."
    DEFVAL          { onePlusOne }
    ::= { sonusApsConfigEntry 3 }

sonusApsConfigRevert OBJECT-TYPE
    SYNTAX          INTEGER { nonrevertive(1), revertive(2) }
    MAX-ACCESS      read-create
    STATUS          deprecated
    DESCRIPTION     
            "The revertive mode of the APS group.
             
             nonrevertive
             
             Traffic remains on the protection line until another switch
             request is received.
             
             revertive
             
             When the condition that caused a switch to the protection
             line has been cleared the signal is switched back to the
             working line. Since switching is revertive with the 1:n
             architecture, apsConfigRevert must be set to revertive if
             apsConfigMode is set to oneToN.
             
             Switching may optionally be revertive with the 1+1 architecture.
             
             
             This object may not be modified if the associated
             
             apsConfigRowStatus object is equal to active(1).
             "
    DEFVAL          { nonrevertive }
    ::= { sonusApsConfigEntry 4 }

sonusApsConfigDirection OBJECT-TYPE
    SYNTAX          INTEGER { unidirectional(1), bidirectional(2) }
    MAX-ACCESS      read-create
    STATUS          deprecated
    DESCRIPTION     
            "The directional mode of the APS group.
             
             unidirectional
             
             The unidirectional mode provides protection in one direction.
             
             bidirectional
             
             The bidirectional mode provides protection in both
             directions.
             
             This object may not be modified if the associated
             apsConfigRowStatus object is equal to active(1).
             "
    DEFVAL          { unidirectional }
    ::= { sonusApsConfigEntry 5 }

sonusApsConfigExtraTraffic OBJECT-TYPE
    SYNTAX          INTEGER { enabled(1), disabled(2) }
    MAX-ACCESS      read-create
    STATUS          deprecated
    DESCRIPTION     
            "This object enables or disables the transfer of extra traffic
             on the protection channel in a 1:n architecture. This object
             must be set to disabled if the architecture is 1+1. It may be
             necessary to disable this in order to interwork with other SONET
             network elements that don't support extra traffic.
             
             This object may not be modified if the associated
             apsConfigRowStatus object is equal to active(1).
             "
    DEFVAL          { disabled }
    ::= { sonusApsConfigEntry 6 }

sonusApsConfigSdBerThreshold OBJECT-TYPE
    SYNTAX          Integer32 (5..9)
    MAX-ACCESS      read-create
    STATUS          deprecated
    DESCRIPTION     
            "The Signal Degrade Bit Error Rate.
             
             The negated value of this number is used as the exponent of
             10 for computing the threshold value for the Bit Error Rate
             (BER). For example, a value of 5 indicates a BER threshold of
             10^-5.
             
             This object may be modified if the associated
             apsConfigRowStatus object is equal to active(1)."
    DEFVAL          { 5 }
    ::= { sonusApsConfigEntry 7 }

sonusApsConfigSfBerThreshold OBJECT-TYPE
    SYNTAX          Integer32 (3..5)
    MAX-ACCESS      read-create
    STATUS          deprecated
    DESCRIPTION     
            "The Signal Failure Bit Error Rate.
             
             The negated value of this number is used as the exponent of
             10 for computing the threshold value for the Bit Error Rate
             (BER). For example, a value of 5 indicates a BER threshold of
             10^-5.
             
             This object may be modified if the associated
             apsConfigRowStatus object is equal to active(1)."
    DEFVAL          { 3 }
    ::= { sonusApsConfigEntry 8 }

sonusApsConfigWaitToRestore OBJECT-TYPE
    SYNTAX          Integer32 (0..720)
    MAX-ACCESS      read-create
    STATUS          deprecated
    DESCRIPTION     
            "The Wait To Restore period in seconds.
             
             After clearing of a condition that necessitated an
             automatic switch, the wait to restore period must elapse
             before reverting. This is intended to avoid rapid switch
             oscillations.
             
             GR-253-CORE specifies a Wait To Restore range of 5 to 12
             minutes. G.783 defines a 5 to 12 minute Wait To Restore
             range in section 5.4.1.1.3, but also allows for a shorter
             WTR period in  Table 2-1,
             WaitToRestore value (MI_WTRtime: 0..(5)..12 minutes).
             
             This object may not be modified if the associated
             apsConfigRowStatus object is equal to active(1)."
    DEFVAL          { 300 }
    ::= { sonusApsConfigEntry 9 }

sonusApsConfigCreationTime OBJECT-TYPE
    SYNTAX          TimeStamp
    MAX-ACCESS      read-only
    STATUS          deprecated
    DESCRIPTION     
            "The value of sysUpTime at the time the row was
             created"
    ::= { sonusApsConfigEntry 10 }

sonusApsStatusTable OBJECT-TYPE
    SYNTAX          SEQUENCE OF SonusApsStatusEntry
    MAX-ACCESS      not-accessible
    STATUS          deprecated
    DESCRIPTION     
            "This table is deprecated as of GSX release V06.00.00.
             It has been replaced by equivilant tabel in RFC3498
             
             This table provides status information about APS groups that have
             been configured on the system."
    ::= { sonusApsMIBObjects 2 }

sonusApsStatusEntry OBJECT-TYPE
    SYNTAX          SonusApsStatusEntry
    MAX-ACCESS      not-accessible
    STATUS          deprecated
    DESCRIPTION     
            "A conceptual row in the apsStatusTable. Entries in this
             table are created as a side effect of row addition in
             apsConfigTable."
    INDEX           { IMPLIED sonusApsConfigName }
    ::= { sonusApsStatusTable 1 }

SonusApsStatusEntry ::=
    SEQUENCE {
        sonusApsStatusK1K2Rcv           SonusApsK1K2,
        sonusApsStatusK1K2Trans         SonusApsK1K2,
        sonusApsStatusCurrent           BITS,
        sonusApsStatusModeMismatches    Counter32,
        sonusApsStatusChannelMismatches Counter32,
        sonusApsStatusPSBFs             Counter32,
        sonusApsStatusFEPLFs            Counter32,
        sonusApsStatusSwitchedChannel   Integer32
    }

sonusApsStatusK1K2Rcv OBJECT-TYPE
    SYNTAX          SonusApsK1K2
    MAX-ACCESS      read-only
    STATUS          deprecated
    DESCRIPTION     
            "The current value of the K1 and K2 bytes received on the
             protection channel."
    ::= { sonusApsStatusEntry 1 }

sonusApsStatusK1K2Trans OBJECT-TYPE
    SYNTAX          SonusApsK1K2
    MAX-ACCESS      read-only
    STATUS          deprecated
    DESCRIPTION     
            "The current value of the K1 and K2 bytes transmitted on the
             protection channel."
    ::= { sonusApsStatusEntry 2 }

sonusApsStatusCurrent OBJECT-TYPE
    SYNTAX          BITS { modeMismatch(0), channelMismatch(1), psbf(2), 
                        feplf(3), extraTraffic(4) }
    MAX-ACCESS      read-only
    STATUS          deprecated
    DESCRIPTION     
            "The current status of the APS group.
             
             modeMismatch
             
             Modes other than 1+1 unidirectional monitor protection line
             K2 bit 5, which indicates the architecture and K2 bits
             6-8, which indicate if the mode is unidirectional or
             bidirectional. A conflict between the current local mode
             and the received K2 mode information constitutes a
             mode mismatch.
             
             channelMismatch
             
             This bit indicates a  mismatch between the transmitted K1 channel
             and the received K2 channel has been detected.
             
             psbf
             
             This bit indicates a Protection Switch Byte Failure (PSBF) is
             in effect. This condition occurs when either an inconsistent
             APS byte or an invalid code is detected. An inconsistent APS
             byte occurs when no three consecutive K1 bytes of the last 12
             successive frames are identical, starting with the last frame
             containing a previously consistent byte. An invalid code occurs
             when the incoming K1 byte contains an unused code or a code
             irrelevant for the specific switching operation (e.g., Reverse
             Request while no switching request is outstanding) in three
             consecutive frames. An invalid code also occurs when the incoming
             K1 byte contains an invalid channel number in three consecutive
             frames.
             
             feplf
             
             Modes other than 1+1 unidirectional monitor the K1 byte
             for Far-End Protection-Line failures. A Far-End
             Protection-Line defect is declared based on receiving
             SF on the protection line.
             
             extraTraffic
             
             This bit indicates whether extra traffic is currently being
             accepted on the protection line."
    ::= { sonusApsStatusEntry 3 }

sonusApsStatusModeMismatches OBJECT-TYPE
    SYNTAX          Counter32
    MAX-ACCESS      read-only
    STATUS          deprecated
    DESCRIPTION     
            "A count of Mode Mismatch conditions."
    ::= { sonusApsStatusEntry 4 }

sonusApsStatusChannelMismatches OBJECT-TYPE
    SYNTAX          Counter32
    MAX-ACCESS      read-only
    STATUS          deprecated
    DESCRIPTION     
            "A count of Channel Mismatch conditions."
    ::= { sonusApsStatusEntry 5 }

sonusApsStatusPSBFs OBJECT-TYPE
    SYNTAX          Counter32
    MAX-ACCESS      read-only
    STATUS          deprecated
    DESCRIPTION     
            "A count of Protection Switch Byte Failure conditions.
             This condition occurs when either an inconsistent APS
             byte or an invalid code is detected. An inconsistent APS
             byte occurs when no three consecutive K1 bytes of the last
             12 successive frames are identical, starting with the last
             frame containing a previously consistent byte. An invalid
             code occurs when the incoming K1 byte contains an unused
             code or a code irrelevant for the specific switching operation
             (e.g., Reverse Request while no switching request is outstanding)
             in three consecutive frames. An invalid code also occurs
             when the incoming K1 byte contains an invalid channel number
             in three consecutive frames."
    ::= { sonusApsStatusEntry 6 }

sonusApsStatusFEPLFs OBJECT-TYPE
    SYNTAX          Counter32
    MAX-ACCESS      read-only
    STATUS          deprecated
    DESCRIPTION     
            "A count of Far-End Protection-Line Failure conditions.
             This condition is declared based on receiving SF on
             the protection line in the K1 byte."
    ::= { sonusApsStatusEntry 7 }

sonusApsStatusSwitchedChannel OBJECT-TYPE
    SYNTAX          Integer32
    MAX-ACCESS      read-only
    STATUS          deprecated
    DESCRIPTION     
            "This field is set to the number of the channel that is currently
             switched to protection. The value 0 indicates no channel is
             switched to protection. The values 1-14 indicate that working
             channel is switched to protection."
    ::= { sonusApsStatusEntry 8 }

sonusApsMap OBJECT IDENTIFIER
    ::= { sonusApsMIBObjects 3 }

sonusApsChanLTEs OBJECT-TYPE
    SYNTAX          Gauge32
    MAX-ACCESS      read-only
    STATUS          deprecated
    DESCRIPTION     
            "The count of SONET LTE interfaces on the system.
             Each interface that is included has an ifType value of sonet(39)."
    ::= { sonusApsMap 1 }

sonusApsMapTable OBJECT-TYPE
    SYNTAX          SEQUENCE OF SonusApsMapEntry
    MAX-ACCESS      not-accessible
    STATUS          deprecated
    DESCRIPTION     
            "This table is deprecated as of GSX release V06.00.00.
             It has been replaced by equivilant tabel in RFC3498
             
             This table lists the SONET LTE interfaces on the system.
             Each interface that is listed has an ifType value of sonet(39)."
    ::= { sonusApsMap 2 }

sonusApsMapEntry OBJECT-TYPE
    SYNTAX          SonusApsMapEntry
    MAX-ACCESS      not-accessible
    STATUS          deprecated
    DESCRIPTION     
            "A conceptual row in the apsMapTable."
    INDEX           { sonusApsMapIfIndex }
    ::= { sonusApsMapTable 1 }

SonusApsMapEntry ::=
    SEQUENCE {
        sonusApsMapIfIndex              InterfaceIndex,
        sonusApsMapGroupName            SnmpAdminString,
        sonusApsMapChanNumber           Integer32
    }

sonusApsMapIfIndex OBJECT-TYPE
    SYNTAX          InterfaceIndex
    MAX-ACCESS      not-accessible
    STATUS          deprecated
    DESCRIPTION     
            "The Interface Index assigned to a SONET LTE. This is an interface
             with ifType sonet(39)."
    ::= { sonusApsMapEntry 1 }

sonusApsMapGroupName OBJECT-TYPE
    SYNTAX          SnmpAdminString (SIZE(0..32))
    MAX-ACCESS      read-only
    STATUS          deprecated
    DESCRIPTION     
            "A textual name for the APS group which this channel is
             included in. If the channel is not part of an APS group
             this value is set to a string of size 0.
             
             When an instance of apsChanConfigIfIndex is set equal to an
             instance of apsMapIfIndex, apsMapGroupName is set equal
             to the corresponding value of apsChanConfigGroupName.
             
             If the apsMapIfIndex ceases to be equal to an instance of
             apsChanConfigIfIndex, either because of a change in the value of
             apsChanConfigIfIndex, or because of row deletion in the
             SonusApsChanConfigTable, apsMapGroupName is set to a string of
             size 0.
             "
    ::= { sonusApsMapEntry 2 }

sonusApsMapChanNumber OBJECT-TYPE
    SYNTAX          Integer32 (-1..14)
    MAX-ACCESS      read-only
    STATUS          deprecated
    DESCRIPTION     
            "This field is set to a unique channel number within an APS group.
             The value 0 indicates the null channel. The values 1-14 define a
             working channel. If the SONET LTE is not part of an APS group this
             value is set to -1.
             
             When an instance of apsChanConfigIfIndex is set equal to an instance of
             apsMapIfIndex, apsMapChanNumber is set equal to the corresponding
             value of apsChanConfigNumber.
             
             If the apsMapIfIndex ceases to be equal to an instance of
             apsChanConfigIfIndex, either because of a change in the value of
             apsChanConfigIfIndex, or because of row deletion in the
             SonusApsChanConfigTable, apsMapChanNumber is set to -1.
             "
    ::= { sonusApsMapEntry 3 }

sonusApsChanConfigTable OBJECT-TYPE
    SYNTAX          SEQUENCE OF SonusApsChanConfigEntry
    MAX-ACCESS      not-accessible
    STATUS          deprecated
    DESCRIPTION     
            "This table is deprecated as of GSX release V06.00.00.
             It has been replaced by equivilant tabel in RFC3498
             
             This table lists the APS channels that have been configured
             in APS groups."
    ::= { sonusApsMIBObjects 4 }

sonusApsChanConfigEntry OBJECT-TYPE
    SYNTAX          SonusApsChanConfigEntry
    MAX-ACCESS      not-accessible
    STATUS          deprecated
    DESCRIPTION     
            "A conceptual row in the apsChanConfigTable."
    INDEX           { sonusApsChanConfigGroupName, 
                      sonusApsChanConfigNumber }
    ::= { sonusApsChanConfigTable 1 }

SonusApsChanConfigEntry ::=
    SEQUENCE {
        sonusApsChanConfigGroupName     SnmpAdminString,
        sonusApsChanConfigNumber        Integer32,
        sonusApsChanConfigRowStatus     RowStatus,
        sonusApsChanConfigIfIndex       InterfaceIndex,
        sonusApsChanConfigPriority      INTEGER
    }

sonusApsChanConfigGroupName OBJECT-TYPE
    SYNTAX          SnmpAdminString (SIZE(1..32))
    MAX-ACCESS      not-accessible
    STATUS          deprecated
    DESCRIPTION     
            "A textual name for the APS group which this channel is
             included in."
    ::= { sonusApsChanConfigEntry 1 }

sonusApsChanConfigNumber OBJECT-TYPE
    SYNTAX          Integer32 (0..14)
    MAX-ACCESS      not-accessible
    STATUS          deprecated
    DESCRIPTION     
            "This field is set to a unique channel number within an APS group.
             The value 0 indicates the null channel. The values 1-14 define a
             working channel.
             
             This field must be assigned a unique number within the group."
    ::= { sonusApsChanConfigEntry 2 }

sonusApsChanConfigRowStatus OBJECT-TYPE
    SYNTAX          RowStatus
    MAX-ACCESS      read-create
    STATUS          deprecated
    DESCRIPTION     
            "The status of this APS channel entry.
             
             An entry may not exist in the active state unless all
             objects in the entry have an appropriate value.
             
             A row in the apsChanConfigTable may not be created,
             deleted, set to notInService or otherwise modified
             if the apsChanConfigGroupName value is equal to an
             apsConfigName value and the associated apsConfigRowStatus
             object is equal to active. However, if the apsConfigRowStatus
             object is equal to notInService, a row may be created, deleted
             or modified. In other words, a channel may not be added, deleted
             or modified if the group is active.
             
             A row may be created with an apsChanConfigGroupName value
             that is not equal to any existing instance of apsConfigName.
             This action is the initial step in adding a SONET LTE to a
             new APS group.
             
             If this object is set to destroy, the associated instance
             of apsMapGroupName will be set to a string of size 0 and
             the apsMapChanNumber will be set to -1. The channel status
             entry will also be deleted by this action.
             
             apsChanConfigNumber must be set to a unique channel number within
             the APS group. The value 0 indicates the null channel.
             The values 1-14 define a working channel. When an attempt is
             made to set the  corresponding apsConfigRowStatus field to
             active the apsChanConfigNumber values of all entries with equal
             apsChanConfigGroupName fields must represent a set of consecutive
             integer values beginning with 0 or 1, depending on the architecture
             of the group, and ending with n, where n is  greater than or
             equal to 1 and less than or equal to 14. Otherwise, the error
             inconsistentValue is returned to the apsConfigRowStatus
             set attempt.
             "
    ::= { sonusApsChanConfigEntry 3 }

sonusApsChanConfigIfIndex OBJECT-TYPE
    SYNTAX          InterfaceIndex
    MAX-ACCESS      read-create
    STATUS          deprecated
    DESCRIPTION     
            "The Interface Index assigned to a SONET LTE. This is an
             interface with ifType sonet(39). The value of this object
             must be unique among all instances of apsChanConfigIfIndex.
             In other words, a particular SONET LTE can only be configured in
             one APS group.
             
             This object cannot be set if the apsChanConfigGroupName instance
             associated with this row is equal to an instance of apsConfigName and
             the corresponding apsConfigRowStatus object is set to active. In other
             words this value cannot be changed if the APS group is active. However,
             This value may be changed if the apsConfigRowStatus value is equal to
             notInService.
             "
    ::= { sonusApsChanConfigEntry 4 }

sonusApsChanConfigPriority OBJECT-TYPE
    SYNTAX          INTEGER { low(1), high(2) }
    MAX-ACCESS      read-create
    STATUS          deprecated
    DESCRIPTION     
            "The priority of the channel.
             
             This field deterimines whether high or low priority
             SD and SF codes are used in K1 requests.
             
             This field is only applicable if the channel is to be included in
             a group using the 1:n architecture. It is not applicable if the
             channel is to be included in a group using the 1+1 architecture,
             and is ignored in that case.
             
             This object cannot be set if the apsChanConfigGroupName instance
             associated with this row is equal to an instance of apsConfigName
             and the corresponding apsConfigRowStatus object is set to active.
             In other words this value cannot be changed if the APS group is
             active. However, This value may be changed if the
             apsConfigRowStatus value is equal to notInService.
             "
    DEFVAL          { low }
    ::= { sonusApsChanConfigEntry 5 }

sonusApsCommandTable OBJECT-TYPE
    SYNTAX          SEQUENCE OF SonusApsCommandEntry
    MAX-ACCESS      not-accessible
    STATUS          deprecated
    DESCRIPTION     
            "This table is deprecated as of GSX release V06.00.00.
             It has been replaced by equivilant tabel in RFC3498
             
             This table allows commands to be sent to configured APS groups."
    ::= { sonusApsMIBObjects 5 }

sonusApsCommandEntry OBJECT-TYPE
    SYNTAX          SonusApsCommandEntry
    MAX-ACCESS      not-accessible
    STATUS          deprecated
    DESCRIPTION     
            "A conceptual row in the apsCommandTable. This row exists only if
             the associated apsConfigEntry is active."
    INDEX           { sonusApsChanConfigGroupName, 
                      sonusApsChanConfigNumber }
    ::= { sonusApsCommandTable 1 }

SonusApsCommandEntry ::=
    SEQUENCE {
        sonusApsCommandSwitch           SonusApsSwitchCommand,
        sonusApsCommandControl          SonusApsControlCommand
    }

sonusApsCommandSwitch OBJECT-TYPE
    SYNTAX          SonusApsSwitchCommand
    MAX-ACCESS      read-write
    STATUS          deprecated
    DESCRIPTION     
            "Allows the initiation of an APS switch command on the
             APS group and channel specified by the index values.
             
             If the APS switch command cannot be executed because an
             equal or higer priority request is in effect, an error
             is returned.
             
             When read this object returns the last command written
             or noCmd if no command has been written to this
             channel since initialization. The return of the last command
             written does not imply that this command is currently in effect.
             This request may have been preempted by a higher priority
             local or remote request. In order to determine the
             current state of the APS group it is necessary to read
             the objects apsStatusK1K2Rcv and apsStatusK1K2Trans.
             
             The value lockoutOfProtection should only be applied
             to the protection line channel since that switch command
             prevents any of the working channels from switching to the protection
             line. Following the same logic, forcedSwitchProtectToWork and
             manualSwitchProtectToWork should only be applied to the protection
             line channel.
             
             forcedSwitchWorkToProtect and manualSwitchWorkToProtect
             should only be applied to a working channel.
             	"
    ::= { sonusApsCommandEntry 1 }

sonusApsCommandControl OBJECT-TYPE
    SYNTAX          SonusApsControlCommand
    MAX-ACCESS      read-write
    STATUS          deprecated
    DESCRIPTION     
            "Allows the initiation of an APS control command on the
             APS group and channel specified by the index values.
             
             When read this object returns the last command written
             or noCmd if no command has been
             written to this channel since initialization.
             
             This object does not apply to the protection line.
             "
    ::= { sonusApsCommandEntry 2 }

sonusApsChanStatusTable OBJECT-TYPE
    SYNTAX          SEQUENCE OF SonusApsChanStatusEntry
    MAX-ACCESS      not-accessible
    STATUS          deprecated
    DESCRIPTION     
            "This table is deprecated as of GSX release V06.00.00.
             It has been replaced by equivilant tabel in RFC3498
             
             This table contains status information for all SONET LTE
             interfaces that are included in APS groups."
    ::= { sonusApsMIBObjects 6 }

sonusApsChanStatusEntry OBJECT-TYPE
    SYNTAX          SonusApsChanStatusEntry
    MAX-ACCESS      not-accessible
    STATUS          deprecated
    DESCRIPTION     
            "A conceptual row in the apsChanStatusTable. A row in this
             table is created as a side effect of row addition in the
             apsChanConfigTable. The apsChanStatusTable row exists
             as long as the apsChanConfigTable entry exists, regardless
             of whether the associated apsChanConfigRowStatus is active.
             "
    INDEX           { sonusApsChanConfigGroupName, 
                      sonusApsChanConfigNumber }
    ::= { sonusApsChanStatusTable 1 }

SonusApsChanStatusEntry ::=
    SEQUENCE {
        sonusApsChanStatusCurrent       BITS,
        sonusApsChanStatusSignalDegrades Counter32,
        sonusApsChanStatusSignalFailures Counter32,
        sonusApsChanStatusSwitchovers   Counter32,
        sonusApsChanStatusLastSwitchover TimeStamp,
        sonusApsChanStatusSwitchoverSeconds   Counter32
    }

sonusApsChanStatusCurrent OBJECT-TYPE
    SYNTAX          BITS { lockedOut(0), sd(1), sf(2), switched(3) }
    MAX-ACCESS      read-only
    STATUS          deprecated
    DESCRIPTION     
            "Indicates the current state of the port.
             
             lockedOut
             
             This bit, when applied to a working channel, indicates that
             the channel is prevented from switching to the protection line.
             When applied to the null channel, this bit indicates that no
             working channel may switch to the protection line.
             
             sd
             
             A signal degrade condition is in effect.
             
             sf
             
             A signal failure condition is in effect.
             
             switched
             
             The switched bit is applied to a working channel if that
             channel is currently switched to the protection line.
             "
    ::= { sonusApsChanStatusEntry 1 }

sonusApsChanStatusSignalDegrades OBJECT-TYPE
    SYNTAX          Counter32
    MAX-ACCESS      read-only
    STATUS          deprecated
    DESCRIPTION     
            "A count of Signal Degrade conditions. This
             condition occurs when the line Bit Error Rate
             exceeds the currently configured threshold."
    ::= { sonusApsChanStatusEntry 2 }

sonusApsChanStatusSignalFailures OBJECT-TYPE
    SYNTAX          Counter32
    MAX-ACCESS      read-only
    STATUS          deprecated
    DESCRIPTION     
            "A count of Signal Failure conditions that have been
             detected on the incoming signal. This condition occurs
             when a loss of signal, loss of frame, AIS-L or a Line
             bit error rate exceeding 10^-3 is detected on an
             incoming line."
    ::= { sonusApsChanStatusEntry 3 }

sonusApsChanStatusSwitchovers OBJECT-TYPE
    SYNTAX          Counter32
    MAX-ACCESS      read-only
    STATUS          deprecated
    DESCRIPTION     
            "The number of times this channel has switched to the protection
             line. When queried with index value apsChanConfigNumber set to 0,
             which is the protection line, this object will return 0."
    ::= { sonusApsChanStatusEntry 4 }

sonusApsChanStatusLastSwitchover OBJECT-TYPE
    SYNTAX          TimeStamp
    MAX-ACCESS      read-only
    STATUS          deprecated
    DESCRIPTION     
            "The value of sysUpTime when this channel last completed a switch
             to the protection line. If this channel has never switched to the
             protection line, or this channel is the protection line, the value
             0  will be returned."
    ::= { sonusApsChanStatusEntry 5 }

sonusApsChanStatusSwitchoverSeconds OBJECT-TYPE
    SYNTAX          Counter32
    MAX-ACCESS      read-only
    STATUS          deprecated
    DESCRIPTION     
            "The cumulative Protection Switching Duration (PSD) time in
             seconds. For a working channel, this is the cumulative number
             of seconds that service was carried on the protection line.
             For the protection line, this is the cumulative number of
             seconds that the protection line has been used to carry any
             working channel traffic. This information is only valid if
             revertive switching is enabled. The value 0 will be returned
             otherwise."
    ::= { sonusApsChanStatusEntry 6 }

sonusApsNameMapTable OBJECT-TYPE
    SYNTAX          SEQUENCE OF SonusApsNameMapEntry
    MAX-ACCESS      not-accessible
    STATUS          current
    DESCRIPTION     
            "This table maps an APS group name to a user-defined
             name"
    ::= { sonusApsMIBObjects 7 }

sonusApsNameMapEntry OBJECT-TYPE
    SYNTAX          SonusApsNameMapEntry
    MAX-ACCESS      not-accessible
    STATUS          current
    DESCRIPTION     
            "A conceptual row in the apsNameMapTable"
    INDEX           { sonusApsNameMapGroupName }
    ::= { sonusApsNameMapTable 1 }

SonusApsNameMapEntry ::=
    SEQUENCE {
        sonusApsNameMapGroupName        SnmpAdminString,
        sonusApsNameMapUserName         SonusName
    }

sonusApsNameMapGroupName OBJECT-TYPE
    SYNTAX          SnmpAdminString (SIZE(1..32))
    MAX-ACCESS      not-accessible
    STATUS          current
    DESCRIPTION     
            "Textual name for the APS group."
    ::= { sonusApsNameMapEntry 1 }

sonusApsNameMapUserName OBJECT-TYPE
    SYNTAX          SonusName
    MAX-ACCESS      read-write
    STATUS          current
    DESCRIPTION     
            "User-assigned textual name for the APS group."
    ::= { sonusApsNameMapEntry 2 }

sonusApsMIBNotifications OBJECT IDENTIFIER
    ::= { sonusApsMIB 2 }

sonusApsNotificationsPrefix OBJECT IDENTIFIER
    ::= { sonusApsMIBNotifications 0 }

sonusApsMIBConformance OBJECT IDENTIFIER
    ::= { sonusApsMIB 3 }

sonusApsGroups OBJECT IDENTIFIER
    ::= { sonusApsMIBConformance 1 }

sonusApsCompliances OBJECT IDENTIFIER
    ::= { sonusApsMIBConformance 2 }

sonusApsEventSwitchover NOTIFICATION-TYPE
    OBJECTS         { apsChanStatusSwitchovers, apsChanStatusCurrent, 
                      sonusEventDescription, sonusEventClass, 
                      sonusEventLevel, sonusSequenceId, sonusEventTime }
    STATUS          current
    DESCRIPTION     
            "An apsEventSwitchover notification is sent when the
             value of an instance of apsChanStatusSwitchovers increments."
    ::= { sonusApsNotificationsPrefix 1 }

sonusApsEventModeMismatch NOTIFICATION-TYPE
    OBJECTS         { apsStatusModeMismatches, apsStatusCurrent, 
                      sonusEventDescription, sonusEventClass, 
                      sonusEventLevel, sonusSequenceId, sonusEventTime }
    STATUS          current
    DESCRIPTION     
            "An apsEventModeMismatch notification is sent when the
             value of an instance of apsStatusModeMismatches increments."
    ::= { sonusApsNotificationsPrefix 2 }

sonusApsEventChannelMismatch NOTIFICATION-TYPE
    OBJECTS         { apsStatusChannelMismatches, apsStatusCurrent, 
                      sonusEventDescription, sonusEventClass, 
                      sonusEventLevel, sonusSequenceId, sonusEventTime }
    STATUS          current
    DESCRIPTION     
            "An apsEventChannelMismatch notification is sent when the
             value of an instance of apsStatusChannelMismatches increments."
    ::= { sonusApsNotificationsPrefix 3 }

sonusApsEventPSBF NOTIFICATION-TYPE
    OBJECTS         { apsStatusPSBFs, apsStatusCurrent, 
                      sonusEventDescription, sonusEventClass, 
                      sonusEventLevel, sonusSequenceId, sonusEventTime }
    STATUS          current
    DESCRIPTION     
            "An apsEventPSBF notification is sent when the
             value of an instance of apsStatusPSBFs increments."
    ::= { sonusApsNotificationsPrefix 4 }

sonusApsEventFEPLF NOTIFICATION-TYPE
    OBJECTS         { apsStatusFEPLFs, apsStatusCurrent, 
                      sonusEventDescription, sonusEventClass, 
                      sonusEventLevel, sonusSequenceId, sonusEventTime }
    STATUS          current
    DESCRIPTION     
            "An apsEventFEPLFs notification is sent when the
             value of an instance of apsStatusFEPLFs increments."
    ::= { sonusApsNotificationsPrefix 5 }

sonusApsConfigGeneral OBJECT-GROUP
    OBJECTS         { sonusApsConfigMode, sonusApsConfigRevert, 
                      sonusApsConfigDirection, 
                      sonusApsConfigExtraTraffic, 
                      sonusApsConfigSdBerThreshold, 
                      sonusApsConfigSfBerThreshold, 
                      sonusApsConfigCreationTime, 
                      sonusApsConfigRowStatus }
    STATUS          deprecated
    DESCRIPTION     
            "A collection of apsConfigTable objects providing configuration
             information applicable to all linear APS groups."
    ::= { sonusApsGroups 1 }

sonusApsConfigWtr OBJECT-GROUP
    OBJECTS         { sonusApsConfigWaitToRestore }
    STATUS          deprecated
    DESCRIPTION     
            "The apsConfigTable object that provides information which is
             applicable to groups supporting a configurable WTR period."
    ::= { sonusApsGroups 2 }

sonusApsCommandOnePlusOne OBJECT-GROUP
    OBJECTS         { sonusApsCommandSwitch }
    STATUS          deprecated
    DESCRIPTION     
            "The  apsCommandTable object which is applicable to groups
             implementing the linear APS 1+1 architecture. Also, set operations
             must be supported."
    ::= { sonusApsGroups 3 }

sonusApsCommandOneToN OBJECT-GROUP
    OBJECTS         { sonusApsCommandSwitch, sonusApsCommandControl }
    STATUS          deprecated
    DESCRIPTION     
            "A collection of apsCommandTable objects which are applicable to
             groups implementing the linear APS 1:n architecture. Also, set
             operations must be supported."
    ::= { sonusApsGroups 4 }

sonusApsStatusGeneral OBJECT-GROUP
    OBJECTS         { sonusApsStatusK1K2Rcv, sonusApsStatusK1K2Trans, 
                      sonusApsStatusCurrent, 
                      sonusApsStatusModeMismatches, 
                      sonusApsStatusChannelMismatches, 
                      sonusApsStatusPSBFs, sonusApsStatusFEPLFs, 
                      sonusApsStatusSwitchedChannel }
    STATUS          deprecated
    DESCRIPTION     
            "A collection of apsStatusTable objects providing status information
             applicable to all linear APS groups."
    ::= { sonusApsGroups 5 }

sonusApsChanGeneral OBJECT-GROUP
    OBJECTS         { sonusApsChanConfigIfIndex, 
                      sonusApsChanConfigRowStatus, 
                      sonusApsChanStatusCurrent, 
                      sonusApsChanStatusSignalDegrades, 
                      sonusApsChanStatusSignalFailures, 
                      sonusApsChanStatusSwitchovers, 
                      sonusApsChanStatusLastSwitchover, 
                      sonusApsChanStatusSwitchoverSeconds }
    STATUS          deprecated
    DESCRIPTION     
            "A collection of channel objects providing information applicable to
             all linear APS channels."
    ::= { sonusApsGroups 6 }

sonusApsChanOneToN OBJECT-GROUP
    OBJECTS         { sonusApsChanConfigPriority }
    STATUS          deprecated
    DESCRIPTION     
            "The apsChanConfigTable object that provides information which is only
             applicable to groups implementing the linear APS 1:n architecture."
    ::= { sonusApsGroups 7 }

sonusApsTotalsGroup OBJECT-GROUP
    OBJECTS         { sonusApsConfigGroups, sonusApsChanLTEs }
    STATUS          deprecated
    DESCRIPTION     
            "A collection of objects providing optional counts of configured APS
             groups and SONET LTE interfaces."
    ::= { sonusApsGroups 8 }

sonusApsMapGroup OBJECT-GROUP
    OBJECTS         { sonusApsMapGroupName, sonusApsMapChanNumber }
    STATUS          deprecated
    DESCRIPTION     
            "A collection of apsMapTable objects providing a mapping
             from sonet(39) InterfaceIndex to group name and channel
             number for assigned APS channels and a list of unassigned
             sonet(39) interfaces."
    ::= { sonusApsGroups 9 }

sonusApsEventOptional NOTIFICATION-GROUP
    NOTIFICATIONS   { sonusApsEventSwitchover, sonusApsEventModeMismatch, 
                      sonusApsEventChannelMismatch, sonusApsEventPSBF, 
                      sonusApsEventFEPLF }
    STATUS          deprecated
    DESCRIPTION     
            "A collection of SONET linear APS notifications that may optionally be
             implemented."
    ::= { sonusApsGroups 10 }

sonusApsCompliance MODULE-COMPLIANCE
    STATUS          deprecated
    DESCRIPTION     
            "The compliance statement for linear APS groups."

    MODULE          -- this module

        MANDATORY-GROUPS    { sonusApsConfigGeneral, 
                      sonusApsStatusGeneral, sonusApsChanGeneral }

        GROUP       sonusApsConfigWtr
        DESCRIPTION 
            "Implementation of this group is optional for all
             linear APS implementations. The information is
             applicable to groups supporting a configurable
             WTR period."

        GROUP       sonusApsCommandOnePlusOne
        DESCRIPTION 
            "Implementation of this group is optional for all
             linear APS implementations. The information is
             applicable to groups implementing the linear
             APS 1+1 architecture and supporting set operations."

        GROUP       sonusApsCommandOneToN
        DESCRIPTION 
            "Implementation of this group is optional for all
             linear APS implementations. The information is
             applicable to groups implementing the linear
             APS 1:n architecture and supporting set operations."

        GROUP       sonusApsChanOneToN
        DESCRIPTION 
            "Implementation of this group is optional for all
             linear APS implementations. The information is
             applicable to groups implementing the linear
             APS 1:n architecture."

        GROUP       sonusApsTotalsGroup
        DESCRIPTION 
            "Implementation of this group is optional for all
             linear APS implementations."

        GROUP       sonusApsMapGroup
        DESCRIPTION 
            "Implementation of this group is optional for all
             linear APS implementations."

        OBJECT      sonusApsConfigMode
        MIN-ACCESS  read-only
        DESCRIPTION 
            "Write access is not required."

        OBJECT      sonusApsConfigRevert
        MIN-ACCESS  read-only
        DESCRIPTION 
            "Write access is not required."

        OBJECT      sonusApsConfigDirection
        MIN-ACCESS  read-only
        DESCRIPTION 
            "Write access is not required."

        OBJECT      sonusApsConfigExtraTraffic
        MIN-ACCESS  read-only
        DESCRIPTION 
            "Write access is not required."

        OBJECT      sonusApsConfigSdBerThreshold
        MIN-ACCESS  read-only
        DESCRIPTION 
            "Write access is not required."

        OBJECT      sonusApsConfigSfBerThreshold
        MIN-ACCESS  read-only
        DESCRIPTION 
            "Write access is not required."

        OBJECT      sonusApsConfigWaitToRestore
        MIN-ACCESS  read-only
        DESCRIPTION 
            "Write access is not required."

        OBJECT      sonusApsConfigRowStatus
        MIN-ACCESS  read-only
        DESCRIPTION 
            "Write access is not required."

        OBJECT      sonusApsChanConfigIfIndex
        MIN-ACCESS  read-only
        DESCRIPTION 
            "Write access is not required."

        OBJECT      sonusApsChanConfigPriority
        MIN-ACCESS  read-only
        DESCRIPTION 
            "Write access is not required."

        OBJECT      sonusApsChanConfigRowStatus
        MIN-ACCESS  read-only
        DESCRIPTION 
            "Write access is not required."

    ::= { sonusApsCompliances 1 }

END -- end of module SONUS-APS-MIB.
