--
-- This SMIv2 module has been generated by smidump 0.2-cvs. Do not edit.
--

SUN-HW-MONITORING-MIB DEFINITIONS ::= BEGIN

IMPORTS
    MODULE-COMPLIANCE, OBJECT-GROUP
        FROM SNMPv2-CONF
    Integer32, IpAddress, MODULE-IDENTITY, OBJECT-TYPE, enterprises
        FROM SNMPv2-SMI
    DisplayString, MacAddress, TEXTUAL-CONVENTION
        FROM SNMPv2-TC;

sunHwMonMIB MODULE-IDENTITY
    LAST-UPDATED    "200903240000Z"
    ORGANIZATION    
            "Sun Microsystems, Inc."
    CONTACT-INFO    
            "Sun Microsystems, Inc.
             4150 Network Circle
             Santa Clara, CA 95054
             
             1-800-555-9SUN or
             1-650-960-1300
             
             http://www.sun.com
             or contact your local support representative"
    DESCRIPTION     
            "Copyright 2008 Sun Microsystems, Inc.  All rights reserved.
             Use is subject to license terms.
             
             SUN-HW-MONITORING-MIB provides hardware inventory, status, 
             version and power consumption information related to the Sun 
             server or blade implementing this MIB. SNMP Traps associated 
             with this server are defined in a separate SUN-HW-TRAP-MIB.
             
             The information that is provided by the various MIB objects is 
             categorized into logically divided groups of scalars, 
             as well as MIB tables.
             
             Here are the details regarding the various groups and the 
             information that they provide. List of mib objects defined in 
             each group is provided in the comments section defined in the 
             beginning of each group.
             
             |
             |__ sunHwMonProductGroup 
             |	- A scalar group that provides product details 
             |         about the Sun server related to the overall 
             |	  server or blade such as part number and serial number.
             |__ sunHwMonProductChassisGroup 
             |       - A scalar group that provides details about 
             |         the metal chassis portion of the Sun server or chassis 
             |	  into which a Sun blade has been inserted.
             |__ sunHwMonSPGroup 
             |	- A scalar group that provides details about the 
             |         Service Processor(ILOM) of the Sun server.
             |__ sunHwMonMibGroup 
             |       - A scalar group that provides details about 
             |         SUN-HW-MONITORING-MIB itself.
             |__ sunHwMonAgentSoftwareGroup 
             |	- A scalar group that provides details about the 
             |         Sun hardware monitoring agent associated with 
             |         this MIB.
             |__ sunHwMonInventoryGroup 
             |       - This group contains sunHwMonInventoryTable that
             |         provides various details about the server's field replacable 
             |	  units (FRUs) including their status and the FRU which
             |         they are contained in. 
             |__ sunHwMonSensorGroup 
             |     |	- This group is further divided into multiple logical groups,
             |     |   that provide details about sensors categorized by device type
             |     |	  and the cumulative status of each device type.
             |     |
             |     |   sunHwMonSensorGroup contains the following groups:
             |     |
             |     |__ sunHwMonSensorAlarmStatusGroup
             |     |     - A scalar group that provides a single view of the
             |     |	      alarm status of Sun Server and rolled up status
             |     |       per device type such as voltage, current etc.,
             |     |
             |     |__ sunHwMonvoltageGroup
             |     |     | - This group contains two MIB tables.
             |     |     |
             |     |     |__ sunHwMonNumericVoltageSensorTable
             |     |     |     - This table provides details about all numeric
             |     |     |       voltage sensors including current reading,
             |     |     |       defined thresholds, current status, perceived
             |     |     |       severity and the FRU they are contained in.
             |     |     |       
             |     |     |__ sunHwMonDiscreteVoltageSensorTable
             |     |           - This table provides details about all discrete
             |     |             voltage sensors including current state, perceived
             |     |             severity and the FRU they are contained in.
             |     |
             |     |__ sunHwMonCurrentGroup
             |     |     |   - This group contains two MIB tables.
             |     |     |
             |     |     |__ sunHwMonNumericCurrentSensorTable
             |     |     |     - This table provides details about all numeric
             |     |     |       current sensors including current reading,
             |     |     |       defined thresholds, current status, perceived
             |     |     |       severity and the FRU they are contained in.
             |     |     |       
             |     |     |__ sunHwMonDiscreteCurrentSensorTable
             |     |           - This table provides details about all discrete
             |     |             current sensors including current state, perceived
             |     |             severity and the FRU they are contained in.
             |     |
             |     |__ sunHwMonPowerDeviceGroup
             |     |     |   - This group contains two MIB tables.
             |     |     |
             |     |     |__ sunHwMonNumericPowerDeviceSensorTable
             |     |     |     - This table provides details about all numeric
             |     |     |       power device sensors including current reading,
             |     |     |       defined thresholds, current status, perceived
             |     |     |       severity and the FRU they are contained in.
             |     |     |       
             |     |     |__ sunHwMonDiscretePowerDeviceSensorTable
             |     |           - This table provides details about all discrete
             |     |             power device sensors including current state,
             |     |             perceived severity and the FRU they are contained in.
             |     |
             |     |__ sunHwMonCoolingDeviceGroup
             |     |     |   - This group contains two MIB tables.
             |     |     |
             |     |     |__ sunHwMonNumericCoolingDeviceSensorTable
             |     |     |     - This table provides details about all numeric
             |     |     |       cooling device sensors including current reading,
             |     |     |       defined thresholds, current status, perceived
             |     |     |       severity and the FRU they are contained in.
             |     |     |       
             |     |     |__ sunHwMonDiscreteCoolingDeviceSensorTable
             |     |           - This table provides details about all discrete
             |     |             cooling device sensors including current state,
             |     |             perceived severity and the FRU they are contained in.
             |     |
             |     |__ sunHwMonTemperatureGroup
             |     |     |   - This group contains two MIB tables.
             |     |     |
             |     |     |__ sunHwMonNumericTemperatureSensorTable
             |     |     |     - This table provides details about all numeric
             |     |     |       temperature sensors including current reading,
             |     |     |       defined thresholds, current status, perceived
             |     |     |       severity and the FRU they are contained in.
             |     |     |       
             |     |     |__ sunHwMonDiscreteTemperatureSensorTable
             |     |           - This table provides details about all discrete
             |     |             temperature sensors including current state,
             |     |             perceived severity and the FRU they are contained in.
             |     |
             |     |__ sunHwMonProcessorGroup
             |     |     |   - This group contains two MIB tables.
             |     |     |
             |     |     |__ sunHwMonNumericProcessorSensorTable
             |     |     |     - This table provides details about all numeric
             |     |     |       processor sensors including current reading,
             |     |     |       defined thresholds, current status, perceived
             |     |     |       severity and the FRU they are contained in.
             |     |     |       
             |     |     |__ sunHwMonDiscreteProcessorSensorTable
             |     |           - This table provides details about all discrete
             |     |             processor sensors including current state,
             |     |             perceived severity and the FRU they are contained in.
             |     | 
             |     |__ sunHwMonMemoryGroup
             |     |     |   - This group contains two MIB tables.
             |     |     |
             |     |     |__ sunHwMonNumericMemorySensorTable
             |     |     |     - This table provides details about all numeric
             |     |     |       memory sensors including current reading,
             |     |     |       defined thresholds, current status, perceived
             |     |     |       severity and the FRU they are contained in.
             |     |     |       
             |     |     |__ sunHwMonDiscreteMemorySensorTable
             |     |           - This table provides details about all discrete
             |     |             memory sensors including current state,
             |     |             perceived severity and the FRU they are contained in.
             |     | 
             |     |__ sunHwMonHardDriveGroup
             |     |     |   - This group contains two MIB tables.
             |     |     |
             |     |     |__ sunHwMonNumericHardDriveSensorTable
             |     |     |     - This table provides details about all numeric
             |     |     |       hard drive sensors including current reading,
             |     |     |       defined thresholds, current status, perceived
             |     |     |       severity and the FRU they are contained in.
             |     |     |       
             |     |     |__ sunHwMonDiscreteHardDriveSensorTable
             |     |           - This table provides details about all discrete
             |     |             hard drive sensors including current state,
             |     |             perceived severity and the FRU they are contained in.
             |     | 
             |     |__ sunHwMonIOGroup
             |     |     |   - This group contains two MIB tables.
             |     |     |
             |     |     |__ sunHwMonNumericIOSensorTable
             |     |     |     - This table provides details about all numeric
             |     |     |       IO sensors including current reading,
             |     |     |       defined thresholds, current status, perceived
             |     |     |       severity and the FRU they are contained in.
             |     |     |       
             |     |     |__ sunHwMonDiscreteIOSensorTable
             |     |           - This table provides details about all discrete
             |     |             IO sensors including current state,
             |     |             perceived severity and the FRU they are contained in.
             |     |
             |     |__ sunHwMonSlotOrConnectorGroup
             |     |     |   - This group contains two MIB tables.
             |     |     |
             |     |     |__ sunHwMonNumericSlotOrConnectorSensorTable
             |     |     |     - This table provides details about all numeric
             |     |     |       slot or connector sensors including current reading,
             |     |     |       defined thresholds, current status, perceived
             |     |     |       severity and the FRU they are contained in.
             |     |     |       
             |     |     |__ sunHwMonDiscreteSlotOrConnectorSensorTable
             |     |           - This table provides details about all discrete
             |     |             slot or connector sensors including current state,
             |     |             perceived severity and the FRU they are contained in.
             |     | 
             |     |__ sunHwMonOtherSensorGroup
             |           |   - This group contains two MIB tables.
             |           |
             |           |__ sunHwMonNumericOtherSensorTable
             |           |     - This table provides details about all numeric
             |           |       sensors (that are not covered by any of the defined categories), 
             |           |       including current reading, defined thresholds, 
             |           |       current status, perceived severity and the
             |           |       FRU they are contained in.
             |           |       
             |           |__ sunHwMonDiscreteOtherSensorTable
             |                 - This table provides details about all discrete
             |                   sensors (that are not covered by any of the defined categories),
             |                   including current state, perceived severity and the
             |                   FRU they are contained in.                         
             |__ sunHwMonIndicatorGroup 
             |     |	- This group contains multiple groups, that provide
             |     |   details about the indicators present on the Sun Server
             |     |	  
             |     |
             |     |   sunHwMonIndicatorGroup contains the following groups
             |     |
             |     |__ sunHwMonIndicatorLocator
             |     |     - A scalar group that provides details about the
             |     |	      locator indicator and its current status.
             |     |
             |     |__ sunHwMonIndicatorService
             |     |     - A scalar group that provides details about the
             |     |	      service indicator and its current status.
             |     |
             |     |__ sunHwMonIndicatorAll
             |           - This group contains sunHwMonIndicatorTable that
             |             provides details about indicators (other than the locator
             |             and service indicators) present on the Sun server
             |
             |
             |__ sunHwMonTotalPowerConsumption
                    - This table provides details about the Sun server's total power
                      consumption such as current reading,
                      defined thresholds, current status and the FRU 
                      that this sensor is contained in.
             
             Conformance and Compliance section describes the groups
             and tables that are mandatory to implement."
    REVISION        "200903240000Z"
    DESCRIPTION     
            "Version: 1.0.0"
    ::= { singlesystem 1 }


SunAlarmStatusTC ::= TEXTUAL-CONVENTION
    STATUS          current
    DESCRIPTION     
            "Describes the alarm levels of an object."
    SYNTAX          INTEGER { cleared(1), critical(2), major(3), 
                        minor(4), warning(5), indeterminate(6), 
                        informational(7), pending(8) }

SunIndicatorStateTC ::= TEXTUAL-CONVENTION
    STATUS          current
    DESCRIPTION     
            "Describes the possible states of an LED indicator."
    SYNTAX          INTEGER { unknown(1), other(2), off(3), on(4), 
                        standby(5), slowBlinking(6), fastBlinking(7) }

SunNumericSensorEnabledThresholdsTC ::= TEXTUAL-CONVENTION
    STATUS          current
    DESCRIPTION     
            "Describes the possible thresholds that may be enabled on a sensor."
    SYNTAX          BITS { lowerThresholdNonCritical(0), 
                        upperThresholdNonCritical(1), 
                        lowerThresholdCritical(2), 
                        upperThresholdCritical(3), 
                        lowerThresholdFatal(4), upperThresholdFatal(5) }

SunChassisTypeTC ::= TEXTUAL-CONVENTION
    STATUS          current
    DESCRIPTION     
            "Describes the product's chassis type."
    SYNTAX          INTEGER { unknown(1), other(2), rackmount(3), 
                        blade(4), chassisMonitoringModule(5) }

SunIPModeTC ::= TEXTUAL-CONVENTION
    STATUS          current
    DESCRIPTION     
            "Describes the IP mode set on the server."
    SYNTAX          INTEGER { unknown(1), dhcp(2), static(3), none(4) }

SunHwMonAgentSPConnectionStatusTC ::= TEXTUAL-CONVENTION
    STATUS          current
    DESCRIPTION     
            "Describes the connection status between Sun hardware monitoring agent and Service Processor (ILOM)."
    SYNTAX          INTEGER { unknown(1), connected(2), degraded(3), 
                        disconnected(4) }

SunFruOrSensorTypeTC ::= TEXTUAL-CONVENTION
    STATUS          current
    DESCRIPTION     
            "Describes the type of FRU or sensor."
    SYNTAX          INTEGER { unknown(1), other(2), alarm(3), 
                        alarmCard(4), asic(5), battery(6), bios(7), 
                        blade(8), bladeCLI(9), 
                        bladeThermalOverrideState(10), chassis(11), 
                        chassisExternalConditions(12), 
                        chassisMonitoringModule(13), container(14), 
                        cpuBoardMemoryBranch(15), 
                        cpuBoardMemoryChannel(16), cpuCMP(17), 
                        cpuCore(18), cpuMemoryControllerChannel(19), 
                        cpuThread(20), current(21), dataMMU(22), 
                        dCache(23), dimm(24), diskBackplane(25), 
                        display(26), driveSlot(27), dvd(28), 
                        dvrm1V5Converter(29), dvrm3V3Converter(30), 
                        dvrmCoreConverter(31), dvrmFBDIMMConverter(32), 
                        dvrmPLXConverter(33), dvrmZambeziConverter(34), 
                        dvrmZambeziPLXConverter(35), 
                        ethernetConnector(36), expressModule(37), 
                        fabricExpansionModule(38), fan(39), 
                        fanModule(40), fanTray(41), fault(42), 
                        floatingPointUnit(43), frontFan(44), 
                        frontFanBoard(45), frontLEDBoard(46), 
                        hardDisk(47), hddFan(48), hostSystem(49), 
                        hotswapController(50), humidity(51), iCache(52), 
                        indicator(53), indicatorModule(54), 
                        infrastructureManager(55), input(56), 
                        instructionMMU(57), ioBoard(58), ioBoat(59), 
                        ioExpansionUnit(60), l2bank(61), l3bank(62), 
                        linkCard(63), memory(64), memoryBoard(65), 
                        memoryBoardMemoryBranch(66), 
                        memoryBoardMemoryChannel(67), memoryBranch(68), 
                        memoryBranchOnMemoryRiser(69), 
                        memoryChannelOnMemoryRiser(70), memoryCMP(71), 
                        memoryController(72), memoryRank(73), 
                        memoryRiser(74), microCore(75), motherBoard(76), 
                        nemState(77), networkConfiguration(78), 
                        networkExpressModule(79), networkInterface(80), 
                        networkInterfacePort(81), networkModule(82), 
                        notReady(83), notReadyDeactivating(84), 
                        nvram(85), output(86), pciExpansionBoard(87), 
                        pciExpressInterface(88), pciSwitch(89), 
                        pciTray(90), pciXModule(91), pdbFan(92), 
                        physicalSecurity(93), powerConditions(94), 
                        powerDistributionBoard(95), powerOn(96), 
                        powerPCCPU(97), powerState(98), powerSupply(99), 
                        powerSupplyExternalConditions(100), 
                        powerSupplyInternalSide(101), 
                        powerSupplyStatus(102), powerUnit(103), 
                        presence(104), processor(105), 
                        processorBoard(106), prom(107), pushButton(108), 
                        raidExpansionModule(109), ready(110), 
                        rearFan(111), rearFanBoard(112), 
                        rearLEDBoard(113), riserBoard(114), 
                        sasController(115), serialConnector(116), 
                        serviceProcessor(117), slot(118), slotId(119), 
                        spBoardModule(120), speed(121), 
                        streamingProcessorUnit(122), systemFan(123), 
                        temperature(124), thermalConditions(125), 
                        toggleSwitch(126), tty(127), usbBoard(128), 
                        usbConnector(129), usbPort(130), vibration(131), 
                        video(132), voltage(133), xauiBoard(134) }

SunBaseUnitsTC ::= TEXTUAL-CONVENTION
    STATUS          current
    DESCRIPTION     
            "Physical values are represented in the units obtained by calculating
             (sunHwMonBaseUnits * 10 raised to the power of sunHwMonExponent). For 
             example, if sunHwMonBaseUnits is volts(6) and sunHwMonExponent is -6, 
             then the values returned are in microvolts."
    SYNTAX          INTEGER { unknown(1), other(2), degC(3), volts(4), 
                        amps(5), watts(6), rpm(7) }

sun OBJECT IDENTIFIER
    ::= { enterprises 42 }

products OBJECT IDENTIFIER
    ::= { enterprises 42 2 }

management OBJECT IDENTIFIER
    ::= { enterprises 42 2 2 }

singlesystem OBJECT IDENTIFIER
    ::= { management 6 }

sunHwMonGroups OBJECT IDENTIFIER
    ::= { sunHwMonMIB 1 }

sunHwMonProductGroup OBJECT IDENTIFIER
    ::= { sunHwMonGroups 1 }

sunHwMonProductName OBJECT-TYPE
    SYNTAX          DisplayString (SIZE(0..255))
    MAX-ACCESS      read-only
    STATUS          current
    DESCRIPTION     
            "Defines the Sun server's product name. If the
             server is a Blade, the text string will contain the chassis
             product name and the Blade product name, in the following
             format <chassis-name>::<blade-name>."
    ::= { sunHwMonProductGroup 1 }

sunHwMonProductType OBJECT-TYPE
    SYNTAX          SunChassisTypeTC
    MAX-ACCESS      read-only
    STATUS          current
    DESCRIPTION     
            "This attribute defines the Sun server's type of chassis."
    ::= { sunHwMonProductGroup 2 }

sunHwMonProductPartNumber OBJECT-TYPE
    SYNTAX          DisplayString (SIZE(0..255))
    MAX-ACCESS      read-only
    STATUS          current
    DESCRIPTION     
            "This attribute defines the Sun server's part number."
    ::= { sunHwMonProductGroup 3 }

sunHwMonProductSerialNumber OBJECT-TYPE
    SYNTAX          DisplayString (SIZE(0..255))
    MAX-ACCESS      read-only
    STATUS          current
    DESCRIPTION     
            "This attribute defines the Sun server's serial number."
    ::= { sunHwMonProductGroup 4 }

sunHwMonProductManufacturer OBJECT-TYPE
    SYNTAX          DisplayString (SIZE(0..255))
    MAX-ACCESS      read-only
    STATUS          current
    DESCRIPTION     
            "This attribute defines the server's manufacturer."
    ::= { sunHwMonProductGroup 5 }

sunHwMonProductSlotNumber OBJECT-TYPE
    SYNTAX          Integer32 (-1..2147483647)
    MAX-ACCESS      read-only
    STATUS          current
    DESCRIPTION     
            "If the server is a Blade, this attribute reports which slot of the
             chassis this Blade is present in. Otherwise, this should be 
             filled by -1."
    ::= { sunHwMonProductGroup 6 }

sunHwMonProductUUID OBJECT-TYPE
    SYNTAX          DisplayString (SIZE(0..255))
    MAX-ACCESS      read-only
    STATUS          current
    DESCRIPTION     
            "This attribute defines the Sun server's UUID."
    ::= { sunHwMonProductGroup 7 }

sunHwMonProductBiosVersion OBJECT-TYPE
    SYNTAX          DisplayString (SIZE(0..255))
    MAX-ACCESS      read-only
    STATUS          current
    DESCRIPTION     
            "This attribute defines the Sun server's BIOS version."
    ::= { sunHwMonProductGroup 8 }

sunHwMonProductChassisGroup OBJECT IDENTIFIER
    ::= { sunHwMonGroups 2 }

sunHwMonProductChassisName OBJECT-TYPE
    SYNTAX          DisplayString (SIZE(0..255))
    MAX-ACCESS      read-only
    STATUS          current
    DESCRIPTION     
            "A text string containing the Sun server's chassis name. If the
             server is a Blade, the text string will contain the chassis
             product name."
    ::= { sunHwMonProductChassisGroup 1 }

sunHwMonProductChassisPartNumber OBJECT-TYPE
    SYNTAX          DisplayString (SIZE(0..255))
    MAX-ACCESS      read-only
    STATUS          current
    DESCRIPTION     
            "This attribute defines the Sun server's chassis part number."
    ::= { sunHwMonProductChassisGroup 2 }

sunHwMonProductChassisSerialNumber OBJECT-TYPE
    SYNTAX          DisplayString (SIZE(0..255))
    MAX-ACCESS      read-only
    STATUS          current
    DESCRIPTION     
            "This attribute defines the Sun server's chassis serial number."
    ::= { sunHwMonProductChassisGroup 3 }

sunHwMonProductChassisManufacturer OBJECT-TYPE
    SYNTAX          DisplayString (SIZE(0..255))
    MAX-ACCESS      read-only
    STATUS          current
    DESCRIPTION     
            "This attribute defines the server's chassis manufacturer."
    ::= { sunHwMonProductChassisGroup 4 }

sunHwMonSPGroup OBJECT IDENTIFIER
    ::= { sunHwMonGroups 3 }

sunHwMonSPSerialNumber OBJECT-TYPE
    SYNTAX          DisplayString (SIZE(0..255))
    MAX-ACCESS      read-only
    STATUS          current
    DESCRIPTION     
            "This attribute defines the Sun server's SP serial number."
    ::= { sunHwMonSPGroup 1 }

sunHwMonSPManufacturer OBJECT-TYPE
    SYNTAX          DisplayString (SIZE(0..255))
    MAX-ACCESS      read-only
    STATUS          current
    DESCRIPTION     
            "This attribute defines the Sun server's SP manufacturer."
    ::= { sunHwMonSPGroup 2 }

sunHwMonSPFWVersion OBJECT-TYPE
    SYNTAX          DisplayString (SIZE(0..255))
    MAX-ACCESS      read-only
    STATUS          current
    DESCRIPTION     
            "This attribute defines the Sun server's SP firwmare version."
    ::= { sunHwMonSPGroup 3 }

sunHwMonSPMacAddress OBJECT-TYPE
    SYNTAX          MacAddress
    MAX-ACCESS      read-only
    STATUS          current
    DESCRIPTION     
            "This attribute defines the Sun server's SP MAC Address."
    ::= { sunHwMonSPGroup 4 }

sunHwMonSPIPAddress OBJECT-TYPE
    SYNTAX          IpAddress
    MAX-ACCESS      read-only
    STATUS          current
    DESCRIPTION     
            "This attribute defines the Sun server's SP IP Address."
    ::= { sunHwMonSPGroup 5 }

sunHwMonSPNetMask OBJECT-TYPE
    SYNTAX          IpAddress
    MAX-ACCESS      read-only
    STATUS          current
    DESCRIPTION     
            "This attribute defines the Sun server's SP net mask."
    ::= { sunHwMonSPGroup 6 }

sunHwMonSPDefaultGateway OBJECT-TYPE
    SYNTAX          IpAddress
    MAX-ACCESS      read-only
    STATUS          current
    DESCRIPTION     
            "This attribute defines the Sun server's SP default gateway."
    ::= { sunHwMonSPGroup 7 }

sunHwMonSPIPMode OBJECT-TYPE
    SYNTAX          SunIPModeTC
    MAX-ACCESS      read-only
    STATUS          current
    DESCRIPTION     
            "This attribute defines the IP mode set on the SP."
    ::= { sunHwMonSPGroup 8 }

sunHwMonSPURLToLaunch OBJECT-TYPE
    SYNTAX          DisplayString (SIZE(0..255))
    MAX-ACCESS      read-only
    STATUS          current
    DESCRIPTION     
            "This attribute defines the URL to launch the SP web GUI."
    ::= { sunHwMonSPGroup 9 }

sunHwMonSPSystemIdentifier OBJECT-TYPE
    SYNTAX          DisplayString (SIZE(0..255))
    MAX-ACCESS      read-only
    STATUS          current
    DESCRIPTION     
            "This attribute defines the System Identifier set on the SP.
             The System Identfier can be set either via the SP ILOM Web GUI or CLI."
    ::= { sunHwMonSPGroup 10 }

sunHwMonMibGroup OBJECT IDENTIFIER
    ::= { sunHwMonGroups 4 }

sunHwMonMibVersion OBJECT-TYPE
    SYNTAX          DisplayString (SIZE(0..255))
    MAX-ACCESS      read-only
    STATUS          current
    DESCRIPTION     
            "This attribute defines the version of the SUN-HW-MONITORING-MIB. 
             The version defined should be in the format of MajorVersion.MinorVersion.
             SubMinorVersion. For example: 1.2.3"
    ::= { sunHwMonMibGroup 1 }

sunHwMonAgentSoftwareGroup OBJECT IDENTIFIER
    ::= { sunHwMonGroups 5 }

sunHwMonAgentVersion OBJECT-TYPE
    SYNTAX          DisplayString (SIZE(0..255))
    MAX-ACCESS      read-only
    STATUS          current
    DESCRIPTION     
            "This attribute defines the version of the Sun agent. 
             The version defined should be in the format of MajorVersion.MinorVersion.
             SubMinorVersion. For example: 1.2.3"
    ::= { sunHwMonAgentSoftwareGroup 1 }

sunHwMonAgentSPConnectionStatus OBJECT-TYPE
    SYNTAX          SunHwMonAgentSPConnectionStatusTC
    MAX-ACCESS      read-only
    STATUS          current
    DESCRIPTION     
            "This attribute defines the status of the connection between Sun hardware 
             monitoring agent and the Service Processor (ILOM)"
    ::= { sunHwMonAgentSoftwareGroup 2 }

sunHwMonInventoryGroup OBJECT IDENTIFIER
    ::= { sunHwMonGroups 6 }

sunHwMonInventoryTable OBJECT-TYPE
    SYNTAX          SEQUENCE OF SunHwMonInventoryEntry
    MAX-ACCESS      not-accessible
    STATUS          current
    DESCRIPTION     
            "This attribute defines the Sun server's hardware inventory table."
    ::= { sunHwMonInventoryGroup 1 }

sunHwMonInventoryEntry OBJECT-TYPE
    SYNTAX          SunHwMonInventoryEntry
    MAX-ACCESS      not-accessible
    STATUS          current
    DESCRIPTION     
            "This attribute defines the Sun server's hardware inventory entry."
    INDEX           { sunHwMonFruIndex }
    ::= { sunHwMonInventoryTable 1 }

SunHwMonInventoryEntry ::=
    SEQUENCE {
        sunHwMonFruIndex                Integer32,
        sunHwMonFruName                 DisplayString,
        sunHwMonFruType                 SunFruOrSensorTypeTC,
        sunHwMonFruDescr                DisplayString,
        sunHwMonFruPartNumber           DisplayString,
        sunHwMonFruSerialNumber         DisplayString,
        sunHwMonFruManufacturer         DisplayString,
        sunHwMonFruStatus               SunAlarmStatusTC,
        sunHwMonParentFruIndex          Integer32,
        sunHwMonParentFruName           DisplayString
    }

sunHwMonFruIndex OBJECT-TYPE
    SYNTAX          Integer32 (1..2147483647)
    MAX-ACCESS      not-accessible
    STATUS          current
    DESCRIPTION     
            "This attribute defines the index of the Sun server's FRU."
    ::= { sunHwMonInventoryEntry 1 }

sunHwMonFruName OBJECT-TYPE
    SYNTAX          DisplayString (SIZE(0..255))
    MAX-ACCESS      read-only
    STATUS          current
    DESCRIPTION     
            "This attribute defines the NAC name of the Sun server's FRU."
    ::= { sunHwMonInventoryEntry 2 }

sunHwMonFruType OBJECT-TYPE
    SYNTAX          SunFruOrSensorTypeTC
    MAX-ACCESS      read-only
    STATUS          current
    DESCRIPTION     
            "This attribute defines the type of Sun server FRU."
    ::= { sunHwMonInventoryEntry 3 }

sunHwMonFruDescr OBJECT-TYPE
    SYNTAX          DisplayString (SIZE(0..255))
    MAX-ACCESS      read-only
    STATUS          current
    DESCRIPTION     
            "This attribute defines the Sun server's FRU description."
    ::= { sunHwMonInventoryEntry 4 }

sunHwMonFruPartNumber OBJECT-TYPE
    SYNTAX          DisplayString (SIZE(0..255))
    MAX-ACCESS      read-only
    STATUS          current
    DESCRIPTION     
            "This attribute defines the Sun server's FRU part number."
    ::= { sunHwMonInventoryEntry 5 }

sunHwMonFruSerialNumber OBJECT-TYPE
    SYNTAX          DisplayString (SIZE(0..255))
    MAX-ACCESS      read-only
    STATUS          current
    DESCRIPTION     
            "This attribute defines the Sun server's FRU serial number."
    ::= { sunHwMonInventoryEntry 6 }

sunHwMonFruManufacturer OBJECT-TYPE
    SYNTAX          DisplayString (SIZE(0..255))
    MAX-ACCESS      read-only
    STATUS          current
    DESCRIPTION     
            "This attribute defines the Sun server's FRU manufacturer."
    ::= { sunHwMonInventoryEntry 7 }

sunHwMonFruStatus OBJECT-TYPE
    SYNTAX          SunAlarmStatusTC
    MAX-ACCESS      read-only
    STATUS          current
    DESCRIPTION     
            "This attribute defines the status of the Sun server's FRU."
    ::= { sunHwMonInventoryEntry 8 }

sunHwMonParentFruIndex OBJECT-TYPE
    SYNTAX          Integer32 (1..2147483647)
    MAX-ACCESS      read-only
    STATUS          current
    DESCRIPTION     
            "This attribute defines the index of the Sun server's FRU parent."
    ::= { sunHwMonInventoryEntry 9 }

sunHwMonParentFruName OBJECT-TYPE
    SYNTAX          DisplayString (SIZE(0..255))
    MAX-ACCESS      read-only
    STATUS          current
    DESCRIPTION     
            "This attribute defines the name of the Sun server's FRU parent."
    ::= { sunHwMonInventoryEntry 10 }

sunHwMonSensorGroup OBJECT IDENTIFIER
    ::= { sunHwMonGroups 7 }

sunHwMonSensorAlarmStatusGroup OBJECT IDENTIFIER
    ::= { sunHwMonSensorGroup 1 }

sunHwMonCumulativeSensorAlarmStatus OBJECT-TYPE
    SYNTAX          SunAlarmStatusTC
    MAX-ACCESS      read-only
    STATUS          current
    DESCRIPTION     
            "This attribute defines the cumulative status of all sensors monitoring
             various parameters on a Sun server."
    ::= { sunHwMonSensorAlarmStatusGroup 1 }

sunHwMonCumulativeVoltageSensorAlarmStatus OBJECT-TYPE
    SYNTAX          SunAlarmStatusTC
    MAX-ACCESS      read-only
    STATUS          current
    DESCRIPTION     
            "This attribute defines the cumulative status of all sensors monitoring
             voltage on a Sun server."
    ::= { sunHwMonSensorAlarmStatusGroup 2 }

sunHwMonCumulativeCurrentSensorAlarmStatus OBJECT-TYPE
    SYNTAX          SunAlarmStatusTC
    MAX-ACCESS      read-only
    STATUS          current
    DESCRIPTION     
            "This attribute defines the cumulative status of all sensors monitoring
             electric current on a Sun server."
    ::= { sunHwMonSensorAlarmStatusGroup 3 }

sunHwMonCumulativePowerDeviceSensorAlarmStatus OBJECT-TYPE
    SYNTAX          SunAlarmStatusTC
    MAX-ACCESS      read-only
    STATUS          current
    DESCRIPTION     
            "This attribute defines the cumulative status of all sensors monitoring
             power supplies on a Sun server."
    ::= { sunHwMonSensorAlarmStatusGroup 4 }

sunHwMonCumulativeCoolingDeviceAlarmStatus OBJECT-TYPE
    SYNTAX          SunAlarmStatusTC
    MAX-ACCESS      read-only
    STATUS          current
    DESCRIPTION     
            "This attribute defines the cumulative status of all cooling units
             on a Sun server."
    ::= { sunHwMonSensorAlarmStatusGroup 5 }

sunHwMonCumulativeTemperatureSensorAlarmStatus OBJECT-TYPE
    SYNTAX          SunAlarmStatusTC
    MAX-ACCESS      read-only
    STATUS          current
    DESCRIPTION     
            "This attribute defines the cumulative status of all sensors monitoring
             temperature on a Sun server."
    ::= { sunHwMonSensorAlarmStatusGroup 6 }

sunHwMonCumulativeProcessorAlarmStatus OBJECT-TYPE
    SYNTAX          SunAlarmStatusTC
    MAX-ACCESS      read-only
    STATUS          current
    DESCRIPTION     
            "This attribute defines the cumulative status of all processors
             on a Sun server."
    ::= { sunHwMonSensorAlarmStatusGroup 7 }

sunHwMonCumulativeMemoryAlarmStatus OBJECT-TYPE
    SYNTAX          SunAlarmStatusTC
    MAX-ACCESS      read-only
    STATUS          current
    DESCRIPTION     
            "This attribute defines the cumulative status of all memory devices
             on a Sun server."
    ::= { sunHwMonSensorAlarmStatusGroup 8 }

sunHwMonCumulativeHardDriveAlarmStatus OBJECT-TYPE
    SYNTAX          SunAlarmStatusTC
    MAX-ACCESS      read-only
    STATUS          current
    DESCRIPTION     
            "This attribute defines the cumulative status of all hard drives
             on a Sun server."
    ::= { sunHwMonSensorAlarmStatusGroup 9 }

sunHwMonCumulativeIOAlarmStatus OBJECT-TYPE
    SYNTAX          SunAlarmStatusTC
    MAX-ACCESS      read-only
    STATUS          current
    DESCRIPTION     
            "This attribute defines the cumulative status of all IO sensors
             on a Sun server."
    ::= { sunHwMonSensorAlarmStatusGroup 10 }

sunHwMonCumulativeSlotOrConnectorAlarmStatus OBJECT-TYPE
    SYNTAX          SunAlarmStatusTC
    MAX-ACCESS      read-only
    STATUS          current
    DESCRIPTION     
            "This attribute defines the cumulative status of all slots or
             connectors on a Sun server."
    ::= { sunHwMonSensorAlarmStatusGroup 11 }

sunHwMonCumulativeOtherSensorAlarmStatus OBJECT-TYPE
    SYNTAX          SunAlarmStatusTC
    MAX-ACCESS      read-only
    STATUS          current
    DESCRIPTION     
            "This attribute defines the cumulative status of all sensors
             that do not fall into any defined category in 
             sunHwMonOtherSensorsGroup."
    ::= { sunHwMonSensorAlarmStatusGroup 12 }

sunHwMonVoltageGroup OBJECT IDENTIFIER
    ::= { sunHwMonSensorGroup 2 }

sunHwMonNumericVoltageSensorTable OBJECT-TYPE
    SYNTAX          SEQUENCE OF SunHwMonNumericVoltageSensorEntry
    MAX-ACCESS      not-accessible
    STATUS          current
    DESCRIPTION     
            "This attribute defines the numeric voltage sensor table."
    ::= { sunHwMonVoltageGroup 1 }

sunHwMonNumericVoltageSensorEntry OBJECT-TYPE
    SYNTAX          SunHwMonNumericVoltageSensorEntry
    MAX-ACCESS      not-accessible
    STATUS          current
    DESCRIPTION     
            "This attribute defines the numeric voltage sensor entry."
    INDEX           { sunHwMonNumericVoltageSensorIndex }
    ::= { sunHwMonNumericVoltageSensorTable 1 }

SunHwMonNumericVoltageSensorEntry ::=
    SEQUENCE {
        sunHwMonNumericVoltageSensorIndex Integer32,
        sunHwMonNumericVoltageSensorType SunFruOrSensorTypeTC,
        sunHwMonNumericVoltageSensorName DisplayString,
        sunHwMonNumericVoltageSensorParentFruIndex          Integer32,
        sunHwMonNumericVoltageSensorParentFruName         DisplayString,
        sunHwMonNumericVoltageSensorAlarmStatus       SunAlarmStatusTC,
        sunHwMonNumericVoltageSensorStateDescr      DisplayString,
        sunHwMonNumericVoltageSensorCurrentValue        Integer32,
        sunHwMonNumericVoltageSensorBaseUnit    SunBaseUnitsTC,
        sunHwMonNumericVoltageSensorExponent    Integer32,
        sunHwMonNumericVoltageSensorUpperNonRecoverableThreshold                        Integer32,
        sunHwMonNumericVoltageSensorUpperCriticalThreshold                  Integer32,
        sunHwMonNumericVoltageSensorUpperNonCriticalThreshold                     Integer32,
        sunHwMonNumericVoltageSensorLowerNonRecoverableThreshold                        Integer32,
        sunHwMonNumericVoltageSensorLowerCriticalThreshold                  Integer32,
        sunHwMonNumericVoltageSensorLowerNonCriticalThreshold                     Integer32,
        sunHwMonNumericVoltageSensorEnabledThresholds             SunNumericSensorEnabledThresholdsTC
    }

sunHwMonNumericVoltageSensorIndex OBJECT-TYPE
    SYNTAX          Integer32 (1..2147483647)
    MAX-ACCESS      not-accessible
    STATUS          current
    DESCRIPTION     
            "This attribute defines the index of the voltage sensor."
    ::= { sunHwMonNumericVoltageSensorEntry 1 }

sunHwMonNumericVoltageSensorType OBJECT-TYPE
    SYNTAX          SunFruOrSensorTypeTC
    MAX-ACCESS      read-only
    STATUS          current
    DESCRIPTION     
            "This attribute defines the type of voltage sensor."
    ::= { sunHwMonNumericVoltageSensorEntry 2 }

sunHwMonNumericVoltageSensorName OBJECT-TYPE
    SYNTAX          DisplayString (SIZE(0..255))
    MAX-ACCESS      read-only
    STATUS          current
    DESCRIPTION     
            "This attribute defines the name of the voltage sensor."
    ::= { sunHwMonNumericVoltageSensorEntry 3 }

sunHwMonNumericVoltageSensorParentFruIndex OBJECT-TYPE
    SYNTAX          Integer32 (1..2147483647)
    MAX-ACCESS      read-only
    STATUS          current
    DESCRIPTION     
            "This attribute defines the index of the field replaceable unit (FRU)
             which contains the sensor."
    ::= { sunHwMonNumericVoltageSensorEntry 4 }

sunHwMonNumericVoltageSensorParentFruName OBJECT-TYPE
    SYNTAX          DisplayString (SIZE(0..255))
    MAX-ACCESS      read-only
    STATUS          current
    DESCRIPTION     
            "This attribute defines the name of the field replaceable unit (FRU)
             which contains the sensor."
    ::= { sunHwMonNumericVoltageSensorEntry 5 }

sunHwMonNumericVoltageSensorAlarmStatus OBJECT-TYPE
    SYNTAX          SunAlarmStatusTC
    MAX-ACCESS      read-only
    STATUS          current
    DESCRIPTION     
            "This attribute defines the status of the voltage sensor."
    ::= { sunHwMonNumericVoltageSensorEntry 6 }

sunHwMonNumericVoltageSensorStateDescr OBJECT-TYPE
    SYNTAX          DisplayString (SIZE(0..255))
    MAX-ACCESS      read-only
    STATUS          current
    DESCRIPTION     
            "This attribute defines the state of the voltage sensor."
    ::= { sunHwMonNumericVoltageSensorEntry 7 }

sunHwMonNumericVoltageSensorCurrentValue OBJECT-TYPE
    SYNTAX          Integer32 (-2147483647..2147483647)
    MAX-ACCESS      read-only
    STATUS          current
    DESCRIPTION     
            "This attribute defines the current reading of the voltage sensor."
    ::= { sunHwMonNumericVoltageSensorEntry 8 }

sunHwMonNumericVoltageSensorBaseUnit OBJECT-TYPE
    SYNTAX          SunBaseUnitsTC
    MAX-ACCESS      read-only
    STATUS          current
    DESCRIPTION     
            "This attribute defines the units used to express the current reading 
             as well as the various thresholds of the voltage sensor."
    ::= { sunHwMonNumericVoltageSensorEntry 9 }

sunHwMonNumericVoltageSensorExponent OBJECT-TYPE
    SYNTAX          Integer32 (-2147483647..2147483647)
    MAX-ACCESS      read-only
    STATUS          current
    DESCRIPTION     
            "This attribute defines the exponent that needs to be applied to the 
             units used to express the current reading, as well as the various
             thresholds of the voltage sensor."
    ::= { sunHwMonNumericVoltageSensorEntry 10 }

sunHwMonNumericVoltageSensorUpperNonRecoverableThreshold OBJECT-TYPE
    SYNTAX          Integer32 (-2147483647..2147483647)
    MAX-ACCESS      read-only
    STATUS          current
    DESCRIPTION     
            "This attribute defines the upper threshold at which a nonrecoverable
             condition occurs."
    ::= { sunHwMonNumericVoltageSensorEntry 11 }

sunHwMonNumericVoltageSensorUpperCriticalThreshold OBJECT-TYPE
    SYNTAX          Integer32 (-2147483647..2147483647)
    MAX-ACCESS      read-only
    STATUS          current
    DESCRIPTION     
            "This attribute defines the upper threshold at which a critical
             condition occurs."
    ::= { sunHwMonNumericVoltageSensorEntry 12 }

sunHwMonNumericVoltageSensorUpperNonCriticalThreshold OBJECT-TYPE
    SYNTAX          Integer32 (-2147483647..2147483647)
    MAX-ACCESS      read-only
    STATUS          current
    DESCRIPTION     
            "This attribute defines the upper threshold at which a noncritical
             condition occurs."
    ::= { sunHwMonNumericVoltageSensorEntry 13 }

sunHwMonNumericVoltageSensorLowerNonRecoverableThreshold OBJECT-TYPE
    SYNTAX          Integer32 (-2147483647..2147483647)
    MAX-ACCESS      read-only
    STATUS          current
    DESCRIPTION     
            "This attribute defines the lower threshold at which a nonrecoverable
             condition occurs."
    ::= { sunHwMonNumericVoltageSensorEntry 14 }

sunHwMonNumericVoltageSensorLowerCriticalThreshold OBJECT-TYPE
    SYNTAX          Integer32 (-2147483647..2147483647)
    MAX-ACCESS      read-only
    STATUS          current
    DESCRIPTION     
            "This attribute defines the lower threshold at which a critical
             condition occurs."
    ::= { sunHwMonNumericVoltageSensorEntry 15 }

sunHwMonNumericVoltageSensorLowerNonCriticalThreshold OBJECT-TYPE
    SYNTAX          Integer32 (-2147483647..2147483647)
    MAX-ACCESS      read-only
    STATUS          current
    DESCRIPTION     
            "This attribute defines the lower threshold at which a noncritical
             condition occurs."
    ::= { sunHwMonNumericVoltageSensorEntry 16 }

sunHwMonNumericVoltageSensorEnabledThresholds OBJECT-TYPE
    SYNTAX          SunNumericSensorEnabledThresholdsTC
    MAX-ACCESS      read-only
    STATUS          current
    DESCRIPTION     
            "This attribute defines the thresholds enabled for this voltage
             sensor."
    ::= { sunHwMonNumericVoltageSensorEntry 17 }

sunHwMonDiscreteVoltageSensorTable OBJECT-TYPE
    SYNTAX          SEQUENCE OF SunHwMonDiscreteVoltageSensorEntry
    MAX-ACCESS      not-accessible
    STATUS          current
    DESCRIPTION     
            "This attribute defines the discrete voltage sensor table."
    ::= { sunHwMonVoltageGroup 2 }

sunHwMonDiscreteVoltageSensorEntry OBJECT-TYPE
    SYNTAX          SunHwMonDiscreteVoltageSensorEntry
    MAX-ACCESS      not-accessible
    STATUS          current
    DESCRIPTION     
            "This attribute defines the discrete voltage sensor entry."
    INDEX           { sunHwMonDiscreteVoltageSensorIndex }
    ::= { sunHwMonDiscreteVoltageSensorTable 1 }

SunHwMonDiscreteVoltageSensorEntry ::=
    SEQUENCE {
        sunHwMonDiscreteVoltageSensorIndex  Integer32,
        sunHwMonDiscreteVoltageSensorType SunFruOrSensorTypeTC,
        sunHwMonDiscreteVoltageSensorName DisplayString,
        sunHwMonDiscreteVoltageSensorParentFruIndex           Integer32,
        sunHwMonDiscreteVoltageSensorParentFruName          DisplayString,
        sunHwMonDiscreteVoltageSensorAlarmStatus        SunAlarmStatusTC,
        sunHwMonDiscreteVoltageSensorStateDescr       DisplayString
    }

sunHwMonDiscreteVoltageSensorIndex OBJECT-TYPE
    SYNTAX          Integer32 (1..2147483647)
    MAX-ACCESS      not-accessible
    STATUS          current
    DESCRIPTION     
            "This attribute defines the index of the voltage sensor."
    ::= { sunHwMonDiscreteVoltageSensorEntry 1 }

sunHwMonDiscreteVoltageSensorType OBJECT-TYPE
    SYNTAX          SunFruOrSensorTypeTC
    MAX-ACCESS      read-only
    STATUS          current
    DESCRIPTION     
            "This attribute defines the type of voltage sensor."
    ::= { sunHwMonDiscreteVoltageSensorEntry 2 }

sunHwMonDiscreteVoltageSensorName OBJECT-TYPE
    SYNTAX          DisplayString (SIZE(0..255))
    MAX-ACCESS      read-only
    STATUS          current
    DESCRIPTION     
            "This attribute defines the name of the voltage sensor."
    ::= { sunHwMonDiscreteVoltageSensorEntry 3 }

sunHwMonDiscreteVoltageSensorParentFruIndex OBJECT-TYPE
    SYNTAX          Integer32 (1..2147483647)
    MAX-ACCESS      read-only
    STATUS          current
    DESCRIPTION     
            "This attribute defines the index of the field replaceable unit (FRU)
             which the contains the sensor."
    ::= { sunHwMonDiscreteVoltageSensorEntry 4 }

sunHwMonDiscreteVoltageSensorParentFruName OBJECT-TYPE
    SYNTAX          DisplayString (SIZE(0..255))
    MAX-ACCESS      read-only
    STATUS          current
    DESCRIPTION     
            "This attribute defines the name of the field replaceable unit (FRU)
             which the contains the sensor."
    ::= { sunHwMonDiscreteVoltageSensorEntry 5 }

sunHwMonDiscreteVoltageSensorAlarmStatus OBJECT-TYPE
    SYNTAX          SunAlarmStatusTC
    MAX-ACCESS      read-only
    STATUS          current
    DESCRIPTION     
            "This attribute defines the status of the voltage sensor."
    ::= { sunHwMonDiscreteVoltageSensorEntry 6 }

sunHwMonDiscreteVoltageSensorStateDescr OBJECT-TYPE
    SYNTAX          DisplayString (SIZE(0..255))
    MAX-ACCESS      read-only
    STATUS          current
    DESCRIPTION     
            "This attribute defines the state of the voltage sensor."
    ::= { sunHwMonDiscreteVoltageSensorEntry 7 }

sunHwMonCurrentGroup OBJECT IDENTIFIER
    ::= { sunHwMonSensorGroup 3 }

sunHwMonNumericCurrentSensorTable OBJECT-TYPE
    SYNTAX          SEQUENCE OF SunHwMonNumericCurrentSensorEntry
    MAX-ACCESS      not-accessible
    STATUS          current
    DESCRIPTION     
            "This attribute defines the numeric current sensor table."
    ::= { sunHwMonCurrentGroup 1 }

sunHwMonNumericCurrentSensorEntry OBJECT-TYPE
    SYNTAX          SunHwMonNumericCurrentSensorEntry
    MAX-ACCESS      not-accessible
    STATUS          current
    DESCRIPTION     
            "This attribute defines the numeric current sensor entry."
    INDEX           { sunHwMonNumericCurrentSensorIndex }
    ::= { sunHwMonNumericCurrentSensorTable 1 }

SunHwMonNumericCurrentSensorEntry ::=
    SEQUENCE {
        sunHwMonNumericCurrentSensorIndex Integer32,
        sunHwMonNumericCurrentSensorType SunFruOrSensorTypeTC,
        sunHwMonNumericCurrentSensorName DisplayString,
        sunHwMonNumericCurrentSensorParentFruIndex          Integer32,
        sunHwMonNumericCurrentSensorParentFruName         DisplayString,
        sunHwMonNumericCurrentSensorAlarmStatus       SunAlarmStatusTC,
        sunHwMonNumericCurrentSensorStateDescr      DisplayString,
        sunHwMonNumericCurrentSensorCurrentValue        Integer32,
        sunHwMonNumericCurrentSensorBaseUnit    SunBaseUnitsTC,
        sunHwMonNumericCurrentSensorExponent    Integer32,
        sunHwMonNumericCurrentSensorUpperNonRecoverableThreshold                        Integer32,
        sunHwMonNumericCurrentSensorUpperCriticalThreshold                  Integer32,
        sunHwMonNumericCurrentSensorUpperNonCriticalThreshold                     Integer32,
        sunHwMonNumericCurrentSensorLowerNonRecoverableThreshold                        Integer32,
        sunHwMonNumericCurrentSensorLowerCriticalThreshold                  Integer32,
        sunHwMonNumericCurrentSensorLowerNonCriticalThreshold                     Integer32,
        sunHwMonNumericCurrentSensorEnabledThresholds             SunNumericSensorEnabledThresholdsTC
    }

sunHwMonNumericCurrentSensorIndex OBJECT-TYPE
    SYNTAX          Integer32 (1..2147483647)
    MAX-ACCESS      not-accessible
    STATUS          current
    DESCRIPTION     
            "This attribute defines the index of the current sensor."
    ::= { sunHwMonNumericCurrentSensorEntry 1 }

sunHwMonNumericCurrentSensorType OBJECT-TYPE
    SYNTAX          SunFruOrSensorTypeTC
    MAX-ACCESS      read-only
    STATUS          current
    DESCRIPTION     
            "This attribute defines the type of current sensor."
    ::= { sunHwMonNumericCurrentSensorEntry 2 }

sunHwMonNumericCurrentSensorName OBJECT-TYPE
    SYNTAX          DisplayString (SIZE(0..255))
    MAX-ACCESS      read-only
    STATUS          current
    DESCRIPTION     
            "This attribute defines the name of the current sensor."
    ::= { sunHwMonNumericCurrentSensorEntry 3 }

sunHwMonNumericCurrentSensorParentFruIndex OBJECT-TYPE
    SYNTAX          Integer32 (1..2147483647)
    MAX-ACCESS      read-only
    STATUS          current
    DESCRIPTION     
            "This attribute defines the index of the field replaceable unit (FRU)
             which the contains the sensor."
    ::= { sunHwMonNumericCurrentSensorEntry 4 }

sunHwMonNumericCurrentSensorParentFruName OBJECT-TYPE
    SYNTAX          DisplayString (SIZE(0..255))
    MAX-ACCESS      read-only
    STATUS          current
    DESCRIPTION     
            "This attribute defines the name of the field replaceable unit (FRU)
             which the contains the sensor."
    ::= { sunHwMonNumericCurrentSensorEntry 5 }

sunHwMonNumericCurrentSensorAlarmStatus OBJECT-TYPE
    SYNTAX          SunAlarmStatusTC
    MAX-ACCESS      read-only
    STATUS          current
    DESCRIPTION     
            "This attribute defines the status of the current sensor."
    ::= { sunHwMonNumericCurrentSensorEntry 6 }

sunHwMonNumericCurrentSensorStateDescr OBJECT-TYPE
    SYNTAX          DisplayString (SIZE(0..255))
    MAX-ACCESS      read-only
    STATUS          current
    DESCRIPTION     
            "This attribute defines the state of the current sensor."
    ::= { sunHwMonNumericCurrentSensorEntry 7 }

sunHwMonNumericCurrentSensorCurrentValue OBJECT-TYPE
    SYNTAX          Integer32 (-2147483647..2147483647)
    MAX-ACCESS      read-only
    STATUS          current
    DESCRIPTION     
            "This attribute defines the current reading of the current sensor."
    ::= { sunHwMonNumericCurrentSensorEntry 8 }

sunHwMonNumericCurrentSensorBaseUnit OBJECT-TYPE
    SYNTAX          SunBaseUnitsTC
    MAX-ACCESS      read-only
    STATUS          current
    DESCRIPTION     
            "This attribute defines the units used to express the current reading, 
             as well as the various thresholds of the current sensor."
    ::= { sunHwMonNumericCurrentSensorEntry 9 }

sunHwMonNumericCurrentSensorExponent OBJECT-TYPE
    SYNTAX          Integer32 (-2147483647..2147483647)
    MAX-ACCESS      read-only
    STATUS          current
    DESCRIPTION     
            "This attribute defines the exponent that needs to be applied to the 
             units used to express the current reading, as well as the various 
             thresholds of the current sensor."
    ::= { sunHwMonNumericCurrentSensorEntry 10 }

sunHwMonNumericCurrentSensorUpperNonRecoverableThreshold OBJECT-TYPE
    SYNTAX          Integer32 (-2147483647..2147483647)
    MAX-ACCESS      read-only
    STATUS          current
    DESCRIPTION     
            "This attribute defines the upper threshold at which a nonrecoverable
             condition occurs."
    ::= { sunHwMonNumericCurrentSensorEntry 11 }

sunHwMonNumericCurrentSensorUpperCriticalThreshold OBJECT-TYPE
    SYNTAX          Integer32 (-2147483647..2147483647)
    MAX-ACCESS      read-only
    STATUS          current
    DESCRIPTION     
            "This attribute defines the upper threshold at which a critical
             condition occurs."
    ::= { sunHwMonNumericCurrentSensorEntry 12 }

sunHwMonNumericCurrentSensorUpperNonCriticalThreshold OBJECT-TYPE
    SYNTAX          Integer32 (-2147483647..2147483647)
    MAX-ACCESS      read-only
    STATUS          current
    DESCRIPTION     
            "This attribute defines the upper threshold at which a noncritical
             condition occurs."
    ::= { sunHwMonNumericCurrentSensorEntry 13 }

sunHwMonNumericCurrentSensorLowerNonRecoverableThreshold OBJECT-TYPE
    SYNTAX          Integer32 (-2147483647..2147483647)
    MAX-ACCESS      read-only
    STATUS          current
    DESCRIPTION     
            "This attribute defines the lower threshold at which a nonrecoverable
             condition occurs."
    ::= { sunHwMonNumericCurrentSensorEntry 14 }

sunHwMonNumericCurrentSensorLowerCriticalThreshold OBJECT-TYPE
    SYNTAX          Integer32 (-2147483647..2147483647)
    MAX-ACCESS      read-only
    STATUS          current
    DESCRIPTION     
            "This attribute defines the lower threshold at which a critical
             condition occurs."
    ::= { sunHwMonNumericCurrentSensorEntry 15 }

sunHwMonNumericCurrentSensorLowerNonCriticalThreshold OBJECT-TYPE
    SYNTAX          Integer32 (-2147483647..2147483647)
    MAX-ACCESS      read-only
    STATUS          current
    DESCRIPTION     
            "This attribute defines the lower threshold at which a noncritical
             condition occurs."
    ::= { sunHwMonNumericCurrentSensorEntry 16 }

sunHwMonNumericCurrentSensorEnabledThresholds OBJECT-TYPE
    SYNTAX          SunNumericSensorEnabledThresholdsTC
    MAX-ACCESS      read-only
    STATUS          current
    DESCRIPTION     
            "This attribute defines the thresholds enabled for the current
             sensor."
    ::= { sunHwMonNumericCurrentSensorEntry 17 }

sunHwMonDiscreteCurrentSensorTable OBJECT-TYPE
    SYNTAX          SEQUENCE OF SunHwMonDiscreteCurrentSensorEntry
    MAX-ACCESS      not-accessible
    STATUS          current
    DESCRIPTION     
            "This attribute defines the discrete current sensor table."
    ::= { sunHwMonCurrentGroup 2 }

sunHwMonDiscreteCurrentSensorEntry OBJECT-TYPE
    SYNTAX          SunHwMonDiscreteCurrentSensorEntry
    MAX-ACCESS      not-accessible
    STATUS          current
    DESCRIPTION     
            "This attribute defines the discrete current sensor entry."
    INDEX           { sunHwMonDiscreteCurrentSensorIndex }
    ::= { sunHwMonDiscreteCurrentSensorTable 1 }

SunHwMonDiscreteCurrentSensorEntry ::=
    SEQUENCE {
        sunHwMonDiscreteCurrentSensorIndex  Integer32,
        sunHwMonDiscreteCurrentSensorType SunFruOrSensorTypeTC,
        sunHwMonDiscreteCurrentSensorName DisplayString,
        sunHwMonDiscreteCurrentSensorParentFruIndex           Integer32,
        sunHwMonDiscreteCurrentSensorParentFruName          DisplayString,
        sunHwMonDiscreteCurrentSensorAlarmStatus        SunAlarmStatusTC,
        sunHwMonDiscreteCurrentSensorStateDescr       DisplayString
    }

sunHwMonDiscreteCurrentSensorIndex OBJECT-TYPE
    SYNTAX          Integer32 (1..2147483647)
    MAX-ACCESS      not-accessible
    STATUS          current
    DESCRIPTION     
            "This attribute defines the index of the current sensor."
    ::= { sunHwMonDiscreteCurrentSensorEntry 1 }

sunHwMonDiscreteCurrentSensorType OBJECT-TYPE
    SYNTAX          SunFruOrSensorTypeTC
    MAX-ACCESS      read-only
    STATUS          current
    DESCRIPTION     
            "This attribute defines the type of current sensor."
    ::= { sunHwMonDiscreteCurrentSensorEntry 2 }

sunHwMonDiscreteCurrentSensorName OBJECT-TYPE
    SYNTAX          DisplayString (SIZE(0..255))
    MAX-ACCESS      read-only
    STATUS          current
    DESCRIPTION     
            "This attribute defines the name of the current sensor."
    ::= { sunHwMonDiscreteCurrentSensorEntry 3 }

sunHwMonDiscreteCurrentSensorParentFruIndex OBJECT-TYPE
    SYNTAX          Integer32 (1..2147483647)
    MAX-ACCESS      read-only
    STATUS          current
    DESCRIPTION     
            "This attribute defines the index of the field replaceable unit (FRU)
             which contains the sensor."
    ::= { sunHwMonDiscreteCurrentSensorEntry 4 }

sunHwMonDiscreteCurrentSensorParentFruName OBJECT-TYPE
    SYNTAX          DisplayString (SIZE(0..255))
    MAX-ACCESS      read-only
    STATUS          current
    DESCRIPTION     
            "This attribute defines the name of the field replaceable unit (FRU)
             which contains the sensor."
    ::= { sunHwMonDiscreteCurrentSensorEntry 5 }

sunHwMonDiscreteCurrentSensorAlarmStatus OBJECT-TYPE
    SYNTAX          SunAlarmStatusTC
    MAX-ACCESS      read-only
    STATUS          current
    DESCRIPTION     
            "This attribute defines the status of the current sensor."
    ::= { sunHwMonDiscreteCurrentSensorEntry 6 }

sunHwMonDiscreteCurrentSensorStateDescr OBJECT-TYPE
    SYNTAX          DisplayString (SIZE(0..255))
    MAX-ACCESS      read-only
    STATUS          current
    DESCRIPTION     
            "This attribute defines the state of the current sensor."
    ::= { sunHwMonDiscreteCurrentSensorEntry 7 }

sunHwMonPowerDeviceGroup OBJECT IDENTIFIER
    ::= { sunHwMonSensorGroup 4 }

sunHwMonNumericPowerDeviceSensorTable OBJECT-TYPE
    SYNTAX          SEQUENCE OF SunHwMonNumericPowerDeviceSensorEntry
    MAX-ACCESS      not-accessible
    STATUS          current
    DESCRIPTION     
            "This attribute defines the numeric power device sensor table."
    ::= { sunHwMonPowerDeviceGroup 1 }

sunHwMonNumericPowerDeviceSensorEntry OBJECT-TYPE
    SYNTAX          SunHwMonNumericPowerDeviceSensorEntry
    MAX-ACCESS      not-accessible
    STATUS          current
    DESCRIPTION     
            "This attribute defines the numeric power device sensor entry."
    INDEX           { sunHwMonNumericPowerDeviceSensorIndex }
    ::= { sunHwMonNumericPowerDeviceSensorTable 1 }

SunHwMonNumericPowerDeviceSensorEntry ::=
    SEQUENCE {
        sunHwMonNumericPowerDeviceSensorIndex     Integer32,
        sunHwMonNumericPowerDeviceSensorType    SunFruOrSensorTypeTC,
        sunHwMonNumericPowerDeviceSensorName    DisplayString,
        sunHwMonNumericPowerDeviceSensorParentFruIndex              Integer32,
        sunHwMonNumericPowerDeviceSensorParentFruName             DisplayString,
        sunHwMonNumericPowerDeviceSensorAlarmStatus           SunAlarmStatusTC,
        sunHwMonNumericPowerDeviceSensorStateDescr          DisplayString,
        sunHwMonNumericPowerDeviceSensorCurrentValue            Integer32,
        sunHwMonNumericPowerDeviceSensorBaseUnit        SunBaseUnitsTC,
        sunHwMonNumericPowerDeviceSensorExponent        Integer32,
        sunHwMonNumericPowerDeviceSensorUpperNonRecoverableThreshold                            Integer32,
        sunHwMonNumericPowerDeviceSensorUpperCriticalThreshold                      Integer32,
        sunHwMonNumericPowerDeviceSensorUpperNonCriticalThreshold                         Integer32,
        sunHwMonNumericPowerDeviceSensorLowerNonRecoverableThreshold                            Integer32,
        sunHwMonNumericPowerDeviceSensorLowerCriticalThreshold                      Integer32,
        sunHwMonNumericPowerDeviceSensorLowerNonCriticalThreshold                         Integer32,
        sunHwMonNumericPowerDeviceSensorEnabledThresholds                 SunNumericSensorEnabledThresholdsTC
    }

sunHwMonNumericPowerDeviceSensorIndex OBJECT-TYPE
    SYNTAX          Integer32 (1..2147483647)
    MAX-ACCESS      not-accessible
    STATUS          current
    DESCRIPTION     
            "This attribute defines the index of the power device sensor."
    ::= { sunHwMonNumericPowerDeviceSensorEntry 1 }

sunHwMonNumericPowerDeviceSensorType OBJECT-TYPE
    SYNTAX          SunFruOrSensorTypeTC
    MAX-ACCESS      read-only
    STATUS          current
    DESCRIPTION     
            "This attribute defines the type of power device sensor."
    ::= { sunHwMonNumericPowerDeviceSensorEntry 2 }

sunHwMonNumericPowerDeviceSensorName OBJECT-TYPE
    SYNTAX          DisplayString (SIZE(0..255))
    MAX-ACCESS      read-only
    STATUS          current
    DESCRIPTION     
            "This attribute defines the name of the power device sensor."
    ::= { sunHwMonNumericPowerDeviceSensorEntry 3 }

sunHwMonNumericPowerDeviceSensorParentFruIndex OBJECT-TYPE
    SYNTAX          Integer32 (1..2147483647)
    MAX-ACCESS      read-only
    STATUS          current
    DESCRIPTION     
            "This attribute defines the index of the field replaceable unit (FRU)
             which contains the sensor."
    ::= { sunHwMonNumericPowerDeviceSensorEntry 4 }

sunHwMonNumericPowerDeviceSensorParentFruName OBJECT-TYPE
    SYNTAX          DisplayString (SIZE(0..255))
    MAX-ACCESS      read-only
    STATUS          current
    DESCRIPTION     
            "This attribute defines the name of the field replaceable unit (FRU)
             which contains the sensor."
    ::= { sunHwMonNumericPowerDeviceSensorEntry 5 }

sunHwMonNumericPowerDeviceSensorAlarmStatus OBJECT-TYPE
    SYNTAX          SunAlarmStatusTC
    MAX-ACCESS      read-only
    STATUS          current
    DESCRIPTION     
            "This attribute defines the status of the power device sensor."
    ::= { sunHwMonNumericPowerDeviceSensorEntry 6 }

sunHwMonNumericPowerDeviceSensorStateDescr OBJECT-TYPE
    SYNTAX          DisplayString (SIZE(0..255))
    MAX-ACCESS      read-only
    STATUS          current
    DESCRIPTION     
            "This attribute defines the state of the power device sensor."
    ::= { sunHwMonNumericPowerDeviceSensorEntry 7 }

sunHwMonNumericPowerDeviceSensorCurrentValue OBJECT-TYPE
    SYNTAX          Integer32 (-2147483647..2147483647)
    MAX-ACCESS      read-only
    STATUS          current
    DESCRIPTION     
            "This attribute defines the current reading of the power device sensor."
    ::= { sunHwMonNumericPowerDeviceSensorEntry 8 }

sunHwMonNumericPowerDeviceSensorBaseUnit OBJECT-TYPE
    SYNTAX          SunBaseUnitsTC
    MAX-ACCESS      read-only
    STATUS          current
    DESCRIPTION     
            "This attribute defines the units used to express the current reading, 
             as well as the various thresholds of the power device sensor."
    ::= { sunHwMonNumericPowerDeviceSensorEntry 9 }

sunHwMonNumericPowerDeviceSensorExponent OBJECT-TYPE
    SYNTAX          Integer32 (-2147483647..2147483647)
    MAX-ACCESS      read-only
    STATUS          current
    DESCRIPTION     
            "This attribute defines the exponent that needs to be applied to the 
             units used to express the current reading, as well as the various 
             thresholds of the power device sensor."
    ::= { sunHwMonNumericPowerDeviceSensorEntry 10 }

sunHwMonNumericPowerDeviceSensorUpperNonRecoverableThreshold OBJECT-TYPE
    SYNTAX          Integer32 (-2147483647..2147483647)
    MAX-ACCESS      read-only
    STATUS          current
    DESCRIPTION     
            "This attribute defines the upper threshold at which a nonrecoverable
             condition occurs."
    ::= { sunHwMonNumericPowerDeviceSensorEntry 11 }

sunHwMonNumericPowerDeviceSensorUpperCriticalThreshold OBJECT-TYPE
    SYNTAX          Integer32 (-2147483647..2147483647)
    MAX-ACCESS      read-only
    STATUS          current
    DESCRIPTION     
            "This attribute defines the upper threshold at which a critical
             condition occurs."
    ::= { sunHwMonNumericPowerDeviceSensorEntry 12 }

sunHwMonNumericPowerDeviceSensorUpperNonCriticalThreshold OBJECT-TYPE
    SYNTAX          Integer32 (-2147483647..2147483647)
    MAX-ACCESS      read-only
    STATUS          current
    DESCRIPTION     
            "This attribute defines the upper threshold at which a noncritical
             condition occurs."
    ::= { sunHwMonNumericPowerDeviceSensorEntry 13 }

sunHwMonNumericPowerDeviceSensorLowerNonRecoverableThreshold OBJECT-TYPE
    SYNTAX          Integer32 (-2147483647..2147483647)
    MAX-ACCESS      read-only
    STATUS          current
    DESCRIPTION     
            "This attribute defines the lower threshold at which a nonrecoverable
             condition occurs."
    ::= { sunHwMonNumericPowerDeviceSensorEntry 14 }

sunHwMonNumericPowerDeviceSensorLowerCriticalThreshold OBJECT-TYPE
    SYNTAX          Integer32 (-2147483647..2147483647)
    MAX-ACCESS      read-only
    STATUS          current
    DESCRIPTION     
            "This attribute defines the lower threshold at which a critical
             condition occurs."
    ::= { sunHwMonNumericPowerDeviceSensorEntry 15 }

sunHwMonNumericPowerDeviceSensorLowerNonCriticalThreshold OBJECT-TYPE
    SYNTAX          Integer32 (-2147483647..2147483647)
    MAX-ACCESS      read-only
    STATUS          current
    DESCRIPTION     
            "This attribute defines the lower threshold at which a noncritical
             condition occurs."
    ::= { sunHwMonNumericPowerDeviceSensorEntry 16 }

sunHwMonNumericPowerDeviceSensorEnabledThresholds OBJECT-TYPE
    SYNTAX          SunNumericSensorEnabledThresholdsTC
    MAX-ACCESS      read-only
    STATUS          current
    DESCRIPTION     
            "This attribute defines the thresholds enabled for this power device
             sensor."
    ::= { sunHwMonNumericPowerDeviceSensorEntry 17 }

sunHwMonDiscretePowerDeviceSensorTable OBJECT-TYPE
    SYNTAX          SEQUENCE OF SunHwMonDiscretePowerDeviceSensorEntry
    MAX-ACCESS      not-accessible
    STATUS          current
    DESCRIPTION     
            "This attribute defines the discrete power device sensors table."
    ::= { sunHwMonPowerDeviceGroup 2 }

sunHwMonDiscretePowerDeviceSensorEntry OBJECT-TYPE
    SYNTAX          SunHwMonDiscretePowerDeviceSensorEntry
    MAX-ACCESS      not-accessible
    STATUS          current
    DESCRIPTION     
            "This attribute defines the discrete power device sensors entry."
    INDEX           { sunHwMonDiscretePowerDeviceSensorIndex }
    ::= { sunHwMonDiscretePowerDeviceSensorTable 1 }

SunHwMonDiscretePowerDeviceSensorEntry ::=
    SEQUENCE {
        sunHwMonDiscretePowerDeviceSensorIndex      Integer32,
        sunHwMonDiscretePowerDeviceSensorType     SunFruOrSensorTypeTC,
        sunHwMonDiscretePowerDeviceSensorName     DisplayString,
        sunHwMonDiscretePowerDeviceSensorParentFruIndex               Integer32,
        sunHwMonDiscretePowerDeviceSensorParentFruName              DisplayString,
        sunHwMonDiscretePowerDeviceSensorAlarmStatus            SunAlarmStatusTC,
        sunHwMonDiscretePowerDeviceSensorStateDescr           DisplayString
    }

sunHwMonDiscretePowerDeviceSensorIndex OBJECT-TYPE
    SYNTAX          Integer32 (1..2147483647)
    MAX-ACCESS      not-accessible
    STATUS          current
    DESCRIPTION     
            "This attribute defines the index of the power device sensor."
    ::= { sunHwMonDiscretePowerDeviceSensorEntry 1 }

sunHwMonDiscretePowerDeviceSensorType OBJECT-TYPE
    SYNTAX          SunFruOrSensorTypeTC
    MAX-ACCESS      read-only
    STATUS          current
    DESCRIPTION     
            "This attribute defines the type of power device sensor."
    ::= { sunHwMonDiscretePowerDeviceSensorEntry 2 }

sunHwMonDiscretePowerDeviceSensorName OBJECT-TYPE
    SYNTAX          DisplayString (SIZE(0..255))
    MAX-ACCESS      read-only
    STATUS          current
    DESCRIPTION     
            "This attribute defines the name of the power device sensor."
    ::= { sunHwMonDiscretePowerDeviceSensorEntry 3 }

sunHwMonDiscretePowerDeviceSensorParentFruIndex OBJECT-TYPE
    SYNTAX          Integer32 (1..2147483647)
    MAX-ACCESS      read-only
    STATUS          current
    DESCRIPTION     
            "This attribute defines the index of the field replaceable unit (FRU)
             which contains the sensor."
    ::= { sunHwMonDiscretePowerDeviceSensorEntry 4 }

sunHwMonDiscretePowerDeviceSensorParentFruName OBJECT-TYPE
    SYNTAX          DisplayString (SIZE(0..255))
    MAX-ACCESS      read-only
    STATUS          current
    DESCRIPTION     
            "This attribute defines the name of the field replaceable unit (FRU)
             which contains the sensor."
    ::= { sunHwMonDiscretePowerDeviceSensorEntry 5 }

sunHwMonDiscretePowerDeviceSensorAlarmStatus OBJECT-TYPE
    SYNTAX          SunAlarmStatusTC
    MAX-ACCESS      read-only
    STATUS          current
    DESCRIPTION     
            "This attribute defines the status of the power device sensor."
    ::= { sunHwMonDiscretePowerDeviceSensorEntry 6 }

sunHwMonDiscretePowerDeviceSensorStateDescr OBJECT-TYPE
    SYNTAX          DisplayString (SIZE(0..255))
    MAX-ACCESS      read-only
    STATUS          current
    DESCRIPTION     
            "This attribute defines the state of the power device sensor."
    ::= { sunHwMonDiscretePowerDeviceSensorEntry 7 }

sunHwMonCoolingDeviceGroup OBJECT IDENTIFIER
    ::= { sunHwMonSensorGroup 5 }

sunHwMonNumericCoolingDeviceSensorTable OBJECT-TYPE
    SYNTAX          SEQUENCE OF SunHwMonNumericCoolingDeviceSensorEntry
    MAX-ACCESS      not-accessible
    STATUS          current
    DESCRIPTION     
            "This attribute defines the numeric cooling device sensor table."
    ::= { sunHwMonCoolingDeviceGroup 1 }

sunHwMonNumericCoolingDeviceSensorEntry OBJECT-TYPE
    SYNTAX          SunHwMonNumericCoolingDeviceSensorEntry
    MAX-ACCESS      not-accessible
    STATUS          current
    DESCRIPTION     
            "This attribute defines the numeric cooling device sensor entry."
    INDEX           { sunHwMonNumericCoolingDeviceSensorIndex }
    ::= { sunHwMonNumericCoolingDeviceSensorTable 1 }

SunHwMonNumericCoolingDeviceSensorEntry ::=
    SEQUENCE {
        sunHwMonNumericCoolingDeviceSensorIndex       Integer32,
        sunHwMonNumericCoolingDeviceSensorType      SunFruOrSensorTypeTC,
        sunHwMonNumericCoolingDeviceSensorName      DisplayString,
        sunHwMonNumericCoolingDeviceSensorParentFruIndex                Integer32,
        sunHwMonNumericCoolingDeviceSensorParentFruName               DisplayString,
        sunHwMonNumericCoolingDeviceSensorAlarmStatus             SunAlarmStatusTC,
        sunHwMonNumericCoolingDeviceSensorStateDescr            DisplayString,
        sunHwMonNumericCoolingDeviceSensorCurrentValue              Integer32,
        sunHwMonNumericCoolingDeviceSensorBaseUnit          SunBaseUnitsTC,
        sunHwMonNumericCoolingDeviceSensorExponent          Integer32,
        sunHwMonNumericCoolingDeviceSensorUpperNonRecoverableThreshold                              Integer32,
        sunHwMonNumericCoolingDeviceSensorUpperCriticalThreshold                        Integer32,
        sunHwMonNumericCoolingDeviceSensorUpperNonCriticalThreshold                           Integer32,
        sunHwMonNumericCoolingDeviceSensorLowerNonRecoverableThreshold                              Integer32,
        sunHwMonNumericCoolingDeviceSensorLowerCriticalThreshold                        Integer32,
        sunHwMonNumericCoolingDeviceSensorLowerNonCriticalThreshold                           Integer32,
        sunHwMonNumericCoolingDeviceSensorEnabledThresholds                   SunNumericSensorEnabledThresholdsTC
    }

sunHwMonNumericCoolingDeviceSensorIndex OBJECT-TYPE
    SYNTAX          Integer32 (1..2147483647)
    MAX-ACCESS      not-accessible
    STATUS          current
    DESCRIPTION     
            "This attribute defines the index of the cooling device sensor."
    ::= { sunHwMonNumericCoolingDeviceSensorEntry 1 }

sunHwMonNumericCoolingDeviceSensorType OBJECT-TYPE
    SYNTAX          SunFruOrSensorTypeTC
    MAX-ACCESS      read-only
    STATUS          current
    DESCRIPTION     
            "This attribute defines the type of cooling device sensor."
    ::= { sunHwMonNumericCoolingDeviceSensorEntry 2 }

sunHwMonNumericCoolingDeviceSensorName OBJECT-TYPE
    SYNTAX          DisplayString (SIZE(0..255))
    MAX-ACCESS      read-only
    STATUS          current
    DESCRIPTION     
            "This attribute defines the name of the cooling device sensor."
    ::= { sunHwMonNumericCoolingDeviceSensorEntry 3 }

sunHwMonNumericCoolingDeviceSensorParentFruIndex OBJECT-TYPE
    SYNTAX          Integer32 (1..2147483647)
    MAX-ACCESS      read-only
    STATUS          current
    DESCRIPTION     
            "This attribute defines the index of the field replaceable unit (FRU)
             which contains the sensor."
    ::= { sunHwMonNumericCoolingDeviceSensorEntry 4 }

sunHwMonNumericCoolingDeviceSensorParentFruName OBJECT-TYPE
    SYNTAX          DisplayString (SIZE(0..255))
    MAX-ACCESS      read-only
    STATUS          current
    DESCRIPTION     
            "This attribute defines the name of the field replaceable unit (FRU)
             which contains the sensor."
    ::= { sunHwMonNumericCoolingDeviceSensorEntry 5 }

sunHwMonNumericCoolingDeviceSensorAlarmStatus OBJECT-TYPE
    SYNTAX          SunAlarmStatusTC
    MAX-ACCESS      read-only
    STATUS          current
    DESCRIPTION     
            "This attribute defines the status of the cooling device sensor."
    ::= { sunHwMonNumericCoolingDeviceSensorEntry 6 }

sunHwMonNumericCoolingDeviceSensorStateDescr OBJECT-TYPE
    SYNTAX          DisplayString (SIZE(0..255))
    MAX-ACCESS      read-only
    STATUS          current
    DESCRIPTION     
            "This attribute defines the state of the cooling device sensor."
    ::= { sunHwMonNumericCoolingDeviceSensorEntry 7 }

sunHwMonNumericCoolingDeviceSensorCurrentValue OBJECT-TYPE
    SYNTAX          Integer32 (-2147483647..2147483647)
    MAX-ACCESS      read-only
    STATUS          current
    DESCRIPTION     
            "This attribute defines the current reading of the cooling device sensor."
    ::= { sunHwMonNumericCoolingDeviceSensorEntry 8 }

sunHwMonNumericCoolingDeviceSensorBaseUnit OBJECT-TYPE
    SYNTAX          SunBaseUnitsTC
    MAX-ACCESS      read-only
    STATUS          current
    DESCRIPTION     
            "This attribute defines the units used to express the current reading 
             as well as the various thresholds of the cooling device sensor."
    ::= { sunHwMonNumericCoolingDeviceSensorEntry 9 }

sunHwMonNumericCoolingDeviceSensorExponent OBJECT-TYPE
    SYNTAX          Integer32 (-2147483647..2147483647)
    MAX-ACCESS      read-only
    STATUS          current
    DESCRIPTION     
            "This attribute defines the exponent that needs to be applied to the 
             units used to express the current reading, as well as the various 
             thresholds of the cooling device sensor."
    ::= { sunHwMonNumericCoolingDeviceSensorEntry 10 }

sunHwMonNumericCoolingDeviceSensorUpperNonRecoverableThreshold OBJECT-TYPE
    SYNTAX          Integer32 (-2147483647..2147483647)
    MAX-ACCESS      read-only
    STATUS          current
    DESCRIPTION     
            "This attribute defines the upper threshold at which a nonrecoverable
             condition occurs."
    ::= { sunHwMonNumericCoolingDeviceSensorEntry 11 }

sunHwMonNumericCoolingDeviceSensorUpperCriticalThreshold OBJECT-TYPE
    SYNTAX          Integer32 (-2147483647..2147483647)
    MAX-ACCESS      read-only
    STATUS          current
    DESCRIPTION     
            "This attribute defines the upper threshold at which a critical
             condition occurs."
    ::= { sunHwMonNumericCoolingDeviceSensorEntry 12 }

sunHwMonNumericCoolingDeviceSensorUpperNonCriticalThreshold OBJECT-TYPE
    SYNTAX          Integer32 (-2147483647..2147483647)
    MAX-ACCESS      read-only
    STATUS          current
    DESCRIPTION     
            "This attribute defines the upper threshold at which a noncritical
             condition occurs."
    ::= { sunHwMonNumericCoolingDeviceSensorEntry 13 }

sunHwMonNumericCoolingDeviceSensorLowerNonRecoverableThreshold OBJECT-TYPE
    SYNTAX          Integer32 (-2147483647..2147483647)
    MAX-ACCESS      read-only
    STATUS          current
    DESCRIPTION     
            "This attribute defines the lower threshold at which a nonrecoverable
             condition occurs."
    ::= { sunHwMonNumericCoolingDeviceSensorEntry 14 }

sunHwMonNumericCoolingDeviceSensorLowerCriticalThreshold OBJECT-TYPE
    SYNTAX          Integer32 (-2147483647..2147483647)
    MAX-ACCESS      read-only
    STATUS          current
    DESCRIPTION     
            "This attribute defines the lower threshold at which a critical
             condition occurs."
    ::= { sunHwMonNumericCoolingDeviceSensorEntry 15 }

sunHwMonNumericCoolingDeviceSensorLowerNonCriticalThreshold OBJECT-TYPE
    SYNTAX          Integer32 (-2147483647..2147483647)
    MAX-ACCESS      read-only
    STATUS          current
    DESCRIPTION     
            "This attribute defines the lower threshold at which a noncritical
             condition occurs."
    ::= { sunHwMonNumericCoolingDeviceSensorEntry 16 }

sunHwMonNumericCoolingDeviceSensorEnabledThresholds OBJECT-TYPE
    SYNTAX          SunNumericSensorEnabledThresholdsTC
    MAX-ACCESS      read-only
    STATUS          current
    DESCRIPTION     
            "This attribute defines the thresholds enabled for this cooling device
             sensor."
    ::= { sunHwMonNumericCoolingDeviceSensorEntry 17 }

sunHwMonDiscreteCoolingDeviceSensorTable OBJECT-TYPE
    SYNTAX          SEQUENCE OF SunHwMonDiscreteCoolingDeviceSensorEntry
    MAX-ACCESS      not-accessible
    STATUS          current
    DESCRIPTION     
            "This attribute defines the discrete cooling device sensor table."
    ::= { sunHwMonCoolingDeviceGroup 2 }

sunHwMonDiscreteCoolingDeviceSensorEntry OBJECT-TYPE
    SYNTAX          SunHwMonDiscreteCoolingDeviceSensorEntry
    MAX-ACCESS      not-accessible
    STATUS          current
    DESCRIPTION     
            "This attribute defines the discrete cooling device sensor entry."
    INDEX           { sunHwMonDiscreteCoolingDeviceSensorIndex }
    ::= { sunHwMonDiscreteCoolingDeviceSensorTable 1 }

SunHwMonDiscreteCoolingDeviceSensorEntry ::=
    SEQUENCE {
        sunHwMonDiscreteCoolingDeviceSensorIndex        Integer32,
        sunHwMonDiscreteCoolingDeviceSensorType       SunFruOrSensorTypeTC,
        sunHwMonDiscreteCoolingDeviceSensorName       DisplayString,
        sunHwMonDiscreteCoolingDeviceSensorParentFruIndex                 Integer32,
        sunHwMonDiscreteCoolingDeviceSensorParentFruName                DisplayString,
        sunHwMonDiscreteCoolingDeviceSensorAlarmStatus              SunAlarmStatusTC,
        sunHwMonDiscreteCoolingDeviceSensorStateDescr             DisplayString
    }

sunHwMonDiscreteCoolingDeviceSensorIndex OBJECT-TYPE
    SYNTAX          Integer32 (1..2147483647)
    MAX-ACCESS      not-accessible
    STATUS          current
    DESCRIPTION     
            "This attribute defines the index of the cooling device sensor."
    ::= { sunHwMonDiscreteCoolingDeviceSensorEntry 1 }

sunHwMonDiscreteCoolingDeviceSensorType OBJECT-TYPE
    SYNTAX          SunFruOrSensorTypeTC
    MAX-ACCESS      read-only
    STATUS          current
    DESCRIPTION     
            "This attribute defines the type of cooling device sensor."
    ::= { sunHwMonDiscreteCoolingDeviceSensorEntry 2 }

sunHwMonDiscreteCoolingDeviceSensorName OBJECT-TYPE
    SYNTAX          DisplayString (SIZE(0..255))
    MAX-ACCESS      read-only
    STATUS          current
    DESCRIPTION     
            "This attribute defines the name of the cooling device sensor."
    ::= { sunHwMonDiscreteCoolingDeviceSensorEntry 3 }

sunHwMonDiscreteCoolingDeviceSensorParentFruIndex OBJECT-TYPE
    SYNTAX          Integer32 (1..2147483647)
    MAX-ACCESS      read-only
    STATUS          current
    DESCRIPTION     
            "This attribute defines the index of the field replaceable unit (FRU)
             which contains the sensor."
    ::= { sunHwMonDiscreteCoolingDeviceSensorEntry 4 }

sunHwMonDiscreteCoolingDeviceSensorParentFruName OBJECT-TYPE
    SYNTAX          DisplayString (SIZE(0..255))
    MAX-ACCESS      read-only
    STATUS          current
    DESCRIPTION     
            "This attribute defines the name of the field replaceable unit (FRU)
             which contains the sensor."
    ::= { sunHwMonDiscreteCoolingDeviceSensorEntry 5 }

sunHwMonDiscreteCoolingDeviceSensorAlarmStatus OBJECT-TYPE
    SYNTAX          SunAlarmStatusTC
    MAX-ACCESS      read-only
    STATUS          current
    DESCRIPTION     
            "This attribute defines the status of the cooling device sensor."
    ::= { sunHwMonDiscreteCoolingDeviceSensorEntry 6 }

sunHwMonDiscreteCoolingDeviceSensorStateDescr OBJECT-TYPE
    SYNTAX          DisplayString (SIZE(0..255))
    MAX-ACCESS      read-only
    STATUS          current
    DESCRIPTION     
            "This attribute defines the state of the cooling device sensor."
    ::= { sunHwMonDiscreteCoolingDeviceSensorEntry 7 }

sunHwMonTemperatureGroup OBJECT IDENTIFIER
    ::= { sunHwMonSensorGroup 6 }

sunHwMonNumericTemperatureSensorTable OBJECT-TYPE
    SYNTAX          SEQUENCE OF SunHwMonNumericTemperatureSensorEntry
    MAX-ACCESS      not-accessible
    STATUS          current
    DESCRIPTION     
            "This attribute defines the numeric temperature sensor table."
    ::= { sunHwMonTemperatureGroup 1 }

sunHwMonNumericTemperatureSensorEntry OBJECT-TYPE
    SYNTAX          SunHwMonNumericTemperatureSensorEntry
    MAX-ACCESS      not-accessible
    STATUS          current
    DESCRIPTION     
            "This attribute defines the numeric temperature sensor entry."
    INDEX           { sunHwMonNumericTemperatureSensorIndex }
    ::= { sunHwMonNumericTemperatureSensorTable 1 }

SunHwMonNumericTemperatureSensorEntry ::=
    SEQUENCE {
        sunHwMonNumericTemperatureSensorIndex     Integer32,
        sunHwMonNumericTemperatureSensorType    SunFruOrSensorTypeTC,
        sunHwMonNumericTemperatureSensorName    DisplayString,
        sunHwMonNumericTemperatureSensorParentFruIndex              Integer32,
        sunHwMonNumericTemperatureSensorParentFruName             DisplayString,
        sunHwMonNumericTemperatureSensorAlarmStatus           SunAlarmStatusTC,
        sunHwMonNumericTemperatureSensorStateDescr          DisplayString,
        sunHwMonNumericTemperatureSensorCurrentValue            Integer32,
        sunHwMonNumericTemperatureSensorBaseUnit        SunBaseUnitsTC,
        sunHwMonNumericTemperatureSensorExponent        Integer32,
        sunHwMonNumericTemperatureSensorUpperNonRecoverableThreshold                            Integer32,
        sunHwMonNumericTemperatureSensorUpperCriticalThreshold                      Integer32,
        sunHwMonNumericTemperatureSensorUpperNonCriticalThreshold                         Integer32,
        sunHwMonNumericTemperatureSensorLowerNonRecoverableThreshold                            Integer32,
        sunHwMonNumericTemperatureSensorLowerCriticalThreshold                      Integer32,
        sunHwMonNumericTemperatureSensorLowerNonCriticalThreshold                         Integer32,
        sunHwMonNumericTemperatureSensorEnabledThresholds                 SunNumericSensorEnabledThresholdsTC
    }

sunHwMonNumericTemperatureSensorIndex OBJECT-TYPE
    SYNTAX          Integer32 (1..2147483647)
    MAX-ACCESS      not-accessible
    STATUS          current
    DESCRIPTION     
            "This attribute defines the index of the temperature sensor."
    ::= { sunHwMonNumericTemperatureSensorEntry 1 }

sunHwMonNumericTemperatureSensorType OBJECT-TYPE
    SYNTAX          SunFruOrSensorTypeTC
    MAX-ACCESS      read-only
    STATUS          current
    DESCRIPTION     
            "This attribute defines the type of temperature sensor."
    ::= { sunHwMonNumericTemperatureSensorEntry 2 }

sunHwMonNumericTemperatureSensorName OBJECT-TYPE
    SYNTAX          DisplayString (SIZE(0..255))
    MAX-ACCESS      read-only
    STATUS          current
    DESCRIPTION     
            "This attribute defines the name of the temperature sensor."
    ::= { sunHwMonNumericTemperatureSensorEntry 3 }

sunHwMonNumericTemperatureSensorParentFruIndex OBJECT-TYPE
    SYNTAX          Integer32 (1..2147483647)
    MAX-ACCESS      read-only
    STATUS          current
    DESCRIPTION     
            "This attribute defines the index of the field replaceable unit (FRU)
             which contains the sensor."
    ::= { sunHwMonNumericTemperatureSensorEntry 4 }

sunHwMonNumericTemperatureSensorParentFruName OBJECT-TYPE
    SYNTAX          DisplayString (SIZE(0..255))
    MAX-ACCESS      read-only
    STATUS          current
    DESCRIPTION     
            "This attribute defines the name of the field replaceable unit (FRU)
             which contains the sensor."
    ::= { sunHwMonNumericTemperatureSensorEntry 5 }

sunHwMonNumericTemperatureSensorAlarmStatus OBJECT-TYPE
    SYNTAX          SunAlarmStatusTC
    MAX-ACCESS      read-only
    STATUS          current
    DESCRIPTION     
            "This attribute defines the status of the temperature sensor."
    ::= { sunHwMonNumericTemperatureSensorEntry 6 }

sunHwMonNumericTemperatureSensorStateDescr OBJECT-TYPE
    SYNTAX          DisplayString (SIZE(0..255))
    MAX-ACCESS      read-only
    STATUS          current
    DESCRIPTION     
            "This attribute defines the state of the temperature sensor."
    ::= { sunHwMonNumericTemperatureSensorEntry 7 }

sunHwMonNumericTemperatureSensorCurrentValue OBJECT-TYPE
    SYNTAX          Integer32 (-2147483647..2147483647)
    MAX-ACCESS      read-only
    STATUS          current
    DESCRIPTION     
            "This attribute defines the current reading of the temperature sensor."
    ::= { sunHwMonNumericTemperatureSensorEntry 8 }

sunHwMonNumericTemperatureSensorBaseUnit OBJECT-TYPE
    SYNTAX          SunBaseUnitsTC
    MAX-ACCESS      read-only
    STATUS          current
    DESCRIPTION     
            "This attribute defines the units used to express the current reading, 
             as well as the various thresholds of the temperature sensor."
    ::= { sunHwMonNumericTemperatureSensorEntry 9 }

sunHwMonNumericTemperatureSensorExponent OBJECT-TYPE
    SYNTAX          Integer32 (-2147483647..2147483647)
    MAX-ACCESS      read-only
    STATUS          current
    DESCRIPTION     
            "This attribute defines the exponent that needs to be applied to the 
             units used to express the current reading, as well as the various 
             thresholds of the temperature sensor."
    ::= { sunHwMonNumericTemperatureSensorEntry 10 }

sunHwMonNumericTemperatureSensorUpperNonRecoverableThreshold OBJECT-TYPE
    SYNTAX          Integer32 (-2147483647..2147483647)
    MAX-ACCESS      read-only
    STATUS          current
    DESCRIPTION     
            "This attribute defines the upper threshold at which a nonrecoverable
             condition occurs."
    ::= { sunHwMonNumericTemperatureSensorEntry 11 }

sunHwMonNumericTemperatureSensorUpperCriticalThreshold OBJECT-TYPE
    SYNTAX          Integer32 (-2147483647..2147483647)
    MAX-ACCESS      read-only
    STATUS          current
    DESCRIPTION     
            "This attribute defines the upper threshold at which a critical
             condition occurs."
    ::= { sunHwMonNumericTemperatureSensorEntry 12 }

sunHwMonNumericTemperatureSensorUpperNonCriticalThreshold OBJECT-TYPE
    SYNTAX          Integer32 (-2147483647..2147483647)
    MAX-ACCESS      read-only
    STATUS          current
    DESCRIPTION     
            "This attribute defines the upper threshold at which a noncritical
             condition occurs."
    ::= { sunHwMonNumericTemperatureSensorEntry 13 }

sunHwMonNumericTemperatureSensorLowerNonRecoverableThreshold OBJECT-TYPE
    SYNTAX          Integer32 (-2147483647..2147483647)
    MAX-ACCESS      read-only
    STATUS          current
    DESCRIPTION     
            "This attribute defines the lower threshold at which a nonrecoverable
             condition occurs."
    ::= { sunHwMonNumericTemperatureSensorEntry 14 }

sunHwMonNumericTemperatureSensorLowerCriticalThreshold OBJECT-TYPE
    SYNTAX          Integer32 (-2147483647..2147483647)
    MAX-ACCESS      read-only
    STATUS          current
    DESCRIPTION     
            "This attribute defines the lower threshold at which a critical
             condition occurs."
    ::= { sunHwMonNumericTemperatureSensorEntry 15 }

sunHwMonNumericTemperatureSensorLowerNonCriticalThreshold OBJECT-TYPE
    SYNTAX          Integer32 (-2147483647..2147483647)
    MAX-ACCESS      read-only
    STATUS          current
    DESCRIPTION     
            "This attribute defines the lower threshold at which a noncritical
             condition occurs."
    ::= { sunHwMonNumericTemperatureSensorEntry 16 }

sunHwMonNumericTemperatureSensorEnabledThresholds OBJECT-TYPE
    SYNTAX          SunNumericSensorEnabledThresholdsTC
    MAX-ACCESS      read-only
    STATUS          current
    DESCRIPTION     
            "This attribute defines the thresholds enabled for this temperature
             sensor."
    ::= { sunHwMonNumericTemperatureSensorEntry 17 }

sunHwMonDiscreteTemperatureSensorTable OBJECT-TYPE
    SYNTAX          SEQUENCE OF SunHwMonDiscreteTemperatureSensorEntry
    MAX-ACCESS      not-accessible
    STATUS          current
    DESCRIPTION     
            "This attribute defines the discrete temperature sensors table."
    ::= { sunHwMonTemperatureGroup 2 }

sunHwMonDiscreteTemperatureSensorEntry OBJECT-TYPE
    SYNTAX          SunHwMonDiscreteTemperatureSensorEntry
    MAX-ACCESS      not-accessible
    STATUS          current
    DESCRIPTION     
            "This attribute defines the discrete temperature sensors entry."
    INDEX           { sunHwMonDiscreteTemperatureSensorIndex }
    ::= { sunHwMonDiscreteTemperatureSensorTable 1 }

SunHwMonDiscreteTemperatureSensorEntry ::=
    SEQUENCE {
        sunHwMonDiscreteTemperatureSensorIndex      Integer32,
        sunHwMonDiscreteTemperatureSensorType     SunFruOrSensorTypeTC,
        sunHwMonDiscreteTemperatureSensorName     DisplayString,
        sunHwMonDiscreteTemperatureSensorParentFruIndex               Integer32,
        sunHwMonDiscreteTemperatureSensorParentFruName              DisplayString,
        sunHwMonDiscreteTemperatureSensorAlarmStatus            SunAlarmStatusTC,
        sunHwMonDiscreteTemperatureSensorStateDescr           DisplayString
    }

sunHwMonDiscreteTemperatureSensorIndex OBJECT-TYPE
    SYNTAX          Integer32 (1..2147483647)
    MAX-ACCESS      not-accessible
    STATUS          current
    DESCRIPTION     
            "This attribute defines the index of the temperature sensor."
    ::= { sunHwMonDiscreteTemperatureSensorEntry 1 }

sunHwMonDiscreteTemperatureSensorType OBJECT-TYPE
    SYNTAX          SunFruOrSensorTypeTC
    MAX-ACCESS      read-only
    STATUS          current
    DESCRIPTION     
            "This attribute defines the type of temperature sensor."
    ::= { sunHwMonDiscreteTemperatureSensorEntry 2 }

sunHwMonDiscreteTemperatureSensorName OBJECT-TYPE
    SYNTAX          DisplayString (SIZE(0..255))
    MAX-ACCESS      read-only
    STATUS          current
    DESCRIPTION     
            "This attribute defines the name of the temperature sensor."
    ::= { sunHwMonDiscreteTemperatureSensorEntry 3 }

sunHwMonDiscreteTemperatureSensorParentFruIndex OBJECT-TYPE
    SYNTAX          Integer32 (1..2147483647)
    MAX-ACCESS      read-only
    STATUS          current
    DESCRIPTION     
            "This attribute defines the index of the field replaceable unit (FRU)
             which contains the sensor."
    ::= { sunHwMonDiscreteTemperatureSensorEntry 4 }

sunHwMonDiscreteTemperatureSensorParentFruName OBJECT-TYPE
    SYNTAX          DisplayString (SIZE(0..255))
    MAX-ACCESS      read-only
    STATUS          current
    DESCRIPTION     
            "This attribute defines the name of the field replaceable unit (FRU)
             which contains the sensor."
    ::= { sunHwMonDiscreteTemperatureSensorEntry 5 }

sunHwMonDiscreteTemperatureSensorAlarmStatus OBJECT-TYPE
    SYNTAX          SunAlarmStatusTC
    MAX-ACCESS      read-only
    STATUS          current
    DESCRIPTION     
            "This attribute defines the status of the temperature sensor."
    ::= { sunHwMonDiscreteTemperatureSensorEntry 6 }

sunHwMonDiscreteTemperatureSensorStateDescr OBJECT-TYPE
    SYNTAX          DisplayString (SIZE(0..255))
    MAX-ACCESS      read-only
    STATUS          current
    DESCRIPTION     
            "This attribute defines the state of the temperature sensor."
    ::= { sunHwMonDiscreteTemperatureSensorEntry 7 }

sunHwMonProcessorGroup OBJECT IDENTIFIER
    ::= { sunHwMonSensorGroup 7 }

sunHwMonNumericProcessorSensorTable OBJECT-TYPE
    SYNTAX          SEQUENCE OF SunHwMonNumericProcessorSensorEntry
    MAX-ACCESS      not-accessible
    STATUS          current
    DESCRIPTION     
            "This attribute defines the numeric processor sensor table."
    ::= { sunHwMonProcessorGroup 1 }

sunHwMonNumericProcessorSensorEntry OBJECT-TYPE
    SYNTAX          SunHwMonNumericProcessorSensorEntry
    MAX-ACCESS      not-accessible
    STATUS          current
    DESCRIPTION     
            "This attribute defines the numeric processor sensor entry."
    INDEX           { sunHwMonNumericProcessorSensorIndex }
    ::= { sunHwMonNumericProcessorSensorTable 1 }

SunHwMonNumericProcessorSensorEntry ::=
    SEQUENCE {
        sunHwMonNumericProcessorSensorIndex   Integer32,
        sunHwMonNumericProcessorSensorType  SunFruOrSensorTypeTC,
        sunHwMonNumericProcessorSensorName  DisplayString,
        sunHwMonNumericProcessorSensorParentFruIndex            Integer32,
        sunHwMonNumericProcessorSensorParentFruName           DisplayString,
        sunHwMonNumericProcessorSensorAlarmStatus         SunAlarmStatusTC,
        sunHwMonNumericProcessorSensorStateDescr        DisplayString,
        sunHwMonNumericProcessorSensorCurrentValue          Integer32,
        sunHwMonNumericProcessorSensorBaseUnit      SunBaseUnitsTC,
        sunHwMonNumericProcessorSensorExponent      Integer32,
        sunHwMonNumericProcessorSensorUpperNonRecoverableThreshold                          Integer32,
        sunHwMonNumericProcessorSensorUpperCriticalThreshold                    Integer32,
        sunHwMonNumericProcessorSensorUpperNonCriticalThreshold                       Integer32,
        sunHwMonNumericProcessorSensorLowerNonRecoverableThreshold                          Integer32,
        sunHwMonNumericProcessorSensorLowerCriticalThreshold                    Integer32,
        sunHwMonNumericProcessorSensorLowerNonCriticalThreshold                       Integer32,
        sunHwMonNumericProcessorSensorEnabledThresholds               SunNumericSensorEnabledThresholdsTC
    }

sunHwMonNumericProcessorSensorIndex OBJECT-TYPE
    SYNTAX          Integer32 (1..2147483647)
    MAX-ACCESS      not-accessible
    STATUS          current
    DESCRIPTION     
            "This attribute defines the index of the processor sensor."
    ::= { sunHwMonNumericProcessorSensorEntry 1 }

sunHwMonNumericProcessorSensorType OBJECT-TYPE
    SYNTAX          SunFruOrSensorTypeTC
    MAX-ACCESS      read-only
    STATUS          current
    DESCRIPTION     
            "This attribute defines the type of processor sensor."
    ::= { sunHwMonNumericProcessorSensorEntry 2 }

sunHwMonNumericProcessorSensorName OBJECT-TYPE
    SYNTAX          DisplayString (SIZE(0..255))
    MAX-ACCESS      read-only
    STATUS          current
    DESCRIPTION     
            "This attribute defines the name of the processor sensor."
    ::= { sunHwMonNumericProcessorSensorEntry 3 }

sunHwMonNumericProcessorSensorParentFruIndex OBJECT-TYPE
    SYNTAX          Integer32 (1..2147483647)
    MAX-ACCESS      read-only
    STATUS          current
    DESCRIPTION     
            "This attribute defines the index of the field replaceable unit (FRU)
             which contains the sensor."
    ::= { sunHwMonNumericProcessorSensorEntry 4 }

sunHwMonNumericProcessorSensorParentFruName OBJECT-TYPE
    SYNTAX          DisplayString (SIZE(0..255))
    MAX-ACCESS      read-only
    STATUS          current
    DESCRIPTION     
            "This attribute defines the name of the field replaceable unit (FRU)
             which contains the sensor."
    ::= { sunHwMonNumericProcessorSensorEntry 5 }

sunHwMonNumericProcessorSensorAlarmStatus OBJECT-TYPE
    SYNTAX          SunAlarmStatusTC
    MAX-ACCESS      read-only
    STATUS          current
    DESCRIPTION     
            "This attribute defines the status of the processor sensor."
    ::= { sunHwMonNumericProcessorSensorEntry 6 }

sunHwMonNumericProcessorSensorStateDescr OBJECT-TYPE
    SYNTAX          DisplayString (SIZE(0..255))
    MAX-ACCESS      read-only
    STATUS          current
    DESCRIPTION     
            "This attribute defines the state of the processor sensor."
    ::= { sunHwMonNumericProcessorSensorEntry 7 }

sunHwMonNumericProcessorSensorCurrentValue OBJECT-TYPE
    SYNTAX          Integer32 (-2147483647..2147483647)
    MAX-ACCESS      read-only
    STATUS          current
    DESCRIPTION     
            "This attribute defines the current reading of the processor sensor."
    ::= { sunHwMonNumericProcessorSensorEntry 8 }

sunHwMonNumericProcessorSensorBaseUnit OBJECT-TYPE
    SYNTAX          SunBaseUnitsTC
    MAX-ACCESS      read-only
    STATUS          current
    DESCRIPTION     
            "This attribute defines the units used to express the current reading 
             as well as the various thresholds of the processor sensor."
    ::= { sunHwMonNumericProcessorSensorEntry 9 }

sunHwMonNumericProcessorSensorExponent OBJECT-TYPE
    SYNTAX          Integer32 (-2147483647..2147483647)
    MAX-ACCESS      read-only
    STATUS          current
    DESCRIPTION     
            "This attribute defines the exponent that needs to be applied to the 
             units used to express the current reading, as well as the various 
             thresholds of the processor sensor."
    ::= { sunHwMonNumericProcessorSensorEntry 10 }

sunHwMonNumericProcessorSensorUpperNonRecoverableThreshold OBJECT-TYPE
    SYNTAX          Integer32 (-2147483647..2147483647)
    MAX-ACCESS      read-only
    STATUS          current
    DESCRIPTION     
            "This attribute defines the upper threshold at which a nonrecoverable
             condition occurs."
    ::= { sunHwMonNumericProcessorSensorEntry 11 }

sunHwMonNumericProcessorSensorUpperCriticalThreshold OBJECT-TYPE
    SYNTAX          Integer32 (-2147483647..2147483647)
    MAX-ACCESS      read-only
    STATUS          current
    DESCRIPTION     
            "This attribute defines the upper threshold at which a critical
             condition occurs."
    ::= { sunHwMonNumericProcessorSensorEntry 12 }

sunHwMonNumericProcessorSensorUpperNonCriticalThreshold OBJECT-TYPE
    SYNTAX          Integer32 (-2147483647..2147483647)
    MAX-ACCESS      read-only
    STATUS          current
    DESCRIPTION     
            "This attribute defines the upper threshold at which a noncritical
             condition occurs."
    ::= { sunHwMonNumericProcessorSensorEntry 13 }

sunHwMonNumericProcessorSensorLowerNonRecoverableThreshold OBJECT-TYPE
    SYNTAX          Integer32 (-2147483647..2147483647)
    MAX-ACCESS      read-only
    STATUS          current
    DESCRIPTION     
            "This attribute defines the lower threshold at which a nonrecoverable
             condition occurs."
    ::= { sunHwMonNumericProcessorSensorEntry 14 }

sunHwMonNumericProcessorSensorLowerCriticalThreshold OBJECT-TYPE
    SYNTAX          Integer32 (-2147483647..2147483647)
    MAX-ACCESS      read-only
    STATUS          current
    DESCRIPTION     
            "This attribute defines the lower threshold at which a critical
             condition occurs."
    ::= { sunHwMonNumericProcessorSensorEntry 15 }

sunHwMonNumericProcessorSensorLowerNonCriticalThreshold OBJECT-TYPE
    SYNTAX          Integer32 (-2147483647..2147483647)
    MAX-ACCESS      read-only
    STATUS          current
    DESCRIPTION     
            "This attribute defines the lower threshold at which a noncritical
             condition occurs."
    ::= { sunHwMonNumericProcessorSensorEntry 16 }

sunHwMonNumericProcessorSensorEnabledThresholds OBJECT-TYPE
    SYNTAX          SunNumericSensorEnabledThresholdsTC
    MAX-ACCESS      read-only
    STATUS          current
    DESCRIPTION     
            "This attribute defines the thresholds enabled for this processor
             sensor."
    ::= { sunHwMonNumericProcessorSensorEntry 17 }

sunHwMonDiscreteProcessorSensorTable OBJECT-TYPE
    SYNTAX          SEQUENCE OF SunHwMonDiscreteProcessorSensorEntry
    MAX-ACCESS      not-accessible
    STATUS          current
    DESCRIPTION     
            "This attribute defines the discrete processor sensors table."
    ::= { sunHwMonProcessorGroup 2 }

sunHwMonDiscreteProcessorSensorEntry OBJECT-TYPE
    SYNTAX          SunHwMonDiscreteProcessorSensorEntry
    MAX-ACCESS      not-accessible
    STATUS          current
    DESCRIPTION     
            "This attribute defines the discrete processor sensors entry."
    INDEX           { sunHwMonDiscreteProcessorSensorIndex }
    ::= { sunHwMonDiscreteProcessorSensorTable 1 }

SunHwMonDiscreteProcessorSensorEntry ::=
    SEQUENCE {
        sunHwMonDiscreteProcessorSensorIndex    Integer32,
        sunHwMonDiscreteProcessorSensorType   SunFruOrSensorTypeTC,
        sunHwMonDiscreteProcessorSensorName   DisplayString,
        sunHwMonDiscreteProcessorSensorParentFruIndex             Integer32,
        sunHwMonDiscreteProcessorSensorParentFruName            DisplayString,
        sunHwMonDiscreteProcessorSensorAlarmStatus          SunAlarmStatusTC,
        sunHwMonDiscreteProcessorSensorStateDescr         DisplayString
    }

sunHwMonDiscreteProcessorSensorIndex OBJECT-TYPE
    SYNTAX          Integer32 (1..2147483647)
    MAX-ACCESS      not-accessible
    STATUS          current
    DESCRIPTION     
            "This attribute defines the index of the processor sensor."
    ::= { sunHwMonDiscreteProcessorSensorEntry 1 }

sunHwMonDiscreteProcessorSensorType OBJECT-TYPE
    SYNTAX          SunFruOrSensorTypeTC
    MAX-ACCESS      read-only
    STATUS          current
    DESCRIPTION     
            "This attribute defines the type of processor sensor."
    ::= { sunHwMonDiscreteProcessorSensorEntry 2 }

sunHwMonDiscreteProcessorSensorName OBJECT-TYPE
    SYNTAX          DisplayString (SIZE(0..255))
    MAX-ACCESS      read-only
    STATUS          current
    DESCRIPTION     
            "This attribute defines the name of the processor sensor."
    ::= { sunHwMonDiscreteProcessorSensorEntry 3 }

sunHwMonDiscreteProcessorSensorParentFruIndex OBJECT-TYPE
    SYNTAX          Integer32 (1..2147483647)
    MAX-ACCESS      read-only
    STATUS          current
    DESCRIPTION     
            "This attribute defines the index of the field replaceable unit (FRU)
             which contains the sensor."
    ::= { sunHwMonDiscreteProcessorSensorEntry 4 }

sunHwMonDiscreteProcessorSensorParentFruName OBJECT-TYPE
    SYNTAX          DisplayString (SIZE(0..255))
    MAX-ACCESS      read-only
    STATUS          current
    DESCRIPTION     
            "This attribute defines the name of the field replaceable unit (FRU)
             which contains the sensor."
    ::= { sunHwMonDiscreteProcessorSensorEntry 5 }

sunHwMonDiscreteProcessorSensorAlarmStatus OBJECT-TYPE
    SYNTAX          SunAlarmStatusTC
    MAX-ACCESS      read-only
    STATUS          current
    DESCRIPTION     
            "This attribute defines the status of the processor sensor."
    ::= { sunHwMonDiscreteProcessorSensorEntry 6 }

sunHwMonDiscreteProcessorSensorStateDescr OBJECT-TYPE
    SYNTAX          DisplayString (SIZE(0..255))
    MAX-ACCESS      read-only
    STATUS          current
    DESCRIPTION     
            "This attribute defines the state of the processor sensor."
    ::= { sunHwMonDiscreteProcessorSensorEntry 7 }

sunHwMonMemoryGroup OBJECT IDENTIFIER
    ::= { sunHwMonSensorGroup 8 }

sunHwMonNumericMemorySensorTable OBJECT-TYPE
    SYNTAX          SEQUENCE OF SunHwMonNumericMemorySensorEntry
    MAX-ACCESS      not-accessible
    STATUS          current
    DESCRIPTION     
            "This attribute defines the numeric memory sensor table."
    ::= { sunHwMonMemoryGroup 1 }

sunHwMonNumericMemorySensorEntry OBJECT-TYPE
    SYNTAX          SunHwMonNumericMemorySensorEntry
    MAX-ACCESS      not-accessible
    STATUS          current
    DESCRIPTION     
            "This attribute defines the numeric memory sensor entry."
    INDEX           { sunHwMonNumericMemorySensorIndex }
    ::= { sunHwMonNumericMemorySensorTable 1 }

SunHwMonNumericMemorySensorEntry ::=
    SEQUENCE {
        sunHwMonNumericMemorySensorIndex Integer32,
        sunHwMonNumericMemorySensorType SunFruOrSensorTypeTC,
        sunHwMonNumericMemorySensorName DisplayString,
        sunHwMonNumericMemorySensorParentFruIndex         Integer32,
        sunHwMonNumericMemorySensorParentFruName        DisplayString,
        sunHwMonNumericMemorySensorAlarmStatus      SunAlarmStatusTC,
        sunHwMonNumericMemorySensorStateDescr     DisplayString,
        sunHwMonNumericMemorySensorCurrentValue       Integer32,
        sunHwMonNumericMemorySensorBaseUnit   SunBaseUnitsTC,
        sunHwMonNumericMemorySensorExponent   Integer32,
        sunHwMonNumericMemorySensorUpperNonRecoverableThreshold                       Integer32,
        sunHwMonNumericMemorySensorUpperCriticalThreshold                 Integer32,
        sunHwMonNumericMemorySensorUpperNonCriticalThreshold                    Integer32,
        sunHwMonNumericMemorySensorLowerNonRecoverableThreshold                       Integer32,
        sunHwMonNumericMemorySensorLowerCriticalThreshold                 Integer32,
        sunHwMonNumericMemorySensorLowerNonCriticalThreshold                    Integer32,
        sunHwMonNumericMemorySensorEnabledThresholds            SunNumericSensorEnabledThresholdsTC
    }

sunHwMonNumericMemorySensorIndex OBJECT-TYPE
    SYNTAX          Integer32 (1..2147483647)
    MAX-ACCESS      not-accessible
    STATUS          current
    DESCRIPTION     
            "This attribute defines the index of the memory sensor."
    ::= { sunHwMonNumericMemorySensorEntry 1 }

sunHwMonNumericMemorySensorType OBJECT-TYPE
    SYNTAX          SunFruOrSensorTypeTC
    MAX-ACCESS      read-only
    STATUS          current
    DESCRIPTION     
            "This attribute defines the type of memory sensor."
    ::= { sunHwMonNumericMemorySensorEntry 2 }

sunHwMonNumericMemorySensorName OBJECT-TYPE
    SYNTAX          DisplayString (SIZE(0..255))
    MAX-ACCESS      read-only
    STATUS          current
    DESCRIPTION     
            "This attribute defines the name of the memory sensor."
    ::= { sunHwMonNumericMemorySensorEntry 3 }

sunHwMonNumericMemorySensorParentFruIndex OBJECT-TYPE
    SYNTAX          Integer32 (1..2147483647)
    MAX-ACCESS      read-only
    STATUS          current
    DESCRIPTION     
            "This attribute defines the index of the field replaceable unit (FRU)
             which contains the sensor."
    ::= { sunHwMonNumericMemorySensorEntry 4 }

sunHwMonNumericMemorySensorParentFruName OBJECT-TYPE
    SYNTAX          DisplayString (SIZE(0..255))
    MAX-ACCESS      read-only
    STATUS          current
    DESCRIPTION     
            "This attribute defines the name of the field replaceable unit (FRU)
             which contains the sensor."
    ::= { sunHwMonNumericMemorySensorEntry 5 }

sunHwMonNumericMemorySensorAlarmStatus OBJECT-TYPE
    SYNTAX          SunAlarmStatusTC
    MAX-ACCESS      read-only
    STATUS          current
    DESCRIPTION     
            "This attribute defines the status of the memory sensor."
    ::= { sunHwMonNumericMemorySensorEntry 6 }

sunHwMonNumericMemorySensorStateDescr OBJECT-TYPE
    SYNTAX          DisplayString (SIZE(0..255))
    MAX-ACCESS      read-only
    STATUS          current
    DESCRIPTION     
            "This attribute defines the state of the memory sensor."
    ::= { sunHwMonNumericMemorySensorEntry 7 }

sunHwMonNumericMemorySensorCurrentValue OBJECT-TYPE
    SYNTAX          Integer32 (-2147483647..2147483647)
    MAX-ACCESS      read-only
    STATUS          current
    DESCRIPTION     
            "This attribute defines the current reading of the memory sensor."
    ::= { sunHwMonNumericMemorySensorEntry 8 }

sunHwMonNumericMemorySensorBaseUnit OBJECT-TYPE
    SYNTAX          SunBaseUnitsTC
    MAX-ACCESS      read-only
    STATUS          current
    DESCRIPTION     
            "This attribute defines the units used to express the current reading, 
             as well as the various thresholds of the memory sensor."
    ::= { sunHwMonNumericMemorySensorEntry 9 }

sunHwMonNumericMemorySensorExponent OBJECT-TYPE
    SYNTAX          Integer32 (-2147483647..2147483647)
    MAX-ACCESS      read-only
    STATUS          current
    DESCRIPTION     
            "This attribute defines the exponent that needs to be applied to the 
             units used to express the current reading, as well as the various 
             thresholds of the memory sensor."
    ::= { sunHwMonNumericMemorySensorEntry 10 }

sunHwMonNumericMemorySensorUpperNonRecoverableThreshold OBJECT-TYPE
    SYNTAX          Integer32 (-2147483647..2147483647)
    MAX-ACCESS      read-only
    STATUS          current
    DESCRIPTION     
            "This attribute defines the upper threshold at which a nonrecoverable
             condition occurs."
    ::= { sunHwMonNumericMemorySensorEntry 11 }

sunHwMonNumericMemorySensorUpperCriticalThreshold OBJECT-TYPE
    SYNTAX          Integer32 (-2147483647..2147483647)
    MAX-ACCESS      read-only
    STATUS          current
    DESCRIPTION     
            "This attribute defines the upper threshold at which a critical
             condition occurs."
    ::= { sunHwMonNumericMemorySensorEntry 12 }

sunHwMonNumericMemorySensorUpperNonCriticalThreshold OBJECT-TYPE
    SYNTAX          Integer32 (-2147483647..2147483647)
    MAX-ACCESS      read-only
    STATUS          current
    DESCRIPTION     
            "This attribute defines the upper threshold at which a noncritical
             condition occurs."
    ::= { sunHwMonNumericMemorySensorEntry 13 }

sunHwMonNumericMemorySensorLowerNonRecoverableThreshold OBJECT-TYPE
    SYNTAX          Integer32 (-2147483647..2147483647)
    MAX-ACCESS      read-only
    STATUS          current
    DESCRIPTION     
            "This attribute defines the lower threshold at which a nonrecoverable
             condition occurs."
    ::= { sunHwMonNumericMemorySensorEntry 14 }

sunHwMonNumericMemorySensorLowerCriticalThreshold OBJECT-TYPE
    SYNTAX          Integer32 (-2147483647..2147483647)
    MAX-ACCESS      read-only
    STATUS          current
    DESCRIPTION     
            "This attribute defines the lower threshold at which a critical
             condition occurs."
    ::= { sunHwMonNumericMemorySensorEntry 15 }

sunHwMonNumericMemorySensorLowerNonCriticalThreshold OBJECT-TYPE
    SYNTAX          Integer32 (-2147483647..2147483647)
    MAX-ACCESS      read-only
    STATUS          current
    DESCRIPTION     
            "This attribute defines the lower threshold at which a noncritical
             condition occurs."
    ::= { sunHwMonNumericMemorySensorEntry 16 }

sunHwMonNumericMemorySensorEnabledThresholds OBJECT-TYPE
    SYNTAX          SunNumericSensorEnabledThresholdsTC
    MAX-ACCESS      read-only
    STATUS          current
    DESCRIPTION     
            "This attribute defines the thresholds enabled for this memory
             sensor."
    ::= { sunHwMonNumericMemorySensorEntry 17 }

sunHwMonDiscreteMemorySensorTable OBJECT-TYPE
    SYNTAX          SEQUENCE OF SunHwMonDiscreteMemorySensorEntry
    MAX-ACCESS      not-accessible
    STATUS          current
    DESCRIPTION     
            "This attribute defines discrete memory sensors table."
    ::= { sunHwMonMemoryGroup 2 }

sunHwMonDiscreteMemorySensorEntry OBJECT-TYPE
    SYNTAX          SunHwMonDiscreteMemorySensorEntry
    MAX-ACCESS      not-accessible
    STATUS          current
    DESCRIPTION     
            "This attribute defines discrete memory sensors entry."
    INDEX           { sunHwMonDiscreteMemorySensorIndex }
    ::= { sunHwMonDiscreteMemorySensorTable 1 }

SunHwMonDiscreteMemorySensorEntry ::=
    SEQUENCE {
        sunHwMonDiscreteMemorySensorIndex Integer32,
        sunHwMonDiscreteMemorySensorType SunFruOrSensorTypeTC,
        sunHwMonDiscreteMemorySensorName DisplayString,
        sunHwMonDiscreteMemorySensorParentFruIndex          Integer32,
        sunHwMonDiscreteMemorySensorParentFruName         DisplayString,
        sunHwMonDiscreteMemorySensorAlarmStatus       SunAlarmStatusTC,
        sunHwMonDiscreteMemorySensorStateDescr      DisplayString
    }

sunHwMonDiscreteMemorySensorIndex OBJECT-TYPE
    SYNTAX          Integer32 (1..2147483647)
    MAX-ACCESS      not-accessible
    STATUS          current
    DESCRIPTION     
            "This attribute defines the index of the memory sensor."
    ::= { sunHwMonDiscreteMemorySensorEntry 1 }

sunHwMonDiscreteMemorySensorType OBJECT-TYPE
    SYNTAX          SunFruOrSensorTypeTC
    MAX-ACCESS      read-only
    STATUS          current
    DESCRIPTION     
            "This attribute defines the type of memory sensor."
    ::= { sunHwMonDiscreteMemorySensorEntry 2 }

sunHwMonDiscreteMemorySensorName OBJECT-TYPE
    SYNTAX          DisplayString (SIZE(0..255))
    MAX-ACCESS      read-only
    STATUS          current
    DESCRIPTION     
            "This attribute defines the name of the memory sensor."
    ::= { sunHwMonDiscreteMemorySensorEntry 3 }

sunHwMonDiscreteMemorySensorParentFruIndex OBJECT-TYPE
    SYNTAX          Integer32 (1..2147483647)
    MAX-ACCESS      read-only
    STATUS          current
    DESCRIPTION     
            "This attribute defines the index of the field replaceable unit (FRU)
             which contains the sensor."
    ::= { sunHwMonDiscreteMemorySensorEntry 4 }

sunHwMonDiscreteMemorySensorParentFruName OBJECT-TYPE
    SYNTAX          DisplayString (SIZE(0..255))
    MAX-ACCESS      read-only
    STATUS          current
    DESCRIPTION     
            "This attribute defines the name of the field replaceable unit (FRU)
             which contains the sensor."
    ::= { sunHwMonDiscreteMemorySensorEntry 5 }

sunHwMonDiscreteMemorySensorAlarmStatus OBJECT-TYPE
    SYNTAX          SunAlarmStatusTC
    MAX-ACCESS      read-only
    STATUS          current
    DESCRIPTION     
            "This attribute defines the status of the memory sensor."
    ::= { sunHwMonDiscreteMemorySensorEntry 6 }

sunHwMonDiscreteMemorySensorStateDescr OBJECT-TYPE
    SYNTAX          DisplayString (SIZE(0..255))
    MAX-ACCESS      read-only
    STATUS          current
    DESCRIPTION     
            "This attribute defines the state of the memory sensor."
    ::= { sunHwMonDiscreteMemorySensorEntry 7 }

sunHwMonHardDriveGroup OBJECT IDENTIFIER
    ::= { sunHwMonSensorGroup 9 }

sunHwMonNumericHardDriveSensorTable OBJECT-TYPE
    SYNTAX          SEQUENCE OF SunHwMonNumericHardDriveSensorEntry
    MAX-ACCESS      not-accessible
    STATUS          current
    DESCRIPTION     
            "This attribute defines the numeric hard drive sensor table."
    ::= { sunHwMonHardDriveGroup 1 }

sunHwMonNumericHardDriveSensorEntry OBJECT-TYPE
    SYNTAX          SunHwMonNumericHardDriveSensorEntry
    MAX-ACCESS      not-accessible
    STATUS          current
    DESCRIPTION     
            "This attribute defines the numeric hard drive sensor entry."
    INDEX           { sunHwMonNumericHardDriveSensorIndex }
    ::= { sunHwMonNumericHardDriveSensorTable 1 }

SunHwMonNumericHardDriveSensorEntry ::=
    SEQUENCE {
        sunHwMonNumericHardDriveSensorIndex   Integer32,
        sunHwMonNumericHardDriveSensorType  SunFruOrSensorTypeTC,
        sunHwMonNumericHardDriveSensorName  DisplayString,
        sunHwMonNumericHardDriveSensorParentFruIndex            Integer32,
        sunHwMonNumericHardDriveSensorParentFruName           DisplayString,
        sunHwMonNumericHardDriveSensorAlarmStatus         SunAlarmStatusTC,
        sunHwMonNumericHardDriveSensorStateDescr        DisplayString,
        sunHwMonNumericHardDriveSensorCurrentValue          Integer32,
        sunHwMonNumericHardDriveSensorBaseUnit      SunBaseUnitsTC,
        sunHwMonNumericHardDriveSensorExponent      Integer32,
        sunHwMonNumericHardDriveSensorUpperNonRecoverableThreshold                          Integer32,
        sunHwMonNumericHardDriveSensorUpperCriticalThreshold                    Integer32,
        sunHwMonNumericHardDriveSensorUpperNonCriticalThreshold                       Integer32,
        sunHwMonNumericHardDriveSensorLowerNonRecoverableThreshold                          Integer32,
        sunHwMonNumericHardDriveSensorLowerCriticalThreshold                    Integer32,
        sunHwMonNumericHardDriveSensorLowerNonCriticalThreshold                       Integer32,
        sunHwMonNumericHardDriveSensorEnabledThresholds               SunNumericSensorEnabledThresholdsTC
    }

sunHwMonNumericHardDriveSensorIndex OBJECT-TYPE
    SYNTAX          Integer32 (1..2147483647)
    MAX-ACCESS      not-accessible
    STATUS          current
    DESCRIPTION     
            "This attribute defines the index of the hard drive sensor."
    ::= { sunHwMonNumericHardDriveSensorEntry 1 }

sunHwMonNumericHardDriveSensorType OBJECT-TYPE
    SYNTAX          SunFruOrSensorTypeTC
    MAX-ACCESS      read-only
    STATUS          current
    DESCRIPTION     
            "This attribute defines the type of hard drive sensor."
    ::= { sunHwMonNumericHardDriveSensorEntry 2 }

sunHwMonNumericHardDriveSensorName OBJECT-TYPE
    SYNTAX          DisplayString (SIZE(0..255))
    MAX-ACCESS      read-only
    STATUS          current
    DESCRIPTION     
            "This attribute defines the name of the hard drive sensor."
    ::= { sunHwMonNumericHardDriveSensorEntry 3 }

sunHwMonNumericHardDriveSensorParentFruIndex OBJECT-TYPE
    SYNTAX          Integer32 (1..2147483647)
    MAX-ACCESS      read-only
    STATUS          current
    DESCRIPTION     
            "This attribute defines the index of the field replaceable unit (FRU)
             which contains the sensor."
    ::= { sunHwMonNumericHardDriveSensorEntry 4 }

sunHwMonNumericHardDriveSensorParentFruName OBJECT-TYPE
    SYNTAX          DisplayString (SIZE(0..255))
    MAX-ACCESS      read-only
    STATUS          current
    DESCRIPTION     
            "This attribute defines the name of the field replaceable unit (FRU)
             which contains the sensor."
    ::= { sunHwMonNumericHardDriveSensorEntry 5 }

sunHwMonNumericHardDriveSensorAlarmStatus OBJECT-TYPE
    SYNTAX          SunAlarmStatusTC
    MAX-ACCESS      read-only
    STATUS          current
    DESCRIPTION     
            "This attribute defines the status of the hard drive sensor."
    ::= { sunHwMonNumericHardDriveSensorEntry 6 }

sunHwMonNumericHardDriveSensorStateDescr OBJECT-TYPE
    SYNTAX          DisplayString (SIZE(0..255))
    MAX-ACCESS      read-only
    STATUS          current
    DESCRIPTION     
            "This attribute defines the state of the hard drive sensor."
    ::= { sunHwMonNumericHardDriveSensorEntry 7 }

sunHwMonNumericHardDriveSensorCurrentValue OBJECT-TYPE
    SYNTAX          Integer32 (-2147483647..2147483647)
    MAX-ACCESS      read-only
    STATUS          current
    DESCRIPTION     
            "This attribute defines the current reading of the hard drive sensor."
    ::= { sunHwMonNumericHardDriveSensorEntry 8 }

sunHwMonNumericHardDriveSensorBaseUnit OBJECT-TYPE
    SYNTAX          SunBaseUnitsTC
    MAX-ACCESS      read-only
    STATUS          current
    DESCRIPTION     
            "This attribute defines the units used to express the current reading, 
             as well as the various thresholds of the hard drive sensor."
    ::= { sunHwMonNumericHardDriveSensorEntry 9 }

sunHwMonNumericHardDriveSensorExponent OBJECT-TYPE
    SYNTAX          Integer32 (-2147483647..2147483647)
    MAX-ACCESS      read-only
    STATUS          current
    DESCRIPTION     
            "This attribute defines the exponent that needs to be applied to the 
             units used to express the current reading, as well as the various 
             thresholds of the hard drive sensor."
    ::= { sunHwMonNumericHardDriveSensorEntry 10 }

sunHwMonNumericHardDriveSensorUpperNonRecoverableThreshold OBJECT-TYPE
    SYNTAX          Integer32 (-2147483647..2147483647)
    MAX-ACCESS      read-only
    STATUS          current
    DESCRIPTION     
            "This attribute defines the upper threshold at which a nonrecoverable
             condition occurs."
    ::= { sunHwMonNumericHardDriveSensorEntry 11 }

sunHwMonNumericHardDriveSensorUpperCriticalThreshold OBJECT-TYPE
    SYNTAX          Integer32 (-2147483647..2147483647)
    MAX-ACCESS      read-only
    STATUS          current
    DESCRIPTION     
            "This attribute defines the upper threshold at which a critical
             condition occurs."
    ::= { sunHwMonNumericHardDriveSensorEntry 12 }

sunHwMonNumericHardDriveSensorUpperNonCriticalThreshold OBJECT-TYPE
    SYNTAX          Integer32 (-2147483647..2147483647)
    MAX-ACCESS      read-only
    STATUS          current
    DESCRIPTION     
            "This attribute defines the upper threshold at which a noncritical
             condition occurs."
    ::= { sunHwMonNumericHardDriveSensorEntry 13 }

sunHwMonNumericHardDriveSensorLowerNonRecoverableThreshold OBJECT-TYPE
    SYNTAX          Integer32 (-2147483647..2147483647)
    MAX-ACCESS      read-only
    STATUS          current
    DESCRIPTION     
            "This attribute defines the lower threshold at which a nonrecoverable
             condition occurs."
    ::= { sunHwMonNumericHardDriveSensorEntry 14 }

sunHwMonNumericHardDriveSensorLowerCriticalThreshold OBJECT-TYPE
    SYNTAX          Integer32 (-2147483647..2147483647)
    MAX-ACCESS      read-only
    STATUS          current
    DESCRIPTION     
            "This attribute defines the lower threshold at which a critical
             condition occurs."
    ::= { sunHwMonNumericHardDriveSensorEntry 15 }

sunHwMonNumericHardDriveSensorLowerNonCriticalThreshold OBJECT-TYPE
    SYNTAX          Integer32 (-2147483647..2147483647)
    MAX-ACCESS      read-only
    STATUS          current
    DESCRIPTION     
            "This attribute defines the lower threshold at which a noncritical
             condition occurs."
    ::= { sunHwMonNumericHardDriveSensorEntry 16 }

sunHwMonNumericHardDriveSensorEnabledThresholds OBJECT-TYPE
    SYNTAX          SunNumericSensorEnabledThresholdsTC
    MAX-ACCESS      read-only
    STATUS          current
    DESCRIPTION     
            "This attribute defines the thresholds enabled for this hard drive
             sensor."
    ::= { sunHwMonNumericHardDriveSensorEntry 17 }

sunHwMonDiscreteHardDriveSensorTable OBJECT-TYPE
    SYNTAX          SEQUENCE OF SunHwMonDiscreteHardDriveSensorEntry
    MAX-ACCESS      not-accessible
    STATUS          current
    DESCRIPTION     
            "This attribute defines the discrete hard drive sensors table."
    ::= { sunHwMonHardDriveGroup 2 }

sunHwMonDiscreteHardDriveSensorEntry OBJECT-TYPE
    SYNTAX          SunHwMonDiscreteHardDriveSensorEntry
    MAX-ACCESS      not-accessible
    STATUS          current
    DESCRIPTION     
            "This attribute defines the discrete hard drive sensors entry."
    INDEX           { sunHwMonDiscreteHardDriveSensorIndex }
    ::= { sunHwMonDiscreteHardDriveSensorTable 1 }

SunHwMonDiscreteHardDriveSensorEntry ::=
    SEQUENCE {
        sunHwMonDiscreteHardDriveSensorIndex    Integer32,
        sunHwMonDiscreteHardDriveSensorType   SunFruOrSensorTypeTC,
        sunHwMonDiscreteHardDriveSensorName   DisplayString,
        sunHwMonDiscreteHardDriveSensorParentFruIndex             Integer32,
        sunHwMonDiscreteHardDriveSensorParentFruName            DisplayString,
        sunHwMonDiscreteHardDriveSensorAlarmStatus          SunAlarmStatusTC,
        sunHwMonDiscreteHardDriveSensorStateDescr         DisplayString
    }

sunHwMonDiscreteHardDriveSensorIndex OBJECT-TYPE
    SYNTAX          Integer32 (1..2147483647)
    MAX-ACCESS      not-accessible
    STATUS          current
    DESCRIPTION     
            "This attribute defines the index of the hard drive sensor."
    ::= { sunHwMonDiscreteHardDriveSensorEntry 1 }

sunHwMonDiscreteHardDriveSensorType OBJECT-TYPE
    SYNTAX          SunFruOrSensorTypeTC
    MAX-ACCESS      read-only
    STATUS          current
    DESCRIPTION     
            "This attribute defines the type of hard drive sensor."
    ::= { sunHwMonDiscreteHardDriveSensorEntry 2 }

sunHwMonDiscreteHardDriveSensorName OBJECT-TYPE
    SYNTAX          DisplayString (SIZE(0..255))
    MAX-ACCESS      read-only
    STATUS          current
    DESCRIPTION     
            "This attribute defines the name of the hard drive sensor."
    ::= { sunHwMonDiscreteHardDriveSensorEntry 3 }

sunHwMonDiscreteHardDriveSensorParentFruIndex OBJECT-TYPE
    SYNTAX          Integer32 (1..2147483647)
    MAX-ACCESS      read-only
    STATUS          current
    DESCRIPTION     
            "This attribute defines the index of the field replaceable unit (FRU)
             which contains the sensor."
    ::= { sunHwMonDiscreteHardDriveSensorEntry 4 }

sunHwMonDiscreteHardDriveSensorParentFruName OBJECT-TYPE
    SYNTAX          DisplayString (SIZE(0..255))
    MAX-ACCESS      read-only
    STATUS          current
    DESCRIPTION     
            "This attribute defines the name of the field replaceable unit (FRU)
             which contains the sensor."
    ::= { sunHwMonDiscreteHardDriveSensorEntry 5 }

sunHwMonDiscreteHardDriveSensorAlarmStatus OBJECT-TYPE
    SYNTAX          SunAlarmStatusTC
    MAX-ACCESS      read-only
    STATUS          current
    DESCRIPTION     
            "This attribute defines the status of the hard drive sensor."
    ::= { sunHwMonDiscreteHardDriveSensorEntry 6 }

sunHwMonDiscreteHardDriveSensorStateDescr OBJECT-TYPE
    SYNTAX          DisplayString (SIZE(0..255))
    MAX-ACCESS      read-only
    STATUS          current
    DESCRIPTION     
            "This attribute defines the state of the hard drive sensor."
    ::= { sunHwMonDiscreteHardDriveSensorEntry 7 }

sunHwMonIOGroup OBJECT IDENTIFIER
    ::= { sunHwMonSensorGroup 10 }

sunHwMonNumericIOSensorTable OBJECT-TYPE
    SYNTAX          SEQUENCE OF SunHwMonNumericIOSensorEntry
    MAX-ACCESS      not-accessible
    STATUS          current
    DESCRIPTION     
            "This attribute defines the numeric IO sensor table."
    ::= { sunHwMonIOGroup 1 }

sunHwMonNumericIOSensorEntry OBJECT-TYPE
    SYNTAX          SunHwMonNumericIOSensorEntry
    MAX-ACCESS      not-accessible
    STATUS          current
    DESCRIPTION     
            "This attribute defines the numeric IO sensor entry."
    INDEX           { sunHwMonNumericIOSensorIndex }
    ::= { sunHwMonNumericIOSensorTable 1 }

SunHwMonNumericIOSensorEntry ::=
    SEQUENCE {
        sunHwMonNumericIOSensorIndex    Integer32,
        sunHwMonNumericIOSensorType     SunFruOrSensorTypeTC,
        sunHwMonNumericIOSensorName     DisplayString,
        sunHwMonNumericIOSensorParentFruIndex     Integer32,
        sunHwMonNumericIOSensorParentFruName    DisplayString,
        sunHwMonNumericIOSensorAlarmStatus  SunAlarmStatusTC,
        sunHwMonNumericIOSensorStateDescr DisplayString,
        sunHwMonNumericIOSensorCurrentValue   Integer32,
        sunHwMonNumericIOSensorBaseUnit SunBaseUnitsTC,
        sunHwMonNumericIOSensorExponent Integer32,
        sunHwMonNumericIOSensorUpperNonRecoverableThreshold                   Integer32,
        sunHwMonNumericIOSensorUpperCriticalThreshold             Integer32,
        sunHwMonNumericIOSensorUpperNonCriticalThreshold                Integer32,
        sunHwMonNumericIOSensorLowerNonRecoverableThreshold                   Integer32,
        sunHwMonNumericIOSensorLowerCriticalThreshold             Integer32,
        sunHwMonNumericIOSensorLowerNonCriticalThreshold                Integer32,
        sunHwMonNumericIOSensorEnabledThresholds        SunNumericSensorEnabledThresholdsTC
    }

sunHwMonNumericIOSensorIndex OBJECT-TYPE
    SYNTAX          Integer32 (1..2147483647)
    MAX-ACCESS      not-accessible
    STATUS          current
    DESCRIPTION     
            "This attribute defines the index of the IO sensor."
    ::= { sunHwMonNumericIOSensorEntry 1 }

sunHwMonNumericIOSensorType OBJECT-TYPE
    SYNTAX          SunFruOrSensorTypeTC
    MAX-ACCESS      read-only
    STATUS          current
    DESCRIPTION     
            "This attribute defines the type of IO sensor."
    ::= { sunHwMonNumericIOSensorEntry 2 }

sunHwMonNumericIOSensorName OBJECT-TYPE
    SYNTAX          DisplayString (SIZE(0..255))
    MAX-ACCESS      read-only
    STATUS          current
    DESCRIPTION     
            "This attribute defines the name of the IO sensor."
    ::= { sunHwMonNumericIOSensorEntry 3 }

sunHwMonNumericIOSensorParentFruIndex OBJECT-TYPE
    SYNTAX          Integer32 (1..2147483647)
    MAX-ACCESS      read-only
    STATUS          current
    DESCRIPTION     
            "This attribute defines the index of the field replaceable unit (FRU)
             which contains the sensor."
    ::= { sunHwMonNumericIOSensorEntry 4 }

sunHwMonNumericIOSensorParentFruName OBJECT-TYPE
    SYNTAX          DisplayString (SIZE(0..255))
    MAX-ACCESS      read-only
    STATUS          current
    DESCRIPTION     
            "This attribute defines the name of the field replaceable unit (FRU)
             which contains the sensor."
    ::= { sunHwMonNumericIOSensorEntry 5 }

sunHwMonNumericIOSensorAlarmStatus OBJECT-TYPE
    SYNTAX          SunAlarmStatusTC
    MAX-ACCESS      read-only
    STATUS          current
    DESCRIPTION     
            "This attribute defines the status of the IO sensor."
    ::= { sunHwMonNumericIOSensorEntry 6 }

sunHwMonNumericIOSensorStateDescr OBJECT-TYPE
    SYNTAX          DisplayString (SIZE(0..255))
    MAX-ACCESS      read-only
    STATUS          current
    DESCRIPTION     
            "This attribute defines the state of the IO sensor."
    ::= { sunHwMonNumericIOSensorEntry 7 }

sunHwMonNumericIOSensorCurrentValue OBJECT-TYPE
    SYNTAX          Integer32 (-2147483647..2147483647)
    MAX-ACCESS      read-only
    STATUS          current
    DESCRIPTION     
            "This attribute defines the current reading of the IO sensor."
    ::= { sunHwMonNumericIOSensorEntry 8 }

sunHwMonNumericIOSensorBaseUnit OBJECT-TYPE
    SYNTAX          SunBaseUnitsTC
    MAX-ACCESS      read-only
    STATUS          current
    DESCRIPTION     
            "This attribute defines the units used to express the current reading, 
             as well as the various thresholds of the IO sensor."
    ::= { sunHwMonNumericIOSensorEntry 9 }

sunHwMonNumericIOSensorExponent OBJECT-TYPE
    SYNTAX          Integer32 (-2147483647..2147483647)
    MAX-ACCESS      read-only
    STATUS          current
    DESCRIPTION     
            "This attribute defines the exponent that needs to be applied to the 
             units used to express the current reading, as well as the various 
             thresholds of the IO sensor."
    ::= { sunHwMonNumericIOSensorEntry 10 }

sunHwMonNumericIOSensorUpperNonRecoverableThreshold OBJECT-TYPE
    SYNTAX          Integer32 (-2147483647..2147483647)
    MAX-ACCESS      read-only
    STATUS          current
    DESCRIPTION     
            "This attribute defines the upper threshold at which a nonrecoverable
             condition occurs."
    ::= { sunHwMonNumericIOSensorEntry 11 }

sunHwMonNumericIOSensorUpperCriticalThreshold OBJECT-TYPE
    SYNTAX          Integer32 (-2147483647..2147483647)
    MAX-ACCESS      read-only
    STATUS          current
    DESCRIPTION     
            "This attribute defines the upper threshold at which a critical
             condition occurs."
    ::= { sunHwMonNumericIOSensorEntry 12 }

sunHwMonNumericIOSensorUpperNonCriticalThreshold OBJECT-TYPE
    SYNTAX          Integer32 (-2147483647..2147483647)
    MAX-ACCESS      read-only
    STATUS          current
    DESCRIPTION     
            "This attribute defines the upper threshold at which a noncritical
             condition occurs."
    ::= { sunHwMonNumericIOSensorEntry 13 }

sunHwMonNumericIOSensorLowerNonRecoverableThreshold OBJECT-TYPE
    SYNTAX          Integer32 (-2147483647..2147483647)
    MAX-ACCESS      read-only
    STATUS          current
    DESCRIPTION     
            "This attribute defines the lower threshold at which a nonrecoverable
             condition occurs."
    ::= { sunHwMonNumericIOSensorEntry 14 }

sunHwMonNumericIOSensorLowerCriticalThreshold OBJECT-TYPE
    SYNTAX          Integer32 (-2147483647..2147483647)
    MAX-ACCESS      read-only
    STATUS          current
    DESCRIPTION     
            "This attribute defines the lower threshold at which a critical
             condition occurs."
    ::= { sunHwMonNumericIOSensorEntry 15 }

sunHwMonNumericIOSensorLowerNonCriticalThreshold OBJECT-TYPE
    SYNTAX          Integer32 (-2147483647..2147483647)
    MAX-ACCESS      read-only
    STATUS          current
    DESCRIPTION     
            "This attribute defines the lower threshold at which a noncritical
             condition occurs."
    ::= { sunHwMonNumericIOSensorEntry 16 }

sunHwMonNumericIOSensorEnabledThresholds OBJECT-TYPE
    SYNTAX          SunNumericSensorEnabledThresholdsTC
    MAX-ACCESS      read-only
    STATUS          current
    DESCRIPTION     
            "This attribute defines the thresholds enabled for this IO
             sensor."
    ::= { sunHwMonNumericIOSensorEntry 17 }

sunHwMonDiscreteIOSensorTable OBJECT-TYPE
    SYNTAX          SEQUENCE OF SunHwMonDiscreteIOSensorEntry
    MAX-ACCESS      not-accessible
    STATUS          current
    DESCRIPTION     
            "This attribute defines the discrete IO sensors table."
    ::= { sunHwMonIOGroup 2 }

sunHwMonDiscreteIOSensorEntry OBJECT-TYPE
    SYNTAX          SunHwMonDiscreteIOSensorEntry
    MAX-ACCESS      not-accessible
    STATUS          current
    DESCRIPTION     
            "This attribute defines the discrete IO sensors entry."
    INDEX           { sunHwMonDiscreteIOSensorIndex }
    ::= { sunHwMonDiscreteIOSensorTable 1 }

SunHwMonDiscreteIOSensorEntry ::=
    SEQUENCE {
        sunHwMonDiscreteIOSensorIndex   Integer32,
        sunHwMonDiscreteIOSensorType    SunFruOrSensorTypeTC,
        sunHwMonDiscreteIOSensorName    DisplayString,
        sunHwMonDiscreteIOSensorParentFruIndex      Integer32,
        sunHwMonDiscreteIOSensorParentFruName     DisplayString,
        sunHwMonDiscreteIOSensorAlarmStatus   SunAlarmStatusTC,
        sunHwMonDiscreteIOSensorStateDescr  DisplayString
    }

sunHwMonDiscreteIOSensorIndex OBJECT-TYPE
    SYNTAX          Integer32 (1..2147483647)
    MAX-ACCESS      not-accessible
    STATUS          current
    DESCRIPTION     
            "This attribute defines the index of the IO sensor."
    ::= { sunHwMonDiscreteIOSensorEntry 1 }

sunHwMonDiscreteIOSensorType OBJECT-TYPE
    SYNTAX          SunFruOrSensorTypeTC
    MAX-ACCESS      read-only
    STATUS          current
    DESCRIPTION     
            "This attribute defines the type of IO sensor."
    ::= { sunHwMonDiscreteIOSensorEntry 2 }

sunHwMonDiscreteIOSensorName OBJECT-TYPE
    SYNTAX          DisplayString (SIZE(0..255))
    MAX-ACCESS      read-only
    STATUS          current
    DESCRIPTION     
            "This attribute defines the name of the IO sensor."
    ::= { sunHwMonDiscreteIOSensorEntry 3 }

sunHwMonDiscreteIOSensorParentFruIndex OBJECT-TYPE
    SYNTAX          Integer32 (1..2147483647)
    MAX-ACCESS      read-only
    STATUS          current
    DESCRIPTION     
            "This attribute defines the index of the field replaceable unit (FRU)
             which contains the sensor."
    ::= { sunHwMonDiscreteIOSensorEntry 4 }

sunHwMonDiscreteIOSensorParentFruName OBJECT-TYPE
    SYNTAX          DisplayString (SIZE(0..255))
    MAX-ACCESS      read-only
    STATUS          current
    DESCRIPTION     
            "This attribute defines the name of the field replaceable unit (FRU)
             which contains the sensor."
    ::= { sunHwMonDiscreteIOSensorEntry 5 }

sunHwMonDiscreteIOSensorAlarmStatus OBJECT-TYPE
    SYNTAX          SunAlarmStatusTC
    MAX-ACCESS      read-only
    STATUS          current
    DESCRIPTION     
            "This attribute defines the status of the IO sensor."
    ::= { sunHwMonDiscreteIOSensorEntry 6 }

sunHwMonDiscreteIOSensorStateDescr OBJECT-TYPE
    SYNTAX          DisplayString (SIZE(0..255))
    MAX-ACCESS      read-only
    STATUS          current
    DESCRIPTION     
            "This attribute defines the state of the IO sensor."
    ::= { sunHwMonDiscreteIOSensorEntry 7 }

sunHwMonSlotOrConnectorGroup OBJECT IDENTIFIER
    ::= { sunHwMonSensorGroup 11 }

sunHwMonNumericSlotOrConnectorSensorTable OBJECT-TYPE
    SYNTAX          SEQUENCE OF SunHwMonNumericSlotOrConnectorSensorEntry
    MAX-ACCESS      not-accessible
    STATUS          current
    DESCRIPTION     
            "This attribute defines the numeric slot or connector sensor table."
    ::= { sunHwMonSlotOrConnectorGroup 1 }

sunHwMonNumericSlotOrConnectorSensorEntry OBJECT-TYPE
    SYNTAX          SunHwMonNumericSlotOrConnectorSensorEntry
    MAX-ACCESS      not-accessible
    STATUS          current
    DESCRIPTION     
            "This attribute defines the numeric slot or connector sensor entry."
    INDEX           { sunHwMonNumericSlotOrConnectorSensorIndex }
    ::= { sunHwMonNumericSlotOrConnectorSensorTable 1 }

SunHwMonNumericSlotOrConnectorSensorEntry ::=
    SEQUENCE {
        sunHwMonNumericSlotOrConnectorSensorIndex         Integer32,
        sunHwMonNumericSlotOrConnectorSensorType        SunFruOrSensorTypeTC,
        sunHwMonNumericSlotOrConnectorSensorName        DisplayString,
        sunHwMonNumericSlotOrConnectorSensorParentFruIndex                  Integer32,
        sunHwMonNumericSlotOrConnectorSensorParentFruName                 DisplayString,
        sunHwMonNumericSlotOrConnectorSensorAlarmStatus               SunAlarmStatusTC,
        sunHwMonNumericSlotOrConnectorSensorStateDescr              DisplayString,
        sunHwMonNumericSlotOrConnectorSensorCurrentValue                Integer32,
        sunHwMonNumericSlotOrConnectorSensorBaseUnit            SunBaseUnitsTC,
        sunHwMonNumericSlotOrConnectorSensorExponent            Integer32,
        sunHwMonNumericSlotOrConnectorSensorUpperNonRecoverableThreshold                                Integer32,
        sunHwMonNumericSlotOrConnectorSensorUpperCriticalThreshold                          Integer32,
        sunHwMonNumericSlotOrConnectorSensorUpperNonCriticalThreshold                             Integer32,
        sunHwMonNumericSlotOrConnectorSensorLowerNonRecoverableThreshold                                Integer32,
        sunHwMonNumericSlotOrConnectorSensorLowerCriticalThreshold                          Integer32,
        sunHwMonNumericSlotOrConnectorSensorLowerNonCriticalThreshold                             Integer32,
        sunHwMonNumericSlotOrConnectorSensorEnabledThresholds                     SunNumericSensorEnabledThresholdsTC
    }

sunHwMonNumericSlotOrConnectorSensorIndex OBJECT-TYPE
    SYNTAX          Integer32 (1..2147483647)
    MAX-ACCESS      not-accessible
    STATUS          current
    DESCRIPTION     
            "This attribute defines the index of the slot or connector sensor."
    ::= { sunHwMonNumericSlotOrConnectorSensorEntry 1 }

sunHwMonNumericSlotOrConnectorSensorType OBJECT-TYPE
    SYNTAX          SunFruOrSensorTypeTC
    MAX-ACCESS      read-only
    STATUS          current
    DESCRIPTION     
            "This attribute defines the type of slot or connector sensor."
    ::= { sunHwMonNumericSlotOrConnectorSensorEntry 2 }

sunHwMonNumericSlotOrConnectorSensorName OBJECT-TYPE
    SYNTAX          DisplayString (SIZE(0..255))
    MAX-ACCESS      read-only
    STATUS          current
    DESCRIPTION     
            "This attribute defines the name of the slot or connector sensor."
    ::= { sunHwMonNumericSlotOrConnectorSensorEntry 3 }

sunHwMonNumericSlotOrConnectorSensorParentFruIndex OBJECT-TYPE
    SYNTAX          Integer32 (1..2147483647)
    MAX-ACCESS      read-only
    STATUS          current
    DESCRIPTION     
            "This attribute defines the index of the field replaceable unit (FRU)
             which contains the sensor."
    ::= { sunHwMonNumericSlotOrConnectorSensorEntry 4 }

sunHwMonNumericSlotOrConnectorSensorParentFruName OBJECT-TYPE
    SYNTAX          DisplayString (SIZE(0..255))
    MAX-ACCESS      read-only
    STATUS          current
    DESCRIPTION     
            "This attribute defines the name of the field replaceable unit (FRU)
             which contains the sensor."
    ::= { sunHwMonNumericSlotOrConnectorSensorEntry 5 }

sunHwMonNumericSlotOrConnectorSensorAlarmStatus OBJECT-TYPE
    SYNTAX          SunAlarmStatusTC
    MAX-ACCESS      read-only
    STATUS          current
    DESCRIPTION     
            "This attribute defines the status of the slot or connector sensor."
    ::= { sunHwMonNumericSlotOrConnectorSensorEntry 6 }

sunHwMonNumericSlotOrConnectorSensorStateDescr OBJECT-TYPE
    SYNTAX          DisplayString (SIZE(0..255))
    MAX-ACCESS      read-only
    STATUS          current
    DESCRIPTION     
            "This attribute defines the state of the slot or connector sensor."
    ::= { sunHwMonNumericSlotOrConnectorSensorEntry 7 }

sunHwMonNumericSlotOrConnectorSensorCurrentValue OBJECT-TYPE
    SYNTAX          Integer32 (-2147483647..2147483647)
    MAX-ACCESS      read-only
    STATUS          current
    DESCRIPTION     
            "This attribute defines the current reading of the slot or connector sensor."
    ::= { sunHwMonNumericSlotOrConnectorSensorEntry 8 }

sunHwMonNumericSlotOrConnectorSensorBaseUnit OBJECT-TYPE
    SYNTAX          SunBaseUnitsTC
    MAX-ACCESS      read-only
    STATUS          current
    DESCRIPTION     
            "This attribute defines the units used to express the current reading, 
             as well as the various thresholds of the slot or connector sensor."
    ::= { sunHwMonNumericSlotOrConnectorSensorEntry 9 }

sunHwMonNumericSlotOrConnectorSensorExponent OBJECT-TYPE
    SYNTAX          Integer32 (-2147483647..2147483647)
    MAX-ACCESS      read-only
    STATUS          current
    DESCRIPTION     
            "This attribute defines the exponent that needs to be applied to the 
             units used to express the current reading, as well as the various 
             thresholds of the slot or connector sensor."
    ::= { sunHwMonNumericSlotOrConnectorSensorEntry 10 }

sunHwMonNumericSlotOrConnectorSensorUpperNonRecoverableThreshold OBJECT-TYPE
    SYNTAX          Integer32 (-2147483647..2147483647)
    MAX-ACCESS      read-only
    STATUS          current
    DESCRIPTION     
            "This attribute defines the upper threshold at which a nonrecoverable
             condition occurs."
    ::= { sunHwMonNumericSlotOrConnectorSensorEntry 11 }

sunHwMonNumericSlotOrConnectorSensorUpperCriticalThreshold OBJECT-TYPE
    SYNTAX          Integer32 (-2147483647..2147483647)
    MAX-ACCESS      read-only
    STATUS          current
    DESCRIPTION     
            "This attribute defines the upper threshold at which a critical
             condition occurs."
    ::= { sunHwMonNumericSlotOrConnectorSensorEntry 12 }

sunHwMonNumericSlotOrConnectorSensorUpperNonCriticalThreshold OBJECT-TYPE
    SYNTAX          Integer32 (-2147483647..2147483647)
    MAX-ACCESS      read-only
    STATUS          current
    DESCRIPTION     
            "This attribute defines the upper threshold at which a noncritical
             condition occurs."
    ::= { sunHwMonNumericSlotOrConnectorSensorEntry 13 }

sunHwMonNumericSlotOrConnectorSensorLowerNonRecoverableThreshold OBJECT-TYPE
    SYNTAX          Integer32 (-2147483647..2147483647)
    MAX-ACCESS      read-only
    STATUS          current
    DESCRIPTION     
            "This attribute defines the lower threshold at which a nonrecoverable
             condition occurs."
    ::= { sunHwMonNumericSlotOrConnectorSensorEntry 14 }

sunHwMonNumericSlotOrConnectorSensorLowerCriticalThreshold OBJECT-TYPE
    SYNTAX          Integer32 (-2147483647..2147483647)
    MAX-ACCESS      read-only
    STATUS          current
    DESCRIPTION     
            "This attribute defines the lower threshold at which a critical
             condition occurs."
    ::= { sunHwMonNumericSlotOrConnectorSensorEntry 15 }

sunHwMonNumericSlotOrConnectorSensorLowerNonCriticalThreshold OBJECT-TYPE
    SYNTAX          Integer32 (-2147483647..2147483647)
    MAX-ACCESS      read-only
    STATUS          current
    DESCRIPTION     
            "This attribute defines the lower threshold at which a noncritical
             condition occurs."
    ::= { sunHwMonNumericSlotOrConnectorSensorEntry 16 }

sunHwMonNumericSlotOrConnectorSensorEnabledThresholds OBJECT-TYPE
    SYNTAX          SunNumericSensorEnabledThresholdsTC
    MAX-ACCESS      read-only
    STATUS          current
    DESCRIPTION     
            "This attribute defines the thresholds enabled for this slot or connector
             sensor."
    ::= { sunHwMonNumericSlotOrConnectorSensorEntry 17 }

sunHwMonDiscreteSlotOrConnectorSensorTable OBJECT-TYPE
    SYNTAX          SEQUENCE OF SunHwMonDiscreteSlotOrConnectorSensorEntry
    MAX-ACCESS      not-accessible
    STATUS          current
    DESCRIPTION     
            "This attribute defines the discrete slot or connector sensors table."
    ::= { sunHwMonSlotOrConnectorGroup 2 }

sunHwMonDiscreteSlotOrConnectorSensorEntry OBJECT-TYPE
    SYNTAX          SunHwMonDiscreteSlotOrConnectorSensorEntry
    MAX-ACCESS      not-accessible
    STATUS          current
    DESCRIPTION     
            "This attribute defines the discrete slot or connector sensors entry."
    INDEX           { sunHwMonDiscreteSlotOrConnectorSensorIndex }
    ::= { sunHwMonDiscreteSlotOrConnectorSensorTable 1 }

SunHwMonDiscreteSlotOrConnectorSensorEntry ::=
    SEQUENCE {
        sunHwMonDiscreteSlotOrConnectorSensorIndex          Integer32,
        sunHwMonDiscreteSlotOrConnectorSensorType         SunFruOrSensorTypeTC,
        sunHwMonDiscreteSlotOrConnectorSensorName         DisplayString,
        sunHwMonDiscreteSlotOrConnectorSensorParentFruIndex                   Integer32,
        sunHwMonDiscreteSlotOrConnectorSensorParentFruName                  DisplayString,
        sunHwMonDiscreteSlotOrConnectorSensorAlarmStatus                SunAlarmStatusTC,
        sunHwMonDiscreteSlotOrConnectorSensorStateDescr               DisplayString
    }

sunHwMonDiscreteSlotOrConnectorSensorIndex OBJECT-TYPE
    SYNTAX          Integer32 (1..2147483647)
    MAX-ACCESS      not-accessible
    STATUS          current
    DESCRIPTION     
            "This attribute defines the index of the slot or connector sensor."
    ::= { sunHwMonDiscreteSlotOrConnectorSensorEntry 1 }

sunHwMonDiscreteSlotOrConnectorSensorType OBJECT-TYPE
    SYNTAX          SunFruOrSensorTypeTC
    MAX-ACCESS      read-only
    STATUS          current
    DESCRIPTION     
            "This attribute defines the type of slot or connector sensor."
    ::= { sunHwMonDiscreteSlotOrConnectorSensorEntry 2 }

sunHwMonDiscreteSlotOrConnectorSensorName OBJECT-TYPE
    SYNTAX          DisplayString (SIZE(0..255))
    MAX-ACCESS      read-only
    STATUS          current
    DESCRIPTION     
            "This attribute defines the name of the slot or connector sensor."
    ::= { sunHwMonDiscreteSlotOrConnectorSensorEntry 3 }

sunHwMonDiscreteSlotOrConnectorSensorParentFruIndex OBJECT-TYPE
    SYNTAX          Integer32 (1..2147483647)
    MAX-ACCESS      read-only
    STATUS          current
    DESCRIPTION     
            "This attribute defines the index of the field replaceable unit (FRU)
             which contains the sensor."
    ::= { sunHwMonDiscreteSlotOrConnectorSensorEntry 4 }

sunHwMonDiscreteSlotOrConnectorSensorParentFruName OBJECT-TYPE
    SYNTAX          DisplayString (SIZE(0..255))
    MAX-ACCESS      read-only
    STATUS          current
    DESCRIPTION     
            "This attribute defines the name of the field replaceable unit (FRU)
             which contains the sensor."
    ::= { sunHwMonDiscreteSlotOrConnectorSensorEntry 5 }

sunHwMonDiscreteSlotOrConnectorSensorAlarmStatus OBJECT-TYPE
    SYNTAX          SunAlarmStatusTC
    MAX-ACCESS      read-only
    STATUS          current
    DESCRIPTION     
            "This attribute defines the status of the slot or connector sensor."
    ::= { sunHwMonDiscreteSlotOrConnectorSensorEntry 6 }

sunHwMonDiscreteSlotOrConnectorSensorStateDescr OBJECT-TYPE
    SYNTAX          DisplayString (SIZE(0..255))
    MAX-ACCESS      read-only
    STATUS          current
    DESCRIPTION     
            "This attribute defines the state of the slot or connector sensor."
    ::= { sunHwMonDiscreteSlotOrConnectorSensorEntry 7 }

sunHwMonOtherSensorGroup OBJECT IDENTIFIER
    ::= { sunHwMonSensorGroup 12 }

sunHwMonNumericOtherSensorTable OBJECT-TYPE
    SYNTAX          SEQUENCE OF SunHwMonNumericOtherSensorEntry
    MAX-ACCESS      not-accessible
    STATUS          current
    DESCRIPTION     
            "This attribute defines the uncategorized sensor table."
    ::= { sunHwMonOtherSensorGroup 1 }

sunHwMonNumericOtherSensorEntry OBJECT-TYPE
    SYNTAX          SunHwMonNumericOtherSensorEntry
    MAX-ACCESS      not-accessible
    STATUS          current
    DESCRIPTION     
            "This attribute defines the uncategorized sensor entry."
    INDEX           { sunHwMonNumericOtherSensorIndex }
    ::= { sunHwMonNumericOtherSensorTable 1 }

SunHwMonNumericOtherSensorEntry ::=
    SEQUENCE {
        sunHwMonNumericOtherSensorIndex Integer32,
        sunHwMonNumericOtherSensorType  SunFruOrSensorTypeTC,
        sunHwMonNumericOtherSensorName  DisplayString,
        sunHwMonNumericOtherSensorParentFruIndex        Integer32,
        sunHwMonNumericOtherSensorParentFruName       DisplayString,
        sunHwMonNumericOtherSensorAlarmStatus     SunAlarmStatusTC,
        sunHwMonNumericOtherSensorStateDescr    DisplayString,
        sunHwMonNumericOtherSensorCurrentValue      Integer32,
        sunHwMonNumericOtherSensorBaseUnit  SunBaseUnitsTC,
        sunHwMonNumericOtherSensorExponent  Integer32,
        sunHwMonNumericOtherSensorUpperNonRecoverableThreshold                      Integer32,
        sunHwMonNumericOtherSensorUpperCriticalThreshold                Integer32,
        sunHwMonNumericOtherSensorUpperNonCriticalThreshold                   Integer32,
        sunHwMonNumericOtherSensorLowerNonRecoverableThreshold                      Integer32,
        sunHwMonNumericOtherSensorLowerCriticalThreshold                Integer32,
        sunHwMonNumericOtherSensorLowerNonCriticalThreshold                   Integer32,
        sunHwMonNumericOtherSensorEnabledThresholds           SunNumericSensorEnabledThresholdsTC
    }

sunHwMonNumericOtherSensorIndex OBJECT-TYPE
    SYNTAX          Integer32 (1..2147483647)
    MAX-ACCESS      not-accessible
    STATUS          current
    DESCRIPTION     
            "This attribute defines the index of the uncategorized sensor."
    ::= { sunHwMonNumericOtherSensorEntry 1 }

sunHwMonNumericOtherSensorType OBJECT-TYPE
    SYNTAX          SunFruOrSensorTypeTC
    MAX-ACCESS      read-only
    STATUS          current
    DESCRIPTION     
            "This attribute defines the type of uncategorized sensor."
    ::= { sunHwMonNumericOtherSensorEntry 2 }

sunHwMonNumericOtherSensorName OBJECT-TYPE
    SYNTAX          DisplayString (SIZE(0..255))
    MAX-ACCESS      read-only
    STATUS          current
    DESCRIPTION     
            "This attribute defines the name of the uncategorized sensor."
    ::= { sunHwMonNumericOtherSensorEntry 3 }

sunHwMonNumericOtherSensorParentFruIndex OBJECT-TYPE
    SYNTAX          Integer32 (1..2147483647)
    MAX-ACCESS      read-only
    STATUS          current
    DESCRIPTION     
            "This attribute defines the index of the field replaceable unit (FRU)
             in which the sensor is contained."
    ::= { sunHwMonNumericOtherSensorEntry 4 }

sunHwMonNumericOtherSensorParentFruName OBJECT-TYPE
    SYNTAX          DisplayString (SIZE(0..255))
    MAX-ACCESS      read-only
    STATUS          current
    DESCRIPTION     
            "This attribute defines the name of the field replaceable unit (FRU)
             in which the sensor is contained."
    ::= { sunHwMonNumericOtherSensorEntry 5 }

sunHwMonNumericOtherSensorAlarmStatus OBJECT-TYPE
    SYNTAX          SunAlarmStatusTC
    MAX-ACCESS      read-only
    STATUS          current
    DESCRIPTION     
            "This attribute defines the status of the uncategorized sensor."
    ::= { sunHwMonNumericOtherSensorEntry 6 }

sunHwMonNumericOtherSensorStateDescr OBJECT-TYPE
    SYNTAX          DisplayString (SIZE(0..255))
    MAX-ACCESS      read-only
    STATUS          current
    DESCRIPTION     
            "This attribute defines the state of the uncategorized sensor."
    ::= { sunHwMonNumericOtherSensorEntry 7 }

sunHwMonNumericOtherSensorCurrentValue OBJECT-TYPE
    SYNTAX          Integer32 (-2147483647..2147483647)
    MAX-ACCESS      read-only
    STATUS          current
    DESCRIPTION     
            "This attribute defines the current reading of the uncategorized sensor."
    ::= { sunHwMonNumericOtherSensorEntry 8 }

sunHwMonNumericOtherSensorBaseUnit OBJECT-TYPE
    SYNTAX          SunBaseUnitsTC
    MAX-ACCESS      read-only
    STATUS          current
    DESCRIPTION     
            "This attribute defines the units used to express the current reading, 
             as well as the various thresholds of the uncategorized sensor."
    ::= { sunHwMonNumericOtherSensorEntry 9 }

sunHwMonNumericOtherSensorExponent OBJECT-TYPE
    SYNTAX          Integer32 (-2147483647..2147483647)
    MAX-ACCESS      read-only
    STATUS          current
    DESCRIPTION     
            "This attribute defines the exponent that needs to be applied to the 
             units used to express the current reading, as well as the various 
             thresholds of the uncategorized sensor."
    ::= { sunHwMonNumericOtherSensorEntry 10 }

sunHwMonNumericOtherSensorUpperNonRecoverableThreshold OBJECT-TYPE
    SYNTAX          Integer32 (-2147483647..2147483647)
    MAX-ACCESS      read-only
    STATUS          current
    DESCRIPTION     
            "This attribute defines the upper threshold at which a nonrecoverable
             condition occurs."
    ::= { sunHwMonNumericOtherSensorEntry 11 }

sunHwMonNumericOtherSensorUpperCriticalThreshold OBJECT-TYPE
    SYNTAX          Integer32 (-2147483647..2147483647)
    MAX-ACCESS      read-only
    STATUS          current
    DESCRIPTION     
            "This attribute defines the upper threshold at which a critical
             condition occurs."
    ::= { sunHwMonNumericOtherSensorEntry 12 }

sunHwMonNumericOtherSensorUpperNonCriticalThreshold OBJECT-TYPE
    SYNTAX          Integer32 (-2147483647..2147483647)
    MAX-ACCESS      read-only
    STATUS          current
    DESCRIPTION     
            "This attribute defines the upper threshold at which a noncritical
             condition occurs."
    ::= { sunHwMonNumericOtherSensorEntry 13 }

sunHwMonNumericOtherSensorLowerNonRecoverableThreshold OBJECT-TYPE
    SYNTAX          Integer32 (-2147483647..2147483647)
    MAX-ACCESS      read-only
    STATUS          current
    DESCRIPTION     
            "This attribute defines the lower threshold at which a nonrecoverable
             condition occurs."
    ::= { sunHwMonNumericOtherSensorEntry 14 }

sunHwMonNumericOtherSensorLowerCriticalThreshold OBJECT-TYPE
    SYNTAX          Integer32 (-2147483647..2147483647)
    MAX-ACCESS      read-only
    STATUS          current
    DESCRIPTION     
            "This attribute defines the lower threshold at which a critical
             condition occurs."
    ::= { sunHwMonNumericOtherSensorEntry 15 }

sunHwMonNumericOtherSensorLowerNonCriticalThreshold OBJECT-TYPE
    SYNTAX          Integer32 (-2147483647..2147483647)
    MAX-ACCESS      read-only
    STATUS          current
    DESCRIPTION     
            "This attribute defines the lower threshold at which a noncritical
             condition occurs."
    ::= { sunHwMonNumericOtherSensorEntry 16 }

sunHwMonNumericOtherSensorEnabledThresholds OBJECT-TYPE
    SYNTAX          SunNumericSensorEnabledThresholdsTC
    MAX-ACCESS      read-only
    STATUS          current
    DESCRIPTION     
            "This attribute defines the thresholds enabled for this sensor."
    ::= { sunHwMonNumericOtherSensorEntry 17 }

sunHwMonDiscreteOtherSensorTable OBJECT-TYPE
    SYNTAX          SEQUENCE OF SunHwMonDiscreteOtherSensorEntry
    MAX-ACCESS      not-accessible
    STATUS          current
    DESCRIPTION     
            "This attribute defines the uncategorized sensor table."
    ::= { sunHwMonOtherSensorGroup 2 }

sunHwMonDiscreteOtherSensorEntry OBJECT-TYPE
    SYNTAX          SunHwMonDiscreteOtherSensorEntry
    MAX-ACCESS      not-accessible
    STATUS          current
    DESCRIPTION     
            "This attribute defines the uncategorized sensor entry."
    INDEX           { sunHwMonDiscreteOtherSensorIndex }
    ::= { sunHwMonDiscreteOtherSensorTable 1 }

SunHwMonDiscreteOtherSensorEntry ::=
    SEQUENCE {
        sunHwMonDiscreteOtherSensorIndex Integer32,
        sunHwMonDiscreteOtherSensorType SunFruOrSensorTypeTC,
        sunHwMonDiscreteOtherSensorName DisplayString,
        sunHwMonDiscreteOtherSensorParentFruIndex         Integer32,
        sunHwMonDiscreteOtherSensorParentFruName        DisplayString,
        sunHwMonDiscreteOtherSensorAlarmStatus      SunAlarmStatusTC,
        sunHwMonDiscreteOtherSensorStateDescr     DisplayString
    }

sunHwMonDiscreteOtherSensorIndex OBJECT-TYPE
    SYNTAX          Integer32 (1..2147483647)
    MAX-ACCESS      not-accessible
    STATUS          current
    DESCRIPTION     
            "This attribute defines the index of the uncategorized sensor."
    ::= { sunHwMonDiscreteOtherSensorEntry 1 }

sunHwMonDiscreteOtherSensorType OBJECT-TYPE
    SYNTAX          SunFruOrSensorTypeTC
    MAX-ACCESS      read-only
    STATUS          current
    DESCRIPTION     
            "This attribute defines the type of uncategorized sensor."
    ::= { sunHwMonDiscreteOtherSensorEntry 2 }

sunHwMonDiscreteOtherSensorName OBJECT-TYPE
    SYNTAX          DisplayString (SIZE(0..255))
    MAX-ACCESS      read-only
    STATUS          current
    DESCRIPTION     
            "This attribute defines the name of the uncategorized sensor."
    ::= { sunHwMonDiscreteOtherSensorEntry 3 }

sunHwMonDiscreteOtherSensorParentFruIndex OBJECT-TYPE
    SYNTAX          Integer32 (1..2147483647)
    MAX-ACCESS      read-only
    STATUS          current
    DESCRIPTION     
            "This attribute defines the index of the field replaceable unit (FRU)
             which contains the sensor."
    ::= { sunHwMonDiscreteOtherSensorEntry 4 }

sunHwMonDiscreteOtherSensorParentFruName OBJECT-TYPE
    SYNTAX          DisplayString (SIZE(0..255))
    MAX-ACCESS      read-only
    STATUS          current
    DESCRIPTION     
            "This attribute defines the name of the field replaceable unit (FRU)
             which contains the sensor."
    ::= { sunHwMonDiscreteOtherSensorEntry 5 }

sunHwMonDiscreteOtherSensorAlarmStatus OBJECT-TYPE
    SYNTAX          SunAlarmStatusTC
    MAX-ACCESS      read-only
    STATUS          current
    DESCRIPTION     
            "This attribute defines the status of the uncategorized sensor."
    ::= { sunHwMonDiscreteOtherSensorEntry 6 }

sunHwMonDiscreteOtherSensorStateDescr OBJECT-TYPE
    SYNTAX          DisplayString (SIZE(0..255))
    MAX-ACCESS      read-only
    STATUS          current
    DESCRIPTION     
            "This attribute defines the state of the uncategorized sensor."
    ::= { sunHwMonDiscreteOtherSensorEntry 7 }

sunHwMonIndicatorGroup OBJECT IDENTIFIER
    ::= { sunHwMonGroups 8 }

sunHwMonIndicatorLocator OBJECT IDENTIFIER
    ::= { sunHwMonIndicatorGroup 1 }

sunHwMonIndicatorLocatorName OBJECT-TYPE
    SYNTAX          DisplayString (SIZE(0..255))
    MAX-ACCESS      read-only
    STATUS          current
    DESCRIPTION     
            "This attribute defines the name of the Sun server locator indicator."
    ::= { sunHwMonIndicatorLocator 1 }

sunHwMonIndicatorLocatorCurrentStatus OBJECT-TYPE
    SYNTAX          SunIndicatorStateTC
    MAX-ACCESS      read-write
    STATUS          current
    DESCRIPTION     
            "This attribute defines the current status of the Sun server locator indicator."
    ::= { sunHwMonIndicatorLocator 2 }

sunHwMonIndicatorService OBJECT IDENTIFIER
    ::= { sunHwMonIndicatorGroup 2 }

sunHwMonIndicatorServiceName OBJECT-TYPE
    SYNTAX          DisplayString (SIZE(0..255))
    MAX-ACCESS      read-only
    STATUS          current
    DESCRIPTION     
            "This attribute defines the name of the Sun server service indicator."
    ::= { sunHwMonIndicatorService 1 }

sunHwMonIndicatorServiceCurrentStatus OBJECT-TYPE
    SYNTAX          SunIndicatorStateTC
    MAX-ACCESS      read-only
    STATUS          current
    DESCRIPTION     
            "This attribute defines the current status of the Sun server service indicator."
    ::= { sunHwMonIndicatorService 2 }

sunHwMonIndicatorAll OBJECT IDENTIFIER
    ::= { sunHwMonIndicatorGroup 3 }

sunHwMonIndicatorTable OBJECT-TYPE
    SYNTAX          SEQUENCE OF SunHwMonIndicatorEntry
    MAX-ACCESS      not-accessible
    STATUS          current
    DESCRIPTION     
            "This attribute defines the indicator table."
    ::= { sunHwMonIndicatorAll 1 }

sunHwMonIndicatorEntry OBJECT-TYPE
    SYNTAX          SunHwMonIndicatorEntry
    MAX-ACCESS      not-accessible
    STATUS          current
    DESCRIPTION     
            "This attribute defines the indicator entry."
    INDEX           { sunHwMonIndicatorIndex }
    ::= { sunHwMonIndicatorTable 1 }

SunHwMonIndicatorEntry ::=
    SEQUENCE {
        sunHwMonIndicatorIndex          Integer32,
        sunHwMonIndicatorName           DisplayString,
        sunHwMonIndicatorType           SunFruOrSensorTypeTC,
        sunHwMonIndicatorCurrentStatus  SunIndicatorStateTC
    }

sunHwMonIndicatorIndex OBJECT-TYPE
    SYNTAX          Integer32 (1..2147483647)
    MAX-ACCESS      not-accessible
    STATUS          current
    DESCRIPTION     
            "This attribute defines the index of the Sun server indicator."
    ::= { sunHwMonIndicatorEntry 1 }

sunHwMonIndicatorName OBJECT-TYPE
    SYNTAX          DisplayString (SIZE(0..255))
    MAX-ACCESS      read-only
    STATUS          current
    DESCRIPTION     
            "This attribute defines the name of the Sun server indicator."
    ::= { sunHwMonIndicatorEntry 2 }

sunHwMonIndicatorType OBJECT-TYPE
    SYNTAX          SunFruOrSensorTypeTC
    MAX-ACCESS      read-only
    STATUS          current
    DESCRIPTION     
            "This attribute defines the type of Sun server indicator."
    ::= { sunHwMonIndicatorEntry 3 }

sunHwMonIndicatorCurrentStatus OBJECT-TYPE
    SYNTAX          SunIndicatorStateTC
    MAX-ACCESS      read-only
    STATUS          current
    DESCRIPTION     
            "This attribute defines the current status of the Sun server indicator."
    ::= { sunHwMonIndicatorEntry 4 }

sunHwMonTotalPowerConsumption OBJECT IDENTIFIER
    ::= { sunHwMonGroups 9 }

sunHwMonTotalPowerConsumptionSensorName OBJECT-TYPE
    SYNTAX          DisplayString (SIZE(0..255))
    MAX-ACCESS      read-only
    STATUS          current
    DESCRIPTION     
            "This attribute defines the name of the total power consumption sensor."
    ::= { sunHwMonTotalPowerConsumption 1 }

sunHwMonTotalPowerConsumptionSensorParentFruIndex OBJECT-TYPE
    SYNTAX          Integer32 (1..2147483647)
    MAX-ACCESS      read-only
    STATUS          current
    DESCRIPTION     
            "This attribute defines the index of the field replaceable unit (FRU)
             which contains the sensor."
    ::= { sunHwMonTotalPowerConsumption 2 }

sunHwMonTotalPowerConsumptionSensorParentFruName OBJECT-TYPE
    SYNTAX          DisplayString (SIZE(0..255))
    MAX-ACCESS      read-only
    STATUS          current
    DESCRIPTION     
            "This attribute defines the name of the field replaceable unit (FRU)
             which contains the sensor."
    ::= { sunHwMonTotalPowerConsumption 3 }

sunHwMonTotalPowerConsumptionSensorAlarmStatus OBJECT-TYPE
    SYNTAX          SunAlarmStatusTC
    MAX-ACCESS      read-only
    STATUS          current
    DESCRIPTION     
            "This attribute defines the status of the total power consumption sensor."
    ::= { sunHwMonTotalPowerConsumption 4 }

sunHwMonTotalPowerConsumptionSensorStateDescr OBJECT-TYPE
    SYNTAX          DisplayString (SIZE(0..255))
    MAX-ACCESS      read-only
    STATUS          current
    DESCRIPTION     
            "This attribute defines the state of the total power consumption sensor."
    ::= { sunHwMonTotalPowerConsumption 5 }

sunHwMonTotalPowerConsumptionSensorCurrentValue OBJECT-TYPE
    SYNTAX          Integer32 (-2147483647..2147483647)
    MAX-ACCESS      read-only
    STATUS          current
    DESCRIPTION     
            "This attribute defines the current reading of the total power consumption sensor."
    ::= { sunHwMonTotalPowerConsumption 6 }

sunHwMonTotalPowerConsumptionSensorBaseUnit OBJECT-TYPE
    SYNTAX          SunBaseUnitsTC
    MAX-ACCESS      read-only
    STATUS          current
    DESCRIPTION     
            "This attribute defines the units used to express the current reading 
             as well as the various thresholds of the total power consumption sensor."
    ::= { sunHwMonTotalPowerConsumption 7 }

sunHwMonTotalPowerConsumptionSensorExponent OBJECT-TYPE
    SYNTAX          Integer32 (-2147483647..2147483647)
    MAX-ACCESS      read-only
    STATUS          current
    DESCRIPTION     
            "This attribute defines the exponent that needs to be applied to the 
             units used to express the current reading as well as the various 
             thresholds of the total power consumption sensor."
    ::= { sunHwMonTotalPowerConsumption 8 }

sunHwMonTotalPowerConsumptionSensorUpperNonRecoverableThreshold OBJECT-TYPE
    SYNTAX          Integer32 (-2147483647..2147483647)
    MAX-ACCESS      read-only
    STATUS          current
    DESCRIPTION     
            "This attribute defines the upper threshold at which a nonrecoverable
             condition occurs."
    ::= { sunHwMonTotalPowerConsumption 9 }

sunHwMonTotalPowerConsumptionSensorUpperCriticalThreshold OBJECT-TYPE
    SYNTAX          Integer32 (-2147483647..2147483647)
    MAX-ACCESS      read-only
    STATUS          current
    DESCRIPTION     
            "This attribute defines the upper threshold at which a critical
             condition occurs."
    ::= { sunHwMonTotalPowerConsumption 10 }

sunHwMonTotalPowerConsumptionSensorUpperNonCriticalThreshold OBJECT-TYPE
    SYNTAX          Integer32 (-2147483647..2147483647)
    MAX-ACCESS      read-only
    STATUS          current
    DESCRIPTION     
            "This attribute defines the upper threshold at which a noncritical
             condition occurs."
    ::= { sunHwMonTotalPowerConsumption 11 }

sunHwMonTotalPowerConsumptionSensorEnabledThresholds OBJECT-TYPE
    SYNTAX          SunNumericSensorEnabledThresholdsTC
    MAX-ACCESS      read-only
    STATUS          current
    DESCRIPTION     
            "This attribute defines the thresholds enabled for this current
             sensor."
    ::= { sunHwMonTotalPowerConsumption 12 }

sunHwMonMibConformances OBJECT IDENTIFIER
    ::= { sunHwMonMIB 2 }

sunHwMonMibCompliances OBJECT IDENTIFIER
    ::= { sunHwMonMibConformances 1 }

sunHwMonMibGroups OBJECT IDENTIFIER
    ::= { sunHwMonMibConformances 2 }

sunHwMonMibObjectGroups OBJECT IDENTIFIER
    ::= { sunHwMonMibGroups 1 }

sunHwMonMibSensorGroup OBJECT IDENTIFIER
    ::= { sunHwMonMibObjectGroups 7 }

sunHwMonMibVoltageGroup OBJECT IDENTIFIER
    ::= { sunHwMonMibSensorGroup 2 }

sunHwMonMibCurrentGroup OBJECT IDENTIFIER
    ::= { sunHwMonMibSensorGroup 3 }

sunHwMonMibPowerDeviceGroup OBJECT IDENTIFIER
    ::= { sunHwMonMibSensorGroup 4 }

sunHwMonMibCoolingDeviceGroup OBJECT IDENTIFIER
    ::= { sunHwMonMibSensorGroup 5 }

sunHwMonMibTemperatureGroup OBJECT IDENTIFIER
    ::= { sunHwMonMibSensorGroup 6 }

sunHwMonMibProcessorGroup OBJECT IDENTIFIER
    ::= { sunHwMonMibSensorGroup 7 }

sunHwMonMibMemoryGroup OBJECT IDENTIFIER
    ::= { sunHwMonMibSensorGroup 8 }

sunHwMonMibHardDriveGroup OBJECT IDENTIFIER
    ::= { sunHwMonMibSensorGroup 9 }

sunHwMonMibIOGroup OBJECT IDENTIFIER
    ::= { sunHwMonMibSensorGroup 10 }

sunHwMonMibSlotOrConnectorGroup OBJECT IDENTIFIER
    ::= { sunHwMonMibSensorGroup 11 }

sunHwMonMibOtherSensorGroup OBJECT IDENTIFIER
    ::= { sunHwMonMibSensorGroup 12 }

sunHwMonMibIndicatorGroup OBJECT IDENTIFIER
    ::= { sunHwMonMibObjectGroups 8 }

sunHwMonMibProductGroup OBJECT-GROUP
    OBJECTS         { sunHwMonProductName, sunHwMonProductType, 
                      sunHwMonProductPartNumber, 
                      sunHwMonProductSerialNumber, 
                      sunHwMonProductManufacturer, 
                      sunHwMonProductSlotNumber, sunHwMonProductUUID, 
                      sunHwMonProductBiosVersion }
    STATUS          current
    DESCRIPTION     
            "The collection of objects used to define the Sun server product."
    ::= { sunHwMonMibObjectGroups 1 }

sunHwMonMibChassisGroup OBJECT-GROUP
    OBJECTS         { sunHwMonProductChassisName, 
                      sunHwMonProductChassisPartNumber, 
                      sunHwMonProductChassisSerialNumber, 
                      sunHwMonProductChassisManufacturer }
    STATUS          current
    DESCRIPTION     
            "The collection of objects used to define the Sun server chassis."
    ::= { sunHwMonMibObjectGroups 2 }

sunHwMonMibSPGroup OBJECT-GROUP
    OBJECTS         { sunHwMonSPSerialNumber, sunHwMonSPManufacturer, 
                      sunHwMonSPFWVersion, sunHwMonSPMacAddress, 
                      sunHwMonSPIPAddress, sunHwMonSPNetMask, 
                      sunHwMonSPDefaultGateway, sunHwMonSPIPMode, 
                      sunHwMonSPURLToLaunch, sunHwMonSPSystemIdentifier }
    STATUS          current
    DESCRIPTION     
            "The collection of objects used to define the Sun server service processor."
    ::= { sunHwMonMibObjectGroups 3 }

sunHwMonMibMibGroup OBJECT-GROUP
    OBJECTS         { sunHwMonMibVersion }
    STATUS          current
    DESCRIPTION     
            "The collection of objects used to define the version of SUN-HW-MONITORING-MIB."
    ::= { sunHwMonMibObjectGroups 4 }

sunHwMonMibAgentSoftwareGroup OBJECT-GROUP
    OBJECTS         { sunHwMonAgentVersion, 
                      sunHwMonAgentSPConnectionStatus }
    STATUS          current
    DESCRIPTION     
            "The collection of objects used to define the version of the Sun agent."
    ::= { sunHwMonMibObjectGroups 5 }

sunHwMonMibInventoryGroup OBJECT-GROUP
    OBJECTS         { sunHwMonFruName, sunHwMonFruType, sunHwMonFruDescr, 
                      sunHwMonFruPartNumber, sunHwMonFruSerialNumber, 
                      sunHwMonFruManufacturer, sunHwMonFruStatus, 
                      sunHwMonParentFruIndex, sunHwMonParentFruName }
    STATUS          current
    DESCRIPTION     
            "The collection of objects used to define the Sun server hardware inventory."
    ::= { sunHwMonMibObjectGroups 6 }

sunHwMonMibSensorAlarmStatusGroup OBJECT-GROUP
    OBJECTS         { sunHwMonCumulativeSensorAlarmStatus, 
                      sunHwMonCumulativeVoltageSensorAlarmStatus, 
                      sunHwMonCumulativeCurrentSensorAlarmStatus, 
                      sunHwMonCumulativePowerDeviceSensorAlarmStatus, 
                      sunHwMonCumulativeCoolingDeviceAlarmStatus, 
                      sunHwMonCumulativeTemperatureSensorAlarmStatus, 
                      sunHwMonCumulativeProcessorAlarmStatus, 
                      sunHwMonCumulativeMemoryAlarmStatus, 
                      sunHwMonCumulativeHardDriveAlarmStatus, 
                      sunHwMonCumulativeIOAlarmStatus, 
                      sunHwMonCumulativeSlotOrConnectorAlarmStatus, 
                      sunHwMonCumulativeOtherSensorAlarmStatus }
    STATUS          current
    DESCRIPTION     
            "The collection of objects used to define the cumulative status of the Sun 
             server sensor category and also the Sun server's sensors overall status."
    ::= { sunHwMonMibSensorGroup 1 }

sunHwMonMibNumericVoltageSensorGroup OBJECT-GROUP
    OBJECTS         { sunHwMonNumericVoltageSensorType, 
                      sunHwMonNumericVoltageSensorName, 
                      sunHwMonNumericVoltageSensorParentFruIndex, 
                      sunHwMonNumericVoltageSensorParentFruName, 
                      sunHwMonNumericVoltageSensorAlarmStatus, 
                      sunHwMonNumericVoltageSensorStateDescr, 
                      sunHwMonNumericVoltageSensorCurrentValue, 
                      sunHwMonNumericVoltageSensorBaseUnit, 
                      sunHwMonNumericVoltageSensorExponent, 
                      sunHwMonNumericVoltageSensorUpperNonRecoverableThreshold, 
                      sunHwMonNumericVoltageSensorUpperCriticalThreshold, 
                      sunHwMonNumericVoltageSensorUpperNonCriticalThreshold, 
                      sunHwMonNumericVoltageSensorLowerNonRecoverableThreshold, 
                      sunHwMonNumericVoltageSensorLowerCriticalThreshold, 
                      sunHwMonNumericVoltageSensorLowerNonCriticalThreshold, 
                      sunHwMonNumericVoltageSensorEnabledThresholds }
    STATUS          current
    DESCRIPTION     
            "The collection of objects used to define the Sun server's numeric voltage sensors properties."
    ::= { sunHwMonMibVoltageGroup 1 }

sunHwMonMibDiscreteVoltageSensorGroup OBJECT-GROUP
    OBJECTS         { sunHwMonDiscreteVoltageSensorType, 
                      sunHwMonDiscreteVoltageSensorName, 
                      sunHwMonDiscreteVoltageSensorParentFruIndex, 
                      sunHwMonDiscreteVoltageSensorParentFruName, 
                      sunHwMonDiscreteVoltageSensorAlarmStatus, 
                      sunHwMonDiscreteVoltageSensorStateDescr }
    STATUS          current
    DESCRIPTION     
            "The collection of objects used to define the Sun server's discrete voltage sensors properties."
    ::= { sunHwMonMibVoltageGroup 2 }

sunHwMonMibNumericCurrentSensorGroup OBJECT-GROUP
    OBJECTS         { sunHwMonNumericCurrentSensorType, 
                      sunHwMonNumericCurrentSensorName, 
                      sunHwMonNumericCurrentSensorParentFruIndex, 
                      sunHwMonNumericCurrentSensorParentFruName, 
                      sunHwMonNumericCurrentSensorAlarmStatus, 
                      sunHwMonNumericCurrentSensorStateDescr, 
                      sunHwMonNumericCurrentSensorCurrentValue, 
                      sunHwMonNumericCurrentSensorBaseUnit, 
                      sunHwMonNumericCurrentSensorExponent, 
                      sunHwMonNumericCurrentSensorUpperNonRecoverableThreshold, 
                      sunHwMonNumericCurrentSensorUpperCriticalThreshold, 
                      sunHwMonNumericCurrentSensorUpperNonCriticalThreshold, 
                      sunHwMonNumericCurrentSensorLowerNonRecoverableThreshold, 
                      sunHwMonNumericCurrentSensorLowerCriticalThreshold, 
                      sunHwMonNumericCurrentSensorLowerNonCriticalThreshold, 
                      sunHwMonNumericCurrentSensorEnabledThresholds }
    STATUS          current
    DESCRIPTION     
            "The collection of objects used to define the Sun server's numeric current sensors properties."
    ::= { sunHwMonMibCurrentGroup 1 }

sunHwMonMibDiscreteCurrentSensorGroup OBJECT-GROUP
    OBJECTS         { sunHwMonDiscreteCurrentSensorType, 
                      sunHwMonDiscreteCurrentSensorName, 
                      sunHwMonDiscreteCurrentSensorParentFruIndex, 
                      sunHwMonDiscreteCurrentSensorParentFruName, 
                      sunHwMonDiscreteCurrentSensorAlarmStatus, 
                      sunHwMonDiscreteCurrentSensorStateDescr }
    STATUS          current
    DESCRIPTION     
            "The collection of objects used to define the Sun server's discrete current sensors properties."
    ::= { sunHwMonMibCurrentGroup 2 }

sunHwMonMibNumericPowerDeviceSensorGroup OBJECT-GROUP
    OBJECTS         { sunHwMonNumericPowerDeviceSensorType, 
                      sunHwMonNumericPowerDeviceSensorName, 
                      sunHwMonNumericPowerDeviceSensorParentFruIndex, 
                      sunHwMonNumericPowerDeviceSensorParentFruName, 
                      sunHwMonNumericPowerDeviceSensorAlarmStatus, 
                      sunHwMonNumericPowerDeviceSensorStateDescr, 
                      sunHwMonNumericPowerDeviceSensorCurrentValue, 
                      sunHwMonNumericPowerDeviceSensorBaseUnit, 
                      sunHwMonNumericPowerDeviceSensorExponent, 
                      sunHwMonNumericPowerDeviceSensorUpperNonRecoverableThreshold, 
                      sunHwMonNumericPowerDeviceSensorUpperCriticalThreshold, 
                      sunHwMonNumericPowerDeviceSensorUpperNonCriticalThreshold, 
                      sunHwMonNumericPowerDeviceSensorLowerNonRecoverableThreshold, 
                      sunHwMonNumericPowerDeviceSensorLowerCriticalThreshold, 
                      sunHwMonNumericPowerDeviceSensorLowerNonCriticalThreshold, 
                      sunHwMonNumericPowerDeviceSensorEnabledThresholds }
    STATUS          current
    DESCRIPTION     
            "The collection of objects used to define the Sun server's numeric power device sensors properties."
    ::= { sunHwMonMibPowerDeviceGroup 1 }

sunHwMonMibDiscretePowerDeviceSensorGroup OBJECT-GROUP
    OBJECTS         { sunHwMonDiscretePowerDeviceSensorType, 
                      sunHwMonDiscretePowerDeviceSensorName, 
                      sunHwMonDiscretePowerDeviceSensorParentFruIndex, 
                      sunHwMonDiscretePowerDeviceSensorParentFruName, 
                      sunHwMonDiscretePowerDeviceSensorAlarmStatus, 
                      sunHwMonDiscretePowerDeviceSensorStateDescr }
    STATUS          current
    DESCRIPTION     
            "The collection of objects used to define the Sun server's discrete power device sensors properties."
    ::= { sunHwMonMibPowerDeviceGroup 2 }

sunHwMonMibNumericCoolingDeviceSensorGroup OBJECT-GROUP
    OBJECTS         { sunHwMonNumericCoolingDeviceSensorType, 
                      sunHwMonNumericCoolingDeviceSensorName, 
                      sunHwMonNumericCoolingDeviceSensorParentFruIndex, 
                      sunHwMonNumericCoolingDeviceSensorParentFruName, 
                      sunHwMonNumericCoolingDeviceSensorAlarmStatus, 
                      sunHwMonNumericCoolingDeviceSensorStateDescr, 
                      sunHwMonNumericCoolingDeviceSensorCurrentValue, 
                      sunHwMonNumericCoolingDeviceSensorBaseUnit, 
                      sunHwMonNumericCoolingDeviceSensorExponent, 
                      sunHwMonNumericCoolingDeviceSensorUpperNonRecoverableThreshold, 
                      sunHwMonNumericCoolingDeviceSensorUpperCriticalThreshold, 
                      sunHwMonNumericCoolingDeviceSensorUpperNonCriticalThreshold, 
                      sunHwMonNumericCoolingDeviceSensorLowerNonRecoverableThreshold, 
                      sunHwMonNumericCoolingDeviceSensorLowerCriticalThreshold, 
                      sunHwMonNumericCoolingDeviceSensorLowerNonCriticalThreshold, 
                      sunHwMonNumericCoolingDeviceSensorEnabledThresholds }
    STATUS          current
    DESCRIPTION     
            "The collection of objects used to define the Sun server's numeric cooling device sensors properties."
    ::= { sunHwMonMibCoolingDeviceGroup 1 }

sunHwMonMibDiscreteCoolingDeviceSensorGroup OBJECT-GROUP
    OBJECTS         { sunHwMonDiscreteCoolingDeviceSensorType, 
                      sunHwMonDiscreteCoolingDeviceSensorName, 
                      sunHwMonDiscreteCoolingDeviceSensorParentFruIndex, 
                      sunHwMonDiscreteCoolingDeviceSensorParentFruName, 
                      sunHwMonDiscreteCoolingDeviceSensorAlarmStatus, 
                      sunHwMonDiscreteCoolingDeviceSensorStateDescr }
    STATUS          current
    DESCRIPTION     
            "The collection of objects used to define the Sun server's discrete cooling device sensors properties."
    ::= { sunHwMonMibCoolingDeviceGroup 2 }

sunHwMonMibNumericTemperatureSensorGroup OBJECT-GROUP
    OBJECTS         { sunHwMonNumericTemperatureSensorType, 
                      sunHwMonNumericTemperatureSensorName, 
                      sunHwMonNumericTemperatureSensorParentFruIndex, 
                      sunHwMonNumericTemperatureSensorParentFruName, 
                      sunHwMonNumericTemperatureSensorAlarmStatus, 
                      sunHwMonNumericTemperatureSensorStateDescr, 
                      sunHwMonNumericTemperatureSensorCurrentValue, 
                      sunHwMonNumericTemperatureSensorBaseUnit, 
                      sunHwMonNumericTemperatureSensorExponent, 
                      sunHwMonNumericTemperatureSensorUpperNonRecoverableThreshold, 
                      sunHwMonNumericTemperatureSensorUpperCriticalThreshold, 
                      sunHwMonNumericTemperatureSensorUpperNonCriticalThreshold, 
                      sunHwMonNumericTemperatureSensorLowerNonRecoverableThreshold, 
                      sunHwMonNumericTemperatureSensorLowerCriticalThreshold, 
                      sunHwMonNumericTemperatureSensorLowerNonCriticalThreshold, 
                      sunHwMonNumericTemperatureSensorEnabledThresholds }
    STATUS          current
    DESCRIPTION     
            "The collection of objects used to define the Sun server's numeric temperature 
             sensors properties."
    ::= { sunHwMonMibTemperatureGroup 1 }

sunHwMonMibDiscreteTemperatureSensorGroup OBJECT-GROUP
    OBJECTS         { sunHwMonDiscreteTemperatureSensorType, 
                      sunHwMonDiscreteTemperatureSensorName, 
                      sunHwMonDiscreteTemperatureSensorParentFruIndex, 
                      sunHwMonDiscreteTemperatureSensorParentFruName, 
                      sunHwMonDiscreteTemperatureSensorAlarmStatus, 
                      sunHwMonDiscreteTemperatureSensorStateDescr }
    STATUS          current
    DESCRIPTION     
            "The collection of objects used to define the Sun server's discrete temperature 
             sensors properties."
    ::= { sunHwMonMibTemperatureGroup 2 }

sunHwMonMibNumericProcessorSensorGroup OBJECT-GROUP
    OBJECTS         { sunHwMonNumericProcessorSensorType, 
                      sunHwMonNumericProcessorSensorName, 
                      sunHwMonNumericProcessorSensorParentFruIndex, 
                      sunHwMonNumericProcessorSensorParentFruName, 
                      sunHwMonNumericProcessorSensorAlarmStatus, 
                      sunHwMonNumericProcessorSensorStateDescr, 
                      sunHwMonNumericProcessorSensorCurrentValue, 
                      sunHwMonNumericProcessorSensorBaseUnit, 
                      sunHwMonNumericProcessorSensorExponent, 
                      sunHwMonNumericProcessorSensorUpperNonRecoverableThreshold, 
                      sunHwMonNumericProcessorSensorUpperCriticalThreshold, 
                      sunHwMonNumericProcessorSensorUpperNonCriticalThreshold, 
                      sunHwMonNumericProcessorSensorLowerNonRecoverableThreshold, 
                      sunHwMonNumericProcessorSensorLowerCriticalThreshold, 
                      sunHwMonNumericProcessorSensorLowerNonCriticalThreshold, 
                      sunHwMonNumericProcessorSensorEnabledThresholds }
    STATUS          current
    DESCRIPTION     
            "The collection of objects used to define the Sun server's numeric processor sensors properties."
    ::= { sunHwMonMibProcessorGroup 1 }

sunHwMonMibDiscreteProcessorSensorGroup OBJECT-GROUP
    OBJECTS         { sunHwMonDiscreteProcessorSensorType, 
                      sunHwMonDiscreteProcessorSensorName, 
                      sunHwMonDiscreteProcessorSensorParentFruIndex, 
                      sunHwMonDiscreteProcessorSensorParentFruName, 
                      sunHwMonDiscreteProcessorSensorAlarmStatus, 
                      sunHwMonDiscreteProcessorSensorStateDescr }
    STATUS          current
    DESCRIPTION     
            "The collection of objects used to define the Sun server's discrete processor sensors properties."
    ::= { sunHwMonMibProcessorGroup 2 }

sunHwMonMibNumericMemorySensorGroup OBJECT-GROUP
    OBJECTS         { sunHwMonNumericMemorySensorType, 
                      sunHwMonNumericMemorySensorName, 
                      sunHwMonNumericMemorySensorParentFruIndex, 
                      sunHwMonNumericMemorySensorParentFruName, 
                      sunHwMonNumericMemorySensorAlarmStatus, 
                      sunHwMonNumericMemorySensorStateDescr, 
                      sunHwMonNumericMemorySensorCurrentValue, 
                      sunHwMonNumericMemorySensorBaseUnit, 
                      sunHwMonNumericMemorySensorExponent, 
                      sunHwMonNumericMemorySensorUpperNonRecoverableThreshold, 
                      sunHwMonNumericMemorySensorUpperCriticalThreshold, 
                      sunHwMonNumericMemorySensorUpperNonCriticalThreshold, 
                      sunHwMonNumericMemorySensorLowerNonRecoverableThreshold, 
                      sunHwMonNumericMemorySensorLowerCriticalThreshold, 
                      sunHwMonNumericMemorySensorLowerNonCriticalThreshold, 
                      sunHwMonNumericMemorySensorEnabledThresholds }
    STATUS          current
    DESCRIPTION     
            "The collection of objects used to define the Sun server's numeric memory sensors properties."
    ::= { sunHwMonMibMemoryGroup 1 }

sunHwMonMibDiscreteMemorySensorGroup OBJECT-GROUP
    OBJECTS         { sunHwMonDiscreteMemorySensorType, 
                      sunHwMonDiscreteMemorySensorName, 
                      sunHwMonDiscreteMemorySensorParentFruIndex, 
                      sunHwMonDiscreteMemorySensorParentFruName, 
                      sunHwMonDiscreteMemorySensorAlarmStatus, 
                      sunHwMonDiscreteMemorySensorStateDescr }
    STATUS          current
    DESCRIPTION     
            "The collection of objects used to define the Sun server's discrete memory sensors properties."
    ::= { sunHwMonMibMemoryGroup 2 }

sunHwMonMibNumericHardDriveSensorGroup OBJECT-GROUP
    OBJECTS         { sunHwMonNumericHardDriveSensorType, 
                      sunHwMonNumericHardDriveSensorName, 
                      sunHwMonNumericHardDriveSensorParentFruIndex, 
                      sunHwMonNumericHardDriveSensorParentFruName, 
                      sunHwMonNumericHardDriveSensorAlarmStatus, 
                      sunHwMonNumericHardDriveSensorStateDescr, 
                      sunHwMonNumericHardDriveSensorCurrentValue, 
                      sunHwMonNumericHardDriveSensorBaseUnit, 
                      sunHwMonNumericHardDriveSensorExponent, 
                      sunHwMonNumericHardDriveSensorUpperNonRecoverableThreshold, 
                      sunHwMonNumericHardDriveSensorUpperCriticalThreshold, 
                      sunHwMonNumericHardDriveSensorUpperNonCriticalThreshold, 
                      sunHwMonNumericHardDriveSensorLowerNonRecoverableThreshold, 
                      sunHwMonNumericHardDriveSensorLowerCriticalThreshold, 
                      sunHwMonNumericHardDriveSensorLowerNonCriticalThreshold, 
                      sunHwMonNumericHardDriveSensorEnabledThresholds }
    STATUS          current
    DESCRIPTION     
            "The collection of objects used to define the Sun server's numeric hard drive sensors properties."
    ::= { sunHwMonMibHardDriveGroup 1 }

sunHwMonMibDiscreteHardDriveSensorGroup OBJECT-GROUP
    OBJECTS         { sunHwMonDiscreteHardDriveSensorType, 
                      sunHwMonDiscreteHardDriveSensorName, 
                      sunHwMonDiscreteHardDriveSensorParentFruIndex, 
                      sunHwMonDiscreteHardDriveSensorParentFruName, 
                      sunHwMonDiscreteHardDriveSensorAlarmStatus, 
                      sunHwMonDiscreteHardDriveSensorStateDescr }
    STATUS          current
    DESCRIPTION     
            "The collection of objects used to define the Sun server's discrete hard drive sensors properties."
    ::= { sunHwMonMibHardDriveGroup 2 }

sunHwMonMibNumericIOSensorGroup OBJECT-GROUP
    OBJECTS         { sunHwMonNumericIOSensorType, 
                      sunHwMonNumericIOSensorName, 
                      sunHwMonNumericIOSensorParentFruIndex, 
                      sunHwMonNumericIOSensorParentFruName, 
                      sunHwMonNumericIOSensorAlarmStatus, 
                      sunHwMonNumericIOSensorStateDescr, 
                      sunHwMonNumericIOSensorCurrentValue, 
                      sunHwMonNumericIOSensorBaseUnit, 
                      sunHwMonNumericIOSensorExponent, 
                      sunHwMonNumericIOSensorUpperNonRecoverableThreshold, 
                      sunHwMonNumericIOSensorUpperCriticalThreshold, 
                      sunHwMonNumericIOSensorUpperNonCriticalThreshold, 
                      sunHwMonNumericIOSensorLowerNonRecoverableThreshold, 
                      sunHwMonNumericIOSensorLowerCriticalThreshold, 
                      sunHwMonNumericIOSensorLowerNonCriticalThreshold, 
                      sunHwMonNumericIOSensorEnabledThresholds }
    STATUS          current
    DESCRIPTION     
            "The collection of objects used to define the Sun server's numeric IO sensors properties."
    ::= { sunHwMonMibIOGroup 1 }

sunHwMonMibDiscreteIOSensorGroup OBJECT-GROUP
    OBJECTS         { sunHwMonDiscreteIOSensorType, 
                      sunHwMonDiscreteIOSensorName, 
                      sunHwMonDiscreteIOSensorParentFruIndex, 
                      sunHwMonDiscreteIOSensorParentFruName, 
                      sunHwMonDiscreteIOSensorAlarmStatus, 
                      sunHwMonDiscreteIOSensorStateDescr }
    STATUS          current
    DESCRIPTION     
            "The collection of objects used to define the Sun server's discrete IO sensors properties."
    ::= { sunHwMonMibIOGroup 2 }

sunHwMonMibNumericSlotOrConnectorSensorGroup OBJECT-GROUP
    OBJECTS         { sunHwMonNumericSlotOrConnectorSensorType, 
                      sunHwMonNumericSlotOrConnectorSensorName, 
                      sunHwMonNumericSlotOrConnectorSensorParentFruIndex, 
                      sunHwMonNumericSlotOrConnectorSensorParentFruName, 
                      sunHwMonNumericSlotOrConnectorSensorAlarmStatus, 
                      sunHwMonNumericSlotOrConnectorSensorStateDescr, 
                      sunHwMonNumericSlotOrConnectorSensorCurrentValue, 
                      sunHwMonNumericSlotOrConnectorSensorBaseUnit, 
                      sunHwMonNumericSlotOrConnectorSensorExponent, 
                      sunHwMonNumericSlotOrConnectorSensorUpperNonRecoverableThreshold, 
                      sunHwMonNumericSlotOrConnectorSensorUpperCriticalThreshold, 
                      sunHwMonNumericSlotOrConnectorSensorUpperNonCriticalThreshold, 
                      sunHwMonNumericSlotOrConnectorSensorLowerNonRecoverableThreshold, 
                      sunHwMonNumericSlotOrConnectorSensorLowerCriticalThreshold, 
                      sunHwMonNumericSlotOrConnectorSensorLowerNonCriticalThreshold, 
                      sunHwMonNumericSlotOrConnectorSensorEnabledThresholds }
    STATUS          current
    DESCRIPTION     
            "The collection of objects used to define the Sun server's numeric slot or connector sensors properties."
    ::= { sunHwMonMibSlotOrConnectorGroup 1 }

sunHwMonMibDiscreteSlotOrConnectorSensorGroup OBJECT-GROUP
    OBJECTS         { sunHwMonDiscreteSlotOrConnectorSensorType, 
                      sunHwMonDiscreteSlotOrConnectorSensorName, 
                      sunHwMonDiscreteSlotOrConnectorSensorParentFruIndex, 
                      sunHwMonDiscreteSlotOrConnectorSensorParentFruName, 
                      sunHwMonDiscreteSlotOrConnectorSensorAlarmStatus, 
                      sunHwMonDiscreteSlotOrConnectorSensorStateDescr }
    STATUS          current
    DESCRIPTION     
            "The collection of objects used to define the Sun server's discrete slot or connector sensors properties."
    ::= { sunHwMonMibSlotOrConnectorGroup 2 }

sunHwMonMibNumericOtherSensorGroup OBJECT-GROUP
    OBJECTS         { sunHwMonNumericOtherSensorType, 
                      sunHwMonNumericOtherSensorName, 
                      sunHwMonNumericOtherSensorParentFruIndex, 
                      sunHwMonNumericOtherSensorParentFruName, 
                      sunHwMonNumericOtherSensorAlarmStatus, 
                      sunHwMonNumericOtherSensorStateDescr, 
                      sunHwMonNumericOtherSensorCurrentValue, 
                      sunHwMonNumericOtherSensorBaseUnit, 
                      sunHwMonNumericOtherSensorExponent, 
                      sunHwMonNumericOtherSensorUpperNonRecoverableThreshold, 
                      sunHwMonNumericOtherSensorUpperCriticalThreshold, 
                      sunHwMonNumericOtherSensorUpperNonCriticalThreshold, 
                      sunHwMonNumericOtherSensorLowerNonRecoverableThreshold, 
                      sunHwMonNumericOtherSensorLowerCriticalThreshold, 
                      sunHwMonNumericOtherSensorLowerNonCriticalThreshold, 
                      sunHwMonNumericOtherSensorEnabledThresholds }
    STATUS          current
    DESCRIPTION     
            "The collection of objects used to define the properties of the Sun 
             server's numeric sensors that are not defined in other groups."
    ::= { sunHwMonMibOtherSensorGroup 1 }

sunHwMonMibDiscreteOtherSensorGroup OBJECT-GROUP
    OBJECTS         { sunHwMonDiscreteOtherSensorType, 
                      sunHwMonDiscreteOtherSensorName, 
                      sunHwMonDiscreteOtherSensorParentFruIndex, 
                      sunHwMonDiscreteOtherSensorParentFruName, 
                      sunHwMonDiscreteOtherSensorAlarmStatus, 
                      sunHwMonDiscreteOtherSensorStateDescr }
    STATUS          current
    DESCRIPTION     
            "The collection of objects used to define the properties of the Sun 
             server's discrete sensors that are not defined in other groups."
    ::= { sunHwMonMibOtherSensorGroup 2 }

sunHwMonMibIndicatorLocatorGroup OBJECT-GROUP
    OBJECTS         { sunHwMonIndicatorLocatorName, 
                      sunHwMonIndicatorLocatorCurrentStatus }
    STATUS          current
    DESCRIPTION     
            "The collection of objects used to define the Sun server's locator
             indicator properties."
    ::= { sunHwMonMibIndicatorGroup 1 }

sunHwMonMibIndicatorServiceGroup OBJECT-GROUP
    OBJECTS         { sunHwMonIndicatorServiceName, 
                      sunHwMonIndicatorServiceCurrentStatus }
    STATUS          current
    DESCRIPTION     
            "The collection of objects used to define the Sun server's service
             indicator properties."
    ::= { sunHwMonMibIndicatorGroup 2 }

sunHwMonMibIndicatorAllGroup OBJECT-GROUP
    OBJECTS         { sunHwMonIndicatorName, sunHwMonIndicatorType, 
                      sunHwMonIndicatorCurrentStatus }
    STATUS          current
    DESCRIPTION     
            "The collection of objects used to define the Sun server's
             indicators properties."
    ::= { sunHwMonMibIndicatorGroup 3 }

sunHwMonMibTotalPowerConsumption OBJECT-GROUP
    OBJECTS         { sunHwMonTotalPowerConsumptionSensorName, 
                      sunHwMonTotalPowerConsumptionSensorParentFruIndex, 
                      sunHwMonTotalPowerConsumptionSensorParentFruName, 
                      sunHwMonTotalPowerConsumptionSensorAlarmStatus, 
                      sunHwMonTotalPowerConsumptionSensorStateDescr, 
                      sunHwMonTotalPowerConsumptionSensorCurrentValue, 
                      sunHwMonTotalPowerConsumptionSensorBaseUnit, 
                      sunHwMonTotalPowerConsumptionSensorExponent, 
                      sunHwMonTotalPowerConsumptionSensorUpperNonRecoverableThreshold, 
                      sunHwMonTotalPowerConsumptionSensorUpperCriticalThreshold, 
                      sunHwMonTotalPowerConsumptionSensorUpperNonCriticalThreshold, 
                      sunHwMonTotalPowerConsumptionSensorEnabledThresholds }
    STATUS          current
    DESCRIPTION     
            "The collection of objects used to define the Sun server's total power consumption sensor properties."
    ::= { sunHwMonMibObjectGroups 9 }

sunHwMonMibCompliance MODULE-COMPLIANCE
    STATUS          current
    DESCRIPTION     
            "The compliance statement for agents implementing the
             SUN-HW-MONITORING-MIB extensions."

    MODULE          -- this module

        MANDATORY-GROUPS    { sunHwMonMibProductGroup, 
                      sunHwMonMibChassisGroup, sunHwMonMibSPGroup, 
                      sunHwMonMibMibGroup, sunHwMonMibAgentSoftwareGroup, 
                      sunHwMonMibInventoryGroup }

        GROUP       sunHwMonMibSensorAlarmStatusGroup
        DESCRIPTION 
            "This group should be implemented wherever possible."

        GROUP       sunHwMonMibNumericVoltageSensorGroup
        DESCRIPTION 
            "This group should be implemented wherever possible."

        GROUP       sunHwMonMibDiscreteVoltageSensorGroup
        DESCRIPTION 
            "This group should be implemented wherever possible."

        GROUP       sunHwMonMibNumericCurrentSensorGroup
        DESCRIPTION 
            "This group should be implemented wherever possible."

        GROUP       sunHwMonMibDiscreteCurrentSensorGroup
        DESCRIPTION 
            "This group should be implemented wherever possible."

        GROUP       sunHwMonMibNumericPowerDeviceSensorGroup
        DESCRIPTION 
            "This group should be implemented wherever possible."

        GROUP       sunHwMonMibDiscretePowerDeviceSensorGroup
        DESCRIPTION 
            "This group should be implemented wherever possible."

        GROUP       sunHwMonMibNumericCoolingDeviceSensorGroup
        DESCRIPTION 
            "This group should be implemented wherever possible."

        GROUP       sunHwMonMibDiscreteCoolingDeviceSensorGroup
        DESCRIPTION 
            "This group should be implemented wherever possible."

        GROUP       sunHwMonMibNumericTemperatureSensorGroup
        DESCRIPTION 
            "This group should be implemented wherever possible."

        GROUP       sunHwMonMibDiscreteTemperatureSensorGroup
        DESCRIPTION 
            "This group should be implemented wherever possible."

        GROUP       sunHwMonMibNumericProcessorSensorGroup
        DESCRIPTION 
            "This group should be implemented wherever possible."

        GROUP       sunHwMonMibDiscreteProcessorSensorGroup
        DESCRIPTION 
            "This group should be implemented wherever possible."

        GROUP       sunHwMonMibDiscreteMemorySensorGroup
        DESCRIPTION 
            "This group should be implemented wherever possible."

        GROUP       sunHwMonMibNumericMemorySensorGroup
        DESCRIPTION 
            "This group should be implemented wherever possible."

        GROUP       sunHwMonMibNumericHardDriveSensorGroup
        DESCRIPTION 
            "This group should be implemented wherever possible."

        GROUP       sunHwMonMibDiscreteHardDriveSensorGroup
        DESCRIPTION 
            "This group should be implemented wherever possible."

        GROUP       sunHwMonMibNumericIOSensorGroup
        DESCRIPTION 
            "This group should be implemented wherever possible."

        GROUP       sunHwMonMibDiscreteIOSensorGroup
        DESCRIPTION 
            "This group should be implemented wherever possible."

        GROUP       sunHwMonMibNumericSlotOrConnectorSensorGroup
        DESCRIPTION 
            "This group should be implemented wherever possible."

        GROUP       sunHwMonMibDiscreteSlotOrConnectorSensorGroup
        DESCRIPTION 
            "This group should be implemented wherever possible."

        GROUP       sunHwMonMibNumericOtherSensorGroup
        DESCRIPTION 
            "This group should be implemented wherever possible."

        GROUP       sunHwMonMibDiscreteOtherSensorGroup
        DESCRIPTION 
            "This group should be implemented wherever possible."

        GROUP       sunHwMonMibIndicatorLocatorGroup
        DESCRIPTION 
            "This group should be implemented wherever possible."

        GROUP       sunHwMonMibIndicatorServiceGroup
        DESCRIPTION 
            "This group should be implemented wherever possible."

        GROUP       sunHwMonMibIndicatorAllGroup
        DESCRIPTION 
            "This group should be implemented wherever possible."

        GROUP       sunHwMonMibTotalPowerConsumption
        DESCRIPTION 
            "This group should be implemented wherever possible."

    ::= { sunHwMonMibCompliances 1 }

END -- end of module SUN-HW-MONITORING-MIB.
