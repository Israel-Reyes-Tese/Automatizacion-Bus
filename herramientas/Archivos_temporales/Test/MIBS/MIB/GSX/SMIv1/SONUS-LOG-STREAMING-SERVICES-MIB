--
-- This SMIv1 module has been generated by smidump 0.2-cvs. Do not edit.
--

SONUS-LOG-STREAMING-SERVICES-MIB DEFINITIONS ::= BEGIN

IMPORTS
    Ipv6Address
        FROM IPV6-TC
    OBJECT-TYPE
        FROM RFC-1212
    TRAP-TYPE
        FROM RFC-1215
    Counter, IpAddress
        FROM RFC1155-SMI
    DateAndTime, RowStatus
        FROM SNMPv2-TC
    sonusEventClass, sonusEventDescription, sonusEventLevel, 
    sonusEventTime, sonusSequenceId, sonusShelfIndex, sonusSlotIndex
        FROM SONUS-COMMON-MIB
    sonusServicesMIBs
        FROM SONUS-SMI
    SonusAdminState, SonusLinkVersion, SonusName, SonusNameReference, 
    SonusServiceState, SonusShelfIndex, SonusSlotIndex, 
    SonusSoftwareVersion
        FROM SONUS-TC;

sonusLogServicesMIB OBJECT IDENTIFIER
    ::= { sonusServicesMIBs 22 }

-- sonusLogServicesMIB MODULE-IDENTITY
--     LAST-UPDATED    "201110090000Z"
--     ORGANIZATION    
--             "Sonus Networks, Inc."
--     CONTACT-INFO    
--             "   Customer Support    
--              Sonus Networks, Inc.
--              7 Technology Park Drive
--              Westford, MA 01886
--              USA
--              
--              Tel: 978-614-8100
--              Fax: 978-614-8609"
--     DESCRIPTION     
--             "The MIB module for Log Streamimng Configuration and Statistics."
--     ::= { sonusServicesMIBs 22 }


sonusLogServicesMibObjects OBJECT IDENTIFIER
    ::= { sonusLogServicesMIB 1 }

sonusLogServer OBJECT IDENTIFIER
    ::= { sonusLogServicesMibObjects 1 }

sonusLogServerNextIndex OBJECT-TYPE
    SYNTAX          INTEGER
    ACCESS          read-only
    STATUS          mandatory
    DESCRIPTION     
            "The next valid index to use when creating an entry in
             the sonusLogServerAdmnTable."
    ::= { sonusLogServer 1 }

sonusLogServerAdmnTable OBJECT-TYPE
    SYNTAX          SEQUENCE OF SonusLogServerAdmnEntry
    ACCESS          not-accessible
    STATUS          mandatory
    DESCRIPTION     
            " Log server ADMN table describes the configuration
             of each log server."
    ::= { sonusLogServer 2 }

sonusLogServerAdmnEntry OBJECT-TYPE
    SYNTAX          SonusLogServerAdmnEntry
    ACCESS          not-accessible
    STATUS          mandatory
    DESCRIPTION     
            "An entry in log server admin table."
    INDEX           { sonusLogServerAdmnIndex }
    ::= { sonusLogServerAdmnTable 1 }

SonusLogServerAdmnEntry ::=
    SEQUENCE {
        sonusLogServerAdmnIndex         INTEGER,
        sonusLogServerAdmnName          SonusName,
        sonusLogServerAdmnIpAddr        IpAddress,
        sonusLogServerAdmnState         SonusAdminState,
        sonusLogServerAdmnMode          SonusServiceState,
        sonusLogServerAdmnPortNumber    INTEGER,
        sonusLogServerAdmnUserName      DisplayString,
        sonusLogServerAdmnUserPassword  DisplayString,
        sonusLogServerAdmnPriority      INTEGER,
        sonusLogServerAdmnStateCntrl    INTEGER,
        sonusLogServerAdmnRowStatus     RowStatus,
        sonusLogServerAdmnIp6Addr       Ipv6Address,
        sonusLogServerAdmnIpVersion     INTEGER,
        sonusLogServerAdmnNetworkDelay  INTEGER,
        sonusLogServerAdmnTotalCdrSize  INTEGER,
        sonusLogServerAdmnCallRate      INTEGER
    }

sonusLogServerAdmnIndex OBJECT-TYPE
    SYNTAX          INTEGER
    ACCESS          read-only
    STATUS          mandatory
    DESCRIPTION     
            "Identifies target log server."
    ::= { sonusLogServerAdmnEntry 1 }

sonusLogServerAdmnName OBJECT-TYPE
    SYNTAX          SonusName
    ACCESS          read-write
    STATUS          mandatory
    DESCRIPTION     
            "Identifies log server name. A log server can be uniquely identified
             in a log server cluster by it's name."
    ::= { sonusLogServerAdmnEntry 2 }

sonusLogServerAdmnIpAddr OBJECT-TYPE
    SYNTAX          IpAddress
    ACCESS          read-write
    STATUS          mandatory
    DESCRIPTION     
            "IP address of log server. A reliable streaming link with log server 
             is established using this IP address."
    DEFVAL          { '00000000'H }
    ::= { sonusLogServerAdmnEntry 3 }

sonusLogServerAdmnState OBJECT-TYPE
    SYNTAX          SonusAdminState
    ACCESS          read-write
    STATUS          mandatory
    DESCRIPTION     
            "Identifies admin state of log server. Log server admin state must be enabled 
             before a reliable streaming link can be established with it. Log server
             must be disabled before it can be deleted."
    DEFVAL          { disabled }
    ::= { sonusLogServerAdmnEntry 4 }

sonusLogServerAdmnMode OBJECT-TYPE
    SYNTAX          SonusServiceState
    ACCESS          read-write
    STATUS          mandatory
    DESCRIPTION     
            "Log server when taken outOfService does not participate in log streaming.
             Log servers are created with a mode of inService. A log server must be 
             outOfService in order to change it's state to disabled."
    DEFVAL          { inService }
    ::= { sonusLogServerAdmnEntry 5 }

sonusLogServerAdmnPortNumber OBJECT-TYPE
    SYNTAX          INTEGER (1..65535)
    ACCESS          read-only
    STATUS          obsolete
    DESCRIPTION     
            "TCP port Number on Log server to which a log streaming link will be opened."
    DEFVAL          { 2653 }
    ::= { sonusLogServerAdmnEntry 6 }

sonusLogServerAdmnUserName OBJECT-TYPE
    SYNTAX          DisplayString (SIZE(0..23))
    ACCESS          read-write
    STATUS          mandatory
    DESCRIPTION     
            "Identifies the user name required to access log server."
    ::= { sonusLogServerAdmnEntry 7 }

sonusLogServerAdmnUserPassword OBJECT-TYPE
    SYNTAX          DisplayString (SIZE(4..16))
    ACCESS          read-write
    STATUS          mandatory
    DESCRIPTION     
            "The user password required to access log server."
    ::= { sonusLogServerAdmnEntry 8 }

sonusLogServerAdmnPriority OBJECT-TYPE
    SYNTAX          INTEGER (1..4)
    ACCESS          read-write
    STATUS          mandatory
    DESCRIPTION     
            "Identifies unique priority of log server. Priority '1' is the highest
             priority."
    ::= { sonusLogServerAdmnEntry 9 }

sonusLogServerAdmnStateCntrl OBJECT-TYPE
    SYNTAX          INTEGER { none(1), forced(2) }
    ACCESS          read-write
    STATUS          mandatory
    DESCRIPTION     
            "When 'forced' allows a log server to be taken outOfService 
             even if no standby accounting server exists.
             1. none 		- Default 
             2. forced		- Force the action."
    DEFVAL          { none }
    ::= { sonusLogServerAdmnEntry 10 }

sonusLogServerAdmnRowStatus OBJECT-TYPE
    SYNTAX          RowStatus
    ACCESS          read-write
    STATUS          mandatory
    DESCRIPTION     
            "Row status object for this table."
    ::= { sonusLogServerAdmnEntry 11 }

sonusLogServerAdmnIp6Addr OBJECT-TYPE
    SYNTAX          Ipv6Address
    ACCESS          read-write
    STATUS          mandatory
    DESCRIPTION     
            "IPV6 address of log server. A reliable streaming link with log server ."
    DEFVAL          { '00000000'H }
    ::= { sonusLogServerAdmnEntry 12 }

sonusLogServerAdmnIpVersion OBJECT-TYPE
    SYNTAX          INTEGER { afInet(2), afInet6(24) }
    ACCESS          read-only
    STATUS          mandatory
    DESCRIPTION     
            "IP address type  of log server. "
    ::= { sonusLogServerAdmnEntry 13 }

sonusLogServerAdmnNetworkDelay OBJECT-TYPE
    SYNTAX          INTEGER
    ACCESS          read-write
    STATUS          mandatory
    DESCRIPTION     
            "This configures the network delay for the log server"
    ::= { sonusLogServerAdmnEntry 14 }

sonusLogServerAdmnTotalCdrSize OBJECT-TYPE
    SYNTAX          INTEGER
    ACCESS          read-write
    STATUS          mandatory
    DESCRIPTION     
            "This configures total CDR Size log server"
    ::= { sonusLogServerAdmnEntry 15 }

sonusLogServerAdmnCallRate OBJECT-TYPE
    SYNTAX          INTEGER
    ACCESS          read-write
    STATUS          mandatory
    DESCRIPTION     
            "This configures the call rate for the log server"
    ::= { sonusLogServerAdmnEntry 16 }

sonusLogServerStatTable OBJECT-TYPE
    SYNTAX          SEQUENCE OF SonusLogServerStatEntry
    ACCESS          not-accessible
    STATUS          mandatory
    DESCRIPTION     
            "Log server STAT table describes the statistics
             of each log server,"
    ::= { sonusLogServicesMibObjects 2 }

sonusLogServerStatEntry OBJECT-TYPE
    SYNTAX          SonusLogServerStatEntry
    ACCESS          not-accessible
    STATUS          mandatory
    DESCRIPTION     
            "An entry in log server stat table."
    INDEX           { sonusLogServerStatIndex }
    ::= { sonusLogServerStatTable 1 }

SonusLogServerStatEntry ::=
    SEQUENCE {
        sonusLogServerStatIndex         INTEGER,
        sonusLogServerStatHostName      DisplayString,
        sonusLogServerStatIpAddr        IpAddress,
        sonusLogServerStatRedundancyStatus  INTEGER,
        sonusLogServerStatActivationTime DateAndTime,
        sonusLogServerStatSwVersionCode SonusSoftwareVersion,
        sonusLogServerStatCdrsSent      INTEGER,
        sonusLogServerStatEventsSent    INTEGER,
        sonusLogServerStatIp6Addr       Ipv6Address,
        sonusLogServerStatIpVersion     INTEGER
    }

sonusLogServerStatIndex OBJECT-TYPE
    SYNTAX          INTEGER
    ACCESS          read-only
    STATUS          mandatory
    DESCRIPTION     
            "Identifies target log server."
    ::= { sonusLogServerStatEntry 1 }

sonusLogServerStatHostName OBJECT-TYPE
    SYNTAX          DisplayString (SIZE(0..63))
    ACCESS          read-only
    STATUS          mandatory
    DESCRIPTION     
            "Identifies log server host name."
    ::= { sonusLogServerStatEntry 2 }

sonusLogServerStatIpAddr OBJECT-TYPE
    SYNTAX          IpAddress
    ACCESS          read-only
    STATUS          mandatory
    DESCRIPTION     
            "Identifies primary IP address of log server."
    DEFVAL          { '00000000'H }
    ::= { sonusLogServerStatEntry 3 }

sonusLogServerStatRedundancyStatus OBJECT-TYPE
    SYNTAX          INTEGER { unknown(0), active(1), standby(2) }
    ACCESS          read-only
    STATUS          mandatory
    DESCRIPTION     
            "Identifies redundancy status of this log server."
    DEFVAL          { unknown }
    ::= { sonusLogServerStatEntry 4 }

sonusLogServerStatActivationTime OBJECT-TYPE
    SYNTAX          DateAndTime
    ACCESS          read-only
    STATUS          mandatory
    DESCRIPTION     
            "Octet string that identifies the GMT time stamp of last
             time this server assumed active redundancy role."
    ::= { sonusLogServerStatEntry 5 }

sonusLogServerStatSwVersionCode OBJECT-TYPE
    SYNTAX          SonusSoftwareVersion
    ACCESS          read-only
    STATUS          mandatory
    DESCRIPTION     
            "Octet string that identifies the version of the runtime
             software application that is currently executing on this
             log server:
             
             	 Byte(s)  Code
             	 -------  ----
             	 0        major version
             	 1        minor version
             	 2        release version
             	 3        type (1:alpha, 2:beta, 3:release, 4:special)
             	 4-5      type number "
    ::= { sonusLogServerStatEntry 6 }

sonusLogServerStatCdrsSent OBJECT-TYPE
    SYNTAX          INTEGER
    ACCESS          read-only
    STATUS          mandatory
    DESCRIPTION     
            "Total number of Call Data Records sent to log server."
    ::= { sonusLogServerStatEntry 7 }

sonusLogServerStatEventsSent OBJECT-TYPE
    SYNTAX          INTEGER
    ACCESS          read-only
    STATUS          mandatory
    DESCRIPTION     
            "Total number of Events sent to log server."
    ::= { sonusLogServerStatEntry 8 }

sonusLogServerStatIp6Addr OBJECT-TYPE
    SYNTAX          Ipv6Address
    ACCESS          read-write
    STATUS          mandatory
    DESCRIPTION     
            "Identifies primary IPv6 address of log server."
    DEFVAL          { '00000000'H }
    ::= { sonusLogServerStatEntry 9 }

sonusLogServerStatIpVersion OBJECT-TYPE
    SYNTAX          INTEGER { afInet(2), afInet6(24) }
    ACCESS          read-only
    STATUS          mandatory
    DESCRIPTION     
            "Identifies primary IP address type  of log server."
    ::= { sonusLogServerStatEntry 10 }

sonusLogStreamStatTable OBJECT-TYPE
    SYNTAX          SEQUENCE OF SonusLogStreamStatEntry
    ACCESS          not-accessible
    STATUS          mandatory
    DESCRIPTION     
            "Log stream stat table describes the statistics
             of each log stream"
    ::= { sonusLogServicesMibObjects 3 }

sonusLogStreamStatEntry OBJECT-TYPE
    SYNTAX          SonusLogStreamStatEntry
    ACCESS          not-accessible
    STATUS          mandatory
    DESCRIPTION     
            "An entry in log stream stat table."
    INDEX           { sonusLogStreamStatShelfIndex, 
                      sonusLogStreamStatSlotIndex, 
                      sonusLogStreamStatLogicalStreamIndex, 
                      sonusLogStreamStatPhysicalStreamIndex }
    ::= { sonusLogStreamStatTable 1 }

SonusLogStreamStatEntry ::=
    SEQUENCE {
        sonusLogStreamStatShelfIndex    SonusShelfIndex,
        sonusLogStreamStatSlotIndex     SonusSlotIndex,
        sonusLogStreamStatLogicalStreamIndex    INTEGER,
        sonusLogStreamStatPhysicalStreamIndex     INTEGER,
        sonusLogStreamStatState         INTEGER,
        sonusLogStreamStatSocket        INTEGER,
        sonusLogStreamStatVersion       SonusLinkVersion,
        sonusLogStreamStatConnectionFailures    INTEGER,
        sonusLogStreamStatAuthFailures  INTEGER,
        sonusLogStreamStatLastFailureReason   INTEGER,
        sonusLogStreamStatEstablishmentTime   DateAndTime,
        sonusLogStreamStatLinkType      INTEGER,
        sonusLogStreamStatPortNumber    INTEGER
    }

sonusLogStreamStatShelfIndex OBJECT-TYPE
    SYNTAX          SonusShelfIndex
    ACCESS          read-only
    STATUS          mandatory
    DESCRIPTION     
            "Identifies the target shelf."
    ::= { sonusLogStreamStatEntry 1 }

sonusLogStreamStatSlotIndex OBJECT-TYPE
    SYNTAX          SonusSlotIndex
    ACCESS          read-only
    STATUS          mandatory
    DESCRIPTION     
            "Identifies the target MNS module within the shelf."
    ::= { sonusLogStreamStatEntry 2 }

sonusLogStreamStatLogicalStreamIndex OBJECT-TYPE
    SYNTAX          INTEGER
    ACCESS          read-only
    STATUS          mandatory
    DESCRIPTION     
            "Identifies the logical stream within MNS module."
    ::= { sonusLogStreamStatEntry 3 }

sonusLogStreamStatPhysicalStreamIndex OBJECT-TYPE
    SYNTAX          INTEGER
    ACCESS          read-only
    STATUS          mandatory
    DESCRIPTION     
            "Identifies the physical stream within MNS module."
    ::= { sonusLogStreamStatEntry 4 }

sonusLogStreamStatState OBJECT-TYPE
    SYNTAX          INTEGER { unknown(1), init(2), connect(3), 
                        connectWait(4), authReq(5), authReqWait(6), 
                        authRpy(7), authRpyWait(8), ready(9), 
                        inactive(10), recovery(11), shutdown(12) }
    ACCESS          read-only
    STATUS          mandatory
    DESCRIPTION     
            "Identifies the state of this log server."
    DEFVAL          { unknown }
    ::= { sonusLogStreamStatEntry 5 }

sonusLogStreamStatSocket OBJECT-TYPE
    SYNTAX          INTEGER
    ACCESS          read-only
    STATUS          mandatory
    DESCRIPTION     
            "Identifies the socket descriptor for this stream."
    DEFVAL          { -1 }
    ::= { sonusLogStreamStatEntry 6 }

sonusLogStreamStatVersion OBJECT-TYPE
    SYNTAX          SonusLinkVersion
    ACCESS          read-only
    STATUS          mandatory
    DESCRIPTION     
            "Identifies the version of this stream.
             
             Byte(s)  Code
             -------  ----
             0        major version
             1        minor version"
    ::= { sonusLogStreamStatEntry 7 }

sonusLogStreamStatConnectionFailures OBJECT-TYPE
    SYNTAX          INTEGER
    ACCESS          read-only
    STATUS          mandatory
    DESCRIPTION     
            "Identifies the total numebr of times connection to 
             log server was dropped."
    ::= { sonusLogStreamStatEntry 8 }

sonusLogStreamStatAuthFailures OBJECT-TYPE
    SYNTAX          INTEGER
    ACCESS          read-only
    STATUS          mandatory
    DESCRIPTION     
            "Identifies number of authentication failures."
    ::= { sonusLogStreamStatEntry 9 }

sonusLogStreamStatLastFailureReason OBJECT-TYPE
    SYNTAX          INTEGER { none(1), initError(2), healthCheck(3), 
                        authFailure(4), commLost(5), adminShutdown(6), 
                        remoteShutdown(7), insufficientResources(8), 
                        authTimeout(9) }
    ACCESS          read-only
    STATUS          mandatory
    DESCRIPTION     
            "Identifies the link failure reason."
    DEFVAL          { none }
    ::= { sonusLogStreamStatEntry 10 }

sonusLogStreamStatEstablishmentTime OBJECT-TYPE
    SYNTAX          DateAndTime
    ACCESS          read-only
    STATUS          mandatory
    DESCRIPTION     
            "Octet string that identifies the GMT time stamp 
             when link was established."
    ::= { sonusLogStreamStatEntry 11 }

sonusLogStreamStatLinkType OBJECT-TYPE
    SYNTAX          INTEGER { acct(1), event(2), trap(3) }
    ACCESS          read-only
    STATUS          mandatory
    DESCRIPTION     
            "Identifies the type of data sent on the link."
    ::= { sonusLogStreamStatEntry 12 }

sonusLogStreamStatPortNumber OBJECT-TYPE
    SYNTAX          INTEGER
    ACCESS          read-only
    STATUS          mandatory
    DESCRIPTION     
            "TCP port Number on GSX to which a log streaming link will be opened."
    DEFVAL          { -1 }
    ::= { sonusLogStreamStatEntry 13 }

sonusLogInterfaceAdmnObjects OBJECT IDENTIFIER
    ::= { sonusLogServicesMibObjects 4 }

sonusLogInterfaceAdmnLogDestination OBJECT-TYPE
    SYNTAX          INTEGER { nfs(1), stream(2) }
    ACCESS          read-write
    STATUS          mandatory
    DESCRIPTION     
            "Identifies the log interface destination
             1. nfs 	  - Log entries are sent to NFS server
             2. stream - Log entries are sent to STREAM server."
    DEFVAL          { nfs }
    ::= { sonusLogInterfaceAdmnObjects 1 }

sonusLogInterfaceAdmnTrapLogState OBJECT-TYPE
    SYNTAX          SonusAdminState
    ACCESS          read-write
    STATUS          mandatory
    DESCRIPTION     
            "State of trap log streaming."
    DEFVAL          { disabled }
    ::= { sonusLogInterfaceAdmnObjects 2 }

sonusLogInterfaceAdmnTrapLogAssociatedMgmtClientName OBJECT-TYPE
    SYNTAX          SonusNameReference
    ACCESS          read-write
    STATUS          mandatory
    DESCRIPTION     
            "Associated management client name for trap log streaming sequence numbers."
    ::= { sonusLogInterfaceAdmnObjects 3 }

sonusLogInterfaceAdmnNifGroupName OBJECT-TYPE
    SYNTAX          SonusNameReference
    ACCESS          read-write
    STATUS          mandatory
    DESCRIPTION     
            "The NIF Group which this Event log Manager streaming application port belongs to."
    ::= { sonusLogInterfaceAdmnObjects 4 }

sonusLogInterfaceAdmnNetworkAccess OBJECT-TYPE
    SYNTAX          INTEGER { none(1), nifgroup(2), anynif(3) }
    ACCESS          read-write
    STATUS          mandatory
    DESCRIPTION     
            "The Network access type of the Event log Manager streaming application. Option NONE is basically as good as disabled; NIFGROUP uses only the interfaces in the NIF group; ANYNIF would use any of the interfaces"
    DEFVAL          { nifgroup }
    ::= { sonusLogInterfaceAdmnObjects 5 }

sonusLogInterfaceStatusObjects OBJECT IDENTIFIER
    ::= { sonusLogServicesMibObjects 5 }

sonusLogInterfaceStreamStatConnectivityErrors OBJECT-TYPE
    SYNTAX          Counter
    ACCESS          read-only
    STATUS          mandatory
    DESCRIPTION     
            "Counts total number times GSX lost connectivity to 
             all configured Log servers."
    ::= { sonusLogInterfaceStatusObjects 1 }

sonusLogInterfaceStreamStatCdrsDropped OBJECT-TYPE
    SYNTAX          Counter
    ACCESS          read-only
    STATUS          mandatory
    DESCRIPTION     
            "Counts total number of Call Data Records dropped."
    ::= { sonusLogInterfaceStatusObjects 2 }

sonusLogInterfaceStreamStatSysEventsDropped OBJECT-TYPE
    SYNTAX          Counter
    ACCESS          read-only
    STATUS          mandatory
    DESCRIPTION     
            "Counts total number of SYS events dropped."
    ::= { sonusLogInterfaceStatusObjects 3 }

sonusLogInterfaceStreamStatDbgEventsDropped OBJECT-TYPE
    SYNTAX          Counter
    ACCESS          read-only
    STATUS          mandatory
    DESCRIPTION     
            "Counts total number of DBG events dropped."
    ::= { sonusLogInterfaceStatusObjects 4 }

sonusLogInterfaceStreamStatTrcEventsDropped OBJECT-TYPE
    SYNTAX          Counter
    ACCESS          read-only
    STATUS          mandatory
    DESCRIPTION     
            "Counts total number of TRC events dropped."
    ::= { sonusLogInterfaceStatusObjects 5 }

sonusLogInterfaceStreamStatSpooledCdrs OBJECT-TYPE
    SYNTAX          INTEGER
    ACCESS          read-only
    STATUS          mandatory
    DESCRIPTION     
            "Counts total number CDRs spooled while logging 
             interface is unavailable."
    ::= { sonusLogInterfaceStatusObjects 6 }

sonusLogInterfaceStreamStatSpooledSysEvents OBJECT-TYPE
    SYNTAX          INTEGER
    ACCESS          read-only
    STATUS          mandatory
    DESCRIPTION     
            "Counts total number SYS Events spooled while logging
             interface is unavailable."
    ::= { sonusLogInterfaceStatusObjects 7 }

sonusLogInterfaceStreamStatSpooledDbgEvents OBJECT-TYPE
    SYNTAX          INTEGER
    ACCESS          read-only
    STATUS          mandatory
    DESCRIPTION     
            "Counts total number DBG Events spooled while logging
             interface is unavailable."
    ::= { sonusLogInterfaceStatusObjects 8 }

sonusLogInterfaceStreamStatSpooledTrcEvents OBJECT-TYPE
    SYNTAX          INTEGER
    ACCESS          read-only
    STATUS          mandatory
    DESCRIPTION     
            "Counts total number TRC Events spooled while logging
             interface is unavailable."
    ::= { sonusLogInterfaceStatusObjects 9 }

sonusLogInterfaceCounterCtrl OBJECT-TYPE
    SYNTAX          INTEGER { unknown(1), reset(2), resetnfs(3), 
                        resetcurrent(4) }
    ACCESS          read-write
    STATUS          mandatory
    DESCRIPTION     
            "Reset the log interface counters.
             1.unknown  - invalid
             2.reset    - reset stats for the stream server
             3.resetnfs - reset stats for the nfs server
             4.resetcurrent - reset stats for the currently active server"
    ::= { sonusLogInterfaceStatusObjects 10 }

sonusLogInterfaceStatLogDestination OBJECT-TYPE
    SYNTAX          INTEGER { nfs(1), stream(2) }
    ACCESS          read-only
    STATUS          mandatory
    DESCRIPTION     
            "Identifies the log interface destination. The log destination
             status is changed once all client applications acknowledge 
             configured logging interface.
             	1. nfs 	  - Log entries are sent to NFS server
             	2. stream - Log entries are sent to STREAM server."
    ::= { sonusLogInterfaceStatusObjects 11 }

sonusLogInterfaceStreamStatTrapsDropped OBJECT-TYPE
    SYNTAX          Counter
    ACCESS          read-only
    STATUS          mandatory
    DESCRIPTION     
            "Counts total number of traps dropped."
    ::= { sonusLogInterfaceStatusObjects 12 }

sonusLogInterfaceStreamStatSpooledTraps OBJECT-TYPE
    SYNTAX          INTEGER
    ACCESS          read-only
    STATUS          mandatory
    DESCRIPTION     
            "Counts total number of traps spooled."
    ::= { sonusLogInterfaceStatusObjects 13 }

sonusLogInterfaceStreamStatTrapsSent OBJECT-TYPE
    SYNTAX          Counter
    ACCESS          read-only
    STATUS          mandatory
    DESCRIPTION     
            "Total number of Traps sent to log server."
    ::= { sonusLogInterfaceStatusObjects 14 }

sonusLogServicesMibNotifications OBJECT IDENTIFIER
    ::= { sonusLogServicesMIB 2 }

sonusLogServicesMibNotificationsPrefix OBJECT IDENTIFIER
    ::= { sonusLogServicesMibNotifications 0 }

sonusLogServicesAuthFailureNotification TRAP-TYPE
    ENTERPRISE      sonusLogServicesMibNotifications
    VARIABLES       { sonusShelfIndex, sonusSlotIndex, 
                      sonusLogServerAdmnName, sonusLogServerAdmnUserName, 
                      sonusEventDescription, sonusEventClass, 
                      sonusEventLevel, sonusSequenceId, sonusEventTime }
--     STATUS          mandatory
    DESCRIPTION     
            "This trap indicates that the user authentication failed for 
             specified Log server. The client module that requested
             authentication and user name is also included."
    ::= 1

sonusLogServicesLinkFailureNotification TRAP-TYPE
    ENTERPRISE      sonusLogServicesMibNotifications
    VARIABLES       { sonusShelfIndex, sonusSlotIndex, 
                      sonusLogServerAdmnName, sonusEventDescription, 
                      sonusEventClass, sonusEventLevel, sonusSequenceId, 
                      sonusEventTime }
--     STATUS          mandatory
    DESCRIPTION     
            "This trap indicates that the communication link between 
             Log server and client module has failed."
    ::= 2

sonusLogServicesLogSrvrUnreachableNotification TRAP-TYPE
    ENTERPRISE      sonusLogServicesMibNotifications
    VARIABLES       { sonusShelfIndex, sonusEventDescription, 
                      sonusEventClass, sonusEventLevel, sonusSequenceId, 
                      sonusEventTime }
--     STATUS          mandatory
    DESCRIPTION     
            "This trap indicates that all the Log servers in
             the cluster can not be reached. The log data will
             not be logged till a communication link is established
             with atleast one Log server in this cluster."
    ::= 3

sonusLogServicesLogSrvrReachableNotification TRAP-TYPE
    ENTERPRISE      sonusLogServicesMibNotifications
    VARIABLES       { sonusShelfIndex, sonusEventDescription, 
                      sonusEventClass, sonusEventLevel, sonusSequenceId, 
                      sonusEventTime }
--     STATUS          mandatory
    DESCRIPTION     
            "This trap indicates that at least one Log server
             in the cluster can be reached."
    ::= 4

sonusLogServicesLogSrvrIsActiveNotification TRAP-TYPE
    ENTERPRISE      sonusLogServicesMibNotifications
    VARIABLES       { sonusShelfIndex, sonusLogServerAdmnName, 
                      sonusEventDescription, sonusEventClass, 
                      sonusEventLevel, sonusSequenceId, sonusEventTime }
--     STATUS          mandatory
    DESCRIPTION     
            "This trap indicates that Log server is active
             for configured Log server cluster. All the log 
             entries are sent to active Log server."
    ::= 5

END -- end of module SONUS-LOG-STREAMING-SERVICES-MIB.
