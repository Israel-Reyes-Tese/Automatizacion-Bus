--
-- This SMIv1 module has been generated by smidump 0.2-cvs. Do not edit.
--

DIFF-SERV-MIB DEFINITIONS ::= BEGIN

IMPORTS
    ifIndex
        FROM IF-MIB
    InetAddress, InetAddressType
        FROM INET-ADDRESS-MIB
    OBJECT-TYPE
        FROM RFC-1212
    Counter
        FROM RFC1155-SMI
    mib-2
        FROM RFC1213-MIB
    zeroDotZero
        FROM SNMPv2-SMI
    RowPointer, RowStatus, TimeStamp
        FROM SNMPv2-TC;

diffServMib OBJECT IDENTIFIER
    ::= { mib-2 12345 }

-- diffServMib MODULE-IDENTITY
--     LAST-UPDATED    "200011190000Z"
--     ORGANIZATION    
--             "IETF Diffserv WG"
--     CONTACT-INFO    
--             "       Fred Baker
--              Cisco Systems
--              519 Lado Drive
--              Santa Barbara, CA 93111, USA
--              E-mail: fred@cisco.com
--              
--              
--              Kwok Ho Chan
--              Nortel Networks
--              600 Technology Park Drive
--              Billerica, MA 01821, USA
--              E-mail: khchan@nortelnetworks.com
--              
--              
--              Andrew Smith
--              Allegro Networks
--              6399 San Ignacio Ave
--              San Jose, CA 95119, USA
--              E-mail: andrew@allegronetworks.com"
--     DESCRIPTION     
--             "This MIB defines the objects necessary to  manage  a
--              device  that  uses the Differentiated Services Archi-
--              tecture  described  in  RFC  2475  and  the  Informal
--              Management  Model for DiffServ Routers in draft-ietf-
--              diffserv-model-05.txt."
--     REVISION        "200011190000Z"
--     DESCRIPTION     
--             "Initial version, published as RFC xxxx."
--     ::= { mib-2 12345 }


BurstSize ::=
    INTEGER (0..2147483647)

-- BurstSize ::= TEXTUAL-CONVENTION
--     DISPLAY-HINT    "d"
--     STATUS          mandatory
--     DESCRIPTION     
--             "The number of octets of IP Data, including  IP
--              Headers, that a stream may send without concern
--              for policing."
--     SYNTAX          INTEGER (0..2147483647)

Dscp ::=
    Gauge (4294967295 | 0..63)

-- Dscp ::= TEXTUAL-CONVENTION
--     DISPLAY-HINT    "d"
--     STATUS          mandatory
--     DESCRIPTION     
--             "The IP header Diffserv Code-Point that may  be  used
--              for  discriminating or marking a traffic stream.  The
--              value  -1  ( 4294967295 for Integer32 )  is  used  to
--              indicate a wildcard i.e. any value."
--     SYNTAX          Gauge (4294967295 | 0..63)

SixTupleClfrL4Port ::=
    Gauge (0..65535)

-- SixTupleClfrL4Port ::= TEXTUAL-CONVENTION
--     DISPLAY-HINT    "d"
--     STATUS          mandatory
--     DESCRIPTION     
--             "A value indicating a Layer-4 protocol port number."
--     SYNTAX          Gauge (0..65535)

IfDirection ::=
    INTEGER { inbound(1), outbound(2) }

-- IfDirection ::= TEXTUAL-CONVENTION
--     STATUS          mandatory
--     DESCRIPTION     
--             "Specifies a direction of data travel  on  an  inter-
--              face.  'inbound' traffic is operated on during recep-
--              tion from the interface, while 'outbound' traffic  is
--              operated on prior to transmission on the interface."
--     SYNTAX          INTEGER
--                       { inbound(1), outbound(2) }

StaticRowPointer ::=
    OBJECT IDENTIFIER

-- StaticRowPointer ::= TEXTUAL-CONVENTION
--     STATUS          mandatory
--     DESCRIPTION     
--             "Like   a   RowPointer,   this   textual   convention
--              represents  a pointer to a conceptual row.  The value
--              is the name of the instance of the  first  accessible
--              columnar object in the conceptual row.
--              
--              The additional semantics of this textual  convention,
--              relative to RowPointer, are related to the object the
--              pointer is pointing to.  The  pointed-to  object  may
--              have  more  than  one  parent  object pointing to it,
--              indicating the pointed-to object can be shared by one
--              or more parent objects.
--              
--              This additional semantics facilitates the creation of
--              instance-specific  objects by cloning, used by higher
--              level  configuration/provisioning  mechanisms.    The
--              objects  being cloned may either be special ones that
--              express    configuration    information    at     the
--              
--              
--              
--              
--              
--              
--              
--              implementation-specific  level,  or  simply instance-
--              specific ones that already  exist  at  the  time  the
--              cloning is done.  When an object with the syntax Sta-
--              ticRowPointer is cloned, the StaticRowPointer in  the
--              newly  cloned object is set to point to the same con-
--              ceptual row that the StaticRowPointer in the  cloned-
--              from object pointed to. The cloning operations may be
--              accomplished either with the  script-based  technique
--              defined  by  SNMP  Configuration, or by ordinary SNMP
--              Get and Set operations, or other mechanisms.
--              
--              Support of  this  additional  semantics  and  cloning
--              functionality is not required for conformance to this
--              MIB.  When the additional semantics is not supported,
--              this  textual  convention  behaves identically to the
--              RowPointer textual convention."
--     SYNTAX          OBJECT IDENTIFIER

diffServMIBObjects OBJECT IDENTIFIER
    ::= { diffServMib 1 }

diffServDataPath OBJECT IDENTIFIER
    ::= { diffServMIBObjects 1 }

diffServDataPathTable OBJECT-TYPE
    SYNTAX          SEQUENCE OF DiffServDataPathEntry
    ACCESS          not-accessible
    STATUS          mandatory
    DESCRIPTION     
            "The data path table defines the data paths  in  this
             device.   Each  data path is defined by the interface
             and traffic direction.  The first diffserv functional
             datapath element to handle traffic for this data path
             is defined by a RowPointer, diffServDataPathStart, in
             the entries of this table."
    ::= { diffServDataPath 1 }

diffServDataPathEntry OBJECT-TYPE
    SYNTAX          DiffServDataPathEntry
    ACCESS          not-accessible
    STATUS          mandatory
    DESCRIPTION     
            "An entry in the data path table describes  a  single
             diffserv datapath in this device."
    INDEX           { ifIndex, diffServDataPathIfDirection }
    ::= { diffServDataPathTable 1 }

DiffServDataPathEntry ::=
    SEQUENCE {
        diffServDataPathIfDirection     IfDirection,
        diffServDataPathStart           RowPointer,
        diffServDataPathStatus          RowStatus
    }

diffServDataPathIfDirection OBJECT-TYPE
    SYNTAX          IfDirection
    ACCESS          not-accessible
    STATUS          mandatory
    DESCRIPTION     
            "Specifies the direction for  which  this  data  path
             entry applies on this interface."
    ::= { diffServDataPathEntry 1 }

diffServDataPathStart OBJECT-TYPE
    SYNTAX          RowPointer
    ACCESS          read-write
    STATUS          mandatory
    DESCRIPTION     
            "This selects the first diffserv functional  datapath
             element  to  handle traffic for this data path.  This
             RowPointer should point to an instance of one of:
             
             
             
             
             
             
             
               diffServClfrEntry
               diffServMeterEntry
               diffServActionEntry
               diffServAlgDropEntry
               diffServQEntry
             
             A value of zeroDotZero in this attribute indicates no
             further Diffserv treatment is performed on traffic of
             this datapath.  The use of zeroDotZero is the  normal
             usage for the last functional datapath element of the
             current data path.
             
             If the row pointed to does not exist,  the  treatment
             is  as  if  this  attribute contains a value of zero-
             DotZero."
    ::= { diffServDataPathEntry 2 }

diffServDataPathStatus OBJECT-TYPE
    SYNTAX          RowStatus
    ACCESS          read-write
    STATUS          mandatory
    DESCRIPTION     
            "The  RowStatus  variable  controls  the  activation,
             deactivation,  or  deletion of a row/entry. Any writ-
             able variable may be  modified  whether  the  row  is
             active or notInService."
    ::= { diffServDataPathEntry 3 }

diffServClassifier OBJECT IDENTIFIER
    ::= { diffServMIBObjects 2 }

diffServClfrNextFree OBJECT-TYPE
    SYNTAX          Gauge
    ACCESS          read-only
    STATUS          mandatory
    DESCRIPTION     
            "This  object  yields  a  value  when  read  that  is
             currently unused for a diffServClfrId instance.  If a
             configuring system attempts to create a  new  row  in
             the  diffServClfrTable  using this value, that opera-
             tion will fail if the value  has,  in  the  meantime,
             been  used  to  create  another row that is currently
             valid."
    ::= { diffServClassifier 1 }

diffServClfrTable OBJECT-TYPE
    SYNTAX          SEQUENCE OF DiffServClfrEntry
    ACCESS          not-accessible
    STATUS          mandatory
    DESCRIPTION     
            "This table enumerates all  the  diffserv  classifier
             functional  datapath  elements  of  this device.  The
             actual  classification  definitions  are  defined  in
             diffServClfrElementTable  entries  belonging  to each
             classifier."
--     REFERENCE       
--             "[MODEL] section 4.1"
    ::= { diffServClassifier 2 }

diffServClfrEntry OBJECT-TYPE
    SYNTAX          DiffServClfrEntry
    ACCESS          not-accessible
    STATUS          mandatory
    DESCRIPTION     
            "An entry in the classifier table describes a  single
             classifier.  All classifier elements belonging to the
             same classifier uses the classifier's  diffServClfrId
             in thier diffServClfrElementClfrId attribute."
    INDEX           { diffServClfrId }
    ::= { diffServClfrTable 1 }

DiffServClfrEntry ::=
    SEQUENCE {
        diffServClfrId                  Gauge,
        diffServClfrStatus              RowStatus
    }

diffServClfrId OBJECT-TYPE
    SYNTAX          Gauge
    ACCESS          not-accessible
    STATUS          mandatory
    DESCRIPTION     
            "An index that enumerates the classifier entries. The
             set  of  such  identifiers  spans  the  whole  agent.
             Managers should obtain new values for row creation in
             this table by reading diffServClfrNextFree."
    ::= { diffServClfrEntry 1 }

diffServClfrStatus OBJECT-TYPE
    SYNTAX          RowStatus
    ACCESS          read-write
    STATUS          mandatory
    DESCRIPTION     
            "The  RowStatus  variable  controls  the  activation,
             deactivation,  or deletion of a classifier. Any writ-
             able variable may be  modified  whether  the  row  is
             active or notInService."
    ::= { diffServClfrEntry 2 }

diffServClfrElementNextFree OBJECT-TYPE
    SYNTAX          Gauge
    ACCESS          read-only
    STATUS          mandatory
    DESCRIPTION     
            "This  object  yields  a  value  when  read  that  is
             currently    unused   for   a   diffServClfrElementId
             instance.  If a configuring system attempts to create
             a  new row in the diffServClfrElementTable using this
             value, that opera- tion will fail if the value   has,
             in   the   meantime,  been  used  to  create  another
             row that is currently valid."
    ::= { diffServClassifier 3 }

diffServClfrElementTable OBJECT-TYPE
    SYNTAX          SEQUENCE OF DiffServClfrElementEntry
    ACCESS          not-accessible
    STATUS          mandatory
    DESCRIPTION     
            "The classifier element table  enumerates  the  rela-
             tionship  between  classification patterns and subse-
             quent downstream diffserv  functional  datapath  ele-
             ments.   Classification  parameters  are  defined  by
             entries   of   filter   tables    pointed    to    by
             diffServClfrElementSpecific.   There  can  be  filter
             tables of different types, and  they  can  be  inter-
             mixed  and used within a classifier.  An example of a
             filter table defined in this  MIB  is  diffServSixTu-
             pleClfrTable,  for IP Multi-Field Classifiers (MFCs).
             Filter tables for other filter types may  be  defined
             elsewhere."
--     REFERENCE       
--             "[MODEL] section 4.1"
    ::= { diffServClassifier 4 }

diffServClfrElementEntry OBJECT-TYPE
    SYNTAX          DiffServClfrElementEntry
    ACCESS          not-accessible
    STATUS          mandatory
    DESCRIPTION     
            "An entry in the classifier element table describes a
             single element of the classifier."
    INDEX           { diffServClfrElementClfrId, diffServClfrElementId }
    ::= { diffServClfrElementTable 1 }

DiffServClfrElementEntry ::=
    SEQUENCE {
        diffServClfrElementId           Gauge,
        diffServClfrElementClfrId       Gauge,
        diffServClfrElementOrder        Gauge,
        diffServClfrElementNext         RowPointer,
        diffServClfrElementSpecific     StaticRowPointer,
        diffServClfrElementStatus       RowStatus
    }

diffServClfrElementId OBJECT-TYPE
    SYNTAX          Gauge
    ACCESS          not-accessible
    STATUS          mandatory
    DESCRIPTION     
            "An index  that  enumerates  the  Classifier  Element
             entries.  The set of such identifiers spans the whole
             agent. Managers should  obtain  new  values  for  row
             creation     in     this     table     by     reading
             diffServClfrElementNextFree."
    ::= { diffServClfrElementEntry 1 }

diffServClfrElementClfrId OBJECT-TYPE
    SYNTAX          Gauge
    ACCESS          not-accessible
    STATUS          mandatory
    DESCRIPTION     
            "A classifier Id  identifies  which  classifier  this
             classifier  element  is  a part of.  This needs to be
             the value of diffServClfrId attribute for an existing
             row in diffServClfrTable."
    ::= { diffServClfrElementEntry 2 }

diffServClfrElementOrder OBJECT-TYPE
    SYNTAX          Gauge
    ACCESS          read-write
    STATUS          mandatory
    DESCRIPTION     
            "The relative order in which classifier elements  are
             applied:   higher  numbers  represent classifier ele-
             ment with  higher  precedence.   Classifier  elements
             with the same order  must  be  unambiguous  i.e. they
             must define non-overlapping patterns, and  are   con-
             sidered   to   be  applied   simultaneously   to  the
             traffic stream. Clas- sifier elements with  different
             
             
             
             
             
             
             
             order   may  overlap in their  filters:  the classif-
             ier element with the highest order  that  matches  is
             taken.
             
             On a given interface, there must be a complete  clas-
             sifier   in   place   at  all  times in   the ingress
             direction.  This means that there will always be  one
             or  more  filters that match every possible pat- tern
             that  could  be  presented  in  an  incoming  packet.
             There  is  no  such  requirement in the egress direc-
             tion."
    DEFVAL          { 0 }
    ::= { diffServClfrElementEntry 3 }

diffServClfrElementNext OBJECT-TYPE
    SYNTAX          RowPointer
    ACCESS          read-write
    STATUS          mandatory
    DESCRIPTION     
            "This attribute provides one branch  of  the  fan-out
             functionality  of  a  classifier described in [MODEL]
             section 4.1.
             
             This selects the next  diffserv  functional  datapath
             element  to  handle traffic for this data path.  This
             RowPointer should point to an instance of one of:
               diffServClfrEntry
               diffServMeterEntry
               diffServActionEntry
               diffServAlgDropEntry
               diffServQEntry
             
             A value of zeroDotZero in this attribute indicates no
             further Diffserv treatment is performed on traffic of
             this datapath.  The use of zeroDotZero is the  normal
             usage for the last functional datapath element of the
             current data path.
             
             If the row pointed to does not exist,  the  treatment
             is  as  if  this  attribute contains a value of zero-
             DotZero."
    ::= { diffServClfrElementEntry 4 }

diffServClfrElementSpecific OBJECT-TYPE
    SYNTAX          StaticRowPointer
    ACCESS          read-write
    STATUS          mandatory
    DESCRIPTION     
            "A pointer to a  valid  entry   in   another   table,
             filter table, that describes  the applicable classif-
             ication parameters, e.g.  an entry in  diffServSixTu-
             pleClfrTable.
             
             If the row pointed to does not exist, the  classifier
             element is ignored.
             
             The  value  zeroDotZero  is  interpreted   to   match
             anything  not matched by another classifier element -
             only one such entry may exist for each classifier."
    DEFVAL          { zeroDotZero }
    ::= { diffServClfrElementEntry 5 }

diffServClfrElementStatus OBJECT-TYPE
    SYNTAX          RowStatus
    ACCESS          read-write
    STATUS          mandatory
    DESCRIPTION     
            "The  RowStatus  variable  controls  the  activation,
             deactivation,   or  deletion of a classifier element.
             Any writ- able variable  may  be   modified   whether
             the  row  is active or notInService."
    ::= { diffServClfrElementEntry 6 }

diffServSixTupleClfrNextFree OBJECT-TYPE
    SYNTAX          Gauge
    ACCESS          read-only
    STATUS          mandatory
    DESCRIPTION     
            "This object yields a value when read that is currently unused
             
             
             
             
             
             
             
             for a diffServSixTupleClfrId instance.
             If a configuring system attempts to create a new row
             in the diffServSixTupleClfrTable using this value, that operation
             will fail if the value has, in the meantime, been used
             to create another row that is currently valid."
    ::= { diffServClassifier 5 }

diffServSixTupleClfrTable OBJECT-TYPE
    SYNTAX          SEQUENCE OF DiffServSixTupleClfrEntry
    ACCESS          not-accessible
    STATUS          mandatory
    DESCRIPTION     
            "A table of IP Six-Tuple  Classifier  filter  entries
             that a system may use to identify IP traffic."
--     REFERENCE       
--             "[MODEL] section 4.2.2"
    ::= { diffServClassifier 6 }

diffServSixTupleClfrEntry OBJECT-TYPE
    SYNTAX          DiffServSixTupleClfrEntry
    ACCESS          not-accessible
    STATUS          mandatory
    DESCRIPTION     
            "An IP Six-Tuple Classifier entry describes a  single
             filter."
    INDEX           { diffServSixTupleClfrId }
    ::= { diffServSixTupleClfrTable 1 }

DiffServSixTupleClfrEntry ::=
    SEQUENCE {
        diffServSixTupleClfrId          Gauge,
        diffServSixTupleClfrDstAddrType InetAddressType,
        diffServSixTupleClfrDstAddr     InetAddress,
        diffServSixTupleClfrDstAddrMask Gauge,
        diffServSixTupleClfrSrcAddrType InetAddressType,
        diffServSixTupleClfrSrcAddr     InetAddress,
        diffServSixTupleClfrSrcAddrMask Gauge,
        diffServSixTupleClfrDscp        Dscp,
        diffServSixTupleClfrProtocol    Gauge,
        diffServSixTupleClfrDstL4PortMin SixTupleClfrL4Port,
        diffServSixTupleClfrDstL4PortMax SixTupleClfrL4Port,
        diffServSixTupleClfrSrcL4PortMin SixTupleClfrL4Port,
        diffServSixTupleClfrSrcL4PortMax SixTupleClfrL4Port,
        diffServSixTupleClfrStatus      RowStatus
    }

diffServSixTupleClfrId OBJECT-TYPE
    SYNTAX          Gauge
    ACCESS          not-accessible
    STATUS          mandatory
    DESCRIPTION     
            "An index that enumerates the  Six  Tuple  Classifier
             filter  entries.   The  set of such identifiers spans
             the whole agent.  Managers should obtain  new  values
             for   row   creation   in   this   table  by  reading
             diffServSixTupleClfrNextFree."
    ::= { diffServSixTupleClfrEntry 1 }

diffServSixTupleClfrDstAddrType OBJECT-TYPE
    SYNTAX          InetAddressType
    ACCESS          read-write
    STATUS          mandatory
    DESCRIPTION     
            "The type of IP  destination  address  used  by  this
             classifier entry."
    ::= { diffServSixTupleClfrEntry 2 }

diffServSixTupleClfrDstAddr OBJECT-TYPE
    SYNTAX          InetAddress
    ACCESS          read-write
    STATUS          mandatory
    DESCRIPTION     
            "The IP address to match against the packet's  desti-
             nation IP address."
    ::= { diffServSixTupleClfrEntry 3 }

diffServSixTupleClfrDstAddrMask OBJECT-TYPE
    SYNTAX          Gauge
    ACCESS          read-write
    STATUS          mandatory
    DESCRIPTION     
            "The length of a mask for the matching of the  desti-
             nation  IP address.  Masks are constructed by setting
             bits in sequence from the most-significant bit  down-
             wards    for   diffServSixTupleClfrDstAddrMask   bits
             length. All other bits in the mask, up to the  number
             needed to fill the length of the address diffServSix-
             TupleClfrDstAddr are cleared to zero.  A zero bit  in
             the mask then means that the corresponding bit in the
             
             
             
             
             
             
             
             address always matches."
    DEFVAL          { 0 }
    ::= { diffServSixTupleClfrEntry 4 }

diffServSixTupleClfrSrcAddrType OBJECT-TYPE
    SYNTAX          InetAddressType
    ACCESS          read-write
    STATUS          mandatory
    DESCRIPTION     
            "The type of IP source address used by this  classif-
             ier entry."
    ::= { diffServSixTupleClfrEntry 5 }

diffServSixTupleClfrSrcAddr OBJECT-TYPE
    SYNTAX          InetAddress
    ACCESS          read-write
    STATUS          mandatory
    DESCRIPTION     
            "The IP  address  to  match  against  the  source  IP
             address of each packet."
    ::= { diffServSixTupleClfrEntry 6 }

diffServSixTupleClfrSrcAddrMask OBJECT-TYPE
    SYNTAX          Gauge
    ACCESS          read-write
    STATUS          mandatory
    DESCRIPTION     
            "The length of a mask for the matching of the  source
             IP address.  Masks are constructed by setting bits in
             sequence from the most-significant bit downwards  for
             diffServSixTupleClfrSrcAddrMask   bits   length.  All
             other bits in the mask, up to the  number  needed  to
             fill   the   length  of  the  address  diffServSixTu-
             pleClfrSrcAddr are cleared to zero.  A  zero  bit  in
             the mask then means that the corresponding bit in the
             address always matches."
    DEFVAL          { 0 }
    ::= { diffServSixTupleClfrEntry 7 }

diffServSixTupleClfrDscp OBJECT-TYPE
    SYNTAX          Dscp
    ACCESS          read-write
    STATUS          mandatory
    DESCRIPTION     
            "The value that the DSCP in the packet must  have  to
             match  this  entry.  A  value  of -1 indicates that a
             specific DSCP value has not been defined and thus all
             DSCP values are considered a match."
    DEFVAL          { 4294967295 }
    ::= { diffServSixTupleClfrEntry 8 }

diffServSixTupleClfrProtocol OBJECT-TYPE
    SYNTAX          Gauge (0..255)
    ACCESS          read-write
    STATUS          mandatory
    DESCRIPTION     
            "The IP protocol to match against the  IPv4  protocol
             number  or the IPv6 Next-Header number in the packet.
             A value of 255 means match all.   Note  the  protocol
             number  of  255  is reserved by IANA, and Next-Header
             number of 0 is used in IPv6."
    DEFVAL          { 255 }
    ::= { diffServSixTupleClfrEntry 9 }

diffServSixTupleClfrDstL4PortMin OBJECT-TYPE
    SYNTAX          SixTupleClfrL4Port
    ACCESS          read-write
    STATUS          mandatory
    DESCRIPTION     
            "The minimum value that the layer-4 destination  port
             number in the packet must have in order to match this
             classifier entry."
    DEFVAL          { 0 }
    ::= { diffServSixTupleClfrEntry 10 }

diffServSixTupleClfrDstL4PortMax OBJECT-TYPE
    SYNTAX          SixTupleClfrL4Port
    ACCESS          read-write
    STATUS          mandatory
    DESCRIPTION     
            "The maximum value that the layer-4 destination  port
             number in the packet must have in order to match this
             classifier entry. This value  must  be  equal  to  or
             greater  than  the  value specified for this entry in
             diffServSixTupleClfrDstL4PortMin."
    DEFVAL          { 65535 }
    ::= { diffServSixTupleClfrEntry 11 }

diffServSixTupleClfrSrcL4PortMin OBJECT-TYPE
    SYNTAX          SixTupleClfrL4Port
    ACCESS          read-write
    STATUS          mandatory
    DESCRIPTION     
            "The minimum  value  that  the  layer-4  source  port
             number in the packet must have in order to match this
             classifier entry."
    DEFVAL          { 0 }
    ::= { diffServSixTupleClfrEntry 12 }

diffServSixTupleClfrSrcL4PortMax OBJECT-TYPE
    SYNTAX          SixTupleClfrL4Port
    ACCESS          read-write
    STATUS          mandatory
    DESCRIPTION     
            "The maximum  value  that  the  layer-4  source  port
             number  in the packet must have in oder to match this
             classifier entry. This value  must  be  equal  to  or
             greater  than  the  value specified for this entry in
             diffServSixTupleClfrSrcL4PortMin."
    DEFVAL          { 65535 }
    ::= { diffServSixTupleClfrEntry 13 }

diffServSixTupleClfrStatus OBJECT-TYPE
    SYNTAX          RowStatus
    ACCESS          read-write
    STATUS          mandatory
    DESCRIPTION     
            "The  RowStatus  variable  controls  the  activation,
             deactivation,  or deletion of a classifier. Any writ-
             able variable may be  modified  whether  the  row  is
             active or notInService."
    ::= { diffServSixTupleClfrEntry 14 }

diffServMeter OBJECT IDENTIFIER
    ::= { diffServMIBObjects 3 }

diffServMeterNextFree OBJECT-TYPE
    SYNTAX          Gauge
    ACCESS          read-only
    STATUS          mandatory
    DESCRIPTION     
            "This  object  yields  a  value  when  read  that  is
             currently  unused for a diffServMeterId instance.  If
             a configuring system attempts to create a new row  in
             the  diffServMeterTable using this value, that opera-
             tion will fail if the value  has,  in  the  meantime,
             been  used  to  create  another row that is currently
             valid."
    ::= { diffServMeter 1 }

diffServMeterTable OBJECT-TYPE
    SYNTAX          SEQUENCE OF DiffServMeterEntry
    ACCESS          not-accessible
    STATUS          mandatory
    DESCRIPTION     
            "This table enumerates specific meters that a  system
             may use to police, or shape, a stream of traffic. The
             traffic stream to be metered  is  determined  by  the
             diffserv  functional  datapath element(s) upstream of
             the meter i.e. by the object(s) that  point  to  each
             entry in this table.  This may include all traffic on
             an interface.
             
             Specific meter details are to be found in table entry
             referenced by diffServMeterSpecific."
--     REFERENCE       
--             "[MODEL] section 5.1"
    ::= { diffServMeter 2 }

diffServMeterEntry OBJECT-TYPE
    SYNTAX          DiffServMeterEntry
    ACCESS          not-accessible
    STATUS          mandatory
    DESCRIPTION     
            "An entry in the meter table describes a single  con-
             formance level of a meter."
    INDEX           { diffServMeterId }
    ::= { diffServMeterTable 1 }

DiffServMeterEntry ::=
    SEQUENCE {
        diffServMeterId                 Gauge,
        diffServMeterSucceedNext        RowPointer,
        diffServMeterFailNext           RowPointer,
        diffServMeterSpecific           StaticRowPointer,
        diffServMeterStatus             RowStatus
    }

diffServMeterId OBJECT-TYPE
    SYNTAX          Gauge
    ACCESS          not-accessible
    STATUS          mandatory
    DESCRIPTION     
            "An index that enumerates the Meter entries. The  set
             of  such  identifiers spans the whole agent. Managers
             should obtain new values for  row  creation  in  this
             table by reading diffServMeterNextFree."
    ::= { diffServMeterEntry 1 }

diffServMeterSucceedNext OBJECT-TYPE
    SYNTAX          RowPointer
    ACCESS          read-write
    STATUS          mandatory
    DESCRIPTION     
            "If the traffic does conform, this selects  the  next
             diffserv   functional   datapath  element  to  handle
             traffic for this data path.  This  RowPointer  should
             point to an instance of one of:
               diffServClfrEntry
               diffServMeterEntry
               diffServActionEntry
               diffServAlgDropEntry
               diffServQEntry
             
             A value of zeroDotZero in this attribute indicates no
             further Diffserv treatment is performed on traffic of
             this datapath.  The use of zeroDotZero is the  normal
             usage for the last functional datapath element of the
             current data path.
             
             If the row pointed to does not exist,  the  treatment
             is  as  if  this  attribute contains a value of zero-
             DotZero."
    DEFVAL          { zeroDotZero }
    ::= { diffServMeterEntry 2 }

diffServMeterFailNext OBJECT-TYPE
    SYNTAX          RowPointer
    ACCESS          read-write
    STATUS          mandatory
    DESCRIPTION     
            "If the traffic does not conform,  this  selects  the
             next  diffserv  functional datapath element to handle
             traffic for this data path.  This  RowPointer  should
             point to an instance of one of:
               diffServClfrEntry
               diffServMeterEntry
               diffServActionEntry
               diffServAlgDropEntry
               diffServQEntry
             
             A value of zeroDotZero in this attribute indicates no
             further Diffserv treatment is performed on traffic of
             this datapath.  The use of zeroDotZero is the  normal
             usage for the last functional datapath element of the
             current data path.
             
             If the row pointed to does not exist,  the  treatment
             is  as  if  this  attribute contains a value of zero-
             DotZero."
    DEFVAL          { zeroDotZero }
    ::= { diffServMeterEntry 3 }

diffServMeterSpecific OBJECT-TYPE
    SYNTAX          StaticRowPointer
    ACCESS          read-write
    STATUS          mandatory
    DESCRIPTION     
            "This indicates the behaviour of the meter by  point-
             ing  to an entry containing detailed parameters. Note
             that entries in that specific table must  be  managed
             explicitly.
             
             For example, diffServMeterSpecific may  point  to  an
             entry  in  diffServTBMeterTable,  which  contains  an
             instance of a single set of Token Bucket parameters."
    ::= { diffServMeterEntry 4 }

diffServMeterStatus OBJECT-TYPE
    SYNTAX          RowStatus
    ACCESS          read-write
    STATUS          mandatory
    DESCRIPTION     
            "The  RowStatus  variable  controls  the  activation,
             
             
             
             
             
             
             
             deactivation,  or  deletion  of a meter. Any writable
             variable may be modified whether the row is active or
             notInService."
    ::= { diffServMeterEntry 5 }

diffServTBMeterNextFree OBJECT-TYPE
    SYNTAX          Gauge
    ACCESS          read-only
    STATUS          mandatory
    DESCRIPTION     
            "This  object  yields  a  value  when  read  that  is
             currently  unused  for  a diffServTBMeterId instance.
             If a configuring system attempts to create a new  row
             in  the  diffServTBMeterTable  using this value, that
             operation will fail if the value has,  in  the  mean-
             time,  been  used  to  create  another  row  that  is
             currently valid."
    ::= { diffServMeter 3 }

diffServTBMeterTable OBJECT-TYPE
    SYNTAX          SEQUENCE OF DiffServTBMeterEntry
    ACCESS          not-accessible
    STATUS          mandatory
    DESCRIPTION     
            "This table enumerates a single set of  token  bucket
             meter  parameters  that  a system may use to police a
             stream of traffic.  Such meters are modelled here  as
             having a single rate and a single burst size."
--     REFERENCE       
--             "[MODEL] section 5.1"
    ::= { diffServMeter 4 }

diffServTBMeterEntry OBJECT-TYPE
    SYNTAX          DiffServTBMeterEntry
    ACCESS          not-accessible
    STATUS          mandatory
    DESCRIPTION     
            "An entry that describes a single set of token bucket
             meter parameters."
    INDEX           { diffServTBMeterId }
    ::= { diffServTBMeterTable 1 }

DiffServTBMeterEntry ::=
    SEQUENCE {
        diffServTBMeterId               Gauge,
        diffServTBMeterType             INTEGER,
        diffServTBMeterRate             Gauge,
        diffServTBMeterBurstSize        BurstSize,
        diffServTBMeterInterval         Gauge,
        diffServTBMeterStatus           RowStatus
    }

diffServTBMeterId OBJECT-TYPE
    SYNTAX          Gauge
    ACCESS          not-accessible
    STATUS          mandatory
    DESCRIPTION     
            "An index that enumerates the  TBMeter  entries.  The
             set  of  such  identifiers  spans  the  whole  agent.
             Managers should obtain new values for row creation in
             this table by reading diffServTBMeterNextFree."
    ::= { diffServTBMeterEntry 1 }

diffServTBMeterType OBJECT-TYPE
    SYNTAX          INTEGER { other(1), tokenBucket(2), avgRate(3), 
                        srTCMBlind(4), srTCMAware(5), trTCMBlind(6), 
                        trTCMAware(7), tswTCM(8) }
    ACCESS          read-write
    STATUS          mandatory
    DESCRIPTION     
            "The type of meter using parameters specified by this
             TBMeter entry.
             
             Value of tokenBucket(2)  indicates  the  use  of  Two
             Parameter  Token Bucket Meter as described in [MODEL]
             section 5.2.3.
             
             Value of avgRate(3) indicates the use of Average Rate
             Meter as described in [MODEL] section 5.2.1.
             
             Value of srTCMBlind(4)  and  srTCMAware(5)  indicates
             the use of Single Rate Three Color Marker Metering as
             defined by RFC 2697, with `Color  Blind'  and  `Color
             Aware' mode as described by the RFC.
             
             Value of trTCMBlind(6)  and  trTCMAware(7)  indicates
             the  use  of  Two Rate Three Color Marker Metering as
             defined by RFC 2698, with `Color  Blind'  and  `Color
             Aware' mode as described by the RFC.
             
             Value of tswTCM(8) indicates the use of Time  Sliding
             Window  Three Color Marker Metering as defined by RFC
             2859."
--     REFERENCE       
--             "[MODEL] section 5"
    ::= { diffServTBMeterEntry 2 }

diffServTBMeterRate OBJECT-TYPE
    SYNTAX          Gauge
    ACCESS          read-write
    STATUS          mandatory
    DESCRIPTION     
            "The  token-bucket  rate,  in  kilobits  per   second
             (kbps).   This  attribute  is used for: 1. CIR in RFC
             2697 for srTCM 2. PIR and CIR in RFC 2698  for  trTCM
             3.  CTR and PTR in RFC 2859 for TSWTCM 4. AverageRate
             used in [MODEL] section 5."
    ::= { diffServTBMeterEntry 3 }

diffServTBMeterBurstSize OBJECT-TYPE
    SYNTAX          BurstSize
    ACCESS          read-write
    STATUS          mandatory
    DESCRIPTION     
            "The maximum number of bytes in a single transmission
             burst.  This attribute is used for: 1. CBS and EBS in
             RFC 2697 for srTCM 2. CBS and PBS  in  RFC  2698  for
             trTCM 3. Burst Size used in [MODEL] section 5."
    ::= { diffServTBMeterEntry 4 }

diffServTBMeterInterval OBJECT-TYPE
    SYNTAX          Gauge
    ACCESS          read-write
    STATUS          mandatory
    DESCRIPTION     
            "The time interval used with the token bucket.   For:
             1.  Average  Rate  Meter,  [MODEL]  section  5.2.1, -
             Delta.  2. Simple Token Bucket Meter, [MODEL] section
             5.1,
                -  time  interval  t.   3.  RFC  2859  TSWTCM,   -
             AVG_INTERVAL.   4.  RFC 2697 srTCM, RFC 2698 trTCM, -
             token bucket
                update time interval."
    ::= { diffServTBMeterEntry 5 }

diffServTBMeterStatus OBJECT-TYPE
    SYNTAX          RowStatus
    ACCESS          read-write
    STATUS          mandatory
    DESCRIPTION     
            "The  RowStatus  variable  controls  the  activation,
             deactivation,  or  deletion  of a meter. Any writable
             variable may be modified whether the row is active or
             notInService."
    ::= { diffServTBMeterEntry 6 }

diffServAction OBJECT IDENTIFIER
    ::= { diffServMIBObjects 4 }

diffServActionNextFree OBJECT-TYPE
    SYNTAX          Gauge
    ACCESS          read-only
    STATUS          mandatory
    DESCRIPTION     
            "This  object  yields  a  value  when  read  that  is
             currently unused for a diffServActionId instance.  If
             a configuring system attempts to create a new row  in
             the diffServActionTable using this value, that opera-
             tion will fail if the value  has,  in  the  meantime,
             been  used  to  create  another row that is currently
             valid."
    ::= { diffServAction 1 }

diffServActionTable OBJECT-TYPE
    SYNTAX          SEQUENCE OF DiffServActionEntry
    ACCESS          not-accessible
    STATUS          mandatory
    DESCRIPTION     
            "The Action Table enumerates actions that can be per-
             formed  to  a stream of traffic. Multiple actions can
             be concatenated.  For example, after marking a stream
             of  traffic  exiting  from a meter, a device can then
             perform a count action  of  the  conforming  or  non-
             conforming traffic.
             
             Specific actions  are  indicated  by  diffServAction-
             Specific  which  points  to  an  entry  of a specific
             action type parameterizing the action in detail."
--     REFERENCE       
--             "[MODEL] section 6."
    ::= { diffServAction 2 }

diffServActionEntry OBJECT-TYPE
    SYNTAX          DiffServActionEntry
    ACCESS          not-accessible
    STATUS          mandatory
    DESCRIPTION     
            "Each entry in the action table allows description of
             one specific action to be applied to traffic."
    INDEX           { diffServActionId }
    ::= { diffServActionTable 1 }

DiffServActionEntry ::=
    SEQUENCE {
        diffServActionId                Gauge,
        diffServActionNext              RowPointer,
        diffServActionSpecific          StaticRowPointer,
        diffServActionType              INTEGER,
        diffServActionStatus            RowStatus
    }

diffServActionId OBJECT-TYPE
    SYNTAX          Gauge
    ACCESS          not-accessible
    STATUS          mandatory
    DESCRIPTION     
            "An index that enumerates the Action entries. The set
             of  such  identifiers spans the whole agent. Managers
             should obtain new values for  row  creation  in  this
             table by reading diffServActionNextFree."
    ::= { diffServActionEntry 1 }

diffServActionNext OBJECT-TYPE
    SYNTAX          RowPointer
    ACCESS          read-write
    STATUS          mandatory
    DESCRIPTION     
            "This selects the next diffserv  functional  datapath
             element  to  handle traffic for this data path.  This
             RowPointer should point to an instance of one of:
               diffServClfrEntry
               diffServMeterEntry
               diffServActionEntry
               diffServAlgDropEntry
               diffServQEntry
             
             A value of zeroDotZero in this attribute indicates no
             further Diffserv treatment is performed on traffic of
             this datapath.  The use of zeroDotZero is the  normal
             usage for the last functional datapath element of the
             current data path.
             
             If the row pointed to does not exist,  the  treatment
             is  as  if  this  attribute contains a value of zero-
             DotZero."
    DEFVAL          { zeroDotZero }
    ::= { diffServActionEntry 2 }

diffServActionSpecific OBJECT-TYPE
    SYNTAX          StaticRowPointer
    ACCESS          read-write
    STATUS          mandatory
    DESCRIPTION     
            "A pointer to an object instance providing additional
             information  for the type of action indicated by this
             action table entry.
             
             For the standard actions defined by this MIB  module,
             this   should  point  to  one  of  the  following:  a
             diffServDscpMarkActEntry,  a   diffServCountActEntry.
             For other actions, it may point to an object instance
             defined in some other MIB."
    ::= { diffServActionEntry 3 }

diffServActionType OBJECT-TYPE
    SYNTAX          INTEGER { other(1), specific(2), absoluteDrop(3) }
    ACCESS          read-write
    STATUS          mandatory
    DESCRIPTION     
            "Indicates the type of action. The values specific(2)
             must   be  associated  with  additional  information,
             pointed to by diffServActionSpecific, with the actual
             action type indicated by the object being pointed to.
             The value absoluteDrop(3) has no associated  informa-
             tion  and will have a diffServActionSpecific value of
             zeroDotZero.  The use  of  other(1)  is  outside  the
             scope  of  this  definition, although the diffServAc-
             tionSpecific pointer may be used  in  this  case,  to
             indicate other information."
    ::= { diffServActionEntry 4 }

diffServActionStatus OBJECT-TYPE
    SYNTAX          RowStatus
    ACCESS          read-write
    STATUS          mandatory
    DESCRIPTION     
            "The  RowStatus  variable  controls  the  activation,
             deactivation  or  deletion  of an action element. Any
             writable variable may be modified whether the row  is
             
             
             
             
             
             
             
             active or notInService."
    ::= { diffServActionEntry 5 }

diffServDscpMarkActTable OBJECT-TYPE
    SYNTAX          SEQUENCE OF DiffServDscpMarkActEntry
    ACCESS          not-accessible
    STATUS          mandatory
    DESCRIPTION     
            "This table enumerates specific DSCPs used for  mark-
             ing  or  remarking  the DSCP field of IP packets. The
             entries of this table may be referenced by a diffSer-
             vActionSpecific attribute."
--     REFERENCE       
--             "[MODEL] section 6.1"
    ::= { diffServAction 3 }

diffServDscpMarkActEntry OBJECT-TYPE
    SYNTAX          DiffServDscpMarkActEntry
    ACCESS          not-accessible
    STATUS          mandatory
    DESCRIPTION     
            "An  entry  in  the  DSCP  mark  action  table   that
             describes a single DSCP used for marking."
    INDEX           { diffServDscpMarkActDscp }
    ::= { diffServDscpMarkActTable 1 }

DiffServDscpMarkActEntry ::=
    SEQUENCE {
        diffServDscpMarkActDscp         Dscp
    }

diffServDscpMarkActDscp OBJECT-TYPE
    SYNTAX          Dscp
    ACCESS          read-only
    STATUS          mandatory
    DESCRIPTION     
            "The DSCP that this Action uses for marking/remarking
             traffic.  Note that a DSCP value of -1 is not permit-
             ted in this table.  It is  quite  possible  that  the
             only  packets  subject  to  this  Action  are already
             marked with this DSCP. Note also  that  Diffserv  may
             result  in packet remarking both on ingress to a net-
             work and on egress from it and it is  quite  possible
             that  ingress  and  egress  would  occur  in the same
             router."
    ::= { diffServDscpMarkActEntry 1 }

diffServCountActNextFree OBJECT-TYPE
    SYNTAX          Gauge
    ACCESS          read-only
    STATUS          mandatory
    DESCRIPTION     
            "This object yields a value when read that is currently unused
             for a diffServCountActId instance.
             If a configuring system attempts to create a new row
             in the diffServCountActTable using this value, that operation
             will fail if the value has, in the meantime, been used
             to create another row that is currently valid."
    ::= { diffServAction 4 }

diffServCountActTable OBJECT-TYPE
    SYNTAX          SEQUENCE OF DiffServCountActEntry
    ACCESS          not-accessible
    STATUS          mandatory
    DESCRIPTION     
            "This table contains counters  for  all  the  traffic
             passing through an action element."
--     REFERENCE       
--             "[MODEL] section 6.4"
    ::= { diffServAction 5 }

diffServCountActEntry OBJECT-TYPE
    SYNTAX          DiffServCountActEntry
    ACCESS          not-accessible
    STATUS          mandatory
    DESCRIPTION     
            "An entry in the count action table describes a  sin-
             gle set of traffic counters."
    INDEX           { diffServCountActId }
    ::= { diffServCountActTable 1 }

DiffServCountActEntry ::=
    SEQUENCE {
        diffServCountActId              Gauge,
        diffServCountActOctets          Counter,
--         diffServCountActHCOctets        Counter64,
        diffServCountActPkts            Counter,
--         diffServCountActHCPkts          Counter64,
        diffServCountActDiscontTime     TimeStamp,
        diffServCountActStatus          RowStatus
    }

diffServCountActId OBJECT-TYPE
    SYNTAX          Gauge
    ACCESS          not-accessible
    STATUS          mandatory
    DESCRIPTION     
            "An index that enumerates the Count  Action  entries.
             The  set  of  such identifiers spans the whole agent.
             Managers should obtain new values for row creation in
             this table by reading diffServCountActNextFree."
    ::= { diffServCountActEntry 1 }

diffServCountActOctets OBJECT-TYPE
    SYNTAX          Counter
    ACCESS          read-only
    STATUS          mandatory
    DESCRIPTION     
            "The number of octets at the Action datapath element.
             On  high  speed  devices,  this object implements the
             least significant 32  bits  of  diffServCountActHCOc-
             tets.
             
             Discontinuities in the  value  of  this  counter  can
             occur  at  re-initialization of the management system
             and at other times  as  indicated  by  the  value  of
             diffServCountActDiscontTime for this entry."
    ::= { diffServCountActEntry 2 }

-- diffServCountActHCOctets OBJECT-TYPE
--     SYNTAX          Counter64
--     ACCESS          read-only
--     STATUS          mandatory
--     DESCRIPTION     
--             "The number of octets at the Action datapath element.
--              This object should be used on high speed interfaces.
--              Discontinuities in the  value  of  this  counter  can
--              occur  at  re-initialization of the management system
--              and at other times  as  indicated  by  the  value  of
--              diffServCountActDiscontTime for this entry."
--     ::= { diffServCountActEntry 3 }

diffServCountActPkts OBJECT-TYPE
    SYNTAX          Counter
    ACCESS          read-only
    STATUS          mandatory
    DESCRIPTION     
            "The number of packets at the  Action  datapath  ele-
             ment.   On high speed devices, this object implements
             the  least  significant  32  bits  of   diffServCoun-
             tActHCPkts.
             
             Discontinuities in the  value  of  this  counter  can
             occur  at  re-initialization of the management system
             and at other times  as  indicated  by  the  value  of
             diffServCountActDiscontTime for this entry."
    ::= { diffServCountActEntry 4 }

-- diffServCountActHCPkts OBJECT-TYPE
--     SYNTAX          Counter64
--     ACCESS          read-only
--     STATUS          mandatory
--     DESCRIPTION     
--             "The number of packets at the  Action  datapath  ele-
--              ment.   This  object  should  be  used  on high speed
--              interfaces.
--              
--              Discontinuities in the  value  of  this  counter  can
--              occur  at  re-initialization of the management system
--              and at other times  as  indicated  by  the  value  of
--              diffServCountActDiscontTime for this entry."
--     ::= { diffServCountActEntry 5 }

diffServCountActDiscontTime OBJECT-TYPE
    SYNTAX          TimeStamp
    ACCESS          read-only
    STATUS          mandatory
    DESCRIPTION     
            "The value of sysUpTime on the most  recent  occasion
             at  which  any  one  or more of this entry's counters
             suffered a discontinuity. If no such  discontinuities
             have occurred since the last re-initialization of the
             local management subsystem, then this object contains
             a zero value."
    ::= { diffServCountActEntry 6 }

diffServCountActStatus OBJECT-TYPE
    SYNTAX          RowStatus
    ACCESS          read-write
    STATUS          mandatory
    DESCRIPTION     
            "The  RowStatus  variable  controls  the  activation,
             deactivation, or deletion of this entry. Any writable
             variable may be modified whether the row is active or
             notInService."
    ::= { diffServCountActEntry 7 }

diffServAlgDrop OBJECT IDENTIFIER
    ::= { diffServMIBObjects 5 }

diffServAlgDropNextFree OBJECT-TYPE
    SYNTAX          Gauge
    ACCESS          read-only
    STATUS          mandatory
    DESCRIPTION     
            "This  object  yields  a  value  when  read  that  is
             currently  unused  for  a diffServAlgDropId instance.
             If a configuring system attempts to create a new  row
             in  the  diffServAlgDropTable  using this value, that
             operation will fail if the value has,  in  the  mean-
             time,  been  used  to  create  another  row  that  is
             currently valid."
    ::= { diffServAlgDrop 1 }

diffServAlgDropTable OBJECT-TYPE
    SYNTAX          SEQUENCE OF DiffServAlgDropEntry
    ACCESS          not-accessible
    STATUS          mandatory
    DESCRIPTION     
            "The algorithmic drop table contains entries describ-
             ing  an  element that drops packets according to some
             algorithm."
--     REFERENCE       
--             "[MODEL] section 7.1.3"
    ::= { diffServAlgDrop 2 }

diffServAlgDropEntry OBJECT-TYPE
    SYNTAX          DiffServAlgDropEntry
    ACCESS          not-accessible
    STATUS          mandatory
    DESCRIPTION     
            "An entry describes  a  process  that  drops  packets
             according  to some algorithm.  Further details of the
             algorithm type are to be found in diffServAlgDropType
             and  with  more  detail parameter entry pointed to by
             diffServAlgDropSpecific when necessary."
    INDEX           { diffServAlgDropId }
    ::= { diffServAlgDropTable 1 }

DiffServAlgDropEntry ::=
    SEQUENCE {
        diffServAlgDropId               Gauge,
        diffServAlgDropType             INTEGER,
        diffServAlgDropNext             RowPointer,
        diffServAlgDropQMeasure         RowPointer,
        diffServAlgDropQThreshold       Gauge,
        diffServAlgDropSpecific         StaticRowPointer,
        diffServAlgDropOctets           Counter,
--         diffServAlgDropHCOctets         Counter64,
        diffServAlgDropPkts             Counter,
--         diffServAlgDropHCPkts           Counter64,
        diffServAlgDropStatus           RowStatus
    }

diffServAlgDropId OBJECT-TYPE
    SYNTAX          Gauge
    ACCESS          not-accessible
    STATUS          mandatory
    DESCRIPTION     
            "An index that  enumerates  the  Algorithmic  Dropper
             entries.  The set of such identifiers spans the whole
             agent. Managers should  obtain  new  values  for  row
             creation  in  this  table by reading diffServAlgDrop-
             NextFree."
    ::= { diffServAlgDropEntry 1 }

diffServAlgDropType OBJECT-TYPE
    SYNTAX          INTEGER { other(1), tailDrop(2), headDrop(3), 
                        randomDrop(4) }
    ACCESS          read-write
    STATUS          mandatory
    DESCRIPTION     
            "The type of algorithm used by this dropper. A  value
             of tailDrop(2) or headDrop(3) represents an algorithm
             that is completely specified by this MIB.  A value of
             other(1) requires further specification in some other
             MIB module.
             
             The tailDrop(2) algorithm is  described  as  follows:
             diffServAlgDropQThreshold represents the depth of the
             queue,  pointed  to  by  diffServAlgDropQMeasure,  at
             which all newly arriving packets will be dropped.
             
             The headDrop(3) algorithm is described as follows: if
             a packet arrives when the current depth of the queue,
             pointed to by diffServAlgDropQMeasure, is at diffSer-
             
             
             
             
             
             
             
             vAlgDropQThreshold,  packets currently at the head of
             the queue are dropped to make room for the new packet
             to be enqueued at the tail of the queue.
             
             The randomDrop(4) algorithm is described as  follows:
             on packet arrival, an algorithm is executed which may
             randomly drop the packet,  or  drop  other  packet(s)
             from  the  queue  in  its place. The specifics of the
             algorithm may be  proprietary.  For  this  algorithm,
             diffServAlgDropSpecific  points  to a diffServRandom-
             DropEntry that describes  the  algorithm.   For  this
             algorithm,  diffServAlgQThreshold is understood to be
             the absolute maximum size of the queue and additional
             parameters are described in diffServRandomDropTable."
    ::= { diffServAlgDropEntry 2 }

diffServAlgDropNext OBJECT-TYPE
    SYNTAX          RowPointer
    ACCESS          read-write
    STATUS          mandatory
    DESCRIPTION     
            "This selects the next diffserv  functional  datapath
             element  to  handle traffic for this data path.  This
             RowPointer should point to an instance of one of:
               diffServClfrEntry
               diffServMeterEntry
               diffServActionEntry
               diffServAlgDropEntry
               diffServQEntry
             
             A value of zeroDotZero in this attribute indicates no
             further Diffserv treatment is performed on traffic of
             this datapath.  The use of zeroDotZero is the  normal
             usage for the last functional datapath element of the
             current data path.
             
             If the row pointed to does not exist,  the  treatment
             is  as  if  this  attribute contains a value of zero-
             DotZero."
    ::= { diffServAlgDropEntry 3 }

diffServAlgDropQMeasure OBJECT-TYPE
    SYNTAX          RowPointer
    ACCESS          read-write
    STATUS          mandatory
    DESCRIPTION     
            "Points to an entry in the diffServQTable to indicate
             the  queue  that  a drop algorithm is to monitor when
             deciding whether  to  drop  a  packet.   If  the  row
             pointed  to  does  not exist, the algorithmic dropper
             element is considered inactive."
    ::= { diffServAlgDropEntry 4 }

diffServAlgDropQThreshold OBJECT-TYPE
    SYNTAX          Gauge
    ACCESS          read-write
    STATUS          mandatory
    DESCRIPTION     
            "A threshold on the depth in bytes of the queue being
             measured at which a trigger is generated to the drop-
             ping algorithm.
             
             For the tailDrop(2) or headDrop(3)  algorithms,  this
             represents  the  depth  of  the  queue, pointed to by
             diffServAlgDropQMeasure, at  which  the  drop  action
             will take place. Other algorithms will need to define
             their own semantics for this threshold."
    ::= { diffServAlgDropEntry 5 }

diffServAlgDropSpecific OBJECT-TYPE
    SYNTAX          StaticRowPointer
    ACCESS          read-write
    STATUS          mandatory
    DESCRIPTION     
            "Points to a table entry that provides further detail
             regarding a drop algorithm.
             
             Entries with diffServAlgDropType  equal  to  other(1)
             may have this point to a table defined in another MIB
             module.
             
             Entries with  diffServAlgDropType  equal  to  random-
             Drop(4)  must have this point to an entry in diffSer-
             vRandomDropTable.
             
             For all other algorithms, this should take the  value
             zeroDotzero."
    ::= { diffServAlgDropEntry 6 }

diffServAlgDropOctets OBJECT-TYPE
    SYNTAX          Counter
    ACCESS          read-only
    STATUS          mandatory
    DESCRIPTION     
            "The number of octets that have been dropped by  this
             drop  process.   On  high  speed devices, this object
             implements the least significant 32 bits of  diffSer-
             vAlgDropHCOctets.
             
             Discontinuities in the  value  of  this  counter  can
             occur  at  re-initialization of the management system
             and at other times  as  indicated  by  the  value  of
             ifCounterDiscontinuityTime appropriate to this inter-
             face."
    ::= { diffServAlgDropEntry 7 }

-- diffServAlgDropHCOctets OBJECT-TYPE
--     SYNTAX          Counter64
--     ACCESS          read-only
--     STATUS          mandatory
--     DESCRIPTION     
--             "The number of octets that have been dropped by  this
--              drop  process.   This  object  should be used on high
--              speed interfaces.
--              
--              Discontinuities in the  value  of  this  counter  can
--              occur  at  re-initialization of the management system
--              and at other times  as  indicated  by  the  value  of
--              ifCounterDiscontinuityTime appropriate to this inter-
--              face."
--     ::= { diffServAlgDropEntry 8 }

diffServAlgDropPkts OBJECT-TYPE
    SYNTAX          Counter
    ACCESS          read-only
    STATUS          mandatory
    DESCRIPTION     
            "The number of packets that have been dropped by this
             drop  process.   On  high  speed devices, this object
             implements the least significant 32 bits of  diffSer-
             vAlgDropHCPkts.
             
             Discontinuities in the  value  of  this  counter  can
             occur  at  re-initialization of the management system
             
             
             
             
             
             
             
             and at other times  as  indicated  by  the  value  of
             ifCounterDiscontinuityTime appropriate to this inter-
             face."
    ::= { diffServAlgDropEntry 9 }

-- diffServAlgDropHCPkts OBJECT-TYPE
--     SYNTAX          Counter64
--     ACCESS          read-only
--     STATUS          mandatory
--     DESCRIPTION     
--             "The number of packets that have been dropped by this
--              drop  process.   This  object  should be used on high
--              speed interfaces.
--              
--              Discontinuities in the  value  of  this  counter  can
--              occur  at  re-initialization of the management system
--              and at other times  as  indicated  by  the  value  of
--              ifCounterDiscontinuityTime appropriate to this inter-
--              face."
--     ::= { diffServAlgDropEntry 10 }

diffServAlgDropStatus OBJECT-TYPE
    SYNTAX          RowStatus
    ACCESS          read-write
    STATUS          mandatory
    DESCRIPTION     
            "The  RowStatus  variable  controls  the  activation,
             deactivation, or deletion of this entry. Any writable
             variable may be modified whether the row is active or
             notInService."
    ::= { diffServAlgDropEntry 11 }

diffServRandomDropNextFree OBJECT-TYPE
    SYNTAX          Gauge
    ACCESS          read-only
    STATUS          mandatory
    DESCRIPTION     
            "This  object  yields  a  value  when  read  that  is
             currently unused for a diffServRandomDropId instance.
             
             
             
             
             
             
             
             If a configuring system attempts to create a new  row
             in the diffServRandomDropTable using this value, that
             operation will fail if the value has,  in  the  mean-
             time,  been  used  to  create  another  row  that  is
             currently valid."
    ::= { diffServAlgDrop 3 }

diffServRandomDropTable OBJECT-TYPE
    SYNTAX          SEQUENCE OF DiffServRandomDropEntry
    ACCESS          not-accessible
    STATUS          mandatory
    DESCRIPTION     
            "The random drop table contains entries describing  a
             process  that drops packets randomly. Entries in this
             table is  intended  to  be  pointed  to  by  diffSer-
             vAlgDropSpecific."
--     REFERENCE       
--             "[MODEL] section 7.1.3"
    ::= { diffServAlgDrop 4 }

diffServRandomDropEntry OBJECT-TYPE
    SYNTAX          DiffServRandomDropEntry
    ACCESS          not-accessible
    STATUS          mandatory
    DESCRIPTION     
            "An entry describes  a  process  that  drops  packets
             according to a random algorithm."
    INDEX           { diffServRandomDropId }
    ::= { diffServRandomDropTable 1 }

DiffServRandomDropEntry ::=
    SEQUENCE {
        diffServRandomDropId            Gauge,
        diffServRandomDropMinThreshBytes Gauge,
        diffServRandomDropMinThreshPkts Gauge,
        diffServRandomDropMaxThreshBytes Gauge,
        diffServRandomDropMaxThreshPkts Gauge,
        diffServRandomDropInvProbMax    Gauge,
        diffServRandomDropInvWeight     Gauge,
        diffServRandomDropSamplingRate  Gauge,
        diffServRandomDropStatus        RowStatus
    }

diffServRandomDropId OBJECT-TYPE
    SYNTAX          Gauge
    ACCESS          not-accessible
    STATUS          mandatory
    DESCRIPTION     
            "An index that enumerates the  Random  Drop  entries.
             The  set  of  such identifiers spans the whole agent.
             Managers should obtain new values for row creation in
             this table by reading diffServRandomDropNextFree."
    ::= { diffServRandomDropEntry 1 }

diffServRandomDropMinThreshBytes OBJECT-TYPE
    SYNTAX          Gauge
    ACCESS          read-write
    STATUS          mandatory
    DESCRIPTION     
            "The average  queue  depth  in  bytes,  beyond  which
             traffic  has a non-zero probability of being dropped.
             Changes in this variable may or may not be  reflected
             in   the   reported   value   of  diffServRandomDrop-
             MinThreshPkts."
    ::= { diffServRandomDropEntry 2 }

diffServRandomDropMinThreshPkts OBJECT-TYPE
    SYNTAX          Gauge
    ACCESS          read-write
    STATUS          mandatory
    DESCRIPTION     
            "The average queue depth  in  packets,  beyond  which
             traffic  has a non-zero probability of being dropped.
             Changes in this variable may or may not be  reflected
             in the reported value of diffServRandomDropMinThresh-
             Bytes."
    ::= { diffServRandomDropEntry 3 }

diffServRandomDropMaxThreshBytes OBJECT-TYPE
    SYNTAX          Gauge
    ACCESS          read-write
    STATUS          mandatory
    DESCRIPTION     
            "The average queue depth beyond which traffic  has  a
             probability indicated by diffServRandomDropInvProbMax
             
             
             
             
             
             
             
             of being dropped or marked. Note  that  this  differs
             from  the  physical  queue  limit, which is stored in
             diffServAlgDropQThreshold.  Changes in this  variable
             may  or may not be reflected in the reported value of
             diffServRandomDropMaxThreshPkts."
    ::= { diffServRandomDropEntry 4 }

diffServRandomDropMaxThreshPkts OBJECT-TYPE
    SYNTAX          Gauge
    ACCESS          read-write
    STATUS          mandatory
    DESCRIPTION     
            "The average queue depth beyond which traffic  has  a
             probability indicated by diffServRandomDropInvProbMax
             of being dropped or marked. Note  that  this  differs
             from  the  physical  queue  limit, which is stored in
             diffServAlgDropQThreshold.  Changes in this  variable
             may  or may not be reflected in the reported value of
             diffServRandomDropMaxThreshBytes."
    ::= { diffServRandomDropEntry 5 }

diffServRandomDropInvProbMax OBJECT-TYPE
    SYNTAX          Gauge
    ACCESS          read-write
    STATUS          mandatory
    DESCRIPTION     
            "The worst case random drop probability, expressed as
             the  inverse  of  the drop probability.  With special
             case of the value zero meaning  zero  probability  of
             drop.
             
             For example, if every packet may be  dropped  in  the
             worst   case   (100%),   this   has   the   value  of
             4,294,967,295."
    ::= { diffServRandomDropEntry 6 }

diffServRandomDropInvWeight OBJECT-TYPE
    SYNTAX          Gauge
    ACCESS          read-write
    STATUS          mandatory
    DESCRIPTION     
            "The weighting of past history in affecting the  cal-
             culation  of  the  current queue average.  The moving
             
             
             
             
             
             
             
             average of the queue depth uses the inverse  of  this
             value  as the factor for the new queue depth, and one
             minus that inverse as the factor for  the  historical
             average.
             
             Implementations may choose to  limit  the  acceptable
             set  of  values to a specified set, such as powers of
             2."
    ::= { diffServRandomDropEntry 7 }

diffServRandomDropSamplingRate OBJECT-TYPE
    SYNTAX          Gauge
    ACCESS          read-write
    STATUS          mandatory
    DESCRIPTION     
            "The number of times per second the queue is  sampled
             for queue average calculation.  A value of zero means
             the queue is sampled approximately each time a packet
             is enqueued (or dequeued)."
    ::= { diffServRandomDropEntry 8 }

diffServRandomDropStatus OBJECT-TYPE
    SYNTAX          RowStatus
    ACCESS          read-write
    STATUS          mandatory
    DESCRIPTION     
            "The  RowStatus  variable  controls  the  activation,
             deactivation, or deletion of this entry. Any writable
             variable may be modified whether the row is active or
             notInService."
    ::= { diffServRandomDropEntry 9 }

diffServQueue OBJECT IDENTIFIER
    ::= { diffServMIBObjects 6 }

diffServQNextFree OBJECT-TYPE
    SYNTAX          Gauge
    ACCESS          read-only
    STATUS          mandatory
    DESCRIPTION     
            "This  object  yields  a  value  when  read  that  is
             currently  unused  for  a diffServQId instance.  If a
             configuring system attempts to create a  new  row  in
             the  diffServQTable  using this value, that operation
             will fail if the value has,  in  the  meantime,  been
             used to create another row that is currently valid."
    ::= { diffServQueue 1 }

diffServQTable OBJECT-TYPE
    SYNTAX          SEQUENCE OF DiffServQEntry
    ACCESS          not-accessible
    STATUS          mandatory
    DESCRIPTION     
            "The Queue Table enumerates the individual queues."
--     REFERENCE       
--             "[MODEL] section 7.1.1"
    ::= { diffServQueue 2 }

diffServQEntry OBJECT-TYPE
    SYNTAX          DiffServQEntry
    ACCESS          not-accessible
    STATUS          mandatory
    DESCRIPTION     
            "An entry in  the  Queue  Table  describes  a  single
             queue.  With each entry belonging to one and only one
             datapath."
    INDEX           { diffServQId }
    ::= { diffServQTable 1 }

DiffServQEntry ::=
    SEQUENCE {
        diffServQId                     Gauge,
        diffServQNext                   RowPointer,
        diffServQSchdParam              StaticRowPointer,
        diffServQStatus                 RowStatus
    }

diffServQId OBJECT-TYPE
    SYNTAX          Gauge
    ACCESS          not-accessible
    STATUS          mandatory
    DESCRIPTION     
            "An index that enumerates the Queue entries. The  set
             of  such  identifiers spans the whole agent. Managers
             should obtain new values for  row  creation  in  this
             table by reading diffServQNextFree."
    ::= { diffServQEntry 1 }

diffServQNext OBJECT-TYPE
    SYNTAX          RowPointer
    ACCESS          read-write
    STATUS          mandatory
    DESCRIPTION     
            "This selects the next diffserv  functional  datapath
             element  to  handle traffic for this data path.  This
             RowPointer must point to an instance of one of:
               diffServSchedulerEntry
             
             A value of zeroDotZero in this attribute indicates an
             incomplete  diffServQEntry instance.  An illegal con-
             figuration.
             
             If the row pointed to does not exist,  the  treatment
             is  as  if  this  attribute contains a value of zero-
             DotZero."
    ::= { diffServQEntry 2 }

diffServQSchdParam OBJECT-TYPE
    SYNTAX          StaticRowPointer
    ACCESS          read-write
    STATUS          mandatory
    DESCRIPTION     
            "This  StaticRowPointer  indicates   the   entry   in
             diffServSchdParamTable  the  scheduler, pointed to by
             diffServQNext, should use to service this queue.
             
             A value of zeroDotZero in this attribute indicates an
             incomplete  diffServQEntry instance.  An illegal con-
             figuration.
             
             If the row pointed to does not exist,  the  treatment
             is  as  if  this  attribute contains a value of zero-
             DotZero."
    ::= { diffServQEntry 3 }

diffServQStatus OBJECT-TYPE
    SYNTAX          RowStatus
    ACCESS          read-write
    STATUS          mandatory
    DESCRIPTION     
            "The  RowStatus  variable  controls  the  activation,
             deactivation,  or  deletion  of a queue. Any writable
             variable may be modified whether the row is active or
             notInService."
    ::= { diffServQEntry 4 }

diffServScheduler OBJECT IDENTIFIER
    ::= { diffServMIBObjects 7 }

diffServSchedulerPriority OBJECT IDENTIFIER
    ::= { diffServScheduler 1 }

diffServSchedulerWRR OBJECT IDENTIFIER
    ::= { diffServScheduler 2 }

diffServSchedulerWFQ OBJECT IDENTIFIER
    ::= { diffServScheduler 3 }

diffServSchedulerShaping OBJECT IDENTIFIER
    ::= { diffServScheduler 4 }

diffServSchedulerNextFree OBJECT-TYPE
    SYNTAX          Gauge
    ACCESS          read-only
    STATUS          mandatory
    DESCRIPTION     
            "This  object  yields  a  value  when  read  that  is
             currently  unused for a diffServSchedulerId instance.
             If a configuring system attempts to create a new  row
             in  the diffServSchedulerTable using this value, that
             operation will fail if the value has,  in  the  mean-
             time,  been  used  to  create  another  row  that  is
             currently valid."
    ::= { diffServScheduler 5 }

diffServSchedulerTable OBJECT-TYPE
    SYNTAX          SEQUENCE OF DiffServSchedulerEntry
    ACCESS          not-accessible
    STATUS          mandatory
    DESCRIPTION     
            "The Scheduler Table  enumerates  packet  schedulers.
             Multiple scheduling algorithms can be used on a given
             datapath,  with  each  algorithm  described  by   one
             diffServSchedulerEntry."
--     REFERENCE       
--             "[MODEL] section 7.1.2"
    ::= { diffServScheduler 6 }

diffServSchedulerEntry OBJECT-TYPE
    SYNTAX          DiffServSchedulerEntry
    ACCESS          not-accessible
    STATUS          mandatory
    DESCRIPTION     
            "An entry in the Scheduler Table describing a  single
             instance of a scheduling algorithm."
    INDEX           { diffServSchedulerId }
    ::= { diffServSchedulerTable 1 }

DiffServSchedulerEntry ::=
    SEQUENCE {
        diffServSchedulerId             Gauge,
        diffServSchedulerNext           RowPointer,
        diffServSchedulerMethod         OBJECT IDENTIFIER,
        diffServSchedulerSchdParam      StaticRowPointer,
        diffServSchedulerStatus         RowStatus
    }

diffServSchedulerId OBJECT-TYPE
    SYNTAX          Gauge
    ACCESS          not-accessible
    STATUS          mandatory
    DESCRIPTION     
            "An index that enumerates the Scheduler entries.  The
             set  of  such  identifiers  spans  the  whole  agent.
             Managers should obtain new values for row creation in
             this table by reading diffServSchedulerNextFree."
    ::= { diffServSchedulerEntry 1 }

diffServSchedulerNext OBJECT-TYPE
    SYNTAX          RowPointer
    ACCESS          read-write
    STATUS          mandatory
    DESCRIPTION     
            "This selects the next diffserv  functional  datapath
             
             
             
             
             
             
             
             element  to  handle traffic for this data path.  This
             RowPointer should point to an instance of one of:
               diffServSchedulerEntry
               diffServQEntry  As  indicated  by  [MODEL]  section
             7.1.4.
             
             But this RowPointer can also point to an instance of:
               diffServClfrEntry
               diffServMeterEntry
               diffServActionEntry
               diffServAlgDropEntry For building of multiple  TCBs
             for the same data path.
             
             This should point to  another  diffServSchedulerEntry
             for  implementation of multiple scheduler methods for
             the  same  datapath,  and   for   implementation   of
             hierarchical schedulers.
             
             A value of zeroDotZero in this attribute indicates no
             further Diffserv treatment is performed on traffic of
             this datapath.  The use of zeroDotZero is the  normal
             usage for the last functional datapath element of the
             current data path.
             
             If the row pointed to does not exist,  the  treatment
             is   as   if  this  attribute  contains  a  value  of
             zeroDotZero."
    DEFVAL          { zeroDotZero }
    ::= { diffServSchedulerEntry 2 }

diffServSchedulerMethod OBJECT-TYPE
    SYNTAX          OBJECT IDENTIFIER
    ACCESS          read-write
    STATUS          mandatory
    DESCRIPTION     
            "The scheduling algorithm used by this Scheduler.  {0
             0}  indicates  this  is unknown.  Standard values for
             generic    algorithms:     diffServSchedulerPriority,
             diffServSchedulerWRR,  and  diffServSchedulerWFQ  are
             specified in  this  MIB;  additional  values  may  be
             further specified in other MIBs."
--     REFERENCE       
--             "[MODEL] section 7.1.2"
    ::= { diffServSchedulerEntry 3 }

diffServSchedulerSchdParam OBJECT-TYPE
    SYNTAX          StaticRowPointer
    ACCESS          read-write
    STATUS          mandatory
    DESCRIPTION     
            "This  StaticRowPointer  indicates   the   entry   in
             diffServSchdParamTable  the  higher  level scheduler,
             pointed to by diffServSchedulerNext,  should  use  to
             service the output of this scheduler.  This attribute
             is only used when there is more  than  one  level  of
             scheduler.   And should have the value of zeroDotZero
             when not used."
    DEFVAL          { zeroDotZero }
    ::= { diffServSchedulerEntry 4 }

diffServSchedulerStatus OBJECT-TYPE
    SYNTAX          RowStatus
    ACCESS          read-write
    STATUS          mandatory
    DESCRIPTION     
            "The  RowStatus  variable  controls  the  activation,
             deactivation,  or  deletion  of a queue. Any writable
             variable may be modified whether the row is active or
             notInService."
    ::= { diffServSchedulerEntry 5 }

diffServSchdParamNextFree OBJECT-TYPE
    SYNTAX          Gauge
    ACCESS          read-only
    STATUS          mandatory
    DESCRIPTION     
            "This  object  yields  a  value  when  read  that  is
             currently  unused for a diffServSchdParamId instance.
             If a configuring system attempts to create a new  row
             in  the diffServSchdParamTable using this value, that
             operation will fail if the value has,  in  the  mean-
             time,  been  used  to  create  another  row  that  is
             currently valid."
    ::= { diffServScheduler 7 }

diffServSchdParamTable OBJECT-TYPE
    SYNTAX          SEQUENCE OF DiffServSchdParamEntry
    ACCESS          not-accessible
    STATUS          mandatory
    DESCRIPTION     
            "The Scheduling Parameter Table enumerates individual
             sets  of scheduling parameter that can be used/reused
             by Queues and Schedulers."
    ::= { diffServScheduler 8 }

diffServSchdParamEntry OBJECT-TYPE
    SYNTAX          DiffServSchdParamEntry
    ACCESS          not-accessible
    STATUS          mandatory
    DESCRIPTION     
            "An entry in the Scheduling Parameter Table describes
             a  single  set  of  scheduling  parameter  for use by
             queues and schedulers.
             
             Notice multiple inter-mixed of  Queue  and  Scheduler
             entries can use the same Scheduler Parameter entry."
    INDEX           { diffServSchdParamId }
    ::= { diffServSchdParamTable 1 }

DiffServSchdParamEntry ::=
    SEQUENCE {
        diffServSchdParamId             Gauge,
        diffServSchdParamPriority       Gauge,
        diffServSchdParamMinRateAbs     Gauge,
        diffServSchdParamMinRateRel     Gauge,
        diffServSchdParamMaxRateAbs     Gauge,
        diffServSchdParamMaxRateRel     Gauge,
        diffServSchdParamBurstSize      BurstSize,
        diffServSchdParamStatus         RowStatus
    }

diffServSchdParamId OBJECT-TYPE
    SYNTAX          Gauge
    ACCESS          not-accessible
    STATUS          mandatory
    DESCRIPTION     
            "An index that  enumerates  the  Scheduler  Parameter
             entries.  The set of such identifiers spans the whole
             agent. Managers should  obtain  new  values  for  row
             creation  in this table by reading diffServSchdParam-
             NextFree."
    ::= { diffServSchdParamEntry 1 }

diffServSchdParamPriority OBJECT-TYPE
    SYNTAX          Gauge
    ACCESS          read-write
    STATUS          mandatory
    DESCRIPTION     
            "The priority of this queue, to be used as a  parame-
             ter  to  the  next  scheduler element downstream from
             this one.  A higher value  means  higher priority and
             should be serviced first."
    ::= { diffServSchdParamEntry 2 }

diffServSchdParamMinRateAbs OBJECT-TYPE
    SYNTAX          Gauge
    ACCESS          read-write
    STATUS          mandatory
    DESCRIPTION     
            "The minimum absolute rate, in kilobits/sec,  that  a
             downstream  scheduler element should allocate to this
             queue.  If the value is zero, then  there  is  effec-
             tively  no  minimum  rate guarantee.  If the value is
             non-zero, the scheduler will assure the servicing  of
             this queue to at least this rate.
             
             Note that this attribute's value is coupled  to  that
             of  diffServSchdParamMinRateRel:  changes to one will
             affect the value of the other. They are linked by the
             following equation:
             
             
             
             
             
             
             
               diffServSchdParamMinRateRel = diffServSchdParamMinRateAbs
                                              * 10,000,000/ifSpeed
             
             or, if appropriate:
             
               diffServSchdParamMinRateRel = diffServSchdParamMinRateAbs
                                               * 10 / ifHighSpeed"
--     REFERENCE       
--             "ifSpeed, ifHighSpeed from [IFMIB]"
    ::= { diffServSchdParamEntry 3 }

diffServSchdParamMinRateRel OBJECT-TYPE
    SYNTAX          Gauge
    ACCESS          read-write
    STATUS          mandatory
    DESCRIPTION     
            "The minimum rate that a downstream scheduler element
             should  allocate  to this queue, relative to the max-
             imum rate of the interface as reported by ifSpeed  or
             ifHighSpeed, in units of 1/10,000 of 1.  If the value
             is zero, then there is effectively  no  minimum  rate
             guarantee.   If  the value is non-zero, the scheduler
             will assure the servicing of this queue to  at  least
             this rate.
             
             Note that this attribute's value is coupled  to  that
             of  diffServSchdParamMinRateAbs:  changes to one will
             affect the value of the other. They are linked by the
             following equation:
             
               diffServSchdParamMinRateAbs = ifSpeed *
                            diffServSchdParamMinRateRel/10,000,000
             
             or, if appropriate:
             
               diffServSchdParamMinRateAbs = ifHighSpeed *
                                  diffServSchdParamMinRateRel / 10"
--     REFERENCE       
--             "ifSpeed, ifHighSpeed from [IFMIB]"
    ::= { diffServSchdParamEntry 4 }

diffServSchdParamMaxRateAbs OBJECT-TYPE
    SYNTAX          Gauge
    ACCESS          read-write
    STATUS          mandatory
    DESCRIPTION     
            "The maximum rate in kilobits/sec that  a  downstream
             scheduler  element  should allocate to this queue. If
             the value is zero, then there is effectively no  max-
             imum rate limit and that the scheduler should attempt
             to be work-conserving for this queue.  If  the  value
             is  non-zero,  the scheduler will limit the servicing
             of this queue to, at most, this rate in  a  non-work-
             conserving manner.
             
             Note that this attribute's value is coupled  to  that
             of  diffServSchdParamMaxRateRel:  changes to one will
             affect the value of the other. They are linked by the
             following equation:
             
               diffServSchdParamMaxRateRel = diffServSchdParamMaxRateAbs
                                              * 10,000,000/ifSpeed
             
             or, if appropriate:
             
               diffServSchdParamMaxRateRel = diffServSchdParamMaxRateAbs
                                               * 10 / ifHighSpeed"
--     REFERENCE       
--             "ifSpeed, ifHighSpeed from [IFMIB]"
    ::= { diffServSchdParamEntry 5 }

diffServSchdParamMaxRateRel OBJECT-TYPE
    SYNTAX          Gauge
    ACCESS          read-write
    STATUS          mandatory
    DESCRIPTION     
            "The maximum rate that a downstream scheduler element
             should  allocate  to this queue, relative to the max-
             imum rate of the interface as reported by ifSpeed  or
             ifHighSpeed, in units of 1/10,000 of 1.  If the value
             is zero, then there is effectively  no  maximum  rate
             limit  and  the  scheduler should attempt to be work-
             conserving for this queue.  If the value is non-zero,
             the  scheduler will limit the servicing of this queue
             to, at  most,  this  rate  in  a  non-work-conserving
             manner.
             
             Note that this attribute's value is coupled  to  that
             of  diffServSchdParamMaxRateAbs:  changes to one will
             affect the value of the other. They are linked by the
             
             
             
             
             
             
             
             following equation:
             
               diffServSchdParamMaxRateAbs = ifSpeed *
                            diffServSchdParamMaxRateRel/10,000,000
             
             or, if appropriate:
             
               diffServSchdParamMaxRateAbs = ifHighSpeed *
                                 diffServSchdParamMaxRateRel / 10"
--     REFERENCE       
--             "ifSpeed, ifHighSpeed from [IFMIB]"
    ::= { diffServSchdParamEntry 6 }

diffServSchdParamBurstSize OBJECT-TYPE
    SYNTAX          BurstSize
    ACCESS          read-write
    STATUS          mandatory
    DESCRIPTION     
            "The maximum number of bytes in a single transmission
             burst.   This  attribute is used when diffServSchedu-
             lerMethod of a downstream Scheduler element  is  used
             for shaping traffic exiting this queue/scheduler."
    ::= { diffServSchdParamEntry 7 }

diffServSchdParamStatus OBJECT-TYPE
    SYNTAX          RowStatus
    ACCESS          read-write
    STATUS          mandatory
    DESCRIPTION     
            "The  RowStatus  variable  controls  the  activation,
             deactivation,  or  deletion  of a queue. Any writable
             variable may be modified whether the row is active or
             notInService."
    ::= { diffServSchdParamEntry 8 }

diffServMIBConformance OBJECT IDENTIFIER
    ::= { diffServMib 2 }

diffServMIBCompliances OBJECT IDENTIFIER
    ::= { diffServMIBConformance 1 }

diffServMIBGroups OBJECT IDENTIFIER
    ::= { diffServMIBConformance 2 }

diffServMIBDataPathGroup OBJECT IDENTIFIER
    ::= { diffServMIBGroups 1 }

-- diffServMIBDataPathGroup OBJECT-GROUP
--     OBJECTS         { diffServDataPathStart, diffServDataPathStatus }
--     STATUS          mandatory
--     DESCRIPTION     
--             "The Data Path Group defines  the  MIB  Objects  that
--              describe a data path."
--     ::= { diffServMIBGroups 1 }

diffServMIBClfrGroup OBJECT IDENTIFIER
    ::= { diffServMIBGroups 2 }

-- diffServMIBClfrGroup OBJECT-GROUP
--     OBJECTS         { diffServClfrStatus }
--     STATUS          mandatory
--     DESCRIPTION     
--             "The Classifier Group defines the  MIB  Objects  that
--              describe a generic classifier."
--     ::= { diffServMIBGroups 2 }

diffServMIBClfrElementGroup OBJECT IDENTIFIER
    ::= { diffServMIBGroups 3 }

-- diffServMIBClfrElementGroup OBJECT-GROUP
--     OBJECTS         { diffServClfrElementOrder, 
--                       diffServClfrElementNext, 
--                       diffServClfrElementSpecific, 
--                       diffServClfrElementStatus }
--     STATUS          mandatory
--     DESCRIPTION     
--             "The Classifier Element Group defines the MIB Objects
--              that  describe the classifier elements that make up a
--              generic classifier."
--     ::= { diffServMIBGroups 3 }

diffServMIBSixTupleClfrGroup OBJECT IDENTIFIER
    ::= { diffServMIBGroups 4 }

-- diffServMIBSixTupleClfrGroup OBJECT-GROUP
--     OBJECTS         { diffServSixTupleClfrDstAddrType, 
--                       diffServSixTupleClfrDstAddr, 
--                       diffServSixTupleClfrDstAddrMask, 
--                       diffServSixTupleClfrSrcAddrType, 
--                       diffServSixTupleClfrSrcAddr, 
--                       diffServSixTupleClfrSrcAddrMask, 
--                       diffServSixTupleClfrDscp, 
--                       diffServSixTupleClfrProtocol, 
--                       diffServSixTupleClfrDstL4PortMin, 
--                       diffServSixTupleClfrDstL4PortMax, 
--                       diffServSixTupleClfrSrcL4PortMin, 
--                       diffServSixTupleClfrSrcL4PortMax, 
--                       diffServSixTupleClfrStatus }
--     STATUS          mandatory
--     DESCRIPTION     
--             "The  Six-tuple  Classifier  Group  defines  the  MIB
--              Objects that describe a classifier element for match-
--              ing on 6 fields of an  IP  and  upper-layer  protocol
--              header."
--     ::= { diffServMIBGroups 4 }

diffServMIBMeterGroup OBJECT IDENTIFIER
    ::= { diffServMIBGroups 5 }

-- diffServMIBMeterGroup OBJECT-GROUP
--     OBJECTS         { diffServMeterSucceedNext, diffServMeterFailNext, 
--                       diffServMeterSpecific, diffServMeterStatus }
--     STATUS          mandatory
--     DESCRIPTION     
--             "The Meter Group defines the objects used in describ-
--              ing a generic meter element."
--     ::= { diffServMIBGroups 5 }

diffServMIBTBMeterGroup OBJECT IDENTIFIER
    ::= { diffServMIBGroups 6 }

-- diffServMIBTBMeterGroup OBJECT-GROUP
--     OBJECTS         { diffServTBMeterType, diffServTBMeterRate, 
--                       diffServTBMeterBurstSize, 
--                       diffServTBMeterInterval, diffServTBMeterStatus }
--     STATUS          mandatory
--     DESCRIPTION     
--             "The Token-Bucket Meter  Group  defines  the  objects
--              used in describing a token bucket meter element."
--     ::= { diffServMIBGroups 6 }

diffServMIBActionGroup OBJECT IDENTIFIER
    ::= { diffServMIBGroups 7 }

-- diffServMIBActionGroup OBJECT-GROUP
--     OBJECTS         { diffServActionNext, diffServActionSpecific, 
--                       diffServActionType, diffServActionStatus }
--     STATUS          mandatory
--     DESCRIPTION     
--             "The  Action  Group  defines  the  objects  used   in
--              describing a generic action element."
--     ::= { diffServMIBGroups 7 }

diffServMIBDscpMarkActGroup OBJECT IDENTIFIER
    ::= { diffServMIBGroups 8 }

-- diffServMIBDscpMarkActGroup OBJECT-GROUP
--     OBJECTS         { diffServDscpMarkActDscp }
--     STATUS          mandatory
--     DESCRIPTION     
--             "The DSCP Mark Action Group defines the objects  used
--              in describing a DSCP Marking Action element."
--     ::= { diffServMIBGroups 8 }

diffServMIBCounterGroup OBJECT IDENTIFIER
    ::= { diffServMIBGroups 9 }

-- diffServMIBCounterGroup OBJECT-GROUP
--     OBJECTS         { diffServCountActOctets, diffServCountActPkts, 
--                       diffServCountActDiscontTime, 
--                       diffServCountActStatus, diffServAlgDropOctets, 
--                       diffServAlgDropPkts }
--     STATUS          mandatory
--     DESCRIPTION     
--             "A  collection  of  objects   providing   information
--              specific to non-high speed (non-high speed interfaces
--              transmit and receive at speeds less than or equal  to
--              20,000,000   bits/second)   packet-oriented   network
--              
--              
--              
--              
--              
--              
--              
--              interfaces."
--     ::= { diffServMIBGroups 9 }

diffServMIBHCCounterGroup OBJECT IDENTIFIER
    ::= { diffServMIBGroups 10 }

-- diffServMIBHCCounterGroup OBJECT-GROUP
--     OBJECTS         { diffServCountActOctets, 
--                       diffServCountActHCOctets, diffServCountActPkts, 
--                       diffServCountActDiscontTime, 
--                       diffServCountActStatus, diffServAlgDropOctets, 
--                       diffServAlgDropHCOctets, diffServAlgDropPkts }
--     STATUS          mandatory
--     DESCRIPTION     
--             "A  collection  of  objects   providing   information
--              specific   to   high  speed  (high  speed  interfaces
--              transmit  and  receive   at   speeds   greater   than
--              20,000,000  but  less  than  or equals to 650,000,000
--              bits/second) packet-oriented network interfaces."
--     ::= { diffServMIBGroups 10 }

diffServMIBVHCCounterGroup OBJECT IDENTIFIER
    ::= { diffServMIBGroups 11 }

-- diffServMIBVHCCounterGroup OBJECT-GROUP
--     OBJECTS         { diffServCountActOctets, 
--                       diffServCountActHCOctets, diffServCountActPkts, 
--                       diffServCountActHCPkts, 
--                       diffServCountActDiscontTime, 
--                       diffServCountActStatus, diffServAlgDropOctets, 
--                       diffServAlgDropHCOctets, diffServAlgDropPkts, 
--                       diffServAlgDropHCPkts }
--     STATUS          mandatory
--     DESCRIPTION     
--             "A  collection  of  objects   providing   information
--              specific  to  very-high speed (very-high speed inter-
--              faces transmit and receive  at  speeds  greater  than
--              650,000,000   bits/second)   packet-oriented  network
--              interfaces."
--     ::= { diffServMIBGroups 11 }

diffServMIBAlgDropGroup OBJECT IDENTIFIER
    ::= { diffServMIBGroups 12 }

-- diffServMIBAlgDropGroup OBJECT-GROUP
--     OBJECTS         { diffServAlgDropType, diffServAlgDropNext, 
--                       diffServAlgDropQMeasure, 
--                       diffServAlgDropQThreshold, 
--                       diffServAlgDropSpecific, diffServAlgDropStatus }
--     STATUS          mandatory
--     DESCRIPTION     
--             "The Algorithmic Drop Group contains the objects that
--              describe algorithmic dropper operation and configura-
--              tion."
--     ::= { diffServMIBGroups 12 }

diffServMIBRandomDropGroup OBJECT IDENTIFIER
    ::= { diffServMIBGroups 13 }

-- diffServMIBRandomDropGroup OBJECT-GROUP
--     OBJECTS         { diffServRandomDropMinThreshBytes, 
--                       diffServRandomDropMinThreshPkts, 
--                       diffServRandomDropMaxThreshBytes, 
--                       diffServRandomDropMaxThreshPkts, 
--                       diffServRandomDropInvProbMax, 
--                       diffServRandomDropInvWeight, 
--                       diffServRandomDropSamplingRate, 
--                       diffServRandomDropStatus }
--     STATUS          mandatory
--     DESCRIPTION     
--             "The Random Drop Group augments the Algorithmic Drop Group for
--              random dropper operation and configuration."
--     ::= { diffServMIBGroups 13 }

diffServMIBQGroup OBJECT IDENTIFIER
    ::= { diffServMIBGroups 14 }

-- diffServMIBQGroup OBJECT-GROUP
--     OBJECTS         { diffServQNext, diffServQSchdParam, 
--                       diffServQStatus }
--     STATUS          mandatory
--     DESCRIPTION     
--             "The Queue Group contains the objects  that  describe
--              an interface's queues."
--     ::= { diffServMIBGroups 14 }

diffServMIBSchedulerGroup OBJECT IDENTIFIER
    ::= { diffServMIBGroups 15 }

-- diffServMIBSchedulerGroup OBJECT-GROUP
--     OBJECTS         { diffServSchedulerNext, diffServSchedulerMethod, 
--                       diffServSchedulerSchdParam, 
--                       diffServSchedulerStatus }
--     STATUS          mandatory
--     DESCRIPTION     
--             "The  Scheduler  Group  contains  the  objects   that
--              
--              
--              
--              
--              
--              
--              
--              describe packet schedulers on interfaces."
--     ::= { diffServMIBGroups 15 }

diffServMIBSchdParamGroup OBJECT IDENTIFIER
    ::= { diffServMIBGroups 16 }

-- diffServMIBSchdParamGroup OBJECT-GROUP
--     OBJECTS         { diffServSchdParamPriority, 
--                       diffServSchdParamMinRateAbs, 
--                       diffServSchdParamMinRateRel, 
--                       diffServSchdParamMaxRateAbs, 
--                       diffServSchdParamMaxRateRel, 
--                       diffServSchdParamBurstSize, 
--                       diffServSchdParamStatus }
--     STATUS          mandatory
--     DESCRIPTION     
--             "The Scheduler Parameter Group contains  the  objects
--              that describe packet schedulers' parameters on inter-
--              faces."
--     ::= { diffServMIBGroups 16 }

diffServMIBStaticGroup OBJECT IDENTIFIER
    ::= { diffServMIBGroups 17 }

-- diffServMIBStaticGroup OBJECT-GROUP
--     OBJECTS         { diffServClfrNextFree, 
--                       diffServClfrElementNextFree, 
--                       diffServSixTupleClfrNextFree, 
--                       diffServMeterNextFree, diffServTBMeterNextFree, 
--                       diffServActionNextFree, 
--                       diffServCountActNextFree, 
--                       diffServAlgDropNextFree, 
--                       diffServRandomDropNextFree, diffServQNextFree, 
--                       diffServSchedulerNextFree, 
--                       diffServSchdParamNextFree }
--     STATUS          mandatory
--     DESCRIPTION     
--             "The Static Group contains  readable  scalar  objects
--              used  in creating unique identifiers for classifiers,
--              meters, actions and queues. These are required  when-
--              ever  row creation operations on such tables are sup-
--              ported."
--     ::= { diffServMIBGroups 17 }

diffServMIBCompliance OBJECT IDENTIFIER
    ::= { diffServMIBCompliances 1 }

-- diffServMIBCompliance MODULE-COMPLIANCE
--     STATUS          mandatory
--     DESCRIPTION     
--             "This MIB may be implemented as a read-only or  as  a
--              read-create MIB. As a result, it may be used for mon-
--              itoring or for configuration."

--     MODULE          -- -- this module

--         MANDATORY-GROUPS    { diffServMIBDataPathGroup, 
--                       diffServMIBClfrGroup, 
--                       diffServMIBClfrElementGroup, 
--                       diffServMIBSixTupleClfrGroup, 
--                       diffServMIBActionGroup, diffServMIBAlgDropGroup, 
--                       diffServMIBQGroup, diffServMIBSchedulerGroup, 
--                       diffServMIBSchdParamGroup }

--         GROUP       diffServMIBCounterGroup
--         DESCRIPTION 
--             "This group is mandatory for table objects indexed by
--              ifIndex  for  which  the  value  of the corresponding
--              instance  of  ifSpeed  is  less  than  or  equal   to
--              20,000,000 bits/second."

--         GROUP       diffServMIBHCCounterGroup
--         DESCRIPTION 
--             "This group is mandatory for table objects indexed by
--              ifIndex  for  which  the  value  of the corresponding
--              instance  of  ifSpeed  is  greater  than   20,000,000
--              
--              
--              
--              
--              
--              
--              
--              bits/second."

--         GROUP       diffServMIBVHCCounterGroup
--         DESCRIPTION 
--             "This group is mandatory for table objects indexed by
--              ifIndex  for  which  the  value  of the corresponding
--              instance  of  ifSpeed  is  greater  than  650,000,000
--              bits/second."

--         GROUP       diffServMIBMeterGroup
--         DESCRIPTION 
--             "This group is mandatory for devices  that  implement
--              metering functions."

--         GROUP       diffServMIBTBMeterGroup
--         DESCRIPTION 
--             "This group is mandatory for devices  that  implement
--              token-bucket metering functions."

--         GROUP       diffServMIBDscpMarkActGroup
--         DESCRIPTION 
--             "This group is mandatory for devices  that  implement
--              DSCP-Marking functions."

--         GROUP       diffServMIBRandomDropGroup
--         DESCRIPTION 
--             "This group is mandatory for devices  that  implement
--              Random Drop functions."

--         GROUP       diffServMIBStaticGroup
--         DESCRIPTION 
--             "This group is mandatory for devices that allow crea-
--              tion  of  rows  in any of the writable tables of this
--              MIB."

--         OBJECT      diffServClfrStatus
--         MIN-ACCESS  read-only
--         DESCRIPTION 
--             "Write access is not required."

--         OBJECT      diffServClfrElementOrder
--         MIN-ACCESS  read-only
--         DESCRIPTION 
--             "Write access is not required."

--         OBJECT      diffServClfrElementNext
--         MIN-ACCESS  read-only
--         DESCRIPTION 
--             "Write access is not required."

--         OBJECT      diffServClfrElementSpecific
--         MIN-ACCESS  read-only
--         DESCRIPTION 
--             "Write access is not required."

--         OBJECT      diffServClfrElementStatus
--         MIN-ACCESS  read-only
--         DESCRIPTION 
--             "Write access is not required."

--         OBJECT      diffServSixTupleClfrDstAddrType
--         MIN-ACCESS  read-only
--         DESCRIPTION 
--             "Write access is not required."

--         OBJECT      diffServSixTupleClfrDstAddr
--         MIN-ACCESS  read-only
--         DESCRIPTION 
--             "Write access is not required."

--         OBJECT      diffServSixTupleClfrDstAddrMask
--         MIN-ACCESS  read-only
--         DESCRIPTION 
--             "Write access is not required."

--         OBJECT      diffServSixTupleClfrSrcAddrType
--         MIN-ACCESS  read-only
--         DESCRIPTION 
--             "Write access is not required."

--         OBJECT      diffServSixTupleClfrSrcAddr
--         MIN-ACCESS  read-only
--         DESCRIPTION 
--             "Write access is not required."

--         OBJECT      diffServSixTupleClfrSrcAddrMask
--         MIN-ACCESS  read-only
--         DESCRIPTION 
--             "Write access is not required."

--         OBJECT      diffServSixTupleClfrDscp
--         MIN-ACCESS  read-only
--         DESCRIPTION 
--             "Write access is not required."

--         OBJECT      diffServSixTupleClfrProtocol
--         MIN-ACCESS  read-only
--         DESCRIPTION 
--             "Write access is not required."

--         OBJECT      diffServSixTupleClfrSrcL4PortMin
--         MIN-ACCESS  read-only
--         DESCRIPTION 
--             "Write access is not required."

--         OBJECT      diffServSixTupleClfrSrcL4PortMax
--         MIN-ACCESS  read-only
--         DESCRIPTION 
--             "Write access is not required."

--         OBJECT      diffServSixTupleClfrDstL4PortMin
--         MIN-ACCESS  read-only
--         DESCRIPTION 
--             "Write access is not required."

--         OBJECT      diffServSixTupleClfrDstL4PortMax
--         MIN-ACCESS  read-only
--         DESCRIPTION 
--             "Write access is not required."

--         OBJECT      diffServSixTupleClfrStatus
--         MIN-ACCESS  read-only
--         DESCRIPTION 
--             "Write access is not required."

--         OBJECT      diffServMeterSucceedNext
--         MIN-ACCESS  read-only
--         DESCRIPTION 
--             "Write access is not required."

--         OBJECT      diffServMeterFailNext
--         MIN-ACCESS  read-only
--         DESCRIPTION 
--             "Write access is not required."

--         OBJECT      diffServMeterSpecific
--         MIN-ACCESS  read-only
--         DESCRIPTION 
--             "Write access is not required."

--         OBJECT      diffServMeterStatus
--         MIN-ACCESS  read-only
--         DESCRIPTION 
--             "Write access is not required."

--         OBJECT      diffServTBMeterType
--         MIN-ACCESS  read-only
--         DESCRIPTION 
--             "Write access is not required."

--         OBJECT      diffServTBMeterRate
--         MIN-ACCESS  read-only
--         DESCRIPTION 
--             "Write access is not required."

--         OBJECT      diffServTBMeterBurstSize
--         MIN-ACCESS  read-only
--         DESCRIPTION 
--             "Write access is not required."

--         OBJECT      diffServTBMeterInterval
--         MIN-ACCESS  read-only
--         DESCRIPTION 
--             "Write access is not required."

--         OBJECT      diffServTBMeterStatus
--         MIN-ACCESS  read-only
--         DESCRIPTION 
--             "Write access is not required."

--         OBJECT      diffServActionNext
--         MIN-ACCESS  read-only
--         DESCRIPTION 
--             "Write access is not required."

--         OBJECT      diffServActionSpecific
--         MIN-ACCESS  read-only
--         DESCRIPTION 
--             "Write access is not required."

--         OBJECT      diffServActionType
--         MIN-ACCESS  read-only
--         DESCRIPTION 
--             "Write access is not required."

--         OBJECT      diffServActionStatus
--         MIN-ACCESS  read-only
--         DESCRIPTION 
--             "Write access is not required."

--         OBJECT      diffServCountActStatus
--         MIN-ACCESS  read-only
--         DESCRIPTION 
--             "Write access is not required."

--         OBJECT      diffServAlgDropType
--         MIN-ACCESS  read-only
--         DESCRIPTION 
--             "Write access is not required."

--         OBJECT      diffServAlgDropNext
--         MIN-ACCESS  read-only
--         DESCRIPTION 
--             "Write access is not required."

--         OBJECT      diffServAlgDropQMeasure
--         MIN-ACCESS  read-only
--         DESCRIPTION 
--             "Write access is not required."

--         OBJECT      diffServAlgDropQThreshold
--         MIN-ACCESS  read-only
--         DESCRIPTION 
--             "Write access is not required."

--         OBJECT      diffServAlgDropSpecific
--         MIN-ACCESS  read-only
--         DESCRIPTION 
--             "Write access is not required."

--         OBJECT      diffServAlgDropStatus
--         MIN-ACCESS  read-only
--         DESCRIPTION 
--             "Write access is not required."

--         OBJECT      diffServRandomDropMinThreshBytes
--         MIN-ACCESS  read-only
--         DESCRIPTION 
--             "Write access is not required."

--         OBJECT      diffServRandomDropMinThreshPkts
--         MIN-ACCESS  read-only
--         DESCRIPTION 
--             "Write access is not required."

--         OBJECT      diffServRandomDropMaxThreshBytes
--         MIN-ACCESS  read-only
--         DESCRIPTION 
--             "Write access is not required."

--         OBJECT      diffServRandomDropMaxThreshPkts
--         MIN-ACCESS  read-only
--         DESCRIPTION 
--             "Write access is not required."

--         OBJECT      diffServRandomDropInvProbMax
--         MIN-ACCESS  read-only
--         DESCRIPTION 
--             "Write access is not required."

--         OBJECT      diffServRandomDropInvWeight
--         MIN-ACCESS  read-only
--         DESCRIPTION 
--             "Write access is not required."

--         OBJECT      diffServRandomDropSamplingRate
--         MIN-ACCESS  read-only
--         DESCRIPTION 
--             "Write access is not required."

--         OBJECT      diffServRandomDropStatus
--         MIN-ACCESS  read-only
--         DESCRIPTION 
--             "Write access is not required."

--         OBJECT      diffServQNext
--         MIN-ACCESS  read-only
--         DESCRIPTION 
--             "Write access is not required."

--         OBJECT      diffServQSchdParam
--         MIN-ACCESS  read-only
--         DESCRIPTION 
--             "Write access is not required."

--         OBJECT      diffServQStatus
--         MIN-ACCESS  read-only
--         DESCRIPTION 
--             "Write access is not required."

--         OBJECT      diffServSchedulerNext
--         MIN-ACCESS  read-only
--         DESCRIPTION 
--             "Write access is not required."

--         OBJECT      diffServSchedulerMethod
--         MIN-ACCESS  read-only
--         DESCRIPTION 
--             "Write access is not required."

--         OBJECT      diffServSchedulerSchdParam
--         MIN-ACCESS  read-only
--         DESCRIPTION 
--             "Write access is not required."

--         OBJECT      diffServSchedulerStatus
--         MIN-ACCESS  read-only
--         DESCRIPTION 
--             "Write access is not required."

--         OBJECT      diffServSchdParamPriority
--         MIN-ACCESS  read-only
--         DESCRIPTION 
--             "Write access is not required."

--         OBJECT      diffServSchdParamMinRateAbs
--         MIN-ACCESS  read-only
--         DESCRIPTION 
--             "Write access is not required."

--         OBJECT      diffServSchdParamMinRateRel
--         MIN-ACCESS  read-only
--         DESCRIPTION 
--             "Write access is not required."

--         OBJECT      diffServSchdParamMaxRateAbs
--         MIN-ACCESS  read-only
--         DESCRIPTION 
--             "Write access is not required."

--         OBJECT      diffServSchdParamMaxRateRel
--         MIN-ACCESS  read-only
--         DESCRIPTION 
--             "Write access is not required."

--         OBJECT      diffServSchdParamBurstSize
--         MIN-ACCESS  read-only
--         DESCRIPTION 
--             "Write access is not required."

--         OBJECT      diffServSchdParamStatus
--         MIN-ACCESS  read-only
--         DESCRIPTION 
--             "Write access is not required."

--     ::= { diffServMIBCompliances 1 }

END -- end of module DIFF-SERV-MIB.
