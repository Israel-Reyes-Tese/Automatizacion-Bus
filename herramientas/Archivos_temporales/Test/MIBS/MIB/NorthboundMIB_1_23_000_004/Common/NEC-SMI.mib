--
-- NEC Corporation root SMI
--
-- Copyright (C) 1999, 2000 by NEC Corporation.
-- All rights reserved.
--

	NEC-SMI DEFINITIONS ::= BEGIN

	IMPORTS
		enterprises
			FROM RFC1155-SMI;

	nec OBJECT IDENTIFIER
		::= { enterprises 119 }

	nec-mib OBJECT IDENTIFIER
		::= { nec 2 }

	necProductDepend OBJECT IDENTIFIER
		::= { nec-mib 3 }

	radioEquipment OBJECT IDENTIFIER
		::= { necProductDepend 69 }

	pnms OBJECT IDENTIFIER
		::= { radioEquipment 201 }

	commonPnms OBJECT IDENTIFIER
		::= { radioEquipment 203 }

	pnmsPlus OBJECT IDENTIFIER
		::= { radioEquipment 211 }

	commonPnmsPlus OBJECT IDENTIFIER
		::= { radioEquipment 213 }

END
