--
-- This SMIv1 module has been generated by smidump 0.2-cvs. Do not edit.
--

SNMPv2-SMI DEFINITIONS ::= BEGIN

ExtUTCTime ::=
    OCTET STRING (SIZE(11 | 13))

ObjectName ::=
    OBJECT IDENTIFIER

NotificationName ::=
    OBJECT IDENTIFIER

Integer32 ::=
    INTEGER (-2147483648..2147483647)

IpAddress ::=
    OCTET STRING (SIZE(4))

Counter32 ::=
    Gauge (0..4294967295)

Gauge32 ::=
    Gauge (0..4294967295)

Unsigned32 ::=
    Gauge (0..4294967295)

TimeTicks ::=
    Gauge (0..4294967295)

Opaque ::=
    OCTET STRING

-- Counter64 ::=
--     Unsigned64 (0..18446744073709551615)

zeroDotZero OBJECT IDENTIFIER
    ::= { 0 0 }

org OBJECT IDENTIFIER
    ::= { iso 3 }

dod OBJECT IDENTIFIER
    ::= { org 6 }

internet OBJECT IDENTIFIER
    ::= { dod 1 }

directory OBJECT IDENTIFIER
    ::= { internet 1 }

mgmt OBJECT IDENTIFIER
    ::= { internet 2 }

mib-2 OBJECT IDENTIFIER
    ::= { mgmt 1 }

transmission OBJECT IDENTIFIER
    ::= { mib-2 10 }

experimental OBJECT IDENTIFIER
    ::= { internet 3 }

private OBJECT IDENTIFIER
    ::= { internet 4 }

enterprises OBJECT IDENTIFIER
    ::= { private 1 }

security OBJECT IDENTIFIER
    ::= { internet 5 }

snmpV2 OBJECT IDENTIFIER
    ::= { internet 6 }

snmpDomains OBJECT IDENTIFIER
    ::= { snmpV2 1 }

snmpProxys OBJECT IDENTIFIER
    ::= { snmpV2 2 }

snmpModules OBJECT IDENTIFIER
    ::= { snmpV2 3 }

END -- end of module SNMPv2-SMI.
