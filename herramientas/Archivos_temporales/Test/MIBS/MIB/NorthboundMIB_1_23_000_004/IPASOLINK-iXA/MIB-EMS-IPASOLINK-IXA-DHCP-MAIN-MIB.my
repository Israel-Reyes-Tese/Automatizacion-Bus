MIB-EMS-IPASOLINK-IXA-DHCP-MAIN-MIB DEFINITIONS ::= BEGIN
    
    IMPORTS
        InterfaceIndex
            FROM IF-MIB
        OBJECT-TYPE
            FROM RFC-1212
        IpAddress
            FROM RFC1155-SMI
        enterprises
            FROM SNMPv2-SMI
        MacAddress, RowStatus
            FROM SNMPv2-TC;
    
    EnableDisableValue ::=
        INTEGER { invalid(0), disable(1), enable(2) }
    
    
    -- 1.3.6.1.4.1.119
    nec OBJECT IDENTIFIER
        ::= { enterprises 119 }
    
    -- 1.3.6.1.4.1.119.2
    nec-mib OBJECT IDENTIFIER
        ::= { nec 2 }
    
    -- 1.3.6.1.4.1.119.2.3
    necProductDepend OBJECT IDENTIFIER
        ::= { nec-mib 3 }
    
    -- 1.3.6.1.4.1.119.2.3.69
    radioEquipment OBJECT IDENTIFIER
        ::= { necProductDepend 69 }
    
    -- 1.3.6.1.4.1.119.2.3.69.203
    commonPnms OBJECT IDENTIFIER
        ::= { radioEquipment 203 }
    
    -- 1.3.6.1.4.1.119.2.3.69.203.518
    ipasolinkIxA OBJECT IDENTIFIER
        ::= { commonPnms 518 }
    
    -- 1.3.6.1.4.1.119.2.3.69.203.518.5
    system5 OBJECT IDENTIFIER
        ::= { ipasolinkIxA 5 }
    
    -- 1.3.6.1.4.1.119.2.3.69.203.518.5.3
    ipeConfigurationGroup OBJECT IDENTIFIER
        ::= { system5 3 }
    
    -- 1.3.6.1.4.1.119.2.3.69.203.518.5.3.13
    ipeCfgDhcpGroup OBJECT IDENTIFIER
        ::= { ipeConfigurationGroup 13 }
    
    -- 1.3.6.1.4.1.119.2.3.69.203.518.5.3.13.2
    ipeCfgDhcpMainServerTable OBJECT-TYPE
        SYNTAX      SEQUENCE OF IpeCfgDhcpMainServerEntry
        ACCESS      not-accessible
        STATUS      mandatory
        DESCRIPTION
            "IPv4 DHCP server/relay configuraion table for main traffic."
        ::= { ipeCfgDhcpGroup 2 }
    
    -- 1.3.6.1.4.1.119.2.3.69.203.518.5.3.13.2.1
    ipeCfgDhcpMainServerEntry OBJECT-TYPE
        SYNTAX      IpeCfgDhcpMainServerEntry
        ACCESS      not-accessible
        STATUS      mandatory
        DESCRIPTION
            "Entry of IPv4 DHCP server/relay configuraion table."
        INDEX       { ipeCfgDhcpMainServerNEAddress, ipeCfgDhcpMainServerIndex }
        ::= { ipeCfgDhcpMainServerTable 1 }
    
    IpeCfgDhcpMainServerEntry ::= SEQUENCE {
        ipeCfgDhcpMainServerIndex                   INTEGER,
        ipeCfgDhcpMainServerNEAddress               IpAddress,
        ipeCfgDhcpMainServerEnable                  EnableDisableValue,
        ipeCfgDhcpMainServerMode                    INTEGER,
        ipeCfgDhcpMainServerInterface               InterfaceIndex,
        ipeCfgDhcpMainServerIpAddr                  IpAddress,
        ipeCfgDhcpMainServerLeaseTime               INTEGER,
        ipeCfgDhcpMainServerLeaseAddrRangeBegin     IpAddress,
        ipeCfgDhcpMainServerLeaseAddrRangeEnd       IpAddress,
        ipeCfgDhcpMainServerLeaseAddrExcludeBegin   IpAddress,
        ipeCfgDhcpMainServerLeaseAddrExcludeEnd     IpAddress,
        ipeCfgDhcpMainServerOptGatewayAddrEnable    INTEGER,
        ipeCfgDhcpMainServerOptGatewayAddr          IpAddress,
        ipeCfgDhcpMainServerOptDnsServerPrimary     IpAddress,
        ipeCfgDhcpMainServerOptDnsServerSecondary   IpAddress,
        ipeCfgDhcpMainServerOptSpecifyEnable        EnableDisableValue,
        ipeCfgDhcpMainServerOptSpecifyId            INTEGER,
        ipeCfgDhcpMainServerOptSpecifyType          INTEGER,
        ipeCfgDhcpMainServerOptSpecifyValue         OCTET STRING,
        ipeCfgDhcpMainServerSecurityLevel           INTEGER,
        ipeCfgDhcpMainServerRegisteredMacId         INTEGER
    }
    
    -- 1.3.6.1.4.1.119.2.3.69.203.518.5.3.13.2.1.1
    ipeCfgDhcpMainServerIndex OBJECT-TYPE
        SYNTAX      INTEGER (1..16)
        ACCESS      not-accessible
        STATUS      mandatory
        DESCRIPTION
            "Index of this table."
        ::= { ipeCfgDhcpMainServerEntry 1 }
    
    -- 1.3.6.1.4.1.119.2.3.69.203.518.5.3.13.2.1.2
    ipeCfgDhcpMainServerNEAddress OBJECT-TYPE
        SYNTAX      IpAddress
        ACCESS      not-accessible
        STATUS      mandatory
        DESCRIPTION
            "Reserved object for northbound interface."
        ::= { ipeCfgDhcpMainServerEntry 2 }
    
    -- 1.3.6.1.4.1.119.2.3.69.203.518.5.3.13.2.1.3
    ipeCfgDhcpMainServerEnable OBJECT-TYPE
        SYNTAX      EnableDisableValue
        ACCESS      read-only
        STATUS      mandatory
        DESCRIPTION
            "Enable/Disable this DHCP server/relay agent.
    
             disable : DHCP server/relay agent is disabled
             enable  : DHCP server/relay agent is enabled"
        DEFVAL      { disable }
        ::= { ipeCfgDhcpMainServerEntry 3 }
    
    -- 1.3.6.1.4.1.119.2.3.69.203.518.5.3.13.2.1.4
    ipeCfgDhcpMainServerMode OBJECT-TYPE
        SYNTAX      INTEGER { invalid(0), server(1), relay(2) }
        ACCESS      read-only
        STATUS      mandatory
        DESCRIPTION
            "Configuration of operation mode.
    
             server : This instance is DHCP server mode.
             relay  : This instance is DHCP relay agent mode.
    
             When ipeCfgDhcpMainServerIndex is 1-3, both server and relay can
             configurable. In this case, the default value is server.
             When ipeCfgDhcpMainServerIndex is 4-16, only relay can
             configurable. In this case, the default value is relay."
        ::= { ipeCfgDhcpMainServerEntry 4 }
    
    -- 1.3.6.1.4.1.119.2.3.69.203.518.5.3.13.2.1.5
    ipeCfgDhcpMainServerInterface OBJECT-TYPE
        SYNTAX      InterfaceIndex
        ACCESS      read-only
        STATUS      mandatory
        DESCRIPTION
            "Interface index of local m-plane interface which communicate
             with DHCP client.
             The value of this object doesn't overlap with other instance."
        ::= { ipeCfgDhcpMainServerEntry 5 }
    
    -- 1.3.6.1.4.1.119.2.3.69.203.518.5.3.13.2.1.6
    ipeCfgDhcpMainServerIpAddr OBJECT-TYPE
        SYNTAX      IpAddress
        ACCESS      read-only
        STATUS      mandatory
        DESCRIPTION
            "IPv4 address of DHCP server.
             This object is effective only if DHCP relay agent mode."
        ::= { ipeCfgDhcpMainServerEntry 6 }
    
    -- 1.3.6.1.4.1.119.2.3.69.203.518.5.3.13.2.1.7
    ipeCfgDhcpMainServerLeaseTime OBJECT-TYPE
        SYNTAX      INTEGER (0 | 60..259200)
        ACCESS      read-only
        STATUS      mandatory
        DESCRIPTION
            "The lease time of IPv4 Address provides to DHCP Client. The unit
             is seconds.
             0 means inifinity.
             This object is effective only if DHCP server mode."
        DEFVAL      { 86400 }
        ::= { ipeCfgDhcpMainServerEntry 7 }
    
    -- 1.3.6.1.4.1.119.2.3.69.203.518.5.3.13.2.1.8
    ipeCfgDhcpMainServerLeaseAddrRangeBegin OBJECT-TYPE
        SYNTAX      IpAddress
        ACCESS      read-only
        STATUS      mandatory
        DESCRIPTION
            "First IPv4 address within the range of lease address.
             This IP address is less equal than
             ipeCfgDhcpMainServerAddrRangeEnd.
             This object is effective only if DHCP server mode."
        DEFVAL      { '00000000'H }
        ::= { ipeCfgDhcpMainServerEntry 8 }
    
    -- 1.3.6.1.4.1.119.2.3.69.203.518.5.3.13.2.1.9
    ipeCfgDhcpMainServerLeaseAddrRangeEnd OBJECT-TYPE
        SYNTAX      IpAddress
        ACCESS      read-only
        STATUS      mandatory
        DESCRIPTION
            "Last IPv4 address within the range of lease address.
             This IPv4 address is greater equal than
             ipeCfgDhcpMainServerAddrRangeBegin. This object is effective only
             if DHCP server mode."
        DEFVAL      { '00000000'H }
        ::= { ipeCfgDhcpMainServerEntry 9 }
    
    -- 1.3.6.1.4.1.119.2.3.69.203.518.5.3.13.2.1.10
    ipeCfgDhcpMainServerLeaseAddrExcludeBegin OBJECT-TYPE
        SYNTAX      IpAddress
        ACCESS      read-only
        STATUS      mandatory
        DESCRIPTION
            "First IPv4 address within the range of lease exclude address.
             DHCP server don't lease IP address within lease exclude address.
             This IPv4 address is less equal than ipeCfgDhcpMainServerAddr-
             ExcludeEnd.
             This object is effective only if  DHCP server mode."
        DEFVAL      { '00000000'H }
        ::= { ipeCfgDhcpMainServerEntry 10 }
    
    -- 1.3.6.1.4.1.119.2.3.69.203.518.5.3.13.2.1.11
    ipeCfgDhcpMainServerLeaseAddrExcludeEnd OBJECT-TYPE
        SYNTAX      IpAddress
        ACCESS      read-only
        STATUS      mandatory
        DESCRIPTION
            "Last IPv4 address within the range of lease exclude address.
             DHCP server don't lease IP address within lease exclude address.
             This IPv4 address is less equal than ipeCfgDhcpMainServerAddr-
             ExcludeBegin.
             This object is effective only if  DHCP server mode."
        DEFVAL      { '00000000'H }
        ::= { ipeCfgDhcpMainServerEntry 11 }
    
    -- 1.3.6.1.4.1.119.2.3.69.203.518.5.3.13.2.1.12
    ipeCfgDhcpMainServerOptGatewayAddrEnable OBJECT-TYPE
        SYNTAX      INTEGER { invalid(0), enabledInterface(1),
                        enabledSpecify(2), disabled(3) }
        ACCESS      read-only
        STATUS      mandatory
        DESCRIPTION
            "Switch that how to handle gateway IP address option on DHCP
             server.
    
               enabledInterface : Use interface IP address. DHCP server
                                  provides gateway IP address configured on
                                  interface which is set to
                                  ipeCfgDhcpMainServerInterface.
               enabledSpecify   : Use IP address which is set to
                                  ipeCfgDhcpMainServerOptGatewayAddr.
               disabled         : DHCP server doesn't provide gateway IP
                                  address.
    
             This object is effective only if DHCP server mode."
        DEFVAL      { enabledInterface }
        ::= { ipeCfgDhcpMainServerEntry 12 }
    
    -- 1.3.6.1.4.1.119.2.3.69.203.518.5.3.13.2.1.13
    ipeCfgDhcpMainServerOptGatewayAddr OBJECT-TYPE
        SYNTAX      IpAddress
        ACCESS      read-only
        STATUS      mandatory
        DESCRIPTION
            "Gateway IP address which is provided by DHCP server.
    
             This object is effective only if DHCP server mode and
             ipeCfgDhcpMainServerOptGatewayAddrEnable is set to
             enabledSpecify."
        DEFVAL      { '00000000'H }
        ::= { ipeCfgDhcpMainServerEntry 13 }
    
    -- 1.3.6.1.4.1.119.2.3.69.203.518.5.3.13.2.1.14
    ipeCfgDhcpMainServerOptDnsServerPrimary OBJECT-TYPE
        SYNTAX      IpAddress
        ACCESS      read-only
        STATUS      mandatory
        DESCRIPTION
            "Primary DNS server address which is provided by DHCP server.
    
             This object is effective only if DHCP server mode."
        DEFVAL      { '00000000'H }
        ::= { ipeCfgDhcpMainServerEntry 14 }
    
    -- 1.3.6.1.4.1.119.2.3.69.203.518.5.3.13.2.1.15
    ipeCfgDhcpMainServerOptDnsServerSecondary OBJECT-TYPE
        SYNTAX      IpAddress
        ACCESS      read-only
        STATUS      mandatory
        DESCRIPTION
            "Secoundary DNS server address which is provided by DHCP server.
    
             In order to configure this object.
             ipeCfgDhcpMainServerOptDnsServerPrimary must be set in advance.
    
    
             This object is effective only if DHCP server mode."
        DEFVAL      { '00000000'H }
        ::= { ipeCfgDhcpMainServerEntry 15 }
    
    -- 1.3.6.1.4.1.119.2.3.69.203.518.5.3.13.2.1.16
    ipeCfgDhcpMainServerOptSpecifyEnable OBJECT-TYPE
        SYNTAX      EnableDisableValue
        ACCESS      read-only
        STATUS      mandatory
        DESCRIPTION
            "Switch that whether DHCP server add user specified option to
             DHCP message.
    
             enable  : DHCP server add user specified option.
             disable : DHCP server doesn't add user specified otption.
    
             This object is effective only if DHCP server mode."
        DEFVAL      { disable }
        ::= { ipeCfgDhcpMainServerEntry 16 }
    
    -- 1.3.6.1.4.1.119.2.3.69.203.518.5.3.13.2.1.17
    ipeCfgDhcpMainServerOptSpecifyId OBJECT-TYPE
        SYNTAX      INTEGER (0..255)
        ACCESS      read-only
        STATUS      mandatory
        DESCRIPTION
            "Option id which DHCP server adds user specified option to DHCP
             message.
             This object is effective only if DHCP server mode and ipeCfgDhcp-
             MainServerOptSpecifyEnable is set to enabled."
        DEFVAL      { 0 }
        ::= { ipeCfgDhcpMainServerEntry 17 }
    
    -- 1.3.6.1.4.1.119.2.3.69.203.518.5.3.13.2.1.18
    ipeCfgDhcpMainServerOptSpecifyType OBJECT-TYPE
        SYNTAX      INTEGER { invalid(0), ipv4(1), ipv6(2), displayString(3),
                        octetString(4) }
        ACCESS      read-only
        STATUS      mandatory
        DESCRIPTION
            "Option type which DHCP server adds to DHCP message.
             This object is effective only if DHCP server mode and ipeCfgDhcp-
             MainServerOptSpecifyEnable is set to enabled."
        DEFVAL      { ipv4 }
        ::= { ipeCfgDhcpMainServerEntry 18 }
    
    -- 1.3.6.1.4.1.119.2.3.69.203.518.5.3.13.2.1.19
    ipeCfgDhcpMainServerOptSpecifyValue OBJECT-TYPE
        SYNTAX      OCTET STRING (SIZE(0..255))
        ACCESS      read-only
        STATUS      mandatory
        DESCRIPTION
            "Option value which DHCP server adds to DHCP message.
             This object is decoded according to
             ipeCfgDhcpMainServerOptSpecifyType.
    
             ipv4          : Syntax is IpAddress.
             ipv6          : Syntax is Ipv6Address.
             displayString : Syntax is DisplayString.
             octetString   : Syntax is OCTET STRING.
    
             This object is effective only if DHCP server mode and
             ipeCfgDhcpMainServerOptSpecifyEnable is set to enabled."
        ::= { ipeCfgDhcpMainServerEntry 19 }
    
    -- 1.3.6.1.4.1.119.2.3.69.203.518.5.3.13.2.1.20
    ipeCfgDhcpMainServerSecurityLevel OBJECT-TYPE
        SYNTAX      INTEGER { invalid(0), any(1), onlyRegistered(2) }
        ACCESS      read-only
        STATUS      mandatory
        DESCRIPTION
            "Security level of this DHCP server.
    
             any            : DHCP server doesn't check MAC address except for
                              rejected MAC address.
             onlyRegistered : DHCP server provides IP address only to
                              registered MAC addresss.
    
             Note : Rejected MAC address is examined even if
                    ipeCfgDhcpMainServerSecurityLevel is set to any.
             This object is effective only if DHCP server mode."
        DEFVAL      { any }
        ::= { ipeCfgDhcpMainServerEntry 20 }
    
    -- 1.3.6.1.4.1.119.2.3.69.203.518.5.3.13.2.1.21
    ipeCfgDhcpMainServerRegisteredMacId OBJECT-TYPE
        SYNTAX      INTEGER (0..3)
        ACCESS      read-only
        STATUS      mandatory
        DESCRIPTION
            "The identifier of ipeCfgDhcpMainServerRegisteredMacEnrty.
             0 means no registered/rejected IP address exists.
             This object is effective only if DHCP server mode."
        DEFVAL      { 0 }
        ::= { ipeCfgDhcpMainServerEntry 21 }
    
    -- 1.3.6.1.4.1.119.2.3.69.203.518.5.3.13.3
    ipeCfgDhcpMainRegisteredMacTable OBJECT-TYPE
        SYNTAX      SEQUENCE OF IpeCfgDhcpMainRegisteredMacEntry
        ACCESS      not-accessible
        STATUS      mandatory
        DESCRIPTION
            "IPv4 registered MAC address table for DHCP server."
        ::= { ipeCfgDhcpGroup 3 }
    
    -- 1.3.6.1.4.1.119.2.3.69.203.518.5.3.13.3.1
    ipeCfgDhcpMainRegisteredMacEntry OBJECT-TYPE
        SYNTAX      IpeCfgDhcpMainRegisteredMacEntry
        ACCESS      not-accessible
        STATUS      mandatory
        DESCRIPTION
            "Entry of IPv4 registered MAC address table."
        INDEX       { ipeCfgDhcpMainRegisteredMacNEAddress, ipeCfgDhcpMainRegisteredMacId,
                      ipeCfgDhcpMainRegisteredMacNo }
        ::= { ipeCfgDhcpMainRegisteredMacTable 1 }
    
    IpeCfgDhcpMainRegisteredMacEntry ::= SEQUENCE {
        ipeCfgDhcpMainRegisteredMacId           INTEGER,
        ipeCfgDhcpMainRegisteredMacNo           INTEGER,
        ipeCfgDhcpMainRegisteredMacNEAddress    IpAddress,
        ipeCfgDhcpMainRegisteredMacAddr         MacAddress,
        ipeCfgDhcpMainRegisteredMacIpAddr       IpAddress,
        ipeCfgDhcpMainRegisteredMacRowStatus    RowStatus
    }
    
    -- 1.3.6.1.4.1.119.2.3.69.203.518.5.3.13.3.1.1
    ipeCfgDhcpMainRegisteredMacId OBJECT-TYPE
        SYNTAX      INTEGER (1..3)
        ACCESS      not-accessible
        STATUS      mandatory
        DESCRIPTION
            "Index of this table. This object means identifier of registered
             MAC entry."
        ::= { ipeCfgDhcpMainRegisteredMacEntry 1 }
    
    -- 1.3.6.1.4.1.119.2.3.69.203.518.5.3.13.3.1.2
    ipeCfgDhcpMainRegisteredMacNo OBJECT-TYPE
        SYNTAX      INTEGER (1..256)
        ACCESS      not-accessible
        STATUS      mandatory
        DESCRIPTION
            "Index of this table. This object means MAC address number whthin
             this registered MAC entry."
        ::= { ipeCfgDhcpMainRegisteredMacEntry 2 }
    
    -- 1.3.6.1.4.1.119.2.3.69.203.518.5.3.13.3.1.3
    ipeCfgDhcpMainRegisteredMacNEAddress OBJECT-TYPE
        SYNTAX      IpAddress
        ACCESS      not-accessible
        STATUS      mandatory
        DESCRIPTION
            "Reserved object for northbound interface."
        ::= { ipeCfgDhcpMainRegisteredMacEntry 3 }
    
    -- 1.3.6.1.4.1.119.2.3.69.203.518.5.3.13.3.1.4
    ipeCfgDhcpMainRegisteredMacAddr OBJECT-TYPE
        SYNTAX      MacAddress
        ACCESS      read-only
        STATUS      mandatory
        DESCRIPTION
            "This object means registered MAC address. When ipeCfgDhcpMain-
             ServerSecurityLevel is set to onlyRegisterd, DHCP server accept
             DHCP message sent from registered MAC address.
    
             This object must be set when the row is created."
        ::= { ipeCfgDhcpMainRegisteredMacEntry 4 }
    
    -- 1.3.6.1.4.1.119.2.3.69.203.518.5.3.13.3.1.5
    ipeCfgDhcpMainRegisteredMacIpAddr OBJECT-TYPE
        SYNTAX      IpAddress
        ACCESS      read-only
        STATUS      mandatory
        DESCRIPTION
            "IP address correspond to registered MAC address. If DHCP server
             receives DHCP DISCOVER from registered MAC address, it provide
             corresponding IP address set to this object.
    
             When this object is set to 0.0.0.0, DHCP server provide any
             address whthin the lease address range.
             When this object is set to 255.255.255.255, DHCP server treats
             this MAC address as rejected MAC Address."
        DEFVAL      { '00000000'H }
        ::= { ipeCfgDhcpMainRegisteredMacEntry 5 }
    
    -- 1.3.6.1.4.1.119.2.3.69.203.518.5.3.13.3.1.6
    ipeCfgDhcpMainRegisteredMacRowStatus OBJECT-TYPE
        SYNTAX      RowStatus
        ACCESS      read-only
        STATUS      mandatory
        DESCRIPTION
            "RowStatus of this entry. The system supports three values shonw
             below.
    
             active(1)      : change attribute in existing instance.
             createAndGo(4) : create the instance.
             destroy(6)     : delete the instance."
        ::= { ipeCfgDhcpMainRegisteredMacEntry 6 }
    
    -- 1.3.6.1.4.1.119.2.3.69.203.518.5.8
    ipeCommandGroup OBJECT IDENTIFIER
        ::= { system5 8 }
    
    -- 1.3.6.1.4.1.119.2.3.69.203.518.5.8.13
    ipeCmdDhcpGroup OBJECT IDENTIFIER
        ::= { ipeCommandGroup 13 }
    
    -- 1.3.6.1.4.1.119.2.3.69.203.518.5.8.13.1
    ipeCmdDhcpMainTable OBJECT-TYPE
        SYNTAX      SEQUENCE OF IpeCmdDhcpMainEntry
        ACCESS      not-accessible
        STATUS      mandatory
        DESCRIPTION
            "Maintenance table for DHCP server."
        ::= { ipeCmdDhcpGroup 1 }
    
    -- 1.3.6.1.4.1.119.2.3.69.203.518.5.8.13.1.1
    ipeCmdDhcpMainEntry OBJECT-TYPE
        SYNTAX      IpeCmdDhcpMainEntry
        ACCESS      not-accessible
        STATUS      mandatory
        DESCRIPTION
            "Command entry for IPv4 DHCP server."
        INDEX       { ipeCmdDhcpMainNEAddress, ipeCmdDhcpMainIndex, ipeCmdDhcpMainLeaseIpAddr }
        ::= { ipeCmdDhcpMainTable 1 }
    
    IpeCmdDhcpMainEntry ::= SEQUENCE {
        ipeCmdDhcpMainIndex         INTEGER,
        ipeCmdDhcpMainLeaseIpAddr   IpAddress,
        ipeCmdDhcpMainNEAddress     IpAddress,
        ipeCmdDhcpMainManualDelete  INTEGER
    }
    
    -- 1.3.6.1.4.1.119.2.3.69.203.518.5.8.13.1.1.1
    ipeCmdDhcpMainIndex OBJECT-TYPE
        SYNTAX      INTEGER (1..3)
        ACCESS      not-accessible
        STATUS      mandatory
        DESCRIPTION
            "Index of table."
        ::= { ipeCmdDhcpMainEntry 1 }
    
    -- 1.3.6.1.4.1.119.2.3.69.203.518.5.8.13.1.1.2
    ipeCmdDhcpMainLeaseIpAddr OBJECT-TYPE
        SYNTAX      IpAddress
        ACCESS      not-accessible
        STATUS      mandatory
        DESCRIPTION
            "The lease IP Address."
        ::= { ipeCmdDhcpMainEntry 2 }
    
    -- 1.3.6.1.4.1.119.2.3.69.203.518.5.8.13.1.1.3
    ipeCmdDhcpMainNEAddress OBJECT-TYPE
        SYNTAX      IpAddress
        ACCESS      not-accessible
        STATUS      mandatory
        DESCRIPTION
            "Index of table."
        ::= { ipeCmdDhcpMainEntry 3 }
    
    -- 1.3.6.1.4.1.119.2.3.69.203.518.5.8.13.1.1.4
    ipeCmdDhcpMainManualDelete OBJECT-TYPE
        SYNTAX      INTEGER { invalid(0), normal(1), manualDelete(2) }
        ACCESS      read-only
        STATUS      mandatory
        DESCRIPTION
            "Operator manually deletes this lease address.
    
             normal       : can not set this value.
             manualDelete : Delete this lease address.
                            If ipeCmdDhcpMainLeaseIpAddr is set to 0.0.0.0,
                            DHCP server deletes all entry in corresponding
                            ipeStsDhcpMainLeaseAddrEntry.
    
             Note : When you read this object, the system alwasys return
             normal."
        ::= { ipeCmdDhcpMainEntry 4 }
    
END -- end of module MIB-EMS-IPASOLINK-IXA-DHCP-MAIN-MIB.
