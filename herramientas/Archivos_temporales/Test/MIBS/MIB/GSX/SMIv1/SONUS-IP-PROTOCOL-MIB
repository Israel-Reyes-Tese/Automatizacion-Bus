--
-- This SMIv1 module has been generated by smidump 0.2-cvs. Do not edit.
--

SONUS-IP-PROTOCOL-MIB DEFINITIONS ::= BEGIN

IMPORTS
    Ipv6Address
        FROM IPV6-TC
    OBJECT-TYPE
        FROM RFC-1212
    TRAP-TYPE
        FROM RFC-1215
    Counter, Gauge, IpAddress
        FROM RFC1155-SMI
    DisplayString, RowStatus
        FROM SNMPv2-TC
    sonusEventClass, sonusEventDescription, sonusEventLevel, 
    sonusEventTime, sonusSequenceId
        FROM SONUS-COMMON-MIB
    sonusPacketMIBs
        FROM SONUS-SMI
    SonusName, SonusShelfIndex, SonusSlotIndex
        FROM SONUS-TC;

sonusIpProtocolMIB OBJECT IDENTIFIER
    ::= { sonusPacketMIBs 4 }

-- sonusIpProtocolMIB MODULE-IDENTITY
--     LAST-UPDATED    "201205050000Z"
--     ORGANIZATION    
--             "Sonus Networks, Inc."
--     CONTACT-INFO    
--             "   Customer Support    
--              Sonus Networks, Inc.
--              7 Technology Park Drive
--              Westford, MA 01886
--              USA
--              
--              Tel: 978-614-8100
--              Fax: 978-614-8609"
--     DESCRIPTION     
--             "The MIB Module for IP Protocol Management."
--     ::= { sonusPacketMIBs 4 }


sonusMib-2 OBJECT IDENTIFIER
    ::= { sonusIpProtocolMIB 2 }

sonusIp OBJECT IDENTIFIER
    ::= { sonusMib-2 4 }

sonusIpGeneralGroupTable OBJECT-TYPE
    SYNTAX          SEQUENCE OF SonusIpGeneralGroupEntry
    ACCESS          not-accessible
    STATUS          mandatory
    DESCRIPTION     
            "The collection of IP General Group information for the
             specified instance."
    ::= { sonusIp 1 }

sonusIpGeneralGroupEntry OBJECT-TYPE
    SYNTAX          SonusIpGeneralGroupEntry
    ACCESS          not-accessible
    STATUS          mandatory
    DESCRIPTION     
            "The collection of IP General Group information for the
             specified instance."
    INDEX           { sonusIpGeneralGroupShelf, sonusIpGeneralGroupSlot, 
                      sonusIpGeneralGroupInstance }
    ::= { sonusIpGeneralGroupTable 1 }

SonusIpGeneralGroupEntry ::=
    SEQUENCE {
        sonusIpForwarding               INTEGER,
        sonusIpDefaultTTL               INTEGER,
        sonusIpInReceives               Counter,
        sonusIpInHdrErrors              Counter,
        sonusIpInAddrErrors             Counter,
        sonusIpForwDatagrams            Counter,
        sonusIpInUnknownProtos          Counter,
        sonusIpInDiscards               Counter,
        sonusIpInDelivers               Counter,
        sonusIpOutRequests              Counter,
        sonusIpOutDiscards              Counter,
        sonusIpOutNoRoutes              Counter,
        sonusIpReasmTimeout             INTEGER,
        sonusIpReasmReqds               Counter,
        sonusIpReasmOKs                 Counter,
        sonusIpReasmFails               Counter,
        sonusIpFragOKs                  Counter,
        sonusIpFragFails                Counter,
        sonusIpFragCreates              Counter,
        sonusIpRoutingDiscards          Counter,
        sonusIpGeneralGroupShelf        SonusShelfIndex,
        sonusIpGeneralGroupSlot         SonusSlotIndex,
        sonusIpGeneralGroupInstance     INTEGER,
        sonusIpAclDiscards              Counter,
        sonusIp6InReceives              Counter,
        sonusIp6InHdrErrors             Counter,
        sonusIp6InAddrErrors            Counter,
        sonusIp6ForwDatagrams           Counter,
        sonusIp6InUnknownProtos         Counter,
        sonusIp6InDiscards              Counter,
        sonusIp6InDelivers              Counter,
        sonusIp6OutRequests             Counter,
        sonusIp6OutDiscards             Counter,
        sonusIp6OutNoRoutes             Counter,
        sonusIp6ReasmTimeout            INTEGER,
        sonusIp6ReasmReqds              Counter,
        sonusIp6ReasmOKs                Counter,
        sonusIp6ReasmFails              Counter,
        sonusIp6FragOKs                 Counter,
        sonusIp6FragFails               Counter,
        sonusIp6FragCreates             Counter,
        sonusIp6RoutingDiscards         Counter,
        sonusIp6AclDiscards             Counter
    }

sonusIpForwarding OBJECT-TYPE
    SYNTAX          INTEGER { forwarding(1), notForwarding(2) }
    ACCESS          read-only
    STATUS          mandatory
    DESCRIPTION     
            "The indication of whether this entity is acting as an IP
             router in respect to the forwarding of datagrams received
             by, but not addressed to, this entity.  IP routers forward
             datagrams.  IP hosts do not (except those source-routed via
             the host)."
    ::= { sonusIpGeneralGroupEntry 1 }

sonusIpDefaultTTL OBJECT-TYPE
    SYNTAX          INTEGER (1..255)
    ACCESS          read-only
    STATUS          mandatory
    DESCRIPTION     
            "The default value inserted into the Time-To-Live field of
             the IP header of datagrams originated at this entity,
             whenever a TTL value is not supplied by the transport layer
             protocol."
    ::= { sonusIpGeneralGroupEntry 2 }

sonusIpInReceives OBJECT-TYPE
    SYNTAX          Counter
    ACCESS          read-only
    STATUS          mandatory
    DESCRIPTION     
            "The total number of input datagrams received from
             interfaces, including those received in error."
    ::= { sonusIpGeneralGroupEntry 3 }

sonusIpInHdrErrors OBJECT-TYPE
    SYNTAX          Counter
    ACCESS          read-only
    STATUS          mandatory
    DESCRIPTION     
            "The number of input datagrams discarded due to errors in
             their IP headers, including bad checksums, version number
             mismatch, other format errors, time-to-live exceeded, errors
             discovered in processing their IP options, etc."
    ::= { sonusIpGeneralGroupEntry 4 }

sonusIpInAddrErrors OBJECT-TYPE
    SYNTAX          Counter
    ACCESS          read-only
    STATUS          mandatory
    DESCRIPTION     
            "The number of input datagrams discarded because the IP
             address in their IP header's destination field was not a
             valid address to be received at this entity.  This count
             includes invalid addresses (e.g., 0.0.0.0) and addresses of
             unsupported Classes (e.g., Class E).  For entities which are
             not IP routers and therefore do not forward datagrams, this
             counter includes datagrams discarded because the destination
             address was not a local address."
    ::= { sonusIpGeneralGroupEntry 5 }

sonusIpForwDatagrams OBJECT-TYPE
    SYNTAX          Counter
    ACCESS          read-only
    STATUS          mandatory
    DESCRIPTION     
            "The number of input datagrams for which this entity was not
             their final IP destination, as a result of which an attempt
             was made to find a route to forward them to that final
             destination.  In entities which do not act as IP routers,
             this counter will include only those packets which were
             Source-Routed via this entity, and the Source-Route option
             processing was successful."
    ::= { sonusIpGeneralGroupEntry 6 }

sonusIpInUnknownProtos OBJECT-TYPE
    SYNTAX          Counter
    ACCESS          read-only
    STATUS          mandatory
    DESCRIPTION     
            "The number of locally-addressed datagrams received
             successfully but discarded because of an unknown or
             unsupported protocol."
    ::= { sonusIpGeneralGroupEntry 7 }

sonusIpInDiscards OBJECT-TYPE
    SYNTAX          Counter
    ACCESS          read-only
    STATUS          mandatory
    DESCRIPTION     
            "The number of input IP datagrams for which no problems were
             encountered to prevent their continued processing, but which
             were discarded (e.g., for lack of buffer space).  Note that
             this counter does not include any datagrams discarded while
             awaiting re-assembly."
    ::= { sonusIpGeneralGroupEntry 8 }

sonusIpInDelivers OBJECT-TYPE
    SYNTAX          Counter
    ACCESS          read-only
    STATUS          mandatory
    DESCRIPTION     
            "The total number of input datagrams successfully delivered
             to IP user-protocols (including ICMP)."
    ::= { sonusIpGeneralGroupEntry 9 }

sonusIpOutRequests OBJECT-TYPE
    SYNTAX          Counter
    ACCESS          read-only
    STATUS          mandatory
    DESCRIPTION     
            "The total number of IP datagrams which local IP user-
             protocols (including ICMP) supplied to IP in requests for
             transmission.  Note that this counter does not include any
             datagrams counted in ipForwDatagrams."
    ::= { sonusIpGeneralGroupEntry 10 }

sonusIpOutDiscards OBJECT-TYPE
    SYNTAX          Counter
    ACCESS          read-only
    STATUS          mandatory
    DESCRIPTION     
            "The number of output IP datagrams for which no problem was
             encountered to prevent their transmission to their
             destination, but which were discarded (e.g., for lack of
             buffer space).  Note that this counter would include
             datagrams counted in ipForwDatagrams if any such packets met
             this (discretionary) discard criterion."
    ::= { sonusIpGeneralGroupEntry 11 }

sonusIpOutNoRoutes OBJECT-TYPE
    SYNTAX          Counter
    ACCESS          read-only
    STATUS          mandatory
    DESCRIPTION     
            "The number of IP datagrams discarded because no route could
             be found to transmit them to their destination.  Note that
             this counter includes any packets counted in ipForwDatagrams
             which meet this `no-route' criterion.  Note that this
             includes any datagrams which a host cannot route because all
             of its default routers are down."
    ::= { sonusIpGeneralGroupEntry 12 }

sonusIpReasmTimeout OBJECT-TYPE
    SYNTAX          INTEGER
    ACCESS          read-only
    STATUS          mandatory
    DESCRIPTION     
            "The maximum number of seconds which received fragments are
             held while they are awaiting reassembly at this entity."
    ::= { sonusIpGeneralGroupEntry 13 }

sonusIpReasmReqds OBJECT-TYPE
    SYNTAX          Counter
    ACCESS          read-only
    STATUS          mandatory
    DESCRIPTION     
            "The number of IP fragments received which needed to be
             reassembled at this entity."
    ::= { sonusIpGeneralGroupEntry 14 }

sonusIpReasmOKs OBJECT-TYPE
    SYNTAX          Counter
    ACCESS          read-only
    STATUS          mandatory
    DESCRIPTION     
            "The number of IP datagrams successfully re-assembled."
    ::= { sonusIpGeneralGroupEntry 15 }

sonusIpReasmFails OBJECT-TYPE
    SYNTAX          Counter
    ACCESS          read-only
    STATUS          mandatory
    DESCRIPTION     
            "The number of failures detected by the IP re-assembly
             algorithm (for whatever reason: timed out, errors, etc).
             Note that this is not necessarily a count of discarded IP
             fragments since some algorithms (notably the algorithm in
             RFC 815) can lose track of the number of fragments by
             combining them as they are received."
    ::= { sonusIpGeneralGroupEntry 16 }

sonusIpFragOKs OBJECT-TYPE
    SYNTAX          Counter
    ACCESS          read-only
    STATUS          mandatory
    DESCRIPTION     
            "The number of IP datagrams that have been successfully
             fragmented at this entity."
    ::= { sonusIpGeneralGroupEntry 17 }

sonusIpFragFails OBJECT-TYPE
    SYNTAX          Counter
    ACCESS          read-only
    STATUS          mandatory
    DESCRIPTION     
            "The number of IP datagrams that have been discarded because
             they needed to be fragmented at this entity but could not
             be, e.g., because their Don't Fragment flag was set."
    ::= { sonusIpGeneralGroupEntry 18 }

sonusIpFragCreates OBJECT-TYPE
    SYNTAX          Counter
    ACCESS          read-only
    STATUS          mandatory
    DESCRIPTION     
            "The number of IP datagram fragments that have been
             generated as a result of fragmentation at this entity."
    ::= { sonusIpGeneralGroupEntry 19 }

sonusIpRoutingDiscards OBJECT-TYPE
    SYNTAX          Counter
    ACCESS          read-only
    STATUS          mandatory
    DESCRIPTION     
            "The number of routing entries which were chosen to be
             discarded even though they are valid.  One possible reason
             for discarding such an entry could be to free-up buffer
             space for other routing entries."
    ::= { sonusIpGeneralGroupEntry 23 }

sonusIpGeneralGroupShelf OBJECT-TYPE
    SYNTAX          SonusShelfIndex
    ACCESS          read-only
    STATUS          mandatory
    DESCRIPTION     
            "A 32-bit integer identifying the shelf
             that the IP General Group table applies to"
    ::= { sonusIpGeneralGroupEntry 24 }

sonusIpGeneralGroupSlot OBJECT-TYPE
    SYNTAX          SonusSlotIndex
    ACCESS          read-only
    STATUS          mandatory
    DESCRIPTION     
            "A 32-bit integer identifying the slot
             that the IP General Group table applies to"
    ::= { sonusIpGeneralGroupEntry 25 }

sonusIpGeneralGroupInstance OBJECT-TYPE
    SYNTAX          INTEGER
    ACCESS          read-only
    STATUS          mandatory
    DESCRIPTION     
            "A 32-bit integer identifying the instance
             that the IP General Group table applies to"
    ::= { sonusIpGeneralGroupEntry 26 }

sonusIpAclDiscards OBJECT-TYPE
    SYNTAX          Counter
    ACCESS          read-only
    STATUS          mandatory
    DESCRIPTION     
            "The number of IP packets which were chosen to be
             discarded due to IP ACL rule mismatch."
    ::= { sonusIpGeneralGroupEntry 27 }

sonusIp6InReceives OBJECT-TYPE
    SYNTAX          Counter
    ACCESS          read-only
    STATUS          mandatory
    DESCRIPTION     
            "The total number of input datagrams received from
             interfaces, including those received in error."
    ::= { sonusIpGeneralGroupEntry 28 }

sonusIp6InHdrErrors OBJECT-TYPE
    SYNTAX          Counter
    ACCESS          read-only
    STATUS          mandatory
    DESCRIPTION     
            "The number of input datagrams discarded due to errors in
             their IP headers, including bad checksums, version number
             mismatch, other format errors, time-to-live exceeded, errors
             discovered in processing their IP options, etc."
    ::= { sonusIpGeneralGroupEntry 29 }

sonusIp6InAddrErrors OBJECT-TYPE
    SYNTAX          Counter
    ACCESS          read-only
    STATUS          mandatory
    DESCRIPTION     
            "The number of input datagrams discarded because the IP
             address in their IP header's destination field was not a
             valid address to be received at this entity.  This count
             includes invalid addresses (e.g., 0.0.0.0) and addresses of
             unsupported Classes (e.g., Class E).  For entities which are
             not IP routers and therefore do not forward datagrams, this
             counter includes datagrams discarded because the destination
             address was not a local address."
    ::= { sonusIpGeneralGroupEntry 30 }

sonusIp6ForwDatagrams OBJECT-TYPE
    SYNTAX          Counter
    ACCESS          read-only
    STATUS          mandatory
    DESCRIPTION     
            "The number of input datagrams for which this entity was not
             their final IP destination, as a result of which an attempt
             was made to find a route to forward them to that final
             destination.  In entities which do not act as IP routers,
             this counter will include only those packets which were
             Source-Routed via this entity, and the Source-Route option
             processing was successful."
    ::= { sonusIpGeneralGroupEntry 31 }

sonusIp6InUnknownProtos OBJECT-TYPE
    SYNTAX          Counter
    ACCESS          read-only
    STATUS          mandatory
    DESCRIPTION     
            "The number of locally-addressed datagrams received
             successfully but discarded because of an unknown or
             unsupported protocol."
    ::= { sonusIpGeneralGroupEntry 32 }

sonusIp6InDiscards OBJECT-TYPE
    SYNTAX          Counter
    ACCESS          read-only
    STATUS          mandatory
    DESCRIPTION     
            "The number of input IP datagrams for which no problems were
             encountered to prevent their continued processing, but which
             were discarded (e.g., for lack of buffer space).  Note that
             this counter does not include any datagrams discarded while
             awaiting re-assembly."
    ::= { sonusIpGeneralGroupEntry 33 }

sonusIp6InDelivers OBJECT-TYPE
    SYNTAX          Counter
    ACCESS          read-only
    STATUS          mandatory
    DESCRIPTION     
            "The total number of input datagrams successfully delivered
             to IP user-protocols (including ICMP)."
    ::= { sonusIpGeneralGroupEntry 34 }

sonusIp6OutRequests OBJECT-TYPE
    SYNTAX          Counter
    ACCESS          read-only
    STATUS          mandatory
    DESCRIPTION     
            "The total number of IP datagrams which local IP user-
             protocols (including ICMP) supplied to IP in requests for
             transmission.  Note that this counter does not include any
             datagrams counted in ipForwDatagrams."
    ::= { sonusIpGeneralGroupEntry 35 }

sonusIp6OutDiscards OBJECT-TYPE
    SYNTAX          Counter
    ACCESS          read-only
    STATUS          mandatory
    DESCRIPTION     
            "The number of output IP datagrams for which no problem was
             encountered to prevent their transmission to their
             destination, but which were discarded (e.g., for lack of
             buffer space).  Note that this counter would include
             datagrams counted in ipForwDatagrams if any such packets met
             this (discretionary) discard criterion."
    ::= { sonusIpGeneralGroupEntry 36 }

sonusIp6OutNoRoutes OBJECT-TYPE
    SYNTAX          Counter
    ACCESS          read-only
    STATUS          mandatory
    DESCRIPTION     
            "The number of IP datagrams discarded because no route could
             be found to transmit them to their destination.  Note that
             this counter includes any packets counted in ipForwDatagrams
             which meet this `no-route' criterion.  Note that this
             includes any datagrams which a host cannot route because all
             of its default routers are down."
    ::= { sonusIpGeneralGroupEntry 37 }

sonusIp6ReasmTimeout OBJECT-TYPE
    SYNTAX          INTEGER
    ACCESS          read-only
    STATUS          mandatory
    DESCRIPTION     
            "The maximum number of seconds which received fragments are
             held while they are awaiting reassembly at this entity."
    ::= { sonusIpGeneralGroupEntry 38 }

sonusIp6ReasmReqds OBJECT-TYPE
    SYNTAX          Counter
    ACCESS          read-only
    STATUS          mandatory
    DESCRIPTION     
            "The number of IP fragments received which needed to be
             reassembled at this entity."
    ::= { sonusIpGeneralGroupEntry 39 }

sonusIp6ReasmOKs OBJECT-TYPE
    SYNTAX          Counter
    ACCESS          read-only
    STATUS          mandatory
    DESCRIPTION     
            "The number of IP datagrams successfully re-assembled."
    ::= { sonusIpGeneralGroupEntry 40 }

sonusIp6ReasmFails OBJECT-TYPE
    SYNTAX          Counter
    ACCESS          read-only
    STATUS          mandatory
    DESCRIPTION     
            "The number of failures detected by the IP re-assembly
             algorithm (for whatever reason: timed out, errors, etc).
             Note that this is not necessarily a count of discarded IP
             fragments since some algorithms (notably the algorithm in
             RFC 815) can lose track of the number of fragments by
             combining them as they are received."
    ::= { sonusIpGeneralGroupEntry 41 }

sonusIp6FragOKs OBJECT-TYPE
    SYNTAX          Counter
    ACCESS          read-only
    STATUS          mandatory
    DESCRIPTION     
            "The number of IP datagrams that have been successfully
             fragmented at this entity."
    ::= { sonusIpGeneralGroupEntry 42 }

sonusIp6FragFails OBJECT-TYPE
    SYNTAX          Counter
    ACCESS          read-only
    STATUS          mandatory
    DESCRIPTION     
            "The number of IP datagrams that have been discarded because
             they needed to be fragmented at this entity but could not
             be, e.g., because their Don't Fragment flag was set."
    ::= { sonusIpGeneralGroupEntry 43 }

sonusIp6FragCreates OBJECT-TYPE
    SYNTAX          Counter
    ACCESS          read-only
    STATUS          mandatory
    DESCRIPTION     
            "The number of IP datagram fragments that have been
             generated as a result of fragmentation at this entity."
    ::= { sonusIpGeneralGroupEntry 44 }

sonusIp6RoutingDiscards OBJECT-TYPE
    SYNTAX          Counter
    ACCESS          read-only
    STATUS          mandatory
    DESCRIPTION     
            "The number of routing entries which were chosen to be
             discarded even though they are valid.  One possible reason
             for discarding such an entry could be to free-up buffer
             space for other routing entries."
    ::= { sonusIpGeneralGroupEntry 45 }

sonusIp6AclDiscards OBJECT-TYPE
    SYNTAX          Counter
    ACCESS          read-only
    STATUS          mandatory
    DESCRIPTION     
            "The number of IP packets which were chosen to be
             discarded due to IP ACL rule mismatch."
    ::= { sonusIpGeneralGroupEntry 46 }

sonusIcmp OBJECT IDENTIFIER
    ::= { sonusMib-2 5 }

sonusIcmpGeneralGroupTable OBJECT-TYPE
    SYNTAX          SEQUENCE OF SonusIcmpGeneralGroupEntry
    ACCESS          not-accessible
    STATUS          mandatory
    DESCRIPTION     
            "The collection of ICMP General Group information for the
             specified instance."
    ::= { sonusIcmp 1 }

sonusIcmpGeneralGroupEntry OBJECT-TYPE
    SYNTAX          SonusIcmpGeneralGroupEntry
    ACCESS          not-accessible
    STATUS          mandatory
    DESCRIPTION     
            "The collection of ICMP General Group information for the
             specified instance."
    INDEX           { sonusIcmpGeneralGroupShelf, 
                      sonusIcmpGeneralGroupSlot, 
                      sonusIcmpGeneralGroupInstance }
    ::= { sonusIcmpGeneralGroupTable 1 }

SonusIcmpGeneralGroupEntry ::=
    SEQUENCE {
        sonusIcmpInMsgs                 Counter,
        sonusIcmpInErrors               Counter,
        sonusIcmpInDestUnreachs         Counter,
        sonusIcmpInTimeExcds            Counter,
        sonusIcmpInParmProbs            Counter,
        sonusIcmpInSrcQuenchs           Counter,
        sonusIcmpInRedirects            Counter,
        sonusIcmpInEchos                Counter,
        sonusIcmpInEchoReps             Counter,
        sonusIcmpInTimestamps           Counter,
        sonusIcmpInTimestampReps        Counter,
        sonusIcmpInAddrMasks            Counter,
        sonusIcmpInAddrMaskReps         Counter,
        sonusIcmpOutMsgs                Counter,
        sonusIcmpOutErrors              Counter,
        sonusIcmpOutDestUnreachs        Counter,
        sonusIcmpOutTimeExcds           Counter,
        sonusIcmpOutParmProbs           Counter,
        sonusIcmpOutSrcQuenchs          Counter,
        sonusIcmpOutRedirects           Counter,
        sonusIcmpOutEchos               Counter,
        sonusIcmpOutEchoReps            Counter,
        sonusIcmpOutTimestamps          Counter,
        sonusIcmpOutTimestampReps       Counter,
        sonusIcmpOutAddrMasks           Counter,
        sonusIcmpOutAddrMaskReps        Counter,
        sonusIcmpGeneralGroupShelf      SonusShelfIndex,
        sonusIcmpGeneralGroupSlot       SonusSlotIndex,
        sonusIcmpGeneralGroupInstance   INTEGER,
        sonusIcmpInRejected             Counter,
        sonusIcmpOutErrorSuppressed     Counter,
        sonusIcmp6InMsgs                Counter,
        sonusIcmp6InErrors              Counter,
        sonusIcmp6InDestUnreachs        Counter,
        sonusIcmp6InTimeExcds           Counter,
        sonusIcmp6InParmProbs           Counter,
        sonusIcmp6InNa                  Counter,
        sonusIcmp6InNs                  Counter,
        sonusIcmp6InRa                  Counter,
        sonusIcmp6InRs                  Counter,
        sonusIcmp6InRedirects           Counter,
        sonusIcmp6InBadNa               Counter,
        sonusIcmp6InBadNs               Counter,
        sonusIcmp6InEchos               Counter,
        sonusIcmp6InEchoReps            Counter,
        sonusIcmp6InBadOptions          Counter,
        sonusIcmp6OutMsgs               Counter,
        sonusIcmp6OutErrors             Counter,
        sonusIcmp6OutNa                 Counter,
        sonusIcmp6OutNs                 Counter,
        sonusIcmp6OutDestUnreachs       Counter,
        sonusIcmp6OutTimeExcds          Counter,
        sonusIcmp6OutParmProbs          Counter,
        sonusIcmp6OutEchos              Counter,
        sonusIcmp6OutEchoReps           Counter
    }

sonusIcmpInMsgs OBJECT-TYPE
    SYNTAX          Counter
    ACCESS          read-only
    STATUS          mandatory
    DESCRIPTION     
            "The total number of ICMP messages which the entity
             received.  Note that this counter includes all those counted
             by icmpInErrors."
    ::= { sonusIcmpGeneralGroupEntry 1 }

sonusIcmpInErrors OBJECT-TYPE
    SYNTAX          Counter
    ACCESS          read-only
    STATUS          mandatory
    DESCRIPTION     
            "The number of ICMP messages which the entity received but
             determined as having ICMP-specific errors (bad ICMP
             checksums, bad length, etc.)."
    ::= { sonusIcmpGeneralGroupEntry 2 }

sonusIcmpInDestUnreachs OBJECT-TYPE
    SYNTAX          Counter
    ACCESS          read-only
    STATUS          mandatory
    DESCRIPTION     
            "The number of ICMP Destination Unreachable messages
             received."
    ::= { sonusIcmpGeneralGroupEntry 3 }

sonusIcmpInTimeExcds OBJECT-TYPE
    SYNTAX          Counter
    ACCESS          read-only
    STATUS          mandatory
    DESCRIPTION     
            "The number of ICMP Time Exceeded messages received."
    ::= { sonusIcmpGeneralGroupEntry 4 }

sonusIcmpInParmProbs OBJECT-TYPE
    SYNTAX          Counter
    ACCESS          read-only
    STATUS          mandatory
    DESCRIPTION     
            "The number of ICMP Parameter Problem messages received."
    ::= { sonusIcmpGeneralGroupEntry 5 }

sonusIcmpInSrcQuenchs OBJECT-TYPE
    SYNTAX          Counter
    ACCESS          read-only
    STATUS          mandatory
    DESCRIPTION     
            "The number of ICMP Source Quench messages received."
    ::= { sonusIcmpGeneralGroupEntry 6 }

sonusIcmpInRedirects OBJECT-TYPE
    SYNTAX          Counter
    ACCESS          read-only
    STATUS          mandatory
    DESCRIPTION     
            "The number of ICMP Redirect messages received."
    ::= { sonusIcmpGeneralGroupEntry 7 }

sonusIcmpInEchos OBJECT-TYPE
    SYNTAX          Counter
    ACCESS          read-only
    STATUS          mandatory
    DESCRIPTION     
            "The number of ICMP Echo (request) messages received."
    ::= { sonusIcmpGeneralGroupEntry 8 }

sonusIcmpInEchoReps OBJECT-TYPE
    SYNTAX          Counter
    ACCESS          read-only
    STATUS          mandatory
    DESCRIPTION     
            "The number of ICMP Echo Reply messages received."
    ::= { sonusIcmpGeneralGroupEntry 9 }

sonusIcmpInTimestamps OBJECT-TYPE
    SYNTAX          Counter
    ACCESS          read-only
    STATUS          mandatory
    DESCRIPTION     
            "The number of ICMP Timestamp (request) messages received."
    ::= { sonusIcmpGeneralGroupEntry 10 }

sonusIcmpInTimestampReps OBJECT-TYPE
    SYNTAX          Counter
    ACCESS          read-only
    STATUS          mandatory
    DESCRIPTION     
            "The number of ICMP Timestamp Reply messages received."
    ::= { sonusIcmpGeneralGroupEntry 11 }

sonusIcmpInAddrMasks OBJECT-TYPE
    SYNTAX          Counter
    ACCESS          read-only
    STATUS          mandatory
    DESCRIPTION     
            "The number of ICMP Address Mask Request messages received."
    ::= { sonusIcmpGeneralGroupEntry 12 }

sonusIcmpInAddrMaskReps OBJECT-TYPE
    SYNTAX          Counter
    ACCESS          read-only
    STATUS          mandatory
    DESCRIPTION     
            "The number of ICMP Address Mask Reply messages received."
    ::= { sonusIcmpGeneralGroupEntry 13 }

sonusIcmpOutMsgs OBJECT-TYPE
    SYNTAX          Counter
    ACCESS          read-only
    STATUS          mandatory
    DESCRIPTION     
            "The total number of ICMP messages which this entity
             attempted to send.  Note that this counter includes all
             those counted by icmpOutErrors."
    ::= { sonusIcmpGeneralGroupEntry 14 }

sonusIcmpOutErrors OBJECT-TYPE
    SYNTAX          Counter
    ACCESS          read-only
    STATUS          mandatory
    DESCRIPTION     
            "The number of ICMP messages which this entity did not send
             due to problems discovered within ICMP such as a lack of
             buffers.  This value should not include errors discovered
             outside the ICMP layer such as the inability of IP to route
             the resultant datagram.  In some implementations there may
             be no types of error which contribute to this counter's
             value."
    ::= { sonusIcmpGeneralGroupEntry 15 }

sonusIcmpOutDestUnreachs OBJECT-TYPE
    SYNTAX          Counter
    ACCESS          read-only
    STATUS          mandatory
    DESCRIPTION     
            "The number of ICMP Destination Unreachable messages sent."
    ::= { sonusIcmpGeneralGroupEntry 16 }

sonusIcmpOutTimeExcds OBJECT-TYPE
    SYNTAX          Counter
    ACCESS          read-only
    STATUS          mandatory
    DESCRIPTION     
            "The number of ICMP Time Exceeded messages sent."
    ::= { sonusIcmpGeneralGroupEntry 17 }

sonusIcmpOutParmProbs OBJECT-TYPE
    SYNTAX          Counter
    ACCESS          read-only
    STATUS          mandatory
    DESCRIPTION     
            "The number of ICMP Parameter Problem messages sent."
    ::= { sonusIcmpGeneralGroupEntry 18 }

sonusIcmpOutSrcQuenchs OBJECT-TYPE
    SYNTAX          Counter
    ACCESS          read-only
    STATUS          mandatory
    DESCRIPTION     
            "The number of ICMP Source Quench messages sent."
    ::= { sonusIcmpGeneralGroupEntry 19 }

sonusIcmpOutRedirects OBJECT-TYPE
    SYNTAX          Counter
    ACCESS          read-only
    STATUS          mandatory
    DESCRIPTION     
            "The number of ICMP Redirect messages sent.  For a host,
             this object will always be zero, since hosts do not send
             redirects."
    ::= { sonusIcmpGeneralGroupEntry 20 }

sonusIcmpOutEchos OBJECT-TYPE
    SYNTAX          Counter
    ACCESS          read-only
    STATUS          mandatory
    DESCRIPTION     
            "The number of ICMP Echo (request) messages sent."
    ::= { sonusIcmpGeneralGroupEntry 21 }

sonusIcmpOutEchoReps OBJECT-TYPE
    SYNTAX          Counter
    ACCESS          read-only
    STATUS          mandatory
    DESCRIPTION     
            "The number of ICMP Echo Reply messages sent."
    ::= { sonusIcmpGeneralGroupEntry 22 }

sonusIcmpOutTimestamps OBJECT-TYPE
    SYNTAX          Counter
    ACCESS          read-only
    STATUS          mandatory
    DESCRIPTION     
            "The number of ICMP Timestamp (request) messages sent."
    ::= { sonusIcmpGeneralGroupEntry 23 }

sonusIcmpOutTimestampReps OBJECT-TYPE
    SYNTAX          Counter
    ACCESS          read-only
    STATUS          mandatory
    DESCRIPTION     
            "The number of ICMP Timestamp Reply messages sent."
    ::= { sonusIcmpGeneralGroupEntry 24 }

sonusIcmpOutAddrMasks OBJECT-TYPE
    SYNTAX          Counter
    ACCESS          read-only
    STATUS          mandatory
    DESCRIPTION     
            "The number of ICMP Address Mask Request messages sent."
    ::= { sonusIcmpGeneralGroupEntry 25 }

sonusIcmpOutAddrMaskReps OBJECT-TYPE
    SYNTAX          Counter
    ACCESS          read-only
    STATUS          mandatory
    DESCRIPTION     
            "The number of ICMP Address Mask Reply messages sent."
    ::= { sonusIcmpGeneralGroupEntry 26 }

sonusIcmpGeneralGroupShelf OBJECT-TYPE
    SYNTAX          SonusShelfIndex
    ACCESS          read-only
    STATUS          mandatory
    DESCRIPTION     
            "A 32-bit integer identifying the shelf
             that the ICMP General Group table applies to"
    ::= { sonusIcmpGeneralGroupEntry 27 }

sonusIcmpGeneralGroupSlot OBJECT-TYPE
    SYNTAX          SonusSlotIndex
    ACCESS          read-only
    STATUS          mandatory
    DESCRIPTION     
            "A 32-bit integer identifying the slot
             that the ICMP General Group table applies to"
    ::= { sonusIcmpGeneralGroupEntry 28 }

sonusIcmpGeneralGroupInstance OBJECT-TYPE
    SYNTAX          INTEGER
    ACCESS          read-only
    STATUS          mandatory
    DESCRIPTION     
            "A 32-bit integer identifying the instance
             that the ICMP General Group table applies to"
    ::= { sonusIcmpGeneralGroupEntry 29 }

sonusIcmpInRejected OBJECT-TYPE
    SYNTAX          Counter
    ACCESS          read-only
    STATUS          mandatory
    DESCRIPTION     
            "The number of ICMP messages rejected. These could be
             Timestamp requests, address mask requests etc. "
    ::= { sonusIcmpGeneralGroupEntry 30 }

sonusIcmpOutErrorSuppressed OBJECT-TYPE
    SYNTAX          Counter
    ACCESS          read-only
    STATUS          mandatory
    DESCRIPTION     
            "The number of ICMP error messages suppressed.  
             Destination unreachable like errors are not sent to 
             protect the box from DOS attacks. This counter keeps
             track of those suppressed messages."
    ::= { sonusIcmpGeneralGroupEntry 31 }

sonusIcmp6InMsgs OBJECT-TYPE
    SYNTAX          Counter
    ACCESS          read-only
    STATUS          mandatory
    DESCRIPTION     
            "The total number of ICMP6 messages which the entity
             received.  Note that this counter includes all those counted
             by icmp6InErrors."
    ::= { sonusIcmpGeneralGroupEntry 32 }

sonusIcmp6InErrors OBJECT-TYPE
    SYNTAX          Counter
    ACCESS          read-only
    STATUS          mandatory
    DESCRIPTION     
            "The number of ICMP6 messages which the entity received but
             determined as having ICMP-specific errors (bad ICMP
             checksums, bad length, etc.)."
    ::= { sonusIcmpGeneralGroupEntry 33 }

sonusIcmp6InDestUnreachs OBJECT-TYPE
    SYNTAX          Counter
    ACCESS          read-only
    STATUS          mandatory
    DESCRIPTION     
            "The number of ICMP6 Destination Unreachable messages
             received."
    ::= { sonusIcmpGeneralGroupEntry 34 }

sonusIcmp6InTimeExcds OBJECT-TYPE
    SYNTAX          Counter
    ACCESS          read-only
    STATUS          mandatory
    DESCRIPTION     
            "The number of ICMP6 Time Exceeded messages received."
    ::= { sonusIcmpGeneralGroupEntry 35 }

sonusIcmp6InParmProbs OBJECT-TYPE
    SYNTAX          Counter
    ACCESS          read-only
    STATUS          mandatory
    DESCRIPTION     
            "The number of ICMP6 Parameter Problem messages received."
    ::= { sonusIcmpGeneralGroupEntry 36 }

sonusIcmp6InNa OBJECT-TYPE
    SYNTAX          Counter
    ACCESS          read-only
    STATUS          mandatory
    DESCRIPTION     
            "The number of ICMP6 Neighbor Advertisement messages received."
    ::= { sonusIcmpGeneralGroupEntry 37 }

sonusIcmp6InNs OBJECT-TYPE
    SYNTAX          Counter
    ACCESS          read-only
    STATUS          mandatory
    DESCRIPTION     
            "The number of ICMP6 Neighbor Solicitation messages received."
    ::= { sonusIcmpGeneralGroupEntry 38 }

sonusIcmp6InRa OBJECT-TYPE
    SYNTAX          Counter
    ACCESS          read-only
    STATUS          mandatory
    DESCRIPTION     
            "The number of ICMP6 Router Advertisement messages received."
    ::= { sonusIcmpGeneralGroupEntry 39 }

sonusIcmp6InRs OBJECT-TYPE
    SYNTAX          Counter
    ACCESS          read-only
    STATUS          mandatory
    DESCRIPTION     
            "The number of ICMP6 Router Solicitation messages received."
    ::= { sonusIcmpGeneralGroupEntry 40 }

sonusIcmp6InRedirects OBJECT-TYPE
    SYNTAX          Counter
    ACCESS          read-only
    STATUS          mandatory
    DESCRIPTION     
            "The number of ICMP6 Redirect messages received."
    ::= { sonusIcmpGeneralGroupEntry 41 }

sonusIcmp6InBadNa OBJECT-TYPE
    SYNTAX          Counter
    ACCESS          read-only
    STATUS          mandatory
    DESCRIPTION     
            "The number of ICMP6 Bad Neighbor Advertisement messages received."
    ::= { sonusIcmpGeneralGroupEntry 42 }

sonusIcmp6InBadNs OBJECT-TYPE
    SYNTAX          Counter
    ACCESS          read-only
    STATUS          mandatory
    DESCRIPTION     
            "The number of ICMP6 Bad Neighbor Solicitation messages received."
    ::= { sonusIcmpGeneralGroupEntry 43 }

sonusIcmp6InEchos OBJECT-TYPE
    SYNTAX          Counter
    ACCESS          read-only
    STATUS          mandatory
    DESCRIPTION     
            "The number of ICMP6 ECHO Request messages received."
    ::= { sonusIcmpGeneralGroupEntry 44 }

sonusIcmp6InEchoReps OBJECT-TYPE
    SYNTAX          Counter
    ACCESS          read-only
    STATUS          mandatory
    DESCRIPTION     
            "The number of ICMP6 ECHO REPLY messages received."
    ::= { sonusIcmpGeneralGroupEntry 45 }

sonusIcmp6InBadOptions OBJECT-TYPE
    SYNTAX          Counter
    ACCESS          read-only
    STATUS          mandatory
    DESCRIPTION     
            "The number of ICMP6 Bad Options in messages received."
    ::= { sonusIcmpGeneralGroupEntry 46 }

sonusIcmp6OutMsgs OBJECT-TYPE
    SYNTAX          Counter
    ACCESS          read-only
    STATUS          mandatory
    DESCRIPTION     
            "The total number of ICMP6 messages which this entity
             attempted to send.  Note that this counter includes all
             those counted by icmp6OutErrors."
    ::= { sonusIcmpGeneralGroupEntry 47 }

sonusIcmp6OutErrors OBJECT-TYPE
    SYNTAX          Counter
    ACCESS          read-only
    STATUS          mandatory
    DESCRIPTION     
            "The number of ICMP6 messages which this entity did not send
             due to problems discovered within ICMP such as a lack of
             buffers.  This value should not include errors discovered
             outside the ICMP layer such as the inability of IP to route
             the resultant datagram.  In some implementations there may
             be no types of error which contribute to this counter's
             value."
    ::= { sonusIcmpGeneralGroupEntry 48 }

sonusIcmp6OutNa OBJECT-TYPE
    SYNTAX          Counter
    ACCESS          read-only
    STATUS          mandatory
    DESCRIPTION     
            "The number of ICMP6 Neighbor Advertisement messages sent."
    ::= { sonusIcmpGeneralGroupEntry 49 }

sonusIcmp6OutNs OBJECT-TYPE
    SYNTAX          Counter
    ACCESS          read-only
    STATUS          mandatory
    DESCRIPTION     
            "The number of ICMP6 Neighbor Solicitation messages sent."
    ::= { sonusIcmpGeneralGroupEntry 50 }

sonusIcmp6OutDestUnreachs OBJECT-TYPE
    SYNTAX          Counter
    ACCESS          read-only
    STATUS          mandatory
    DESCRIPTION     
            "The number of ICMP6 Destination Unreachable messages sent."
    ::= { sonusIcmpGeneralGroupEntry 51 }

sonusIcmp6OutTimeExcds OBJECT-TYPE
    SYNTAX          Counter
    ACCESS          read-only
    STATUS          mandatory
    DESCRIPTION     
            "The number of ICMP6 Time Exceeded messages sent."
    ::= { sonusIcmpGeneralGroupEntry 52 }

sonusIcmp6OutParmProbs OBJECT-TYPE
    SYNTAX          Counter
    ACCESS          read-only
    STATUS          mandatory
    DESCRIPTION     
            "The number of ICMP6 Parameter Problem messages sent."
    ::= { sonusIcmpGeneralGroupEntry 53 }

sonusIcmp6OutEchos OBJECT-TYPE
    SYNTAX          Counter
    ACCESS          read-only
    STATUS          mandatory
    DESCRIPTION     
            "The number of ICMP6 Echo (request) messages sent."
    ::= { sonusIcmpGeneralGroupEntry 54 }

sonusIcmp6OutEchoReps OBJECT-TYPE
    SYNTAX          Counter
    ACCESS          read-only
    STATUS          mandatory
    DESCRIPTION     
            "The number of ICMP6 Echo Reply messages sent."
    ::= { sonusIcmpGeneralGroupEntry 55 }

sonusTcp OBJECT IDENTIFIER
    ::= { sonusMib-2 6 }

sonusTcpGeneralGroupTable OBJECT-TYPE
    SYNTAX          SEQUENCE OF SonusTcpGeneralGroupEntry
    ACCESS          not-accessible
    STATUS          mandatory
    DESCRIPTION     
            "The collection of TCP General Group information for the
             specified instance."
    ::= { sonusTcp 1 }

sonusTcpGeneralGroupEntry OBJECT-TYPE
    SYNTAX          SonusTcpGeneralGroupEntry
    ACCESS          not-accessible
    STATUS          mandatory
    DESCRIPTION     
            "The collection of TCP General Group information for the
             specified instance."
    INDEX           { sonusTcpGeneralGroupShelf, 
                      sonusTcpGeneralGroupSlot, 
                      sonusTcpGeneralGroupInstance }
    ::= { sonusTcpGeneralGroupTable 1 }

SonusTcpGeneralGroupEntry ::=
    SEQUENCE {
        sonusTcpRtoAlgorithm            INTEGER,
        sonusTcpRtoMin                  INTEGER,
        sonusTcpRtoMax                  INTEGER,
        sonusTcpMaxConn                 INTEGER,
        sonusTcpActiveOpens             Counter,
        sonusTcpPassiveOpens            Counter,
        sonusTcpAttemptFails            Counter,
        sonusTcpEstabResets             Counter,
        sonusTcpCurrEstab               Gauge,
        sonusTcpInSegs                  Counter,
        sonusTcpOutSegs                 Counter,
        sonusTcpRetransSegs             Counter,
        sonusTcpInErrs                  Counter,
        sonusTcpOutRsts                 Counter,
        sonusTcpGeneralGroupShelf       SonusShelfIndex,
        sonusTcpGeneralGroupSlot        SonusSlotIndex,
        sonusTcpGeneralGroupInstance    INTEGER,
        sonusTcpMaxSegSize              Counter
    }

sonusTcpRtoAlgorithm OBJECT-TYPE
    SYNTAX          INTEGER { other(1), constant(2), rsre(3), vanj(4) }
    ACCESS          read-only
    STATUS          mandatory
    DESCRIPTION     
            "The algorithm used to determine the timeout value used for
             retransmitting unacknowledged octets."
    ::= { sonusTcpGeneralGroupEntry 1 }

sonusTcpRtoMin OBJECT-TYPE
    SYNTAX          INTEGER
    ACCESS          read-only
    STATUS          mandatory
    DESCRIPTION     
            "The minimum value permitted by a TCP implementation for the
             retransmission timeout, measured in milliseconds.  More
             refined semantics for objects of this type depend upon the
             algorithm used to determine the retransmission timeout.  In
             particular, when the timeout algorithm is rsre(3), an object
             of this type has the semantics of the LBOUND quantity
             described in RFC 793."
    ::= { sonusTcpGeneralGroupEntry 2 }

sonusTcpRtoMax OBJECT-TYPE
    SYNTAX          INTEGER
    ACCESS          read-only
    STATUS          mandatory
    DESCRIPTION     
            "The maximum value permitted by a TCP implementation for the
             retransmission timeout, measured in milliseconds.  More
             refined semantics for objects of this type depend upon the
             algorithm used to determine the retransmission timeout.  In
             particular, when the timeout algorithm is rsre(3), an object
             of this type has the semantics of the UBOUND quantity
             described in RFC 793."
    ::= { sonusTcpGeneralGroupEntry 3 }

sonusTcpMaxConn OBJECT-TYPE
    SYNTAX          INTEGER
    ACCESS          read-only
    STATUS          mandatory
    DESCRIPTION     
            "The limit on the total number of TCP connections the entity
             can support.  In entities where the maximum number of
             connections is dynamic, this object should contain the value
             -1."
    ::= { sonusTcpGeneralGroupEntry 4 }

sonusTcpActiveOpens OBJECT-TYPE
    SYNTAX          Counter
    ACCESS          read-only
    STATUS          mandatory
    DESCRIPTION     
            "The number of times TCP connections have made a direct
             transition to the SYN-SENT state from the CLOSED state."
    ::= { sonusTcpGeneralGroupEntry 5 }

sonusTcpPassiveOpens OBJECT-TYPE
    SYNTAX          Counter
    ACCESS          read-only
    STATUS          mandatory
    DESCRIPTION     
            "The number of times TCP connections have made a direct
             transition to the SYN-RCVD state from the LISTEN state."
    ::= { sonusTcpGeneralGroupEntry 6 }

sonusTcpAttemptFails OBJECT-TYPE
    SYNTAX          Counter
    ACCESS          read-only
    STATUS          mandatory
    DESCRIPTION     
            "The number of times TCP connections have made a direct
             transition to the CLOSED state from either the SYN-SENT
             state or the SYN-RCVD state, plus the number of times TCP
             connections have made a direct transition to the LISTEN
             state from the SYN-RCVD state."
    ::= { sonusTcpGeneralGroupEntry 7 }

sonusTcpEstabResets OBJECT-TYPE
    SYNTAX          Counter
    ACCESS          read-only
    STATUS          mandatory
    DESCRIPTION     
            "The number of times TCP connections have made a direct
             transition to the CLOSED state from either the ESTABLISHED
             state or the CLOSE-WAIT state."
    ::= { sonusTcpGeneralGroupEntry 8 }

sonusTcpCurrEstab OBJECT-TYPE
    SYNTAX          Gauge
    ACCESS          read-only
    STATUS          mandatory
    DESCRIPTION     
            "The number of TCP connections for which the current state
             is either ESTABLISHED or CLOSE- WAIT."
    ::= { sonusTcpGeneralGroupEntry 9 }

sonusTcpInSegs OBJECT-TYPE
    SYNTAX          Counter
    ACCESS          read-only
    STATUS          mandatory
    DESCRIPTION     
            "The total number of segments received, including those
             received in error.  This count includes segments received on
             currently established connections."
    ::= { sonusTcpGeneralGroupEntry 10 }

sonusTcpOutSegs OBJECT-TYPE
    SYNTAX          Counter
    ACCESS          read-only
    STATUS          mandatory
    DESCRIPTION     
            "The total number of segments sent, including those on
             current connections but excluding those containing only
             retransmitted octets."
    ::= { sonusTcpGeneralGroupEntry 11 }

sonusTcpRetransSegs OBJECT-TYPE
    SYNTAX          Counter
    ACCESS          read-only
    STATUS          mandatory
    DESCRIPTION     
            "The total number of segments retransmitted - that is, the
             number of TCP segments transmitted containing one or more
             previously transmitted octets."
    ::= { sonusTcpGeneralGroupEntry 12 }

sonusTcpInErrs OBJECT-TYPE
    SYNTAX          Counter
    ACCESS          read-only
    STATUS          mandatory
    DESCRIPTION     
            "The total number of segments received in error (e.g., bad
             TCP checksums)."
    ::= { sonusTcpGeneralGroupEntry 14 }

sonusTcpOutRsts OBJECT-TYPE
    SYNTAX          Counter
    ACCESS          read-only
    STATUS          mandatory
    DESCRIPTION     
            "The number of TCP segments sent containing the RST flag."
    ::= { sonusTcpGeneralGroupEntry 15 }

sonusTcpGeneralGroupShelf OBJECT-TYPE
    SYNTAX          SonusShelfIndex
    ACCESS          read-only
    STATUS          mandatory
    DESCRIPTION     
            "A 32-bit integer identifying the shelf
             that the TCP General Group table applies to"
    ::= { sonusTcpGeneralGroupEntry 16 }

sonusTcpGeneralGroupSlot OBJECT-TYPE
    SYNTAX          SonusSlotIndex
    ACCESS          read-only
    STATUS          mandatory
    DESCRIPTION     
            "A 32-bit integer identifying the slot
             that the TCP General Group table applies to"
    ::= { sonusTcpGeneralGroupEntry 17 }

sonusTcpGeneralGroupInstance OBJECT-TYPE
    SYNTAX          INTEGER
    ACCESS          read-only
    STATUS          mandatory
    DESCRIPTION     
            "A 32-bit integer identifying the instance
             that the TCP General Group table applies to"
    ::= { sonusTcpGeneralGroupEntry 18 }

sonusTcpMaxSegSize OBJECT-TYPE
    SYNTAX          Counter
    ACCESS          read-only
    STATUS          mandatory
    DESCRIPTION     
            "Current maximum segement size."
    ::= { sonusTcpGeneralGroupEntry 19 }

sonusTcpConnTable OBJECT-TYPE
    SYNTAX          SEQUENCE OF SonusTcpConnEntry
    ACCESS          not-accessible
    STATUS          mandatory
    DESCRIPTION     
            "A table containing TCP connection-specific information."
    ::= { sonusTcp 13 }

sonusTcpConnEntry OBJECT-TYPE
    SYNTAX          SonusTcpConnEntry
    ACCESS          not-accessible
    STATUS          mandatory
    DESCRIPTION     
            "A conceptual row of the tcpConnTable containing information
             about a particular current TCP connection.  Each row of this
             table is transient, in that it ceases to exist when (or soon
             after) the connection makes the transition to the CLOSED
             state."
    INDEX           { sonusTcpConnIpVersion, sonusTcpConnShelf, 
                      sonusTcpConnSlot, sonusTcpConnInstance, 
                      sonusTcpConnLocalAddress, sonusTcpConnLocalPort, 
                      sonusTcpConnRemAddress, sonusTcpConnRemPort, 
                      sonusTcpConnLocal6Address, sonusTcpConnRem6Address }
    ::= { sonusTcpConnTable 1 }

SonusTcpConnEntry ::=
    SEQUENCE {
        sonusTcpConnState               INTEGER,
        sonusTcpConnLocalAddress        IpAddress,
        sonusTcpConnLocalPort           INTEGER,
        sonusTcpConnRemAddress          IpAddress,
        sonusTcpConnRemPort             INTEGER,
        sonusTcpConnShelf               SonusShelfIndex,
        sonusTcpConnSlot                SonusSlotIndex,
        sonusTcpConnInstance            INTEGER,
        sonusTcpConnLocal6Address       Ipv6Address,
        sonusTcpConnRem6Address         Ipv6Address,
        sonusTcpConnIpVersion           INTEGER
    }

sonusTcpConnState OBJECT-TYPE
    SYNTAX          INTEGER { closed(1), listen(2), synSent(3), 
                        synReceived(4), established(5), finWait1(6), 
                        finWait2(7), closeWait(8), lastAck(9), 
                        closing(10), timeWait(11), deleteTCB(12) }
    ACCESS          read-only
    STATUS          mandatory
    DESCRIPTION     
            "The state of this TCP connection.
             
             The only value which may be set by a management station is
             deleteTCB(12).  Accordingly, it is appropriate for an agent
             to return a `badValue' response if a management station
             attempts to set this object to any other value.
             
             If a management station sets this object to the value
             deleteTCB(12), then this has the effect of deleting the TCB
             (as defined in RFC 793) of the corresponding connection on
             the managed node, resulting in immediate termination of the
             connection.
             
             As an implementation-specific option, a RST segment may be
             sent from the managed node to the other TCP endpoint (note
             however that RST segments are not sent reliably)."
    ::= { sonusTcpConnEntry 1 }

sonusTcpConnLocalAddress OBJECT-TYPE
    SYNTAX          IpAddress
    ACCESS          read-only
    STATUS          mandatory
    DESCRIPTION     
            "The local IP address for this TCP connection.  In the case
             of a connection in the listen state which is willing to
             accept connections for any IP interface associated with the
             node, the value 0.0.0.0 is used."
    ::= { sonusTcpConnEntry 2 }

sonusTcpConnLocalPort OBJECT-TYPE
    SYNTAX          INTEGER (0..65535)
    ACCESS          read-only
    STATUS          mandatory
    DESCRIPTION     
            "The local port number for this TCP connection."
    ::= { sonusTcpConnEntry 3 }

sonusTcpConnRemAddress OBJECT-TYPE
    SYNTAX          IpAddress
    ACCESS          read-only
    STATUS          mandatory
    DESCRIPTION     
            "The remote IP address for this TCP connection."
    ::= { sonusTcpConnEntry 4 }

sonusTcpConnRemPort OBJECT-TYPE
    SYNTAX          INTEGER (0..65535)
    ACCESS          read-only
    STATUS          mandatory
    DESCRIPTION     
            "The remote port number for this TCP connection."
    ::= { sonusTcpConnEntry 5 }

sonusTcpConnShelf OBJECT-TYPE
    SYNTAX          SonusShelfIndex
    ACCESS          read-only
    STATUS          mandatory
    DESCRIPTION     
            "A 32-bit integer identifying the shelf
             that the TCP Connection Group table applies to"
    ::= { sonusTcpConnEntry 6 }

sonusTcpConnSlot OBJECT-TYPE
    SYNTAX          SonusSlotIndex
    ACCESS          read-only
    STATUS          mandatory
    DESCRIPTION     
            "A 32-bit integer identifying the slot
             that the TCP Connection Group table applies to"
    ::= { sonusTcpConnEntry 7 }

sonusTcpConnInstance OBJECT-TYPE
    SYNTAX          INTEGER
    ACCESS          read-only
    STATUS          mandatory
    DESCRIPTION     
            "A 32-bit integer identifying the instance
             that the TCP Connection Group table applies to"
    ::= { sonusTcpConnEntry 8 }

sonusTcpConnLocal6Address OBJECT-TYPE
    SYNTAX          Ipv6Address
    ACCESS          read-only
    STATUS          mandatory
    DESCRIPTION     
            "The local IPv6 address for this TCP connection.  In the case
             of a connection in the listen state which is willing to
             accept connections for any IPv6 interface associated with the
             node, the value :: is used."
    ::= { sonusTcpConnEntry 9 }

sonusTcpConnRem6Address OBJECT-TYPE
    SYNTAX          Ipv6Address
    ACCESS          read-only
    STATUS          mandatory
    DESCRIPTION     
            "The remote IPv6 address for this TCP connection."
    ::= { sonusTcpConnEntry 10 }

sonusTcpConnIpVersion OBJECT-TYPE
    SYNTAX          INTEGER { afInet(2), afInet6(24) }
    ACCESS          read-only
    STATUS          mandatory
    DESCRIPTION     
            "The remote IP version for this TCP connection."
    ::= { sonusTcpConnEntry 11 }

sonusUdp OBJECT IDENTIFIER
    ::= { sonusMib-2 7 }

sonusUdpGeneralGroupTable OBJECT-TYPE
    SYNTAX          SEQUENCE OF SonusUdpGeneralGroupEntry
    ACCESS          not-accessible
    STATUS          mandatory
    DESCRIPTION     
            "The collection of UDP General Group information for the
             specified instance."
    ::= { sonusUdp 1 }

sonusUdpGeneralGroupEntry OBJECT-TYPE
    SYNTAX          SonusUdpGeneralGroupEntry
    ACCESS          not-accessible
    STATUS          mandatory
    DESCRIPTION     
            "The collection of UDP General Group information for the
             specified instance."
    INDEX           { sonusUdpGeneralGroupShelf, 
                      sonusUdpGeneralGroupSlot, 
                      sonusUdpGeneralGroupInstance }
    ::= { sonusUdpGeneralGroupTable 1 }

SonusUdpGeneralGroupEntry ::=
    SEQUENCE {
        sonusUdpInDatagrams             Counter,
        sonusUdpNoPorts                 Counter,
        sonusUdpInErrors                Counter,
        sonusUdpOutDatagrams            Counter,
        sonusUdpGeneralGroupShelf       SonusShelfIndex,
        sonusUdpGeneralGroupSlot        SonusSlotIndex,
        sonusUdpGeneralGroupInstance    INTEGER
    }

sonusUdpInDatagrams OBJECT-TYPE
    SYNTAX          Counter
    ACCESS          read-only
    STATUS          mandatory
    DESCRIPTION     
            "The total number of UDP datagrams delivered to UDP users."
    ::= { sonusUdpGeneralGroupEntry 1 }

sonusUdpNoPorts OBJECT-TYPE
    SYNTAX          Counter
    ACCESS          read-only
    STATUS          mandatory
    DESCRIPTION     
            "The total number of received UDP datagrams for which there
             was no application at the destination port."
    ::= { sonusUdpGeneralGroupEntry 2 }

sonusUdpInErrors OBJECT-TYPE
    SYNTAX          Counter
    ACCESS          read-only
    STATUS          mandatory
    DESCRIPTION     
            "The number of received UDP datagrams that could not be
             delivered for reasons other than the lack of an application
             at the destination port."
    ::= { sonusUdpGeneralGroupEntry 3 }

sonusUdpOutDatagrams OBJECT-TYPE
    SYNTAX          Counter
    ACCESS          read-only
    STATUS          mandatory
    DESCRIPTION     
            "The total number of UDP datagrams sent from this entity."
    ::= { sonusUdpGeneralGroupEntry 4 }

sonusUdpGeneralGroupShelf OBJECT-TYPE
    SYNTAX          SonusShelfIndex
    ACCESS          read-only
    STATUS          mandatory
    DESCRIPTION     
            "A 32-bit integer identifying the shelf
             that the UDP General Group table applies to"
    ::= { sonusUdpGeneralGroupEntry 5 }

sonusUdpGeneralGroupSlot OBJECT-TYPE
    SYNTAX          SonusSlotIndex
    ACCESS          read-only
    STATUS          mandatory
    DESCRIPTION     
            "A 32-bit integer identifying the slot
             that the UDP General Group table applies to"
    ::= { sonusUdpGeneralGroupEntry 6 }

sonusUdpGeneralGroupInstance OBJECT-TYPE
    SYNTAX          INTEGER
    ACCESS          read-only
    STATUS          mandatory
    DESCRIPTION     
            "A 32-bit integer identifying the instance
             that the UDP General Group table applies to"
    ::= { sonusUdpGeneralGroupEntry 7 }

sonusUdpTable OBJECT-TYPE
    SYNTAX          SEQUENCE OF SonusUdpEntry
    ACCESS          not-accessible
    STATUS          mandatory
    DESCRIPTION     
            "A table containing UDP listener information."
    ::= { sonusUdp 5 }

sonusUdpEntry OBJECT-TYPE
    SYNTAX          SonusUdpEntry
    ACCESS          not-accessible
    STATUS          mandatory
    DESCRIPTION     
            "Information about a particular current UDP listener."
    INDEX           { sonusUdpIpVersion, sonusUdpShelf, sonusUdpSlot, 
                      sonusUdpInstance, sonusUdpLocalAddress, 
                      sonusUdpLocalPort, sonusUdpLocal6Address }
    ::= { sonusUdpTable 1 }

SonusUdpEntry ::=
    SEQUENCE {
        sonusUdpLocalAddress            IpAddress,
        sonusUdpLocalPort               INTEGER,
        sonusUdpShelf                   SonusShelfIndex,
        sonusUdpSlot                    SonusSlotIndex,
        sonusUdpInstance                INTEGER,
        sonusUdpLocal6Address           Ipv6Address,
        sonusUdpIpVersion               INTEGER
    }

sonusUdpLocalAddress OBJECT-TYPE
    SYNTAX          IpAddress
    ACCESS          read-only
    STATUS          mandatory
    DESCRIPTION     
            "The local IP address for this UDP listener.  In the case of
             a UDP listener which is willing to accept datagrams for any
             IP interface associated with the node, the value 0.0.0.0 is
             used."
    ::= { sonusUdpEntry 1 }

sonusUdpLocalPort OBJECT-TYPE
    SYNTAX          INTEGER (0..65535)
    ACCESS          read-only
    STATUS          mandatory
    DESCRIPTION     
            "The local port number for this UDP listener."
    ::= { sonusUdpEntry 2 }

sonusUdpShelf OBJECT-TYPE
    SYNTAX          SonusShelfIndex
    ACCESS          read-only
    STATUS          mandatory
    DESCRIPTION     
            "A 32-bit integer identifying the shelf
             that the UDP Listener table applies to"
    ::= { sonusUdpEntry 3 }

sonusUdpSlot OBJECT-TYPE
    SYNTAX          SonusSlotIndex
    ACCESS          read-only
    STATUS          mandatory
    DESCRIPTION     
            "A 32-bit integer identifying the slot
             that the UDP Listener table applies to"
    ::= { sonusUdpEntry 4 }

sonusUdpInstance OBJECT-TYPE
    SYNTAX          INTEGER
    ACCESS          read-only
    STATUS          mandatory
    DESCRIPTION     
            "A 32-bit integer identifying the instance
             that the UDP Listener table applies to"
    ::= { sonusUdpEntry 5 }

sonusUdpLocal6Address OBJECT-TYPE
    SYNTAX          Ipv6Address
    ACCESS          read-only
    STATUS          mandatory
    DESCRIPTION     
            "The local IPv6 address for this UDP listener.  In the case of
             a UDP listener which is willing to accept datagrams for any
             IP interface associated with the node, the value :: is
             used."
    ::= { sonusUdpEntry 6 }

sonusUdpIpVersion OBJECT-TYPE
    SYNTAX          INTEGER { afInet(2), afInet6(24) }
    ACCESS          read-only
    STATUS          mandatory
    DESCRIPTION     
            "The local IP version for this UDP connection."
    ::= { sonusUdpEntry 7 }

sonusSctp OBJECT IDENTIFIER
    ::= { sonusMib-2 8 }

sonusSctpGeneralGroupTable OBJECT-TYPE
    SYNTAX          SEQUENCE OF SonusSctpGeneralGroupEntry
    ACCESS          not-accessible
    STATUS          mandatory
    DESCRIPTION     
            "The collection of SCTP General Group information for the
             specified instance."
    ::= { sonusSctp 1 }

sonusSctpGeneralGroupEntry OBJECT-TYPE
    SYNTAX          SonusSctpGeneralGroupEntry
    ACCESS          not-accessible
    STATUS          mandatory
    DESCRIPTION     
            "The collection of SCTP General Group information for the
             specified instance."
    INDEX           { sonusSctpGeneralGroupShelf, 
                      sonusSctpGeneralGroupSlot, 
                      sonusSctpGeneralGroupInstance }
    ::= { sonusSctpGeneralGroupTable 1 }

SonusSctpGeneralGroupEntry ::=
    SEQUENCE {
        sonusSctpActiveAssociations     Counter,
        sonusSctpActiveStreams          Counter,
        sonusSctpAttemptFails           Counter,
        sonusSctpCurrEstab              Counter,
        sonusSctpInPkts                 Counter,
        sonusSctpInBadchecksum          Counter,
        sonusSctpInErrs                 Counter,
        sonusSctpInChunks               Counter,
        sonusSctpInInitChunks           Counter,
        sonusSctpInDataChunks           Counter,
        sonusSctpInSackChunks           Counter,
        sonusSctpInHeartBeatChunks      Counter,
        sonusSctpInAbortChunks          Counter,
        sonusSctpInErrChunks            Counter,
        sonusSctpInOotbChunks           Counter,
        sonusSctpOutPkts                Counter,
        sonusSctpOutChunks              Counter,
        sonusSctpOutInitChunks          Counter,
        sonusSctpOutDataChunks          Counter,
        sonusSctpOutSackChunks          Counter,
        sonusSctpOutHeartBeatChunks     Counter,
        sonusSctpOutAbortChunks         Counter,
        sonusSctpOutErrChunks           Counter,
        sonusSctpGeneralGroupShelf      SonusShelfIndex,
        sonusSctpGeneralGroupSlot       SonusSlotIndex,
        sonusSctpGeneralGroupInstance   INTEGER
    }

sonusSctpActiveAssociations OBJECT-TYPE
    SYNTAX          Counter
    ACCESS          read-only
    STATUS          mandatory
    DESCRIPTION     
            "Number of active SCTP associations that are in 
             > COOKIE_WAIT state"
    ::= { sonusSctpGeneralGroupEntry 1 }

sonusSctpActiveStreams OBJECT-TYPE
    SYNTAX          Counter
    ACCESS          read-only
    STATUS          mandatory
    DESCRIPTION     
            "Total number of streams in all the established
             associations combined. At minimum there will be as
             many streams as the number of associations"
    ::= { sonusSctpGeneralGroupEntry 2 }

sonusSctpAttemptFails OBJECT-TYPE
    SYNTAX          Counter
    ACCESS          read-only
    STATUS          mandatory
    DESCRIPTION     
            "Number of failed attempts by SCTP to initiate an
             association with peer."
    ::= { sonusSctpGeneralGroupEntry 3 }

sonusSctpCurrEstab OBJECT-TYPE
    SYNTAX          Counter
    ACCESS          read-only
    STATUS          mandatory
    DESCRIPTION     
            "Total number of associations in ESTABLISHED state"
    ::= { sonusSctpGeneralGroupEntry 4 }

sonusSctpInPkts OBJECT-TYPE
    SYNTAX          Counter
    ACCESS          read-only
    STATUS          mandatory
    DESCRIPTION     
            "Total number of SCTP packets received from all the peers
             combined."
    ::= { sonusSctpGeneralGroupEntry 5 }

sonusSctpInBadchecksum OBJECT-TYPE
    SYNTAX          Counter
    ACCESS          read-only
    STATUS          mandatory
    DESCRIPTION     
            "Number of received packets with bad checksum"
    ::= { sonusSctpGeneralGroupEntry 6 }

sonusSctpInErrs OBJECT-TYPE
    SYNTAX          Counter
    ACCESS          read-only
    STATUS          mandatory
    DESCRIPTION     
            "Number of packets received in error"
    ::= { sonusSctpGeneralGroupEntry 7 }

sonusSctpInChunks OBJECT-TYPE
    SYNTAX          Counter
    ACCESS          read-only
    STATUS          mandatory
    DESCRIPTION     
            "Total number of SCTP chunks received on all associations"
    ::= { sonusSctpGeneralGroupEntry 8 }

sonusSctpInInitChunks OBJECT-TYPE
    SYNTAX          Counter
    ACCESS          read-only
    STATUS          mandatory
    DESCRIPTION     
            "Total number of INIT/INIT_ACK chunks received on all
             associations"
    ::= { sonusSctpGeneralGroupEntry 9 }

sonusSctpInDataChunks OBJECT-TYPE
    SYNTAX          Counter
    ACCESS          read-only
    STATUS          mandatory
    DESCRIPTION     
            "Number of DATA chunks received on all associations"
    ::= { sonusSctpGeneralGroupEntry 10 }

sonusSctpInSackChunks OBJECT-TYPE
    SYNTAX          Counter
    ACCESS          read-only
    STATUS          mandatory
    DESCRIPTION     
            "Number of SACK chunks received on all associations"
    ::= { sonusSctpGeneralGroupEntry 11 }

sonusSctpInHeartBeatChunks OBJECT-TYPE
    SYNTAX          Counter
    ACCESS          read-only
    STATUS          mandatory
    DESCRIPTION     
            "Number of HEARTBEAT/HEARTBEAT_ACK chunks received on
             all the associations"
    ::= { sonusSctpGeneralGroupEntry 12 }

sonusSctpInAbortChunks OBJECT-TYPE
    SYNTAX          Counter
    ACCESS          read-only
    STATUS          mandatory
    DESCRIPTION     
            "Total number of ABORT chunks received on all the
             associations"
    ::= { sonusSctpGeneralGroupEntry 13 }

sonusSctpInErrChunks OBJECT-TYPE
    SYNTAX          Counter
    ACCESS          read-only
    STATUS          mandatory
    DESCRIPTION     
            "Total number of ERROR chunks received on all the
             associations "
    ::= { sonusSctpGeneralGroupEntry 14 }

sonusSctpInOotbChunks OBJECT-TYPE
    SYNTAX          Counter
    ACCESS          read-only
    STATUS          mandatory
    DESCRIPTION     
            "Total number of Out of the blue chunks received"
    ::= { sonusSctpGeneralGroupEntry 15 }

sonusSctpOutPkts OBJECT-TYPE
    SYNTAX          Counter
    ACCESS          read-only
    STATUS          mandatory
    DESCRIPTION     
            "Total number of SCTP packets sent on all associations"
    ::= { sonusSctpGeneralGroupEntry 16 }

sonusSctpOutChunks OBJECT-TYPE
    SYNTAX          Counter
    ACCESS          read-only
    STATUS          mandatory
    DESCRIPTION     
            "Total number of SCTP chunks sent on all associations"
    ::= { sonusSctpGeneralGroupEntry 17 }

sonusSctpOutInitChunks OBJECT-TYPE
    SYNTAX          Counter
    ACCESS          read-only
    STATUS          mandatory
    DESCRIPTION     
            "Total number of INIT/INIT_ACK chunks sent on all
             associations"
    ::= { sonusSctpGeneralGroupEntry 18 }

sonusSctpOutDataChunks OBJECT-TYPE
    SYNTAX          Counter
    ACCESS          read-only
    STATUS          mandatory
    DESCRIPTION     
            "Number of DATA chunks sent on all associations"
    ::= { sonusSctpGeneralGroupEntry 19 }

sonusSctpOutSackChunks OBJECT-TYPE
    SYNTAX          Counter
    ACCESS          read-only
    STATUS          mandatory
    DESCRIPTION     
            "Number of SACK chunks sent on all associations"
    ::= { sonusSctpGeneralGroupEntry 20 }

sonusSctpOutHeartBeatChunks OBJECT-TYPE
    SYNTAX          Counter
    ACCESS          read-only
    STATUS          mandatory
    DESCRIPTION     
            "Number of HEARTBEAT/HEARTBEAT_ACK chunks sent on all
             the associations"
    ::= { sonusSctpGeneralGroupEntry 21 }

sonusSctpOutAbortChunks OBJECT-TYPE
    SYNTAX          Counter
    ACCESS          read-only
    STATUS          mandatory
    DESCRIPTION     
            "Total number of ABORT chunks sent on all the
             associations"
    ::= { sonusSctpGeneralGroupEntry 22 }

sonusSctpOutErrChunks OBJECT-TYPE
    SYNTAX          Counter
    ACCESS          read-only
    STATUS          mandatory
    DESCRIPTION     
            "Total number of ERROR chunks sent on all the
             associations "
    ::= { sonusSctpGeneralGroupEntry 23 }

sonusSctpGeneralGroupShelf OBJECT-TYPE
    SYNTAX          SonusShelfIndex
    ACCESS          read-only
    STATUS          mandatory
    DESCRIPTION     
            "A 32-bit integer identifying the shelf
             that the SCTP General Group table applies to"
    ::= { sonusSctpGeneralGroupEntry 24 }

sonusSctpGeneralGroupSlot OBJECT-TYPE
    SYNTAX          SonusSlotIndex
    ACCESS          read-only
    STATUS          mandatory
    DESCRIPTION     
            "A 32-bit integer identifying the slot
             that the SCTP General Group table applies to"
    ::= { sonusSctpGeneralGroupEntry 25 }

sonusSctpGeneralGroupInstance OBJECT-TYPE
    SYNTAX          INTEGER
    ACCESS          read-only
    STATUS          mandatory
    DESCRIPTION     
            "A 32-bit integer identifying the instance
             that the SCTP General Group table applies to"
    ::= { sonusSctpGeneralGroupEntry 26 }

sonusSctpAssocTable OBJECT-TYPE
    SYNTAX          SEQUENCE OF SonusSctpAssocEntry
    ACCESS          not-accessible
    STATUS          mandatory
    DESCRIPTION     
            "A table containing SCTP connection-specific information."
    ::= { sonusSctp 2 }

sonusSctpAssocEntry OBJECT-TYPE
    SYNTAX          SonusSctpAssocEntry
    ACCESS          not-accessible
    STATUS          mandatory
    DESCRIPTION     
            "A conceptual row of the sctpAssocTable containing information
             about a particular current SCTP association.  Each row of this
             table is transient, in that it ceases to exist when (or soon
             after) the association makes the transition to the CLOSED
             state."
    INDEX           { sonusSctpAssocIpVersion, sonusSctpAssocShelf, 
                      sonusSctpAssocSlot, sonusSctpAssocInstance, 
                      sonusSctpAssocLocalAddress, 
                      sonusSctpAssocLocalPort, sonusSctpAssocRemAddress, 
                      sonusSctpAssocRemPort, sonusSctpAssocLocalAddress6, 
                      sonusSctpAssocRemAddress6 }
    ::= { sonusSctpAssocTable 1 }

SonusSctpAssocEntry ::=
    SEQUENCE {
        sonusSctpAssocState             INTEGER,
        sonusSctpAssocLocalAddrCount    INTEGER,
        sonusSctpAssocLocalAddress      IpAddress,
        sonusSctpAssocLocalPort         INTEGER,
        sonusSctpAssocRemAddrCount      INTEGER,
        sonusSctpAssocRemAddress        IpAddress,
        sonusSctpAssocRemPort           INTEGER,
        sonusSctpAssocShelf             SonusShelfIndex,
        sonusSctpAssocSlot              SonusSlotIndex,
        sonusSctpAssocInstance          INTEGER,
        sonusSctpAssocLocalAddress6     Ipv6Address,
        sonusSctpAssocRemAddress6       Ipv6Address,
        sonusSctpAssocIpVersion         INTEGER
    }

sonusSctpAssocState OBJECT-TYPE
    SYNTAX          INTEGER { closed(0), listen(1), cookieWait(2), 
                        cookieEchoed(3), established(4), 
                        shutdownPending(5), shutdownSent(6), 
                        shutdownReceived(7), shutdownRecvWait(8), 
                        shutdownAckSent(9), unreachable(10) }
    ACCESS          read-only
    STATUS          mandatory
    DESCRIPTION     
            "The state of this SCTP connection."
    ::= { sonusSctpAssocEntry 1 }

sonusSctpAssocLocalAddrCount OBJECT-TYPE
    SYNTAX          INTEGER
    ACCESS          read-only
    STATUS          mandatory
    DESCRIPTION     
            "Number of local addresses SCTP association is bound to"
    ::= { sonusSctpAssocEntry 2 }

sonusSctpAssocLocalAddress OBJECT-TYPE
    SYNTAX          IpAddress
    ACCESS          read-only
    STATUS          mandatory
    DESCRIPTION     
            "The local IP address for this SCTP connection.  In the case
             of a connection in the listen state which is willing to
             accept connections for any IP interface associated with the
             node, the value 0.0.0.0 is used."
    ::= { sonusSctpAssocEntry 3 }

sonusSctpAssocLocalPort OBJECT-TYPE
    SYNTAX          INTEGER (0..65535)
    ACCESS          read-only
    STATUS          mandatory
    DESCRIPTION     
            "The local port number for this SCTP connection."
    ::= { sonusSctpAssocEntry 4 }

sonusSctpAssocRemAddrCount OBJECT-TYPE
    SYNTAX          INTEGER
    ACCESS          read-only
    STATUS          mandatory
    DESCRIPTION     
            "Number of remote addresses on this SCTP association"
    ::= { sonusSctpAssocEntry 5 }

sonusSctpAssocRemAddress OBJECT-TYPE
    SYNTAX          IpAddress
    ACCESS          read-only
    STATUS          mandatory
    DESCRIPTION     
            "The remote IP address for this SCTP connection."
    ::= { sonusSctpAssocEntry 6 }

sonusSctpAssocRemPort OBJECT-TYPE
    SYNTAX          INTEGER (0..65535)
    ACCESS          read-only
    STATUS          mandatory
    DESCRIPTION     
            "The remote port number for this SCTP connection."
    ::= { sonusSctpAssocEntry 7 }

sonusSctpAssocShelf OBJECT-TYPE
    SYNTAX          SonusShelfIndex
    ACCESS          read-only
    STATUS          mandatory
    DESCRIPTION     
            "A 32-bit integer identifying the shelf
             that the SCTP Connection Group table applies to"
    ::= { sonusSctpAssocEntry 8 }

sonusSctpAssocSlot OBJECT-TYPE
    SYNTAX          SonusSlotIndex
    ACCESS          read-only
    STATUS          mandatory
    DESCRIPTION     
            "A 32-bit integer identifying the slot
             that the SCTP Connection Group table applies to"
    ::= { sonusSctpAssocEntry 9 }

sonusSctpAssocInstance OBJECT-TYPE
    SYNTAX          INTEGER
    ACCESS          read-only
    STATUS          mandatory
    DESCRIPTION     
            "A 32-bit integer identifying the instance
             that the SCTP Connection Group table applies to"
    ::= { sonusSctpAssocEntry 10 }

sonusSctpAssocLocalAddress6 OBJECT-TYPE
    SYNTAX          Ipv6Address
    ACCESS          read-only
    STATUS          mandatory
    DESCRIPTION     
            "The local IPv6 address for this SCTP connection."
    ::= { sonusSctpAssocEntry 11 }

sonusSctpAssocRemAddress6 OBJECT-TYPE
    SYNTAX          Ipv6Address
    ACCESS          read-only
    STATUS          mandatory
    DESCRIPTION     
            "The remote IPv6 address for this SCTP connection."
    ::= { sonusSctpAssocEntry 12 }

sonusSctpAssocIpVersion OBJECT-TYPE
    SYNTAX          INTEGER { afInet(2), afInet6(24) }
    ACCESS          read-only
    STATUS          mandatory
    DESCRIPTION     
            "The remote IP version for this TCP connection."
    ::= { sonusSctpAssocEntry 13 }

sonusIpSec OBJECT IDENTIFIER
    ::= { sonusMib-2 9 }

sonusIpSecPolicyNextIndex OBJECT-TYPE
    SYNTAX          INTEGER
    ACCESS          read-only
    STATUS          mandatory
    DESCRIPTION     
            "The next valid index to use when creating an entry
             in the sonusIpSecPolicy table."
    ::= { sonusIpSec 1 }

sonusIpSecPolicyTable OBJECT-TYPE
    SYNTAX          SEQUENCE OF SonusIpSecPolicyEntry
    ACCESS          not-accessible
    STATUS          mandatory
    DESCRIPTION     
            "Table of IPsec Policies"
    ::= { sonusIpSec 2 }

sonusIpSecPolicyEntry OBJECT-TYPE
    SYNTAX          SonusIpSecPolicyEntry
    ACCESS          not-accessible
    STATUS          mandatory
    DESCRIPTION     
            "The collection of IPsec Policy information 
             for the specified index."
    INDEX           { sonusIpSecPolicyIndex }
    ::= { sonusIpSecPolicyTable 1 }

SonusIpSecPolicyEntry ::=
    SEQUENCE {
        sonusIpSecPolicyRowStatus       RowStatus,
        sonusIpSecPolicyIndex           INTEGER,
        sonusIpSecPolicyName            SonusName
    }

sonusIpSecPolicyRowStatus OBJECT-TYPE
    SYNTAX          RowStatus
    ACCESS          read-write
    STATUS          mandatory
    DESCRIPTION     
            "SNMP use"
    ::= { sonusIpSecPolicyEntry 1 }

sonusIpSecPolicyIndex OBJECT-TYPE
    SYNTAX          INTEGER
    ACCESS          read-only
    STATUS          mandatory
    DESCRIPTION     
            "The index assigned to this IPsec Policy
             when it was created. Cannot be modified."
    ::= { sonusIpSecPolicyEntry 2 }

sonusIpSecPolicyName OBJECT-TYPE
    SYNTAX          SonusName
    ACCESS          read-write
    STATUS          mandatory
    DESCRIPTION     
            "The administrative name of the IPsec Policy."
    ::= { sonusIpSecPolicyEntry 3 }

sonusIpSecSpdNextIndex OBJECT-TYPE
    SYNTAX          INTEGER
    ACCESS          read-only
    STATUS          mandatory
    DESCRIPTION     
            "The next valid index to use when creating an entry
             in the sonusIpSecSpd table."
    ::= { sonusIpSec 3 }

sonusIpSecSpdTable OBJECT-TYPE
    SYNTAX          SEQUENCE OF SonusIpSecSpdEntry
    ACCESS          not-accessible
    STATUS          mandatory
    DESCRIPTION     
            "Table of IPsec SPDs"
    ::= { sonusIpSec 4 }

sonusIpSecSpdEntry OBJECT-TYPE
    SYNTAX          SonusIpSecSpdEntry
    ACCESS          not-accessible
    STATUS          mandatory
    DESCRIPTION     
            "The collection of IPsec SPD information 
             for the specified indices."
    INDEX           { sonusIpSecSpdIndex }
    ::= { sonusIpSecSpdTable 1 }

SonusIpSecSpdEntry ::=
    SEQUENCE {
        sonusIpSecSpdRowStatus          RowStatus,
        sonusIpSecSpdIndex              INTEGER,
        sonusIpSecSpdName               SonusName,
        sonusIpSecSpdIpSecPolicyIndex   INTEGER,
        sonusIpSecSpdPrecedence         INTEGER,
        sonusIpSecSpdTrafficSelectorLocalIpAddr       IpAddress,
        sonusIpSecSpdTrafficSelectorLocalIpMask       IpAddress,
        sonusIpSecSpdTrafficSelectorLocalPort     INTEGER,
        sonusIpSecSpdTrafficSelectorRemoteIpAddr        IpAddress,
        sonusIpSecSpdTrafficSelectorRemoteIpMask        IpAddress,
        sonusIpSecSpdTrafficSelectorRemotePort      INTEGER,
        sonusIpSecSpdTrafficSelectorIpProtocol      INTEGER,
        sonusIpSecSpdAction             INTEGER,
        sonusIpSecSpdIkePeerEntryName   DisplayString,
        sonusIpSecSpdIpSecProfileNamePrefOne    DisplayString,
        sonusIpSecSpdIpSecProfileNamePrefTwo    DisplayString,
        sonusIpSecSpdIpSecProfileNamePrefThree      DisplayString,
        sonusIpSecSpdTrafficSelectorLocalIp6Addr        Ipv6Address,
        sonusIpSecSpdTrafficSelectorLocalIpv6PrefixLength                 INTEGER,
        sonusIpSecSpdTrafficSelectorRemoteIp6Addr         Ipv6Address,
        sonusIpSecSpdTrafficSelectorRemoteIpV6PrefixLength                  INTEGER,
        sonusIpSecSpdTrafficSelectorIpAddrVersion         INTEGER
    }

sonusIpSecSpdRowStatus OBJECT-TYPE
    SYNTAX          RowStatus
    ACCESS          read-write
    STATUS          mandatory
    DESCRIPTION     
            "SNMP use"
    ::= { sonusIpSecSpdEntry 1 }

sonusIpSecSpdIndex OBJECT-TYPE
    SYNTAX          INTEGER
    ACCESS          read-only
    STATUS          mandatory
    DESCRIPTION     
            "The index assigned to this IPsec SPD
             when it was created. Cannot be modified."
    ::= { sonusIpSecSpdEntry 2 }

sonusIpSecSpdName OBJECT-TYPE
    SYNTAX          SonusName
    ACCESS          read-write
    STATUS          mandatory
    DESCRIPTION     
            "The administrative name of the IPsec SPD."
    ::= { sonusIpSecSpdEntry 3 }

sonusIpSecSpdIpSecPolicyIndex OBJECT-TYPE
    SYNTAX          INTEGER
    ACCESS          read-write
    STATUS          mandatory
    DESCRIPTION     
            "The index of the parent IPsec Policy to this SPD."
    ::= { sonusIpSecSpdEntry 4 }

sonusIpSecSpdPrecedence OBJECT-TYPE
    SYNTAX          INTEGER
    ACCESS          read-write
    STATUS          mandatory
    DESCRIPTION     
            "This selection precedence of this SPD, 1-65535."
    ::= { sonusIpSecSpdEntry 5 }

sonusIpSecSpdTrafficSelectorLocalIpAddr OBJECT-TYPE
    SYNTAX          IpAddress
    ACCESS          read-write
    STATUS          mandatory
    DESCRIPTION     
            "The SPD traffic selector local IP address"
    ::= { sonusIpSecSpdEntry 6 }

sonusIpSecSpdTrafficSelectorLocalIpMask OBJECT-TYPE
    SYNTAX          IpAddress
    ACCESS          read-write
    STATUS          mandatory
    DESCRIPTION     
            "The SPD traffic selector local IP mask"
    ::= { sonusIpSecSpdEntry 7 }

sonusIpSecSpdTrafficSelectorLocalPort OBJECT-TYPE
    SYNTAX          INTEGER (-1..65535)
    ACCESS          read-write
    STATUS          mandatory
    DESCRIPTION     
            "The SPD traffic selector local IP port, -1 to 65535."
    DEFVAL          { 0 }
    ::= { sonusIpSecSpdEntry 8 }

sonusIpSecSpdTrafficSelectorRemoteIpAddr OBJECT-TYPE
    SYNTAX          IpAddress
    ACCESS          read-write
    STATUS          mandatory
    DESCRIPTION     
            "The SPD traffic selector remote IP address"
    ::= { sonusIpSecSpdEntry 9 }

sonusIpSecSpdTrafficSelectorRemoteIpMask OBJECT-TYPE
    SYNTAX          IpAddress
    ACCESS          read-write
    STATUS          mandatory
    DESCRIPTION     
            "The SPD traffic selector remote IP mask"
    ::= { sonusIpSecSpdEntry 10 }

sonusIpSecSpdTrafficSelectorRemotePort OBJECT-TYPE
    SYNTAX          INTEGER (-1..65535)
    ACCESS          read-write
    STATUS          mandatory
    DESCRIPTION     
            "The SPD traffic selector remote IP port, -1 to 65535."
    DEFVAL          { 0 }
    ::= { sonusIpSecSpdEntry 11 }

sonusIpSecSpdTrafficSelectorIpProtocol OBJECT-TYPE
    SYNTAX          INTEGER (0..255)
    ACCESS          read-write
    STATUS          mandatory
    DESCRIPTION     
            "The SPD traffic selector IP protocol, 0 to 255."
    DEFVAL          { 0 }
    ::= { sonusIpSecSpdEntry 12 }

sonusIpSecSpdAction OBJECT-TYPE
    SYNTAX          INTEGER { discard(0), bypass(1), protect(2) }
    ACCESS          read-write
    STATUS          mandatory
    DESCRIPTION     
            "The SPD action for the traffic selector subset"
    DEFVAL          { discard }
    ::= { sonusIpSecSpdEntry 13 }

sonusIpSecSpdIkePeerEntryName OBJECT-TYPE
    SYNTAX          DisplayString
    ACCESS          read-write
    STATUS          mandatory
    DESCRIPTION     
            "The name of the sub-referenced Ike Peer Entry (IPD)."
    ::= { sonusIpSecSpdEntry 14 }

sonusIpSecSpdIpSecProfileNamePrefOne OBJECT-TYPE
    SYNTAX          DisplayString
    ACCESS          read-write
    STATUS          mandatory
    DESCRIPTION     
            "The name of the first preference IPsec Protection 
             Profile for SPD action PROTECT."
    ::= { sonusIpSecSpdEntry 15 }

sonusIpSecSpdIpSecProfileNamePrefTwo OBJECT-TYPE
    SYNTAX          DisplayString
    ACCESS          read-write
    STATUS          mandatory
    DESCRIPTION     
            "The name of the second preference IPsec Protection 
             Profile for SPD action PROTECT."
    ::= { sonusIpSecSpdEntry 16 }

sonusIpSecSpdIpSecProfileNamePrefThree OBJECT-TYPE
    SYNTAX          DisplayString
    ACCESS          read-write
    STATUS          mandatory
    DESCRIPTION     
            "The name of the third preference IPsec Protection 
             Profile for SPD action PROTECT."
    ::= { sonusIpSecSpdEntry 17 }

sonusIpSecSpdTrafficSelectorLocalIp6Addr OBJECT-TYPE
    SYNTAX          Ipv6Address
    ACCESS          read-write
    STATUS          mandatory
    DESCRIPTION     
            "The SPD traffic selector local Ip6 address."
    ::= { sonusIpSecSpdEntry 18 }

sonusIpSecSpdTrafficSelectorLocalIpv6PrefixLength OBJECT-TYPE
    SYNTAX          INTEGER
    ACCESS          read-write
    STATUS          mandatory
    DESCRIPTION     
            "The SPD traffic selector local Ipv6 prefix length."
    ::= { sonusIpSecSpdEntry 19 }

sonusIpSecSpdTrafficSelectorRemoteIp6Addr OBJECT-TYPE
    SYNTAX          Ipv6Address
    ACCESS          read-write
    STATUS          mandatory
    DESCRIPTION     
            "The SPD traffic selector IP address."
    ::= { sonusIpSecSpdEntry 20 }

sonusIpSecSpdTrafficSelectorRemoteIpV6PrefixLength OBJECT-TYPE
    SYNTAX          INTEGER
    ACCESS          read-write
    STATUS          mandatory
    DESCRIPTION     
            "The SPD traffic selector Remote IPv6 Prefix ."
    ::= { sonusIpSecSpdEntry 21 }

sonusIpSecSpdTrafficSelectorIpAddrVersion OBJECT-TYPE
    SYNTAX          INTEGER { afInet(2), afInet6(24) }
    ACCESS          read-only
    STATUS          mandatory
    DESCRIPTION     
            "The SPD traffic selector local IP address type."
    ::= { sonusIpSecSpdEntry 22 }

sonusIpSecSpdIpSecPolicyTable OBJECT-TYPE
    SYNTAX          SEQUENCE OF SonusIpSecSpdAdmnEntry
    ACCESS          not-accessible
    STATUS          mandatory
    DESCRIPTION     
            "Table of IPsec SPDs by IPsec Policy"
    ::= { sonusIpSec 5 }

sonusIpSecSpdAdmnEntry OBJECT-TYPE
    SYNTAX          SonusIpSecSpdAdmnEntry
    ACCESS          not-accessible
    STATUS          mandatory
    DESCRIPTION     
            "The collection of IPsec SPD information 
             for the specified indices."
    INDEX           { sonusIpSecSpdAdmnIpSecPolicyIndex, 
                      sonusIpSecSpdAdmnPrecedence }
    ::= { sonusIpSecSpdIpSecPolicyTable 1 }

SonusIpSecSpdAdmnEntry ::=
    SEQUENCE {
        sonusIpSecSpdAdmnIpSecPolicyIndex INTEGER,
        sonusIpSecSpdAdmnPrecedence     INTEGER,
        sonusIpSecSpdAdmnIndex          INTEGER
    }

sonusIpSecSpdAdmnIpSecPolicyIndex OBJECT-TYPE
    SYNTAX          INTEGER
    ACCESS          read-only
    STATUS          mandatory
    DESCRIPTION     
            "The index of the parent IPsec Policy to this SPD."
    ::= { sonusIpSecSpdAdmnEntry 1 }

sonusIpSecSpdAdmnPrecedence OBJECT-TYPE
    SYNTAX          INTEGER
    ACCESS          read-only
    STATUS          mandatory
    DESCRIPTION     
            "The selection precedence of this SPD, 1-65535."
    ::= { sonusIpSecSpdAdmnEntry 2 }

sonusIpSecSpdAdmnIndex OBJECT-TYPE
    SYNTAX          INTEGER
    ACCESS          read-only
    STATUS          mandatory
    DESCRIPTION     
            "The index of this SPD"
    ::= { sonusIpSecSpdAdmnEntry 3 }

sonusIpSecIpdNextIndex OBJECT-TYPE
    SYNTAX          INTEGER
    ACCESS          read-only
    STATUS          mandatory
    DESCRIPTION     
            "The next valid index to use when creating an entry
             in the sonusIpSecIpd table."
    ::= { sonusIpSec 6 }

sonusIpSecIpdTable OBJECT-TYPE
    SYNTAX          SEQUENCE OF SonusIpSecIpdEntry
    ACCESS          not-accessible
    STATUS          mandatory
    DESCRIPTION     
            "Table of IPsec IKE Peer Database (IPD) entries"
    ::= { sonusIpSec 7 }

sonusIpSecIpdEntry OBJECT-TYPE
    SYNTAX          SonusIpSecIpdEntry
    ACCESS          not-accessible
    STATUS          mandatory
    DESCRIPTION     
            "The collection of IPsec IKE Peer Database (IPD) 
             information for the specified indices."
    INDEX           { sonusIpSecIpdIndex }
    ::= { sonusIpSecIpdTable 1 }

SonusIpSecIpdEntry ::=
    SEQUENCE {
        sonusIpSecIpdRowStatus          RowStatus,
        sonusIpSecIpdIndex              INTEGER,
        sonusIpSecIpdName               SonusName,
        sonusIpSecIpdIpSecPolicyIndex   INTEGER,
        sonusIpSecIpdLocalIkeIdentityType INTEGER,
        sonusIpSecIpdLocalIkeIdentityIpAddr   IpAddress,
        sonusIpSecIpdLocalIkeIdentityFqdn DisplayString,
        sonusIpSecIpdPeerIpAddr         IpAddress,
        sonusIpSecIpdPeerIkeIdentityType INTEGER,
        sonusIpSecIpdPeerIkeIdentityIpAddr  IpAddress,
        sonusIpSecIpdPeerIkeIdentityFqdn DisplayString,
        sonusIpSecIpdPresharedSecret    OCTET STRING,
        sonusIpSecIpdIkeProfileNamePrefOne  DisplayString,
        sonusIpSecIpdIkeProfileNamePrefTwo  DisplayString,
        sonusIpSecIpdIkeProfileNamePrefThree    DisplayString,
        sonusIpSecIpdLocalIkeIdentityIp6Addr    Ipv6Address,
        sonusIpSecIpdPeerIp6Addr        Ipv6Address,
        sonusIpSecIpdPeerIkeIdentityIp6Addr   Ipv6Address,
        sonusIpSecIpdPeerIpVersion      INTEGER,
        sonusIpSecIpdIkeIdentityIpAddrVersion     INTEGER,
        sonusIpSecIpdIkeVersion         INTEGER
    }

sonusIpSecIpdRowStatus OBJECT-TYPE
    SYNTAX          RowStatus
    ACCESS          read-write
    STATUS          mandatory
    DESCRIPTION     
            "SNMP use"
    ::= { sonusIpSecIpdEntry 1 }

sonusIpSecIpdIndex OBJECT-TYPE
    SYNTAX          INTEGER
    ACCESS          read-only
    STATUS          mandatory
    DESCRIPTION     
            "The index assigned to this IPsec IPD
             when it was created. Cannot be modified."
    ::= { sonusIpSecIpdEntry 2 }

sonusIpSecIpdName OBJECT-TYPE
    SYNTAX          SonusName
    ACCESS          read-write
    STATUS          mandatory
    DESCRIPTION     
            "The administrative name of the IPsec IPD."
    ::= { sonusIpSecIpdEntry 3 }

sonusIpSecIpdIpSecPolicyIndex OBJECT-TYPE
    SYNTAX          INTEGER
    ACCESS          read-write
    STATUS          mandatory
    DESCRIPTION     
            "The index of the parent IPsec Policy to this IPD."
    ::= { sonusIpSecIpdEntry 4 }

sonusIpSecIpdLocalIkeIdentityType OBJECT-TYPE
    SYNTAX          INTEGER { none(0), ipv4(1), fqdn(2), dynamic(3), 
                        ipv6(4) }
    ACCESS          read-write
    STATUS          mandatory
    DESCRIPTION     
            "The Local IKE Identity type."
    DEFVAL          { dynamic }
    ::= { sonusIpSecIpdEntry 5 }

sonusIpSecIpdLocalIkeIdentityIpAddr OBJECT-TYPE
    SYNTAX          IpAddress
    ACCESS          read-write
    STATUS          mandatory
    DESCRIPTION     
            "The Local IKE Identity IP address, if 
             sonusIpSecIpdLocalIkeIdentityType is IPV4."
    ::= { sonusIpSecIpdEntry 6 }

sonusIpSecIpdLocalIkeIdentityFqdn OBJECT-TYPE
    SYNTAX          DisplayString (SIZE(0..255))
    ACCESS          read-write
    STATUS          mandatory
    DESCRIPTION     
            "The Local IKE Identity Fully Qualified Domain
             Name (FQDN), if sonusIpSecIpdLocalIkeIdentityType 
             is FQDN."
    ::= { sonusIpSecIpdEntry 7 }

sonusIpSecIpdPeerIpAddr OBJECT-TYPE
    SYNTAX          IpAddress
    ACCESS          read-write
    STATUS          mandatory
    DESCRIPTION     
            "The Peer IKE IP address."
    ::= { sonusIpSecIpdEntry 8 }

sonusIpSecIpdPeerIkeIdentityType OBJECT-TYPE
    SYNTAX          INTEGER { none(0), ipv4(1), fqdn(2), ipv6(3) }
    ACCESS          read-write
    STATUS          mandatory
    DESCRIPTION     
            "The Peer IKE Identity type."
    DEFVAL          { none }
    ::= { sonusIpSecIpdEntry 9 }

sonusIpSecIpdPeerIkeIdentityIpAddr OBJECT-TYPE
    SYNTAX          IpAddress
    ACCESS          read-write
    STATUS          mandatory
    DESCRIPTION     
            "The Peer IKE Identity IP address, if 
             sonusIpSecIpdPeerIkeIdentityType is IPV4."
    ::= { sonusIpSecIpdEntry 10 }

sonusIpSecIpdPeerIkeIdentityFqdn OBJECT-TYPE
    SYNTAX          DisplayString (SIZE(0..255))
    ACCESS          read-write
    STATUS          mandatory
    DESCRIPTION     
            "The Peer IKE Identity Fully Qualified Domain
             Name (FQDN), if sonusIpSecIpdPeerIkeIdentityType 
             is FQDN."
    ::= { sonusIpSecIpdEntry 11 }

sonusIpSecIpdPresharedSecret OBJECT-TYPE
    SYNTAX          OCTET STRING (SIZE(0..128))
    ACCESS          read-write
    STATUS          mandatory
    DESCRIPTION     
            "The IPD Preshared Secret string."
    ::= { sonusIpSecIpdEntry 12 }

sonusIpSecIpdIkeProfileNamePrefOne OBJECT-TYPE
    SYNTAX          DisplayString
    ACCESS          read-write
    STATUS          mandatory
    DESCRIPTION     
            "The name of the first preference IKE Protection 
             Profile for this IPD."
    ::= { sonusIpSecIpdEntry 13 }

sonusIpSecIpdIkeProfileNamePrefTwo OBJECT-TYPE
    SYNTAX          DisplayString
    ACCESS          read-write
    STATUS          mandatory
    DESCRIPTION     
            "The name of the second preference IKE Protection 
             Profile for this IPD."
    ::= { sonusIpSecIpdEntry 14 }

sonusIpSecIpdIkeProfileNamePrefThree OBJECT-TYPE
    SYNTAX          DisplayString
    ACCESS          read-write
    STATUS          mandatory
    DESCRIPTION     
            "The name of the third preference IKE Protection 
             Profile for this IPD."
    ::= { sonusIpSecIpdEntry 15 }

sonusIpSecIpdLocalIkeIdentityIp6Addr OBJECT-TYPE
    SYNTAX          Ipv6Address
    ACCESS          read-write
    STATUS          mandatory
    DESCRIPTION     
            "The Local IKE Identity IP address, if 
             sonusIpSecIpdLocalIkeIdentityType is IPV6."
    ::= { sonusIpSecIpdEntry 16 }

sonusIpSecIpdPeerIp6Addr OBJECT-TYPE
    SYNTAX          Ipv6Address
    ACCESS          read-write
    STATUS          mandatory
    DESCRIPTION     
            "The Peer IKE IP6 address."
    ::= { sonusIpSecIpdEntry 17 }

sonusIpSecIpdPeerIkeIdentityIp6Addr OBJECT-TYPE
    SYNTAX          Ipv6Address
    ACCESS          read-write
    STATUS          mandatory
    DESCRIPTION     
            "The Peer IKE Identity IPV6 address, if 
             sonusIpSecIpdPeerIkeIdentityType is IPV6."
    ::= { sonusIpSecIpdEntry 18 }

sonusIpSecIpdPeerIpVersion OBJECT-TYPE
    SYNTAX          INTEGER { afInet(2), afInet6(24) }
    ACCESS          read-only
    STATUS          mandatory
    DESCRIPTION     
            "The peer IP address type."
    ::= { sonusIpSecIpdEntry 19 }

sonusIpSecIpdIkeIdentityIpAddrVersion OBJECT-TYPE
    SYNTAX          INTEGER { afInet(2), afInet6(24) }
    ACCESS          read-only
    STATUS          mandatory
    DESCRIPTION     
            "The Local IKE Identity IP address type."
    ::= { sonusIpSecIpdEntry 20 }

sonusIpSecIpdIkeVersion OBJECT-TYPE
    SYNTAX          INTEGER { ikev1(1), ikev2(2) }
    ACCESS          read-write
    STATUS          mandatory
    DESCRIPTION     
            "This object indicates the IKE version configured "
    DEFVAL          { ikev1 }
    ::= { sonusIpSecIpdEntry 21 }

sonusIpSecIpdIpSecPolicyTable OBJECT-TYPE
    SYNTAX          SEQUENCE OF SonusIpSecIpdAdmnEntry
    ACCESS          not-accessible
    STATUS          mandatory
    DESCRIPTION     
            "Table of IPsec IPDs by IPsec Policy"
    ::= { sonusIpSec 8 }

sonusIpSecIpdAdmnEntry OBJECT-TYPE
    SYNTAX          SonusIpSecIpdAdmnEntry
    ACCESS          not-accessible
    STATUS          mandatory
    DESCRIPTION     
            "The collection of IPsec IPD information 
             for the specified indices."
    INDEX           { sonusIpSecIpdAdmnIpSecPolicyIndex, 
                      sonusIpSecIpdAdmnIndex }
    ::= { sonusIpSecIpdIpSecPolicyTable 1 }

SonusIpSecIpdAdmnEntry ::=
    SEQUENCE {
        sonusIpSecIpdAdmnIpSecPolicyIndex INTEGER,
        sonusIpSecIpdAdmnIndex          INTEGER
    }

sonusIpSecIpdAdmnIpSecPolicyIndex OBJECT-TYPE
    SYNTAX          INTEGER
    ACCESS          read-only
    STATUS          mandatory
    DESCRIPTION     
            "The index of the parent IPsec Policy to this IPD."
    ::= { sonusIpSecIpdAdmnEntry 1 }

sonusIpSecIpdAdmnIndex OBJECT-TYPE
    SYNTAX          INTEGER
    ACCESS          read-only
    STATUS          mandatory
    DESCRIPTION     
            "This index of this IPD."
    ::= { sonusIpSecIpdAdmnEntry 2 }

sonusIpSecIpSecProtectionProfileNextIndex OBJECT-TYPE
    SYNTAX          INTEGER
    ACCESS          read-only
    STATUS          mandatory
    DESCRIPTION     
            "The next valid index to use when creating an entry
             in the sonusIpSecIpSecProtectionProfile table."
    ::= { sonusIpSec 9 }

sonusIpSecIpSecProtectionProfileTable OBJECT-TYPE
    SYNTAX          SEQUENCE OF SonusIpSecIpSecProtectionProfileEntry
    ACCESS          not-accessible
    STATUS          mandatory
    DESCRIPTION     
            "Table of IPsec Protection Profile entries"
    ::= { sonusIpSec 10 }

sonusIpSecIpSecProtectionProfileEntry OBJECT-TYPE
    SYNTAX          SonusIpSecIpSecProtectionProfileEntry
    ACCESS          not-accessible
    STATUS          mandatory
    DESCRIPTION     
            "The collection of IPsec Protection Profile information 
             for the specified index."
    INDEX           { sonusIpSecIpSecProtectionProfileIndex }
    ::= { sonusIpSecIpSecProtectionProfileTable 1 }

SonusIpSecIpSecProtectionProfileEntry ::=
    SEQUENCE {
        sonusIpSecIpSecProtectionProfileRowStatus         RowStatus,
        sonusIpSecIpSecProtectionProfileIndex     INTEGER,
        sonusIpSecIpSecProtectionProfileName    SonusName,
        sonusIpSecIpSecProtectionProfileSecurityProtocol                INTEGER,
        sonusIpSecIpSecProtectionProfileIntegrityCipher               INTEGER,
        sonusIpSecIpSecProtectionProfileEncryptionCipher                INTEGER,
        sonusIpSecIpSecProtectionProfileAntiReplaySetting                 INTEGER,
        sonusIpSecIpSecProtectionProfileSaLifetime          INTEGER,
        sonusIpSecIpSecProtectionProfileEncapsulationMode                 INTEGER
    }

sonusIpSecIpSecProtectionProfileRowStatus OBJECT-TYPE
    SYNTAX          RowStatus
    ACCESS          read-write
    STATUS          mandatory
    DESCRIPTION     
            "SNMP use"
    ::= { sonusIpSecIpSecProtectionProfileEntry 1 }

sonusIpSecIpSecProtectionProfileIndex OBJECT-TYPE
    SYNTAX          INTEGER
    ACCESS          read-only
    STATUS          mandatory
    DESCRIPTION     
            "The index assigned to this IPsec Protection Profile
             when it was created. Cannot be modified."
    ::= { sonusIpSecIpSecProtectionProfileEntry 2 }

sonusIpSecIpSecProtectionProfileName OBJECT-TYPE
    SYNTAX          SonusName
    ACCESS          read-write
    STATUS          mandatory
    DESCRIPTION     
            "The administrative name of the IPsec Protection Profile."
    ::= { sonusIpSecIpSecProtectionProfileEntry 3 }

sonusIpSecIpSecProtectionProfileSecurityProtocol OBJECT-TYPE
    SYNTAX          INTEGER { esp(0) }
    ACCESS          read-write
    STATUS          mandatory
    DESCRIPTION     
            "The IPsec Protection Profile Security Protocol.
             Currently only ESP is supported."
    DEFVAL          { esp }
    ::= { sonusIpSecIpSecProtectionProfileEntry 4 }

sonusIpSecIpSecProtectionProfileIntegrityCipher OBJECT-TYPE
    SYNTAX          INTEGER { hmac-sha1-96(0) }
    ACCESS          read-write
    STATUS          mandatory
    DESCRIPTION     
            "The IPsec Protection Profile Integrity Cipher."
    DEFVAL          { hmac-sha1-96 }
    ::= { sonusIpSecIpSecProtectionProfileEntry 5 }

sonusIpSecIpSecProtectionProfileEncryptionCipher OBJECT-TYPE
    SYNTAX          INTEGER { null(0), three-des-cbc(1), aes-cbc-128(2) }
    ACCESS          read-write
    STATUS          mandatory
    DESCRIPTION     
            "The IPsec Protection Profile Encryption Cipher."
    DEFVAL          { aes-cbc-128 }
    ::= { sonusIpSecIpSecProtectionProfileEntry 6 }

sonusIpSecIpSecProtectionProfileAntiReplaySetting OBJECT-TYPE
    SYNTAX          INTEGER { disabled(0), enabled(1) }
    ACCESS          read-write
    STATUS          mandatory
    DESCRIPTION     
            "The IPsec Protection Profile Anti-Replay Setting."
    DEFVAL          { enabled }
    ::= { sonusIpSecIpSecProtectionProfileEntry 7 }

sonusIpSecIpSecProtectionProfileSaLifetime OBJECT-TYPE
    SYNTAX          INTEGER (1200..1000000)
    ACCESS          read-write
    STATUS          mandatory
    DESCRIPTION     
            "The IPsec Protection Profile SA Lifetime setting,
             in seconds. Enforced valid range is 1200-1,000,000 seconds,
             with the default value of 28,800 corresponding to 8 hours."
    DEFVAL          { 28800 }
    ::= { sonusIpSecIpSecProtectionProfileEntry 8 }

sonusIpSecIpSecProtectionProfileEncapsulationMode OBJECT-TYPE
    SYNTAX          INTEGER { tunnel(0), transport(1) }
    ACCESS          read-write
    STATUS          mandatory
    DESCRIPTION     
            "The IPsec Protection Profile encapsulation mode settings"
    DEFVAL          { tunnel }
    ::= { sonusIpSecIpSecProtectionProfileEntry 9 }

sonusIpSecIkeProtectionProfileNextIndex OBJECT-TYPE
    SYNTAX          INTEGER
    ACCESS          read-only
    STATUS          mandatory
    DESCRIPTION     
            "The next valid index to use when creating an entry
             in the sonusIpSecIkeProtectionProfile table."
    ::= { sonusIpSec 11 }

sonusIpSecIkeProtectionProfileTable OBJECT-TYPE
    SYNTAX          SEQUENCE OF SonusIpSecIkeProtectionProfileEntry
    ACCESS          not-accessible
    STATUS          mandatory
    DESCRIPTION     
            "Table of IKE Protection Profile entries"
    ::= { sonusIpSec 12 }

sonusIpSecIkeProtectionProfileEntry OBJECT-TYPE
    SYNTAX          SonusIpSecIkeProtectionProfileEntry
    ACCESS          not-accessible
    STATUS          mandatory
    DESCRIPTION     
            "The collection of IKE Protection Profile information 
             for the specified index."
    INDEX           { sonusIpSecIkeProtectionProfileIndex }
    ::= { sonusIpSecIkeProtectionProfileTable 1 }

SonusIpSecIkeProtectionProfileEntry ::=
    SEQUENCE {
        sonusIpSecIkeProtectionProfileRowStatus       RowStatus,
        sonusIpSecIkeProtectionProfileIndex   INTEGER,
        sonusIpSecIkeProtectionProfileName  SonusName,
        sonusIpSecIkeProtectionProfileIntegrityCipher             INTEGER,
        sonusIpSecIkeProtectionProfileEncryptionCipher              INTEGER,
        sonusIpSecIkeProtectionProfileSaLifetime        INTEGER,
        sonusIpSecIkeProtectionProfileDeadPeerDetectInterval                    INTEGER,
        sonusIpSecIkeProtectionProfileTransactionRetries                INTEGER
    }

sonusIpSecIkeProtectionProfileRowStatus OBJECT-TYPE
    SYNTAX          RowStatus
    ACCESS          read-write
    STATUS          mandatory
    DESCRIPTION     
            "SNMP use"
    ::= { sonusIpSecIkeProtectionProfileEntry 1 }

sonusIpSecIkeProtectionProfileIndex OBJECT-TYPE
    SYNTAX          INTEGER
    ACCESS          read-only
    STATUS          mandatory
    DESCRIPTION     
            "The index assigned to this IPsec Protection Profile
             when it was created. Cannot be modified."
    ::= { sonusIpSecIkeProtectionProfileEntry 2 }

sonusIpSecIkeProtectionProfileName OBJECT-TYPE
    SYNTAX          SonusName
    ACCESS          read-write
    STATUS          mandatory
    DESCRIPTION     
            "The administrative name of the IKE Protection Profile."
    ::= { sonusIpSecIkeProtectionProfileEntry 3 }

sonusIpSecIkeProtectionProfileIntegrityCipher OBJECT-TYPE
    SYNTAX          INTEGER { hmac-sha1-96(0) }
    ACCESS          read-write
    STATUS          mandatory
    DESCRIPTION     
            "The IKE Protection Profile Integrity Cipher."
    DEFVAL          { hmac-sha1-96 }
    ::= { sonusIpSecIkeProtectionProfileEntry 4 }

sonusIpSecIkeProtectionProfileEncryptionCipher OBJECT-TYPE
    SYNTAX          INTEGER { aes-cbc-128(0), three-des-cbc(1) }
    ACCESS          read-write
    STATUS          mandatory
    DESCRIPTION     
            "The IKE Protection Profile Encryption Cipher."
    DEFVAL          { aes-cbc-128 }
    ::= { sonusIpSecIkeProtectionProfileEntry 5 }

sonusIpSecIkeProtectionProfileSaLifetime OBJECT-TYPE
    SYNTAX          INTEGER (1200..1000000)
    ACCESS          read-write
    STATUS          mandatory
    DESCRIPTION     
            "The IKE Protection Profile SA Lifetime setting,
             in seconds. Enforced valid range is 1200-1,000,000 seconds,
             with the default value of 28,800 corresponding to 8 hours."
    DEFVAL          { 28800 }
    ::= { sonusIpSecIkeProtectionProfileEntry 6 }

sonusIpSecIkeProtectionProfileDeadPeerDetectInterval OBJECT-TYPE
    SYNTAX          INTEGER (0..3600)
    ACCESS          read-write
    STATUS          mandatory
    DESCRIPTION     
            "The IKE Protection Profile SA Dead Peer Detection 
             test interval period in seconds. Zero value corresponds
             to DPD disabled."
    DEFVAL          { 0 }
    ::= { sonusIpSecIkeProtectionProfileEntry 7 }

sonusIpSecIkeProtectionProfileTransactionRetries OBJECT-TYPE
    SYNTAX          INTEGER (0..6)
    ACCESS          read-write
    STATUS          mandatory
    DESCRIPTION     
            "The IKE Protection Profile SA
             number of retries before failure declaration"
    DEFVAL          { 3 }
    ::= { sonusIpSecIkeProtectionProfileEntry 8 }

sonusIpSecSystemStatusTable OBJECT-TYPE
    SYNTAX          SEQUENCE OF SonusIpSecSystemStatusEntry
    ACCESS          not-accessible
    STATUS          mandatory
    DESCRIPTION     
            "The collection of IPsec system status information for the
             specified instance."
    ::= { sonusIpSec 13 }

sonusIpSecSystemStatusEntry OBJECT-TYPE
    SYNTAX          SonusIpSecSystemStatusEntry
    ACCESS          not-accessible
    STATUS          mandatory
    DESCRIPTION     
            "The collection of IPsec system status information for the
             specified instance."
    INDEX           { sonusIpSecStatusShelfIndex }
    ::= { sonusIpSecSystemStatusTable 1 }

SonusIpSecSystemStatusEntry ::=
    SEQUENCE {
        sonusIpSecStatusShelfIndex      SonusShelfIndex,
        sonusIpSecStatusIpSecPolicyCount Counter,
        sonusIpSecStatusSpdCount        Counter,
        sonusIpSecStatusIpdCount        Counter,
        sonusIpSecStatusIkeSaCount      Counter,
        sonusIpSecStatusIpSecSaCount    Counter,
        sonusIpSecStatusIkeV2SaCount    Counter
    }

sonusIpSecStatusShelfIndex OBJECT-TYPE
    SYNTAX          SonusShelfIndex
    ACCESS          read-only
    STATUS          mandatory
    DESCRIPTION     
            "Integer identifying the shelf that the
             IPsec system status table applies to"
    ::= { sonusIpSecSystemStatusEntry 1 }

sonusIpSecStatusIpSecPolicyCount OBJECT-TYPE
    SYNTAX          Counter
    ACCESS          read-only
    STATUS          mandatory
    DESCRIPTION     
            "Count of IPsec policies"
    ::= { sonusIpSecSystemStatusEntry 2 }

sonusIpSecStatusSpdCount OBJECT-TYPE
    SYNTAX          Counter
    ACCESS          read-only
    STATUS          mandatory
    DESCRIPTION     
            "Count of IPsec SPD entries"
    ::= { sonusIpSecSystemStatusEntry 3 }

sonusIpSecStatusIpdCount OBJECT-TYPE
    SYNTAX          Counter
    ACCESS          read-only
    STATUS          mandatory
    DESCRIPTION     
            "Count of IPsec IPD entries"
    ::= { sonusIpSecSystemStatusEntry 4 }

sonusIpSecStatusIkeSaCount OBJECT-TYPE
    SYNTAX          Counter
    ACCESS          read-only
    STATUS          mandatory
    DESCRIPTION     
            "Count of IKE SA entries"
    ::= { sonusIpSecSystemStatusEntry 5 }

sonusIpSecStatusIpSecSaCount OBJECT-TYPE
    SYNTAX          Counter
    ACCESS          read-only
    STATUS          mandatory
    DESCRIPTION     
            "Count of IPsec SA entries"
    ::= { sonusIpSecSystemStatusEntry 6 }

sonusIpSecStatusIkeV2SaCount OBJECT-TYPE
    SYNTAX          Counter
    ACCESS          read-only
    STATUS          mandatory
    DESCRIPTION     
            "Count of IKEV2 SA entries"
    ::= { sonusIpSecSystemStatusEntry 7 }

sonusIpSecSystemStatisticsTable OBJECT-TYPE
    SYNTAX          SEQUENCE OF SonusIpSecSystemStatisticsEntry
    ACCESS          not-accessible
    STATUS          mandatory
    DESCRIPTION     
            "The collection of IPsec system statistics information for the
             specified instance."
    ::= { sonusIpSec 14 }

sonusIpSecSystemStatisticsEntry OBJECT-TYPE
    SYNTAX          SonusIpSecSystemStatisticsEntry
    ACCESS          not-accessible
    STATUS          mandatory
    DESCRIPTION     
            "The collection of IPsec system statistics information for the
             specified instance."
    INDEX           { sonusIpSecStatisticsShelfIndex }
    ::= { sonusIpSecSystemStatisticsTable 1 }

SonusIpSecSystemStatisticsEntry ::=
    SEQUENCE {
        sonusIpSecStatisticsShelfIndex  SonusShelfIndex,
        sonusIpSecStatisticsInboundPacketsDiscardedInvalidSpi                     Counter,
        sonusIpSecStatisticsInboundPacketsDiscardedProtectPolicy                        Counter,
        sonusIpSecStatisticsInboundPacketsDiscardedDiscardPolicy                        Counter,
        sonusIpSecStatisticsOutboundPacketsDiscardedProtectPolicy                         Counter,
        sonusIpSecStatisticsOutboundPacketsDiscardedDiscardPolicy                         Counter,
        sonusIpSecStatisticsIkeSaNegotiationsSucceeded              Counter,
        sonusIpSecStatisticsIkeSaNegotiationsFailed           Counter,
        sonusIpSecStatisticsIpSecSaNegotiationsSucceeded                Counter,
        sonusIpSecStatisticsIpSecSaNegotiationsFailed             Counter,
        sonusIpSecStatisticsIkeV2SaNegotiationsSucceeded                Counter,
        sonusIpSecStatisticsIkeV2SaNegotiationsFailed             Counter
    }

sonusIpSecStatisticsShelfIndex OBJECT-TYPE
    SYNTAX          SonusShelfIndex
    ACCESS          read-only
    STATUS          mandatory
    DESCRIPTION     
            "Integer identifying the shelf that the
             IPsec system status table applies to"
    ::= { sonusIpSecSystemStatisticsEntry 1 }

sonusIpSecStatisticsInboundPacketsDiscardedInvalidSpi OBJECT-TYPE
    SYNTAX          Counter
    ACCESS          read-only
    STATUS          mandatory
    DESCRIPTION     
            "Count of inbound packets discarded due 
             to invalid SPI"
    ::= { sonusIpSecSystemStatisticsEntry 2 }

sonusIpSecStatisticsInboundPacketsDiscardedProtectPolicy OBJECT-TYPE
    SYNTAX          Counter
    ACCESS          read-only
    STATUS          mandatory
    DESCRIPTION     
            "Count of inbound packets discarded due 
             to a protect policy rule"
    ::= { sonusIpSecSystemStatisticsEntry 3 }

sonusIpSecStatisticsInboundPacketsDiscardedDiscardPolicy OBJECT-TYPE
    SYNTAX          Counter
    ACCESS          read-only
    STATUS          mandatory
    DESCRIPTION     
            "Count of inbound packets discarded due 
             to a dicard policy rule"
    ::= { sonusIpSecSystemStatisticsEntry 4 }

sonusIpSecStatisticsOutboundPacketsDiscardedProtectPolicy OBJECT-TYPE
    SYNTAX          Counter
    ACCESS          read-only
    STATUS          mandatory
    DESCRIPTION     
            "Count of outbound packets discarded due 
             to a protect policy rule"
    ::= { sonusIpSecSystemStatisticsEntry 5 }

sonusIpSecStatisticsOutboundPacketsDiscardedDiscardPolicy OBJECT-TYPE
    SYNTAX          Counter
    ACCESS          read-only
    STATUS          mandatory
    DESCRIPTION     
            "Count of outbound packets discarded due 
             to a dicard policy rule"
    ::= { sonusIpSecSystemStatisticsEntry 6 }

sonusIpSecStatisticsIkeSaNegotiationsSucceeded OBJECT-TYPE
    SYNTAX          Counter
    ACCESS          read-only
    STATUS          mandatory
    DESCRIPTION     
            "Count of IKE SA negotiation succeeded"
    ::= { sonusIpSecSystemStatisticsEntry 7 }

sonusIpSecStatisticsIkeSaNegotiationsFailed OBJECT-TYPE
    SYNTAX          Counter
    ACCESS          read-only
    STATUS          mandatory
    DESCRIPTION     
            "Count of IKE SA negotiation failed"
    ::= { sonusIpSecSystemStatisticsEntry 8 }

sonusIpSecStatisticsIpSecSaNegotiationsSucceeded OBJECT-TYPE
    SYNTAX          Counter
    ACCESS          read-only
    STATUS          mandatory
    DESCRIPTION     
            "Count of IPsec SA negotiation succeeded"
    ::= { sonusIpSecSystemStatisticsEntry 9 }

sonusIpSecStatisticsIpSecSaNegotiationsFailed OBJECT-TYPE
    SYNTAX          Counter
    ACCESS          read-only
    STATUS          mandatory
    DESCRIPTION     
            "Count of IPsec SA negotiation failed"
    ::= { sonusIpSecSystemStatisticsEntry 10 }

sonusIpSecStatisticsIkeV2SaNegotiationsSucceeded OBJECT-TYPE
    SYNTAX          Counter
    ACCESS          read-only
    STATUS          mandatory
    DESCRIPTION     
            "Count of IKE SA negotiation succeeded"
    ::= { sonusIpSecSystemStatisticsEntry 11 }

sonusIpSecStatisticsIkeV2SaNegotiationsFailed OBJECT-TYPE
    SYNTAX          Counter
    ACCESS          read-only
    STATUS          mandatory
    DESCRIPTION     
            "Count of IKE SA negotiation failed"
    ::= { sonusIpSecSystemStatisticsEntry 12 }

sonusIpSecSadIkeStatusTable OBJECT-TYPE
    SYNTAX          SEQUENCE OF SonusIpSecSadIkeStatusEntry
    ACCESS          not-accessible
    STATUS          mandatory
    DESCRIPTION     
            "The collection of IKE SA status information for the
             specified instance."
    ::= { sonusIpSec 15 }

sonusIpSecSadIkeStatusEntry OBJECT-TYPE
    SYNTAX          SonusIpSecSadIkeStatusEntry
    ACCESS          not-accessible
    STATUS          mandatory
    DESCRIPTION     
            "The collection of IKE SA status information for the
             specified instance."
    INDEX           { sonusIpSecSadIkeStatusIkeVersion, 
                      sonusIpSecSadIkeStatusIpVersion, 
                      sonusIpSecSadIkeStatusPeerIpAddr, 
                      sonusIpSecSadIkeStatusPeerIp6Addr, 
                      sonusIpSecSadIkeStatusIkeSaId }
    ::= { sonusIpSecSadIkeStatusTable 1 }

SonusIpSecSadIkeStatusEntry ::=
    SEQUENCE {
        sonusIpSecSadIkeStatusLocalIpAddr IpAddress,
        sonusIpSecSadIkeStatusPeerIpAddr IpAddress,
        sonusIpSecSadIkeStatusIkeSaId   INTEGER,
        sonusIpSecSadIkeStatusLocalIkeIdentityType          INTEGER,
        sonusIpSecSadIkeStatusLocalIkeIdentityIpAddr            IpAddress,
        sonusIpSecSadIkeStatusLocalIkeIdentityFqdn          DisplayString,
        sonusIpSecSadIkeStatusPeerIkeIdentityType         INTEGER,
        sonusIpSecSadIkeStatusPeerIkeIdentityIpAddr           IpAddress,
        sonusIpSecSadIkeStatusPeerIkeIdentityFqdn         DisplayString,
        sonusIpSecSadIkeStatusAuthenticationType        INTEGER,
        sonusIpSecSadIkeStatusIntegrityCipher     INTEGER,
        sonusIpSecSadIkeStatusEncryptionCipher      INTEGER,
        sonusIpSecSadIkeStatusLifetimeRemaining       INTEGER,
        sonusIpSecSadIkeStatusProtectionProfile       DisplayString,
        sonusIpSecSadIkeStatusLocalIp6Addr  Ipv6Address,
        sonusIpSecSadIkeStatusPeerIp6Addr Ipv6Address,
        sonusIpSecSadIkeStatusLocalIkeIdentityIp6Addr             Ipv6Address,
        sonusIpSecSadIkeStatusPeerIkeIdentityIp6Addr            Ipv6Address,
        sonusIpSecSadIkeStatusIpVersion INTEGER,
        sonusIpSecSadIkeStatusIkeIdentityIpVersion          INTEGER,
        sonusIpSecSadIkeStatusIkeVersion INTEGER
    }

sonusIpSecSadIkeStatusLocalIpAddr OBJECT-TYPE
    SYNTAX          IpAddress
    ACCESS          read-only
    STATUS          mandatory
    DESCRIPTION     
            "The IKE SA Local IP address."
    ::= { sonusIpSecSadIkeStatusEntry 1 }

sonusIpSecSadIkeStatusPeerIpAddr OBJECT-TYPE
    SYNTAX          IpAddress
    ACCESS          read-write
    STATUS          mandatory
    DESCRIPTION     
            "The IKE SA Peer IP address."
    ::= { sonusIpSecSadIkeStatusEntry 2 }

sonusIpSecSadIkeStatusIkeSaId OBJECT-TYPE
    SYNTAX          INTEGER
    ACCESS          read-write
    STATUS          mandatory
    DESCRIPTION     
            "The IKE SA internal identifier"
    ::= { sonusIpSecSadIkeStatusEntry 3 }

sonusIpSecSadIkeStatusLocalIkeIdentityType OBJECT-TYPE
    SYNTAX          INTEGER { none(0), ipv4(1), fqdn(2), dynamic(3), 
                        ipv6(4) }
    ACCESS          read-only
    STATUS          mandatory
    DESCRIPTION     
            "The Local IKE Identity type."
    ::= { sonusIpSecSadIkeStatusEntry 4 }

sonusIpSecSadIkeStatusLocalIkeIdentityIpAddr OBJECT-TYPE
    SYNTAX          IpAddress
    ACCESS          read-only
    STATUS          mandatory
    DESCRIPTION     
            "The Local IKE Identity IP address, if 
             sonusIpSecSadIkeStatusLocalIkeIdentityType is IPV4."
    ::= { sonusIpSecSadIkeStatusEntry 5 }

sonusIpSecSadIkeStatusLocalIkeIdentityFqdn OBJECT-TYPE
    SYNTAX          DisplayString (SIZE(0..255))
    ACCESS          read-only
    STATUS          mandatory
    DESCRIPTION     
            "The Local IKE Identity Fully Qualified Domain
             Name (FQDN), if sonusIpSecSadIkeStatusLocalIkeIdentityType 
             is FQDN."
    ::= { sonusIpSecSadIkeStatusEntry 6 }

sonusIpSecSadIkeStatusPeerIkeIdentityType OBJECT-TYPE
    SYNTAX          INTEGER { none(0), ipv4(1), fqdn(2), ipv6(3) }
    ACCESS          read-only
    STATUS          mandatory
    DESCRIPTION     
            "The Peer IKE Identity type."
    ::= { sonusIpSecSadIkeStatusEntry 7 }

sonusIpSecSadIkeStatusPeerIkeIdentityIpAddr OBJECT-TYPE
    SYNTAX          IpAddress
    ACCESS          read-only
    STATUS          mandatory
    DESCRIPTION     
            "The Peer IKE Identity IP address, if 
             sonusIpSecSadIkeStatusPeerIkeIdentityType is IPV4."
    ::= { sonusIpSecSadIkeStatusEntry 8 }

sonusIpSecSadIkeStatusPeerIkeIdentityFqdn OBJECT-TYPE
    SYNTAX          DisplayString (SIZE(0..255))
    ACCESS          read-only
    STATUS          mandatory
    DESCRIPTION     
            "The Peer IKE Identity Fully Qualified Domain
             Name (FQDN), if sonusIpSecSadIkeStatusPeerIkeIdentityType 
             is FQDN."
    ::= { sonusIpSecSadIkeStatusEntry 9 }

sonusIpSecSadIkeStatusAuthenticationType OBJECT-TYPE
    SYNTAX          INTEGER { presharedsecret(0) }
    ACCESS          read-only
    STATUS          mandatory
    DESCRIPTION     
            "The IKE Protection Profile Integrity Cipher."
    ::= { sonusIpSecSadIkeStatusEntry 10 }

sonusIpSecSadIkeStatusIntegrityCipher OBJECT-TYPE
    SYNTAX          INTEGER { hmac-sha1-96(0) }
    ACCESS          read-only
    STATUS          mandatory
    DESCRIPTION     
            "The IKE Protection Profile Integrity Cipher."
    ::= { sonusIpSecSadIkeStatusEntry 11 }

sonusIpSecSadIkeStatusEncryptionCipher OBJECT-TYPE
    SYNTAX          INTEGER { aes-cbc-128(0), three-des-cbc(1) }
    ACCESS          read-only
    STATUS          mandatory
    DESCRIPTION     
            "The IKE Protection Profile Encryption Cipher."
    ::= { sonusIpSecSadIkeStatusEntry 12 }

sonusIpSecSadIkeStatusLifetimeRemaining OBJECT-TYPE
    SYNTAX          INTEGER
    ACCESS          read-only
    STATUS          mandatory
    DESCRIPTION     
            "The IKE SA Lifetime remaining, in seconds.
             Valid range is 1200-1,000,000 seconds."
    ::= { sonusIpSecSadIkeStatusEntry 13 }

sonusIpSecSadIkeStatusProtectionProfile OBJECT-TYPE
    SYNTAX          DisplayString
    ACCESS          read-only
    STATUS          mandatory
    DESCRIPTION     
            "The IKE protection profile used by this SA."
    ::= { sonusIpSecSadIkeStatusEntry 14 }

sonusIpSecSadIkeStatusLocalIp6Addr OBJECT-TYPE
    SYNTAX          Ipv6Address
    ACCESS          read-only
    STATUS          mandatory
    DESCRIPTION     
            "The IKE SA Local IPV6 address."
    ::= { sonusIpSecSadIkeStatusEntry 15 }

sonusIpSecSadIkeStatusPeerIp6Addr OBJECT-TYPE
    SYNTAX          Ipv6Address
    ACCESS          read-write
    STATUS          mandatory
    DESCRIPTION     
            "The IKE SA Peer IPV6 address."
    ::= { sonusIpSecSadIkeStatusEntry 16 }

sonusIpSecSadIkeStatusLocalIkeIdentityIp6Addr OBJECT-TYPE
    SYNTAX          Ipv6Address
    ACCESS          read-only
    STATUS          mandatory
    DESCRIPTION     
            "The Local IKE Identity IPV6 address, if 
             sonusIpSecSadIkeStatusLocalIkeIdentityType is IPV6."
    ::= { sonusIpSecSadIkeStatusEntry 17 }

sonusIpSecSadIkeStatusPeerIkeIdentityIp6Addr OBJECT-TYPE
    SYNTAX          Ipv6Address
    ACCESS          read-only
    STATUS          mandatory
    DESCRIPTION     
            "The Peer IKE Identity IPV6 address, if 
             sonusIpSecSadIkeStatusPeerIkeIdentityType is IPV6."
    ::= { sonusIpSecSadIkeStatusEntry 18 }

sonusIpSecSadIkeStatusIpVersion OBJECT-TYPE
    SYNTAX          INTEGER { afInet(2), afInet6(24) }
    ACCESS          read-only
    STATUS          mandatory
    DESCRIPTION     
            "The Peer IP address type."
    ::= { sonusIpSecSadIkeStatusEntry 19 }

sonusIpSecSadIkeStatusIkeIdentityIpVersion OBJECT-TYPE
    SYNTAX          INTEGER { afInet(2), afInet6(24) }
    ACCESS          read-only
    STATUS          mandatory
    DESCRIPTION     
            "The Local Ike IP address type."
    ::= { sonusIpSecSadIkeStatusEntry 20 }

sonusIpSecSadIkeStatusIkeVersion OBJECT-TYPE
    SYNTAX          INTEGER { ikev1(1), ikev2(2) }
    ACCESS          read-write
    STATUS          mandatory
    DESCRIPTION     
            "This object indicates the IKE version configured "
    DEFVAL          { ikev1 }
    ::= { sonusIpSecSadIkeStatusEntry 21 }

sonusIpSecSadIkeStatisticsTable OBJECT-TYPE
    SYNTAX          SEQUENCE OF SonusIpSecSadIkeStatisticsEntry
    ACCESS          not-accessible
    STATUS          mandatory
    DESCRIPTION     
            "The collection of IKE SA statistics information for the
             specified instance."
    ::= { sonusIpSec 16 }

sonusIpSecSadIkeStatisticsEntry OBJECT-TYPE
    SYNTAX          SonusIpSecSadIkeStatisticsEntry
    ACCESS          not-accessible
    STATUS          mandatory
    DESCRIPTION     
            "The collection of IKE SA statistics information for the
             specified instance."
    INDEX           { sonusIpSecSadIkeStatisticsIkeSaId }
    ::= { sonusIpSecSadIkeStatisticsTable 1 }

SonusIpSecSadIkeStatisticsEntry ::=
    SEQUENCE {
        sonusIpSecSadIkeStatisticsLocalIpAddr     IpAddress,
        sonusIpSecSadIkeStatisticsPeerIpAddr    IpAddress,
        sonusIpSecSadIkeStatisticsIkeSaId INTEGER,
        sonusIpSecSadIkeStatisticsNegotiationsSucceeded               Counter,
        sonusIpSecSadIkeStatisticsNegotiationsFailed            Counter,
        sonusIpSecSadIkeStatisticsLocalIp6Addr      Ipv6Address,
        sonusIpSecSadIkeStatisticsPeerIp6Addr     Ipv6Address,
        sonusIpSecSadIkeStatisticsIpVersion   INTEGER
    }

sonusIpSecSadIkeStatisticsLocalIpAddr OBJECT-TYPE
    SYNTAX          IpAddress
    ACCESS          read-only
    STATUS          mandatory
    DESCRIPTION     
            "The IKE SA Local IP address."
    ::= { sonusIpSecSadIkeStatisticsEntry 1 }

sonusIpSecSadIkeStatisticsPeerIpAddr OBJECT-TYPE
    SYNTAX          IpAddress
    ACCESS          read-only
    STATUS          mandatory
    DESCRIPTION     
            "The IKE SA Peer IP address."
    ::= { sonusIpSecSadIkeStatisticsEntry 2 }

sonusIpSecSadIkeStatisticsIkeSaId OBJECT-TYPE
    SYNTAX          INTEGER
    ACCESS          read-only
    STATUS          mandatory
    DESCRIPTION     
            "The IKE SA internal identifier."
    ::= { sonusIpSecSadIkeStatisticsEntry 3 }

sonusIpSecSadIkeStatisticsNegotiationsSucceeded OBJECT-TYPE
    SYNTAX          Counter
    ACCESS          read-only
    STATUS          mandatory
    DESCRIPTION     
            "The IKE SA count of successful negotiations."
    ::= { sonusIpSecSadIkeStatisticsEntry 4 }

sonusIpSecSadIkeStatisticsNegotiationsFailed OBJECT-TYPE
    SYNTAX          Counter
    ACCESS          read-only
    STATUS          mandatory
    DESCRIPTION     
            "The IKE SA count of failed negotiations."
    ::= { sonusIpSecSadIkeStatisticsEntry 5 }

sonusIpSecSadIkeStatisticsLocalIp6Addr OBJECT-TYPE
    SYNTAX          Ipv6Address
    ACCESS          read-only
    STATUS          mandatory
    DESCRIPTION     
            "The IKE SA Local IP address."
    ::= { sonusIpSecSadIkeStatisticsEntry 6 }

sonusIpSecSadIkeStatisticsPeerIp6Addr OBJECT-TYPE
    SYNTAX          Ipv6Address
    ACCESS          read-only
    STATUS          mandatory
    DESCRIPTION     
            "The IKE SA Peer IPV6 address."
    ::= { sonusIpSecSadIkeStatisticsEntry 7 }

sonusIpSecSadIkeStatisticsIpVersion OBJECT-TYPE
    SYNTAX          INTEGER { afInet(2), afInet6(24) }
    ACCESS          read-only
    STATUS          mandatory
    DESCRIPTION     
            "The SadIke Local IP address type."
    ::= { sonusIpSecSadIkeStatisticsEntry 8 }

sonusIpSecSadIpSecStatusTable OBJECT-TYPE
    SYNTAX          SEQUENCE OF SonusIpSecSadIpSecStatusEntry
    ACCESS          not-accessible
    STATUS          mandatory
    DESCRIPTION     
            "The collection of IPsec SA status information for the
             specified instance."
    ::= { sonusIpSec 17 }

sonusIpSecSadIpSecStatusEntry OBJECT-TYPE
    SYNTAX          SonusIpSecSadIpSecStatusEntry
    ACCESS          not-accessible
    STATUS          mandatory
    DESCRIPTION     
            "The collection of IPsec SA status information for the
             specified instance."
    INDEX           { sonusIpSecSadIpSecStatusIpVersion, 
                      sonusIpSecSadIpSecStatusRemoteTunnelIpAddr, 
                      sonusIpSecSadIpSecStatusLocalTunnelIpAddr, 
                      sonusIpSecSadIpSecStatusRemoteTunnelIp6Addr, 
                      sonusIpSecSadIpSecStatusLocalTunnelIp6Addr, 
                      sonusIpSecSadIpSecStatusLocalSpi }
    ::= { sonusIpSecSadIpSecStatusTable 1 }

SonusIpSecSadIpSecStatusEntry ::=
    SEQUENCE {
        sonusIpSecSadIpSecStatusLocalTunnelIpAddr         IpAddress,
        sonusIpSecSadIpSecStatusLocalSpi INTEGER,
        sonusIpSecSadIpSecStatusRemoteTunnelIpAddr          IpAddress,
        sonusIpSecSadIpSecStatusRemoteSpi INTEGER,
        sonusIpSecSadIpSecStatusLocalIpAddr   IpAddress,
        sonusIpSecSadIpSecStatusLocalMask IpAddress,
        sonusIpSecSadIpSecStatusLocalPort INTEGER,
        sonusIpSecSadIpSecStatusRemoteIpAddr    IpAddress,
        sonusIpSecSadIpSecStatusRemoteMask  IpAddress,
        sonusIpSecSadIpSecStatusRemotePort  INTEGER,
        sonusIpSecSadIpSecStatusIpProtocol  INTEGER,
        sonusIpSecSadIpSecStatusSpdName DisplayString,
        sonusIpSecSadIpSecStatusEncapsulationMode         INTEGER,
        sonusIpSecSadIpSecStatusSecurityProtocol        INTEGER,
        sonusIpSecSadIpSecStatusIntegrityCipher       INTEGER,
        sonusIpSecSadIpSecStatusEncryptionCipher        INTEGER,
        sonusIpSecSadIpSecStatusAntiReplaySetting         INTEGER,
        sonusIpSecSadIpSecStatusLifetimeRemaining         INTEGER,
        sonusIpSecSadIpSecStatusParentIkeSaPeerIpAddr             IpAddress,
        sonusIpSecSadIpSecStatusParentIkeSaId     INTEGER,
        sonusIpSecSadIpSecStatusProtectionProfile         DisplayString,
        sonusIpSecSadIpSecStatusLocalTunnelIp6Addr          Ipv6Address,
        sonusIpSecSadIpSecStatusRemoteTunnelIp6Addr           Ipv6Address,
        sonusIpSecSadIpSecStatusLocalIp6Addr    Ipv6Address,
        sonusIpSecSadIpSecStatusLocalIpPrefixLength           INTEGER,
        sonusIpSecSadIpSecStatusRemoteIp6Addr     Ipv6Address,
        sonusIpSecSadIpSecStatusRemoteIpPrefixLength            INTEGER,
        sonusIpSecSadIpSecStatusParentIkeSaPeerIp6Addr              Ipv6Address,
        sonusIpSecSadIpSecStatusTunnelIpVersion       INTEGER,
        sonusIpSecSadIpSecStatusIpVersion INTEGER,
        sonusIpSecSadIpSecStatusParentIkeSaPeerIpVersion                INTEGER
    }

sonusIpSecSadIpSecStatusLocalTunnelIpAddr OBJECT-TYPE
    SYNTAX          IpAddress
    ACCESS          read-write
    STATUS          mandatory
    DESCRIPTION     
            "The IPsec SA Local Tunnel IP address."
    ::= { sonusIpSecSadIpSecStatusEntry 1 }

sonusIpSecSadIpSecStatusLocalSpi OBJECT-TYPE
    SYNTAX          INTEGER
    ACCESS          read-write
    STATUS          mandatory
    DESCRIPTION     
            "The IPsec SA Local SPI."
    ::= { sonusIpSecSadIpSecStatusEntry 2 }

sonusIpSecSadIpSecStatusRemoteTunnelIpAddr OBJECT-TYPE
    SYNTAX          IpAddress
    ACCESS          read-only
    STATUS          mandatory
    DESCRIPTION     
            "The IPsec SA Remote Tunnel IP address."
    ::= { sonusIpSecSadIpSecStatusEntry 3 }

sonusIpSecSadIpSecStatusRemoteSpi OBJECT-TYPE
    SYNTAX          INTEGER
    ACCESS          read-only
    STATUS          mandatory
    DESCRIPTION     
            "The IPsec SA Remote SPI."
    ::= { sonusIpSecSadIpSecStatusEntry 4 }

sonusIpSecSadIpSecStatusLocalIpAddr OBJECT-TYPE
    SYNTAX          IpAddress
    ACCESS          read-only
    STATUS          mandatory
    DESCRIPTION     
            "The IPsec SA traffic selector local IP address"
    ::= { sonusIpSecSadIpSecStatusEntry 5 }

sonusIpSecSadIpSecStatusLocalMask OBJECT-TYPE
    SYNTAX          IpAddress
    ACCESS          read-only
    STATUS          mandatory
    DESCRIPTION     
            "The IPsec SA traffic selector local IP mask"
    ::= { sonusIpSecSadIpSecStatusEntry 6 }

sonusIpSecSadIpSecStatusLocalPort OBJECT-TYPE
    SYNTAX          INTEGER (-1..65535)
    ACCESS          read-only
    STATUS          mandatory
    DESCRIPTION     
            "The IPsec SA traffic selector local IP port, -1 to 65535."
    ::= { sonusIpSecSadIpSecStatusEntry 7 }

sonusIpSecSadIpSecStatusRemoteIpAddr OBJECT-TYPE
    SYNTAX          IpAddress
    ACCESS          read-only
    STATUS          mandatory
    DESCRIPTION     
            "The IPsec SA traffic selector remote IP address"
    ::= { sonusIpSecSadIpSecStatusEntry 8 }

sonusIpSecSadIpSecStatusRemoteMask OBJECT-TYPE
    SYNTAX          IpAddress
    ACCESS          read-only
    STATUS          mandatory
    DESCRIPTION     
            "The IPsec SA traffic selector remote IP mask"
    ::= { sonusIpSecSadIpSecStatusEntry 9 }

sonusIpSecSadIpSecStatusRemotePort OBJECT-TYPE
    SYNTAX          INTEGER (-1..65535)
    ACCESS          read-only
    STATUS          mandatory
    DESCRIPTION     
            "The IPsec SA traffic selector remote IP port, -1 to 65535."
    ::= { sonusIpSecSadIpSecStatusEntry 10 }

sonusIpSecSadIpSecStatusIpProtocol OBJECT-TYPE
    SYNTAX          INTEGER (0..255)
    ACCESS          read-only
    STATUS          mandatory
    DESCRIPTION     
            "The IPsec SA traffic selector IP protocol, 0 to 255."
    ::= { sonusIpSecSadIpSecStatusEntry 11 }

sonusIpSecSadIpSecStatusSpdName OBJECT-TYPE
    SYNTAX          DisplayString
    ACCESS          read-only
    STATUS          mandatory
    DESCRIPTION     
            "The IPsec SPD rule used by this SA."
    ::= { sonusIpSecSadIpSecStatusEntry 12 }

sonusIpSecSadIpSecStatusEncapsulationMode OBJECT-TYPE
    SYNTAX          INTEGER { tunnelmode(0), transportmode(1) }
    ACCESS          read-only
    STATUS          mandatory
    DESCRIPTION     
            "The IPsec Protection Profile Security Protocol.
             Currently only ESP is supported."
    ::= { sonusIpSecSadIpSecStatusEntry 13 }

sonusIpSecSadIpSecStatusSecurityProtocol OBJECT-TYPE
    SYNTAX          INTEGER { esp(0) }
    ACCESS          read-only
    STATUS          mandatory
    DESCRIPTION     
            "The IPsec Protection Profile Security Protocol.
             Currently only ESP is supported."
    ::= { sonusIpSecSadIpSecStatusEntry 14 }

sonusIpSecSadIpSecStatusIntegrityCipher OBJECT-TYPE
    SYNTAX          INTEGER { hmac-sha1-96(0) }
    ACCESS          read-only
    STATUS          mandatory
    DESCRIPTION     
            "The IPsec Protection Profile Integrity Cipher."
    ::= { sonusIpSecSadIpSecStatusEntry 15 }

sonusIpSecSadIpSecStatusEncryptionCipher OBJECT-TYPE
    SYNTAX          INTEGER { null(0), three-des-cbc(1), aes-cbc-128(2) }
    ACCESS          read-only
    STATUS          mandatory
    DESCRIPTION     
            "The IPsec Protection Profile Encryption Cipher."
    ::= { sonusIpSecSadIpSecStatusEntry 16 }

sonusIpSecSadIpSecStatusAntiReplaySetting OBJECT-TYPE
    SYNTAX          INTEGER { disabled(0), enabled(1) }
    ACCESS          read-only
    STATUS          mandatory
    DESCRIPTION     
            "The IPsec Protection Profile Anti-Replay Setting."
    ::= { sonusIpSecSadIpSecStatusEntry 17 }

sonusIpSecSadIpSecStatusLifetimeRemaining OBJECT-TYPE
    SYNTAX          INTEGER
    ACCESS          read-only
    STATUS          mandatory
    DESCRIPTION     
            "The IPsec SA Lifetime remaining, in seconds.
             Valid range is 1200-1,000,000 seconds."
    ::= { sonusIpSecSadIpSecStatusEntry 18 }

sonusIpSecSadIpSecStatusParentIkeSaPeerIpAddr OBJECT-TYPE
    SYNTAX          IpAddress
    ACCESS          read-only
    STATUS          mandatory
    DESCRIPTION     
            "The IPsec SA Parent IKE SA IP address."
    ::= { sonusIpSecSadIpSecStatusEntry 19 }

sonusIpSecSadIpSecStatusParentIkeSaId OBJECT-TYPE
    SYNTAX          INTEGER
    ACCESS          read-only
    STATUS          mandatory
    DESCRIPTION     
            "The IPsec SA Parent IKE SA internal identifier."
    ::= { sonusIpSecSadIpSecStatusEntry 20 }

sonusIpSecSadIpSecStatusProtectionProfile OBJECT-TYPE
    SYNTAX          DisplayString
    ACCESS          read-only
    STATUS          mandatory
    DESCRIPTION     
            "The IPsec protection profile used by this SA."
    ::= { sonusIpSecSadIpSecStatusEntry 21 }

sonusIpSecSadIpSecStatusLocalTunnelIp6Addr OBJECT-TYPE
    SYNTAX          Ipv6Address
    ACCESS          read-write
    STATUS          mandatory
    DESCRIPTION     
            "The IPsec SA Local Tunnel IPV6 address."
    ::= { sonusIpSecSadIpSecStatusEntry 22 }

sonusIpSecSadIpSecStatusRemoteTunnelIp6Addr OBJECT-TYPE
    SYNTAX          Ipv6Address
    ACCESS          read-write
    STATUS          mandatory
    DESCRIPTION     
            "The IPsec SA Remote Tunnel IPV6 address."
    ::= { sonusIpSecSadIpSecStatusEntry 23 }

sonusIpSecSadIpSecStatusLocalIp6Addr OBJECT-TYPE
    SYNTAX          Ipv6Address
    ACCESS          read-only
    STATUS          mandatory
    DESCRIPTION     
            "The IPsec SA traffic selector local IPV6 address"
    ::= { sonusIpSecSadIpSecStatusEntry 24 }

sonusIpSecSadIpSecStatusLocalIpPrefixLength OBJECT-TYPE
    SYNTAX          INTEGER
    ACCESS          read-only
    STATUS          mandatory
    DESCRIPTION     
            "The IPsec SA traffic selector local IP prefix."
    ::= { sonusIpSecSadIpSecStatusEntry 25 }

sonusIpSecSadIpSecStatusRemoteIp6Addr OBJECT-TYPE
    SYNTAX          Ipv6Address
    ACCESS          read-only
    STATUS          mandatory
    DESCRIPTION     
            "The IPsec SA traffic selector local IPV6 address"
    ::= { sonusIpSecSadIpSecStatusEntry 26 }

sonusIpSecSadIpSecStatusRemoteIpPrefixLength OBJECT-TYPE
    SYNTAX          INTEGER
    ACCESS          read-only
    STATUS          mandatory
    DESCRIPTION     
            "The IPsec SA traffic selector local IP prefix."
    ::= { sonusIpSecSadIpSecStatusEntry 27 }

sonusIpSecSadIpSecStatusParentIkeSaPeerIp6Addr OBJECT-TYPE
    SYNTAX          Ipv6Address
    ACCESS          read-only
    STATUS          mandatory
    DESCRIPTION     
            "The IPsec SA Parent IKE SA IPV6 address."
    ::= { sonusIpSecSadIpSecStatusEntry 28 }

sonusIpSecSadIpSecStatusTunnelIpVersion OBJECT-TYPE
    SYNTAX          INTEGER { afInet(2), afInet6(24) }
    ACCESS          read-only
    STATUS          mandatory
    DESCRIPTION     
            "The Local Tunnel Ip Address Type"
    ::= { sonusIpSecSadIpSecStatusEntry 29 }

sonusIpSecSadIpSecStatusIpVersion OBJECT-TYPE
    SYNTAX          INTEGER { afInet(2), afInet6(24) }
    ACCESS          read-only
    STATUS          mandatory
    DESCRIPTION     
            "The Local Ip Address Type"
    ::= { sonusIpSecSadIpSecStatusEntry 30 }

sonusIpSecSadIpSecStatusParentIkeSaPeerIpVersion OBJECT-TYPE
    SYNTAX          INTEGER { afInet(2), afInet6(24) }
    ACCESS          read-only
    STATUS          mandatory
    DESCRIPTION     
            "The Peer Ip Address Type"
    ::= { sonusIpSecSadIpSecStatusEntry 31 }

sonusIpSecSadIpSecStatisticsTable OBJECT-TYPE
    SYNTAX          SEQUENCE OF SonusIpSecSadIpSecStatisticsEntry
    ACCESS          not-accessible
    STATUS          mandatory
    DESCRIPTION     
            "The collection of IPsec SA statistics information for the
             specified instance."
    ::= { sonusIpSec 18 }

sonusIpSecSadIpSecStatisticsEntry OBJECT-TYPE
    SYNTAX          SonusIpSecSadIpSecStatisticsEntry
    ACCESS          not-accessible
    STATUS          mandatory
    DESCRIPTION     
            "The collection of IPsec SA statistics information for the
             specified instance."
    INDEX           { sonusIpSecSadIpSecStatisticsLocalTunnelIpAddr, 
                      sonusIpSecSadIpSecStatisticsLocalSpi, 
                      sonusIpSecSadIpSecStatisticsLocalTunnelIp6Addr, 
                      sonusIpSecSadIpSecStatisticsIpVersion }
    ::= { sonusIpSecSadIpSecStatisticsTable 1 }

SonusIpSecSadIpSecStatisticsEntry ::=
    SEQUENCE {
        sonusIpSecSadIpSecStatisticsLocalTunnelIpAddr             IpAddress,
        sonusIpSecSadIpSecStatisticsLocalSpi    INTEGER,
        sonusIpSecSadIpSecStatisticsRemoteTunnelIpAddr              IpAddress,
        sonusIpSecSadIpSecStatisticsRemoteSpi     INTEGER,
        sonusIpSecSadIpSecStatisticsPacketsSent       Counter,
        sonusIpSecSadIpSecStatisticsPacketsReceived           Counter,
        sonusIpSecSadIpSecStatisticsPacketsDiscardedFailedIntegrity                           Counter,
        sonusIpSecSadIpSecStatisticsPacketsDiscardedFailedSelector                          Counter,
        sonusIpSecSadIpSecStatisticsPacketsDiscardedFailedAntiReplay                            Counter,
        sonusIpSecSadIpSecStatisticsLocalTunnelIp6Addr              Ipv6Address,
        sonusIpSecSadIpSecStatisticsRemoteTunnelIp6Addr               Ipv6Address,
        sonusIpSecSadIpSecStatisticsIpVersion     INTEGER
    }

sonusIpSecSadIpSecStatisticsLocalTunnelIpAddr OBJECT-TYPE
    SYNTAX          IpAddress
    ACCESS          read-only
    STATUS          mandatory
    DESCRIPTION     
            "The IPsec SA Local Tunnel IP address."
    ::= { sonusIpSecSadIpSecStatisticsEntry 1 }

sonusIpSecSadIpSecStatisticsLocalSpi OBJECT-TYPE
    SYNTAX          INTEGER
    ACCESS          read-only
    STATUS          mandatory
    DESCRIPTION     
            "The IPsec SA Local SPI."
    ::= { sonusIpSecSadIpSecStatisticsEntry 2 }

sonusIpSecSadIpSecStatisticsRemoteTunnelIpAddr OBJECT-TYPE
    SYNTAX          IpAddress
    ACCESS          read-only
    STATUS          mandatory
    DESCRIPTION     
            "The IPsec SA Remote Tunnel IP address."
    ::= { sonusIpSecSadIpSecStatisticsEntry 3 }

sonusIpSecSadIpSecStatisticsRemoteSpi OBJECT-TYPE
    SYNTAX          INTEGER
    ACCESS          read-only
    STATUS          mandatory
    DESCRIPTION     
            "The IPsec SA Remote SPI."
    ::= { sonusIpSecSadIpSecStatisticsEntry 4 }

sonusIpSecSadIpSecStatisticsPacketsSent OBJECT-TYPE
    SYNTAX          Counter
    ACCESS          read-only
    STATUS          mandatory
    DESCRIPTION     
            "The IPsec SA count of packets sent."
    ::= { sonusIpSecSadIpSecStatisticsEntry 5 }

sonusIpSecSadIpSecStatisticsPacketsReceived OBJECT-TYPE
    SYNTAX          Counter
    ACCESS          read-only
    STATUS          mandatory
    DESCRIPTION     
            "The IPsec SA count of packets received."
    ::= { sonusIpSecSadIpSecStatisticsEntry 6 }

sonusIpSecSadIpSecStatisticsPacketsDiscardedFailedIntegrity OBJECT-TYPE
    SYNTAX          Counter
    ACCESS          read-only
    STATUS          mandatory
    DESCRIPTION     
            "The IPsec SA count of packets discarded due
             to failed integrity check."
    ::= { sonusIpSecSadIpSecStatisticsEntry 7 }

sonusIpSecSadIpSecStatisticsPacketsDiscardedFailedSelector OBJECT-TYPE
    SYNTAX          Counter
    ACCESS          read-only
    STATUS          mandatory
    DESCRIPTION     
            "The IPsec SA count of packets discarded due
             to failed traffic selector check."
    ::= { sonusIpSecSadIpSecStatisticsEntry 8 }

sonusIpSecSadIpSecStatisticsPacketsDiscardedFailedAntiReplay OBJECT-TYPE
    SYNTAX          Counter
    ACCESS          read-only
    STATUS          mandatory
    DESCRIPTION     
            "The IPsec SA count of packets discarded due
             to failed anti-replay test."
    ::= { sonusIpSecSadIpSecStatisticsEntry 9 }

sonusIpSecSadIpSecStatisticsLocalTunnelIp6Addr OBJECT-TYPE
    SYNTAX          Ipv6Address
    ACCESS          read-write
    STATUS          mandatory
    DESCRIPTION     
            "The IPsec SA Local Tunnel IPV6 address."
    ::= { sonusIpSecSadIpSecStatisticsEntry 10 }

sonusIpSecSadIpSecStatisticsRemoteTunnelIp6Addr OBJECT-TYPE
    SYNTAX          Ipv6Address
    ACCESS          read-write
    STATUS          mandatory
    DESCRIPTION     
            "The IPsec SA Remote Tunnel IPV6 address."
    ::= { sonusIpSecSadIpSecStatisticsEntry 11 }

sonusIpSecSadIpSecStatisticsIpVersion OBJECT-TYPE
    SYNTAX          INTEGER { afInet(2), afInet6(24) }
    ACCESS          read-only
    STATUS          mandatory
    DESCRIPTION     
            "The Local Tunnel IP sersion."
    ::= { sonusIpSecSadIpSecStatisticsEntry 12 }

sonusIpSecSadIpSecStatusByIkeTable OBJECT-TYPE
    SYNTAX          SEQUENCE OF SonusIpSecSadIpSecStatusByIkeEntry
    ACCESS          not-accessible
    STATUS          mandatory
    DESCRIPTION     
            "The collection of IPsec SA status information for the
             specified instance."
    ::= { sonusIpSec 19 }

sonusIpSecSadIpSecStatusByIkeEntry OBJECT-TYPE
    SYNTAX          SonusIpSecSadIpSecStatusByIkeEntry
    ACCESS          not-accessible
    STATUS          mandatory
    DESCRIPTION     
            "The collection of IPsec SA status information for the
             specified instance."
    INDEX           { sonusIpSecSadIpSecStatusByIkeParentIkeSaId, 
                      sonusIpSecSadIpSecStatusByIkeLocalTunnelIpAddr, 
                      sonusIpSecSadIpSecStatusByIkeLocalTunnelIp6Addr, 
                      sonusIpSecSadIpSecStatusByIkeTunnelIpVersion, 
                      sonusIpSecSadIpSecStatusByIkeLocalSpi }
    ::= { sonusIpSecSadIpSecStatusByIkeTable 1 }

SonusIpSecSadIpSecStatusByIkeEntry ::=
    SEQUENCE {
        sonusIpSecSadIpSecStatusByIkeLocalTunnelIpAddr              IpAddress,
        sonusIpSecSadIpSecStatusByIkeLocalSpi     INTEGER,
        sonusIpSecSadIpSecStatusByIkeRemoteTunnelIpAddr               IpAddress,
        sonusIpSecSadIpSecStatusByIkeRemoteSpi      INTEGER,
        sonusIpSecSadIpSecStatusByIkeLocalIpAddr        IpAddress,
        sonusIpSecSadIpSecStatusByIkeLocalMask      IpAddress,
        sonusIpSecSadIpSecStatusByIkeLocalPort      INTEGER,
        sonusIpSecSadIpSecStatusByIkeRemoteIpAddr         IpAddress,
        sonusIpSecSadIpSecStatusByIkeRemoteMask       IpAddress,
        sonusIpSecSadIpSecStatusByIkeRemotePort       INTEGER,
        sonusIpSecSadIpSecStatusByIkeIpProtocol       INTEGER,
        sonusIpSecSadIpSecStatusByIkeSpdName    DisplayString,
        sonusIpSecSadIpSecStatusByIkeEncapsulationMode              INTEGER,
        sonusIpSecSadIpSecStatusByIkeSecurityProtocol             INTEGER,
        sonusIpSecSadIpSecStatusByIkeIntegrityCipher            INTEGER,
        sonusIpSecSadIpSecStatusByIkeEncryptionCipher             INTEGER,
        sonusIpSecSadIpSecStatusByIkeAntiReplaySetting              INTEGER,
        sonusIpSecSadIpSecStatusByIkeLifetimeRemaining              INTEGER,
        sonusIpSecSadIpSecStatusByIkeParentIkeSaPeerIpAddr                  IpAddress,
        sonusIpSecSadIpSecStatusByIkeParentIkeSaId          INTEGER,
        sonusIpSecSadIpSecStatusByIkeParentProtectionProfile                    DisplayString,
        sonusIpSecSadIpSecStatusByIkeLocalTunnelIp6Addr               Ipv6Address,
        sonusIpSecSadIpSecStatusByIkeRemoteTunnelIp6Addr                Ipv6Address,
        sonusIpSecSadIpSecStatusByIkeLocalIp6Addr         Ipv6Address,
        sonusIpSecSadIpSecStatusIkeLocalIpPrefixLength              INTEGER,
        sonusIpSecSadIpSecStatusByIkeRemoteIp6Addr          Ipv6Address,
        sonusIpSecSadIpSecStatusIkeRemoteIpPrefixLength               INTEGER,
        sonusIpSecSadIpSecStatusByIkeParentIkeSaPeerIp6Addr                   Ipv6Address,
        sonusIpSecSadIpSecStatusByIkeTunnelIpVersion            INTEGER,
        sonusIpSecSadIpSecStatusByIkeIpVersion      INTEGER,
        sonusIpSecSadIpSecStatusByIkeParentIkeSaPeerIpVersion                     INTEGER
    }

sonusIpSecSadIpSecStatusByIkeLocalTunnelIpAddr OBJECT-TYPE
    SYNTAX          IpAddress
    ACCESS          read-only
    STATUS          mandatory
    DESCRIPTION     
            "The IPsec SA Local Tunnel IP address."
    ::= { sonusIpSecSadIpSecStatusByIkeEntry 1 }

sonusIpSecSadIpSecStatusByIkeLocalSpi OBJECT-TYPE
    SYNTAX          INTEGER
    ACCESS          read-only
    STATUS          mandatory
    DESCRIPTION     
            "The IPsec SA Local SPI."
    ::= { sonusIpSecSadIpSecStatusByIkeEntry 2 }

sonusIpSecSadIpSecStatusByIkeRemoteTunnelIpAddr OBJECT-TYPE
    SYNTAX          IpAddress
    ACCESS          read-only
    STATUS          mandatory
    DESCRIPTION     
            "The IPsec SA Remote Tunnel IP address."
    ::= { sonusIpSecSadIpSecStatusByIkeEntry 3 }

sonusIpSecSadIpSecStatusByIkeRemoteSpi OBJECT-TYPE
    SYNTAX          INTEGER
    ACCESS          read-only
    STATUS          mandatory
    DESCRIPTION     
            "The IPsec SA Remote SPI."
    ::= { sonusIpSecSadIpSecStatusByIkeEntry 4 }

sonusIpSecSadIpSecStatusByIkeLocalIpAddr OBJECT-TYPE
    SYNTAX          IpAddress
    ACCESS          read-only
    STATUS          mandatory
    DESCRIPTION     
            "The IPsec SA traffic selector local IP address"
    ::= { sonusIpSecSadIpSecStatusByIkeEntry 5 }

sonusIpSecSadIpSecStatusByIkeLocalMask OBJECT-TYPE
    SYNTAX          IpAddress
    ACCESS          read-only
    STATUS          mandatory
    DESCRIPTION     
            "The IPsec SA traffic selector local IP mask"
    ::= { sonusIpSecSadIpSecStatusByIkeEntry 6 }

sonusIpSecSadIpSecStatusByIkeLocalPort OBJECT-TYPE
    SYNTAX          INTEGER (-1..65535)
    ACCESS          read-only
    STATUS          mandatory
    DESCRIPTION     
            "The IPsec SA traffic selector local IP port, -1 to 65535."
    ::= { sonusIpSecSadIpSecStatusByIkeEntry 7 }

sonusIpSecSadIpSecStatusByIkeRemoteIpAddr OBJECT-TYPE
    SYNTAX          IpAddress
    ACCESS          read-only
    STATUS          mandatory
    DESCRIPTION     
            "The IPsec SA traffic selector remote IP address"
    ::= { sonusIpSecSadIpSecStatusByIkeEntry 8 }

sonusIpSecSadIpSecStatusByIkeRemoteMask OBJECT-TYPE
    SYNTAX          IpAddress
    ACCESS          read-only
    STATUS          mandatory
    DESCRIPTION     
            "The IPsec SA traffic selector remote IP mask"
    ::= { sonusIpSecSadIpSecStatusByIkeEntry 9 }

sonusIpSecSadIpSecStatusByIkeRemotePort OBJECT-TYPE
    SYNTAX          INTEGER (-1..65535)
    ACCESS          read-only
    STATUS          mandatory
    DESCRIPTION     
            "The IPsec SA traffic selector remote IP port, -1 to 65535."
    ::= { sonusIpSecSadIpSecStatusByIkeEntry 10 }

sonusIpSecSadIpSecStatusByIkeIpProtocol OBJECT-TYPE
    SYNTAX          INTEGER (0..255)
    ACCESS          read-only
    STATUS          mandatory
    DESCRIPTION     
            "The IPsec SA traffic selector IP protocol, 0 to 255."
    ::= { sonusIpSecSadIpSecStatusByIkeEntry 11 }

sonusIpSecSadIpSecStatusByIkeSpdName OBJECT-TYPE
    SYNTAX          DisplayString
    ACCESS          read-only
    STATUS          mandatory
    DESCRIPTION     
            "The IPsec SPD rule used by this SA."
    ::= { sonusIpSecSadIpSecStatusByIkeEntry 12 }

sonusIpSecSadIpSecStatusByIkeEncapsulationMode OBJECT-TYPE
    SYNTAX          INTEGER { tunnelmode(0), transportmode(1) }
    ACCESS          read-only
    STATUS          mandatory
    DESCRIPTION     
            "The IPsec Protection Profile Security Protocol.
             Currently only ESP is supported."
    ::= { sonusIpSecSadIpSecStatusByIkeEntry 13 }

sonusIpSecSadIpSecStatusByIkeSecurityProtocol OBJECT-TYPE
    SYNTAX          INTEGER { esp(0) }
    ACCESS          read-only
    STATUS          mandatory
    DESCRIPTION     
            "The IPsec Protection Profile Security Protocol.
             Currently only ESP is supported."
    ::= { sonusIpSecSadIpSecStatusByIkeEntry 14 }

sonusIpSecSadIpSecStatusByIkeIntegrityCipher OBJECT-TYPE
    SYNTAX          INTEGER { hmac-sha1-96(0) }
    ACCESS          read-only
    STATUS          mandatory
    DESCRIPTION     
            "The IPsec Protection Profile Integrity Cipher."
    ::= { sonusIpSecSadIpSecStatusByIkeEntry 15 }

sonusIpSecSadIpSecStatusByIkeEncryptionCipher OBJECT-TYPE
    SYNTAX          INTEGER { null(0), three-des-cbc(1), aes-cbc-128(2) }
    ACCESS          read-only
    STATUS          mandatory
    DESCRIPTION     
            "The IPsec Protection Profile Encryption Cipher."
    ::= { sonusIpSecSadIpSecStatusByIkeEntry 16 }

sonusIpSecSadIpSecStatusByIkeAntiReplaySetting OBJECT-TYPE
    SYNTAX          INTEGER { disabled(0), enabled(1) }
    ACCESS          read-only
    STATUS          mandatory
    DESCRIPTION     
            "The IPsec Protection Profile Anti-Replay Setting."
    ::= { sonusIpSecSadIpSecStatusByIkeEntry 17 }

sonusIpSecSadIpSecStatusByIkeLifetimeRemaining OBJECT-TYPE
    SYNTAX          INTEGER
    ACCESS          read-only
    STATUS          mandatory
    DESCRIPTION     
            "The IPsec SA Lifetime remaining, in seconds.
             Valid range is 1200-1,000,000 seconds."
    ::= { sonusIpSecSadIpSecStatusByIkeEntry 18 }

sonusIpSecSadIpSecStatusByIkeParentIkeSaPeerIpAddr OBJECT-TYPE
    SYNTAX          IpAddress
    ACCESS          read-only
    STATUS          mandatory
    DESCRIPTION     
            "The IPsec SA Parent IKE SA IP address."
    ::= { sonusIpSecSadIpSecStatusByIkeEntry 19 }

sonusIpSecSadIpSecStatusByIkeParentIkeSaId OBJECT-TYPE
    SYNTAX          INTEGER
    ACCESS          read-only
    STATUS          mandatory
    DESCRIPTION     
            "The IPsec SA Parent IKE SA internal identifier."
    ::= { sonusIpSecSadIpSecStatusByIkeEntry 20 }

sonusIpSecSadIpSecStatusByIkeParentProtectionProfile OBJECT-TYPE
    SYNTAX          DisplayString
    ACCESS          read-only
    STATUS          mandatory
    DESCRIPTION     
            "The IPsec protection profile used by this SA."
    ::= { sonusIpSecSadIpSecStatusByIkeEntry 21 }

sonusIpSecSadIpSecStatusByIkeLocalTunnelIp6Addr OBJECT-TYPE
    SYNTAX          Ipv6Address
    ACCESS          read-only
    STATUS          mandatory
    DESCRIPTION     
            "The IPsec SA Local Tunnel IP address."
    ::= { sonusIpSecSadIpSecStatusByIkeEntry 22 }

sonusIpSecSadIpSecStatusByIkeRemoteTunnelIp6Addr OBJECT-TYPE
    SYNTAX          Ipv6Address
    ACCESS          read-only
    STATUS          mandatory
    DESCRIPTION     
            "The IPsec SA Remote Tunnel IPV6 address."
    ::= { sonusIpSecSadIpSecStatusByIkeEntry 23 }

sonusIpSecSadIpSecStatusByIkeLocalIp6Addr OBJECT-TYPE
    SYNTAX          Ipv6Address
    ACCESS          read-only
    STATUS          mandatory
    DESCRIPTION     
            "The IPsec SA traffic selector local IPV6 address"
    ::= { sonusIpSecSadIpSecStatusByIkeEntry 24 }

sonusIpSecSadIpSecStatusIkeLocalIpPrefixLength OBJECT-TYPE
    SYNTAX          INTEGER
    ACCESS          read-only
    STATUS          mandatory
    DESCRIPTION     
            "The IPsec SA traffic selector local IP mask"
    ::= { sonusIpSecSadIpSecStatusByIkeEntry 25 }

sonusIpSecSadIpSecStatusByIkeRemoteIp6Addr OBJECT-TYPE
    SYNTAX          Ipv6Address
    ACCESS          read-only
    STATUS          mandatory
    DESCRIPTION     
            "The IPsec SA traffic selector remote IP address"
    ::= { sonusIpSecSadIpSecStatusByIkeEntry 26 }

sonusIpSecSadIpSecStatusIkeRemoteIpPrefixLength OBJECT-TYPE
    SYNTAX          INTEGER
    ACCESS          read-only
    STATUS          mandatory
    DESCRIPTION     
            "The IPsec SA traffic selector remote IP mask"
    ::= { sonusIpSecSadIpSecStatusByIkeEntry 27 }

sonusIpSecSadIpSecStatusByIkeParentIkeSaPeerIp6Addr OBJECT-TYPE
    SYNTAX          Ipv6Address
    ACCESS          read-only
    STATUS          mandatory
    DESCRIPTION     
            "The IPsec SA Parent IKE SA IPV6 address."
    ::= { sonusIpSecSadIpSecStatusByIkeEntry 28 }

sonusIpSecSadIpSecStatusByIkeTunnelIpVersion OBJECT-TYPE
    SYNTAX          INTEGER { afInet(2), afInet6(24) }
    ACCESS          read-only
    STATUS          mandatory
    DESCRIPTION     
            "The Local Tunnel IP version."
    ::= { sonusIpSecSadIpSecStatusByIkeEntry 29 }

sonusIpSecSadIpSecStatusByIkeIpVersion OBJECT-TYPE
    SYNTAX          INTEGER { afInet(2), afInet6(24) }
    ACCESS          read-only
    STATUS          mandatory
    DESCRIPTION     
            "The Local Tunnel IP version."
    ::= { sonusIpSecSadIpSecStatusByIkeEntry 30 }

sonusIpSecSadIpSecStatusByIkeParentIkeSaPeerIpVersion OBJECT-TYPE
    SYNTAX          INTEGER { afInet(2), afInet6(24) }
    ACCESS          read-only
    STATUS          mandatory
    DESCRIPTION     
            "The Local Tunnel IP version."
    ::= { sonusIpSecSadIpSecStatusByIkeEntry 31 }

sonusIpSecSadIkeV2StatisticsTable OBJECT-TYPE
    SYNTAX          SEQUENCE OF SonusIpSecSadIkeV2StatisticsEntry
    ACCESS          not-accessible
    STATUS          mandatory
    DESCRIPTION     
            "The collection of IKEv2 SA statistics information for the
             specified instance."
    ::= { sonusIpSec 20 }

sonusIpSecSadIkeV2StatisticsEntry OBJECT-TYPE
    SYNTAX          SonusIpSecSadIkeV2StatisticsEntry
    ACCESS          not-accessible
    STATUS          mandatory
    DESCRIPTION     
            "The collection of IKEV2 SA statistics information for the
             specified instance."
    INDEX           { sonusIpSecSadIkeV2StatisticsIpVersion, 
                      sonusIpSecSadIkeV2StatisticsPeerIpAddr, 
                      sonusIpSecSadIkeV2StatisticsPeerIp6Addr }
    ::= { sonusIpSecSadIkeV2StatisticsTable 1 }

SonusIpSecSadIkeV2StatisticsEntry ::=
    SEQUENCE {
        sonusIpSecSadIkeV2StatisticsLocalIpAddr       IpAddress,
        sonusIpSecSadIkeV2StatisticsPeerIpAddr      IpAddress,
        sonusIpSecSadIkeV2StatisticsNegotiationsSucceeded                 Counter,
        sonusIpSecSadIkeV2StatisticsNegotiationsFailed              Counter,
        sonusIpSecSadIkeV2StatisticsLocalIp6Addr        Ipv6Address,
        sonusIpSecSadIkeV2StatisticsPeerIp6Addr       Ipv6Address,
        sonusIpSecSadIkeV2StatisticsIpVersion     INTEGER
    }

sonusIpSecSadIkeV2StatisticsLocalIpAddr OBJECT-TYPE
    SYNTAX          IpAddress
    ACCESS          read-only
    STATUS          mandatory
    DESCRIPTION     
            "The IKEV2 SA Local IP address."
    ::= { sonusIpSecSadIkeV2StatisticsEntry 1 }

sonusIpSecSadIkeV2StatisticsPeerIpAddr OBJECT-TYPE
    SYNTAX          IpAddress
    ACCESS          read-only
    STATUS          mandatory
    DESCRIPTION     
            "The IKEV2 SA Peer IP address."
    ::= { sonusIpSecSadIkeV2StatisticsEntry 2 }

sonusIpSecSadIkeV2StatisticsNegotiationsSucceeded OBJECT-TYPE
    SYNTAX          Counter
    ACCESS          read-only
    STATUS          mandatory
    DESCRIPTION     
            "The IKEV2 SA count of successful negotiations."
    ::= { sonusIpSecSadIkeV2StatisticsEntry 3 }

sonusIpSecSadIkeV2StatisticsNegotiationsFailed OBJECT-TYPE
    SYNTAX          Counter
    ACCESS          read-only
    STATUS          mandatory
    DESCRIPTION     
            "The IKEV2 SA count of failed negotiations."
    ::= { sonusIpSecSadIkeV2StatisticsEntry 4 }

sonusIpSecSadIkeV2StatisticsLocalIp6Addr OBJECT-TYPE
    SYNTAX          Ipv6Address
    ACCESS          read-only
    STATUS          mandatory
    DESCRIPTION     
            "The IKEV2 SA Local IP address."
    ::= { sonusIpSecSadIkeV2StatisticsEntry 5 }

sonusIpSecSadIkeV2StatisticsPeerIp6Addr OBJECT-TYPE
    SYNTAX          Ipv6Address
    ACCESS          read-only
    STATUS          mandatory
    DESCRIPTION     
            "The IKEV2 SA Peer IPV6 address."
    ::= { sonusIpSecSadIkeV2StatisticsEntry 6 }

sonusIpSecSadIkeV2StatisticsIpVersion OBJECT-TYPE
    SYNTAX          INTEGER { afInet(2), afInet6(24) }
    ACCESS          read-only
    STATUS          mandatory
    DESCRIPTION     
            "The SadIke Local IP address type."
    ::= { sonusIpSecSadIkeV2StatisticsEntry 7 }

sonusNrsIsakmpdIkeStatTable OBJECT-TYPE
    SYNTAX          SEQUENCE OF SonusNrsIsakmpdIkeStatEntry
    ACCESS          not-accessible
    STATUS          mandatory
    DESCRIPTION     
            "The collection of IKE SA statistics information for the
             specified instance and all peers."
    ::= { sonusIpSec 21 }

sonusNrsIsakmpdIkeStatEntry OBJECT-TYPE
    SYNTAX          SonusNrsIsakmpdIkeStatEntry
    ACCESS          not-accessible
    STATUS          mandatory
    DESCRIPTION     
            "The collection of IKE SA statistics information for the
             specified instance and all peers."
    INDEX           { sonusNrsIsakmpdIkeStatIndex }
    ::= { sonusNrsIsakmpdIkeStatTable 1 }

SonusNrsIsakmpdIkeStatEntry ::=
    SEQUENCE {
        sonusNrsIsakmpdIkeStatIndex     INTEGER,
        sonusNrsIsakmpdIkeStatName      DisplayString,
        sonusNrsIsakmpdIkeStatIkeSASucceeded    Counter,
        sonusNrsIsakmpdIkeStatIpsecSASucceeded      Counter,
        sonusNrsIsakmpdIkeP1negotiationFailedCnt        Counter,
        sonusNrsIsakmpdIkeP2negotiationFailedCnt        Counter,
        sonusNrsIsakmpdIkeV2InitFailedCnt Counter,
        sonusNrsIsakmpdIkeV2ChildSaFailedCnt    Counter,
        sonusNrsIsakmpdIkePeerNoResponse Counter,
        sonusNrsIsakmpdIkePldMalformedCnt Counter,
        sonusNrsIsakmpdIkeProposalIkeFailedCnt      Counter,
        sonusNrsIsakmpdIkeProposalIpsecFailedCnt        Counter,
        sonusNrsIsakmpdIkeInvalidIDinfoCnt  Counter,
        sonusNrsIsakmpdIkeInvalidHashCnt Counter,
        sonusNrsIsakmpdIkeV2AuthFailedCnt Counter,
        sonusNrsIsakmpdIkeTSFailedCnt   Counter,
        sonusNrsIsakmpdIkePeerIpAddress IpAddress,
        sonusNrsIsakmpdIkePeerIp6Address Ipv6Address,
        sonusNrsIsakmpdIkePeerIpVersion INTEGER,
        sonusNrsIsakmpdIkeDPDFailedCnt  Counter
    }

sonusNrsIsakmpdIkeStatIndex OBJECT-TYPE
    SYNTAX          INTEGER
    ACCESS          read-only
    STATUS          mandatory
    DESCRIPTION     
            "The index assigned to this IPsec IPD
             when it was created. Cannot be modified."
    ::= { sonusNrsIsakmpdIkeStatEntry 1 }

sonusNrsIsakmpdIkeStatName OBJECT-TYPE
    SYNTAX          DisplayString
    ACCESS          read-only
    STATUS          mandatory
    DESCRIPTION     
            "The administrative name of the IPsec IPD."
    ::= { sonusNrsIsakmpdIkeStatEntry 2 }

sonusNrsIsakmpdIkeStatIkeSASucceeded OBJECT-TYPE
    SYNTAX          Counter
    ACCESS          read-only
    STATUS          mandatory
    DESCRIPTION     
            "Count of successful IKE SA negotiations per IPD."
    ::= { sonusNrsIsakmpdIkeStatEntry 3 }

sonusNrsIsakmpdIkeStatIpsecSASucceeded OBJECT-TYPE
    SYNTAX          Counter
    ACCESS          read-only
    STATUS          mandatory
    DESCRIPTION     
            "Count of successful  IPSEC SAs per IPD"
    ::= { sonusNrsIsakmpdIkeStatEntry 4 }

sonusNrsIsakmpdIkeP1negotiationFailedCnt OBJECT-TYPE
    SYNTAX          Counter
    ACCESS          read-only
    STATUS          mandatory
    DESCRIPTION     
            "Count of Phase 1 negotiation failure for IKEv1"
    ::= { sonusNrsIsakmpdIkeStatEntry 5 }

sonusNrsIsakmpdIkeP2negotiationFailedCnt OBJECT-TYPE
    SYNTAX          Counter
    ACCESS          read-only
    STATUS          mandatory
    DESCRIPTION     
            "Count of Phase 2 negotiation failure for IKEv2"
    ::= { sonusNrsIsakmpdIkeStatEntry 6 }

sonusNrsIsakmpdIkeV2InitFailedCnt OBJECT-TYPE
    SYNTAX          Counter
    ACCESS          read-only
    STATUS          mandatory
    DESCRIPTION     
            "Count of SA failed during INIT for IKEv2"
    ::= { sonusNrsIsakmpdIkeStatEntry 7 }

sonusNrsIsakmpdIkeV2ChildSaFailedCnt OBJECT-TYPE
    SYNTAX          Counter
    ACCESS          read-only
    STATUS          mandatory
    DESCRIPTION     
            "Count of failed CHILDSA negotiations for IKEv2"
    ::= { sonusNrsIsakmpdIkeStatEntry 8 }

sonusNrsIsakmpdIkePeerNoResponse OBJECT-TYPE
    SYNTAX          Counter
    ACCESS          read-only
    STATUS          mandatory
    DESCRIPTION     
            "Count of failures due to no response from peers."
    ::= { sonusNrsIsakmpdIkeStatEntry 9 }

sonusNrsIsakmpdIkePldMalformedCnt OBJECT-TYPE
    SYNTAX          Counter
    ACCESS          read-only
    STATUS          mandatory
    DESCRIPTION     
            "Count of SA failure due to malformed payload"
    ::= { sonusNrsIsakmpdIkeStatEntry 10 }

sonusNrsIsakmpdIkeProposalIkeFailedCnt OBJECT-TYPE
    SYNTAX          Counter
    ACCESS          read-only
    STATUS          mandatory
    DESCRIPTION     
            "Count of SA failure due to proposal failures"
    ::= { sonusNrsIsakmpdIkeStatEntry 11 }

sonusNrsIsakmpdIkeProposalIpsecFailedCnt OBJECT-TYPE
    SYNTAX          Counter
    ACCESS          read-only
    STATUS          mandatory
    DESCRIPTION     
            "Count of SA failure due to proposal failures"
    ::= { sonusNrsIsakmpdIkeStatEntry 12 }

sonusNrsIsakmpdIkeInvalidIDinfoCnt OBJECT-TYPE
    SYNTAX          Counter
    ACCESS          read-only
    STATUS          mandatory
    DESCRIPTION     
            "Count of SA failure due to invalid ID information"
    ::= { sonusNrsIsakmpdIkeStatEntry 13 }

sonusNrsIsakmpdIkeInvalidHashCnt OBJECT-TYPE
    SYNTAX          Counter
    ACCESS          read-only
    STATUS          mandatory
    DESCRIPTION     
            "Count of SA failure due to invalid hash information"
    ::= { sonusNrsIsakmpdIkeStatEntry 14 }

sonusNrsIsakmpdIkeV2AuthFailedCnt OBJECT-TYPE
    SYNTAX          Counter
    ACCESS          read-only
    STATUS          mandatory
    DESCRIPTION     
            "Count of SA failed during AUTH for IKEv2"
    ::= { sonusNrsIsakmpdIkeStatEntry 15 }

sonusNrsIsakmpdIkeTSFailedCnt OBJECT-TYPE
    SYNTAX          Counter
    ACCESS          read-only
    STATUS          mandatory
    DESCRIPTION     
            "Count of SA failed due to Traffic Selector"
    ::= { sonusNrsIsakmpdIkeStatEntry 16 }

sonusNrsIsakmpdIkePeerIpAddress OBJECT-TYPE
    SYNTAX          IpAddress
    ACCESS          read-only
    STATUS          mandatory
    DESCRIPTION     
            "The ISAKMPD Peer IP address."
    ::= { sonusNrsIsakmpdIkeStatEntry 17 }

sonusNrsIsakmpdIkePeerIp6Address OBJECT-TYPE
    SYNTAX          Ipv6Address
    ACCESS          read-write
    STATUS          mandatory
    DESCRIPTION     
            "The Peer IKE IP6 address."
    ::= { sonusNrsIsakmpdIkeStatEntry 18 }

sonusNrsIsakmpdIkePeerIpVersion OBJECT-TYPE
    SYNTAX          INTEGER { afInet(2), afInet6(24) }
    ACCESS          read-only
    STATUS          mandatory
    DESCRIPTION     
            "The SPD traffic selector local IP address type."
    ::= { sonusNrsIsakmpdIkeStatEntry 19 }

sonusNrsIsakmpdIkeDPDFailedCnt OBJECT-TYPE
    SYNTAX          Counter
    ACCESS          read-only
    STATUS          mandatory
    DESCRIPTION     
            "Count of SA failed due to DPD Failure"
    ::= { sonusNrsIsakmpdIkeStatEntry 20 }

sonusIpTrap OBJECT IDENTIFIER
    ::= { sonusMib-2 10 }

sonusIpsecMIBNotifications OBJECT IDENTIFIER
    ::= { sonusIpTrap 1 }

sonusIpsecMIBNotificationsPrefix OBJECT IDENTIFIER
    ::= { sonusIpsecMIBNotifications 0 }

sonusIpsecMIBNotificationsObjects OBJECT IDENTIFIER
    ::= { sonusIpsecMIBNotifications 1 }

sonusIpsecIkeFailureNotification TRAP-TYPE
    ENTERPRISE      sonusIpsecMIBNotifications
    VARIABLES       { sonusEventDescription, sonusEventClass, 
                      sonusEventLevel, sonusSequenceId, sonusEventTime }
--     STATUS          mandatory
    DESCRIPTION     
            "This trap indicates that IKE/IPSEC failure"
    ::= 1

END -- end of module SONUS-IP-PROTOCOL-MIB.
