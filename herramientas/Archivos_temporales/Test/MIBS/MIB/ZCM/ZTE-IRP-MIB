ZTE-IRP-MIB DEFINITIONS ::= BEGIN

IMPORTS
        MODULE-IDENTITY, OBJECT-TYPE, NOTIFICATION-TYPE,
        enterprises
                FROM SNMPv2-SMI
        TEXTUAL-CONVENTION, DisplayString, DateAndTime
                FROM SNMPv2-TC
        OBJECT-GROUP, NOTIFICATION-GROUP, MODULE-COMPLIANCE
                FROM SNMPv2-CONF;


zteMIB MODULE-IDENTITY
        LAST-UPDATED "200512310000Z"
        ORGANIZATION "ZTE Corp. Ltd ."
        CONTACT-INFO
                "E-mail: wu.chunhui@mail.zte.com.cn"
        DESCRIPTION
                "This SNMP MIB-module specifies the SNMP Solution Set
                 of 3GPP Alarm Integration Reference Point (IRP),
                 this MIB-module complies with the SNMPV2C"
        REVISION "200512310000Z"
        DESCRIPTION "Alarm IRP V2.0"
        ::= { prises 3902 }

alarm				  OBJECT IDENTIFIER ::= { zteMIB 4101 }

END
