--
-- This SMIv2 module has been generated by smidump 0.2-cvs. Do not edit.
--

FOUNDRY-SN-IGMP-MIB DEFINITIONS ::= BEGIN

IMPORTS
    snIgmp
        FROM FOUNDRY-SN-ROOT-MIB
    Integer32, IpAddress, OBJECT-TYPE
        FROM SNMPv2-SMI;

snIgmpMIBObjects OBJECT IDENTIFIER
    ::= { snIgmp 1 }

snIgmpQueryInterval OBJECT-TYPE
    SYNTAX          Integer32 (1..3600)
    MAX-ACCESS      read-write
    STATUS          current
    DESCRIPTION     
            "This is the time interval at which this entity sends out
             IGMP host query packets. For a router, snDvmrpEnable must
             have been set to 'enabled' before this object is writen.
             For a switch, snSwGroupIpMcastMode must have been set to
             'enabled' and snSwIpMcastQuerierMode must have been set
             to 'querier' before this object is writen."
    DEFVAL          { 60 }
    ::= { snIgmpMIBObjects 1 }

snIgmpGroupMembershipTime OBJECT-TYPE
    SYNTAX          Integer32 (1..7200)
    MAX-ACCESS      read-write
    STATUS          current
    DESCRIPTION     
            "This is the time interval after which a group is considered
             inactive. For a router, snDvmrpEnable must have been set to
             'enabled' before this object is writen. For a switch,
             snSwGroupIpMcastMode must have been set to 'enabled' before
             this object is writen."
    DEFVAL          { 140 }
    ::= { snIgmpMIBObjects 2 }

snIgmpIfTable OBJECT-TYPE
    SYNTAX          SEQUENCE OF SnIgmpIfEntry
    MAX-ACCESS      not-accessible
    STATUS          current
    DESCRIPTION     
            "This table comprises of a list of IGMP interface entries."
    ::= { snIgmpMIBObjects 3 }

snIgmpIfEntry OBJECT-TYPE
    SYNTAX          SnIgmpIfEntry
    MAX-ACCESS      not-accessible
    STATUS          current
    DESCRIPTION     
            "An entry (conceptual row) contains the group
             membership information for that port."
    INDEX           { snIgmpIfEntryIndex }
    ::= { snIgmpIfTable 1 }

SnIgmpIfEntry ::=
    SEQUENCE {
        snIgmpIfEntryIndex              Integer32,
        snIgmpIfPortNumber              Integer32,
        snIgmpIfGroupAddress            IpAddress,
        snIgmpIfGroupAge                Integer32
    }

snIgmpIfEntryIndex OBJECT-TYPE
    SYNTAX          Integer32
    MAX-ACCESS      read-only
    STATUS          current
    DESCRIPTION     
            "The table entry index."
    ::= { snIgmpIfEntry 1 }

snIgmpIfPortNumber OBJECT-TYPE
    SYNTAX          Integer32
    MAX-ACCESS      read-only
    STATUS          current
    DESCRIPTION     
            "This is the interface on which the group was learnt."
    ::= { snIgmpIfEntry 2 }

snIgmpIfGroupAddress OBJECT-TYPE
    SYNTAX          IpAddress
    MAX-ACCESS      read-only
    STATUS          current
    DESCRIPTION     
            "The group address learnt from the interface."
    ::= { snIgmpIfEntry 3 }

snIgmpIfGroupAge OBJECT-TYPE
    SYNTAX          Integer32
    MAX-ACCESS      read-only
    STATUS          current
    DESCRIPTION     
            "This is the interval (seconds) after which the group
             information will be aged out."
    ::= { snIgmpIfEntry 4 }

END -- end of module FOUNDRY-SN-IGMP-MIB.
