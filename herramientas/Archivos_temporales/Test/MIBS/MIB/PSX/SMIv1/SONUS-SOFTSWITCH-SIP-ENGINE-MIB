--
-- This SMIv1 module has been generated by smidump 0.2-cvs. Do not edit.
--

SONUS-SOFTSWITCH-SIP-ENGINE-MIB DEFINITIONS ::= BEGIN

IMPORTS
    InetAddress, InetAddressType
        FROM INET-ADDRESS-MIB
    OBJECT-TYPE
        FROM RFC-1212
    TRAP-TYPE
        FROM RFC-1215
    Counter, Gauge, IpAddress, TimeTicks
        FROM RFC1155-SMI
    sonusEventClass, sonusEventDescription, sonusEventLevel, 
    sonusEventTime
        FROM SONUS-COMMON-MIB
    sonusServicesMIBs
        FROM SONUS-SMI;

sonusSoftSwitchSIPEngineMIB OBJECT IDENTIFIER
    ::= { sonusServicesMIBs 14 }

-- sonusSoftSwitchSIPEngineMIB MODULE-IDENTITY
--     LAST-UPDATED    "200205030000Z"
--     ORGANIZATION    
--             "Sonus Networks, Inc."
--     CONTACT-INFO    
--             "   Customer Support    
--              Sonus Networks, Inc.
--              250 Apollo Drive
--              Chelmsford, MA 01824
--              USA
--              
--              Tel: 978-614-8100
--              Fax: 978-614-8609"
--     DESCRIPTION     
--             "The MIB Module for SoftSwitch SIP Engine Management."
--     ::= { sonusServicesMIBs 14 }


sonusSoftSwitchSIPEngineMIBObjects OBJECT IDENTIFIER
    ::= { sonusSoftSwitchSIPEngineMIB 1 }

sonusSoftSwitchSIPEngineStatistics OBJECT IDENTIFIER
    ::= { sonusSoftSwitchSIPEngineMIBObjects 1 }

sonusSoftSwitchSipeReqRcvdCounters OBJECT IDENTIFIER
    ::= { sonusSoftSwitchSIPEngineStatistics 1 }

sonusSoftSwitchSipeReqRcvdINVITE OBJECT-TYPE
    SYNTAX          Counter
    ACCESS          read-only
    STATUS          mandatory
    DESCRIPTION     
            "This counter keeps track of the number of INVITE requests 
             which have been received by SIPE process.  Retransmissions 
             of messages (while the original one is being processed) are 
             not counted."
    ::= { sonusSoftSwitchSipeReqRcvdCounters 1 }

sonusSoftSwitchSipeReqRcvdBYE OBJECT-TYPE
    SYNTAX          Counter
    ACCESS          read-only
    STATUS          mandatory
    DESCRIPTION     
            "This counter keeps track of the number of BYE  requests 
             which have been received by SIPE process.  Retransmissions of 
             messages (while the original one is being processed) are not 
             counted."
    ::= { sonusSoftSwitchSipeReqRcvdCounters 2 }

sonusSoftSwitchSipeReqRcvdCANCEL OBJECT-TYPE
    SYNTAX          Counter
    ACCESS          read-only
    STATUS          mandatory
    DESCRIPTION     
            "This counter keeps track of the number of CANCEL requests 
             which have been received by SIPE process.  Retransmissions 
             of messages (while the original one is being processed) are 
             not counted."
    ::= { sonusSoftSwitchSipeReqRcvdCounters 3 }

sonusSoftSwitchSipeReqRcvdOPTIONS OBJECT-TYPE
    SYNTAX          Counter
    ACCESS          read-only
    STATUS          mandatory
    DESCRIPTION     
            "This counter keeps track of the number of OPTIONS requests 
             which have been received by SIPE process.  Retransmissions of 
             messages (while the original one is being processed) are not 
             counted."
    ::= { sonusSoftSwitchSipeReqRcvdCounters 4 }

sonusSoftSwitchSipeReqRcvdOTHER OBJECT-TYPE
    SYNTAX          Counter
    ACCESS          read-only
    STATUS          mandatory
    DESCRIPTION     
            "This counter keeps track of the number of miscellaneous 
             requests which have been received (and are not counted in 
             specific counters) by SIPE process.  Retransmissions of 
             messages (while the original one is being processed) are not 
             counted."
    ::= { sonusSoftSwitchSipeReqRcvdCounters 5 }

sonusSoftSwitchSipeReqRcvdREGISTER OBJECT-TYPE
    SYNTAX          Counter
    ACCESS          read-only
    STATUS          mandatory
    DESCRIPTION     
            "This counter keeps track of the number of REGISTER requests 
             which have been received by SIPE process.  Retransmissions of
             messages (while the original one is being processed) are not counted."
    ::= { sonusSoftSwitchSipeReqRcvdCounters 6 }

sonusSoftSwitchSipeReqRcvdSUBSCRIBE OBJECT-TYPE
    SYNTAX          Counter
    ACCESS          read-only
    STATUS          mandatory
    DESCRIPTION     
            "This counter keeps track of the number of  SUBSCRIBE requests 
             which have been received by SIPE process.  Retransmissions of 
             messages (while the original one is being processed) are not counted."
    ::= { sonusSoftSwitchSipeReqRcvdCounters 7 }

sonusSoftSwitchSipeReqRcvdNOTIFY OBJECT-TYPE
    SYNTAX          Counter
    ACCESS          read-only
    STATUS          mandatory
    DESCRIPTION     
            "This counter keeps track of the number of NOTIFY requests which 
             have been received by SIPE process.  Retransmissions of messages 
             (while the original one is being processed) are not counted."
    ::= { sonusSoftSwitchSipeReqRcvdCounters 8 }

sonusSoftSwitchSipeReqRcvdINFO OBJECT-TYPE
    SYNTAX          Counter
    ACCESS          read-only
    STATUS          obsolete
    DESCRIPTION     
            "This counter keeps track of the number of INFO requests which 
             have been received by SIPE process.  Retransmissions of messages 
             (while the original one is being processed) are not counted."
    ::= { sonusSoftSwitchSipeReqRcvdCounters 9 }

sonusSoftSwitchSipeReqRcvdIntervalTime OBJECT-TYPE
    SYNTAX          TimeTicks
    ACCESS          read-only
    STATUS          mandatory
    DESCRIPTION     
            "This variable contains the end of interval time stamp for 
             the specified interval."
    ::= { sonusSoftSwitchSipeReqRcvdCounters 10 }

sonusSoftSwitchSipeReqRcvdNOTIFYMWIOn OBJECT-TYPE
    SYNTAX          Counter
    ACCESS          read-only
    STATUS          mandatory
    DESCRIPTION     
            "This counter keeps track of the number of NOTIFY requests with 
             MWI ON status, which have been received by SIPE process.  
             Retransmissions of messages (while the original one is being processed) 
             are not counted."
    ::= { sonusSoftSwitchSipeReqRcvdCounters 11 }

sonusSoftSwitchSipeReqRcvdNOTIFYMWIOff OBJECT-TYPE
    SYNTAX          Counter
    ACCESS          read-only
    STATUS          mandatory
    DESCRIPTION     
            "This counter keeps track of the number of NOTIFY requests with 
             MWI OFF status, which have been received by SIPE process.  
             Retransmissions of messages (while the original one is being processed)
             are not counted."
    ::= { sonusSoftSwitchSipeReqRcvdCounters 12 }

sonusSoftSwitchSipeReqRcvdNOTIFYRegn OBJECT-TYPE
    SYNTAX          Counter
    ACCESS          read-only
    STATUS          mandatory
    DESCRIPTION     
            "This counter keeps track of the number of NOTIFY requests with 
             Registration event, which have been received by SIPE process.  
             Retransmissions of messages (while the original one is being processed) 
             are not counted."
    ::= { sonusSoftSwitchSipeReqRcvdCounters 13 }

sonusSoftSwitchSipeReqRcvdINVITEwithEtsRph OBJECT-TYPE
    SYNTAX          Counter
    ACCESS          read-only
    STATUS          mandatory
    DESCRIPTION     
            "This counter keeps track of the number of INVITE requests with
             ETS RPH, which have been received by SIPE process. 
             Retransmissions of messages (while the original one is being processed) 
             are not counted."
    ::= { sonusSoftSwitchSipeReqRcvdCounters 14 }

sonusSoftSwitchSipeReqRcvdINVITEwithEtsDn OBJECT-TYPE
    SYNTAX          Counter
    ACCESS          read-only
    STATUS          mandatory
    DESCRIPTION     
            "This counter keeps track of the number of INVITE requests with
             ETS DN but no ETS RPH, which have been received by SIPE process. 
             Retransmissions of messages (while the original one is being processed) 
             are not counted."
    ::= { sonusSoftSwitchSipeReqRcvdCounters 15 }

sonusSoftSwitchSipeReqRcvd400RespWith417Reason OBJECT-TYPE
    SYNTAX          Counter
    ACCESS          read-only
    STATUS          mandatory
    DESCRIPTION     
            "This counter keeps track of the number of 400 Response messages 
             with 417 Reason Code,  which have been received by SIPE process."
    ::= { sonusSoftSwitchSipeReqRcvdCounters 16 }

sonusSoftSwitchSipeReqWithEtsRphDiscardedOverload OBJECT-TYPE
    SYNTAX          Counter
    ACCESS          read-only
    STATUS          mandatory
    DESCRIPTION     
            "This counter keeps track of the number of Requests with 
             ETS RPH discarded due to overload."
    ::= { sonusSoftSwitchSipeReqRcvdCounters 17 }

sonusSoftSwitchSipeReqWithoutEtsRphDiscardedOverload OBJECT-TYPE
    SYNTAX          Counter
    ACCESS          read-only
    STATUS          mandatory
    DESCRIPTION     
            "This counter keeps track of the number of Requests without
             ETS RPH discarded due to overload."
    ::= { sonusSoftSwitchSipeReqRcvdCounters 18 }

sonusSoftSwitchSipeReqRcvdCNAMESUBSCRIBE OBJECT-TYPE
    SYNTAX          Counter
    ACCESS          read-only
    STATUS          mandatory
    DESCRIPTION     
            "This counter keeps track of the number of SUBSCRIBE Requests 
             for CNAME query. Event type - calling-name. Retransmissions 
             are not counted."
    ::= { sonusSoftSwitchSipeReqRcvdCounters 19 }

sonusSoftSwitchSipeReqRcvdMESSAGE OBJECT-TYPE
    SYNTAX          Counter
    ACCESS          read-only
    STATUS          mandatory
    DESCRIPTION     
            "This counter keeps track of the number of  MESSAGE requests 
             which have been received by SIPE process.  Retransmissions of 
             messages (while the original one is being processed) are not counted."
    ::= { sonusSoftSwitchSipeReqRcvdCounters 20 }

sonusSoftSwitchSipeRspSentCounters OBJECT IDENTIFIER
    ::= { sonusSoftSwitchSIPEngineStatistics 2 }

sonusSoftSwitchSipeRspSent2XX OBJECT-TYPE
    SYNTAX          Counter
    ACCESS          read-only
    STATUS          mandatory
    DESCRIPTION     
            "This counter keeps track of the number of 2XX responses which  
             have been sent by SIPE process in INVITE and non INVITE transactions.
             Retransmissions of messages are not counted."
    ::= { sonusSoftSwitchSipeRspSentCounters 1 }

sonusSoftSwitchSipeRspSent3XX OBJECT-TYPE
    SYNTAX          Counter
    ACCESS          read-only
    STATUS          mandatory
    DESCRIPTION     
            "This counter keeps track of the number of 3XX responses which 
             have been sent by SIPE process in INVITE transactions. Retransmissions
              of messages are not counted."
    ::= { sonusSoftSwitchSipeRspSentCounters 2 }

sonusSoftSwitchSipeRspSent4XX OBJECT-TYPE
    SYNTAX          Counter
    ACCESS          read-only
    STATUS          mandatory
    DESCRIPTION     
            "This counter keeps track of the number of 4XX responses which 
             have been sent by SIPE process in INVITE transactions. Retransmissions
             of messages are not counted."
    ::= { sonusSoftSwitchSipeRspSentCounters 3 }

sonusSoftSwitchSipeRspSent5XX OBJECT-TYPE
    SYNTAX          Counter
    ACCESS          read-only
    STATUS          mandatory
    DESCRIPTION     
            "This counter keeps track of the number of 5XX responses which
             have been sent by SIPE process in INVITE transactions. Retransmissions
             of messages are not counted."
    ::= { sonusSoftSwitchSipeRspSentCounters 4 }

sonusSoftSwitchSipeRspSent6XX OBJECT-TYPE
    SYNTAX          Counter
    ACCESS          read-only
    STATUS          mandatory
    DESCRIPTION     
            "This counter keeps track of the number of 6XX responses which
             have been sent by SIPE process in INVITE transactions. Retransmissions
             of messages are not counted."
    ::= { sonusSoftSwitchSipeRspSentCounters 5 }

sonusSoftSwitchSipeRspSentIntervalTime OBJECT-TYPE
    SYNTAX          TimeTicks
    ACCESS          read-only
    STATUS          obsolete
    DESCRIPTION     
            "This variable contains the end of interval time stamp for 
             the specified interval."
    ::= { sonusSoftSwitchSipeRspSentCounters 6 }

sonusSoftSwitchSipeRspSentNonInvite OBJECT-TYPE
    SYNTAX          Counter
    ACCESS          read-only
    STATUS          mandatory
    DESCRIPTION     
            "This counter keeps track of the number of 3xx, 4xx, 5xx and 6xx 
             responses which have been sent by SIPE process in non INVITE transactions.
              Retransmissions of messages are not counted."
    ::= { sonusSoftSwitchSipeRspSentCounters 7 }

sonusSoftSwitchSipeRspSentInviteWithEtsRph OBJECT-TYPE
    SYNTAX          Counter
    ACCESS          read-only
    STATUS          mandatory
    DESCRIPTION     
            "This counter keeps track of the number of INVITE requests sent with ETS RPH
             which have been sent by SIPE process.
             Retransmissions of messages are not counted."
    ::= { sonusSoftSwitchSipeRspSentCounters 8 }

sonusSoftSwitchSipeProxyCounters OBJECT IDENTIFIER
    ::= { sonusSoftSwitchSIPEngineStatistics 3 }

sonusSoftSwitchSipeProxyReqSentCounters OBJECT IDENTIFIER
    ::= { sonusSoftSwitchSipeProxyCounters 1 }

sonusSoftSwitchSipeProxyReqSentINVITE OBJECT-TYPE
    SYNTAX          Counter
    ACCESS          read-only
    STATUS          mandatory
    DESCRIPTION     
            "This counter keeps track of the number of INVITE requests which 
             have been sent by SIPE process in proxy mode.  Retransmissions 
             of messages are not counted."
    ::= { sonusSoftSwitchSipeProxyReqSentCounters 1 }

sonusSoftSwitchSipeProxyReqSentBYE OBJECT-TYPE
    SYNTAX          Counter
    ACCESS          read-only
    STATUS          mandatory
    DESCRIPTION     
            "This counter keeps track of the number of BYE requests which have 
             been sent by SIPE process in proxy mode.  Retransmissions of messages 
             are not counted."
    ::= { sonusSoftSwitchSipeProxyReqSentCounters 2 }

sonusSoftSwitchSipeProxyReqSentCANCEL OBJECT-TYPE
    SYNTAX          Counter
    ACCESS          read-only
    STATUS          mandatory
    DESCRIPTION     
            "This counter keeps track of the number of CANCEL requests 
             which have been sent by SIPE process in proxy mode.  
             Retransmissions of messages are not counted."
    ::= { sonusSoftSwitchSipeProxyReqSentCounters 3 }

sonusSoftSwitchSipeProxyReqSentOPTIONS OBJECT-TYPE
    SYNTAX          Counter
    ACCESS          read-only
    STATUS          mandatory
    DESCRIPTION     
            "This counter keeps track of the number of OPTIONS requests 
             which have been sent by SIPE process in proxy mode.  
             Retransmissions of messages are not counted."
    ::= { sonusSoftSwitchSipeProxyReqSentCounters 4 }

sonusSoftSwitchSipeProxyReqSentOTHER OBJECT-TYPE
    SYNTAX          Counter
    ACCESS          read-only
    STATUS          mandatory
    DESCRIPTION     
            "This counter keeps track of the number of miscellaneous requests 
             which have been sent by SIPE process in proxy mode (and are not 
             counted in specific counters). Retransmissions of messages 
             (while the original one is being processed) are not counted."
    ::= { sonusSoftSwitchSipeProxyReqSentCounters 5 }

sonusSoftSwitchSipeProxyReqSentREGISTER OBJECT-TYPE
    SYNTAX          Counter
    ACCESS          read-only
    STATUS          mandatory
    DESCRIPTION     
            "This counter keeps track of the number of REGISTER requests 
             which have been sent by SIPE process in proxy mode.  
             Retransmissions of messages are not counted."
    ::= { sonusSoftSwitchSipeProxyReqSentCounters 6 }

sonusSoftSwitchSipeProxyReqSentSUBSCRIBE OBJECT-TYPE
    SYNTAX          Counter
    ACCESS          read-only
    STATUS          mandatory
    DESCRIPTION     
            "This counter keeps track of the number of SUBSCRIBE requests 
             which have been sent by SIPE process in proxy mode.  
             Retransmissions of messages are not counted."
    ::= { sonusSoftSwitchSipeProxyReqSentCounters 7 }

sonusSoftSwitchSipeProxyReqSentNOTIFY OBJECT-TYPE
    SYNTAX          Counter
    ACCESS          read-only
    STATUS          mandatory
    DESCRIPTION     
            "This counter keeps track of the number of NOTIFY requests 
             which have been sent by SIPE process in proxy mode.  
             Retransmissions of messages are not counted."
    ::= { sonusSoftSwitchSipeProxyReqSentCounters 8 }

sonusSoftSwitchSipeProxyReqSentINFO OBJECT-TYPE
    SYNTAX          Counter
    ACCESS          read-only
    STATUS          obsolete
    DESCRIPTION     
            "This counter keeps track of the number of INFO requests 
             which have been sent by SIPE process in proxy mode.  
             Retransmissions of messages are not counted."
    ::= { sonusSoftSwitchSipeProxyReqSentCounters 9 }

sonusSoftSwitchSipeProxyReqSentIntervalTime OBJECT-TYPE
    SYNTAX          TimeTicks
    ACCESS          read-only
    STATUS          obsolete
    DESCRIPTION     
            "This variable contains the end of interval time stamp for 
             the specified interval."
    ::= { sonusSoftSwitchSipeProxyReqSentCounters 10 }

sonusSoftSwitchSipeProxyReqReSentINVITE OBJECT-TYPE
    SYNTAX          Counter
    ACCESS          read-only
    STATUS          mandatory
    DESCRIPTION     
            "This counter keeps track of the number of INVITE requests which 
             have been re-sent by SIPE process in proxy mode."
    ::= { sonusSoftSwitchSipeProxyReqSentCounters 11 }

sonusSoftSwitchSipeProxyReqSentMESSAGE OBJECT-TYPE
    SYNTAX          Counter
    ACCESS          read-only
    STATUS          mandatory
    DESCRIPTION     
            "This counter keeps track of the number of MESSAGE requests 
             which have been sent by SIPE process in proxy mode.  
             Retransmissions of messages are not counted."
    ::= { sonusSoftSwitchSipeProxyReqSentCounters 12 }

sonusSoftSwitchSipeProxyRspRcvdCounters OBJECT IDENTIFIER
    ::= { sonusSoftSwitchSipeProxyCounters 2 }

sonusSoftSwitchSipeProxyRspRcvd2XX OBJECT-TYPE
    SYNTAX          Counter
    ACCESS          read-only
    STATUS          mandatory
    DESCRIPTION     
            "This counter keeps track of the number of 2XX responses 
             which have been received by SIPE process in proxy mode for both INVITE  
             and non-INVITE transactions. Retransmissions of messages are not counted."
    ::= { sonusSoftSwitchSipeProxyRspRcvdCounters 1 }

sonusSoftSwitchSipeProxyRspRcvd3XX OBJECT-TYPE
    SYNTAX          Counter
    ACCESS          read-only
    STATUS          mandatory
    DESCRIPTION     
            "This counter keeps track of the number of 3XX responses 
             which have been received by SIPE process in proxy mode for INVITE  
             transactions. Retransmissions of messages are not counted."
    ::= { sonusSoftSwitchSipeProxyRspRcvdCounters 2 }

sonusSoftSwitchSipeProxyRspRcvd4XX OBJECT-TYPE
    SYNTAX          Counter
    ACCESS          read-only
    STATUS          mandatory
    DESCRIPTION     
            "This counter keeps track of the number of 4XX responses 
             which have been received by SIPE process in proxy mode for INVITE  
             transactions. Retransmissions of messages are not counted."
    ::= { sonusSoftSwitchSipeProxyRspRcvdCounters 3 }

sonusSoftSwitchSipeProxyRspRcvd5XX OBJECT-TYPE
    SYNTAX          Counter
    ACCESS          read-only
    STATUS          mandatory
    DESCRIPTION     
            "This counter keeps track of the number of 5XX responses 
             which have been received  by SIPE process in proxy mode for INVITE  
             transactions. Retransmissions of messages are not counted."
    ::= { sonusSoftSwitchSipeProxyRspRcvdCounters 4 }

sonusSoftSwitchSipeProxyRspRcvd6XX OBJECT-TYPE
    SYNTAX          Counter
    ACCESS          read-only
    STATUS          mandatory
    DESCRIPTION     
            "This counter keeps track of the number of 6XX responses 
             which have been received  by SIPE process in proxy mode for INVITE  
             transactions. Retransmissions of messages are not counted."
    ::= { sonusSoftSwitchSipeProxyRspRcvdCounters 5 }

sonusSoftSwitchSipeProxyRspRcvdIntervalTime OBJECT-TYPE
    SYNTAX          TimeTicks
    ACCESS          read-only
    STATUS          obsolete
    DESCRIPTION     
            "This variable contains the end of interval time stamp for 
             the specified interval."
    ::= { sonusSoftSwitchSipeProxyRspRcvdCounters 6 }

sonusSoftSwitchSipeProxyRspRcvdNonINV OBJECT-TYPE
    SYNTAX          Counter
    ACCESS          read-only
    STATUS          mandatory
    DESCRIPTION     
            "This counter keeps track of the number of 3xx, 4xx, 5xx and 6xx responses 
             which have been received  by SIPE process in proxy mode for non INVITE  
             transactions. Retransmissions of messages are not counted."
    ::= { sonusSoftSwitchSipeProxyRspRcvdCounters 7 }

sonusSoftSwitchSipeProxyLocalRecurCounter OBJECT-TYPE
    SYNTAX          Counter
    ACCESS          read-only
    STATUS          mandatory
    DESCRIPTION     
            "This counter keeps track of the number of times the local 
             recursion service of SIPE proxy has caused a final response 
             to be handled locally and another request has been sent toward 
             the next route in the route list."
    ::= { sonusSoftSwitchSipeProxyCounters 3 }

sonusSoftSwitchSipeProxyTimerC OBJECT-TYPE
    SYNTAX          Counter
    ACCESS          read-only
    STATUS          mandatory
    DESCRIPTION     
            "This counter keeps track of the number of times the SIPE proxy 
             Timer C has expired, the request has been cancelled and a final 
             response has been sent back to the UAC."
    ::= { sonusSoftSwitchSipeProxyCounters 4 }

sonusSoftSwitchSipeProxyIntervalTime OBJECT-TYPE
    SYNTAX          TimeTicks
    ACCESS          read-only
    STATUS          mandatory
    DESCRIPTION     
            "This variable contains the end of interval time stamp for
             the specified interval."
    ::= { sonusSoftSwitchSipeProxyCounters 5 }

sonusSoftSwitchSipeProxyPeerOverloadThrottlingCounters OBJECT IDENTIFIER
    ::= { sonusSoftSwitchSipeProxyCounters 6 }

sonusSoftSwitchSipeProxyPeerOverloadThrottlingTable OBJECT-TYPE
    SYNTAX          SEQUENCE OF SonusSoftSwitchSipeProxyPeerOverloadThrottlingEntry
    ACCESS          not-accessible
    STATUS          mandatory
    DESCRIPTION     
            "SIP Peer Overload Throtting related Counters"
    ::= { sonusSoftSwitchSipeProxyPeerOverloadThrottlingCounters 1 }

sonusSoftSwitchSipeProxyPeerOverloadThrottlingEntry OBJECT-TYPE
    SYNTAX          SonusSoftSwitchSipeProxyPeerOverloadThrottlingEntry
    ACCESS          not-accessible
    STATUS          mandatory
    DESCRIPTION     
            "An entry of SIP Peer Throtting related counters corresponding to a Peer"
    INDEX           { 
                      sonusSoftSwitchSipeProxyPeerOverloadThrottlingIpAddressType, 
                      sonusSoftSwitchSipeProxyPeerOverloadThrottlingIpAddress, 
                      sonusSoftSwitchSipeProxyPeerOverloadThrottlingPort, 
                      sonusSoftSwitchSipeProxyPeerOverloadThrottlingTansportType }
    ::= { sonusSoftSwitchSipeProxyPeerOverloadThrottlingTable 1 }

SonusSoftSwitchSipeProxyPeerOverloadThrottlingEntry ::=
    SEQUENCE {
        sonusSoftSwitchSipeProxyPeerOverloadThrottlingIpAddressType                           InetAddressType,
        sonusSoftSwitchSipeProxyPeerOverloadThrottlingIpAddress                       InetAddress,
        sonusSoftSwitchSipeProxyPeerOverloadThrottlingPort                  INTEGER,
        sonusSoftSwitchSipeProxyPeerOverloadThrottlingTansportType                          INTEGER,
        sonusSoftSwitchSipeProxyPeerOverloadThrottlingReqRcvd                     Counter,
        sonusSoftSwitchSipeProxyPeerOverloadThrottlingReqSent                     Counter,
        sonusSoftSwitchSipeProxyPeerOverloadThrottlingReqRej                    Counter,
        sonusSoftSwitchSipeProxyPeerOverloadThrottlingRejRcvd                     Counter
    }

sonusSoftSwitchSipeProxyPeerOverloadThrottlingIpAddressType OBJECT-TYPE
    SYNTAX          InetAddressType
    ACCESS          read-only
    STATUS          mandatory
    DESCRIPTION     
            "SIP PEER Host's IP address Type."
    ::= { sonusSoftSwitchSipeProxyPeerOverloadThrottlingEntry 1 }

sonusSoftSwitchSipeProxyPeerOverloadThrottlingIpAddress OBJECT-TYPE
    SYNTAX          InetAddress
    ACCESS          read-only
    STATUS          mandatory
    DESCRIPTION     
            "The IP address of the Peer for which throttling is performed"
    ::= { sonusSoftSwitchSipeProxyPeerOverloadThrottlingEntry 2 }

sonusSoftSwitchSipeProxyPeerOverloadThrottlingPort OBJECT-TYPE
    SYNTAX          INTEGER
    ACCESS          read-only
    STATUS          mandatory
    DESCRIPTION     
            "The Port on which Peer is listening when throttling is performed"
    ::= { sonusSoftSwitchSipeProxyPeerOverloadThrottlingEntry 3 }

sonusSoftSwitchSipeProxyPeerOverloadThrottlingTansportType OBJECT-TYPE
    SYNTAX          INTEGER
    ACCESS          read-only
    STATUS          mandatory
    DESCRIPTION     
            "The transport used towards the Peer for which throttling is performed.1-tcp,2-udp and 3-sctp"
    ::= { sonusSoftSwitchSipeProxyPeerOverloadThrottlingEntry 4 }

sonusSoftSwitchSipeProxyPeerOverloadThrottlingReqRcvd OBJECT-TYPE
    SYNTAX          Counter
    ACCESS          read-only
    STATUS          mandatory
    DESCRIPTION     
            "This counter keeps track of no. of requests received for the Peer 
             being throttled "
    ::= { sonusSoftSwitchSipeProxyPeerOverloadThrottlingEntry 5 }

sonusSoftSwitchSipeProxyPeerOverloadThrottlingReqSent OBJECT-TYPE
    SYNTAX          Counter
    ACCESS          read-only
    STATUS          mandatory
    DESCRIPTION     
            "This counter keeps track of no. of requests sent to the Peer
             that is being throttled "
    ::= { sonusSoftSwitchSipeProxyPeerOverloadThrottlingEntry 6 }

sonusSoftSwitchSipeProxyPeerOverloadThrottlingReqRej OBJECT-TYPE
    SYNTAX          Counter
    ACCESS          read-only
    STATUS          mandatory
    DESCRIPTION     
            "This counter keeps track of no. of requests rejected for the Peer 
             that is being throttled"
    ::= { sonusSoftSwitchSipeProxyPeerOverloadThrottlingEntry 7 }

sonusSoftSwitchSipeProxyPeerOverloadThrottlingRejRcvd OBJECT-TYPE
    SYNTAX          Counter
    ACCESS          read-only
    STATUS          mandatory
    DESCRIPTION     
            "This counter keeps track of no. of rejects received from Peer  
             that is being throttled"
    ::= { sonusSoftSwitchSipeProxyPeerOverloadThrottlingEntry 8 }

sonusSoftSwitchSipeProxyMiscCounters OBJECT IDENTIFIER
    ::= { sonusSoftSwitchSipeProxyCounters 7 }

sonusSoftSwitchSipeProxyMiscLocalRecurCounter OBJECT-TYPE
    SYNTAX          Counter
    ACCESS          read-only
    STATUS          mandatory
    DESCRIPTION     
            "This counter keeps track of the number of times the local 
             recursion service of SIPE proxy has caused a final response 
             to be handled locally and another request has been sent toward 
             the next route in the route list."
    ::= { sonusSoftSwitchSipeProxyMiscCounters 1 }

sonusSoftSwitchSipeProxyMiscTimerC OBJECT-TYPE
    SYNTAX          Counter
    ACCESS          read-only
    STATUS          mandatory
    DESCRIPTION     
            "This counter keeps track of the number of times the SIPE proxy 
             Timer C has expired, the request has been cancelled and a final 
             response has been sent back to the UAC."
    ::= { sonusSoftSwitchSipeProxyMiscCounters 2 }

sonusSoftSwitchSipeProxyMiscIntervalTime OBJECT-TYPE
    SYNTAX          TimeTicks
    ACCESS          read-only
    STATUS          mandatory
    DESCRIPTION     
            "This variable contains the end of interval time stamp for
             the specified interval."
    ::= { sonusSoftSwitchSipeProxyMiscCounters 3 }

sonusSoftSwitchSipeSummaryCounters OBJECT IDENTIFIER
    ::= { sonusSoftSwitchSIPEngineStatistics 4 }

sonusSoftSwitchSipeSumAvgTransTimer OBJECT-TYPE
    SYNTAX          Gauge
    ACCESS          read-only
    STATUS          mandatory
    DESCRIPTION     
            "This is the average time in milliseconds it took to process 
             a SIPE request.  For Redirector, this is from the time a request 
             is received to the time a 3XX is sent back.  
             For Proxy, this is from the time the request is received to 
             the time the request is forwarded."
    ::= { sonusSoftSwitchSipeSummaryCounters 1 }

sonusSoftSwitchSipeSumAvgCallRate OBJECT-TYPE
    SYNTAX          Gauge
    ACCESS          read-only
    STATUS          mandatory
    DESCRIPTION     
            "This is the average number of requests per second, 
             which the SIPE is receiving."
    ::= { sonusSoftSwitchSipeSummaryCounters 2 }

sonusSoftSwitchSipeSumTotalRedirectReq OBJECT-TYPE
    SYNTAX          Counter
    ACCESS          read-only
    STATUS          mandatory
    DESCRIPTION     
            "This counter keeps track of the number of requests, 
             which have been redirected."
    ::= { sonusSoftSwitchSipeSummaryCounters 3 }

sonusSoftSwitchSipeSumTotalProxyReq OBJECT-TYPE
    SYNTAX          Counter
    ACCESS          read-only
    STATUS          mandatory
    DESCRIPTION     
            "This counter keeps track of the number of requests, 
             which have been proxied."
    ::= { sonusSoftSwitchSipeSummaryCounters 4 }

sonusSoftSwitchSipeSumIntervalTime OBJECT-TYPE
    SYNTAX          TimeTicks
    ACCESS          read-only
    STATUS          obsolete
    DESCRIPTION     
            "This variable contains the end of interval time stamp for 
             the specified interval."
    ::= { sonusSoftSwitchSipeSummaryCounters 5 }

sonusSoftSwitchSipeSumParseError OBJECT-TYPE
    SYNTAX          Counter
    ACCESS          read-only
    STATUS          mandatory
    DESCRIPTION     
            "This counter keeps track of the number of parse errors."
    ::= { sonusSoftSwitchSipeSummaryCounters 6 }

sonusSoftSwitchSipeSumRetransOtherMsg OBJECT-TYPE
    SYNTAX          Counter
    ACCESS          read-only
    STATUS          mandatory
    DESCRIPTION     
            "This counter keeps track of the number of retransmitted messages
             other than INVITE."
    ::= { sonusSoftSwitchSipeSummaryCounters 7 }

sonusSoftSwitchSipeMiscCounters OBJECT IDENTIFIER
    ::= { sonusSoftSwitchSIPEngineStatistics 5 }

sonusSoftSwitchSipeMiscNumOfGCedCalls OBJECT-TYPE
    SYNTAX          Counter
    ACCESS          read-only
    STATUS          mandatory
    DESCRIPTION     
            "This counter keeps track of the number of transactions 
             which have remained in the system for too long and 
             have been removed by the Garbage Collector."
    ::= { sonusSoftSwitchSipeMiscCounters 1 }

sonusSoftSwitchSipeMiscIntervalTime OBJECT-TYPE
    SYNTAX          TimeTicks
    ACCESS          read-only
    STATUS          mandatory
    DESCRIPTION     
            "This variable contains the end of interval time stamp for 
             the specified interval."
    ::= { sonusSoftSwitchSipeMiscCounters 2 }

sonusSoftSwitchSipeMiscNumOfGuardTimerClearedCalls OBJECT-TYPE
    SYNTAX          Counter
    ACCESS          read-only
    STATUS          mandatory
    DESCRIPTION     
            "This counter keeps track of the number of transactions 
             which have been removed by Guard Timer Expiry."
    ::= { sonusSoftSwitchSipeMiscCounters 3 }

sonusSoftSwitchSipeDnsCounters OBJECT IDENTIFIER
    ::= { sonusSoftSwitchSIPEngineStatistics 6 }

sonusSoftSwitchSipeDnsKARequestsSent OBJECT-TYPE
    SYNTAX          Counter
    ACCESS          read-only
    STATUS          mandatory
    DESCRIPTION     
            "Total number of KeepAlive requests sent by SIPE."
    ::= { sonusSoftSwitchSipeDnsCounters 1 }

sonusSoftSwitchSipeDnsKAResponsesReceived OBJECT-TYPE
    SYNTAX          Counter
    ACCESS          read-only
    STATUS          mandatory
    DESCRIPTION     
            "Total number of KeepAlive responses received by SIPE."
    ::= { sonusSoftSwitchSipeDnsCounters 2 }

sonusSoftSwitchSipeDnsDNSCanceledRequests OBJECT-TYPE
    SYNTAX          Counter
    ACCESS          read-only
    STATUS          mandatory
    DESCRIPTION     
            "Total number of DNS requests canceled by SIPE."
    ::= { sonusSoftSwitchSipeDnsCounters 3 }

sonusSoftSwitchSipeDnsLongTermAverageTransactionTime OBJECT-TYPE
    SYNTAX          Gauge
    ACCESS          read-only
    STATUS          mandatory
    DESCRIPTION     
            "Long term average of transaction time."
    ::= { sonusSoftSwitchSipeDnsCounters 4 }

sonusSoftSwitchSipeDnsShortTermAverageTransactionTime OBJECT-TYPE
    SYNTAX          Gauge
    ACCESS          read-only
    STATUS          mandatory
    DESCRIPTION     
            "Short term average of transaction time."
    ::= { sonusSoftSwitchSipeDnsCounters 5 }

sonusSoftSwitchSipeDnsDNSAResourceRecordRequestsSent OBJECT-TYPE
    SYNTAX          Counter
    ACCESS          read-only
    STATUS          mandatory
    DESCRIPTION     
            "Number of DNS A Resource Record requests sent by SIPE."
    ::= { sonusSoftSwitchSipeDnsCounters 6 }

sonusSoftSwitchSipeDnsDNSAResourceRecordResponsesReceived OBJECT-TYPE
    SYNTAX          Counter
    ACCESS          read-only
    STATUS          mandatory
    DESCRIPTION     
            "Number of DNS A Resource Record responses received by SIPE."
    ::= { sonusSoftSwitchSipeDnsCounters 7 }

sonusSoftSwitchSipeDnsDNSAResourceRecordCanceledRequests OBJECT-TYPE
    SYNTAX          Counter
    ACCESS          read-only
    STATUS          mandatory
    DESCRIPTION     
            "Number of DNS A Resource Record requests canceled by SIPE."
    ::= { sonusSoftSwitchSipeDnsCounters 8 }

sonusSoftSwitchSipeDnsDNSAResourceRecordRspSuccess OBJECT-TYPE
    SYNTAX          Counter
    ACCESS          read-only
    STATUS          mandatory
    DESCRIPTION     
            "Number of Successful DNS A Resource Record Responses."
    ::= { sonusSoftSwitchSipeDnsCounters 9 }

sonusSoftSwitchSipeDnsDNSAResourceRecordRspHostNotFound OBJECT-TYPE
    SYNTAX          Counter
    ACCESS          read-only
    STATUS          mandatory
    DESCRIPTION     
            "Number of DNS A Resource Record Responses with Host_Not_Found Failure."
    ::= { sonusSoftSwitchSipeDnsCounters 10 }

sonusSoftSwitchSipeDnsDNSAResourceRecordRspTryAgain OBJECT-TYPE
    SYNTAX          Counter
    ACCESS          read-only
    STATUS          mandatory
    DESCRIPTION     
            "Number of DNS A Resource Record Responses with Temporary_Server_Error_Try_Again Failure."
    ::= { sonusSoftSwitchSipeDnsCounters 11 }

sonusSoftSwitchSipeDnsDNSAResourceRecordRspNoRecovery OBJECT-TYPE
    SYNTAX          Counter
    ACCESS          read-only
    STATUS          mandatory
    DESCRIPTION     
            "Number of DNS A Resource Record Responses with Non_Recoverable_Name_Server_Error Failure."
    ::= { sonusSoftSwitchSipeDnsCounters 12 }

sonusSoftSwitchSipeDnsDNSAResourceRecordRspNoData OBJECT-TYPE
    SYNTAX          Counter
    ACCESS          read-only
    STATUS          mandatory
    DESCRIPTION     
            "Number of DNS A Resource Record Responses with Valid_Name_But_No_Data_Record Failure."
    ::= { sonusSoftSwitchSipeDnsCounters 13 }

sonusSoftSwitchSipeDNSRequestsSent OBJECT-TYPE
    SYNTAX          Counter
    ACCESS          read-only
    STATUS          mandatory
    DESCRIPTION     
            "Total number of DNS requests sent by SIPE."
    ::= { sonusSoftSwitchSipeDnsCounters 14 }

sonusSoftSwitchSipeDNSResponsesReceived OBJECT-TYPE
    SYNTAX          Counter
    ACCESS          read-only
    STATUS          mandatory
    DESCRIPTION     
            "Total number of DNS responses received by SIPE."
    ::= { sonusSoftSwitchSipeDnsCounters 15 }

sonusSoftSwitchSipeDNSResponseSuccess OBJECT-TYPE
    SYNTAX          Counter
    ACCESS          read-only
    STATUS          deprecated
    DESCRIPTION     
            "Total number of Successful DNS Responses."
    ::= { sonusSoftSwitchSipeDnsCounters 16 }

sonusSoftSwitchSipeDNSResponseHostNotFound OBJECT-TYPE
    SYNTAX          Counter
    ACCESS          read-only
    STATUS          deprecated
    DESCRIPTION     
            "Total number of DNS Responses with Host_Not_Found Failure."
    ::= { sonusSoftSwitchSipeDnsCounters 17 }

sonusSoftSwitchSipeDNSResponseTryAgain OBJECT-TYPE
    SYNTAX          Counter
    ACCESS          read-only
    STATUS          deprecated
    DESCRIPTION     
            "Total number of DNS Responses with Temporary_Server_Error_Try_Again Failure."
    ::= { sonusSoftSwitchSipeDnsCounters 18 }

sonusSoftSwitchSipeDNSResponseNoRecovery OBJECT-TYPE
    SYNTAX          Counter
    ACCESS          read-only
    STATUS          deprecated
    DESCRIPTION     
            "Total number of DNS Responses with Non_Recoverable_Name_Server_Error Failure."
    ::= { sonusSoftSwitchSipeDnsCounters 19 }

sonusSoftSwitchSipeDNSResponseNoData OBJECT-TYPE
    SYNTAX          Counter
    ACCESS          read-only
    STATUS          deprecated
    DESCRIPTION     
            "Total number of DNS Responses with Valid_Name_But_No_Data_Record Failure."
    ::= { sonusSoftSwitchSipeDnsCounters 20 }

sonusSoftSwitchSIPEDNSIntervalTime OBJECT-TYPE
    SYNTAX          TimeTicks
    ACCESS          read-only
    STATUS          obsolete
    DESCRIPTION     
            "This variable contains the end of interval time stamp for 
             the specified interval."
    ::= { sonusSoftSwitchSipeDnsCounters 21 }

sonusSoftSwitchSipeDNSNAPTRResourceRecordRequestsSent OBJECT-TYPE
    SYNTAX          Counter
    ACCESS          read-only
    STATUS          mandatory
    DESCRIPTION     
            "Number of DNS NAPTR Resource Record requests sent by SIPE."
    ::= { sonusSoftSwitchSipeDnsCounters 22 }

sonusSoftSwitchSipeDNSNAPTRResourceRecordResponsesReceived OBJECT-TYPE
    SYNTAX          Counter
    ACCESS          read-only
    STATUS          mandatory
    DESCRIPTION     
            "Number of DNS NAPTR Resource Record responses received by SIPE."
    ::= { sonusSoftSwitchSipeDnsCounters 23 }

sonusSoftSwitchSipeDNSNAPTRResourceRecordCanceledRequests OBJECT-TYPE
    SYNTAX          Counter
    ACCESS          read-only
    STATUS          mandatory
    DESCRIPTION     
            "Number of DNS NAPTR Resource Record requests canceled by SIPE."
    ::= { sonusSoftSwitchSipeDnsCounters 24 }

sonusSoftSwitchSipeDNSNAPTRResourceRecordRspSuccess OBJECT-TYPE
    SYNTAX          Counter
    ACCESS          read-only
    STATUS          mandatory
    DESCRIPTION     
            "Number of Successful DNS NAPTR Resource Record responses."
    ::= { sonusSoftSwitchSipeDnsCounters 25 }

sonusSoftSwitchSipeDNSNAPTRResourceRecordRspGeneralFailure OBJECT-TYPE
    SYNTAX          Counter
    ACCESS          read-only
    STATUS          mandatory
    DESCRIPTION     
            "Number of DNS NAPTR Resource Record responses with General Failure."
    ::= { sonusSoftSwitchSipeDnsCounters 26 }

sonusSoftSwitchSipeDNSNAPTRResourceRecordRspNoMemory OBJECT-TYPE
    SYNTAX          Counter
    ACCESS          read-only
    STATUS          mandatory
    DESCRIPTION     
            "Number of DNS NAPTR Resource Record responses with Memory_Unavailable Failure."
    ::= { sonusSoftSwitchSipeDnsCounters 27 }

sonusSoftSwitchSipeDNSNAPTRResourceRecordRspInvalidParam OBJECT-TYPE
    SYNTAX          Counter
    ACCESS          read-only
    STATUS          mandatory
    DESCRIPTION     
            "Number of DNS NAPTR Resource Record responses with Invalid_Parameter Failure."
    ::= { sonusSoftSwitchSipeDnsCounters 28 }

sonusSoftSwitchSipeDNSNAPTRResourceRecordRspNoName OBJECT-TYPE
    SYNTAX          Counter
    ACCESS          read-only
    STATUS          mandatory
    DESCRIPTION     
            "Number of DNS NAPTR Resource Record responses with Name_Does_Not_Exist Failure."
    ::= { sonusSoftSwitchSipeDnsCounters 29 }

sonusSoftSwitchSipeDNSNAPTRResourceRecordRspNoData OBJECT-TYPE
    SYNTAX          Counter
    ACCESS          read-only
    STATUS          mandatory
    DESCRIPTION     
            "Number of DNS NAPTR Resource Record responses with Valid_Name_But_No_Data_Record Failure."
    ::= { sonusSoftSwitchSipeDnsCounters 30 }

sonusSoftSwitchSipeDNSSRVResourceRecordRequestsSent OBJECT-TYPE
    SYNTAX          Counter
    ACCESS          read-only
    STATUS          mandatory
    DESCRIPTION     
            "Number of DNS SRV Resource Record requests sent by SIPE."
    ::= { sonusSoftSwitchSipeDnsCounters 31 }

sonusSoftSwitchSipeDNSSRVResourceRecordResponsesReceived OBJECT-TYPE
    SYNTAX          Counter
    ACCESS          read-only
    STATUS          mandatory
    DESCRIPTION     
            "Number of DNS SRV Resource Record responses received by SIPE."
    ::= { sonusSoftSwitchSipeDnsCounters 32 }

sonusSoftSwitchSipeDNSSRVResourceRecordCanceledRequests OBJECT-TYPE
    SYNTAX          Counter
    ACCESS          read-only
    STATUS          mandatory
    DESCRIPTION     
            "Number of DNS SRV Resource Record requests canceled by SIPE."
    ::= { sonusSoftSwitchSipeDnsCounters 33 }

sonusSoftSwitchSipeDNSSRVResourceRecordRspSuccess OBJECT-TYPE
    SYNTAX          Counter
    ACCESS          read-only
    STATUS          mandatory
    DESCRIPTION     
            "Number of Successful DNS SRV Resource Record responses."
    ::= { sonusSoftSwitchSipeDnsCounters 34 }

sonusSoftSwitchSipeDNSSRVResourceRecordRspGeneralFailure OBJECT-TYPE
    SYNTAX          Counter
    ACCESS          read-only
    STATUS          mandatory
    DESCRIPTION     
            "Number of DNS SRV Resource Record responses with General Failure."
    ::= { sonusSoftSwitchSipeDnsCounters 35 }

sonusSoftSwitchSipeDNSSRVResourceRecordRspNoMemory OBJECT-TYPE
    SYNTAX          Counter
    ACCESS          read-only
    STATUS          mandatory
    DESCRIPTION     
            "Number of DNS SRV Resource Record responses with Memory_Unavailable Failure."
    ::= { sonusSoftSwitchSipeDnsCounters 36 }

sonusSoftSwitchSipeDNSSRVResourceRecordRspInvalidParam OBJECT-TYPE
    SYNTAX          Counter
    ACCESS          read-only
    STATUS          mandatory
    DESCRIPTION     
            "Number of DNS SRV Resource Record responses with Invalid_Parameter Failure."
    ::= { sonusSoftSwitchSipeDnsCounters 37 }

sonusSoftSwitchSipeDNSSRVResourceRecordRspNoName OBJECT-TYPE
    SYNTAX          Counter
    ACCESS          read-only
    STATUS          mandatory
    DESCRIPTION     
            "Number of DNS SRV Resource Record responses with Name_Does_Not_Exist Failure."
    ::= { sonusSoftSwitchSipeDnsCounters 38 }

sonusSoftSwitchSipeDNSSRVResourceRecordRspNoData OBJECT-TYPE
    SYNTAX          Counter
    ACCESS          read-only
    STATUS          mandatory
    DESCRIPTION     
            "Number of DNS SRV Resource Record responses with Valid_Name_But_No_Data_Record Failure."
    ::= { sonusSoftSwitchSipeDnsCounters 39 }

sonusSoftSwitchSipeDnsDNSAAAAResourceRecordRequestsSent OBJECT-TYPE
    SYNTAX          Counter
    ACCESS          read-only
    STATUS          mandatory
    DESCRIPTION     
            "Number of DNS AAAA Resource Record requests sent by SIPE."
    ::= { sonusSoftSwitchSipeDnsCounters 40 }

sonusSoftSwitchSipeDnsDNSAAAAResourceRecordResponsesReceived OBJECT-TYPE
    SYNTAX          Counter
    ACCESS          read-only
    STATUS          mandatory
    DESCRIPTION     
            "Number of DNS AAAA Resource Record responses received by SIPE."
    ::= { sonusSoftSwitchSipeDnsCounters 41 }

sonusSoftSwitchSipeDnsDNSAAAAResourceRecordCanceledRequests OBJECT-TYPE
    SYNTAX          Counter
    ACCESS          read-only
    STATUS          mandatory
    DESCRIPTION     
            "Number of DNS AAAA Resource Record requests canceled by SIPE."
    ::= { sonusSoftSwitchSipeDnsCounters 42 }

sonusSoftSwitchSipeDnsDNSAAAAResourceRecordRspSuccess OBJECT-TYPE
    SYNTAX          Counter
    ACCESS          read-only
    STATUS          mandatory
    DESCRIPTION     
            "Number of Successful DNS AAAA Resource Record Responses."
    ::= { sonusSoftSwitchSipeDnsCounters 43 }

sonusSoftSwitchSipeDnsDNSAAAAResourceRecordRspHostNotFound OBJECT-TYPE
    SYNTAX          Counter
    ACCESS          read-only
    STATUS          mandatory
    DESCRIPTION     
            "Number of DNS AAAA Resource Record Responses with Host_Not_Found Failure."
    ::= { sonusSoftSwitchSipeDnsCounters 44 }

sonusSoftSwitchSipeDnsDNSAAAAResourceRecordRspTryAgain OBJECT-TYPE
    SYNTAX          Counter
    ACCESS          read-only
    STATUS          mandatory
    DESCRIPTION     
            "Number of DNS AAAA Resource Record Responses with Temporary_Server_Error_Try_Again Failure."
    ::= { sonusSoftSwitchSipeDnsCounters 45 }

sonusSoftSwitchSipeDnsDNSAAAAResourceRecordRspNoRecovery OBJECT-TYPE
    SYNTAX          Counter
    ACCESS          read-only
    STATUS          mandatory
    DESCRIPTION     
            "Number of DNS AAAA Resource Record Responses with Non_Recoverable_Name_Server_Error Failure."
    ::= { sonusSoftSwitchSipeDnsCounters 46 }

sonusSoftSwitchSipeDnsDNSAAAAResourceRecordRspNoData OBJECT-TYPE
    SYNTAX          Counter
    ACCESS          read-only
    STATUS          mandatory
    DESCRIPTION     
            "Number of DNS AAAA Resource Record Responses with Valid_Name_But_No_Data_Record Failure."
    ::= { sonusSoftSwitchSipeDnsCounters 47 }

sonusSoftSwitchSipeSipIInterworkingCounters OBJECT IDENTIFIER
    ::= { sonusSoftSwitchSIPEngineStatistics 7 }

sonusSoftSwitchSipeSipIInvitesSent OBJECT-TYPE
    SYNTAX          Counter
    ACCESS          read-only
    STATUS          mandatory
    DESCRIPTION     
            "The number of SIP-I Invites with ISUP IAM sent by SIPE."
    ::= { sonusSoftSwitchSipeSipIInterworkingCounters 1 }

sonusSoftSwitchSipeSipIInvitesReceived OBJECT-TYPE
    SYNTAX          Counter
    ACCESS          read-only
    STATUS          mandatory
    DESCRIPTION     
            "The number of SIP-I Invites with ISUP IAM received by SIPE."
    ::= { sonusSoftSwitchSipeSipIInterworkingCounters 2 }

sonusSoftSwitchSipeSipI18xCpgSent OBJECT-TYPE
    SYNTAX          Counter
    ACCESS          read-only
    STATUS          mandatory
    DESCRIPTION     
            "The number of SIP-I 18x with ISUP CPG sent by SIPE."
    ::= { sonusSoftSwitchSipeSipIInterworkingCounters 3 }

sonusSoftSwitchSipeSipI18xCpgReceived OBJECT-TYPE
    SYNTAX          Counter
    ACCESS          read-only
    STATUS          mandatory
    DESCRIPTION     
            "The number of SIP-I 18x with ISUP CPG received by SIPE."
    ::= { sonusSoftSwitchSipeSipIInterworkingCounters 4 }

sonusSoftSwitchSipeSipI18xAcmSent OBJECT-TYPE
    SYNTAX          Counter
    ACCESS          read-only
    STATUS          mandatory
    DESCRIPTION     
            "The number of SIP-I 18x with ISUP ACM sent by SIPE."
    ::= { sonusSoftSwitchSipeSipIInterworkingCounters 5 }

sonusSoftSwitchSipeSipI18xAcmReceived OBJECT-TYPE
    SYNTAX          Counter
    ACCESS          read-only
    STATUS          mandatory
    DESCRIPTION     
            "The number of SIP-I 18x with ISUP ACM received by SIPE."
    ::= { sonusSoftSwitchSipeSipIInterworkingCounters 6 }

sonusSoftSwitchSipeSipI200AnmSent OBJECT-TYPE
    SYNTAX          Counter
    ACCESS          read-only
    STATUS          mandatory
    DESCRIPTION     
            "The number of SIP-I 200 OK with ISUP ANM sent by SIPE."
    ::= { sonusSoftSwitchSipeSipIInterworkingCounters 7 }

sonusSoftSwitchSipeSipI200AnmReceived OBJECT-TYPE
    SYNTAX          Counter
    ACCESS          read-only
    STATUS          mandatory
    DESCRIPTION     
            "The number of SIP-I 200 OK with ISUP ANM received by SIPE."
    ::= { sonusSoftSwitchSipeSipIInterworkingCounters 8 }

sonusSoftSwitchHPCSipeReqRcvdCounters OBJECT IDENTIFIER
    ::= { sonusSoftSwitchSIPEngineStatistics 8 }

sonusSoftSwitchSipeReqRcvdSUBSCRIBEwithEtsRph OBJECT-TYPE
    SYNTAX          Counter
    ACCESS          read-only
    STATUS          mandatory
    DESCRIPTION     
            "This counter keeps track of the number of SUBSCRIBE requests with
             ETS RPH, which have been received by SIPE process.
             Retransmissions of messages (while the original one is being processed)
             are not counted."
    ::= { sonusSoftSwitchHPCSipeReqRcvdCounters 1 }

sonusSoftSwitchSipeReqRcvdSUBSCRIBEwithEtsDn OBJECT-TYPE
    SYNTAX          Counter
    ACCESS          read-only
    STATUS          mandatory
    DESCRIPTION     
            "This counter keeps track of the number of SUBSCRIBE requests with
             ETS DN but no ETS RPH, which have been received by SIPE process.
             Retransmissions of messages (while the original one is being processed)
             are not counted."
    ::= { sonusSoftSwitchHPCSipeReqRcvdCounters 2 }

sonusSoftSwitchSipeSubscribeReqWithEtsRphDiscardedOverload OBJECT-TYPE
    SYNTAX          Counter
    ACCESS          read-only
    STATUS          mandatory
    DESCRIPTION     
            "This counter keeps track of the number of SUBSCRIBE Requests with
             ETS RPH discarded due to overload."
    ::= { sonusSoftSwitchHPCSipeReqRcvdCounters 3 }

sonusSoftSwitchSipeSubscribeReqWithoutEtsRphDiscardedOverload OBJECT-TYPE
    SYNTAX          Counter
    ACCESS          read-only
    STATUS          mandatory
    DESCRIPTION     
            "This counter keeps track of the number of SUBSCRIBE Requests without
             ETS RPH discarded due to overload."
    ::= { sonusSoftSwitchHPCSipeReqRcvdCounters 4 }

sonusSoftSwitchSipeReqRcvdNOTIFYwithEtsRph OBJECT-TYPE
    SYNTAX          Counter
    ACCESS          read-only
    STATUS          mandatory
    DESCRIPTION     
            "This counter keeps track of the number of NOTIFY requests with
             ETS RPH, which have been received by SIPE process.
             Retransmissions of messages (while the original one is being processed)
             are not counted."
    ::= { sonusSoftSwitchHPCSipeReqRcvdCounters 5 }

sonusSoftSwitchSipeReqRcvdNOTIFYwithEtsDn OBJECT-TYPE
    SYNTAX          Counter
    ACCESS          read-only
    STATUS          mandatory
    DESCRIPTION     
            "This counter keeps track of the number of NOTIFY requests with
             ETS DN but no ETS RPH, which have been received by SIPE process.
             Retransmissions of messages (while the original one is being processed)
             are not counted."
    ::= { sonusSoftSwitchHPCSipeReqRcvdCounters 6 }

sonusSoftSwitchSipeNotifyReqWithEtsRphDiscardedOverload OBJECT-TYPE
    SYNTAX          Counter
    ACCESS          read-only
    STATUS          mandatory
    DESCRIPTION     
            "This counter keeps track of the number of NOTIFY Requests with
             ETS RPH discarded due to overload."
    ::= { sonusSoftSwitchHPCSipeReqRcvdCounters 7 }

sonusSoftSwitchSipeNotifyReqWithoutEtsRphDiscardedOverload OBJECT-TYPE
    SYNTAX          Counter
    ACCESS          read-only
    STATUS          mandatory
    DESCRIPTION     
            "This counter keeps track of the number of NOTIFY Requests without
             ETS RPH discarded due to overload."
    ::= { sonusSoftSwitchHPCSipeReqRcvdCounters 8 }

sonusSoftSwitchSipeReqRcvdREGISTERwithEtsRph OBJECT-TYPE
    SYNTAX          Counter
    ACCESS          read-only
    STATUS          mandatory
    DESCRIPTION     
            "This counter keeps track of the number of REGISTER requests with
             ETS RPH, which have been received by SIPE process.
             Retransmissions of messages (while the original one is being processed)
             are not counted."
    ::= { sonusSoftSwitchHPCSipeReqRcvdCounters 9 }

sonusSoftSwitchSipeReqRcvdREGISTERwithEtsDn OBJECT-TYPE
    SYNTAX          Counter
    ACCESS          read-only
    STATUS          mandatory
    DESCRIPTION     
            "This counter keeps track of the number of REGISTER requests with
             ETS DN but no ETS RPH, which have been received by SIPE process.
             Retransmissions of messages (while the original one is being processed)
             are not counted."
    ::= { sonusSoftSwitchHPCSipeReqRcvdCounters 10 }

sonusSoftSwitchSipeRegisterReqWithEtsRphDiscardedOverload OBJECT-TYPE
    SYNTAX          Counter
    ACCESS          read-only
    STATUS          mandatory
    DESCRIPTION     
            "This counter keeps track of the number of REGISTER Requests with
             ETS RPH discarded due to overload."
    ::= { sonusSoftSwitchHPCSipeReqRcvdCounters 11 }

sonusSoftSwitchSipeRegisterReqWithoutEtsRphDiscardedOverload OBJECT-TYPE
    SYNTAX          Counter
    ACCESS          read-only
    STATUS          mandatory
    DESCRIPTION     
            "This counter keeps track of the number of REGISTER Requests without
             ETS RPH discarded due to overload."
    ::= { sonusSoftSwitchHPCSipeReqRcvdCounters 12 }

sonusSoftSwitchSipeReqRcvdOPTIONSwithEtsRph OBJECT-TYPE
    SYNTAX          Counter
    ACCESS          read-only
    STATUS          mandatory
    DESCRIPTION     
            "This counter keeps track of the number of OPTIONS requests with
             ETS RPH, which have been received by SIPE process.
             Retransmissions of messages (while the original one is being processed)
             are not counted."
    ::= { sonusSoftSwitchHPCSipeReqRcvdCounters 13 }

sonusSoftSwitchSipeReqRcvdOPTIONSwithEtsDn OBJECT-TYPE
    SYNTAX          Counter
    ACCESS          read-only
    STATUS          mandatory
    DESCRIPTION     
            "This counter keeps track of the number of OPTIONS requests with
             ETS DN but no ETS RPH, which have been received by SIPE process.
             Retransmissions of messages (while the original one is being processed)
             are not counted."
    ::= { sonusSoftSwitchHPCSipeReqRcvdCounters 14 }

sonusSoftSwitchSipeOptionsReqWithEtsRphDiscardedOverload OBJECT-TYPE
    SYNTAX          Counter
    ACCESS          read-only
    STATUS          mandatory
    DESCRIPTION     
            "This counter keeps track of the number of OPTIONS Requests with
             ETS RPH discarded due to overload."
    ::= { sonusSoftSwitchHPCSipeReqRcvdCounters 15 }

sonusSoftSwitchSipeOptionsReqWithoutEtsRphDiscardedOverload OBJECT-TYPE
    SYNTAX          Counter
    ACCESS          read-only
    STATUS          mandatory
    DESCRIPTION     
            "This counter keeps track of the number of OPTIONS Requests without
             ETS RPH discarded due to overload."
    ::= { sonusSoftSwitchHPCSipeReqRcvdCounters 16 }

sonusSoftSwitchSipeReqRcvdMESSAGEwithEtsRph OBJECT-TYPE
    SYNTAX          Counter
    ACCESS          read-only
    STATUS          mandatory
    DESCRIPTION     
            "This counter keeps track of the number of MESSAGE requests with
             ETS RPH, which have been received by SIPE process.
             Retransmissions of messages (while the original one is being processed)
             are not counted."
    ::= { sonusSoftSwitchHPCSipeReqRcvdCounters 17 }

sonusSoftSwitchSipeReqRcvdMESSAGEwithEtsDn OBJECT-TYPE
    SYNTAX          Counter
    ACCESS          read-only
    STATUS          mandatory
    DESCRIPTION     
            "This counter keeps track of the number of MESSAGE requests with
             ETS DN but no ETS RPH, which have been received by SIPE process.
             Retransmissions of messages (while the original one is being processed)
             are not counted."
    ::= { sonusSoftSwitchHPCSipeReqRcvdCounters 18 }

sonusSoftSwitchSipeMessageReqWithEtsRphDiscardedOverload OBJECT-TYPE
    SYNTAX          Counter
    ACCESS          read-only
    STATUS          mandatory
    DESCRIPTION     
            "This counter keeps track of the number of MESSAGE Requests with
             ETS RPH discarded due to overload."
    ::= { sonusSoftSwitchHPCSipeReqRcvdCounters 19 }

sonusSoftSwitchSipeMessageReqWithoutEtsRphDiscardedOverload OBJECT-TYPE
    SYNTAX          Counter
    ACCESS          read-only
    STATUS          mandatory
    DESCRIPTION     
            "This counter keeps track of the number of MESSAGE Requests without
             ETS RPH discarded due to overload."
    ::= { sonusSoftSwitchHPCSipeReqRcvdCounters 20 }

sonusSoftSwitchSipeReqRcvdREFERwithEtsRph OBJECT-TYPE
    SYNTAX          Counter
    ACCESS          read-only
    STATUS          mandatory
    DESCRIPTION     
            "This counter keeps track of the number of REFER requests with
             ETS RPH, which have been received by SIPE process.
             Retransmissions of messages (while the original one is being processed)
             are not counted."
    ::= { sonusSoftSwitchHPCSipeReqRcvdCounters 21 }

sonusSoftSwitchSipeReqRcvdREFERwithEtsDn OBJECT-TYPE
    SYNTAX          Counter
    ACCESS          read-only
    STATUS          mandatory
    DESCRIPTION     
            "This counter keeps track of the number of REFER requests with
             ETS DN but no ETS RPH, which have been received by SIPE process.
             Retransmissions of messages (while the original one is being processed)
             are not counted."
    ::= { sonusSoftSwitchHPCSipeReqRcvdCounters 22 }

sonusSoftSwitchSipeReferReqWithEtsRphDiscardedOverload OBJECT-TYPE
    SYNTAX          Counter
    ACCESS          read-only
    STATUS          mandatory
    DESCRIPTION     
            "This counter keeps track of the number of REFER Requests with
             ETS RPH discarded due to overload."
    ::= { sonusSoftSwitchHPCSipeReqRcvdCounters 23 }

sonusSoftSwitchSipeReferReqWithoutEtsRphDiscardedOverload OBJECT-TYPE
    SYNTAX          Counter
    ACCESS          read-only
    STATUS          mandatory
    DESCRIPTION     
            "This counter keeps track of the number of REFER Requests without
             ETS RPH discarded due to overload."
    ::= { sonusSoftSwitchHPCSipeReqRcvdCounters 24 }

sonusSoftSwitchHPCSipeRspSentCounters OBJECT IDENTIFIER
    ::= { sonusSoftSwitchSIPEngineStatistics 9 }

sonusSoftSwitchSipeRspSentSubscribeWithEtsRph OBJECT-TYPE
    SYNTAX          Counter
    ACCESS          read-only
    STATUS          mandatory
    DESCRIPTION     
            "This counter keeps track of the number of SUBSCRIBE requests sent with ETS RPH
             which have been sent by SIPE process.
             Retransmissions of messages are not counted."
    ::= { sonusSoftSwitchHPCSipeRspSentCounters 1 }

sonusSoftSwitchSipeRspSentNotifyWithEtsRph OBJECT-TYPE
    SYNTAX          Counter
    ACCESS          read-only
    STATUS          mandatory
    DESCRIPTION     
            "This counter keeps track of the number of NOTIFY requests sent with ETS RPH
             which have been sent by SIPE process.
             Retransmissions of messages are not counted."
    ::= { sonusSoftSwitchHPCSipeRspSentCounters 2 }

sonusSoftSwitchSipeRspSentRegisterWithEtsRph OBJECT-TYPE
    SYNTAX          Counter
    ACCESS          read-only
    STATUS          mandatory
    DESCRIPTION     
            "This counter keeps track of the number of REGISTER requests sent with ETS RPH
             which have been sent by SIPE process.
             Retransmissions of messages are not counted."
    ::= { sonusSoftSwitchHPCSipeRspSentCounters 3 }

sonusSoftSwitchSipeRspSentOptionsWithEtsRph OBJECT-TYPE
    SYNTAX          Counter
    ACCESS          read-only
    STATUS          mandatory
    DESCRIPTION     
            "This counter keeps track of the number of OPTIONS requests sent with ETS RPH
             which have been sent by SIPE process.
             Retransmissions of messages are not counted."
    ::= { sonusSoftSwitchHPCSipeRspSentCounters 4 }

sonusSoftSwitchSipeRspSentMessageWithEtsRph OBJECT-TYPE
    SYNTAX          Counter
    ACCESS          read-only
    STATUS          mandatory
    DESCRIPTION     
            "This counter keeps track of the number of MESSAGE requests sent with ETS RPH
             which have been sent by SIPE process.
             Retransmissions of messages are not counted."
    ::= { sonusSoftSwitchHPCSipeRspSentCounters 5 }

sonusSoftSwitchSipeRspSentReferWithEtsRph OBJECT-TYPE
    SYNTAX          Counter
    ACCESS          read-only
    STATUS          mandatory
    DESCRIPTION     
            "This counter keeps track of the number of REFER requests sent with ETS RPH
             which have been sent by SIPE process.
             Retransmissions of messages are not counted."
    ::= { sonusSoftSwitchHPCSipeRspSentCounters 6 }

sonusSoftSwitchSipeStirShakenCounters OBJECT IDENTIFIER
    ::= { sonusSoftSwitchSIPEngineStatistics 10 }

sonusSoftSwitchRedirectorSignedCalls OBJECT-TYPE
    SYNTAX          Counter
    ACCESS          read-only
    STATUS          mandatory
    DESCRIPTION     
            "This counter keeps track of the number of signed calls in Redirector Mode"
    ::= { sonusSoftSwitchSipeStirShakenCounters 1 }

sonusSoftSwitchRedirectorVerifiedCalls OBJECT-TYPE
    SYNTAX          Counter
    ACCESS          read-only
    STATUS          mandatory
    DESCRIPTION     
            "This counter keeps track of the number of verified calls in Redirector Mode"
    ::= { sonusSoftSwitchSipeStirShakenCounters 2 }

sonusSoftSwitchRedirectorTaggedCalls OBJECT-TYPE
    SYNTAX          Counter
    ACCESS          read-only
    STATUS          mandatory
    DESCRIPTION     
            "This counter keeps track of the number of tagged calls in Redirector Mode"
    ::= { sonusSoftSwitchSipeStirShakenCounters 3 }

sonusSoftSwitchProxySignedCalls OBJECT-TYPE
    SYNTAX          Counter
    ACCESS          read-only
    STATUS          mandatory
    DESCRIPTION     
            "This counter keeps track of the number of signed calls in Proxy Mode"
    ::= { sonusSoftSwitchSipeStirShakenCounters 4 }

sonusSoftSwitchProxyVerifiedCalls OBJECT-TYPE
    SYNTAX          Counter
    ACCESS          read-only
    STATUS          mandatory
    DESCRIPTION     
            "This counter keeps track of the number of verified calls in Proxy Mode"
    ::= { sonusSoftSwitchSipeStirShakenCounters 5 }

sonusSoftSwitchProxyTaggedCalls OBJECT-TYPE
    SYNTAX          Counter
    ACCESS          read-only
    STATUS          mandatory
    DESCRIPTION     
            "This counter keeps track of the number of tagged calls in Proxy Mode"
    ::= { sonusSoftSwitchSipeStirShakenCounters 6 }

sonusSoftSwitchSIPEngineMIBNotifications OBJECT IDENTIFIER
    ::= { sonusSoftSwitchSIPEngineMIB 2 }

sonusSoftSwitchSIPEngineMIBNotificationsPrefix OBJECT IDENTIFIER
    ::= { sonusSoftSwitchSIPEngineMIBNotifications 0 }

sonusSoftSwitchSIPEngineMIBNotificationsObjects OBJECT IDENTIFIER
    ::= { sonusSoftSwitchSIPEngineMIBNotifications 1 }

sonusSoftSwitchSipePesInterfaceIdentifier OBJECT-TYPE
    SYNTAX          INTEGER { primary(1), secondary(2) }
    ACCESS          read-only
    STATUS          mandatory
    DESCRIPTION     
            "SoftSwitch SIPE-PES redundant interface identifier"
    ::= { sonusSoftSwitchSIPEngineMIBNotificationsObjects 1 }

sonusSoftSwitchSipeUpNotification TRAP-TYPE
    ENTERPRISE      sonusSoftSwitchSIPEngineMIBNotifications
    VARIABLES       { sonusEventDescription, sonusEventClass, 
                      sonusEventLevel, sonusEventTime }
--     STATUS          mandatory
    DESCRIPTION     
            "SoftSwitch SIP Engine is up."
    ::= 1

sonusSoftSwitchSipeDownNotification TRAP-TYPE
    ENTERPRISE      sonusSoftSwitchSIPEngineMIBNotifications
    VARIABLES       { sonusEventDescription, sonusEventClass, 
                      sonusEventLevel, sonusEventTime }
--     STATUS          mandatory
    DESCRIPTION     
            "SoftSwitch SIP Engine is down."
    ::= 2

sonusSoftSwitchSipePesServiceUpNotification TRAP-TYPE
    ENTERPRISE      sonusSoftSwitchSIPEngineMIBNotifications
    VARIABLES       { sonusEventDescription, sonusEventClass, 
                      sonusEventLevel, sonusEventTime }
--     STATUS          mandatory
    DESCRIPTION     
            "SoftSwitch SIPE-PES communication is up."
    ::= 3

sonusSoftSwitchSipePesServiceDownNotification TRAP-TYPE
    ENTERPRISE      sonusSoftSwitchSIPEngineMIBNotifications
    VARIABLES       { sonusEventDescription, sonusEventClass, 
                      sonusEventLevel, sonusEventTime }
--     STATUS          mandatory
    DESCRIPTION     
            "SoftSwitch SIPE-PES communication is down."
    ::= 4

sonusSoftswitchSipeLoadAboveMaxNotification TRAP-TYPE
    ENTERPRISE      sonusSoftSwitchSIPEngineMIBNotifications
    VARIABLES       { sonusEventDescription, sonusEventClass, 
                      sonusEventLevel, sonusEventTime }
--     STATUS          mandatory
    DESCRIPTION     
            "SoftSwitch SIP Engine is experiencing load above the maximum allowable limit."
    ::= 5

sonusSoftSwitchSipeLoadBelowMaxNotification TRAP-TYPE
    ENTERPRISE      sonusSoftSwitchSIPEngineMIBNotifications
    VARIABLES       { sonusEventDescription, sonusEventClass, 
                      sonusEventLevel, sonusEventTime }
--     STATUS          mandatory
    DESCRIPTION     
            "SoftSwitch SIP Engine is experiencing load back in the allowable range."
    ::= 6

sonusSoftswitchSipeStaleTransactionAboveMaxNotification TRAP-TYPE
    ENTERPRISE      sonusSoftSwitchSIPEngineMIBNotifications
    VARIABLES       { sonusEventDescription, sonusEventClass, 
                      sonusEventLevel, sonusEventTime }
--     STATUS          mandatory
    DESCRIPTION     
            "SoftSwitch SIP Engine detects number of stale transactions above the maximum allowable limit."
    ::= 7

sonusSoftSwitchSipeStaleTransactionBelowMaxNotification TRAP-TYPE
    ENTERPRISE      sonusSoftSwitchSIPEngineMIBNotifications
    VARIABLES       { sonusEventDescription, sonusEventClass, 
                      sonusEventLevel, sonusEventTime }
--     STATUS          mandatory
    DESCRIPTION     
            "SoftSwitch SIP Engine detects number of stale transactions back in the allowable range."
    ::= 8

sonusSoftswitchSipePesHighCongestionTimeExceeded TRAP-TYPE
    ENTERPRISE      sonusSoftSwitchSIPEngineMIBNotifications
    VARIABLES       { sonusEventDescription, sonusEventClass, 
                      sonusEventLevel, sonusEventTime }
--     STATUS          mandatory
    DESCRIPTION     
            "Indicates that the softswitch SIP Engine has detected that Policy Execution Server has been under a high level of congestion for the past 5 minutes."
    ::= 9

sonusSoftswitchSipePesHighCongestionTimeExceededCleared TRAP-TYPE
    ENTERPRISE      sonusSoftSwitchSIPEngineMIBNotifications
    VARIABLES       { sonusEventDescription, sonusEventClass, 
                      sonusEventLevel, sonusEventTime }
--     STATUS          mandatory
    DESCRIPTION     
            "Indicates that the softswitch SIP Engine has detected that Policy Execution Server is experiencing lower congestion."
    ::= 10

sonusSoftSwitchSipeDnsServiceUpNotification TRAP-TYPE
    ENTERPRISE      sonusSoftSwitchSIPEngineMIBNotifications
    VARIABLES       { sonusEventDescription, sonusEventClass, 
                      sonusEventLevel, sonusEventTime }
--     STATUS          mandatory
    DESCRIPTION     
            "SoftSwitch SIPE-DNS communication is up."
    ::= 11

sonusSoftSwitchSipeDnsServiceDownNotification TRAP-TYPE
    ENTERPRISE      sonusSoftSwitchSIPEngineMIBNotifications
    VARIABLES       { sonusEventDescription, sonusEventClass, 
                      sonusEventLevel, sonusEventTime }
--     STATUS          mandatory
    DESCRIPTION     
            "SoftSwitch SIPE-DNS communication is down."
    ::= 12

sonusSoftSwitchSipeIpQosEnabled TRAP-TYPE
    ENTERPRISE      sonusSoftSwitchSIPEngineMIBNotifications
    VARIABLES       { sonusEventDescription, sonusEventClass, 
                      sonusEventLevel, sonusEventTime }
--     STATUS          mandatory
    DESCRIPTION     
            "SoftSwitch SIPE IPQOS is enabled."
    ::= 13

sonusSoftSwitchSipeIpQosDisabled TRAP-TYPE
    ENTERPRISE      sonusSoftSwitchSIPEngineMIBNotifications
    VARIABLES       { sonusEventDescription, sonusEventClass, 
                      sonusEventLevel, sonusEventTime }
--     STATUS          mandatory
    DESCRIPTION     
            "SoftSwitch SIPE IPQOS is disabled."
    ::= 14

sonusSoftSwitchSipePeerBlacklisted TRAP-TYPE
    ENTERPRISE      sonusSoftSwitchSIPEngineMIBNotifications
    VARIABLES       { sonusEventDescription, sonusEventClass, 
                      sonusEventLevel, sonusEventTime }
--     STATUS          mandatory
    DESCRIPTION     
            "SIP SERVER Blacklisted."
    ::= 15

sonusSoftSwitchSipePeerRecovered TRAP-TYPE
    ENTERPRISE      sonusSoftSwitchSIPEngineMIBNotifications
    VARIABLES       { sonusEventDescription, sonusEventClass, 
                      sonusEventLevel, sonusEventTime }
--     STATUS          mandatory
    DESCRIPTION     
            "SIP SERVER Recovered from Blacklist."
    ::= 16

sonusSoftSwitchSipePeerRecoveryStopped TRAP-TYPE
    ENTERPRISE      sonusSoftSwitchSIPEngineMIBNotifications
    VARIABLES       { sonusEventDescription, sonusEventClass, 
                      sonusEventLevel, sonusEventTime }
--     STATUS          mandatory
    DESCRIPTION     
            "SIP SERVER PING based Recovery Stopped after HighWaterMark Timer."
    ::= 17

sonusSoftSwitchSipePlmServiceUpNotification TRAP-TYPE
    ENTERPRISE      sonusSoftSwitchSIPEngineMIBNotifications
    VARIABLES       { sonusEventDescription, sonusEventClass, 
                      sonusEventLevel, sonusEventTime }
--     STATUS          deprecated
    DESCRIPTION     
            "SoftSwitch SIPE-PLM communication is up."
    ::= 18

sonusSoftSwitchSipePlmServiceDownNotification TRAP-TYPE
    ENTERPRISE      sonusSoftSwitchSIPEngineMIBNotifications
    VARIABLES       { sonusEventDescription, sonusEventClass, 
                      sonusEventLevel, sonusEventTime }
--     STATUS          deprecated
    DESCRIPTION     
            "SoftSwitch SIPE-PLM communication is down."
    ::= 19

sonusSoftSwitchSipeRDNSSIPServerFQDNResolutionFailedNotification TRAP-TYPE
    ENTERPRISE      sonusSoftSwitchSIPEngineMIBNotifications
    VARIABLES       { sonusEventDescription, sonusEventClass, 
                      sonusEventLevel, sonusEventTime }
--     STATUS          mandatory
    DESCRIPTION     
            "Indicates that the SIPE's attempt to resolve the SIP Server FQDN failed."
    ::= 20

sonusSoftSwitchSipeRDNSSIPServerFQDNResolutionSuccessNotification TRAP-TYPE
    ENTERPRISE      sonusSoftSwitchSIPEngineMIBNotifications
    VARIABLES       { sonusEventDescription, sonusEventClass, 
                      sonusEventLevel, sonusEventTime }
--     STATUS          mandatory
    DESCRIPTION     
            "Indicates that the SIPE's attempt to resolve the SIP Server FQDN succeeded."
    ::= 21

sonusSoftSwitchSipeThreadKeepAliveFailedNotification TRAP-TYPE
    ENTERPRISE      sonusSoftSwitchSIPEngineMIBNotifications
    VARIABLES       { sonusEventDescription, sonusEventClass, 
                      sonusEventLevel, sonusEventTime }
--     STATUS          mandatory
    DESCRIPTION     
            "Indicates that the one of the threads of SIPE process failed to send keepalive message."
    ::= 22

sonusSoftSwitchSipeRDNSSIPServerFQDNResolutionSucessNotification TRAP-TYPE
    ENTERPRISE      sonusSoftSwitchSIPEngineMIBNotifications
    VARIABLES       { sonusEventDescription, sonusEventClass, 
                      sonusEventLevel, sonusEventTime }
--     STATUS          mandatory
    DESCRIPTION     
            "Indicates that the SIPE's attempt to resolve the SIP Server FQDN succeeded."
    ::= 23

END -- end of module SONUS-SOFTSWITCH-SIP-ENGINE-MIB.
