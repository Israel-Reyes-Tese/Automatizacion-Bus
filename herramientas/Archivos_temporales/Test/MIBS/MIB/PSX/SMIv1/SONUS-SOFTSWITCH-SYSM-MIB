--
-- This SMIv1 module has been generated by smidump 0.2-cvs. Do not edit.
--

SONUS-SOFTSWITCH-SYSM-MIB DEFINITIONS ::= BEGIN

IMPORTS
    TRAP-TYPE
        FROM RFC-1215
    Counter, Gauge
        FROM RFC1155-SMI
    sonusEventClass, sonusEventDescription, sonusEventLevel, 
    sonusEventTime
        FROM SONUS-COMMON-MIB
    sonusServicesMIBs
        FROM SONUS-SMI;

sonusSoftSwitchSystemManagerMIB OBJECT IDENTIFIER
    ::= { sonusServicesMIBs 44 }

-- sonusSoftSwitchSystemManagerMIB MODULE-IDENTITY
--     LAST-UPDATED    "200205030000Z"
--     ORGANIZATION    
--             "Sonus Networks, Inc."
--     CONTACT-INFO    
--             " Customer Support
--              Sonus Networks, Inc.
--              250 Apollo Drive
--              Chelmsford, MA 01824
--              USA
--              Tel: 978-614-8100
--              Fax: 978-614-8609"
--     DESCRIPTION     
--             "The MIB Module for SoftSwitch System Manager."
--     ::= { sonusServicesMIBs 44 }


sonusSoftSwitchSystemManagerMIBObjects OBJECT IDENTIFIER
    ::= { sonusSoftSwitchSystemManagerMIB 1 }

sonusSoftSwitchSysmMIBNotifications OBJECT IDENTIFIER
    ::= { sonusSoftSwitchSystemManagerMIB 2 }

sonusSoftSwitchSysmMIBNotificationsPrefix OBJECT IDENTIFIER
    ::= { sonusSoftSwitchSysmMIBNotifications 0 }

sonusSoftSwitchSysmMIBNotificationsObjects OBJECT IDENTIFIER
    ::= { sonusSoftSwitchSysmMIBNotifications 1 }

sonusSoftSwitchSysmUpNotification TRAP-TYPE
    ENTERPRISE      sonusSoftSwitchSysmMIBNotifications
    VARIABLES       { sonusEventDescription, sonusEventClass, 
                      sonusEventLevel, sonusEventTime }
--     STATUS          mandatory
    DESCRIPTION     
            "SoftSwitch SYSM is up."
    ::= 1

sonusSoftSwitchSysmDownNotification TRAP-TYPE
    ENTERPRISE      sonusSoftSwitchSysmMIBNotifications
    VARIABLES       { sonusEventDescription, sonusEventClass, 
                      sonusEventLevel, sonusEventTime }
--     STATUS          mandatory
    DESCRIPTION     
            "SoftSwitch SYSM is down."
    ::= 2

END -- end of module SONUS-SOFTSWITCH-SYSM-MIB.
