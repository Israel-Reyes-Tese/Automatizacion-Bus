--
-- This SMIv2 module has been generated by smidump 0.2-cvs. Do not edit.
--

SONUS-PERFORMANCE-STATISTICS-MIB DEFINITIONS ::= BEGIN

IMPORTS
    PerfCurrentCount, PerfIntervalCount
        FROM PerfHist-TC-MIB
    Counter64, Integer32, MODULE-IDENTITY, OBJECT-TYPE, TimeTicks, 
    Unsigned32
        FROM SNMPv2-SMI
    DisplayString, RowStatus, TruthValue
        FROM SNMPv2-TC
    sonusResourcesMIBs
        FROM SONUS-SMI
    SonusAdminState, SonusName, SonusShelfIndex, SonusSlotIndex
        FROM SONUS-TC;

sonusPerformanceStatisticsMIB MODULE-IDENTITY
    LAST-UPDATED    "201611010000Z"
    ORGANIZATION    
            "Sonus Networks, Inc."
    CONTACT-INFO    
            "   Customer Support    
             Sonus Networks, Inc.
             7 Technology Park Drive
             Westford, MA 01886
             USA
             
             Tel: 978-614-8100
             Fax: 978-614-8609"
    DESCRIPTION     
            "The MIB module to describe
             Sonus Performance Statistics objects."
    ::= { sonusResourcesMIBs 6 }


sonusPerformanceStatisticsObjects OBJECT IDENTIFIER
    ::= { sonusPerformanceStatisticsMIB 1 }

sonusTrunkGroup OBJECT IDENTIFIER
    ::= { sonusPerformanceStatisticsObjects 1 }

sonusTrunkGroupIntervalSize OBJECT-TYPE
    SYNTAX          Integer32 (5..1440)
    MAX-ACCESS      read-write
    STATUS          current
    DESCRIPTION     
            "The size of the intervals in minutes for the Sonus
             Trunk Group interval table."
    DEFVAL          { 15 }
    ::= { sonusTrunkGroup 1 }

sonusTrunkGroupNumberOfIntervals OBJECT-TYPE
    SYNTAX          Integer32 (1..288)
    MAX-ACCESS      read-write
    STATUS          current
    DESCRIPTION     
            "The number of intervals for the Sonus Trunk Group 
             interval table. The sonusTrunkGroupIntervalSize times
             the sonusTrunkGroupNumberOfIntervals must be <= 1440."
    DEFVAL          { 4 }
    ::= { sonusTrunkGroup 2 }

sonusTrunkGroupCurrentTable OBJECT-TYPE
    SYNTAX          SEQUENCE OF SonusTrunkGroupCurrentEntry
    MAX-ACCESS      not-accessible
    STATUS          current
    DESCRIPTION     
            "The Sonus Trunk Group Current table."
    ::= { sonusTrunkGroup 3 }

sonusTrunkGroupCurrentEntry OBJECT-TYPE
    SYNTAX          SonusTrunkGroupCurrentEntry
    MAX-ACCESS      not-accessible
    STATUS          current
    DESCRIPTION     
            "An entry in the Sonus Trunk Group Current table."
    INDEX           { sonusTrunkGroupCurrentIndex }
    ::= { sonusTrunkGroupCurrentTable 1 }

SonusTrunkGroupCurrentEntry ::=
    SEQUENCE {
        sonusTrunkGroupCurrentIndex     Integer32,
        sonusTrunkGroupCurrentInUsage   PerfCurrentCount,
        sonusTrunkGroupCurrentOutUsage  PerfCurrentCount,
        sonusTrunkGroupCurrentInCalls   PerfCurrentCount,
        sonusTrunkGroupCurrentOutCalls  PerfCurrentCount,
        sonusTrunkGroupCurrentInCallAttempts    PerfCurrentCount,
        sonusTrunkGroupCurrentOutCallAttempts     PerfCurrentCount,
        sonusTrunkGroupCurrentMaxCompletedCalls       PerfCurrentCount,
        sonusTrunkGroupCurrentCallSetupTime   PerfCurrentCount,
        sonusTrunkGroupCurrentCallSetups PerfCurrentCount,
        sonusTrunkGroupCurrentInCallFailNoRoutes        PerfCurrentCount,
        sonusTrunkGroupCurrentInCallFailNoResources           PerfCurrentCount,
        sonusTrunkGroupCurrentInCallFailNoService         PerfCurrentCount,
        sonusTrunkGroupCurrentInCallFailInvalidCall           PerfCurrentCount,
        sonusTrunkGroupCurrentInCallFailNetworkFailure              PerfCurrentCount,
        sonusTrunkGroupCurrentInCallFailProtocolError             PerfCurrentCount,
        sonusTrunkGroupCurrentInCallFailUnspecified           PerfCurrentCount,
        sonusTrunkGroupCurrentOutCallFailNoRoutes         PerfCurrentCount,
        sonusTrunkGroupCurrentOutCallFailNoResources            PerfCurrentCount,
        sonusTrunkGroupCurrentOutCallFailNoService          PerfCurrentCount,
        sonusTrunkGroupCurrentOutCallFailInvalidCall            PerfCurrentCount,
        sonusTrunkGroupCurrentOutCallFailNetworkFailure               PerfCurrentCount,
        sonusTrunkGroupCurrentOutCallFailProtocolError              PerfCurrentCount,
        sonusTrunkGroupCurrentOutCallFailUnspecified            PerfCurrentCount,
        sonusTrunkGroupCurrentRoutingAttempts     PerfCurrentCount,
        sonusTrunkGroupCurrentRoutingFailuresNoCircuits               PerfCurrentCount,
        sonusTrunkGroupCurrentRoutingFailuresSFG        PerfCurrentCount,
        sonusTrunkGroupCurrentRoutingFailuresResv         PerfCurrentCount,
        sonusTrunkGroupCurrentOutTrunkStartTimeout          PerfCurrentCount,
        sonusTrunkGroupCurrentSILC      PerfCurrentCount,
        sonusTrunkGroupCurrentSTRCANT   PerfCurrentCount,
        sonusTrunkGroupCurrentSTRSKIP   PerfCurrentCount,
        sonusTrunkGroupCurrentSKIP      PerfCurrentCount,
        sonusTrunkGroupCurrentCANT      PerfCurrentCount,
        sonusTrunkGroupCurrentCANF      PerfCurrentCount,
        sonusTrunkGroupCurrentACCCANT   PerfCurrentCount,
        sonusTrunkGroupCurrentACCSKIP   PerfCurrentCount,
        sonusTrunkGroupCurrentRouteAttemptsIRR      PerfCurrentCount,
        sonusTrunkGroupCurrentRouteAttemptsSIRR       PerfCurrentCount,
        sonusTrunkGroupCurrentRouteAttemptsORR      PerfCurrentCount,
        sonusTrunkGroupCurrentRouteAttemptsSORR       PerfCurrentCount,
        sonusTrunkGroupCurrentSuccessfulIRR   PerfCurrentCount,
        sonusTrunkGroupCurrentSuccessfulSIRR    PerfCurrentCount,
        sonusTrunkGroupCurrentSuccessfulORR   PerfCurrentCount,
        sonusTrunkGroupCurrentSuccessfulSORR    PerfCurrentCount,
        sonusTrunkGroupCurrentNoUnreservedCiruits         PerfCurrentCount,
        sonusTrunkGroupCurrentInCallNoCircuits      PerfCurrentCount,
        sonusTrunkGroupCurrentInBwUsage PerfCurrentCount,
        sonusTrunkGroupCurrentOutBwUsage PerfCurrentCount,
        sonusTrunkGroupCurrentMaxActiveBwUsage      PerfCurrentCount,
        sonusTrunkGroupCurrentAllocFailBwLimit      PerfCurrentCount,
        sonusTrunkGroupCurrentAllocFailCallLimit        PerfCurrentCount,
        sonusTrunkGroupCurrentAllocFailParentTgLimit            PerfCurrentCount,
        sonusTrunkGroupCurrentCallsWithPktOutage        PerfCurrentCount,
        sonusTrunkGroupCurrentCallsWithPktOutageAtEnd             PerfCurrentCount,
        sonusTrunkGroupCurrentTotalPktOutage    PerfCurrentCount,
        sonusTrunkGroupCurrentMaxPktOutage  PerfCurrentCount,
        sonusTrunkGroupCurrentPodEvents PerfCurrentCount,
        sonusTrunkGroupCurrentPlayoutBufferGood       PerfCurrentCount,
        sonusTrunkGroupCurrentPlayoutBufferAcceptable             PerfCurrentCount,
        sonusTrunkGroupCurrentPlayoutBufferPoor       PerfCurrentCount,
        sonusTrunkGroupCurrentPlayoutBufferUnacceptable               PerfCurrentCount,
        sonusTrunkGroupCurrentNoPsxRoute PerfCurrentCount,
        sonusTrunkGroupCurrentCotInAttempts   PerfCurrentCount,
        sonusTrunkGroupCurrentCotOutAttempts    PerfCurrentCount,
        sonusTrunkGroupCurrentCotSuccess PerfCurrentCount,
        sonusTrunkGroupCurrentCotFailure PerfCurrentCount,
        sonusTrunkGroupCurrentCotAborted PerfCurrentCount,
        sonusTrunkGroupCurrentInGlareBlocked    PerfCurrentCount,
        sonusTrunkGroupCurrentOutGlareBlocked     PerfCurrentCount,
        sonusTrunkGroupCurrentGlareEncountered      PerfCurrentCount,
        sonusTrunkGroupCurrentCallAbandoned   PerfCurrentCount,
        sonusTrunkGroupCurrentCallFailPolicing      PerfCurrentCount,
        sonusTrunkGroupCurrentSIPRegAttempts    PerfCurrentCount,
        sonusTrunkGroupCurrentSIPRegCompletions       PerfCurrentCount,
        sonusTrunkGroupCurrentSIPRegFailPolicing        PerfCurrentCount,
        sonusTrunkGroupCurrentSIPRegFailInternal        PerfCurrentCount,
        sonusTrunkGroupCurrentSIPRegFailOther     PerfCurrentCount,
        sonusTrunkGroupCurrentSecurityFail  PerfCurrentCount,
        sonusTrunkGroupCurrentNonRegistrantCallsFailed              PerfCurrentCount,
        sonusTrunkGroupCurrentNonMatchingSourceIpCallsFailed                    PerfCurrentCount,
        sonusTrunkGroupCurrentInvalidServiceProviderCallsFailed                       PerfCurrentCount,
        sonusTrunkGroupCurrentCallsWithPsxDips      PerfCurrentCount,
        sonusTrunkGroupCurrentTotalPsxDips  PerfCurrentCount,
        sonusTrunkGroupCurrentActiveRegistrations         PerfCurrentCount,
        sonusTrunkGroupCurrentMaximumActiveRegistrations                PerfCurrentCount,
        sonusTrunkGroupCurrentOutCallFailPolicing         PerfCurrentCount,
        sonusTrunkGroupCurrentReferAcceptWithIPTarget             PerfCurrentCount,
        sonusTrunkGroupCurrentReferRejectWithIPTarget             PerfCurrentCount,
        sonusTrunkGroupCurrentReferAcceptWithTNTarget             PerfCurrentCount,
        sonusTrunkGroupCurrentReferRejectWithTNTarget             PerfCurrentCount,
        sonusTrunkGroupCurrent3xxAcceptWithIPTarget           PerfCurrentCount,
        sonusTrunkGroupCurrent3xxRejectWithIPTarget           PerfCurrentCount,
        sonusTrunkGroupCurrent3xxAcceptWithTNTarget           PerfCurrentCount,
        sonusTrunkGroupCurrent3xxRejectWithTNTarget           PerfCurrentCount,
        sonusTrunkGroupCurrentAverageCalls  PerfCurrentCount,
        sonusTrunkGroupCurrentInActiveCalls   PerfCurrentCount,
        sonusTrunkGroupCurrentOutActiveCalls    PerfCurrentCount,
        sonusTrunkGroupCurrentInActiveBwUsage     PerfCurrentCount,
        sonusTrunkGroupCurrentOutActiveBwUsage      PerfCurrentCount,
        sonusTrunkGroupCurrentMaxRoutingAttempts        PerfCurrentCount,
        sonusTrunkGroupCurrentIngressPeakSustainedCallRate                  PerfCurrentCount,
        sonusTrunkGroupCurrentEgressPeakSustainedCallRate                 PerfCurrentCount,
        sonusTrunkGroupCurrentIngressPeakCallBurstSize              PerfCurrentCount,
        sonusTrunkGroupCurrentEgressPeakCallBurstSize             PerfCurrentCount,
        sonusTrunkGroupCurrentPstnPeakInboundUsage          PerfCurrentCount,
        sonusTrunkGroupCurrentPstnPeakOutboundUsage           PerfCurrentCount,
        sonusTrunkGroupCurrentTimePstnPeakInboundUsage              DisplayString,
        sonusTrunkGroupCurrentTimePstnPeakOutboundUsage               DisplayString,
        sonusTrunkGroupCurrentTimeMaxCompletedCalls           DisplayString
    }

sonusTrunkGroupCurrentIndex OBJECT-TYPE
    SYNTAX          Integer32
    MAX-ACCESS      not-accessible
    STATUS          current
    DESCRIPTION     
            "The index into the sonusTgTable."
    ::= { sonusTrunkGroupCurrentEntry 1 }

sonusTrunkGroupCurrentInUsage OBJECT-TYPE
    SYNTAX          PerfCurrentCount
    MAX-ACCESS      read-only
    STATUS          current
    DESCRIPTION     
            "The current usage in the inbound direction for this trunk group
             in seconds.  For PSTN trunk groups usage is defined as the time a 
             trunk is seized to the time it is released.  For Selected IP Trunk
             Groups, usage is defined as the time media bandwidth is activated
             to the time it is deactivated.
             
             Note: This field is applicable to Circuit TGs and Selected-IP TGs,
                   but not Linked-IP TGs."
    ::= { sonusTrunkGroupCurrentEntry 2 }

sonusTrunkGroupCurrentOutUsage OBJECT-TYPE
    SYNTAX          PerfCurrentCount
    MAX-ACCESS      read-only
    STATUS          current
    DESCRIPTION     
            "The current usage in the outbound direction for this trunk group 
             in seconds. For PSTN Trunk Groups, usage is defined as the time a 
             trunk is seized to the time it is released.  For Selected IP Trunk
             Groups, usage is defined as the time media bandwidth is activated
             to the time it is deactivated.
             
             Note: This field is applicable to Circuit TGs and Selected-IP TGs,
                   but not Linked-IP TGs."
    ::= { sonusTrunkGroupCurrentEntry 3 }

sonusTrunkGroupCurrentInCalls OBJECT-TYPE
    SYNTAX          PerfCurrentCount
    MAX-ACCESS      read-only
    STATUS          current
    DESCRIPTION     
            "The current number of completed inbound calls on this trunk 
             group.
             
             Note: This field is applicable to Circuit TGs and Selected-IP TGs,
                   but not Linked-IP TGs."
    ::= { sonusTrunkGroupCurrentEntry 4 }

sonusTrunkGroupCurrentOutCalls OBJECT-TYPE
    SYNTAX          PerfCurrentCount
    MAX-ACCESS      read-only
    STATUS          current
    DESCRIPTION     
            "The current number of completed outbound calls on this trunk
             group.
             
             Note: This field is applicable to Circuit TGs and Selected-IP TGs,
                   but not Linked-IP TGs."
    ::= { sonusTrunkGroupCurrentEntry 5 }

sonusTrunkGroupCurrentInCallAttempts OBJECT-TYPE
    SYNTAX          PerfCurrentCount
    MAX-ACCESS      read-only
    STATUS          current
    DESCRIPTION     
            "The current number of inbound call attempts on this trunk
             group.
             
             Note: This field is applicable to Circuit TGs and Selected-IP TGs,
                   but not Linked-IP TGs."
    ::= { sonusTrunkGroupCurrentEntry 6 }

sonusTrunkGroupCurrentOutCallAttempts OBJECT-TYPE
    SYNTAX          PerfCurrentCount
    MAX-ACCESS      read-only
    STATUS          current
    DESCRIPTION     
            "The current number of outbound call attempts on this trunk
             group.  
             
             Note: This field is applicable to Circuit TGs and Selected-IP TGs,
                   but not Linked-IP TGs."
    ::= { sonusTrunkGroupCurrentEntry 7 }

sonusTrunkGroupCurrentMaxCompletedCalls OBJECT-TYPE
    SYNTAX          PerfCurrentCount
    MAX-ACCESS      read-only
    STATUS          current
    DESCRIPTION     
            "The current maximum number of completed calls in the inbound
             and outbound directions for this trunk group.
             
             Note: This field is applicable to all TG types."
    ::= { sonusTrunkGroupCurrentEntry 8 }

sonusTrunkGroupCurrentCallSetupTime OBJECT-TYPE
    SYNTAX          PerfCurrentCount
    MAX-ACCESS      read-only
    STATUS          current
    DESCRIPTION     
            "The current total call setup time for all completed calls
             in the inbound and outbound directions for this trunk group
             measured in hundredths of a second.  This object can be used 
             as the numerator for calculating average call setup time.
             
             Note: This field is applicable to Circuit TGs and Selected-IP TGs,
                   but not Linked-IP TGs."
    ::= { sonusTrunkGroupCurrentEntry 9 }

sonusTrunkGroupCurrentCallSetups OBJECT-TYPE
    SYNTAX          PerfCurrentCount
    MAX-ACCESS      read-only
    STATUS          current
    DESCRIPTION     
            "The current total number of calls setup but not necessarily
             completed in the inbound and outbound directions for 
             this trunk group.  This object can be used as the denominator
             for calculating average call setup time.
             
             Note: This field is applicable to Circuit TGs and Selected-IP TGs,
                   but not Linked-IP TGs."
    ::= { sonusTrunkGroupCurrentEntry 10 }

sonusTrunkGroupCurrentInCallFailNoRoutes OBJECT-TYPE
    SYNTAX          PerfCurrentCount
    MAX-ACCESS      read-only
    STATUS          current
    DESCRIPTION     
            "The current number of inbound failed calls because there was no
             route available for this trunk group.
             
             Note: This field is applicable to Circuit TGs and Selected-IP TGs,
                   but not Linked-IP TGs."
    ::= { sonusTrunkGroupCurrentEntry 11 }

sonusTrunkGroupCurrentInCallFailNoResources OBJECT-TYPE
    SYNTAX          PerfCurrentCount
    MAX-ACCESS      read-only
    STATUS          current
    DESCRIPTION     
            "The current number of inbound failed calls because there was an
             unavailable resource for this trunk group.
             
             Note: This field is applicable to Circuit TGs and Selected-IP TGs,
                   but not Linked-IP TGs."
    ::= { sonusTrunkGroupCurrentEntry 12 }

sonusTrunkGroupCurrentInCallFailNoService OBJECT-TYPE
    SYNTAX          PerfCurrentCount
    MAX-ACCESS      read-only
    STATUS          current
    DESCRIPTION     
            "The current number of inbound failed calls because there was an
             unavailable service for this trunk group.
             
             Note: This field is applicable to Circuit TGs and Selected-IP TGs,
                   but not Linked-IP TGs."
    ::= { sonusTrunkGroupCurrentEntry 13 }

sonusTrunkGroupCurrentInCallFailInvalidCall OBJECT-TYPE
    SYNTAX          PerfCurrentCount
    MAX-ACCESS      read-only
    STATUS          current
    DESCRIPTION     
            "The current number of inbound failed calls because there was an
             invalid call attempt for this trunk group.
             
             Note: This field is applicable to Circuit TGs and Selected-IP TGs,
                   but not Linked-IP TGs."
    ::= { sonusTrunkGroupCurrentEntry 14 }

sonusTrunkGroupCurrentInCallFailNetworkFailure OBJECT-TYPE
    SYNTAX          PerfCurrentCount
    MAX-ACCESS      read-only
    STATUS          current
    DESCRIPTION     
            "The current number of inbound failed calls because there was a
             network failure for this trunk group.
             
             Note: This field is applicable to Circuit TGs and Selected-IP TGs,
                   but not Linked-IP TGs."
    ::= { sonusTrunkGroupCurrentEntry 15 }

sonusTrunkGroupCurrentInCallFailProtocolError OBJECT-TYPE
    SYNTAX          PerfCurrentCount
    MAX-ACCESS      read-only
    STATUS          current
    DESCRIPTION     
            "The current number of inbound failed calls because there was a
             protocol error for this trunk group.
             
             Note: This field is applicable to Circuit TGs and Selected-IP TGs,
                   but not Linked-IP TGs."
    ::= { sonusTrunkGroupCurrentEntry 16 }

sonusTrunkGroupCurrentInCallFailUnspecified OBJECT-TYPE
    SYNTAX          PerfCurrentCount
    MAX-ACCESS      read-only
    STATUS          current
    DESCRIPTION     
            "The current number of inbound failed calls for an unspecified
             reason for this trunk group.
             
             Note: This field is applicable to Circuit TGs and Selected-IP TGs,
                   but not Linked-IP TGs."
    ::= { sonusTrunkGroupCurrentEntry 17 }

sonusTrunkGroupCurrentOutCallFailNoRoutes OBJECT-TYPE
    SYNTAX          PerfCurrentCount
    MAX-ACCESS      read-only
    STATUS          current
    DESCRIPTION     
            "The current number of outbound failed calls because there was no
             route available for this trunk group.
             
             Note: This field is applicable to Circuit TGs and Selected-IP TGs,
                   but not Linked-IP TGs."
    ::= { sonusTrunkGroupCurrentEntry 18 }

sonusTrunkGroupCurrentOutCallFailNoResources OBJECT-TYPE
    SYNTAX          PerfCurrentCount
    MAX-ACCESS      read-only
    STATUS          current
    DESCRIPTION     
            "The current number of outbound failed calls because there was an
             unavailable resource for this trunk group.
             
             Note: This field is applicable to Circuit TGs and Selected-IP TGs,
                   but not Linked-IP TGs."
    ::= { sonusTrunkGroupCurrentEntry 19 }

sonusTrunkGroupCurrentOutCallFailNoService OBJECT-TYPE
    SYNTAX          PerfCurrentCount
    MAX-ACCESS      read-only
    STATUS          current
    DESCRIPTION     
            "The current number of outbound failed calls because there was an
             unavailable service for this trunk group.
             
             Note: This field is applicable to Circuit TGs and Selected-IP TGs,
                   but not Linked-IP TGs."
    ::= { sonusTrunkGroupCurrentEntry 20 }

sonusTrunkGroupCurrentOutCallFailInvalidCall OBJECT-TYPE
    SYNTAX          PerfCurrentCount
    MAX-ACCESS      read-only
    STATUS          current
    DESCRIPTION     
            "The current number of outbound failed calls because there was an
             invalid call attempt for this trunk group.
             
             Note: This field is applicable to Circuit TGs and Selected-IP TGs,
                   but not Linked-IP TGs."
    ::= { sonusTrunkGroupCurrentEntry 21 }

sonusTrunkGroupCurrentOutCallFailNetworkFailure OBJECT-TYPE
    SYNTAX          PerfCurrentCount
    MAX-ACCESS      read-only
    STATUS          current
    DESCRIPTION     
            "The current number of outbound failed calls because there was a
             network failure for this trunk group.
             
             Note: This field is applicable to Circuit TGs and Selected-IP TGs,
                   but not Linked-IP TGs."
    ::= { sonusTrunkGroupCurrentEntry 22 }

sonusTrunkGroupCurrentOutCallFailProtocolError OBJECT-TYPE
    SYNTAX          PerfCurrentCount
    MAX-ACCESS      read-only
    STATUS          current
    DESCRIPTION     
            "The current number of outbound failed calls because there was a
             protocol error for this trunk group.
             
             Note: This field is applicable to Circuit TGs and Selected-IP TGs,
                   but not Linked-IP TGs."
    ::= { sonusTrunkGroupCurrentEntry 23 }

sonusTrunkGroupCurrentOutCallFailUnspecified OBJECT-TYPE
    SYNTAX          PerfCurrentCount
    MAX-ACCESS      read-only
    STATUS          current
    DESCRIPTION     
            "The current number of outbound failed calls for an unspecified
             reason for this trunk group.
             
             Note: This field is applicable to Circuit TGs and Selected-IP TGs,
                   but not Linked-IP TGs."
    ::= { sonusTrunkGroupCurrentEntry 24 }

sonusTrunkGroupCurrentRoutingAttempts OBJECT-TYPE
    SYNTAX          PerfCurrentCount
    MAX-ACCESS      read-only
    STATUS          current
    DESCRIPTION     
            "The current number of routing attempts for this trunk group.
             
             Note: This field is applicable to all trunk group types."
    ::= { sonusTrunkGroupCurrentEntry 25 }

sonusTrunkGroupCurrentRoutingFailuresNoCircuits OBJECT-TYPE
    SYNTAX          PerfCurrentCount
    MAX-ACCESS      read-only
    STATUS          current
    DESCRIPTION     
            "The current number of routing failures due to no circuits 
             available for this trunk group.
             
             Note: This field is only applicable to Circuit TGs."
    ::= { sonusTrunkGroupCurrentEntry 26 }

sonusTrunkGroupCurrentRoutingFailuresSFG OBJECT-TYPE
    SYNTAX          PerfCurrentCount
    MAX-ACCESS      read-only
    STATUS          current
    DESCRIPTION     
            "The current number of routing failures due to a simulated 
             facility group at its capacity for this trunk group.
             
             Note: This field is only applicable to Circuit TGs."
    ::= { sonusTrunkGroupCurrentEntry 27 }

sonusTrunkGroupCurrentRoutingFailuresResv OBJECT-TYPE
    SYNTAX          PerfCurrentCount
    MAX-ACCESS      read-only
    STATUS          current
    DESCRIPTION     
            "The current number of routing failures due to no un-reserved
             circuits available for this trunk group.
             
             Note: This field is applicable to all Trunk Group types."
    ::= { sonusTrunkGroupCurrentEntry 28 }

sonusTrunkGroupCurrentOutTrunkStartTimeout OBJECT-TYPE
    SYNTAX          PerfCurrentCount
    MAX-ACCESS      read-only
    STATUS          current
    DESCRIPTION     
            "The current number of outgoing trunk start timeouts for this
             trunk group.
             
             Note: This field is only applicable to Circuit TGs."
    ::= { sonusTrunkGroupCurrentEntry 29 }

sonusTrunkGroupCurrentSILC OBJECT-TYPE
    SYNTAX          PerfCurrentCount
    MAX-ACCESS      read-only
    STATUS          current
    DESCRIPTION     
            "The current number of calls cancelled due to SILC for this
             trunk group.
             
             Note: This field is applicable to Circuit TGs and Selected-IP TGs,
                   but not Linked-IP TGs."
    ::= { sonusTrunkGroupCurrentEntry 30 }

sonusTrunkGroupCurrentSTRCANT OBJECT-TYPE
    SYNTAX          PerfCurrentCount
    MAX-ACCESS      read-only
    STATUS          current
    DESCRIPTION     
            "The current number of call cancelled due to STR for this
             trunk group.
             
             Note: This field is applicable to Circuit TGs and Selected-IP TGs,
                   but not Linked-IP TGs."
    ::= { sonusTrunkGroupCurrentEntry 31 }

sonusTrunkGroupCurrentSTRSKIP OBJECT-TYPE
    SYNTAX          PerfCurrentCount
    MAX-ACCESS      read-only
    STATUS          current
    DESCRIPTION     
            "The current number of calls skipped due to STR for this
             trunk group.
             
             Note: This field is applicable to Circuit TGs and Selected-IP TGs,
                   but not Linked-IP TGs."
    ::= { sonusTrunkGroupCurrentEntry 32 }

sonusTrunkGroupCurrentSKIP OBJECT-TYPE
    SYNTAX          PerfCurrentCount
    MAX-ACCESS      read-only
    STATUS          current
    DESCRIPTION     
            "The current number calls skipped due to the SKIP traffic
             control for this trunk group.
             
             Note: This field is applicable to Circuit TGs and Selected-IP TGs,
                   but not Linked-IP TGs."
    ::= { sonusTrunkGroupCurrentEntry 33 }

sonusTrunkGroupCurrentCANT OBJECT-TYPE
    SYNTAX          PerfCurrentCount
    MAX-ACCESS      read-only
    STATUS          current
    DESCRIPTION     
            "The current number of call cancelled due to CANT for this
             trunk group.
             
             Note: This field is applicable to Circuit TGs and Selected-IP TGs,
                   but not Linked-IP TGs."
    ::= { sonusTrunkGroupCurrentEntry 34 }

sonusTrunkGroupCurrentCANF OBJECT-TYPE
    SYNTAX          PerfCurrentCount
    MAX-ACCESS      read-only
    STATUS          current
    DESCRIPTION     
            "The current number of call cancelled due to CANF for this
             trunk group.
             
             Note: This field is applicable to Circuit TGs and Selected-IP TGs,
                   but not Linked-IP TGs."
    ::= { sonusTrunkGroupCurrentEntry 35 }

sonusTrunkGroupCurrentACCCANT OBJECT-TYPE
    SYNTAX          PerfCurrentCount
    MAX-ACCESS      read-only
    STATUS          current
    DESCRIPTION     
            "The current number of calls cancelled due to ACC for this
             trunk group.
             
             Note: This field is applicable to Circuit TGs and Selected-IP TGs,
                   but not Linked-IP TGs."
    ::= { sonusTrunkGroupCurrentEntry 36 }

sonusTrunkGroupCurrentACCSKIP OBJECT-TYPE
    SYNTAX          PerfCurrentCount
    MAX-ACCESS      read-only
    STATUS          current
    DESCRIPTION     
            "The current number of calls skipped due to ACC for this
             trunk group.
             
             Note: This field is applicable to Circuit TGs and Selected-IP TGs,
                   but not Linked-IP TGs."
    ::= { sonusTrunkGroupCurrentEntry 37 }

sonusTrunkGroupCurrentRouteAttemptsIRR OBJECT-TYPE
    SYNTAX          PerfCurrentCount
    MAX-ACCESS      read-only
    STATUS          current
    DESCRIPTION     
            "The current number of reroute attempts due to IRR for this
             trunk group.
             
             Note: This field is applicable to Circuit TGs and Selected-IP TGs,
                   but not Linked-IP TGs."
    ::= { sonusTrunkGroupCurrentEntry 38 }

sonusTrunkGroupCurrentRouteAttemptsSIRR OBJECT-TYPE
    SYNTAX          PerfCurrentCount
    MAX-ACCESS      read-only
    STATUS          current
    DESCRIPTION     
            "The current number of reroute attempts due to SIRR for this
             trunk group.
             
             Note: This field is applicable to Circuit TGs and Selected-IP TGs,
                   but not Linked-IP TGs."
    ::= { sonusTrunkGroupCurrentEntry 39 }

sonusTrunkGroupCurrentRouteAttemptsORR OBJECT-TYPE
    SYNTAX          PerfCurrentCount
    MAX-ACCESS      read-only
    STATUS          current
    DESCRIPTION     
            "The current number of reroute attempts due to ORR for this
             trunk group.
             
             Note: This field is applicable to Circuit TGs and Selected-IP TGs,
                   but not Linked-IP TGs."
    ::= { sonusTrunkGroupCurrentEntry 40 }

sonusTrunkGroupCurrentRouteAttemptsSORR OBJECT-TYPE
    SYNTAX          PerfCurrentCount
    MAX-ACCESS      read-only
    STATUS          current
    DESCRIPTION     
            "The current number of reroute attempts due to SORR for this
             trunk group.
             
             Note: This field is applicable to Circuit TGs and Selected-IP TGs,
                   but not Linked-IP TGs."
    ::= { sonusTrunkGroupCurrentEntry 41 }

sonusTrunkGroupCurrentSuccessfulIRR OBJECT-TYPE
    SYNTAX          PerfCurrentCount
    MAX-ACCESS      read-only
    STATUS          current
    DESCRIPTION     
            "The current number of successful reroutes due to IRR for this
             trunk group.
             
             Note: This field is applicable to Circuit TGs and Selected-IP TGs,
                   but not Linked-IP TGs."
    ::= { sonusTrunkGroupCurrentEntry 42 }

sonusTrunkGroupCurrentSuccessfulSIRR OBJECT-TYPE
    SYNTAX          PerfCurrentCount
    MAX-ACCESS      read-only
    STATUS          current
    DESCRIPTION     
            "The current number of successful reroutes due to SIRR for this
             trunk group.
             
             Note: This field is applicable to Circuit TGs and Selected-IP TGs,
                   but not Linked-IP TGs."
    ::= { sonusTrunkGroupCurrentEntry 43 }

sonusTrunkGroupCurrentSuccessfulORR OBJECT-TYPE
    SYNTAX          PerfCurrentCount
    MAX-ACCESS      read-only
    STATUS          current
    DESCRIPTION     
            "The current number of successful reroutes due to ORR for this
             trunk group.
             
             Note: This field is applicable to Circuit TGs and Selected-IP TGs,
                   but not Linked-IP TGs."
    ::= { sonusTrunkGroupCurrentEntry 44 }

sonusTrunkGroupCurrentSuccessfulSORR OBJECT-TYPE
    SYNTAX          PerfCurrentCount
    MAX-ACCESS      read-only
    STATUS          current
    DESCRIPTION     
            "The current number of successful reroutes due to SORR for this
             trunk group.
             
             Note: This field is applicable to Circuit TGs and Selected-IP TGs,
                   but not Linked-IP TGs."
    ::= { sonusTrunkGroupCurrentEntry 45 }

sonusTrunkGroupCurrentNoUnreservedCiruits OBJECT-TYPE
    SYNTAX          PerfCurrentCount
    MAX-ACCESS      read-only
    STATUS          current
    DESCRIPTION     
            "The current number of calls cancelled due to
             no unreserved circuits on an ingress trunk group.
             
             Note: This field is only applicable to Circuit TGs."
    ::= { sonusTrunkGroupCurrentEntry 46 }

sonusTrunkGroupCurrentInCallNoCircuits OBJECT-TYPE
    SYNTAX          PerfCurrentCount
    MAX-ACCESS      read-only
    STATUS          current
    DESCRIPTION     
            "The current number of calls on an ingress trunk 
             group that were cancelled due to no circuits.
             
             Note: This field is only applicable to Circuit TGs."
    ::= { sonusTrunkGroupCurrentEntry 47 }

sonusTrunkGroupCurrentInBwUsage OBJECT-TYPE
    SYNTAX          PerfCurrentCount
    MAX-ACCESS      read-only
    STATUS          current
    DESCRIPTION     
            "The sum of BW usage (expected data rate in Kbits per second multiplied
             by call duration in seconds) for every inbound call associated with
             this trunk group.
             
             Note: This field is only applicable to IP Trunk Groups."
    ::= { sonusTrunkGroupCurrentEntry 48 }

sonusTrunkGroupCurrentOutBwUsage OBJECT-TYPE
    SYNTAX          PerfCurrentCount
    MAX-ACCESS      read-only
    STATUS          current
    DESCRIPTION     
            "The sum of BW usage (expected data rate in Kbits per second multiplied
             by call duration in seconds) for every outbound call associated with
             this trunk group. 
             
             Note: This field is only applicable to IP Trunk Groups."
    ::= { sonusTrunkGroupCurrentEntry 49 }

sonusTrunkGroupCurrentMaxActiveBwUsage OBJECT-TYPE
    SYNTAX          PerfCurrentCount
    MAX-ACCESS      read-only
    STATUS          current
    DESCRIPTION     
            "The high water mark of BW usage in either direction associated
             with this trunk group. 
             
             Note: This field is only applicable to IP Trunk Groups."
    ::= { sonusTrunkGroupCurrentEntry 50 }

sonusTrunkGroupCurrentAllocFailBwLimit OBJECT-TYPE
    SYNTAX          PerfCurrentCount
    MAX-ACCESS      read-only
    STATUS          current
    DESCRIPTION     
            "The number of BW Requests which fail because the configured bandwidth
             limit (sonusTgIpBandwidthLimit) has been exceeded for this trunk 
             group.
             
             Note: This field is only applicable to IP Trunk Groups."
    ::= { sonusTrunkGroupCurrentEntry 51 }

sonusTrunkGroupCurrentAllocFailCallLimit OBJECT-TYPE
    SYNTAX          PerfCurrentCount
    MAX-ACCESS      read-only
    STATUS          current
    DESCRIPTION     
            "The number of BW Requests which fail because configured call limit
             (sonusTgIpCallLimit)has been exceeded for this trunk group. 
             
             Note: This field is only applicable to IP Trunk Groups."
    ::= { sonusTrunkGroupCurrentEntry 52 }

sonusTrunkGroupCurrentAllocFailParentTgLimit OBJECT-TYPE
    SYNTAX          PerfCurrentCount
    MAX-ACCESS      read-only
    STATUS          current
    DESCRIPTION     
            "The number of BW Requests which fail because a configured call or
             bandwidth limit has been exceeded for one of this trunk group's
             parent trunk groups.  This will only occur when an IP Trunk Group
             hierarchy has been established. 
             
             Note: This field is only applicable to IP Trunk Groups."
    ::= { sonusTrunkGroupCurrentEntry 53 }

sonusTrunkGroupCurrentCallsWithPktOutage OBJECT-TYPE
    SYNTAX          PerfCurrentCount
    MAX-ACCESS      read-only
    STATUS          current
    DESCRIPTION     
            "The number of calls with a maximum packet outage whose duration
             exceeds the configured minimum 
             (sonusTgIpPacketOutageDetectionMinimumDuration) for this trunk group.
             
             Note: This field is only applicable to Selected-IP TGs.  It is not
                   applicable to Linked-IP or Circuit TGs."
    ::= { sonusTrunkGroupCurrentEntry 54 }

sonusTrunkGroupCurrentCallsWithPktOutageAtEnd OBJECT-TYPE
    SYNTAX          PerfCurrentCount
    MAX-ACCESS      read-only
    STATUS          current
    DESCRIPTION     
            "The number of calls whose maximum packet outage occurs at the end
             of the call for this trunk group.  This is an indication that the call
             may have been terminated the because of poor quality. 
             
             Note: This field is only applicable to Selected-IP TGs.  It is not
                   applicable to Linked-IP or Circuit TGs."
    ::= { sonusTrunkGroupCurrentEntry 55 }

sonusTrunkGroupCurrentTotalPktOutage OBJECT-TYPE
    SYNTAX          PerfCurrentCount
    MAX-ACCESS      read-only
    STATUS          current
    DESCRIPTION     
            "The summation of all packet outage durations (in milliseconds) 
             whose duration exceeds the configured minimum 
             (sonusTgIpPacketOutageDetectionMinimumDuration),
             which is experienced during the current performance interval 
             for this trunk group.
             The average packet outage duration can be calculated by dividing
             this field by the number of calls reporting packet outages
             (sonusTrunkGroupCurrentCallsWithPktOutage).
             
             Note: This field is only applicable to Selected-IP TGs.  It is not
                   applicable to Linked-IP or Circuit TGs."
    ::= { sonusTrunkGroupCurrentEntry 56 }

sonusTrunkGroupCurrentMaxPktOutage OBJECT-TYPE
    SYNTAX          PerfCurrentCount
    MAX-ACCESS      read-only
    STATUS          current
    DESCRIPTION     
            "The single longest maximum reported packet outage duration (in milliseconds) 
             experienced during the current performance interval for this trunk group.
             
             Note: This field is only applicable to Selected-IP TGs.  It is not
                   applicable to Linked-IP or Circuit TGs."
    ::= { sonusTrunkGroupCurrentEntry 57 }

sonusTrunkGroupCurrentPodEvents OBJECT-TYPE
    SYNTAX          PerfCurrentCount
    MAX-ACCESS      read-only
    STATUS          current
    DESCRIPTION     
            "The number of Packet Outage Detection (POD) Events detected for this
             trunk group.  A POD event occurs when a configurable number of calls
             (sonusTgIpPacketOutageDetectionMinimumCalls) experience a packet
             outage with duration exceeding a programmable threshold 
             (sonusTgIpPacketOutageDetectionMinimumDuration). 
             
             Note: This field is only applicable to Selected-IP TGs.  It is not
                   applicable to Linked-IP or Circuit TGs."
    ::= { sonusTrunkGroupCurrentEntry 58 }

sonusTrunkGroupCurrentPlayoutBufferGood OBJECT-TYPE
    SYNTAX          PerfCurrentCount
    MAX-ACCESS      read-only
    STATUS          current
    DESCRIPTION     
            "Number of calls with all sub-intervals reporting GOOD playout
             buffer quality for this trunk group.
             
             Note: This field is only applicable to Selected-IP TGs.  It is not
                   applicable to Linked-IP or Circuit TGs."
    ::= { sonusTrunkGroupCurrentEntry 59 }

sonusTrunkGroupCurrentPlayoutBufferAcceptable OBJECT-TYPE
    SYNTAX          PerfCurrentCount
    MAX-ACCESS      read-only
    STATUS          current
    DESCRIPTION     
            "Number of calls with all sub-intervals reporting ACCEPTABLE or
             better playout buffer quality for this trunk group.
             
             Note: This field is only applicable to Selected-IP TGs.  It is not
                   applicable to Linked-IP or Circuit TGs."
    ::= { sonusTrunkGroupCurrentEntry 60 }

sonusTrunkGroupCurrentPlayoutBufferPoor OBJECT-TYPE
    SYNTAX          PerfCurrentCount
    MAX-ACCESS      read-only
    STATUS          current
    DESCRIPTION     
            "Number of calls with all sub-intervals reporting POOR or better
             playout buffer quality for this trunk group.
             
             Note: This field is only applicable to Selected-IP TGs.  It is not
                   applicable to Linked-IP or Circuit TGs."
    ::= { sonusTrunkGroupCurrentEntry 61 }

sonusTrunkGroupCurrentPlayoutBufferUnacceptable OBJECT-TYPE
    SYNTAX          PerfCurrentCount
    MAX-ACCESS      read-only
    STATUS          current
    DESCRIPTION     
            "Number of calls with at least one sub-interval reporting UNACCEPTABLE
             playout buffer quality for this trunk group.
             
             Note: This field is only applicable to Selected-IP TGs.  It is not
                   applicable to Linked-IP or Circuit TGs."
    ::= { sonusTrunkGroupCurrentEntry 62 }

sonusTrunkGroupCurrentNoPsxRoute OBJECT-TYPE
    SYNTAX          PerfCurrentCount
    MAX-ACCESS      read-only
    STATUS          current
    DESCRIPTION     
            "The current number of calls on an ingress trunk 
             group that failed due to no routes returned from
             the PSX.
             
             Note: This field is applicable to Circuit TGs and
                    Selected-IP TGs, but not Linked-IP TGs."
    ::= { sonusTrunkGroupCurrentEntry 63 }

sonusTrunkGroupCurrentCotInAttempts OBJECT-TYPE
    SYNTAX          PerfCurrentCount
    MAX-ACCESS      read-only
    STATUS          current
    DESCRIPTION     
            "The current number of inbound continuity tests attempted.
             
             Note: This field is only applicable to Circuit TGs."
    ::= { sonusTrunkGroupCurrentEntry 64 }

sonusTrunkGroupCurrentCotOutAttempts OBJECT-TYPE
    SYNTAX          PerfCurrentCount
    MAX-ACCESS      read-only
    STATUS          current
    DESCRIPTION     
            "The current number of outbound continuity tests attempted.
             
             Note: This field is only applicable to Circuit TGs."
    ::= { sonusTrunkGroupCurrentEntry 65 }

sonusTrunkGroupCurrentCotSuccess OBJECT-TYPE
    SYNTAX          PerfCurrentCount
    MAX-ACCESS      read-only
    STATUS          current
    DESCRIPTION     
            "The current number of successful continuity tests.
             
             Note: This field is only applicable to Circuit TGs."
    ::= { sonusTrunkGroupCurrentEntry 66 }

sonusTrunkGroupCurrentCotFailure OBJECT-TYPE
    SYNTAX          PerfCurrentCount
    MAX-ACCESS      read-only
    STATUS          current
    DESCRIPTION     
            "The current number of failed a continuity tests.
             
             Note: This field is only applicable to Circuit TGs."
    ::= { sonusTrunkGroupCurrentEntry 67 }

sonusTrunkGroupCurrentCotAborted OBJECT-TYPE
    SYNTAX          PerfCurrentCount
    MAX-ACCESS      read-only
    STATUS          current
    DESCRIPTION     
            "The current number of aborted continuity tests.
             
             Note: This field is only applicable to Circuit TGs."
    ::= { sonusTrunkGroupCurrentEntry 68 }

sonusTrunkGroupCurrentInGlareBlocked OBJECT-TYPE
    SYNTAX          PerfCurrentCount
    MAX-ACCESS      read-only
    STATUS          current
    DESCRIPTION     
            "The current number of ingress calls on a trunk 
             group that were blocked due to glare.
             
             Note: This field is only applicable to Circuit TGs."
    ::= { sonusTrunkGroupCurrentEntry 69 }

sonusTrunkGroupCurrentOutGlareBlocked OBJECT-TYPE
    SYNTAX          PerfCurrentCount
    MAX-ACCESS      read-only
    STATUS          current
    DESCRIPTION     
            "The current number of egress calls on a trunk 
             group that were blocked due to glare.
             
             Note: This field is only applicable to Circuit TGs."
    ::= { sonusTrunkGroupCurrentEntry 70 }

sonusTrunkGroupCurrentGlareEncountered OBJECT-TYPE
    SYNTAX          PerfCurrentCount
    MAX-ACCESS      read-only
    STATUS          current
    DESCRIPTION     
            "The current number of calls on a trunk group
             that encountered glare.
             
             Note: This field is only applicable to Circuit TGs."
    ::= { sonusTrunkGroupCurrentEntry 71 }

sonusTrunkGroupCurrentCallAbandoned OBJECT-TYPE
    SYNTAX          PerfCurrentCount
    MAX-ACCESS      read-only
    STATUS          current
    DESCRIPTION     
            "The current number of calls on a trunk group
             that were abandoned while dialing.
             
             Note: This field is applicable to Circuit TGs and
                    Selected-IP TGs, but not Linked-IP TGs."
    ::= { sonusTrunkGroupCurrentEntry 72 }

sonusTrunkGroupCurrentCallFailPolicing OBJECT-TYPE
    SYNTAX          PerfCurrentCount
    MAX-ACCESS      read-only
    STATUS          current
    DESCRIPTION     
            "The current number of calls on a trunk group
             that failed due to ingress call policing.
             
             Note: This field is applicable to Selected-IP TGs, 
                   but not Linked-IP TGs."
    ::= { sonusTrunkGroupCurrentEntry 73 }

sonusTrunkGroupCurrentSIPRegAttempts OBJECT-TYPE
    SYNTAX          PerfCurrentCount
    MAX-ACCESS      read-only
    STATUS          current
    DESCRIPTION     
            "The current number of SIP registration attempts 
             on a trunk group.
             
             Note: This field is applicable Selected-IP TGs, 
                   but not Linked-IP TGs."
    ::= { sonusTrunkGroupCurrentEntry 74 }

sonusTrunkGroupCurrentSIPRegCompletions OBJECT-TYPE
    SYNTAX          PerfCurrentCount
    MAX-ACCESS      read-only
    STATUS          current
    DESCRIPTION     
            "The current number of SIP registrations that have
             successfully completed on a trunk group.
             
             Note: This field is applicable Selected-IP TGs, 
                   but not Linked-IP TGs."
    ::= { sonusTrunkGroupCurrentEntry 75 }

sonusTrunkGroupCurrentSIPRegFailPolicing OBJECT-TYPE
    SYNTAX          PerfCurrentCount
    MAX-ACCESS      read-only
    STATUS          current
    DESCRIPTION     
            "The current number of SIP registration attempts 
             that failed due to policing on a trunk group.
             
             Note: This field is applicable to Selected-IP TGs, 
                   but not Linked-IP TGs."
    ::= { sonusTrunkGroupCurrentEntry 76 }

sonusTrunkGroupCurrentSIPRegFailInternal OBJECT-TYPE
    SYNTAX          PerfCurrentCount
    MAX-ACCESS      read-only
    STATUS          current
    DESCRIPTION     
            "The current number of SIP registration attempts 
             that failed due to internal conditions (congestion,
             call admission, resources, etc.) on a trunk group.
             
             Note: This field is applicable to Selected-IP TGs, 
                   but not Linked-IP TGs."
    ::= { sonusTrunkGroupCurrentEntry 77 }

sonusTrunkGroupCurrentSIPRegFailOther OBJECT-TYPE
    SYNTAX          PerfCurrentCount
    MAX-ACCESS      read-only
    STATUS          current
    DESCRIPTION     
            "The current number of SIP registration attempts 
             that failed due to other reasons (signaling failures,
             etc.) on a trunk group.
             
             Note: This field is applicable to Selected-IP TGs, 
                   but not Linked-IP TGs."
    ::= { sonusTrunkGroupCurrentEntry 78 }

sonusTrunkGroupCurrentSecurityFail OBJECT-TYPE
    SYNTAX          PerfCurrentCount
    MAX-ACCESS      read-only
    STATUS          current
    DESCRIPTION     
            "The current number of calls that failed due to  
             a mismatch between the peer security and route
             packet service profile security on a trunk group.
             
             Note: This field is applicable to Selected-IP TGs, 
                   but not Linked-IP TGs."
    ::= { sonusTrunkGroupCurrentEntry 79 }

sonusTrunkGroupCurrentNonRegistrantCallsFailed OBJECT-TYPE
    SYNTAX          PerfCurrentCount
    MAX-ACCESS      read-only
    STATUS          current
    DESCRIPTION     
            "The current number of calls that failed due to  
             registration requirement for SIP service group.
             
             Note: This field is applicable to Selected-IP TGs, 
                   but not Linked-IP TGs."
    ::= { sonusTrunkGroupCurrentEntry 80 }

sonusTrunkGroupCurrentNonMatchingSourceIpCallsFailed OBJECT-TYPE
    SYNTAX          PerfCurrentCount
    MAX-ACCESS      read-only
    STATUS          current
    DESCRIPTION     
            "The current number of calls that failed due to  
             mismatched source IP of IAD according to its RCB.
             
             Note: This field is applicable to Selected-IP TGs, 
                   but not Linked-IP TGs."
    ::= { sonusTrunkGroupCurrentEntry 81 }

sonusTrunkGroupCurrentInvalidServiceProviderCallsFailed OBJECT-TYPE
    SYNTAX          PerfCurrentCount
    MAX-ACCESS      read-only
    STATUS          current
    DESCRIPTION     
            "The current number of calls that failed due to  
             mismatched ingress sig port from CP according to RCB.
             
             Note: This field is applicable to Selected-IP TGs, 
                   but not Linked-IP TGs."
    ::= { sonusTrunkGroupCurrentEntry 82 }

sonusTrunkGroupCurrentCallsWithPsxDips OBJECT-TYPE
    SYNTAX          PerfCurrentCount
    MAX-ACCESS      read-only
    STATUS          current
    DESCRIPTION     
            "The current number of calls that made a PSX Dip"
    ::= { sonusTrunkGroupCurrentEntry 83 }

sonusTrunkGroupCurrentTotalPsxDips OBJECT-TYPE
    SYNTAX          PerfCurrentCount
    MAX-ACCESS      read-only
    STATUS          current
    DESCRIPTION     
            "The current number of PSX Dips made."
    ::= { sonusTrunkGroupCurrentEntry 84 }

sonusTrunkGroupCurrentActiveRegistrations OBJECT-TYPE
    SYNTAX          PerfCurrentCount
    MAX-ACCESS      read-only
    STATUS          current
    DESCRIPTION     
            "The current number of active registrations on this trunk group. 
             Note: This field is applicable to only to Selected-IP TGs, 
             but not Linked-IP TGs."
    ::= { sonusTrunkGroupCurrentEntry 85 }

sonusTrunkGroupCurrentMaximumActiveRegistrations OBJECT-TYPE
    SYNTAX          PerfCurrentCount
    MAX-ACCESS      read-only
    STATUS          current
    DESCRIPTION     
            "The current number of maximum active registrations on this trunk group 
             (this is the high-watermark achieved on this TG). 
             Note: This field is applicable to only to Selected-IP TGs,
             but not Linked-IP TGs."
    ::= { sonusTrunkGroupCurrentEntry 86 }

sonusTrunkGroupCurrentOutCallFailPolicing OBJECT-TYPE
    SYNTAX          PerfCurrentCount
    MAX-ACCESS      read-only
    STATUS          current
    DESCRIPTION     
            "The current number of calls on a trunk group
             that failed due to egress call policing.
             
             Note: This field is applicable to Selected-IP TGs, 
                   but not Linked-IP TGs."
    ::= { sonusTrunkGroupCurrentEntry 87 }

sonusTrunkGroupCurrentReferAcceptWithIPTarget OBJECT-TYPE
    SYNTAX          PerfCurrentCount
    MAX-ACCESS      read-only
    STATUS          current
    DESCRIPTION     
            "The current number of Refer accepted with target type IP on this trunk
             group."
    ::= { sonusTrunkGroupCurrentEntry 88 }

sonusTrunkGroupCurrentReferRejectWithIPTarget OBJECT-TYPE
    SYNTAX          PerfCurrentCount
    MAX-ACCESS      read-only
    STATUS          current
    DESCRIPTION     
            "The current number of Refer rejected with target type IP on this trunk
             group."
    ::= { sonusTrunkGroupCurrentEntry 89 }

sonusTrunkGroupCurrentReferAcceptWithTNTarget OBJECT-TYPE
    SYNTAX          PerfCurrentCount
    MAX-ACCESS      read-only
    STATUS          current
    DESCRIPTION     
            "The current number of REFER accepted with target type TN on this trunk
             group."
    ::= { sonusTrunkGroupCurrentEntry 90 }

sonusTrunkGroupCurrentReferRejectWithTNTarget OBJECT-TYPE
    SYNTAX          PerfCurrentCount
    MAX-ACCESS      read-only
    STATUS          current
    DESCRIPTION     
            "The current number of REFER rejected with target type TN on this trunk
             group."
    ::= { sonusTrunkGroupCurrentEntry 91 }

sonusTrunkGroupCurrent3xxAcceptWithIPTarget OBJECT-TYPE
    SYNTAX          PerfCurrentCount
    MAX-ACCESS      read-only
    STATUS          current
    DESCRIPTION     
            "The current number of 3xx accepted with target type IP on this trunk
             group."
    ::= { sonusTrunkGroupCurrentEntry 92 }

sonusTrunkGroupCurrent3xxRejectWithIPTarget OBJECT-TYPE
    SYNTAX          PerfCurrentCount
    MAX-ACCESS      read-only
    STATUS          current
    DESCRIPTION     
            "The current number of 3xx rejected with target type IP on this trunk
             group."
    ::= { sonusTrunkGroupCurrentEntry 93 }

sonusTrunkGroupCurrent3xxAcceptWithTNTarget OBJECT-TYPE
    SYNTAX          PerfCurrentCount
    MAX-ACCESS      read-only
    STATUS          current
    DESCRIPTION     
            "The current number of 3xx accepted with target type TN on this trunk
             group."
    ::= { sonusTrunkGroupCurrentEntry 94 }

sonusTrunkGroupCurrent3xxRejectWithTNTarget OBJECT-TYPE
    SYNTAX          PerfCurrentCount
    MAX-ACCESS      read-only
    STATUS          current
    DESCRIPTION     
            "The current number of 3xx rejected with target type IP on this trunk
             group."
    ::= { sonusTrunkGroupCurrentEntry 95 }

sonusTrunkGroupCurrentAverageCalls OBJECT-TYPE
    SYNTAX          PerfCurrentCount
    MAX-ACCESS      read-only
    STATUS          current
    DESCRIPTION     
            "The current average usage for this trunk group
             in seconds.  For PSTN trunk groups usage is defined as the time a 
             trunk is seized to the time it is released.  For Selected IP Trunk
             Groups, usage is defined as the time media bandwidth is activated
             to the time it is deactivated.
             
             Note: This field is applicable to Circuit TGs and Selected-IP TGs,
                   but not Linked-IP TGs."
    ::= { sonusTrunkGroupCurrentEntry 96 }

sonusTrunkGroupCurrentInActiveCalls OBJECT-TYPE
    SYNTAX          PerfCurrentCount
    MAX-ACCESS      read-only
    STATUS          current
    DESCRIPTION     
            "The current number of incoming calls on this trunk group
             at that instant. It includes calls being establishing and 
             already established calls at the given point of time.
             
             Note: This field is applicable to Circuit TGs, Selected-IP TGs,
             and Linked-IP TGs. For Linked-IP TGs, it is the sum of active 
             inbound calls on all its Selected-IP TGs. This field will be 
             shown as zero(0) when there are no active calls on that TG."
    ::= { sonusTrunkGroupCurrentEntry 97 }

sonusTrunkGroupCurrentOutActiveCalls OBJECT-TYPE
    SYNTAX          PerfCurrentCount
    MAX-ACCESS      read-only
    STATUS          current
    DESCRIPTION     
            "The current number of outgoing calls on this trunk group
             at that instant. It includes calls being establishing and 
             already established calls at the given point of time.
             
             Note: This field is applicable to Circuit TGs, Selected-IP TGs,
             and Linked-IP TGs. For Linked-IP TGs it is the sum of active 
             outbound calls on its Selected-IP TGs. This fields will be   
             shown as zero(0) when there are no active calls on that TG."
    ::= { sonusTrunkGroupCurrentEntry 98 }

sonusTrunkGroupCurrentInActiveBwUsage OBJECT-TYPE
    SYNTAX          PerfCurrentCount
    MAX-ACCESS      read-only
    STATUS          current
    DESCRIPTION     
            "The current active BW usage (expressed in Kbits per second) for 
             active inbound sessions at that time on a trunk group.
             
             Note: This field is applicable to both IPLINKED and IPSELECTED TGs. 
             For IPLINKED TGs, it is the sum of In active bandwidth usage on all 
             its IPSELECTED TGs. This stat will be shown as zero(0) when there 
             are no active calls on this TG."
    ::= { sonusTrunkGroupCurrentEntry 99 }

sonusTrunkGroupCurrentOutActiveBwUsage OBJECT-TYPE
    SYNTAX          PerfCurrentCount
    MAX-ACCESS      read-only
    STATUS          current
    DESCRIPTION     
            "The current active BW usage (expressed in Kbits per second) for 
             active outbound sessions at that time on a trunk group.
             
             Note: This field is applicable to both IPLINKED and IPSELECTED TGs. 
             For IPLINKED TGs, it is the sum of In active bandwidth usage on all 
             its IPSELECTED TGs. This stat will be shown as zero(0) when there 
             are no active calls on this TG."
    ::= { sonusTrunkGroupCurrentEntry 100 }

sonusTrunkGroupCurrentMaxRoutingAttempts OBJECT-TYPE
    SYNTAX          PerfCurrentCount
    MAX-ACCESS      read-only
    STATUS          current
    DESCRIPTION     
            "It is the peak routing attempts on a trunk group. Peak routing attempts
             is reported as the high water mark of routing attempts reached on a TG 
             at a given point of time. Note that this is applicable only for outbound
             call attempts.
             
              Note: This field is applicable to all trunk group types."
    ::= { sonusTrunkGroupCurrentEntry 101 }

sonusTrunkGroupCurrentIngressPeakSustainedCallRate OBJECT-TYPE
    SYNTAX          PerfCurrentCount
    MAX-ACCESS      read-only
    STATUS          current
    DESCRIPTION     
            "The peak number of inbound calls / sec that were successfully handled.
             
             Note: This field is applicable to all trunk group types."
    ::= { sonusTrunkGroupCurrentEntry 102 }

sonusTrunkGroupCurrentEgressPeakSustainedCallRate OBJECT-TYPE
    SYNTAX          PerfCurrentCount
    MAX-ACCESS      read-only
    STATUS          current
    DESCRIPTION     
            "The peak number of outbound calls / sec that were successfully handled.
             
             Note: This field is applicable to all trunk group types."
    ::= { sonusTrunkGroupCurrentEntry 103 }

sonusTrunkGroupCurrentIngressPeakCallBurstSize OBJECT-TYPE
    SYNTAX          PerfCurrentCount
    MAX-ACCESS      read-only
    STATUS          current
    DESCRIPTION     
            "The peak number of inbound calls / sec that were requested on a trunk group, 
             including those that could not be successfully handled.
             
             Note: This field is applicable to all trunk group types."
    ::= { sonusTrunkGroupCurrentEntry 104 }

sonusTrunkGroupCurrentEgressPeakCallBurstSize OBJECT-TYPE
    SYNTAX          PerfCurrentCount
    MAX-ACCESS      read-only
    STATUS          current
    DESCRIPTION     
            "The peak number of outbound calls / sec that were requested on a trunk group, 
             including those that could not be successfully handled.
             
             Note: This field is applicable to all trunk group types."
    ::= { sonusTrunkGroupCurrentEntry 105 }

sonusTrunkGroupCurrentPstnPeakInboundUsage OBJECT-TYPE
    SYNTAX          PerfCurrentCount
    MAX-ACCESS      read-only
    STATUS          current
    DESCRIPTION     
            "The current  peak number of circuit usage in the inbound
             directions. 
             Note: This field is applicable to only PSTN types."
    ::= { sonusTrunkGroupCurrentEntry 106 }

sonusTrunkGroupCurrentPstnPeakOutboundUsage OBJECT-TYPE
    SYNTAX          PerfCurrentCount
    MAX-ACCESS      read-only
    STATUS          current
    DESCRIPTION     
            "The current  peak number of circuit usage in the outbound
             directions.
             Note: This field is applicable to only PSTN types."
    ::= { sonusTrunkGroupCurrentEntry 107 }

sonusTrunkGroupCurrentTimePstnPeakInboundUsage OBJECT-TYPE
    SYNTAX          DisplayString (SIZE(0..23))
    MAX-ACCESS      read-only
    STATUS          current
    DESCRIPTION     
            "Time of current  peak number of circuit usage in the inbound
             directions.
             Note: This field is applicable to only PSTN types."
    ::= { sonusTrunkGroupCurrentEntry 108 }

sonusTrunkGroupCurrentTimePstnPeakOutboundUsage OBJECT-TYPE
    SYNTAX          DisplayString (SIZE(0..23))
    MAX-ACCESS      read-only
    STATUS          current
    DESCRIPTION     
            "Time of current  peak number of circuit usage in the outbound
             directions.
             Note: This field is applicable to only PSTN types."
    ::= { sonusTrunkGroupCurrentEntry 109 }

sonusTrunkGroupCurrentTimeMaxCompletedCalls OBJECT-TYPE
    SYNTAX          DisplayString (SIZE(0..23))
    MAX-ACCESS      read-only
    STATUS          current
    DESCRIPTION     
            "Time of current  peak number of circuit usage in both inbound and outbound
             directions.
             Note: This field is applicable to only PSTN types."
    ::= { sonusTrunkGroupCurrentEntry 110 }

sonusTrunkGroupIntervalTable OBJECT-TYPE
    SYNTAX          SEQUENCE OF SonusTrunkGroupIntervalEntry
    MAX-ACCESS      not-accessible
    STATUS          current
    DESCRIPTION     
            "The Sonus Trunk Group Interval table."
    ::= { sonusTrunkGroup 4 }

sonusTrunkGroupIntervalEntry OBJECT-TYPE
    SYNTAX          SonusTrunkGroupIntervalEntry
    MAX-ACCESS      not-accessible
    STATUS          current
    DESCRIPTION     
            "An entry in the Sonus Trunk Group Interval table."
    INDEX           { sonusTrunkGroupIntervalIndex, 
                      sonusTrunkGroupIntervalNumber }
    ::= { sonusTrunkGroupIntervalTable 1 }

SonusTrunkGroupIntervalEntry ::=
    SEQUENCE {
        sonusTrunkGroupIntervalIndex    Integer32,
        sonusTrunkGroupIntervalNumber   Integer32,
        sonusTrunkGroupIntervalInUsage  PerfIntervalCount,
        sonusTrunkGroupIntervalOutUsage PerfIntervalCount,
        sonusTrunkGroupIntervalInCalls  PerfIntervalCount,
        sonusTrunkGroupIntervalOutCalls PerfIntervalCount,
        sonusTrunkGroupIntervalInCallAttempts     PerfIntervalCount,
        sonusTrunkGroupIntervalOutCallAttempts      PerfIntervalCount,
        sonusTrunkGroupIntervalMaxCompletedCalls        PerfIntervalCount,
        sonusTrunkGroupIntervalCallSetupTime    PerfIntervalCount,
        sonusTrunkGroupIntervalCallSetups PerfIntervalCount,
        sonusTrunkGroupIntervalInCallFailNoRoutes         PerfIntervalCount,
        sonusTrunkGroupIntervalInCallFailNoResources            PerfIntervalCount,
        sonusTrunkGroupIntervalInCallFailNoService          PerfIntervalCount,
        sonusTrunkGroupIntervalInCallFailInvalidCall            PerfIntervalCount,
        sonusTrunkGroupIntervalInCallFailNetworkFailure               PerfIntervalCount,
        sonusTrunkGroupIntervalInCallFailProtocolError              PerfIntervalCount,
        sonusTrunkGroupIntervalInCallFailUnspecified            PerfIntervalCount,
        sonusTrunkGroupIntervalOutCallFailNoRoutes          PerfIntervalCount,
        sonusTrunkGroupIntervalOutCallFailNoResources             PerfIntervalCount,
        sonusTrunkGroupIntervalOutCallFailNoService           PerfIntervalCount,
        sonusTrunkGroupIntervalOutCallFailInvalidCall             PerfIntervalCount,
        sonusTrunkGroupIntervalOutCallFailNetworkFailure                PerfIntervalCount,
        sonusTrunkGroupIntervalOutCallFailProtocolError               PerfIntervalCount,
        sonusTrunkGroupIntervalOutCallFailUnspecified             PerfIntervalCount,
        sonusTrunkGroupIntervalTime     TimeTicks,
        sonusTrunkGroupIntervalValidData TruthValue,
        sonusTrunkGroupIntervalRoutingAttempts      PerfIntervalCount,
        sonusTrunkGroupIntervalRoutingFailuresNoCircuits                PerfIntervalCount,
        sonusTrunkGroupIntervalRoutingFailuresSFG         PerfIntervalCount,
        sonusTrunkGroupIntervalRoutingFailuresResv          PerfIntervalCount,
        sonusTrunkGroupIntervalOutTrunkStartTimeout           PerfIntervalCount,
        sonusTrunkGroupIntervalSILC     PerfIntervalCount,
        sonusTrunkGroupIntervalSTRCANT  PerfIntervalCount,
        sonusTrunkGroupIntervalSTRSKIP  PerfIntervalCount,
        sonusTrunkGroupIntervalSKIP     PerfIntervalCount,
        sonusTrunkGroupIntervalCANT     PerfIntervalCount,
        sonusTrunkGroupIntervalCANF     PerfIntervalCount,
        sonusTrunkGroupIntervalACCCANT  PerfIntervalCount,
        sonusTrunkGroupIntervalACCSKIP  PerfIntervalCount,
        sonusTrunkGroupIntervalRouteAttemptsIRR       PerfIntervalCount,
        sonusTrunkGroupIntervalRouteAttemptsSIRR        PerfIntervalCount,
        sonusTrunkGroupIntervalRouteAttemptsORR       PerfIntervalCount,
        sonusTrunkGroupIntervalRouteAttemptsSORR        PerfIntervalCount,
        sonusTrunkGroupIntervalSuccessfulIRR    PerfIntervalCount,
        sonusTrunkGroupIntervalSuccessfulSIRR     PerfIntervalCount,
        sonusTrunkGroupIntervalSuccessfulORR    PerfIntervalCount,
        sonusTrunkGroupIntervalSuccessfulSORR     PerfIntervalCount,
        sonusTrunkGroupIntervalNoUnreservedCircuits           PerfIntervalCount,
        sonusTrunkGroupIntervalInCallNoCircuits       PerfIntervalCount,
        sonusTrunkGroupIntervalInBwUsage PerfIntervalCount,
        sonusTrunkGroupIntervalOutBwUsage PerfIntervalCount,
        sonusTrunkGroupIntervalMaxActiveBwUsage       PerfIntervalCount,
        sonusTrunkGroupIntervalAllocFailBwLimit       PerfIntervalCount,
        sonusTrunkGroupIntervalAllocFailCallLimit         PerfIntervalCount,
        sonusTrunkGroupIntervalAllocFailParentTgLimit             PerfIntervalCount,
        sonusTrunkGroupIntervalCallsWithPktOutage         PerfIntervalCount,
        sonusTrunkGroupIntervalCallsWithPktOutageAtEnd              PerfIntervalCount,
        sonusTrunkGroupIntervalTotalPktOutage     PerfIntervalCount,
        sonusTrunkGroupIntervalMaxPktOutage   PerfIntervalCount,
        sonusTrunkGroupIntervalPodEvents PerfIntervalCount,
        sonusTrunkGroupIntervalPlayoutBufferGood        PerfIntervalCount,
        sonusTrunkGroupIntervalPlayoutBufferAcceptable              PerfIntervalCount,
        sonusTrunkGroupIntervalPlayoutBufferPoor        PerfIntervalCount,
        sonusTrunkGroupIntervalPlayoutBufferUnacceptable                PerfIntervalCount,
        sonusTrunkGroupIntervalNoPsxRoute PerfIntervalCount,
        sonusTrunkGroupIntervalCotInAttempts    PerfIntervalCount,
        sonusTrunkGroupIntervalCotOutAttempts     PerfIntervalCount,
        sonusTrunkGroupIntervalCotSuccess PerfIntervalCount,
        sonusTrunkGroupIntervalCotFailure PerfIntervalCount,
        sonusTrunkGroupIntervalCotAborted PerfIntervalCount,
        sonusTrunkGroupIntervalInGlareBlocked     PerfIntervalCount,
        sonusTrunkGroupIntervalOutGlareBlocked      PerfIntervalCount,
        sonusTrunkGroupIntervalGlareEncountered       PerfIntervalCount,
        sonusTrunkGroupIntervalCallAbandoned    PerfIntervalCount,
        sonusTrunkGroupIntervalCallFailPolicing       PerfIntervalCount,
        sonusTrunkGroupIntervalSIPRegAttempts     PerfIntervalCount,
        sonusTrunkGroupIntervalSIPRegCompletions        PerfIntervalCount,
        sonusTrunkGroupIntervalSIPRegFailPolicing         PerfIntervalCount,
        sonusTrunkGroupIntervalSIPRegFailInternal         PerfIntervalCount,
        sonusTrunkGroupIntervalSIPRegFailOther      PerfIntervalCount,
        sonusTrunkGroupIntervalSecurityFail   PerfIntervalCount,
        sonusTrunkGroupIntervalNonRegistrantCallsFailed               PerfIntervalCount,
        sonusTrunkGroupIntervalNonMatchingSourceIpCallsFailed                     PerfIntervalCount,
        sonusTrunkGroupIntervalInvalidServiceProviderCallsFailed                        PerfIntervalCount,
        sonusTrunkGroupIntervalCallsWithPsxDips       PerfIntervalCount,
        sonusTrunkGroupIntervalTotalPsxDips   PerfIntervalCount,
        sonusTrunkGroupIntervalActiveRegistrations          PerfIntervalCount,
        sonusTrunkGroupIntervalMaximumActiveRegistrations                 PerfIntervalCount,
        sonusTrunkGroupIntervalOutCallFailPolicing          PerfIntervalCount,
        sonusTrunkGroupIntervalReferAcceptWithIPTarget              PerfIntervalCount,
        sonusTrunkGroupIntervalReferRejectWithIPTarget              PerfIntervalCount,
        sonusTrunkGroupIntervalReferAcceptWithTNTarget              PerfIntervalCount,
        sonusTrunkGroupIntervalReferRejectWithTNTarget              PerfIntervalCount,
        sonusTrunkGroupInterval3xxAcceptWithIPTarget            PerfIntervalCount,
        sonusTrunkGroupInterval3xxRejectWithIPTarget            PerfIntervalCount,
        sonusTrunkGroupInterval3xxAcceptWithTNTarget            PerfIntervalCount,
        sonusTrunkGroupInterval3xxRejectWithTNTarget            PerfIntervalCount,
        sonusTrunkGroupIntervalAverageCalls   PerfIntervalCount,
        sonusTrunkGroupIntervalInActiveCalls    PerfIntervalCount,
        sonusTrunkGroupIntervalOutActiveCalls     PerfIntervalCount,
        sonusTrunkGroupIntervalInActiveBwUsage      PerfIntervalCount,
        sonusTrunkGroupIntervalOutActiveBwUsage       PerfIntervalCount,
        sonusTrunkGroupIntervalMaxRoutingAttempts         PerfIntervalCount,
        sonusTrunkGroupIntervalIngressPeakSustainedCallRate                   PerfIntervalCount,
        sonusTrunkGroupIntervalEgressPeakSustainedCallRate                  PerfIntervalCount,
        sonusTrunkGroupIntervalIngressPeakCallBurstSize               PerfIntervalCount,
        sonusTrunkGroupIntervalEgressPeakCallBurstSize              PerfIntervalCount,
        sonusTrunkGroupIntervalPstnPeakInboundUsage           PerfIntervalCount,
        sonusTrunkGroupIntervalPstnPeakOutboundUsage            PerfIntervalCount,
        sonusTrunkGroupIntervalTimePstnPeakInboundUsage               DisplayString,
        sonusTrunkGroupIntervalTimePstnPeakOutboundUsage                DisplayString,
        sonusTrunkGroupIntervalTimeMaxCompletedCalls            DisplayString
    }

sonusTrunkGroupIntervalIndex OBJECT-TYPE
    SYNTAX          Integer32
    MAX-ACCESS      not-accessible
    STATUS          current
    DESCRIPTION     
            "The index into the sonusTgTable."
    ::= { sonusTrunkGroupIntervalEntry 1 }

sonusTrunkGroupIntervalNumber OBJECT-TYPE
    SYNTAX          Integer32 (1..288)
    MAX-ACCESS      not-accessible
    STATUS          current
    DESCRIPTION     
            "A number between 1 and 288, which identifies the
             interval for which the set of statistics is available.
             The interval identified by 1 is the most recently
             completed interval,
             and the interval identified
             by N is the interval immediately preceding the
             one identified
             by N-1."
    ::= { sonusTrunkGroupIntervalEntry 2 }

sonusTrunkGroupIntervalInUsage OBJECT-TYPE
    SYNTAX          PerfIntervalCount
    MAX-ACCESS      read-only
    STATUS          current
    DESCRIPTION     
            "The usage in the inbound direction for this trunk group for
             the specified interval.  For PSTN trunk groups usage is defined
             as the time a trunk is seized to the time it is released.  For
             Selected IP Trunk Groups usage is defined as the time media
             bandwidth is activated to the time it is deactivated.
             
             Note: This field is applicable to Circuit TGs and Selected-IP TGs,
                   but not Linked-IP TGs."
    ::= { sonusTrunkGroupIntervalEntry 3 }

sonusTrunkGroupIntervalOutUsage OBJECT-TYPE
    SYNTAX          PerfIntervalCount
    MAX-ACCESS      read-only
    STATUS          current
    DESCRIPTION     
            "The usage in the outbound direction for this trunk group for
             the specified interval.  For PSTN trunk groups usage is defined
             as the time a trunk is seized to the time it is released.  For
             Selected IP Trunk Groups usage is defined as the time media
             bandwidth is activated to the time it is deactivated.
             
             Note: This field is applicable to Circuit TGs and Selected-IP TGs,
                   but not Linked-IP TGs."
    ::= { sonusTrunkGroupIntervalEntry 4 }

sonusTrunkGroupIntervalInCalls OBJECT-TYPE
    SYNTAX          PerfIntervalCount
    MAX-ACCESS      read-only
    STATUS          current
    DESCRIPTION     
            "The number of completed inbound calls on this trunk
             group for the specified interval.
             
             Note: This field is applicable to Circuit TGs and Selected-IP TGs,
                   but not Linked-IP TGs."
    ::= { sonusTrunkGroupIntervalEntry 5 }

sonusTrunkGroupIntervalOutCalls OBJECT-TYPE
    SYNTAX          PerfIntervalCount
    MAX-ACCESS      read-only
    STATUS          current
    DESCRIPTION     
            "The number of completed outbound calls on this trunk
             group for the specified interval.
             
             Note: This field is applicable to Circuit TGs and Selected-IP TGs,
                   but not Linked-IP TGs."
    ::= { sonusTrunkGroupIntervalEntry 6 }

sonusTrunkGroupIntervalInCallAttempts OBJECT-TYPE
    SYNTAX          PerfIntervalCount
    MAX-ACCESS      read-only
    STATUS          current
    DESCRIPTION     
            "The number of inbound call attempts on this trunk
             group for the specified interval.
             
             Note: This field is applicable to Circuit TGs and Selected-IP TGs,
                   but not Linked-IP TGs."
    ::= { sonusTrunkGroupIntervalEntry 7 }

sonusTrunkGroupIntervalOutCallAttempts OBJECT-TYPE
    SYNTAX          PerfIntervalCount
    MAX-ACCESS      read-only
    STATUS          current
    DESCRIPTION     
            "The number of outbound call attempts on this trunk
             group for the specified interval.  
             
             Note: This field is applicable to Circuit TGs and Selected-IP TGs,
                   but not Linked-IP TGs."
    ::= { sonusTrunkGroupIntervalEntry 8 }

sonusTrunkGroupIntervalMaxCompletedCalls OBJECT-TYPE
    SYNTAX          PerfIntervalCount
    MAX-ACCESS      read-only
    STATUS          current
    DESCRIPTION     
            "The maximum number of completed calls
             in the inbound and outbound direction for this trunk group
             for the specified interval.
             
             Note: This field is applicable to all TG types."
    ::= { sonusTrunkGroupIntervalEntry 9 }

sonusTrunkGroupIntervalCallSetupTime OBJECT-TYPE
    SYNTAX          PerfIntervalCount
    MAX-ACCESS      read-only
    STATUS          current
    DESCRIPTION     
            "The total call setup time for all completed calls
             in the inbound and outbound directions for this trunk group
             for the specified interval measured in hundredths of a second.
             This object can be used as the numerator for calculating 
             average call setup time.
             
             Note: This field is applicable to Circuit TGs and Selected-IP TGs,
                   but not Linked-IP TGs."
    ::= { sonusTrunkGroupIntervalEntry 10 }

sonusTrunkGroupIntervalCallSetups OBJECT-TYPE
    SYNTAX          PerfIntervalCount
    MAX-ACCESS      read-only
    STATUS          current
    DESCRIPTION     
            "The total number of calls setup but not necessarily
             completed in the inbound and outbound directions for 
             this trunk group for the specified interval.  This object 
             can be used as the denominator for calculating average 
             call setup time.
             
             Note: This field is applicable to Circuit TGs and Selected-IP TGs,
                   but not Linked-IP TGs."
    ::= { sonusTrunkGroupIntervalEntry 11 }

sonusTrunkGroupIntervalInCallFailNoRoutes OBJECT-TYPE
    SYNTAX          PerfIntervalCount
    MAX-ACCESS      read-only
    STATUS          current
    DESCRIPTION     
            "The number of inbound failed calls because there was no
             route available for this trunk group for the specified 
             interval.
             
             Note: This field is applicable to Circuit TGs and Selected-IP TGs,
                   but not Linked-IP TGs."
    ::= { sonusTrunkGroupIntervalEntry 12 }

sonusTrunkGroupIntervalInCallFailNoResources OBJECT-TYPE
    SYNTAX          PerfIntervalCount
    MAX-ACCESS      read-only
    STATUS          current
    DESCRIPTION     
            "The number of inbound failed calls because there was an
             unavailable resource for this trunk group for the 
             specified interval.
             
             Note: This field is applicable to Circuit TGs and Selected-IP TGs,
                   but not Linked-IP TGs."
    ::= { sonusTrunkGroupIntervalEntry 13 }

sonusTrunkGroupIntervalInCallFailNoService OBJECT-TYPE
    SYNTAX          PerfIntervalCount
    MAX-ACCESS      read-only
    STATUS          current
    DESCRIPTION     
            "The number of inbound failed calls because there was an
             unavailable service for this trunk group for the 
             specified interval.
             
             Note: This field is applicable to Circuit TGs and Selected-IP TGs,
                   but not Linked-IP TGs."
    ::= { sonusTrunkGroupIntervalEntry 14 }

sonusTrunkGroupIntervalInCallFailInvalidCall OBJECT-TYPE
    SYNTAX          PerfIntervalCount
    MAX-ACCESS      read-only
    STATUS          current
    DESCRIPTION     
            "The number of inbound failed calls because there was an
             invalid call attempt for this trunk group for the 
             specified interval.
             
             Note: This field is applicable to Circuit TGs and Selected-IP TGs,
                   but not Linked-IP TGs."
    ::= { sonusTrunkGroupIntervalEntry 15 }

sonusTrunkGroupIntervalInCallFailNetworkFailure OBJECT-TYPE
    SYNTAX          PerfIntervalCount
    MAX-ACCESS      read-only
    STATUS          current
    DESCRIPTION     
            "The number of inbound failed calls because there was a
             network failure for this trunk group for the specified 
             interval.
             
             Note: This field is applicable to Circuit TGs and Selected-IP TGs,
                   but not Linked-IP TGs."
    ::= { sonusTrunkGroupIntervalEntry 16 }

sonusTrunkGroupIntervalInCallFailProtocolError OBJECT-TYPE
    SYNTAX          PerfIntervalCount
    MAX-ACCESS      read-only
    STATUS          current
    DESCRIPTION     
            "The number of inbound failed calls because there was a
             protocol error for this trunk group for the specified 
             interval.
             
             Note: This field is applicable to Circuit TGs and Selected-IP TGs,
                   but not Linked-IP TGs."
    ::= { sonusTrunkGroupIntervalEntry 17 }

sonusTrunkGroupIntervalInCallFailUnspecified OBJECT-TYPE
    SYNTAX          PerfIntervalCount
    MAX-ACCESS      read-only
    STATUS          current
    DESCRIPTION     
            "The number of inbound failed calls for an unspecified
             reason for this trunk group for the specified interval.
             
             Note: This field is applicable to Circuit TGs and Selected-IP TGs,
                   but not Linked-IP TGs."
    ::= { sonusTrunkGroupIntervalEntry 18 }

sonusTrunkGroupIntervalOutCallFailNoRoutes OBJECT-TYPE
    SYNTAX          PerfIntervalCount
    MAX-ACCESS      read-only
    STATUS          current
    DESCRIPTION     
            "The number of outbound failed calls because there was no
             route available for this trunk group for the specified 
             interval.
             
             Note: This field is applicable to Circuit TGs and Selected-IP TGs,
                   but not Linked-IP TGs."
    ::= { sonusTrunkGroupIntervalEntry 19 }

sonusTrunkGroupIntervalOutCallFailNoResources OBJECT-TYPE
    SYNTAX          PerfIntervalCount
    MAX-ACCESS      read-only
    STATUS          current
    DESCRIPTION     
            "The number of outbound failed calls because there was an
             unavailable resource for this trunk group for the 
             specified interval.
             
             Note: This field is applicable to Circuit TGs and Selected-IP TGs,
                   but not Linked-IP TGs."
    ::= { sonusTrunkGroupIntervalEntry 20 }

sonusTrunkGroupIntervalOutCallFailNoService OBJECT-TYPE
    SYNTAX          PerfIntervalCount
    MAX-ACCESS      read-only
    STATUS          current
    DESCRIPTION     
            "The number of outbound failed calls because there was an
             unavailable service for this trunk group for the 
             specified interval.
             
             Note: This field is applicable to Circuit TGs and Selected-IP TGs,
                   but not Linked-IP TGs."
    ::= { sonusTrunkGroupIntervalEntry 21 }

sonusTrunkGroupIntervalOutCallFailInvalidCall OBJECT-TYPE
    SYNTAX          PerfIntervalCount
    MAX-ACCESS      read-only
    STATUS          current
    DESCRIPTION     
            "The number of outbound failed calls because there was an
             invalid call attempt for this trunk group for the 
             specified interval.
             
             Note: This field is applicable to Circuit TGs and Selected-IP TGs,
                   but not Linked-IP TGs."
    ::= { sonusTrunkGroupIntervalEntry 22 }

sonusTrunkGroupIntervalOutCallFailNetworkFailure OBJECT-TYPE
    SYNTAX          PerfIntervalCount
    MAX-ACCESS      read-only
    STATUS          current
    DESCRIPTION     
            "The number of outbound failed calls because there was a
             network failure for this trunk group for the specified 
             interval.
             
             Note: This field is applicable to Circuit TGs and Selected-IP TGs,
                   but not Linked-IP TGs."
    ::= { sonusTrunkGroupIntervalEntry 23 }

sonusTrunkGroupIntervalOutCallFailProtocolError OBJECT-TYPE
    SYNTAX          PerfIntervalCount
    MAX-ACCESS      read-only
    STATUS          current
    DESCRIPTION     
            "The number of outbound failed calls because there was a
             protocol error for this trunk group for the specified 
             interval.
             
             Note: This field is applicable to Circuit TGs and Selected-IP TGs,
                   but not Linked-IP TGs."
    ::= { sonusTrunkGroupIntervalEntry 24 }

sonusTrunkGroupIntervalOutCallFailUnspecified OBJECT-TYPE
    SYNTAX          PerfIntervalCount
    MAX-ACCESS      read-only
    STATUS          current
    DESCRIPTION     
            "The number of outbound failed calls for an unspecified
             reason for this trunk group for the specified interval.
             
             Note: This field is applicable to Circuit TGs and Selected-IP TGs,
                   but not Linked-IP TGs."
    ::= { sonusTrunkGroupIntervalEntry 25 }

sonusTrunkGroupIntervalTime OBJECT-TYPE
    SYNTAX          TimeTicks
    MAX-ACCESS      read-only
    STATUS          current
    DESCRIPTION     
            "This variable contains the end of interval time
             stamp for the specified interval."
    ::= { sonusTrunkGroupIntervalEntry 26 }

sonusTrunkGroupIntervalValidData OBJECT-TYPE
    SYNTAX          TruthValue
    MAX-ACCESS      read-only
    STATUS          current
    DESCRIPTION     
            "This variable indicates if the data for this
             interval is valid."
    ::= { sonusTrunkGroupIntervalEntry 27 }

sonusTrunkGroupIntervalRoutingAttempts OBJECT-TYPE
    SYNTAX          PerfIntervalCount
    MAX-ACCESS      read-only
    STATUS          current
    DESCRIPTION     
            "The number of routing attempts for this trunk group
             for the specified interval.
             
             Note: This field is applicable to all trunk group types."
    ::= { sonusTrunkGroupIntervalEntry 28 }

sonusTrunkGroupIntervalRoutingFailuresNoCircuits OBJECT-TYPE
    SYNTAX          PerfIntervalCount
    MAX-ACCESS      read-only
    STATUS          current
    DESCRIPTION     
            "The number of routing failures due to no circuits 
             available for this trunk group for the specified interval.
             
             Note: This field is only applicable to Circuit TGs."
    ::= { sonusTrunkGroupIntervalEntry 29 }

sonusTrunkGroupIntervalRoutingFailuresSFG OBJECT-TYPE
    SYNTAX          PerfIntervalCount
    MAX-ACCESS      read-only
    STATUS          current
    DESCRIPTION     
            "The number of routing failures due to a simulated 
             facility group at its capacity for this trunk group
             for the specified interval.
             
             Note: This field is only applicable to Circuit TGs."
    ::= { sonusTrunkGroupIntervalEntry 30 }

sonusTrunkGroupIntervalRoutingFailuresResv OBJECT-TYPE
    SYNTAX          PerfIntervalCount
    MAX-ACCESS      read-only
    STATUS          current
    DESCRIPTION     
            "The number of routing failures due to no un-reserved
             circuits for this trunk group for the specified interval.
             
             Note: This field is applicable to all Trunk Group types."
    ::= { sonusTrunkGroupIntervalEntry 31 }

sonusTrunkGroupIntervalOutTrunkStartTimeout OBJECT-TYPE
    SYNTAX          PerfIntervalCount
    MAX-ACCESS      read-only
    STATUS          current
    DESCRIPTION     
            "The number of outgoing trunk start timeouts for this
             trunk group for the specified interval.
             
             Note: This field is only applicable to Circuit TGs."
    ::= { sonusTrunkGroupIntervalEntry 32 }

sonusTrunkGroupIntervalSILC OBJECT-TYPE
    SYNTAX          PerfIntervalCount
    MAX-ACCESS      read-only
    STATUS          current
    DESCRIPTION     
            "The number of calls cancelled due to SILC for this
             trunk group for the specified interval.
             
             Note: This field is applicable to Circuit TGs and Selected-IP TGs,
                   but not Linked-IP TGs."
    ::= { sonusTrunkGroupIntervalEntry 33 }

sonusTrunkGroupIntervalSTRCANT OBJECT-TYPE
    SYNTAX          PerfIntervalCount
    MAX-ACCESS      read-only
    STATUS          current
    DESCRIPTION     
            "The number of calls cancelled due to STR for this trunk group
             for the specified interval.
             
              Note: This field is applicable to Circuit TGs and Selected-IP TGs,
                    but not Linked-IP TGs."
    ::= { sonusTrunkGroupIntervalEntry 34 }

sonusTrunkGroupIntervalSTRSKIP OBJECT-TYPE
    SYNTAX          PerfIntervalCount
    MAX-ACCESS      read-only
    STATUS          current
    DESCRIPTION     
            "The number of calls skipped due to STR for this trunk group
             for the specified interval.
             
             Note: This field is applicable to Circuit TGs and Selected-IP TGs,
                   but not Linked-IP TGs."
    ::= { sonusTrunkGroupIntervalEntry 35 }

sonusTrunkGroupIntervalSKIP OBJECT-TYPE
    SYNTAX          PerfIntervalCount
    MAX-ACCESS      read-only
    STATUS          current
    DESCRIPTION     
            "The number calls skipped due to the SKIP traffic control for
             this trunk group for the specified interval.
             
             Note: This field is applicable to Circuit TGs and Selected-IP TGs,
                   but not Linked-IP TGs."
    ::= { sonusTrunkGroupIntervalEntry 36 }

sonusTrunkGroupIntervalCANT OBJECT-TYPE
    SYNTAX          PerfIntervalCount
    MAX-ACCESS      read-only
    STATUS          current
    DESCRIPTION     
            "The number of calls cancelled due to CANT for this trunk group
             for the specified interval.
             
             Note: This field is applicable to Circuit TGs and Selected-IP TGs,
                   but not Linked-IP TGs."
    ::= { sonusTrunkGroupIntervalEntry 37 }

sonusTrunkGroupIntervalCANF OBJECT-TYPE
    SYNTAX          PerfIntervalCount
    MAX-ACCESS      read-only
    STATUS          current
    DESCRIPTION     
            "The number of calls cancelled due to CANF for this trunk group
             for the specified interval.
             
             Note: This field is applicable to Circuit TGs and Selected-IP TGs,
                   but not Linked-IP TGs."
    ::= { sonusTrunkGroupIntervalEntry 38 }

sonusTrunkGroupIntervalACCCANT OBJECT-TYPE
    SYNTAX          PerfIntervalCount
    MAX-ACCESS      read-only
    STATUS          current
    DESCRIPTION     
            "The number of calls cancelled due to ACC for this trunk group
             for the specified interval.
             
             Note: This field is applicable to Circuit TGs and Selected-IP TGs,
                   but not Linked-IP TGs."
    ::= { sonusTrunkGroupIntervalEntry 39 }

sonusTrunkGroupIntervalACCSKIP OBJECT-TYPE
    SYNTAX          PerfIntervalCount
    MAX-ACCESS      read-only
    STATUS          current
    DESCRIPTION     
            "The number of calls skipped due to ACC for this trunk group
             for the specified interval.
             
             Note: This field is applicable to Circuit TGs and Selected-IP TGs,
                   but not Linked-IP TGs."
    ::= { sonusTrunkGroupIntervalEntry 40 }

sonusTrunkGroupIntervalRouteAttemptsIRR OBJECT-TYPE
    SYNTAX          PerfIntervalCount
    MAX-ACCESS      read-only
    STATUS          current
    DESCRIPTION     
            "The number of reroute attempts due to IRR for this trunk group
             for the specified interval.
             
             Note: This field is applicable to Circuit TGs and Selected-IP TGs,
                   but not Linked-IP TGs."
    ::= { sonusTrunkGroupIntervalEntry 41 }

sonusTrunkGroupIntervalRouteAttemptsSIRR OBJECT-TYPE
    SYNTAX          PerfIntervalCount
    MAX-ACCESS      read-only
    STATUS          current
    DESCRIPTION     
            "The number of reroute attempts due to SIRR for this trunk group
             for the specified interval.
             
             Note: This field is applicable to Circuit TGs and Selected-IP TGs,
                   but not Linked-IP TGs."
    ::= { sonusTrunkGroupIntervalEntry 42 }

sonusTrunkGroupIntervalRouteAttemptsORR OBJECT-TYPE
    SYNTAX          PerfIntervalCount
    MAX-ACCESS      read-only
    STATUS          current
    DESCRIPTION     
            "The number of reroute attempts due to ORR for this trunk group
             for the specified interval.
             
             Note: This field is applicable to Circuit TGs and Selected-IP TGs,
                   but not Linked-IP TGs."
    ::= { sonusTrunkGroupIntervalEntry 43 }

sonusTrunkGroupIntervalRouteAttemptsSORR OBJECT-TYPE
    SYNTAX          PerfIntervalCount
    MAX-ACCESS      read-only
    STATUS          current
    DESCRIPTION     
            "The number of reroute attempts due to SORR for this trunk group
             for the specified interval.
             
             Note: This field is applicable to Circuit TGs and Selected-IP TGs,
                   but not Linked-IP TGs."
    ::= { sonusTrunkGroupIntervalEntry 44 }

sonusTrunkGroupIntervalSuccessfulIRR OBJECT-TYPE
    SYNTAX          PerfIntervalCount
    MAX-ACCESS      read-only
    STATUS          current
    DESCRIPTION     
            "The number of successful reroutes due to IRR for this trunk group
             for the specified interval.
             
             Note: This field is applicable to Circuit TGs and Selected-IP TGs,
                   but not Linked-IP TGs."
    ::= { sonusTrunkGroupIntervalEntry 45 }

sonusTrunkGroupIntervalSuccessfulSIRR OBJECT-TYPE
    SYNTAX          PerfIntervalCount
    MAX-ACCESS      read-only
    STATUS          current
    DESCRIPTION     
            "The number of successful reroutes due to SIRR for this trunk group
             for the specified interval.
             
             Note: This field is applicable to Circuit TGs and Selected-IP TGs,
                   but not Linked-IP TGs."
    ::= { sonusTrunkGroupIntervalEntry 46 }

sonusTrunkGroupIntervalSuccessfulORR OBJECT-TYPE
    SYNTAX          PerfIntervalCount
    MAX-ACCESS      read-only
    STATUS          current
    DESCRIPTION     
            "The number of successful reroutes due to ORR for this trunk group
             for the specified interval.
             
             Note: This field is applicable to Circuit TGs and Selected-IP TGs,
                   but not Linked-IP TGs."
    ::= { sonusTrunkGroupIntervalEntry 47 }

sonusTrunkGroupIntervalSuccessfulSORR OBJECT-TYPE
    SYNTAX          PerfIntervalCount
    MAX-ACCESS      read-only
    STATUS          current
    DESCRIPTION     
            "The number of successful reroutes due to SORR for this trunk group
             for the specified interval.
             
              Note: This field is applicable to Circuit TGs and Selected-IP TGs,
                    but not Linked-IP TGs."
    ::= { sonusTrunkGroupIntervalEntry 48 }

sonusTrunkGroupIntervalNoUnreservedCircuits OBJECT-TYPE
    SYNTAX          PerfIntervalCount
    MAX-ACCESS      read-only
    STATUS          current
    DESCRIPTION     
            "The current number of calls cancelled due to
             no unreserved circuits on an ingress trunk group
             for the specified interval.
             
              Note: This field is only applicable to Circuit TGs."
    ::= { sonusTrunkGroupIntervalEntry 49 }

sonusTrunkGroupIntervalInCallNoCircuits OBJECT-TYPE
    SYNTAX          PerfIntervalCount
    MAX-ACCESS      read-only
    STATUS          current
    DESCRIPTION     
            "The current number of calls on an ingress trunk group
             that were cancelled due to no circuits 
             for the specified interval.
             
              Note: This field is only applicable to Circuit TGs."
    ::= { sonusTrunkGroupIntervalEntry 50 }

sonusTrunkGroupIntervalInBwUsage OBJECT-TYPE
    SYNTAX          PerfIntervalCount
    MAX-ACCESS      read-only
    STATUS          current
    DESCRIPTION     
            "The sum of BW usage (expected data rate in bits per second multiplied
             by call duration in seconds) for every inbound call associated with
             this trunk group for the specified interval. 
             
             Note: This field is only applicable to IP Trunk Groups."
    ::= { sonusTrunkGroupIntervalEntry 51 }

sonusTrunkGroupIntervalOutBwUsage OBJECT-TYPE
    SYNTAX          PerfIntervalCount
    MAX-ACCESS      read-only
    STATUS          current
    DESCRIPTION     
            "The sum of BW usage (expected data rate in bits per second multiplied
             by call duration in seconds) for every outbound call associated with
             this trunk group for the specified interval.
             
             Note: This field is only applicable to IP Trunk Groups."
    ::= { sonusTrunkGroupIntervalEntry 52 }

sonusTrunkGroupIntervalMaxActiveBwUsage OBJECT-TYPE
    SYNTAX          PerfIntervalCount
    MAX-ACCESS      read-only
    STATUS          current
    DESCRIPTION     
            "The high water mark of BW usage in either direction associated
             with this trunk group for the specified interval.
             
             Note: This field is only applicable to IP Trunk Groups."
    ::= { sonusTrunkGroupIntervalEntry 53 }

sonusTrunkGroupIntervalAllocFailBwLimit OBJECT-TYPE
    SYNTAX          PerfIntervalCount
    MAX-ACCESS      read-only
    STATUS          current
    DESCRIPTION     
            "The number of BW Requests which fail because the configured bandwidth
             limit (sonusTgIpBandwidthLimit) has been exceeded for this trunk 
             group for the specified interval.
             
             Note: This field is only applicable to IP Trunk Groups."
    ::= { sonusTrunkGroupIntervalEntry 54 }

sonusTrunkGroupIntervalAllocFailCallLimit OBJECT-TYPE
    SYNTAX          PerfIntervalCount
    MAX-ACCESS      read-only
    STATUS          current
    DESCRIPTION     
            "The number of BW Requests which fail because configured call limit
             (sonusTgIpCallLimit)has been exceeded for this trunk group for the 
             specified interval. 
             
             Note: This field is only applicable to IP Trunk Groups."
    ::= { sonusTrunkGroupIntervalEntry 55 }

sonusTrunkGroupIntervalAllocFailParentTgLimit OBJECT-TYPE
    SYNTAX          PerfIntervalCount
    MAX-ACCESS      read-only
    STATUS          current
    DESCRIPTION     
            "The number of BW Requests which fail because a configured call or
             bandwidth limit has been exceeded for one of this trunk group's
             parent trunk groups for the specified interval.  This will only
             occur when an IP Trunk Group hierarchy has been established. 
             
             Note: This field is only applicable to IP Trunk Groups."
    ::= { sonusTrunkGroupIntervalEntry 56 }

sonusTrunkGroupIntervalCallsWithPktOutage OBJECT-TYPE
    SYNTAX          PerfIntervalCount
    MAX-ACCESS      read-only
    STATUS          current
    DESCRIPTION     
            "The number of calls with a maximum packet outage whose duration
             exceeds the configured minimum 
             (sonusTgIpPacketOutageDetectionMinimumDuration) for this trunk group
             for the specified interval.
             
             Note: This field is only applicable to Selected-IP TGs.  It is not
                   applicable to Linked-IP or Circuit TGs."
    ::= { sonusTrunkGroupIntervalEntry 57 }

sonusTrunkGroupIntervalCallsWithPktOutageAtEnd OBJECT-TYPE
    SYNTAX          PerfIntervalCount
    MAX-ACCESS      read-only
    STATUS          current
    DESCRIPTION     
            "The number of calls whose maximum packet outage occurs at the end
             of the call for this trunk group for the specified interval.  This is 
             an indication that the call
             may have been terminated the because of poor quality. 
             
             Note: This field is only applicable to Selected-IP TGs.  It is not
                   applicable to Linked-IP or Circuit TGs."
    ::= { sonusTrunkGroupIntervalEntry 58 }

sonusTrunkGroupIntervalTotalPktOutage OBJECT-TYPE
    SYNTAX          PerfIntervalCount
    MAX-ACCESS      read-only
    STATUS          current
    DESCRIPTION     
            "The summation of packet outage durations (in milliseconds) 
             whose duration exceeds the configured minimum 
             (sonusTgIpPacketOutageDetectionMinimumDuration),
             which is reported during the specified performance interval.
             The average packet outage duration can be calculated by dividing
             this field by the number of calls reporting packet outages
             (sonusTrunkGroupCurrentCallsWithPktOutage).
             
             Note: This field is only applicable to Selected-IP TGs.  It is not
                   applicable to Linked-IP or Circuit TGs."
    ::= { sonusTrunkGroupIntervalEntry 59 }

sonusTrunkGroupIntervalMaxPktOutage OBJECT-TYPE
    SYNTAX          PerfIntervalCount
    MAX-ACCESS      read-only
    STATUS          current
    DESCRIPTION     
            "The single longest maximum reported packet outage duration (in  milliseconds) 
             experienced during the specified performance interval for this
             trunk group.
             
             Note: This field is only applicable to Selected-IP TGs.  It is not
                   applicable to Linked-IP or Circuit TGs."
    ::= { sonusTrunkGroupIntervalEntry 60 }

sonusTrunkGroupIntervalPodEvents OBJECT-TYPE
    SYNTAX          PerfIntervalCount
    MAX-ACCESS      read-only
    STATUS          current
    DESCRIPTION     
            "The number of Packet Outage Detection (POD) Events detected for this
             trunk group for the specified interval.  A POD event occurs when a 
             configurable number of calls
             (sonusTgIpPacketOutageDetectionMinimumCalls) experience a packet
             outage with duration exceeding a programmable threshold 
             (sonusTgIpPacketOutageDetectionMinimumDuration). 
             
             Note: This field is only applicable to Selected-IP TGs.  It is not
                   applicable to Linked-IP or Circuit TGs."
    ::= { sonusTrunkGroupIntervalEntry 61 }

sonusTrunkGroupIntervalPlayoutBufferGood OBJECT-TYPE
    SYNTAX          PerfIntervalCount
    MAX-ACCESS      read-only
    STATUS          current
    DESCRIPTION     
            "Number of calls with all sub-intervals reporting GOOD playout
             buffer quality for this trunk group for the specified interval.
             
             Note: This field is only applicable to Selected-IP TGs.  It is not
                   applicable to Linked-IP or Circuit TGs."
    ::= { sonusTrunkGroupIntervalEntry 62 }

sonusTrunkGroupIntervalPlayoutBufferAcceptable OBJECT-TYPE
    SYNTAX          PerfIntervalCount
    MAX-ACCESS      read-only
    STATUS          current
    DESCRIPTION     
            "Number of calls with all sub-intervals reporting ACCEPTABLE or
             better playout buffer quality for this trunk group for the specified interval.
             
             Note: This field is only applicable to Selected-IP TGs.  It is not
                   applicable to Linked-IP or Circuit TGs."
    ::= { sonusTrunkGroupIntervalEntry 63 }

sonusTrunkGroupIntervalPlayoutBufferPoor OBJECT-TYPE
    SYNTAX          PerfIntervalCount
    MAX-ACCESS      read-only
    STATUS          current
    DESCRIPTION     
            "Number of calls with all sub-intervals reporting POOR or better
             playout buffer quality for this trunk group for the specified interval.
             
             Note: This field is only applicable to Selected-IP TGs.  It is not
                   applicable to Linked-IP or Circuit TGs."
    ::= { sonusTrunkGroupIntervalEntry 64 }

sonusTrunkGroupIntervalPlayoutBufferUnacceptable OBJECT-TYPE
    SYNTAX          PerfIntervalCount
    MAX-ACCESS      read-only
    STATUS          current
    DESCRIPTION     
            "Number of calls with at least one sub-interval reporting UNACCEPTABLE
             playout buffer quality for this trunk group for the specified interval.
             
             Note: This field is only applicable to Selected-IP TGs.  It is not
                   applicable to Linked-IP or Circuit TGs."
    ::= { sonusTrunkGroupIntervalEntry 65 }

sonusTrunkGroupIntervalNoPsxRoute OBJECT-TYPE
    SYNTAX          PerfIntervalCount
    MAX-ACCESS      read-only
    STATUS          current
    DESCRIPTION     
            "The current number of calls on an ingress trunk group
             that failed due to no routes returned from the PSX for
             the specified interval.
             
             Note: This field is applicable to Circuit TGs and
                   Selected-IP TGs, but not Linked-IP TGs."
    ::= { sonusTrunkGroupIntervalEntry 66 }

sonusTrunkGroupIntervalCotInAttempts OBJECT-TYPE
    SYNTAX          PerfIntervalCount
    MAX-ACCESS      read-only
    STATUS          current
    DESCRIPTION     
            "The current number of inbound continuity tests for the 
             specified interval.
             
              Note: This field is only applicable to Circuit TGs."
    ::= { sonusTrunkGroupIntervalEntry 67 }

sonusTrunkGroupIntervalCotOutAttempts OBJECT-TYPE
    SYNTAX          PerfIntervalCount
    MAX-ACCESS      read-only
    STATUS          current
    DESCRIPTION     
            "The current number of outbound continuity tests
             for the specified interval.
             
             Note: This field is only applicable to Circuit TGs."
    ::= { sonusTrunkGroupIntervalEntry 68 }

sonusTrunkGroupIntervalCotSuccess OBJECT-TYPE
    SYNTAX          PerfIntervalCount
    MAX-ACCESS      read-only
    STATUS          current
    DESCRIPTION     
            "The current number of successful continuity tests for the 
             specified interval.
             
              Note: This field is only applicable to Circuit TGs."
    ::= { sonusTrunkGroupIntervalEntry 69 }

sonusTrunkGroupIntervalCotFailure OBJECT-TYPE
    SYNTAX          PerfIntervalCount
    MAX-ACCESS      read-only
    STATUS          current
    DESCRIPTION     
            "The current number of failed continuity test for the 
             specified interval.
             
              Note: This field is only applicable to Circuit TGs."
    ::= { sonusTrunkGroupIntervalEntry 70 }

sonusTrunkGroupIntervalCotAborted OBJECT-TYPE
    SYNTAX          PerfIntervalCount
    MAX-ACCESS      read-only
    STATUS          current
    DESCRIPTION     
            "The current number of aborted continuity tests for the 
             specified interval.
             
              Note: This field is only applicable to Circuit TGs."
    ::= { sonusTrunkGroupIntervalEntry 71 }

sonusTrunkGroupIntervalInGlareBlocked OBJECT-TYPE
    SYNTAX          PerfIntervalCount
    MAX-ACCESS      read-only
    STATUS          current
    DESCRIPTION     
            "The number of ingress calls on a trunk group that
             were blocked due to glare for the specified interval.
             
             Note: This field is only applicable to Circuit TGs."
    ::= { sonusTrunkGroupIntervalEntry 72 }

sonusTrunkGroupIntervalOutGlareBlocked OBJECT-TYPE
    SYNTAX          PerfIntervalCount
    MAX-ACCESS      read-only
    STATUS          current
    DESCRIPTION     
            "The number of egress calls on a trunk group that
             were blocked due to glare for the specified interval.
             
             Note: This field is only applicable to Circuit TGs."
    ::= { sonusTrunkGroupIntervalEntry 73 }

sonusTrunkGroupIntervalGlareEncountered OBJECT-TYPE
    SYNTAX          PerfIntervalCount
    MAX-ACCESS      read-only
    STATUS          current
    DESCRIPTION     
            "The number of calls on a trunk group that encountered glare.
             
             Note: This field is only applicable to Circuit TGs."
    ::= { sonusTrunkGroupIntervalEntry 74 }

sonusTrunkGroupIntervalCallAbandoned OBJECT-TYPE
    SYNTAX          PerfIntervalCount
    MAX-ACCESS      read-only
    STATUS          current
    DESCRIPTION     
            "The current number of calls on a trunk group
             that were abandoned while dialing for the 
             specified interval.
             
             Note: This field is applicable to Circuit TGs and
                    Selected-IP TGs, but not Linked-IP TGs."
    ::= { sonusTrunkGroupIntervalEntry 75 }

sonusTrunkGroupIntervalCallFailPolicing OBJECT-TYPE
    SYNTAX          PerfIntervalCount
    MAX-ACCESS      read-only
    STATUS          current
    DESCRIPTION     
            "The current number of calls on a trunk group
             that failed due to ingress call policing for the 
             specified interval.
             
             Note: This field is applicable to Selected-IP TGs, 
                   but not Linked-IP TGs."
    ::= { sonusTrunkGroupIntervalEntry 76 }

sonusTrunkGroupIntervalSIPRegAttempts OBJECT-TYPE
    SYNTAX          PerfIntervalCount
    MAX-ACCESS      read-only
    STATUS          current
    DESCRIPTION     
            "The current number of SIP registration attempts 
             on a trunk group for the 
             specified interval.
             
             Note: This field is applicable to Selected-IP TGs, 
                   but not Linked-IP TGs."
    ::= { sonusTrunkGroupIntervalEntry 77 }

sonusTrunkGroupIntervalSIPRegCompletions OBJECT-TYPE
    SYNTAX          PerfIntervalCount
    MAX-ACCESS      read-only
    STATUS          current
    DESCRIPTION     
            "The current number of SIP registrations that have
             successfully completed on a trunk group for the 
             specified interval.
             
             Note: This field is applicable to Selected-IP TGs, 
                   but not Linked-IP TGs."
    ::= { sonusTrunkGroupIntervalEntry 78 }

sonusTrunkGroupIntervalSIPRegFailPolicing OBJECT-TYPE
    SYNTAX          PerfIntervalCount
    MAX-ACCESS      read-only
    STATUS          current
    DESCRIPTION     
            "The current number SIP registration attempts 
             that failed due to policing on a trunk group
             for the specified interval.
             
             Note: This field is applicable to Selected-IP TGs, 
                   but not Linked-IP TGs."
    ::= { sonusTrunkGroupIntervalEntry 79 }

sonusTrunkGroupIntervalSIPRegFailInternal OBJECT-TYPE
    SYNTAX          PerfIntervalCount
    MAX-ACCESS      read-only
    STATUS          current
    DESCRIPTION     
            "The current number SIP registration attempts 
             that failed due to other reasons (signaling failures,
             etc.)  on a trunk group
             for the specified interval.
             
             Note: This field is applicable to Selected-IP TGs, 
                   but not Linked-IP TGs."
    ::= { sonusTrunkGroupIntervalEntry 80 }

sonusTrunkGroupIntervalSIPRegFailOther OBJECT-TYPE
    SYNTAX          PerfIntervalCount
    MAX-ACCESS      read-only
    STATUS          current
    DESCRIPTION     
            "The current number SIP registration attempts 
             that failed due to other reasons (signaling failures,
             etc.)  on a trunk group
             for the specified interval.
             
             Note: This field is applicable to Selected-IP TGs, 
                   but not Linked-IP TGs."
    ::= { sonusTrunkGroupIntervalEntry 81 }

sonusTrunkGroupIntervalSecurityFail OBJECT-TYPE
    SYNTAX          PerfIntervalCount
    MAX-ACCESS      read-only
    STATUS          current
    DESCRIPTION     
            "The current number of calls that failed due to  
             a mismatch between the peer security and route
             packet service profile security on a trunk group
             for the specified interval.
             
             Note: This field is applicable to Selected-IP TGs, 
                   but not Linked-IP TGs."
    ::= { sonusTrunkGroupIntervalEntry 82 }

sonusTrunkGroupIntervalNonRegistrantCallsFailed OBJECT-TYPE
    SYNTAX          PerfIntervalCount
    MAX-ACCESS      read-only
    STATUS          current
    DESCRIPTION     
            "The current number of calls that failed due to  
             registration requirement for SIP service group
             for the specified interval.
             
             Note: This field is applicable to Selected-IP TGs, 
                   but not Linked-IP TGs."
    ::= { sonusTrunkGroupIntervalEntry 83 }

sonusTrunkGroupIntervalNonMatchingSourceIpCallsFailed OBJECT-TYPE
    SYNTAX          PerfIntervalCount
    MAX-ACCESS      read-only
    STATUS          current
    DESCRIPTION     
            "The current number of calls that failed due to  
             mismatched source IP of IAD according to its RCB
             for the specified interval.
             
             Note: This field is applicable to Selected-IP TGs, 
                   but not Linked-IP TGs."
    ::= { sonusTrunkGroupIntervalEntry 84 }

sonusTrunkGroupIntervalInvalidServiceProviderCallsFailed OBJECT-TYPE
    SYNTAX          PerfIntervalCount
    MAX-ACCESS      read-only
    STATUS          current
    DESCRIPTION     
            "The current number of calls that failed due to  
             mismatched ingress sig port from CP according to RCB
             for the specified interval.
             
             Note: This field is applicable to Selected-IP TGs, 
                   but not Linked-IP TGs."
    ::= { sonusTrunkGroupIntervalEntry 85 }

sonusTrunkGroupIntervalCallsWithPsxDips OBJECT-TYPE
    SYNTAX          PerfIntervalCount
    MAX-ACCESS      read-only
    STATUS          current
    DESCRIPTION     
            "The number of calls that made a PSX Dip in the interval"
    ::= { sonusTrunkGroupIntervalEntry 86 }

sonusTrunkGroupIntervalTotalPsxDips OBJECT-TYPE
    SYNTAX          PerfIntervalCount
    MAX-ACCESS      read-only
    STATUS          current
    DESCRIPTION     
            "The number of PSX Dips in the interval"
    ::= { sonusTrunkGroupIntervalEntry 87 }

sonusTrunkGroupIntervalActiveRegistrations OBJECT-TYPE
    SYNTAX          PerfIntervalCount
    MAX-ACCESS      read-only
    STATUS          current
    DESCRIPTION     
            "The Interval number of active registrations on this trunk group.
             Note: This field is applicable to only to Selected-IP TGs,
             but not Linked-IP TGs."
    ::= { sonusTrunkGroupIntervalEntry 88 }

sonusTrunkGroupIntervalMaximumActiveRegistrations OBJECT-TYPE
    SYNTAX          PerfIntervalCount
    MAX-ACCESS      read-only
    STATUS          current
    DESCRIPTION     
            "The Interval number of maximum active registrations on this trunk group
             (this is the high-watermark achieved on this TG).
             Note: This field is applicable to only to Selected-IP TGs,
             but not Linked-IP TGs."
    ::= { sonusTrunkGroupIntervalEntry 89 }

sonusTrunkGroupIntervalOutCallFailPolicing OBJECT-TYPE
    SYNTAX          PerfIntervalCount
    MAX-ACCESS      read-only
    STATUS          current
    DESCRIPTION     
            "The current number of calls on a trunk group
             that failed due to egress call policing for the 
             specified interval.
             
             Note: This field is applicable to Selected-IP TGs, 
                   but not Linked-IP TGs."
    ::= { sonusTrunkGroupIntervalEntry 90 }

sonusTrunkGroupIntervalReferAcceptWithIPTarget OBJECT-TYPE
    SYNTAX          PerfIntervalCount
    MAX-ACCESS      read-only
    STATUS          current
    DESCRIPTION     
            "The current number of REFER accepted with target type IP on this trunk
             group."
    ::= { sonusTrunkGroupIntervalEntry 91 }

sonusTrunkGroupIntervalReferRejectWithIPTarget OBJECT-TYPE
    SYNTAX          PerfIntervalCount
    MAX-ACCESS      read-only
    STATUS          current
    DESCRIPTION     
            "The current number of REFER rejected with target type IP on this trunk
             group."
    ::= { sonusTrunkGroupIntervalEntry 92 }

sonusTrunkGroupIntervalReferAcceptWithTNTarget OBJECT-TYPE
    SYNTAX          PerfIntervalCount
    MAX-ACCESS      read-only
    STATUS          current
    DESCRIPTION     
            "The current number of REFER accepted with target type TN on this trunk
             group."
    ::= { sonusTrunkGroupIntervalEntry 93 }

sonusTrunkGroupIntervalReferRejectWithTNTarget OBJECT-TYPE
    SYNTAX          PerfIntervalCount
    MAX-ACCESS      read-only
    STATUS          current
    DESCRIPTION     
            "The current number of REFER rejected with target type TN on this trunk
             group."
    ::= { sonusTrunkGroupIntervalEntry 94 }

sonusTrunkGroupInterval3xxAcceptWithIPTarget OBJECT-TYPE
    SYNTAX          PerfIntervalCount
    MAX-ACCESS      read-only
    STATUS          current
    DESCRIPTION     
            "The current number of 3xx accepted with target type IP on this trunk
             group."
    ::= { sonusTrunkGroupIntervalEntry 95 }

sonusTrunkGroupInterval3xxRejectWithIPTarget OBJECT-TYPE
    SYNTAX          PerfIntervalCount
    MAX-ACCESS      read-only
    STATUS          current
    DESCRIPTION     
            "The current number of 3xx rejected with target type IP on this trunk
             group."
    ::= { sonusTrunkGroupIntervalEntry 96 }

sonusTrunkGroupInterval3xxAcceptWithTNTarget OBJECT-TYPE
    SYNTAX          PerfIntervalCount
    MAX-ACCESS      read-only
    STATUS          current
    DESCRIPTION     
            "The current number of 3xx accepted with target type TN on this trunk
             group."
    ::= { sonusTrunkGroupIntervalEntry 97 }

sonusTrunkGroupInterval3xxRejectWithTNTarget OBJECT-TYPE
    SYNTAX          PerfIntervalCount
    MAX-ACCESS      read-only
    STATUS          current
    DESCRIPTION     
            "The current number of 3xx rejected with target type IP on this trunk
             group."
    ::= { sonusTrunkGroupIntervalEntry 98 }

sonusTrunkGroupIntervalAverageCalls OBJECT-TYPE
    SYNTAX          PerfIntervalCount
    MAX-ACCESS      read-only
    STATUS          current
    DESCRIPTION     
            "The average usage for this trunk group for
             the specified interval.  For PSTN trunk groups usage is defined
             as the time a trunk is seized to the time it is released.  For
             Selected IP Trunk Groups usage is defined as the time media
             bandwidth is activated to the time it is deactivated.
             
             Note: This field is applicable to Circuit TGs and Selected-IP TGs,
                   but not Linked-IP TGs."
    ::= { sonusTrunkGroupIntervalEntry 99 }

sonusTrunkGroupIntervalInActiveCalls OBJECT-TYPE
    SYNTAX          PerfIntervalCount
    MAX-ACCESS      read-only
    STATUS          current
    DESCRIPTION     
            "The number of active incoming sessions at the time of interval rollover from 
             CURRENT stats to INTERVAL stats.
             
             Note: This field will be shown as '0' when there are no active in-coming sessions 
             at the time of interval rollover."
    ::= { sonusTrunkGroupIntervalEntry 100 }

sonusTrunkGroupIntervalOutActiveCalls OBJECT-TYPE
    SYNTAX          PerfIntervalCount
    MAX-ACCESS      read-only
    STATUS          current
    DESCRIPTION     
            "The number of active outgoing sessions at the time of interval rollover from 
             CURRENT stats to INTERVAL stats.
             
             Note: This field will be shown as '0' when there are no active outgoing sessions 
             at the time of interval rollover."
    ::= { sonusTrunkGroupIntervalEntry 101 }

sonusTrunkGroupIntervalInActiveBwUsage OBJECT-TYPE
    SYNTAX          PerfIntervalCount
    MAX-ACCESS      read-only
    STATUS          current
    DESCRIPTION     
            "The amount of bandwidth usage for the active in-coming sessions 
             at the time of interval rollover from CURRENT stats to INTERVAL stats.
             
             Note: This field will be shown as '0' when there are no active 
             in-coming sessions at the time of interval rollover"
    ::= { sonusTrunkGroupIntervalEntry 102 }

sonusTrunkGroupIntervalOutActiveBwUsage OBJECT-TYPE
    SYNTAX          PerfIntervalCount
    MAX-ACCESS      read-only
    STATUS          current
    DESCRIPTION     
            "The amount of bandwidth usage for the active outgoing sessions 
             at the time of interval rollover from CURRENT stats to INTERVAL stats.
             
             Note: This field will be shown as '0' when there are no active 
             outgoing sessions at the time of interval rollover"
    ::= { sonusTrunkGroupIntervalEntry 103 }

sonusTrunkGroupIntervalMaxRoutingAttempts OBJECT-TYPE
    SYNTAX          PerfIntervalCount
    MAX-ACCESS      read-only
    STATUS          current
    DESCRIPTION     
            "The peak routing attempts for this trunk group
             for the specified interval.
             
             Note: This field is applicable to all trunk group types."
    ::= { sonusTrunkGroupIntervalEntry 104 }

sonusTrunkGroupIntervalIngressPeakSustainedCallRate OBJECT-TYPE
    SYNTAX          PerfIntervalCount
    MAX-ACCESS      read-only
    STATUS          current
    DESCRIPTION     
            "The peak number of inbound calls / sec that were successfully handled for the 
             specified interval.
             
             Note: This field is applicable to all trunk group types."
    ::= { sonusTrunkGroupIntervalEntry 105 }

sonusTrunkGroupIntervalEgressPeakSustainedCallRate OBJECT-TYPE
    SYNTAX          PerfIntervalCount
    MAX-ACCESS      read-only
    STATUS          current
    DESCRIPTION     
            "The peak number of outbound calls / sec that were successfully handled for the 
             specified interval.
             
             Note: This field is applicable to all trunk group types."
    ::= { sonusTrunkGroupIntervalEntry 106 }

sonusTrunkGroupIntervalIngressPeakCallBurstSize OBJECT-TYPE
    SYNTAX          PerfIntervalCount
    MAX-ACCESS      read-only
    STATUS          current
    DESCRIPTION     
            "The peak number of inbound calls / sec that were requested on a trunk group, 
             including those that could not be successfully handled for the specified interval.
             
             Note: This field is applicable to all trunk group types."
    ::= { sonusTrunkGroupIntervalEntry 107 }

sonusTrunkGroupIntervalEgressPeakCallBurstSize OBJECT-TYPE
    SYNTAX          PerfIntervalCount
    MAX-ACCESS      read-only
    STATUS          current
    DESCRIPTION     
            "The peak number of outbound calls / sec that were requested on a trunk group, 
             including those that could not be successfully handled for the specified interval.
             
             Note: This field is applicable to all trunk group types."
    ::= { sonusTrunkGroupIntervalEntry 108 }

sonusTrunkGroupIntervalPstnPeakInboundUsage OBJECT-TYPE
    SYNTAX          PerfIntervalCount
    MAX-ACCESS      read-only
    STATUS          current
    DESCRIPTION     
            "The interval  peak number of circuit usage in the inbound
             directions.
                 Note: This field is applicable to only PSTN types."
    ::= { sonusTrunkGroupIntervalEntry 109 }

sonusTrunkGroupIntervalPstnPeakOutboundUsage OBJECT-TYPE
    SYNTAX          PerfIntervalCount
    MAX-ACCESS      read-only
    STATUS          current
    DESCRIPTION     
            "The interval peak number of circuit usage in the outbound
             directions. 
                 Note: This field is applicable to only PSTN types."
    ::= { sonusTrunkGroupIntervalEntry 110 }

sonusTrunkGroupIntervalTimePstnPeakInboundUsage OBJECT-TYPE
    SYNTAX          DisplayString (SIZE(0..23))
    MAX-ACCESS      read-only
    STATUS          current
    DESCRIPTION     
            "Time interval peak number of circuit usage in the inbound
             directions.
             Note: This field is applicable to only PSTN types."
    ::= { sonusTrunkGroupIntervalEntry 111 }

sonusTrunkGroupIntervalTimePstnPeakOutboundUsage OBJECT-TYPE
    SYNTAX          DisplayString (SIZE(0..23))
    MAX-ACCESS      read-only
    STATUS          current
    DESCRIPTION     
            "Time interval peak number of circuit usage in the outbound
             directions.
             Note: This field is applicable to only PSTN types."
    ::= { sonusTrunkGroupIntervalEntry 112 }

sonusTrunkGroupIntervalTimeMaxCompletedCalls OBJECT-TYPE
    SYNTAX          DisplayString (SIZE(0..23))
    MAX-ACCESS      read-only
    STATUS          current
    DESCRIPTION     
            "Time interval peak number of circuit usage in both inbound
             and outbound directions.
             Note: This field is applicable to only PSTN types."
    ::= { sonusTrunkGroupIntervalEntry 113 }

sonusCongestionStatisticsObjects OBJECT IDENTIFIER
    ::= { sonusPerformanceStatisticsObjects 2 }

sonusSysCongestionCurrentTable OBJECT-TYPE
    SYNTAX          SEQUENCE OF SonusSysCongestionCurrentEntry
    MAX-ACCESS      not-accessible
    STATUS          current
    DESCRIPTION     
            "The Sonus System Congestion Current table."
    ::= { sonusCongestionStatisticsObjects 1 }

sonusSysCongestionCurrentEntry OBJECT-TYPE
    SYNTAX          SonusSysCongestionCurrentEntry
    MAX-ACCESS      not-accessible
    STATUS          current
    DESCRIPTION     
            "An entry in the Sonus System Congestion Current table."
    INDEX           { sonusSysCongestionCurrentShelfIndex }
    ::= { sonusSysCongestionCurrentTable 1 }

SonusSysCongestionCurrentEntry ::=
    SEQUENCE {
        sonusSysCongestionCurrentShelfIndex   SonusShelfIndex,
        sonusSysCongestionCurrentMC1Count PerfCurrentCount,
        sonusSysCongestionCurrentMC1TotalTime     PerfCurrentCount,
        sonusSysCongestionCurrentMC2Count PerfCurrentCount,
        sonusSysCongestionCurrentMC2TotalTime     PerfCurrentCount,
        sonusSysCongestionCurrentMC3Count PerfCurrentCount,
        sonusSysCongestionCurrentMC3TotalTime     PerfCurrentCount,
        sonusSysCongestionCurrentOverloadRejects        PerfCurrentCount,
        sonusSysCongestionCurrentAvgCallRate    PerfCurrentCount,
        sonusSysCongestionCurrentPeakCallRate     PerfCurrentCount,
        sonusSysCongestionCurrentDsOverloadRejects          PerfCurrentCount,
        sonusSysCongestionCurrentArrivals PerfCurrentCount,
        sonusSysCongestionCurrentEmergencyCallArrivals              PerfCurrentCount,
        sonusSysCongestionCurrentEmergencyCallRejects             PerfCurrentCount,
        sonusSysCongestionCurrentRegArrivals    PerfCurrentCount,
        sonusSysCongestionCurrentRegRejects   PerfCurrentCount,
        sonusSysCongestionCurrentAvgRegRate   PerfCurrentCount,
        sonusSysCongestionCurrentPeakRegRate    PerfCurrentCount
    }

sonusSysCongestionCurrentShelfIndex OBJECT-TYPE
    SYNTAX          SonusShelfIndex
    MAX-ACCESS      read-only
    STATUS          current
    DESCRIPTION     
            "The index into the sonusSysCongestionCurrentTable."
    ::= { sonusSysCongestionCurrentEntry 1 }

sonusSysCongestionCurrentMC1Count OBJECT-TYPE
    SYNTAX          PerfCurrentCount
    MAX-ACCESS      read-only
    STATUS          current
    DESCRIPTION     
            "The current number of transitions into MC1."
    ::= { sonusSysCongestionCurrentEntry 2 }

sonusSysCongestionCurrentMC1TotalTime OBJECT-TYPE
    SYNTAX          PerfCurrentCount
    MAX-ACCESS      read-only
    STATUS          current
    DESCRIPTION     
            "The current sum of time spent in MC1."
    ::= { sonusSysCongestionCurrentEntry 3 }

sonusSysCongestionCurrentMC2Count OBJECT-TYPE
    SYNTAX          PerfCurrentCount
    MAX-ACCESS      read-only
    STATUS          current
    DESCRIPTION     
            "The current number of transitions into MC2."
    ::= { sonusSysCongestionCurrentEntry 4 }

sonusSysCongestionCurrentMC2TotalTime OBJECT-TYPE
    SYNTAX          PerfCurrentCount
    MAX-ACCESS      read-only
    STATUS          current
    DESCRIPTION     
            "The current sum of time spent in MC2."
    ::= { sonusSysCongestionCurrentEntry 5 }

sonusSysCongestionCurrentMC3Count OBJECT-TYPE
    SYNTAX          PerfCurrentCount
    MAX-ACCESS      read-only
    STATUS          current
    DESCRIPTION     
            "The current number of transitions into MC3."
    ::= { sonusSysCongestionCurrentEntry 6 }

sonusSysCongestionCurrentMC3TotalTime OBJECT-TYPE
    SYNTAX          PerfCurrentCount
    MAX-ACCESS      read-only
    STATUS          current
    DESCRIPTION     
            "The current sum of time spent in MC3."
    ::= { sonusSysCongestionCurrentEntry 7 }

sonusSysCongestionCurrentOverloadRejects OBJECT-TYPE
    SYNTAX          PerfCurrentCount
    MAX-ACCESS      read-only
    STATUS          current
    DESCRIPTION     
            "The current number of calls rejected by NRM due to GSX congestion."
    ::= { sonusSysCongestionCurrentEntry 8 }

sonusSysCongestionCurrentAvgCallRate OBJECT-TYPE
    SYNTAX          PerfCurrentCount
    MAX-ACCESS      read-only
    STATUS          current
    DESCRIPTION     
            "The current system average call arrival rate."
    ::= { sonusSysCongestionCurrentEntry 9 }

sonusSysCongestionCurrentPeakCallRate OBJECT-TYPE
    SYNTAX          PerfCurrentCount
    MAX-ACCESS      read-only
    STATUS          current
    DESCRIPTION     
            "The current system peak call arrival rate."
    ::= { sonusSysCongestionCurrentEntry 10 }

sonusSysCongestionCurrentDsOverloadRejects OBJECT-TYPE
    SYNTAX          PerfCurrentCount
    MAX-ACCESS      read-only
    STATUS          current
    DESCRIPTION     
            "The current number of calls rejected by DS due to PSX congestion."
    ::= { sonusSysCongestionCurrentEntry 11 }

sonusSysCongestionCurrentArrivals OBJECT-TYPE
    SYNTAX          PerfCurrentCount
    MAX-ACCESS      read-only
    STATUS          current
    DESCRIPTION     
            "The current number of call arrivals."
    ::= { sonusSysCongestionCurrentEntry 12 }

sonusSysCongestionCurrentEmergencyCallArrivals OBJECT-TYPE
    SYNTAX          PerfCurrentCount
    MAX-ACCESS      read-only
    STATUS          current
    DESCRIPTION     
            "The current number of SIP emergency calls arrived."
    ::= { sonusSysCongestionCurrentEntry 13 }

sonusSysCongestionCurrentEmergencyCallRejects OBJECT-TYPE
    SYNTAX          PerfCurrentCount
    MAX-ACCESS      read-only
    STATUS          current
    DESCRIPTION     
            "The current number of SIP emergency calls rejected during GSX congestion."
    ::= { sonusSysCongestionCurrentEntry 14 }

sonusSysCongestionCurrentRegArrivals OBJECT-TYPE
    SYNTAX          PerfCurrentCount
    MAX-ACCESS      read-only
    STATUS          current
    DESCRIPTION     
            "The current number of SIP registrations arrived."
    ::= { sonusSysCongestionCurrentEntry 15 }

sonusSysCongestionCurrentRegRejects OBJECT-TYPE
    SYNTAX          PerfCurrentCount
    MAX-ACCESS      read-only
    STATUS          current
    DESCRIPTION     
            "The current number of SIP registrations rejected."
    ::= { sonusSysCongestionCurrentEntry 16 }

sonusSysCongestionCurrentAvgRegRate OBJECT-TYPE
    SYNTAX          PerfCurrentCount
    MAX-ACCESS      read-only
    STATUS          current
    DESCRIPTION     
            "The current average SIP registration arrival rate."
    ::= { sonusSysCongestionCurrentEntry 17 }

sonusSysCongestionCurrentPeakRegRate OBJECT-TYPE
    SYNTAX          PerfCurrentCount
    MAX-ACCESS      read-only
    STATUS          current
    DESCRIPTION     
            "The current peak SIP registration arrival rate."
    ::= { sonusSysCongestionCurrentEntry 18 }

sonusSysCongestionIntervalTable OBJECT-TYPE
    SYNTAX          SEQUENCE OF SonusSysCongestionIntervalEntry
    MAX-ACCESS      not-accessible
    STATUS          current
    DESCRIPTION     
            "The Sonus System Congestion Interval table."
    ::= { sonusCongestionStatisticsObjects 2 }

sonusSysCongestionIntervalEntry OBJECT-TYPE
    SYNTAX          SonusSysCongestionIntervalEntry
    MAX-ACCESS      not-accessible
    STATUS          current
    DESCRIPTION     
            "An entry in the Sonus System Congestion Interval table."
    INDEX           { sonusSysCongestionIntervalShelfIndex, 
                      sonusSysCongestionIntervalNumber }
    ::= { sonusSysCongestionIntervalTable 1 }

SonusSysCongestionIntervalEntry ::=
    SEQUENCE {
        sonusSysCongestionIntervalShelfIndex    SonusShelfIndex,
        sonusSysCongestionIntervalNumber Integer32,
        sonusSysCongestionIntervalTime  TimeTicks,
        sonusSysCongestionIntervalValidData   TruthValue,
        sonusSysCongestionIntervalMC1Count  PerfIntervalCount,
        sonusSysCongestionIntervalMC1TotalTime      PerfIntervalCount,
        sonusSysCongestionIntervalMC2Count  PerfIntervalCount,
        sonusSysCongestionIntervalMC2TotalTime      PerfIntervalCount,
        sonusSysCongestionIntervalMC3Count  PerfIntervalCount,
        sonusSysCongestionIntervalMC3TotalTime      PerfIntervalCount,
        sonusSysCongestionIntervalOverloadRejects         PerfIntervalCount,
        sonusSysCongestionIntervalAvgCallRate     PerfIntervalCount,
        sonusSysCongestionIntervalPeakCallRate      PerfIntervalCount,
        sonusSysCongestionIntervalDsOverloadRejects           PerfIntervalCount,
        sonusSysCongestionIntervalArrivals  PerfIntervalCount,
        sonusSysCongestionIntervalEmergencyCallArrivals               PerfIntervalCount,
        sonusSysCongestionIntervalEmergencyCallRejects              PerfIntervalCount,
        sonusSysCongestionIntervalRegArrivals     PerfIntervalCount,
        sonusSysCongestionIntervalRegRejects    PerfIntervalCount,
        sonusSysCongestionIntervalAvgRegRate    PerfIntervalCount,
        sonusSysCongestionIntervalPeakRegRate     PerfIntervalCount
    }

sonusSysCongestionIntervalShelfIndex OBJECT-TYPE
    SYNTAX          SonusShelfIndex
    MAX-ACCESS      read-only
    STATUS          current
    DESCRIPTION     
            "The index into the sonusSysCongestionIntervalTable."
    ::= { sonusSysCongestionIntervalEntry 1 }

sonusSysCongestionIntervalNumber OBJECT-TYPE
    SYNTAX          Integer32 (1..288)
    MAX-ACCESS      not-accessible
    STATUS          current
    DESCRIPTION     
            "A number between 1 and 288, which identifies the
             interval for which the set of statistics is available.
             The interval identified by 1 is the most recently
             completed interval, and the interval identified
             by N is the interval immediately preceding the
             one identified by N-1."
    ::= { sonusSysCongestionIntervalEntry 2 }

sonusSysCongestionIntervalTime OBJECT-TYPE
    SYNTAX          TimeTicks
    MAX-ACCESS      read-only
    STATUS          current
    DESCRIPTION     
            "This variable contains the end of interval time
             stamp for the specified interval."
    ::= { sonusSysCongestionIntervalEntry 3 }

sonusSysCongestionIntervalValidData OBJECT-TYPE
    SYNTAX          TruthValue
    MAX-ACCESS      read-only
    STATUS          current
    DESCRIPTION     
            "This variable indicates if the data for this
             interval is valid."
    ::= { sonusSysCongestionIntervalEntry 4 }

sonusSysCongestionIntervalMC1Count OBJECT-TYPE
    SYNTAX          PerfIntervalCount
    MAX-ACCESS      read-only
    STATUS          current
    DESCRIPTION     
            "The  number of transitions into MC1."
    ::= { sonusSysCongestionIntervalEntry 5 }

sonusSysCongestionIntervalMC1TotalTime OBJECT-TYPE
    SYNTAX          PerfIntervalCount
    MAX-ACCESS      read-only
    STATUS          current
    DESCRIPTION     
            "The  sum of time spent in MC1."
    ::= { sonusSysCongestionIntervalEntry 6 }

sonusSysCongestionIntervalMC2Count OBJECT-TYPE
    SYNTAX          PerfIntervalCount
    MAX-ACCESS      read-only
    STATUS          current
    DESCRIPTION     
            "The  number of transitions into MC2."
    ::= { sonusSysCongestionIntervalEntry 7 }

sonusSysCongestionIntervalMC2TotalTime OBJECT-TYPE
    SYNTAX          PerfIntervalCount
    MAX-ACCESS      read-only
    STATUS          current
    DESCRIPTION     
            "The  sum of time spent in MC2."
    ::= { sonusSysCongestionIntervalEntry 8 }

sonusSysCongestionIntervalMC3Count OBJECT-TYPE
    SYNTAX          PerfIntervalCount
    MAX-ACCESS      read-only
    STATUS          current
    DESCRIPTION     
            "The  number of transitions into MC3."
    ::= { sonusSysCongestionIntervalEntry 9 }

sonusSysCongestionIntervalMC3TotalTime OBJECT-TYPE
    SYNTAX          PerfIntervalCount
    MAX-ACCESS      read-only
    STATUS          current
    DESCRIPTION     
            "The  sum of time spent in MC3."
    ::= { sonusSysCongestionIntervalEntry 10 }

sonusSysCongestionIntervalOverloadRejects OBJECT-TYPE
    SYNTAX          PerfIntervalCount
    MAX-ACCESS      read-only
    STATUS          current
    DESCRIPTION     
            "The  number of calls rejected by NRM due to GSX congestion."
    ::= { sonusSysCongestionIntervalEntry 11 }

sonusSysCongestionIntervalAvgCallRate OBJECT-TYPE
    SYNTAX          PerfIntervalCount
    MAX-ACCESS      read-only
    STATUS          current
    DESCRIPTION     
            "The  system average call arrival rate."
    ::= { sonusSysCongestionIntervalEntry 12 }

sonusSysCongestionIntervalPeakCallRate OBJECT-TYPE
    SYNTAX          PerfIntervalCount
    MAX-ACCESS      read-only
    STATUS          current
    DESCRIPTION     
            "The  system peak call arrival rate."
    ::= { sonusSysCongestionIntervalEntry 13 }

sonusSysCongestionIntervalDsOverloadRejects OBJECT-TYPE
    SYNTAX          PerfIntervalCount
    MAX-ACCESS      read-only
    STATUS          current
    DESCRIPTION     
            "The  number of calls rejected by DS due to PSX congestion."
    ::= { sonusSysCongestionIntervalEntry 14 }

sonusSysCongestionIntervalArrivals OBJECT-TYPE
    SYNTAX          PerfIntervalCount
    MAX-ACCESS      read-only
    STATUS          current
    DESCRIPTION     
            "The  number of call arrivals."
    ::= { sonusSysCongestionIntervalEntry 15 }

sonusSysCongestionIntervalEmergencyCallArrivals OBJECT-TYPE
    SYNTAX          PerfIntervalCount
    MAX-ACCESS      read-only
    STATUS          current
    DESCRIPTION     
            "The number of SIP emergency calls arrived."
    ::= { sonusSysCongestionIntervalEntry 16 }

sonusSysCongestionIntervalEmergencyCallRejects OBJECT-TYPE
    SYNTAX          PerfIntervalCount
    MAX-ACCESS      read-only
    STATUS          current
    DESCRIPTION     
            "The number of SIP emergency calls rejected during GSX congestion."
    ::= { sonusSysCongestionIntervalEntry 17 }

sonusSysCongestionIntervalRegArrivals OBJECT-TYPE
    SYNTAX          PerfIntervalCount
    MAX-ACCESS      read-only
    STATUS          current
    DESCRIPTION     
            "The number of SIP registrations arrived in an interval."
    ::= { sonusSysCongestionIntervalEntry 18 }

sonusSysCongestionIntervalRegRejects OBJECT-TYPE
    SYNTAX          PerfIntervalCount
    MAX-ACCESS      read-only
    STATUS          current
    DESCRIPTION     
            "The number of SIP registrations rejected in an interval."
    ::= { sonusSysCongestionIntervalEntry 19 }

sonusSysCongestionIntervalAvgRegRate OBJECT-TYPE
    SYNTAX          PerfIntervalCount
    MAX-ACCESS      read-only
    STATUS          current
    DESCRIPTION     
            "The average SIP registration arrival rate in an interval."
    ::= { sonusSysCongestionIntervalEntry 20 }

sonusSysCongestionIntervalPeakRegRate OBJECT-TYPE
    SYNTAX          PerfIntervalCount
    MAX-ACCESS      read-only
    STATUS          current
    DESCRIPTION     
            "The peak SIP registration arrival rate in an interval."
    ::= { sonusSysCongestionIntervalEntry 21 }

sonusServerCongestionCurrentTable OBJECT-TYPE
    SYNTAX          SEQUENCE OF SonusServerCongestionCurrentEntry
    MAX-ACCESS      not-accessible
    STATUS          current
    DESCRIPTION     
            "The Sonus Server Congestion Current table."
    ::= { sonusCongestionStatisticsObjects 3 }

sonusServerCongestionCurrentEntry OBJECT-TYPE
    SYNTAX          SonusServerCongestionCurrentEntry
    MAX-ACCESS      not-accessible
    STATUS          current
    DESCRIPTION     
            "An entry in the Sonus Server Congestion Current table."
    INDEX           { sonusServerCongestionCurrentShelfIndex, 
                      sonusServerCongestionCurrentSlotIndex }
    ::= { sonusServerCongestionCurrentTable 1 }

SonusServerCongestionCurrentEntry ::=
    SEQUENCE {
        sonusServerCongestionCurrentShelfIndex      SonusShelfIndex,
        sonusServerCongestionCurrentSlotIndex     SonusSlotIndex,
        sonusServerCongestionCurrentCongestedCount          PerfCurrentCount,
        sonusServerCongestionCurrentCongestedTotalTime              PerfCurrentCount,
        sonusServerCongestionCurrentOverloadRejects           PerfCurrentCount,
        sonusServerCongestionCurrentAvgCallRate       PerfCurrentCount,
        sonusServerCongestionCurrentPeakCallRate        PerfCurrentCount,
        sonusServerCongestionCurrentArrivals    PerfCurrentCount,
        sonusServerCongestionCurrentEmergencyCallArrivals                 PerfCurrentCount,
        sonusServerCongestionCurrentEmergencyCallRejects                PerfCurrentCount,
        sonusServerCongestionCurrentRegArrivals       PerfCurrentCount,
        sonusServerCongestionCurrentRegRejects      PerfCurrentCount,
        sonusServerCongestionCurrentAvgRegRate      PerfCurrentCount,
        sonusServerCongestionCurrentPeakRegRate       PerfCurrentCount
    }

sonusServerCongestionCurrentShelfIndex OBJECT-TYPE
    SYNTAX          SonusShelfIndex
    MAX-ACCESS      read-only
    STATUS          current
    DESCRIPTION     
            "The shelf index into the sonusServerCongestionCurrentTable."
    ::= { sonusServerCongestionCurrentEntry 1 }

sonusServerCongestionCurrentSlotIndex OBJECT-TYPE
    SYNTAX          SonusSlotIndex
    MAX-ACCESS      read-only
    STATUS          current
    DESCRIPTION     
            "The slot index into the sonusServerCongestionCurrentTable."
    ::= { sonusServerCongestionCurrentEntry 2 }

sonusServerCongestionCurrentCongestedCount OBJECT-TYPE
    SYNTAX          PerfCurrentCount
    MAX-ACCESS      read-only
    STATUS          current
    DESCRIPTION     
            "The current number of transitions into congested state."
    ::= { sonusServerCongestionCurrentEntry 3 }

sonusServerCongestionCurrentCongestedTotalTime OBJECT-TYPE
    SYNTAX          PerfCurrentCount
    MAX-ACCESS      read-only
    STATUS          current
    DESCRIPTION     
            "The current sum of time spent in congested state."
    ::= { sonusServerCongestionCurrentEntry 4 }

sonusServerCongestionCurrentOverloadRejects OBJECT-TYPE
    SYNTAX          PerfCurrentCount
    MAX-ACCESS      read-only
    STATUS          current
    DESCRIPTION     
            "The current number of calls rejected."
    ::= { sonusServerCongestionCurrentEntry 5 }

sonusServerCongestionCurrentAvgCallRate OBJECT-TYPE
    SYNTAX          PerfCurrentCount
    MAX-ACCESS      read-only
    STATUS          current
    DESCRIPTION     
            "The current server average call arrival rate."
    ::= { sonusServerCongestionCurrentEntry 6 }

sonusServerCongestionCurrentPeakCallRate OBJECT-TYPE
    SYNTAX          PerfCurrentCount
    MAX-ACCESS      read-only
    STATUS          current
    DESCRIPTION     
            "The current server peak call arrival rate."
    ::= { sonusServerCongestionCurrentEntry 7 }

sonusServerCongestionCurrentArrivals OBJECT-TYPE
    SYNTAX          PerfCurrentCount
    MAX-ACCESS      read-only
    STATUS          current
    DESCRIPTION     
            "The current number of call arrivals."
    ::= { sonusServerCongestionCurrentEntry 8 }

sonusServerCongestionCurrentEmergencyCallArrivals OBJECT-TYPE
    SYNTAX          PerfCurrentCount
    MAX-ACCESS      read-only
    STATUS          current
    DESCRIPTION     
            "The current number of SIP emergency calls arrived."
    ::= { sonusServerCongestionCurrentEntry 9 }

sonusServerCongestionCurrentEmergencyCallRejects OBJECT-TYPE
    SYNTAX          PerfCurrentCount
    MAX-ACCESS      read-only
    STATUS          current
    DESCRIPTION     
            "The current number of SIP emergency calls rejected during server congestion."
    ::= { sonusServerCongestionCurrentEntry 10 }

sonusServerCongestionCurrentRegArrivals OBJECT-TYPE
    SYNTAX          PerfCurrentCount
    MAX-ACCESS      read-only
    STATUS          current
    DESCRIPTION     
            "The current number of SIP registrations arrived."
    ::= { sonusServerCongestionCurrentEntry 11 }

sonusServerCongestionCurrentRegRejects OBJECT-TYPE
    SYNTAX          PerfCurrentCount
    MAX-ACCESS      read-only
    STATUS          current
    DESCRIPTION     
            "The current number of SIP registrations rejected."
    ::= { sonusServerCongestionCurrentEntry 12 }

sonusServerCongestionCurrentAvgRegRate OBJECT-TYPE
    SYNTAX          PerfCurrentCount
    MAX-ACCESS      read-only
    STATUS          current
    DESCRIPTION     
            "The current average SIP registration arrival rate."
    ::= { sonusServerCongestionCurrentEntry 13 }

sonusServerCongestionCurrentPeakRegRate OBJECT-TYPE
    SYNTAX          PerfCurrentCount
    MAX-ACCESS      read-only
    STATUS          current
    DESCRIPTION     
            "The current peak SIP registration arrival rate."
    ::= { sonusServerCongestionCurrentEntry 14 }

sonusServerCongestionIntervalTable OBJECT-TYPE
    SYNTAX          SEQUENCE OF SonusServerCongestionIntervalEntry
    MAX-ACCESS      not-accessible
    STATUS          current
    DESCRIPTION     
            "The Sonus Server Congestion Interval table."
    ::= { sonusCongestionStatisticsObjects 4 }

sonusServerCongestionIntervalEntry OBJECT-TYPE
    SYNTAX          SonusServerCongestionIntervalEntry
    MAX-ACCESS      not-accessible
    STATUS          current
    DESCRIPTION     
            "An entry in the Sonus Server Congestion Interval table."
    INDEX           { sonusServerCongestionIntervalShelfIndex, 
                      sonusServerCongestionIntervalSlotIndex, 
                      sonusServerCongestionIntervalNumber }
    ::= { sonusServerCongestionIntervalTable 1 }

SonusServerCongestionIntervalEntry ::=
    SEQUENCE {
        sonusServerCongestionIntervalShelfIndex       SonusShelfIndex,
        sonusServerCongestionIntervalSlotIndex      SonusSlotIndex,
        sonusServerCongestionIntervalNumber   Integer32,
        sonusServerCongestionIntervalTime TimeTicks,
        sonusServerCongestionIntervalValidData      TruthValue,
        sonusServerCongestionIntervalCongestedCount           PerfIntervalCount,
        sonusServerCongestionIntervalCongestedTotalTime               PerfIntervalCount,
        sonusServerCongestionIntervalOverloadRejects            PerfIntervalCount,
        sonusServerCongestionIntervalAvgCallRate        PerfIntervalCount,
        sonusServerCongestionIntervalPeakCallRate         PerfIntervalCount,
        sonusServerCongestionIntervalArrivals     PerfIntervalCount,
        sonusServerCongestionIntervalEmergencyCallArrivals                  PerfIntervalCount,
        sonusServerCongestionIntervalEmergencyCallRejects                 PerfIntervalCount,
        sonusServerCongestionIntervalRegArrivals        PerfIntervalCount,
        sonusServerCongestionIntervalRegRejects       PerfIntervalCount,
        sonusServerCongestionIntervalAvgRegRate       PerfIntervalCount,
        sonusServerCongestionIntervalPeakRegRate        PerfIntervalCount
    }

sonusServerCongestionIntervalShelfIndex OBJECT-TYPE
    SYNTAX          SonusShelfIndex
    MAX-ACCESS      read-only
    STATUS          current
    DESCRIPTION     
            "The shelf index into the sonusServerCongestionIntervalTable."
    ::= { sonusServerCongestionIntervalEntry 1 }

sonusServerCongestionIntervalSlotIndex OBJECT-TYPE
    SYNTAX          SonusSlotIndex
    MAX-ACCESS      read-only
    STATUS          current
    DESCRIPTION     
            "The slot index into the sonusServerCongestionIntervalTable."
    ::= { sonusServerCongestionIntervalEntry 2 }

sonusServerCongestionIntervalNumber OBJECT-TYPE
    SYNTAX          Integer32 (1..288)
    MAX-ACCESS      not-accessible
    STATUS          current
    DESCRIPTION     
            "A number between 1 and 288, which identifies the
             interval for which the set of statistics is available.
             The interval identified by 1 is the most recently
             completed interval, and the interval identified
             by N is the interval immediately preceding the
             one identified by N-1."
    ::= { sonusServerCongestionIntervalEntry 3 }

sonusServerCongestionIntervalTime OBJECT-TYPE
    SYNTAX          TimeTicks
    MAX-ACCESS      read-only
    STATUS          current
    DESCRIPTION     
            "This variable contains the end of interval time
             stamp for the specified interval."
    ::= { sonusServerCongestionIntervalEntry 4 }

sonusServerCongestionIntervalValidData OBJECT-TYPE
    SYNTAX          TruthValue
    MAX-ACCESS      read-only
    STATUS          current
    DESCRIPTION     
            "This variable indicates if the data for this
             interval is valid."
    ::= { sonusServerCongestionIntervalEntry 5 }

sonusServerCongestionIntervalCongestedCount OBJECT-TYPE
    SYNTAX          PerfIntervalCount
    MAX-ACCESS      read-only
    STATUS          current
    DESCRIPTION     
            "The current number of transitions into congested state."
    ::= { sonusServerCongestionIntervalEntry 6 }

sonusServerCongestionIntervalCongestedTotalTime OBJECT-TYPE
    SYNTAX          PerfIntervalCount
    MAX-ACCESS      read-only
    STATUS          current
    DESCRIPTION     
            "The current sum of time spent in congested state."
    ::= { sonusServerCongestionIntervalEntry 7 }

sonusServerCongestionIntervalOverloadRejects OBJECT-TYPE
    SYNTAX          PerfIntervalCount
    MAX-ACCESS      read-only
    STATUS          current
    DESCRIPTION     
            "The current number of calls rejected."
    ::= { sonusServerCongestionIntervalEntry 8 }

sonusServerCongestionIntervalAvgCallRate OBJECT-TYPE
    SYNTAX          PerfIntervalCount
    MAX-ACCESS      read-only
    STATUS          current
    DESCRIPTION     
            "The current server average call arrival rate."
    ::= { sonusServerCongestionIntervalEntry 9 }

sonusServerCongestionIntervalPeakCallRate OBJECT-TYPE
    SYNTAX          PerfIntervalCount
    MAX-ACCESS      read-only
    STATUS          current
    DESCRIPTION     
            "The current server peak call arrival rate."
    ::= { sonusServerCongestionIntervalEntry 10 }

sonusServerCongestionIntervalArrivals OBJECT-TYPE
    SYNTAX          PerfIntervalCount
    MAX-ACCESS      read-only
    STATUS          current
    DESCRIPTION     
            "The number of call arrivals."
    ::= { sonusServerCongestionIntervalEntry 11 }

sonusServerCongestionIntervalEmergencyCallArrivals OBJECT-TYPE
    SYNTAX          PerfIntervalCount
    MAX-ACCESS      read-only
    STATUS          current
    DESCRIPTION     
            "The number of SIP emergency calls arrived."
    ::= { sonusServerCongestionIntervalEntry 12 }

sonusServerCongestionIntervalEmergencyCallRejects OBJECT-TYPE
    SYNTAX          PerfIntervalCount
    MAX-ACCESS      read-only
    STATUS          current
    DESCRIPTION     
            "The number of SIP emergency calls rejected during server congestion."
    ::= { sonusServerCongestionIntervalEntry 13 }

sonusServerCongestionIntervalRegArrivals OBJECT-TYPE
    SYNTAX          PerfIntervalCount
    MAX-ACCESS      read-only
    STATUS          current
    DESCRIPTION     
            "The number of SIP registrations arrived in an interval."
    ::= { sonusServerCongestionIntervalEntry 14 }

sonusServerCongestionIntervalRegRejects OBJECT-TYPE
    SYNTAX          PerfIntervalCount
    MAX-ACCESS      read-only
    STATUS          current
    DESCRIPTION     
            "The number of SIP registrations rejected in an interval."
    ::= { sonusServerCongestionIntervalEntry 15 }

sonusServerCongestionIntervalAvgRegRate OBJECT-TYPE
    SYNTAX          PerfIntervalCount
    MAX-ACCESS      read-only
    STATUS          current
    DESCRIPTION     
            "The average SIP registration arrival rate in an interval."
    ::= { sonusServerCongestionIntervalEntry 16 }

sonusServerCongestionIntervalPeakRegRate OBJECT-TYPE
    SYNTAX          PerfIntervalCount
    MAX-ACCESS      read-only
    STATUS          current
    DESCRIPTION     
            "The peak SIP registration arrival rate in an interval."
    ::= { sonusServerCongestionIntervalEntry 17 }

sonusPolicerStatisticsObjects OBJECT IDENTIFIER
    ::= { sonusPerformanceStatisticsObjects 3 }

sonusSysPolicerCurrentTable OBJECT-TYPE
    SYNTAX          SEQUENCE OF SonusSysPolicerCurrentEntry
    MAX-ACCESS      not-accessible
    STATUS          current
    DESCRIPTION     
            "The Sonus System Policer Current table."
    ::= { sonusPolicerStatisticsObjects 1 }

sonusSysPolicerCurrentEntry OBJECT-TYPE
    SYNTAX          SonusSysPolicerCurrentEntry
    MAX-ACCESS      not-accessible
    STATUS          current
    DESCRIPTION     
            "An entry in the Sonus System Policer Current table."
    INDEX           { sonusSysPolicerCurrentShelfIndex }
    ::= { sonusSysPolicerCurrentTable 1 }

SonusSysPolicerCurrentEntry ::=
    SEQUENCE {
        sonusSysPolicerCurrentShelfIndex SonusShelfIndex,
        sonusSysPolicerCurrentWhiteListDiscardPacketCount                 Counter64,
        sonusSysPolicerCurrentWhiteListPeakDiscardRate              PerfCurrentCount,
        sonusSysPolicerCurrentWhiteListMinorAlarmCount              PerfCurrentCount,
        sonusSysPolicerCurrentWhiteListMinorAlarmDuration                 PerfCurrentCount,
        sonusSysPolicerCurrentWhiteListMajorAlarmCount              PerfCurrentCount,
        sonusSysPolicerCurrentWhiteListMajorAlarmDuration                 PerfCurrentCount,
        sonusSysPolicerCurrentBlackListDiscardPacketCount                 Counter64,
        sonusSysPolicerCurrentBlackListPeakDiscardRate              PerfCurrentCount,
        sonusSysPolicerCurrentBlackListMinorAlarmCount              PerfCurrentCount,
        sonusSysPolicerCurrentBlackListMinorAlarmDuration                 PerfCurrentCount,
        sonusSysPolicerCurrentBlackListMajorAlarmCount              PerfCurrentCount,
        sonusSysPolicerCurrentBlackListMajorAlarmDuration                 PerfCurrentCount,
        sonusSysPolicerCurrentDarkGrayListDiscardPacketCount                    Counter64,
        sonusSysPolicerCurrentDarkGrayListAcceptPacketCount                   Counter64,
        sonusSysPolicerCurrentDarkGrayListPeakDiscardRate                 PerfCurrentCount,
        sonusSysPolicerCurrentDarkGrayListMinorAlarmCount                 PerfCurrentCount,
        sonusSysPolicerCurrentDarkGrayListMinorAlarmDuration                    PerfCurrentCount,
        sonusSysPolicerCurrentDarkGrayListMajorAlarmCount                 PerfCurrentCount,
        sonusSysPolicerCurrentDarkGrayListMajorAlarmDuration                    PerfCurrentCount,
        sonusSysPolicerCurrentServerProtectDiscardPacketCount                     Counter64,
        sonusSysPolicerCurrentServerProtectAcceptPacketCount                    Counter64,
        sonusSysPolicerCurrentServerProtectPeakDiscardRate                  PerfCurrentCount,
        sonusSysPolicerCurrentServerProtectMinorAlarmCount                  PerfCurrentCount,
        sonusSysPolicerCurrentServerProtectMinorAlarmDuration                     PerfCurrentCount,
        sonusSysPolicerCurrentServerProtectMajorAlarmCount                  PerfCurrentCount,
        sonusSysPolicerCurrentServerProtectMajorAlarmDuration                     PerfCurrentCount,
        sonusSysPolicerCurrentMediaDiscardPacketCount             Counter64,
        sonusSysPolicerCurrentMediaPeakDiscardRate          PerfCurrentCount,
        sonusSysPolicerCurrentMediaMinorAlarmCount          PerfCurrentCount,
        sonusSysPolicerCurrentMediaMinorAlarmDuration             PerfCurrentCount,
        sonusSysPolicerCurrentMediaMajorAlarmCount          PerfCurrentCount,
        sonusSysPolicerCurrentMediaMajorAlarmDuration             PerfCurrentCount,
        sonusSysPolicerCurrentRogueMediaUnallocatedPortDiscardPacketCount                                 Counter64,
        sonusSysPolicerCurrentRogueMediaUnallocatedPortPeakDiscardRate                              PerfCurrentCount,
        sonusSysPolicerCurrentRogueMediaUnallocatedPortMinorAlarmCount                              PerfCurrentCount,
        sonusSysPolicerCurrentRogueMediaUnallocatedPortMinorAlarmDuration                                 PerfCurrentCount,
        sonusSysPolicerCurrentRogueMediaUnallocatedPortMajorAlarmCount                              PerfCurrentCount,
        sonusSysPolicerCurrentRogueMediaUnallocatedPortMajorAlarmDuration                                 PerfCurrentCount,
        sonusSysPolicerCurrentRogueMediaMidCallBadDestDiscardPacketCount                                Counter64,
        sonusSysPolicerCurrentRogueMediaMidCallBadDestPeakDiscardRate                             PerfCurrentCount,
        sonusSysPolicerCurrentRogueMediaMidCallBadDestMinorAlarmCount                             PerfCurrentCount,
        sonusSysPolicerCurrentRogueMediaMidCallBadDestMinorAlarmDuration                                PerfCurrentCount,
        sonusSysPolicerCurrentRogueMediaMidCallBadDestMajorAlarmCount                             PerfCurrentCount,
        sonusSysPolicerCurrentRogueMediaMidCallBadDestMajorAlarmDuration                                PerfCurrentCount,
        sonusSysPolicerCurrentRogueMediaMidCallBadSourceDiscardPacketCount                                  Counter64,
        sonusSysPolicerCurrentRogueMediaMidCallBadSourcePeakDiscardRate                               PerfCurrentCount,
        sonusSysPolicerCurrentRogueMediaMidCallBadSourceMinorAlarmCount                               PerfCurrentCount,
        sonusSysPolicerCurrentRogueMediaMidCallBadSourceMinorAlarmDuration                                  PerfCurrentCount,
        sonusSysPolicerCurrentRogueMediaMidCallBadSourceMajorAlarmCount                               PerfCurrentCount,
        sonusSysPolicerCurrentRogueMediaMidCallBadSourceMajorAlarmDuration                                  PerfCurrentCount,
        sonusSysPolicerCurrentRogueMediaMidCallBadVLanDiscardPacketCount                                Counter64,
        sonusSysPolicerCurrentRogueMediaMidCallBadVLanPeakDiscardRate                             PerfCurrentCount,
        sonusSysPolicerCurrentRogueMediaMidCallBadVLanMinorAlarmCount                             PerfCurrentCount,
        sonusSysPolicerCurrentRogueMediaMidCallBadVLanMinorAlarmDuration                                PerfCurrentCount,
        sonusSysPolicerCurrentRogueMediaMidCallBadVLanMajorAlarmCount                             PerfCurrentCount,
        sonusSysPolicerCurrentRogueMediaMidCallBadVLanMajorAlarmDuration                                PerfCurrentCount,
        sonusSysPolicerCurrentRogueMediaInGracePeriodDiscardPacketCount                               Counter64,
        sonusSysPolicerCurrentRogueMediaInGracePeriodPeakDiscardRate                            PerfCurrentCount,
        sonusSysPolicerCurrentLightGrayListDiscardPacketCount                     Counter64,
        sonusSysPolicerCurrentLightGrayListPeakDiscardRate                  PerfCurrentCount,
        sonusSysPolicerCurrentLightGrayListMinorAlarmCount                  PerfCurrentCount,
        sonusSysPolicerCurrentLightGrayListMinorAlarmDuration                     PerfCurrentCount,
        sonusSysPolicerCurrentLightGrayListMajorAlarmCount                  PerfCurrentCount,
        sonusSysPolicerCurrentLightGrayListMajorAlarmDuration                     PerfCurrentCount,
        sonusSysPolicerCurrentVLanDiscardPacketCount            Counter64,
        sonusSysPolicerCurrentVLanPeakDiscardRate         PerfCurrentCount,
        sonusSysPolicerCurrentVLanMinorAlarmCount         PerfCurrentCount,
        sonusSysPolicerCurrentVLanMinorAlarmDuration            PerfCurrentCount,
        sonusSysPolicerCurrentVLanMajorAlarmCount         PerfCurrentCount,
        sonusSysPolicerCurrentVLanMajorAlarmDuration            PerfCurrentCount
    }

sonusSysPolicerCurrentShelfIndex OBJECT-TYPE
    SYNTAX          SonusShelfIndex
    MAX-ACCESS      read-only
    STATUS          current
    DESCRIPTION     
            "The index into the sonusSysPolicerCurrentTable."
    ::= { sonusSysPolicerCurrentEntry 1 }

sonusSysPolicerCurrentWhiteListDiscardPacketCount OBJECT-TYPE
    SYNTAX          Counter64
    MAX-ACCESS      read-only
    STATUS          current
    DESCRIPTION     
            "The current number of discarded packets for the 
             White List policer."
    ::= { sonusSysPolicerCurrentEntry 2 }

sonusSysPolicerCurrentWhiteListPeakDiscardRate OBJECT-TYPE
    SYNTAX          PerfCurrentCount
    MAX-ACCESS      read-only
    STATUS          current
    DESCRIPTION     
            "The current peak discard rate for the 
             White List policer."
    ::= { sonusSysPolicerCurrentEntry 3 }

sonusSysPolicerCurrentWhiteListMinorAlarmCount OBJECT-TYPE
    SYNTAX          PerfCurrentCount
    MAX-ACCESS      read-only
    STATUS          current
    DESCRIPTION     
            "The current number of minor alarms for the 
             White List policer."
    ::= { sonusSysPolicerCurrentEntry 4 }

sonusSysPolicerCurrentWhiteListMinorAlarmDuration OBJECT-TYPE
    SYNTAX          PerfCurrentCount
    MAX-ACCESS      read-only
    STATUS          current
    DESCRIPTION     
            "The current duration of the minor alarms in seconds
             for the White List policer."
    ::= { sonusSysPolicerCurrentEntry 5 }

sonusSysPolicerCurrentWhiteListMajorAlarmCount OBJECT-TYPE
    SYNTAX          PerfCurrentCount
    MAX-ACCESS      read-only
    STATUS          current
    DESCRIPTION     
            "The current number of major alarms for the 
             White List policer."
    ::= { sonusSysPolicerCurrentEntry 6 }

sonusSysPolicerCurrentWhiteListMajorAlarmDuration OBJECT-TYPE
    SYNTAX          PerfCurrentCount
    MAX-ACCESS      read-only
    STATUS          current
    DESCRIPTION     
            "The current duration of the major alarms in seconds
             for the White List policer."
    ::= { sonusSysPolicerCurrentEntry 7 }

sonusSysPolicerCurrentBlackListDiscardPacketCount OBJECT-TYPE
    SYNTAX          Counter64
    MAX-ACCESS      read-only
    STATUS          current
    DESCRIPTION     
            "The current number of discarded packets for the 
             Black List policer."
    ::= { sonusSysPolicerCurrentEntry 8 }

sonusSysPolicerCurrentBlackListPeakDiscardRate OBJECT-TYPE
    SYNTAX          PerfCurrentCount
    MAX-ACCESS      read-only
    STATUS          current
    DESCRIPTION     
            "The current peak discard rate for the 
             Black List policer."
    ::= { sonusSysPolicerCurrentEntry 9 }

sonusSysPolicerCurrentBlackListMinorAlarmCount OBJECT-TYPE
    SYNTAX          PerfCurrentCount
    MAX-ACCESS      read-only
    STATUS          current
    DESCRIPTION     
            "The current number of minor alarms for the 
             Black List policer."
    ::= { sonusSysPolicerCurrentEntry 10 }

sonusSysPolicerCurrentBlackListMinorAlarmDuration OBJECT-TYPE
    SYNTAX          PerfCurrentCount
    MAX-ACCESS      read-only
    STATUS          current
    DESCRIPTION     
            "The current duration of the minor alarms in seconds
             for the Black List policer."
    ::= { sonusSysPolicerCurrentEntry 11 }

sonusSysPolicerCurrentBlackListMajorAlarmCount OBJECT-TYPE
    SYNTAX          PerfCurrentCount
    MAX-ACCESS      read-only
    STATUS          current
    DESCRIPTION     
            "The current number of major alarms for the 
             Black List policer."
    ::= { sonusSysPolicerCurrentEntry 12 }

sonusSysPolicerCurrentBlackListMajorAlarmDuration OBJECT-TYPE
    SYNTAX          PerfCurrentCount
    MAX-ACCESS      read-only
    STATUS          current
    DESCRIPTION     
            "The current duration of the major alarms in seconds
             for the Black List policer."
    ::= { sonusSysPolicerCurrentEntry 13 }

sonusSysPolicerCurrentDarkGrayListDiscardPacketCount OBJECT-TYPE
    SYNTAX          Counter64
    MAX-ACCESS      read-only
    STATUS          current
    DESCRIPTION     
            "The current number of discarded packets for the 
             Dark Gray List policer."
    ::= { sonusSysPolicerCurrentEntry 14 }

sonusSysPolicerCurrentDarkGrayListAcceptPacketCount OBJECT-TYPE
    SYNTAX          Counter64
    MAX-ACCESS      read-only
    STATUS          current
    DESCRIPTION     
            "The current number of accepted packets for the
             Dark Gray List policer."
    ::= { sonusSysPolicerCurrentEntry 15 }

sonusSysPolicerCurrentDarkGrayListPeakDiscardRate OBJECT-TYPE
    SYNTAX          PerfCurrentCount
    MAX-ACCESS      read-only
    STATUS          current
    DESCRIPTION     
            "The current peak discard rate for the 
             Dark Gray List policer."
    ::= { sonusSysPolicerCurrentEntry 16 }

sonusSysPolicerCurrentDarkGrayListMinorAlarmCount OBJECT-TYPE
    SYNTAX          PerfCurrentCount
    MAX-ACCESS      read-only
    STATUS          current
    DESCRIPTION     
            "The current number of minor alarms for the 
             Dark Gray List policer."
    ::= { sonusSysPolicerCurrentEntry 17 }

sonusSysPolicerCurrentDarkGrayListMinorAlarmDuration OBJECT-TYPE
    SYNTAX          PerfCurrentCount
    MAX-ACCESS      read-only
    STATUS          current
    DESCRIPTION     
            "The current duration of the minor alarms in seconds
             for the Dark Gray List policer."
    ::= { sonusSysPolicerCurrentEntry 18 }

sonusSysPolicerCurrentDarkGrayListMajorAlarmCount OBJECT-TYPE
    SYNTAX          PerfCurrentCount
    MAX-ACCESS      read-only
    STATUS          current
    DESCRIPTION     
            "The current number of major alarms for the 
             Dark Gray List policer."
    ::= { sonusSysPolicerCurrentEntry 19 }

sonusSysPolicerCurrentDarkGrayListMajorAlarmDuration OBJECT-TYPE
    SYNTAX          PerfCurrentCount
    MAX-ACCESS      read-only
    STATUS          current
    DESCRIPTION     
            "The current duration of the major alarms in seconds
             for the Dark Gray List policer."
    ::= { sonusSysPolicerCurrentEntry 20 }

sonusSysPolicerCurrentServerProtectDiscardPacketCount OBJECT-TYPE
    SYNTAX          Counter64
    MAX-ACCESS      read-only
    STATUS          current
    DESCRIPTION     
            "The current number of discarded packets for the 
             Server Protect policer."
    ::= { sonusSysPolicerCurrentEntry 21 }

sonusSysPolicerCurrentServerProtectAcceptPacketCount OBJECT-TYPE
    SYNTAX          Counter64
    MAX-ACCESS      read-only
    STATUS          current
    DESCRIPTION     
            "The current number of accepted packets for the
             Server Protect policer."
    ::= { sonusSysPolicerCurrentEntry 22 }

sonusSysPolicerCurrentServerProtectPeakDiscardRate OBJECT-TYPE
    SYNTAX          PerfCurrentCount
    MAX-ACCESS      read-only
    STATUS          current
    DESCRIPTION     
            "The current peak discard rate for the 
             Server Protect policer."
    ::= { sonusSysPolicerCurrentEntry 23 }

sonusSysPolicerCurrentServerProtectMinorAlarmCount OBJECT-TYPE
    SYNTAX          PerfCurrentCount
    MAX-ACCESS      read-only
    STATUS          current
    DESCRIPTION     
            "The current number of minor alarms for the 
             Server Protect policer."
    ::= { sonusSysPolicerCurrentEntry 24 }

sonusSysPolicerCurrentServerProtectMinorAlarmDuration OBJECT-TYPE
    SYNTAX          PerfCurrentCount
    MAX-ACCESS      read-only
    STATUS          current
    DESCRIPTION     
            "The current duration of the minor alarms in seconds
             for the Server Protect policer."
    ::= { sonusSysPolicerCurrentEntry 25 }

sonusSysPolicerCurrentServerProtectMajorAlarmCount OBJECT-TYPE
    SYNTAX          PerfCurrentCount
    MAX-ACCESS      read-only
    STATUS          current
    DESCRIPTION     
            "The current number of major alarms for the 
             Server Protect policer."
    ::= { sonusSysPolicerCurrentEntry 26 }

sonusSysPolicerCurrentServerProtectMajorAlarmDuration OBJECT-TYPE
    SYNTAX          PerfCurrentCount
    MAX-ACCESS      read-only
    STATUS          current
    DESCRIPTION     
            "The current duration of the major alarms in seconds
             for the Server Protect policer."
    ::= { sonusSysPolicerCurrentEntry 27 }

sonusSysPolicerCurrentMediaDiscardPacketCount OBJECT-TYPE
    SYNTAX          Counter64
    MAX-ACCESS      read-only
    STATUS          current
    DESCRIPTION     
            "The current number of discarded packets for the 
             Media policer."
    ::= { sonusSysPolicerCurrentEntry 28 }

sonusSysPolicerCurrentMediaPeakDiscardRate OBJECT-TYPE
    SYNTAX          PerfCurrentCount
    MAX-ACCESS      read-only
    STATUS          current
    DESCRIPTION     
            "The current peak discard rate for the 
             Media policer."
    ::= { sonusSysPolicerCurrentEntry 29 }

sonusSysPolicerCurrentMediaMinorAlarmCount OBJECT-TYPE
    SYNTAX          PerfCurrentCount
    MAX-ACCESS      read-only
    STATUS          current
    DESCRIPTION     
            "The current number of minor alarms for the 
             Media policer."
    ::= { sonusSysPolicerCurrentEntry 30 }

sonusSysPolicerCurrentMediaMinorAlarmDuration OBJECT-TYPE
    SYNTAX          PerfCurrentCount
    MAX-ACCESS      read-only
    STATUS          current
    DESCRIPTION     
            "The current duration of the minor alarms in seconds
             for the Media policer."
    ::= { sonusSysPolicerCurrentEntry 31 }

sonusSysPolicerCurrentMediaMajorAlarmCount OBJECT-TYPE
    SYNTAX          PerfCurrentCount
    MAX-ACCESS      read-only
    STATUS          current
    DESCRIPTION     
            "The current number of major alarms for the 
             Media policer."
    ::= { sonusSysPolicerCurrentEntry 32 }

sonusSysPolicerCurrentMediaMajorAlarmDuration OBJECT-TYPE
    SYNTAX          PerfCurrentCount
    MAX-ACCESS      read-only
    STATUS          current
    DESCRIPTION     
            "The current duration of the major alarms in seconds
             for the Media policer."
    ::= { sonusSysPolicerCurrentEntry 33 }

sonusSysPolicerCurrentRogueMediaUnallocatedPortDiscardPacketCount OBJECT-TYPE
    SYNTAX          Counter64
    MAX-ACCESS      read-only
    STATUS          current
    DESCRIPTION     
            "The current number of discarded packets for the 
             policer."
    ::= { sonusSysPolicerCurrentEntry 34 }

sonusSysPolicerCurrentRogueMediaUnallocatedPortPeakDiscardRate OBJECT-TYPE
    SYNTAX          PerfCurrentCount
    MAX-ACCESS      read-only
    STATUS          current
    DESCRIPTION     
            "The current peak discard rate for the 
             policer."
    ::= { sonusSysPolicerCurrentEntry 35 }

sonusSysPolicerCurrentRogueMediaUnallocatedPortMinorAlarmCount OBJECT-TYPE
    SYNTAX          PerfCurrentCount
    MAX-ACCESS      read-only
    STATUS          current
    DESCRIPTION     
            "The current number of minor alarms for the 
             policer."
    ::= { sonusSysPolicerCurrentEntry 36 }

sonusSysPolicerCurrentRogueMediaUnallocatedPortMinorAlarmDuration OBJECT-TYPE
    SYNTAX          PerfCurrentCount
    MAX-ACCESS      read-only
    STATUS          current
    DESCRIPTION     
            "The current duration of the minor alarms in seconds
             for the  policer."
    ::= { sonusSysPolicerCurrentEntry 37 }

sonusSysPolicerCurrentRogueMediaUnallocatedPortMajorAlarmCount OBJECT-TYPE
    SYNTAX          PerfCurrentCount
    MAX-ACCESS      read-only
    STATUS          current
    DESCRIPTION     
            "The current number of major alarms for the 
             policer."
    ::= { sonusSysPolicerCurrentEntry 38 }

sonusSysPolicerCurrentRogueMediaUnallocatedPortMajorAlarmDuration OBJECT-TYPE
    SYNTAX          PerfCurrentCount
    MAX-ACCESS      read-only
    STATUS          current
    DESCRIPTION     
            "The current duration of the major alarms in seconds
             for the  policer."
    ::= { sonusSysPolicerCurrentEntry 39 }

sonusSysPolicerCurrentRogueMediaMidCallBadDestDiscardPacketCount OBJECT-TYPE
    SYNTAX          Counter64
    MAX-ACCESS      read-only
    STATUS          current
    DESCRIPTION     
            "The current number of discarded packets for the 
             policer."
    ::= { sonusSysPolicerCurrentEntry 40 }

sonusSysPolicerCurrentRogueMediaMidCallBadDestPeakDiscardRate OBJECT-TYPE
    SYNTAX          PerfCurrentCount
    MAX-ACCESS      read-only
    STATUS          current
    DESCRIPTION     
            "The current peak discard rate for the 
             policer."
    ::= { sonusSysPolicerCurrentEntry 41 }

sonusSysPolicerCurrentRogueMediaMidCallBadDestMinorAlarmCount OBJECT-TYPE
    SYNTAX          PerfCurrentCount
    MAX-ACCESS      read-only
    STATUS          current
    DESCRIPTION     
            "The current number of minor alarms for the 
             policer."
    ::= { sonusSysPolicerCurrentEntry 42 }

sonusSysPolicerCurrentRogueMediaMidCallBadDestMinorAlarmDuration OBJECT-TYPE
    SYNTAX          PerfCurrentCount
    MAX-ACCESS      read-only
    STATUS          current
    DESCRIPTION     
            "The current duration of the minor alarms in seconds
             for the  policer."
    ::= { sonusSysPolicerCurrentEntry 43 }

sonusSysPolicerCurrentRogueMediaMidCallBadDestMajorAlarmCount OBJECT-TYPE
    SYNTAX          PerfCurrentCount
    MAX-ACCESS      read-only
    STATUS          current
    DESCRIPTION     
            "The current number of major alarms for the 
             policer."
    ::= { sonusSysPolicerCurrentEntry 44 }

sonusSysPolicerCurrentRogueMediaMidCallBadDestMajorAlarmDuration OBJECT-TYPE
    SYNTAX          PerfCurrentCount
    MAX-ACCESS      read-only
    STATUS          current
    DESCRIPTION     
            "The current duration of the major alarms in seconds
             for the  policer."
    ::= { sonusSysPolicerCurrentEntry 45 }

sonusSysPolicerCurrentRogueMediaMidCallBadSourceDiscardPacketCount OBJECT-TYPE
    SYNTAX          Counter64
    MAX-ACCESS      read-only
    STATUS          current
    DESCRIPTION     
            "The current number of discarded packets for the 
             policer."
    ::= { sonusSysPolicerCurrentEntry 46 }

sonusSysPolicerCurrentRogueMediaMidCallBadSourcePeakDiscardRate OBJECT-TYPE
    SYNTAX          PerfCurrentCount
    MAX-ACCESS      read-only
    STATUS          current
    DESCRIPTION     
            "The current peak discard rate for the 
             policer."
    ::= { sonusSysPolicerCurrentEntry 47 }

sonusSysPolicerCurrentRogueMediaMidCallBadSourceMinorAlarmCount OBJECT-TYPE
    SYNTAX          PerfCurrentCount
    MAX-ACCESS      read-only
    STATUS          current
    DESCRIPTION     
            "The current number of minor alarms for the 
             policer."
    ::= { sonusSysPolicerCurrentEntry 48 }

sonusSysPolicerCurrentRogueMediaMidCallBadSourceMinorAlarmDuration OBJECT-TYPE
    SYNTAX          PerfCurrentCount
    MAX-ACCESS      read-only
    STATUS          current
    DESCRIPTION     
            "The current duration of the minor alarms in seconds
             for the  policer."
    ::= { sonusSysPolicerCurrentEntry 49 }

sonusSysPolicerCurrentRogueMediaMidCallBadSourceMajorAlarmCount OBJECT-TYPE
    SYNTAX          PerfCurrentCount
    MAX-ACCESS      read-only
    STATUS          current
    DESCRIPTION     
            "The current number of major alarms for the 
             policer."
    ::= { sonusSysPolicerCurrentEntry 50 }

sonusSysPolicerCurrentRogueMediaMidCallBadSourceMajorAlarmDuration OBJECT-TYPE
    SYNTAX          PerfCurrentCount
    MAX-ACCESS      read-only
    STATUS          current
    DESCRIPTION     
            "The current duration of the major alarms in seconds
             for the  policer."
    ::= { sonusSysPolicerCurrentEntry 51 }

sonusSysPolicerCurrentRogueMediaMidCallBadVLanDiscardPacketCount OBJECT-TYPE
    SYNTAX          Counter64
    MAX-ACCESS      read-only
    STATUS          current
    DESCRIPTION     
            "The current number of discarded packets for the 
             policer."
    ::= { sonusSysPolicerCurrentEntry 52 }

sonusSysPolicerCurrentRogueMediaMidCallBadVLanPeakDiscardRate OBJECT-TYPE
    SYNTAX          PerfCurrentCount
    MAX-ACCESS      read-only
    STATUS          current
    DESCRIPTION     
            "The current peak discard rate for the 
             policer."
    ::= { sonusSysPolicerCurrentEntry 53 }

sonusSysPolicerCurrentRogueMediaMidCallBadVLanMinorAlarmCount OBJECT-TYPE
    SYNTAX          PerfCurrentCount
    MAX-ACCESS      read-only
    STATUS          current
    DESCRIPTION     
            "The current number of minor alarms for the 
             policer."
    ::= { sonusSysPolicerCurrentEntry 54 }

sonusSysPolicerCurrentRogueMediaMidCallBadVLanMinorAlarmDuration OBJECT-TYPE
    SYNTAX          PerfCurrentCount
    MAX-ACCESS      read-only
    STATUS          current
    DESCRIPTION     
            "The current duration of the minor alarms in seconds
             for the  policer."
    ::= { sonusSysPolicerCurrentEntry 55 }

sonusSysPolicerCurrentRogueMediaMidCallBadVLanMajorAlarmCount OBJECT-TYPE
    SYNTAX          PerfCurrentCount
    MAX-ACCESS      read-only
    STATUS          current
    DESCRIPTION     
            "The current number of major alarms for the 
             policer."
    ::= { sonusSysPolicerCurrentEntry 56 }

sonusSysPolicerCurrentRogueMediaMidCallBadVLanMajorAlarmDuration OBJECT-TYPE
    SYNTAX          PerfCurrentCount
    MAX-ACCESS      read-only
    STATUS          current
    DESCRIPTION     
            "The current duration of the major alarms in seconds
             for the  policer."
    ::= { sonusSysPolicerCurrentEntry 57 }

sonusSysPolicerCurrentRogueMediaInGracePeriodDiscardPacketCount OBJECT-TYPE
    SYNTAX          Counter64
    MAX-ACCESS      read-only
    STATUS          current
    DESCRIPTION     
            "The current number of discarded packets for the 
             policer."
    ::= { sonusSysPolicerCurrentEntry 58 }

sonusSysPolicerCurrentRogueMediaInGracePeriodPeakDiscardRate OBJECT-TYPE
    SYNTAX          PerfCurrentCount
    MAX-ACCESS      read-only
    STATUS          current
    DESCRIPTION     
            "The current peak discard rate for the 
             policer."
    ::= { sonusSysPolicerCurrentEntry 59 }

sonusSysPolicerCurrentLightGrayListDiscardPacketCount OBJECT-TYPE
    SYNTAX          Counter64
    MAX-ACCESS      read-only
    STATUS          current
    DESCRIPTION     
            "The current number of discarded packets for the 
             Light Gray List policer."
    ::= { sonusSysPolicerCurrentEntry 60 }

sonusSysPolicerCurrentLightGrayListPeakDiscardRate OBJECT-TYPE
    SYNTAX          PerfCurrentCount
    MAX-ACCESS      read-only
    STATUS          current
    DESCRIPTION     
            "The current peak discard rate for the 
             Light Gray List policer."
    ::= { sonusSysPolicerCurrentEntry 61 }

sonusSysPolicerCurrentLightGrayListMinorAlarmCount OBJECT-TYPE
    SYNTAX          PerfCurrentCount
    MAX-ACCESS      read-only
    STATUS          current
    DESCRIPTION     
            "The current number of minor alarms for the 
             Light Gray List policer."
    ::= { sonusSysPolicerCurrentEntry 62 }

sonusSysPolicerCurrentLightGrayListMinorAlarmDuration OBJECT-TYPE
    SYNTAX          PerfCurrentCount
    MAX-ACCESS      read-only
    STATUS          current
    DESCRIPTION     
            "The current duration of the minor alarms in seconds
             for the Light Gray List policer."
    ::= { sonusSysPolicerCurrentEntry 63 }

sonusSysPolicerCurrentLightGrayListMajorAlarmCount OBJECT-TYPE
    SYNTAX          PerfCurrentCount
    MAX-ACCESS      read-only
    STATUS          current
    DESCRIPTION     
            "The current number of major alarms for the 
             Light Gray List policer."
    ::= { sonusSysPolicerCurrentEntry 64 }

sonusSysPolicerCurrentLightGrayListMajorAlarmDuration OBJECT-TYPE
    SYNTAX          PerfCurrentCount
    MAX-ACCESS      read-only
    STATUS          current
    DESCRIPTION     
            "The current duration of the major alarms in seconds
             for the Light Gray List policer."
    ::= { sonusSysPolicerCurrentEntry 65 }

sonusSysPolicerCurrentVLanDiscardPacketCount OBJECT-TYPE
    SYNTAX          Counter64
    MAX-ACCESS      read-only
    STATUS          current
    DESCRIPTION     
            "The current number of discarded packets for the 
             VLAN policer."
    ::= { sonusSysPolicerCurrentEntry 66 }

sonusSysPolicerCurrentVLanPeakDiscardRate OBJECT-TYPE
    SYNTAX          PerfCurrentCount
    MAX-ACCESS      read-only
    STATUS          current
    DESCRIPTION     
            "The current peak discard rate for the 
             VLAN policer."
    ::= { sonusSysPolicerCurrentEntry 67 }

sonusSysPolicerCurrentVLanMinorAlarmCount OBJECT-TYPE
    SYNTAX          PerfCurrentCount
    MAX-ACCESS      read-only
    STATUS          current
    DESCRIPTION     
            "The current number of minor alarms for the 
             VLAN policer."
    ::= { sonusSysPolicerCurrentEntry 68 }

sonusSysPolicerCurrentVLanMinorAlarmDuration OBJECT-TYPE
    SYNTAX          PerfCurrentCount
    MAX-ACCESS      read-only
    STATUS          current
    DESCRIPTION     
            "The current duration of the minor alarms in seconds
             for the VLAN policer."
    ::= { sonusSysPolicerCurrentEntry 69 }

sonusSysPolicerCurrentVLanMajorAlarmCount OBJECT-TYPE
    SYNTAX          PerfCurrentCount
    MAX-ACCESS      read-only
    STATUS          current
    DESCRIPTION     
            "The current number of major alarms for the 
             VLAN policer."
    ::= { sonusSysPolicerCurrentEntry 70 }

sonusSysPolicerCurrentVLanMajorAlarmDuration OBJECT-TYPE
    SYNTAX          PerfCurrentCount
    MAX-ACCESS      read-only
    STATUS          current
    DESCRIPTION     
            "The current duration of the major alarms in seconds
             for the VLAN policer."
    ::= { sonusSysPolicerCurrentEntry 71 }

sonusSysPolicerIntervalTable OBJECT-TYPE
    SYNTAX          SEQUENCE OF SonusSysPolicerIntervalEntry
    MAX-ACCESS      not-accessible
    STATUS          current
    DESCRIPTION     
            "The Sonus System Policer Interval table."
    ::= { sonusPolicerStatisticsObjects 2 }

sonusSysPolicerIntervalEntry OBJECT-TYPE
    SYNTAX          SonusSysPolicerIntervalEntry
    MAX-ACCESS      not-accessible
    STATUS          current
    DESCRIPTION     
            "An entry in the Sonus System Policer Interval table."
    INDEX           { sonusSysPolicerIntervalShelfIndex, 
                      sonusSysPolicerIntervalNumber }
    ::= { sonusSysPolicerIntervalTable 1 }

SonusSysPolicerIntervalEntry ::=
    SEQUENCE {
        sonusSysPolicerIntervalShelfIndex SonusShelfIndex,
        sonusSysPolicerIntervalNumber   Integer32,
        sonusSysPolicerIntervalTime     TimeTicks,
        sonusSysPolicerIntervalValidData TruthValue,
        sonusSysPolicerIntervalWhiteListDiscardPacketCount                  Counter64,
        sonusSysPolicerIntervalWhiteListPeakDiscardRate               PerfIntervalCount,
        sonusSysPolicerIntervalWhiteListMinorAlarmCount               PerfIntervalCount,
        sonusSysPolicerIntervalWhiteListMinorAlarmDuration                  PerfIntervalCount,
        sonusSysPolicerIntervalWhiteListMajorAlarmCount               PerfIntervalCount,
        sonusSysPolicerIntervalWhiteListMajorAlarmDuration                  PerfIntervalCount,
        sonusSysPolicerIntervalBlackListDiscardPacketCount                  Counter64,
        sonusSysPolicerIntervalBlackListPeakDiscardRate               PerfIntervalCount,
        sonusSysPolicerIntervalBlackListMinorAlarmCount               PerfIntervalCount,
        sonusSysPolicerIntervalBlackListMinorAlarmDuration                  PerfIntervalCount,
        sonusSysPolicerIntervalBlackListMajorAlarmCount               PerfIntervalCount,
        sonusSysPolicerIntervalBlackListMajorAlarmDuration                  PerfIntervalCount,
        sonusSysPolicerIntervalDarkGrayListDiscardPacketCount                     Counter64,
        sonusSysPolicerIntervalDarkGrayListAcceptPacketCount                    Counter64,
        sonusSysPolicerIntervalDarkGrayListPeakDiscardRate                  PerfIntervalCount,
        sonusSysPolicerIntervalDarkGrayListMinorAlarmCount                  PerfIntervalCount,
        sonusSysPolicerIntervalDarkGrayListMinorAlarmDuration                     PerfIntervalCount,
        sonusSysPolicerIntervalDarkGrayListMajorAlarmCount                  PerfIntervalCount,
        sonusSysPolicerIntervalDarkGrayListMajorAlarmDuration                     PerfIntervalCount,
        sonusSysPolicerIntervalServerProtectDiscardPacketCount                      Counter64,
        sonusSysPolicerIntervalServerProtectAcceptPacketCount                     Counter64,
        sonusSysPolicerIntervalServerProtectPeakDiscardRate                   PerfIntervalCount,
        sonusSysPolicerIntervalServerProtectMinorAlarmCount                   PerfIntervalCount,
        sonusSysPolicerIntervalServerProtectMinorAlarmDuration                      PerfIntervalCount,
        sonusSysPolicerIntervalServerProtectMajorAlarmCount                   PerfIntervalCount,
        sonusSysPolicerIntervalServerProtectMajorAlarmDuration                      PerfIntervalCount,
        sonusSysPolicerIntervalMediaDiscardPacketCount              Counter64,
        sonusSysPolicerIntervalMediaPeakDiscardRate           PerfIntervalCount,
        sonusSysPolicerIntervalMediaMinorAlarmCount           PerfIntervalCount,
        sonusSysPolicerIntervalMediaMinorAlarmDuration              PerfIntervalCount,
        sonusSysPolicerIntervalMediaMajorAlarmCount           PerfIntervalCount,
        sonusSysPolicerIntervalMediaMajorAlarmDuration              PerfIntervalCount,
        sonusSysPolicerIntervalRogueMediaUnallocatedPortDiscardPacketCount                                  Counter64,
        sonusSysPolicerIntervalRogueMediaUnallocatedPortPeakDiscardRate                               PerfIntervalCount,
        sonusSysPolicerIntervalRogueMediaUnallocatedPortMinorAlarmCount                               PerfIntervalCount,
        sonusSysPolicerIntervalRogueMediaUnallocatedPortMinorAlarmDuration                                  PerfIntervalCount,
        sonusSysPolicerIntervalRogueMediaUnallocatedPortMajorAlarmCount                               PerfIntervalCount,
        sonusSysPolicerIntervalRogueMediaUnallocatedPortMajorAlarmDuration                                  PerfIntervalCount,
        sonusSysPolicerIntervalRogueMediaMidCallBadDestDiscardPacketCount                                 Counter64,
        sonusSysPolicerIntervalRogueMediaMidCallBadDestPeakDiscardRate                              PerfIntervalCount,
        sonusSysPolicerIntervalRogueMediaMidCallBadDestMinorAlarmCount                              PerfIntervalCount,
        sonusSysPolicerIntervalRogueMediaMidCallBadDestMinorAlarmDuration                                 PerfIntervalCount,
        sonusSysPolicerIntervalRogueMediaMidCallBadDestMajorAlarmCount                              PerfIntervalCount,
        sonusSysPolicerIntervalRogueMediaMidCallBadDestMajorAlarmDuration                                 PerfIntervalCount,
        sonusSysPolicerIntervalRogueMediaMidCallBadSourceDiscardPacketCount                                   Counter64,
        sonusSysPolicerIntervalRogueMediaMidCallBadSourcePeakDiscardRate                                PerfIntervalCount,
        sonusSysPolicerIntervalRogueMediaMidCallBadSourceMinorAlarmCount                                PerfIntervalCount,
        sonusSysPolicerIntervalRogueMediaMidCallBadSourceMinorAlarmDuration                                   PerfIntervalCount,
        sonusSysPolicerIntervalRogueMediaMidCallBadSourceMajorAlarmCount                                PerfIntervalCount,
        sonusSysPolicerIntervalRogueMediaMidCallBadSourceMajorAlarmDuration                                   PerfIntervalCount,
        sonusSysPolicerIntervalRogueMediaMidCallBadVLanDiscardPacketCount                                 Counter64,
        sonusSysPolicerIntervalRogueMediaMidCallBadVLanPeakDiscardRate                              PerfIntervalCount,
        sonusSysPolicerIntervalRogueMediaMidCallBadVLanMinorAlarmCount                              PerfIntervalCount,
        sonusSysPolicerIntervalRogueMediaMidCallBadVLanMinorAlarmDuration                                 PerfIntervalCount,
        sonusSysPolicerIntervalRogueMediaMidCallBadVLanMajorAlarmCount                              PerfIntervalCount,
        sonusSysPolicerIntervalRogueMediaMidCallBadVLanMajorAlarmDuration                                 PerfIntervalCount,
        sonusSysPolicerIntervalRogueMediaInGracePeriodDiscardPacketCount                                Counter64,
        sonusSysPolicerIntervalRogueMediaInGracePeriodPeakDiscardRate                             PerfIntervalCount,
        sonusSysPolicerIntervalLightGrayListDiscardPacketCount                      Counter64,
        sonusSysPolicerIntervalLightGrayListPeakDiscardRate                   PerfIntervalCount,
        sonusSysPolicerIntervalLightGrayListMinorAlarmCount                   PerfIntervalCount,
        sonusSysPolicerIntervalLightGrayListMinorAlarmDuration                      PerfIntervalCount,
        sonusSysPolicerIntervalLightGrayListMajorAlarmCount                   PerfIntervalCount,
        sonusSysPolicerIntervalLightGrayListMajorAlarmDuration                      PerfIntervalCount,
        sonusSysPolicerIntervalVLanDiscardPacketCount             Counter64,
        sonusSysPolicerIntervalVLanPeakDiscardRate          PerfIntervalCount,
        sonusSysPolicerIntervalVLanMinorAlarmCount          PerfIntervalCount,
        sonusSysPolicerIntervalVLanMinorAlarmDuration             PerfIntervalCount,
        sonusSysPolicerIntervalVLanMajorAlarmCount          PerfIntervalCount,
        sonusSysPolicerIntervalVLanMajorAlarmDuration             PerfIntervalCount
    }

sonusSysPolicerIntervalShelfIndex OBJECT-TYPE
    SYNTAX          SonusShelfIndex
    MAX-ACCESS      read-only
    STATUS          current
    DESCRIPTION     
            "The index into the sonusSysPolicerIntervalTable."
    ::= { sonusSysPolicerIntervalEntry 1 }

sonusSysPolicerIntervalNumber OBJECT-TYPE
    SYNTAX          Integer32 (1..288)
    MAX-ACCESS      not-accessible
    STATUS          current
    DESCRIPTION     
            "A number between 1 and 288, which identifies the
             interval for which the set of statistics is available.
             The interval identified by 1 is the most recently
             completed interval, and the interval identified
             by N is the interval immediately preceding the
             one identified by N-1."
    ::= { sonusSysPolicerIntervalEntry 2 }

sonusSysPolicerIntervalTime OBJECT-TYPE
    SYNTAX          TimeTicks
    MAX-ACCESS      read-only
    STATUS          current
    DESCRIPTION     
            "This variable contains the end of interval time
             stamp for the specified interval."
    ::= { sonusSysPolicerIntervalEntry 3 }

sonusSysPolicerIntervalValidData OBJECT-TYPE
    SYNTAX          TruthValue
    MAX-ACCESS      read-only
    STATUS          current
    DESCRIPTION     
            "This variable indicates if the data for this
             interval is valid."
    ::= { sonusSysPolicerIntervalEntry 4 }

sonusSysPolicerIntervalWhiteListDiscardPacketCount OBJECT-TYPE
    SYNTAX          Counter64
    MAX-ACCESS      read-only
    STATUS          current
    DESCRIPTION     
            "The number of discarded packets for the 
             White List policer for the specified interval."
    ::= { sonusSysPolicerIntervalEntry 5 }

sonusSysPolicerIntervalWhiteListPeakDiscardRate OBJECT-TYPE
    SYNTAX          PerfIntervalCount
    MAX-ACCESS      read-only
    STATUS          current
    DESCRIPTION     
            "The peak discard rate for the  
             White List policer for the specified interval."
    ::= { sonusSysPolicerIntervalEntry 6 }

sonusSysPolicerIntervalWhiteListMinorAlarmCount OBJECT-TYPE
    SYNTAX          PerfIntervalCount
    MAX-ACCESS      read-only
    STATUS          current
    DESCRIPTION     
            "The number of minor alarms for the 
             White List policer for the specified interval."
    ::= { sonusSysPolicerIntervalEntry 7 }

sonusSysPolicerIntervalWhiteListMinorAlarmDuration OBJECT-TYPE
    SYNTAX          PerfIntervalCount
    MAX-ACCESS      read-only
    STATUS          current
    DESCRIPTION     
            "The duration of the minor alarms in seconds
             for the White List policer for the specified interval."
    ::= { sonusSysPolicerIntervalEntry 8 }

sonusSysPolicerIntervalWhiteListMajorAlarmCount OBJECT-TYPE
    SYNTAX          PerfIntervalCount
    MAX-ACCESS      read-only
    STATUS          current
    DESCRIPTION     
            "The number of of major alarms for the 
             White List policer for the specified interval."
    ::= { sonusSysPolicerIntervalEntry 9 }

sonusSysPolicerIntervalWhiteListMajorAlarmDuration OBJECT-TYPE
    SYNTAX          PerfIntervalCount
    MAX-ACCESS      read-only
    STATUS          current
    DESCRIPTION     
            "The duration of the major alarms in seconds
             for the White List policer for the specified interval."
    ::= { sonusSysPolicerIntervalEntry 10 }

sonusSysPolicerIntervalBlackListDiscardPacketCount OBJECT-TYPE
    SYNTAX          Counter64
    MAX-ACCESS      read-only
    STATUS          current
    DESCRIPTION     
            "The number of discarded packets for the 
             Black List policer for the specified interval."
    ::= { sonusSysPolicerIntervalEntry 11 }

sonusSysPolicerIntervalBlackListPeakDiscardRate OBJECT-TYPE
    SYNTAX          PerfIntervalCount
    MAX-ACCESS      read-only
    STATUS          current
    DESCRIPTION     
            "The peak discard rate for the  
             Black List policer for the specified interval."
    ::= { sonusSysPolicerIntervalEntry 12 }

sonusSysPolicerIntervalBlackListMinorAlarmCount OBJECT-TYPE
    SYNTAX          PerfIntervalCount
    MAX-ACCESS      read-only
    STATUS          current
    DESCRIPTION     
            "The number of minor alarms for the 
             Black List policer for the specified interval."
    ::= { sonusSysPolicerIntervalEntry 13 }

sonusSysPolicerIntervalBlackListMinorAlarmDuration OBJECT-TYPE
    SYNTAX          PerfIntervalCount
    MAX-ACCESS      read-only
    STATUS          current
    DESCRIPTION     
            "The duration of the minor alarms in seconds
             for the Black List policer for the specified interval."
    ::= { sonusSysPolicerIntervalEntry 14 }

sonusSysPolicerIntervalBlackListMajorAlarmCount OBJECT-TYPE
    SYNTAX          PerfIntervalCount
    MAX-ACCESS      read-only
    STATUS          current
    DESCRIPTION     
            "The number of of major alarms for the 
             Black List policer for the specified interval."
    ::= { sonusSysPolicerIntervalEntry 15 }

sonusSysPolicerIntervalBlackListMajorAlarmDuration OBJECT-TYPE
    SYNTAX          PerfIntervalCount
    MAX-ACCESS      read-only
    STATUS          current
    DESCRIPTION     
            "The duration of the major alarms in seconds
             for the Black List policer for the specified interval."
    ::= { sonusSysPolicerIntervalEntry 16 }

sonusSysPolicerIntervalDarkGrayListDiscardPacketCount OBJECT-TYPE
    SYNTAX          Counter64
    MAX-ACCESS      read-only
    STATUS          current
    DESCRIPTION     
            "The number of discarded packets for the 
             Dark Gray List policer for the specified interval."
    ::= { sonusSysPolicerIntervalEntry 17 }

sonusSysPolicerIntervalDarkGrayListAcceptPacketCount OBJECT-TYPE
    SYNTAX          Counter64
    MAX-ACCESS      read-only
    STATUS          current
    DESCRIPTION     
            "The number of accepted packets for the 
             Dark Gray List policer for the specified interval."
    ::= { sonusSysPolicerIntervalEntry 18 }

sonusSysPolicerIntervalDarkGrayListPeakDiscardRate OBJECT-TYPE
    SYNTAX          PerfIntervalCount
    MAX-ACCESS      read-only
    STATUS          current
    DESCRIPTION     
            "The peak discard rate for the  
             Dark Gray List policer for the specified interval."
    ::= { sonusSysPolicerIntervalEntry 19 }

sonusSysPolicerIntervalDarkGrayListMinorAlarmCount OBJECT-TYPE
    SYNTAX          PerfIntervalCount
    MAX-ACCESS      read-only
    STATUS          current
    DESCRIPTION     
            "The number of minor alarms for the 
             Dark Gray List policer for the specified interval."
    ::= { sonusSysPolicerIntervalEntry 20 }

sonusSysPolicerIntervalDarkGrayListMinorAlarmDuration OBJECT-TYPE
    SYNTAX          PerfIntervalCount
    MAX-ACCESS      read-only
    STATUS          current
    DESCRIPTION     
            "The duration of the minor alarms in seconds
             for the Dark Gray List policer for the specified interval."
    ::= { sonusSysPolicerIntervalEntry 21 }

sonusSysPolicerIntervalDarkGrayListMajorAlarmCount OBJECT-TYPE
    SYNTAX          PerfIntervalCount
    MAX-ACCESS      read-only
    STATUS          current
    DESCRIPTION     
            "The number of of major alarms for the 
             Dark Gray List policer for the specified interval."
    ::= { sonusSysPolicerIntervalEntry 22 }

sonusSysPolicerIntervalDarkGrayListMajorAlarmDuration OBJECT-TYPE
    SYNTAX          PerfIntervalCount
    MAX-ACCESS      read-only
    STATUS          current
    DESCRIPTION     
            "The duration of the major alarms in seconds
             for the Dark Gray List policer for the specified interval."
    ::= { sonusSysPolicerIntervalEntry 23 }

sonusSysPolicerIntervalServerProtectDiscardPacketCount OBJECT-TYPE
    SYNTAX          Counter64
    MAX-ACCESS      read-only
    STATUS          current
    DESCRIPTION     
            "The number of discarded packets for the 
             Server Protect policer for the specified interval."
    ::= { sonusSysPolicerIntervalEntry 24 }

sonusSysPolicerIntervalServerProtectAcceptPacketCount OBJECT-TYPE
    SYNTAX          Counter64
    MAX-ACCESS      read-only
    STATUS          current
    DESCRIPTION     
            "The number of accepted packets for the 
             Server Protect policer for the specified interval."
    ::= { sonusSysPolicerIntervalEntry 25 }

sonusSysPolicerIntervalServerProtectPeakDiscardRate OBJECT-TYPE
    SYNTAX          PerfIntervalCount
    MAX-ACCESS      read-only
    STATUS          current
    DESCRIPTION     
            "The peak discard rate for the  
             Server Protect policer for the specified interval."
    ::= { sonusSysPolicerIntervalEntry 26 }

sonusSysPolicerIntervalServerProtectMinorAlarmCount OBJECT-TYPE
    SYNTAX          PerfIntervalCount
    MAX-ACCESS      read-only
    STATUS          current
    DESCRIPTION     
            "The number of minor alarms for the 
             Server Protect policer for the specified interval."
    ::= { sonusSysPolicerIntervalEntry 27 }

sonusSysPolicerIntervalServerProtectMinorAlarmDuration OBJECT-TYPE
    SYNTAX          PerfIntervalCount
    MAX-ACCESS      read-only
    STATUS          current
    DESCRIPTION     
            "The duration of the minor alarms in seconds
             for the Server Protect policer for the specified interval."
    ::= { sonusSysPolicerIntervalEntry 28 }

sonusSysPolicerIntervalServerProtectMajorAlarmCount OBJECT-TYPE
    SYNTAX          PerfIntervalCount
    MAX-ACCESS      read-only
    STATUS          current
    DESCRIPTION     
            "The number of of major alarms for the 
             Server Protect policer for the specified interval."
    ::= { sonusSysPolicerIntervalEntry 29 }

sonusSysPolicerIntervalServerProtectMajorAlarmDuration OBJECT-TYPE
    SYNTAX          PerfIntervalCount
    MAX-ACCESS      read-only
    STATUS          current
    DESCRIPTION     
            "The duration of the major alarms in seconds
             for the Server Protect policer for the specified interval."
    ::= { sonusSysPolicerIntervalEntry 30 }

sonusSysPolicerIntervalMediaDiscardPacketCount OBJECT-TYPE
    SYNTAX          Counter64
    MAX-ACCESS      read-only
    STATUS          current
    DESCRIPTION     
            "The number of discarded packets for the 
             Media policer for the specified interval."
    ::= { sonusSysPolicerIntervalEntry 31 }

sonusSysPolicerIntervalMediaPeakDiscardRate OBJECT-TYPE
    SYNTAX          PerfIntervalCount
    MAX-ACCESS      read-only
    STATUS          current
    DESCRIPTION     
            "The peak discard rate for the  
             Media policer for the specified interval."
    ::= { sonusSysPolicerIntervalEntry 32 }

sonusSysPolicerIntervalMediaMinorAlarmCount OBJECT-TYPE
    SYNTAX          PerfIntervalCount
    MAX-ACCESS      read-only
    STATUS          current
    DESCRIPTION     
            "The number of minor alarms for the 
             Media policer for the specified interval."
    ::= { sonusSysPolicerIntervalEntry 33 }

sonusSysPolicerIntervalMediaMinorAlarmDuration OBJECT-TYPE
    SYNTAX          PerfIntervalCount
    MAX-ACCESS      read-only
    STATUS          current
    DESCRIPTION     
            "The duration of the minor alarms in seconds
             for the Media policer for the specified interval."
    ::= { sonusSysPolicerIntervalEntry 34 }

sonusSysPolicerIntervalMediaMajorAlarmCount OBJECT-TYPE
    SYNTAX          PerfIntervalCount
    MAX-ACCESS      read-only
    STATUS          current
    DESCRIPTION     
            "The number of of major alarms for the 
             Media policer for the specified interval."
    ::= { sonusSysPolicerIntervalEntry 35 }

sonusSysPolicerIntervalMediaMajorAlarmDuration OBJECT-TYPE
    SYNTAX          PerfIntervalCount
    MAX-ACCESS      read-only
    STATUS          current
    DESCRIPTION     
            "The duration of the major alarms in seconds
             for the Media policer for the specified interval."
    ::= { sonusSysPolicerIntervalEntry 36 }

sonusSysPolicerIntervalRogueMediaUnallocatedPortDiscardPacketCount OBJECT-TYPE
    SYNTAX          Counter64
    MAX-ACCESS      read-only
    STATUS          current
    DESCRIPTION     
            "The number of discarded packets for the 
             Rogue Media Unallocated Port policer for the specified interval."
    ::= { sonusSysPolicerIntervalEntry 37 }

sonusSysPolicerIntervalRogueMediaUnallocatedPortPeakDiscardRate OBJECT-TYPE
    SYNTAX          PerfIntervalCount
    MAX-ACCESS      read-only
    STATUS          current
    DESCRIPTION     
            "The peak discard rate for the  
             Rogue Media Unallocated Port policer for the specified interval."
    ::= { sonusSysPolicerIntervalEntry 38 }

sonusSysPolicerIntervalRogueMediaUnallocatedPortMinorAlarmCount OBJECT-TYPE
    SYNTAX          PerfIntervalCount
    MAX-ACCESS      read-only
    STATUS          current
    DESCRIPTION     
            "The number of minor alarms for the 
             Rogue Media Unallocated Port policer for the specified interval."
    ::= { sonusSysPolicerIntervalEntry 39 }

sonusSysPolicerIntervalRogueMediaUnallocatedPortMinorAlarmDuration OBJECT-TYPE
    SYNTAX          PerfIntervalCount
    MAX-ACCESS      read-only
    STATUS          current
    DESCRIPTION     
            "The duration of the minor alarms in seconds
             for the Rogue Media Unallocated Port policer for the specified interval."
    ::= { sonusSysPolicerIntervalEntry 40 }

sonusSysPolicerIntervalRogueMediaUnallocatedPortMajorAlarmCount OBJECT-TYPE
    SYNTAX          PerfIntervalCount
    MAX-ACCESS      read-only
    STATUS          current
    DESCRIPTION     
            "The number of of major alarms for the 
             Rogue Media Unallocated Port policer for the specified interval."
    ::= { sonusSysPolicerIntervalEntry 41 }

sonusSysPolicerIntervalRogueMediaUnallocatedPortMajorAlarmDuration OBJECT-TYPE
    SYNTAX          PerfIntervalCount
    MAX-ACCESS      read-only
    STATUS          current
    DESCRIPTION     
            "The duration of the major alarms in seconds
             for the Rogue Media Unallocated Port policer for the specified interval."
    ::= { sonusSysPolicerIntervalEntry 42 }

sonusSysPolicerIntervalRogueMediaMidCallBadDestDiscardPacketCount OBJECT-TYPE
    SYNTAX          Counter64
    MAX-ACCESS      read-only
    STATUS          current
    DESCRIPTION     
            "The number of discarded packets for the 
             Rogue Media Unallocated Port policer for the specified interval."
    ::= { sonusSysPolicerIntervalEntry 43 }

sonusSysPolicerIntervalRogueMediaMidCallBadDestPeakDiscardRate OBJECT-TYPE
    SYNTAX          PerfIntervalCount
    MAX-ACCESS      read-only
    STATUS          current
    DESCRIPTION     
            "The peak discard rate for the  
             Rogue Media Unallocated Port policer for the specified interval."
    ::= { sonusSysPolicerIntervalEntry 44 }

sonusSysPolicerIntervalRogueMediaMidCallBadDestMinorAlarmCount OBJECT-TYPE
    SYNTAX          PerfIntervalCount
    MAX-ACCESS      read-only
    STATUS          current
    DESCRIPTION     
            "The number of minor alarms for the 
             Rogue Media Unallocated Port policer for the specified interval."
    ::= { sonusSysPolicerIntervalEntry 45 }

sonusSysPolicerIntervalRogueMediaMidCallBadDestMinorAlarmDuration OBJECT-TYPE
    SYNTAX          PerfIntervalCount
    MAX-ACCESS      read-only
    STATUS          current
    DESCRIPTION     
            "The duration of the minor alarms in seconds
             for the Rogue Media Unallocated Port policer for the specified interval."
    ::= { sonusSysPolicerIntervalEntry 46 }

sonusSysPolicerIntervalRogueMediaMidCallBadDestMajorAlarmCount OBJECT-TYPE
    SYNTAX          PerfIntervalCount
    MAX-ACCESS      read-only
    STATUS          current
    DESCRIPTION     
            "The number of of major alarms for the 
             Rogue Media Unallocated Port policer for the specified interval."
    ::= { sonusSysPolicerIntervalEntry 47 }

sonusSysPolicerIntervalRogueMediaMidCallBadDestMajorAlarmDuration OBJECT-TYPE
    SYNTAX          PerfIntervalCount
    MAX-ACCESS      read-only
    STATUS          current
    DESCRIPTION     
            "The duration of the major alarms in seconds
             for the Rogue Media Unallocated Port policer for the specified interval."
    ::= { sonusSysPolicerIntervalEntry 48 }

sonusSysPolicerIntervalRogueMediaMidCallBadSourceDiscardPacketCount OBJECT-TYPE
    SYNTAX          Counter64
    MAX-ACCESS      read-only
    STATUS          current
    DESCRIPTION     
            "The number of discarded packets for the 
             Rogue Media Unallocated Port policer for the specified interval."
    ::= { sonusSysPolicerIntervalEntry 49 }

sonusSysPolicerIntervalRogueMediaMidCallBadSourcePeakDiscardRate OBJECT-TYPE
    SYNTAX          PerfIntervalCount
    MAX-ACCESS      read-only
    STATUS          current
    DESCRIPTION     
            "The peak discard rate for the  
             Rogue Media Unallocated Port policer for the specified interval."
    ::= { sonusSysPolicerIntervalEntry 50 }

sonusSysPolicerIntervalRogueMediaMidCallBadSourceMinorAlarmCount OBJECT-TYPE
    SYNTAX          PerfIntervalCount
    MAX-ACCESS      read-only
    STATUS          current
    DESCRIPTION     
            "The number of minor alarms for the 
             Rogue Media Unallocated Port policer for the specified interval."
    ::= { sonusSysPolicerIntervalEntry 51 }

sonusSysPolicerIntervalRogueMediaMidCallBadSourceMinorAlarmDuration OBJECT-TYPE
    SYNTAX          PerfIntervalCount
    MAX-ACCESS      read-only
    STATUS          current
    DESCRIPTION     
            "The duration of the minor alarms in seconds
             for the Rogue Media Unallocated Port policer for the specified interval."
    ::= { sonusSysPolicerIntervalEntry 52 }

sonusSysPolicerIntervalRogueMediaMidCallBadSourceMajorAlarmCount OBJECT-TYPE
    SYNTAX          PerfIntervalCount
    MAX-ACCESS      read-only
    STATUS          current
    DESCRIPTION     
            "The number of of major alarms for the 
             Rogue Media Unallocated Port policer for the specified interval."
    ::= { sonusSysPolicerIntervalEntry 53 }

sonusSysPolicerIntervalRogueMediaMidCallBadSourceMajorAlarmDuration OBJECT-TYPE
    SYNTAX          PerfIntervalCount
    MAX-ACCESS      read-only
    STATUS          current
    DESCRIPTION     
            "The duration of the major alarms in seconds
             for the Rogue Media Unallocated Port policer for the specified interval."
    ::= { sonusSysPolicerIntervalEntry 54 }

sonusSysPolicerIntervalRogueMediaMidCallBadVLanDiscardPacketCount OBJECT-TYPE
    SYNTAX          Counter64
    MAX-ACCESS      read-only
    STATUS          current
    DESCRIPTION     
            "The number of discarded packets for the 
             Rogue Media Unallocated Port policer for the specified interval."
    ::= { sonusSysPolicerIntervalEntry 55 }

sonusSysPolicerIntervalRogueMediaMidCallBadVLanPeakDiscardRate OBJECT-TYPE
    SYNTAX          PerfIntervalCount
    MAX-ACCESS      read-only
    STATUS          current
    DESCRIPTION     
            "The peak discard rate for the  
             Rogue Media Unallocated Port policer for the specified interval."
    ::= { sonusSysPolicerIntervalEntry 56 }

sonusSysPolicerIntervalRogueMediaMidCallBadVLanMinorAlarmCount OBJECT-TYPE
    SYNTAX          PerfIntervalCount
    MAX-ACCESS      read-only
    STATUS          current
    DESCRIPTION     
            "The number of minor alarms for the 
             Rogue Media Unallocated Port policer for the specified interval."
    ::= { sonusSysPolicerIntervalEntry 57 }

sonusSysPolicerIntervalRogueMediaMidCallBadVLanMinorAlarmDuration OBJECT-TYPE
    SYNTAX          PerfIntervalCount
    MAX-ACCESS      read-only
    STATUS          current
    DESCRIPTION     
            "The duration of the minor alarms in seconds
             for the Rogue Media Unallocated Port policer for the specified interval."
    ::= { sonusSysPolicerIntervalEntry 58 }

sonusSysPolicerIntervalRogueMediaMidCallBadVLanMajorAlarmCount OBJECT-TYPE
    SYNTAX          PerfIntervalCount
    MAX-ACCESS      read-only
    STATUS          current
    DESCRIPTION     
            "The number of of major alarms for the 
             Rogue Media Unallocated Port policer for the specified interval."
    ::= { sonusSysPolicerIntervalEntry 59 }

sonusSysPolicerIntervalRogueMediaMidCallBadVLanMajorAlarmDuration OBJECT-TYPE
    SYNTAX          PerfIntervalCount
    MAX-ACCESS      read-only
    STATUS          current
    DESCRIPTION     
            "The duration of the major alarms in seconds
             for the Rogue Media Unallocated Port policer for the specified interval."
    ::= { sonusSysPolicerIntervalEntry 60 }

sonusSysPolicerIntervalRogueMediaInGracePeriodDiscardPacketCount OBJECT-TYPE
    SYNTAX          Counter64
    MAX-ACCESS      read-only
    STATUS          current
    DESCRIPTION     
            "The number of discarded packets for the 
             Rogue Media In Grace Period policer for the specified interval."
    ::= { sonusSysPolicerIntervalEntry 61 }

sonusSysPolicerIntervalRogueMediaInGracePeriodPeakDiscardRate OBJECT-TYPE
    SYNTAX          PerfIntervalCount
    MAX-ACCESS      read-only
    STATUS          current
    DESCRIPTION     
            "The peak discard rate for the  
             Rogue Media In Grace Period policer for the specified interval."
    ::= { sonusSysPolicerIntervalEntry 62 }

sonusSysPolicerIntervalLightGrayListDiscardPacketCount OBJECT-TYPE
    SYNTAX          Counter64
    MAX-ACCESS      read-only
    STATUS          current
    DESCRIPTION     
            "The number of discarded packets for the 
             Light Gray List policer for the specified interval."
    ::= { sonusSysPolicerIntervalEntry 63 }

sonusSysPolicerIntervalLightGrayListPeakDiscardRate OBJECT-TYPE
    SYNTAX          PerfIntervalCount
    MAX-ACCESS      read-only
    STATUS          current
    DESCRIPTION     
            "The peak discard rate for the  
             Light Gray List policer for the specified interval."
    ::= { sonusSysPolicerIntervalEntry 64 }

sonusSysPolicerIntervalLightGrayListMinorAlarmCount OBJECT-TYPE
    SYNTAX          PerfIntervalCount
    MAX-ACCESS      read-only
    STATUS          current
    DESCRIPTION     
            "The number of minor alarms for the 
             Light Gray List policer for the specified interval."
    ::= { sonusSysPolicerIntervalEntry 65 }

sonusSysPolicerIntervalLightGrayListMinorAlarmDuration OBJECT-TYPE
    SYNTAX          PerfIntervalCount
    MAX-ACCESS      read-only
    STATUS          current
    DESCRIPTION     
            "The duration of the minor alarms in seconds
             for the Light Gray List policer for the specified interval."
    ::= { sonusSysPolicerIntervalEntry 66 }

sonusSysPolicerIntervalLightGrayListMajorAlarmCount OBJECT-TYPE
    SYNTAX          PerfIntervalCount
    MAX-ACCESS      read-only
    STATUS          current
    DESCRIPTION     
            "The number of of major alarms for the 
             Light Gray List policer for the specified interval."
    ::= { sonusSysPolicerIntervalEntry 67 }

sonusSysPolicerIntervalLightGrayListMajorAlarmDuration OBJECT-TYPE
    SYNTAX          PerfIntervalCount
    MAX-ACCESS      read-only
    STATUS          current
    DESCRIPTION     
            "The duration of the major alarms in seconds
             for the Light Gray List policer for the specified interval."
    ::= { sonusSysPolicerIntervalEntry 68 }

sonusSysPolicerIntervalVLanDiscardPacketCount OBJECT-TYPE
    SYNTAX          Counter64
    MAX-ACCESS      read-only
    STATUS          current
    DESCRIPTION     
            "The number of discarded packets for the 
             VLAN policer for the specified interval."
    ::= { sonusSysPolicerIntervalEntry 69 }

sonusSysPolicerIntervalVLanPeakDiscardRate OBJECT-TYPE
    SYNTAX          PerfIntervalCount
    MAX-ACCESS      read-only
    STATUS          current
    DESCRIPTION     
            "The peak discard rate for the  
             VLAN policer for the specified interval."
    ::= { sonusSysPolicerIntervalEntry 70 }

sonusSysPolicerIntervalVLanMinorAlarmCount OBJECT-TYPE
    SYNTAX          PerfIntervalCount
    MAX-ACCESS      read-only
    STATUS          current
    DESCRIPTION     
            "The number of minor alarms for the 
             VLAN policer for the specified interval."
    ::= { sonusSysPolicerIntervalEntry 71 }

sonusSysPolicerIntervalVLanMinorAlarmDuration OBJECT-TYPE
    SYNTAX          PerfIntervalCount
    MAX-ACCESS      read-only
    STATUS          current
    DESCRIPTION     
            "The duration of the minor alarms in seconds
             for the VLAN policer for the specified interval."
    ::= { sonusSysPolicerIntervalEntry 72 }

sonusSysPolicerIntervalVLanMajorAlarmCount OBJECT-TYPE
    SYNTAX          PerfIntervalCount
    MAX-ACCESS      read-only
    STATUS          current
    DESCRIPTION     
            "The number of of major alarms for the 
             VLAN policer for the specified interval."
    ::= { sonusSysPolicerIntervalEntry 73 }

sonusSysPolicerIntervalVLanMajorAlarmDuration OBJECT-TYPE
    SYNTAX          PerfIntervalCount
    MAX-ACCESS      read-only
    STATUS          current
    DESCRIPTION     
            "The duration of the major alarms in seconds
             for the VLAN policer for the specified interval."
    ::= { sonusSysPolicerIntervalEntry 74 }

sonusServerPolicerCurrentTable OBJECT-TYPE
    SYNTAX          SEQUENCE OF SonusServerPolicerCurrentEntry
    MAX-ACCESS      not-accessible
    STATUS          current
    DESCRIPTION     
            "The Sonus Server Policer Current table."
    ::= { sonusPolicerStatisticsObjects 3 }

sonusServerPolicerCurrentEntry OBJECT-TYPE
    SYNTAX          SonusServerPolicerCurrentEntry
    MAX-ACCESS      not-accessible
    STATUS          current
    DESCRIPTION     
            "An entry in the Sonus Server Policer Current table."
    INDEX           { sonusServerPolicerCurrentShelfIndex, 
                      sonusServerPolicerCurrentSlotIndex }
    ::= { sonusServerPolicerCurrentTable 1 }

SonusServerPolicerCurrentEntry ::=
    SEQUENCE {
        sonusServerPolicerCurrentShelfIndex   SonusShelfIndex,
        sonusServerPolicerCurrentSlotIndex  SonusSlotIndex,
        sonusServerPolicerCurrentWhiteListDiscardPacketCount                    Counter64,
        sonusServerPolicerCurrentWhiteListPeakDiscardRate                 PerfCurrentCount,
        sonusServerPolicerCurrentWhiteListMinorAlarmCount                 PerfCurrentCount,
        sonusServerPolicerCurrentWhiteListMinorAlarmDuration                    PerfCurrentCount,
        sonusServerPolicerCurrentWhiteListMajorAlarmCount                 PerfCurrentCount,
        sonusServerPolicerCurrentWhiteListMajorAlarmDuration                    PerfCurrentCount,
        sonusServerPolicerCurrentBlackListDiscardPacketCount                    Counter64,
        sonusServerPolicerCurrentBlackListPeakDiscardRate                 PerfCurrentCount,
        sonusServerPolicerCurrentBlackListMinorAlarmCount                 PerfCurrentCount,
        sonusServerPolicerCurrentBlackListMinorAlarmDuration                    PerfCurrentCount,
        sonusServerPolicerCurrentBlackListMajorAlarmCount                 PerfCurrentCount,
        sonusServerPolicerCurrentBlackListMajorAlarmDuration                    PerfCurrentCount,
        sonusServerPolicerCurrentDarkGrayListDiscardPacketCount                       Counter64,
        sonusServerPolicerCurrentDarkGrayListAcceptPacketCount                      Counter64,
        sonusServerPolicerCurrentDarkGrayListPeakDiscardRate                    PerfCurrentCount,
        sonusServerPolicerCurrentDarkGrayListMinorAlarmCount                    PerfCurrentCount,
        sonusServerPolicerCurrentDarkGrayListMinorAlarmDuration                       PerfCurrentCount,
        sonusServerPolicerCurrentDarkGrayListMajorAlarmCount                    PerfCurrentCount,
        sonusServerPolicerCurrentDarkGrayListMajorAlarmDuration                       PerfCurrentCount,
        sonusServerPolicerCurrentServerProtectDiscardPacketCount                        Counter64,
        sonusServerPolicerCurrentServerProtectAcceptPacketCount                       Counter64,
        sonusServerPolicerCurrentServerProtectPeakDiscardRate                     PerfCurrentCount,
        sonusServerPolicerCurrentServerProtectMinorAlarmCount                     PerfCurrentCount,
        sonusServerPolicerCurrentServerProtectMinorAlarmDuration                        PerfCurrentCount,
        sonusServerPolicerCurrentServerProtectMajorAlarmCount                     PerfCurrentCount,
        sonusServerPolicerCurrentServerProtectMajorAlarmDuration                        PerfCurrentCount,
        sonusServerPolicerCurrentMediaDiscardPacketCount                Counter64,
        sonusServerPolicerCurrentMediaPeakDiscardRate             PerfCurrentCount,
        sonusServerPolicerCurrentMediaMinorAlarmCount             PerfCurrentCount,
        sonusServerPolicerCurrentMediaMinorAlarmDuration                PerfCurrentCount,
        sonusServerPolicerCurrentMediaMajorAlarmCount             PerfCurrentCount,
        sonusServerPolicerCurrentMediaMajorAlarmDuration                PerfCurrentCount,
        sonusServerPolicerCurrentRogueMediaUnallocatedPortDiscardPacketCount                                    Counter64,
        sonusServerPolicerCurrentRogueMediaUnallocatedPortPeakDiscardRate                                 PerfCurrentCount,
        sonusServerPolicerCurrentRogueMediaUnallocatedPortMinorAlarmCount                                 PerfCurrentCount,
        sonusServerPolicerCurrentRogueMediaUnallocatedPortMinorAlarmDuration                                    PerfCurrentCount,
        sonusServerPolicerCurrentRogueMediaUnallocatedPortMajorAlarmCount                                 PerfCurrentCount,
        sonusServerPolicerCurrentRogueMediaUnallocatedPortMajorAlarmDuration                                    PerfCurrentCount,
        sonusServerPolicerCurrentRogueMediaMidCallBadDestDiscardPacketCount                                   Counter64,
        sonusServerPolicerCurrentRogueMediaMidCallBadDestPeakDiscardRate                                PerfCurrentCount,
        sonusServerPolicerCurrentRogueMediaMidCallBadDestMinorAlarmCount                                PerfCurrentCount,
        sonusServerPolicerCurrentRogueMediaMidCallBadDestMinorAlarmDuration                                   PerfCurrentCount,
        sonusServerPolicerCurrentRogueMediaMidCallBadDestMajorAlarmCount                                PerfCurrentCount,
        sonusServerPolicerCurrentRogueMediaMidCallBadDestMajorAlarmDuration                                   PerfCurrentCount,
        sonusServerPolicerCurrentRogueMediaMidCallBadSourceDiscardPacketCount                                     Counter64,
        sonusServerPolicerCurrentRogueMediaMidCallBadSourcePeakDiscardRate                                  PerfCurrentCount,
        sonusServerPolicerCurrentRogueMediaMidCallBadSourceMinorAlarmCount                                  PerfCurrentCount,
        sonusServerPolicerCurrentRogueMediaMidCallBadSourceMinorAlarmDuration                                     PerfCurrentCount,
        sonusServerPolicerCurrentRogueMediaMidCallBadSourceMajorAlarmCount                                  PerfCurrentCount,
        sonusServerPolicerCurrentRogueMediaMidCallBadSourceMajorAlarmDuration                                     PerfCurrentCount,
        sonusServerPolicerCurrentRogueMediaMidCallBadVLanDiscardPacketCount                                   Counter64,
        sonusServerPolicerCurrentRogueMediaMidCallBadVLanPeakDiscardRate                                PerfCurrentCount,
        sonusServerPolicerCurrentRogueMediaMidCallBadVLanMinorAlarmCount                                PerfCurrentCount,
        sonusServerPolicerCurrentRogueMediaMidCallBadVLanMinorAlarmDuration                                   PerfCurrentCount,
        sonusServerPolicerCurrentRogueMediaMidCallBadVLanMajorAlarmCount                                PerfCurrentCount,
        sonusServerPolicerCurrentRogueMediaMidCallBadVLanMajorAlarmDuration                                   PerfCurrentCount,
        sonusServerPolicerCurrentRogueMediaInGracePeriodDiscardPacketCount                                  Counter64,
        sonusServerPolicerCurrentRogueMediaInGracePeriodPeakDiscardRate                               PerfCurrentCount,
        sonusServerPolicerCurrentLightGrayListDiscardPacketCount                        Counter64,
        sonusServerPolicerCurrentLightGrayListPeakDiscardRate                     PerfCurrentCount,
        sonusServerPolicerCurrentLightGrayListMinorAlarmCount                     PerfCurrentCount,
        sonusServerPolicerCurrentLightGrayListMinorAlarmDuration                        PerfCurrentCount,
        sonusServerPolicerCurrentLightGrayListMajorAlarmCount                     PerfCurrentCount,
        sonusServerPolicerCurrentLightGrayListMajorAlarmDuration                        PerfCurrentCount,
        sonusServerPolicerCurrentVLanDiscardPacketCount               Counter64,
        sonusServerPolicerCurrentVLanPeakDiscardRate            PerfCurrentCount,
        sonusServerPolicerCurrentVLanMinorAlarmCount            PerfCurrentCount,
        sonusServerPolicerCurrentVLanMinorAlarmDuration               PerfCurrentCount,
        sonusServerPolicerCurrentVLanMajorAlarmCount            PerfCurrentCount,
        sonusServerPolicerCurrentVLanMajorAlarmDuration               PerfCurrentCount
    }

sonusServerPolicerCurrentShelfIndex OBJECT-TYPE
    SYNTAX          SonusShelfIndex
    MAX-ACCESS      read-only
    STATUS          current
    DESCRIPTION     
            "The shelf index into the sonusServerPolicerCurrentTable."
    ::= { sonusServerPolicerCurrentEntry 1 }

sonusServerPolicerCurrentSlotIndex OBJECT-TYPE
    SYNTAX          SonusSlotIndex
    MAX-ACCESS      read-only
    STATUS          current
    DESCRIPTION     
            "The slot index into the sonusServerPolicerCurrentTable."
    ::= { sonusServerPolicerCurrentEntry 2 }

sonusServerPolicerCurrentWhiteListDiscardPacketCount OBJECT-TYPE
    SYNTAX          Counter64
    MAX-ACCESS      read-only
    STATUS          current
    DESCRIPTION     
            "The current number of discarded packets for the 
             White List policer."
    ::= { sonusServerPolicerCurrentEntry 3 }

sonusServerPolicerCurrentWhiteListPeakDiscardRate OBJECT-TYPE
    SYNTAX          PerfCurrentCount
    MAX-ACCESS      read-only
    STATUS          current
    DESCRIPTION     
            "The current peak discard rate for the 
             White List policer."
    ::= { sonusServerPolicerCurrentEntry 4 }

sonusServerPolicerCurrentWhiteListMinorAlarmCount OBJECT-TYPE
    SYNTAX          PerfCurrentCount
    MAX-ACCESS      read-only
    STATUS          current
    DESCRIPTION     
            "The current number of minor alarms for the 
             White List policer."
    ::= { sonusServerPolicerCurrentEntry 5 }

sonusServerPolicerCurrentWhiteListMinorAlarmDuration OBJECT-TYPE
    SYNTAX          PerfCurrentCount
    MAX-ACCESS      read-only
    STATUS          current
    DESCRIPTION     
            "The current duration of the minor alarms in seconds
             for the White List policer."
    ::= { sonusServerPolicerCurrentEntry 6 }

sonusServerPolicerCurrentWhiteListMajorAlarmCount OBJECT-TYPE
    SYNTAX          PerfCurrentCount
    MAX-ACCESS      read-only
    STATUS          current
    DESCRIPTION     
            "The current number of major alarms for the 
             White List policer."
    ::= { sonusServerPolicerCurrentEntry 7 }

sonusServerPolicerCurrentWhiteListMajorAlarmDuration OBJECT-TYPE
    SYNTAX          PerfCurrentCount
    MAX-ACCESS      read-only
    STATUS          current
    DESCRIPTION     
            "The current duration of the major alarms in seconds
             for the White List policer."
    ::= { sonusServerPolicerCurrentEntry 8 }

sonusServerPolicerCurrentBlackListDiscardPacketCount OBJECT-TYPE
    SYNTAX          Counter64
    MAX-ACCESS      read-only
    STATUS          current
    DESCRIPTION     
            "The current number of discarded packets for the 
             Black List policer."
    ::= { sonusServerPolicerCurrentEntry 9 }

sonusServerPolicerCurrentBlackListPeakDiscardRate OBJECT-TYPE
    SYNTAX          PerfCurrentCount
    MAX-ACCESS      read-only
    STATUS          current
    DESCRIPTION     
            "The current peak discard rate for the 
             Black List policer."
    ::= { sonusServerPolicerCurrentEntry 10 }

sonusServerPolicerCurrentBlackListMinorAlarmCount OBJECT-TYPE
    SYNTAX          PerfCurrentCount
    MAX-ACCESS      read-only
    STATUS          current
    DESCRIPTION     
            "The current number of minor alarms for the 
             Black List policer."
    ::= { sonusServerPolicerCurrentEntry 11 }

sonusServerPolicerCurrentBlackListMinorAlarmDuration OBJECT-TYPE
    SYNTAX          PerfCurrentCount
    MAX-ACCESS      read-only
    STATUS          current
    DESCRIPTION     
            "The current duration of the minor alarms in seconds
             for the Black List policer."
    ::= { sonusServerPolicerCurrentEntry 12 }

sonusServerPolicerCurrentBlackListMajorAlarmCount OBJECT-TYPE
    SYNTAX          PerfCurrentCount
    MAX-ACCESS      read-only
    STATUS          current
    DESCRIPTION     
            "The current number of major alarms for the 
             Black List policer."
    ::= { sonusServerPolicerCurrentEntry 13 }

sonusServerPolicerCurrentBlackListMajorAlarmDuration OBJECT-TYPE
    SYNTAX          PerfCurrentCount
    MAX-ACCESS      read-only
    STATUS          current
    DESCRIPTION     
            "The current duration of the major alarms in seconds
             for the Black List policer."
    ::= { sonusServerPolicerCurrentEntry 14 }

sonusServerPolicerCurrentDarkGrayListDiscardPacketCount OBJECT-TYPE
    SYNTAX          Counter64
    MAX-ACCESS      read-only
    STATUS          current
    DESCRIPTION     
            "The current number of discarded packets for the 
             Dark Gray List policer."
    ::= { sonusServerPolicerCurrentEntry 15 }

sonusServerPolicerCurrentDarkGrayListAcceptPacketCount OBJECT-TYPE
    SYNTAX          Counter64
    MAX-ACCESS      read-only
    STATUS          current
    DESCRIPTION     
            "The current number of accepted packets for the
             Dark Gray List policer."
    ::= { sonusServerPolicerCurrentEntry 16 }

sonusServerPolicerCurrentDarkGrayListPeakDiscardRate OBJECT-TYPE
    SYNTAX          PerfCurrentCount
    MAX-ACCESS      read-only
    STATUS          current
    DESCRIPTION     
            "The current peak discard rate for the 
             Dark Gray List policer."
    ::= { sonusServerPolicerCurrentEntry 17 }

sonusServerPolicerCurrentDarkGrayListMinorAlarmCount OBJECT-TYPE
    SYNTAX          PerfCurrentCount
    MAX-ACCESS      read-only
    STATUS          current
    DESCRIPTION     
            "The current number of minor alarms for the 
             Dark Gray List policer."
    ::= { sonusServerPolicerCurrentEntry 18 }

sonusServerPolicerCurrentDarkGrayListMinorAlarmDuration OBJECT-TYPE
    SYNTAX          PerfCurrentCount
    MAX-ACCESS      read-only
    STATUS          current
    DESCRIPTION     
            "The current duration of the minor alarms in seconds
             for the Dark Gray List policer."
    ::= { sonusServerPolicerCurrentEntry 19 }

sonusServerPolicerCurrentDarkGrayListMajorAlarmCount OBJECT-TYPE
    SYNTAX          PerfCurrentCount
    MAX-ACCESS      read-only
    STATUS          current
    DESCRIPTION     
            "The current number of major alarms for the 
             Dark Gray List policer."
    ::= { sonusServerPolicerCurrentEntry 20 }

sonusServerPolicerCurrentDarkGrayListMajorAlarmDuration OBJECT-TYPE
    SYNTAX          PerfCurrentCount
    MAX-ACCESS      read-only
    STATUS          current
    DESCRIPTION     
            "The current duration of the major alarms in seconds
             for the Dark Gray List policer."
    ::= { sonusServerPolicerCurrentEntry 21 }

sonusServerPolicerCurrentServerProtectDiscardPacketCount OBJECT-TYPE
    SYNTAX          Counter64
    MAX-ACCESS      read-only
    STATUS          current
    DESCRIPTION     
            "The current number of discarded packets for the 
             Server Protect policer."
    ::= { sonusServerPolicerCurrentEntry 22 }

sonusServerPolicerCurrentServerProtectAcceptPacketCount OBJECT-TYPE
    SYNTAX          Counter64
    MAX-ACCESS      read-only
    STATUS          current
    DESCRIPTION     
            "The current number of accepted packets for the
             Server Protect policer."
    ::= { sonusServerPolicerCurrentEntry 23 }

sonusServerPolicerCurrentServerProtectPeakDiscardRate OBJECT-TYPE
    SYNTAX          PerfCurrentCount
    MAX-ACCESS      read-only
    STATUS          current
    DESCRIPTION     
            "The current peak discard rate for the 
             Server Protect policer."
    ::= { sonusServerPolicerCurrentEntry 24 }

sonusServerPolicerCurrentServerProtectMinorAlarmCount OBJECT-TYPE
    SYNTAX          PerfCurrentCount
    MAX-ACCESS      read-only
    STATUS          current
    DESCRIPTION     
            "The current number of minor alarms for the 
             Server Protect policer."
    ::= { sonusServerPolicerCurrentEntry 25 }

sonusServerPolicerCurrentServerProtectMinorAlarmDuration OBJECT-TYPE
    SYNTAX          PerfCurrentCount
    MAX-ACCESS      read-only
    STATUS          current
    DESCRIPTION     
            "The current duration of the minor alarms in seconds
             for the Server Protect policer."
    ::= { sonusServerPolicerCurrentEntry 26 }

sonusServerPolicerCurrentServerProtectMajorAlarmCount OBJECT-TYPE
    SYNTAX          PerfCurrentCount
    MAX-ACCESS      read-only
    STATUS          current
    DESCRIPTION     
            "The current number of major alarms for the 
             Server Protect policer."
    ::= { sonusServerPolicerCurrentEntry 27 }

sonusServerPolicerCurrentServerProtectMajorAlarmDuration OBJECT-TYPE
    SYNTAX          PerfCurrentCount
    MAX-ACCESS      read-only
    STATUS          current
    DESCRIPTION     
            "The current duration of the major alarms in seconds
             for the Server Protect policer."
    ::= { sonusServerPolicerCurrentEntry 28 }

sonusServerPolicerCurrentMediaDiscardPacketCount OBJECT-TYPE
    SYNTAX          Counter64
    MAX-ACCESS      read-only
    STATUS          current
    DESCRIPTION     
            "The current number of discarded packets for the 
             Media policer."
    ::= { sonusServerPolicerCurrentEntry 29 }

sonusServerPolicerCurrentMediaPeakDiscardRate OBJECT-TYPE
    SYNTAX          PerfCurrentCount
    MAX-ACCESS      read-only
    STATUS          current
    DESCRIPTION     
            "The current peak discard rate for the 
             Media policer."
    ::= { sonusServerPolicerCurrentEntry 30 }

sonusServerPolicerCurrentMediaMinorAlarmCount OBJECT-TYPE
    SYNTAX          PerfCurrentCount
    MAX-ACCESS      read-only
    STATUS          current
    DESCRIPTION     
            "The current number of minor alarms for the 
             Media policer."
    ::= { sonusServerPolicerCurrentEntry 31 }

sonusServerPolicerCurrentMediaMinorAlarmDuration OBJECT-TYPE
    SYNTAX          PerfCurrentCount
    MAX-ACCESS      read-only
    STATUS          current
    DESCRIPTION     
            "The current duration of the minor alarms in seconds
             for the Media policer."
    ::= { sonusServerPolicerCurrentEntry 32 }

sonusServerPolicerCurrentMediaMajorAlarmCount OBJECT-TYPE
    SYNTAX          PerfCurrentCount
    MAX-ACCESS      read-only
    STATUS          current
    DESCRIPTION     
            "The current number of major alarms for the 
             Media policer."
    ::= { sonusServerPolicerCurrentEntry 33 }

sonusServerPolicerCurrentMediaMajorAlarmDuration OBJECT-TYPE
    SYNTAX          PerfCurrentCount
    MAX-ACCESS      read-only
    STATUS          current
    DESCRIPTION     
            "The current duration of the major alarms in seconds
             for the Media policer."
    ::= { sonusServerPolicerCurrentEntry 34 }

sonusServerPolicerCurrentRogueMediaUnallocatedPortDiscardPacketCount OBJECT-TYPE
    SYNTAX          Counter64
    MAX-ACCESS      read-only
    STATUS          current
    DESCRIPTION     
            "The current number of discarded packets for the 
             policer."
    ::= { sonusServerPolicerCurrentEntry 35 }

sonusServerPolicerCurrentRogueMediaUnallocatedPortPeakDiscardRate OBJECT-TYPE
    SYNTAX          PerfCurrentCount
    MAX-ACCESS      read-only
    STATUS          current
    DESCRIPTION     
            "The current peak discard rate for the 
             policer."
    ::= { sonusServerPolicerCurrentEntry 36 }

sonusServerPolicerCurrentRogueMediaUnallocatedPortMinorAlarmCount OBJECT-TYPE
    SYNTAX          PerfCurrentCount
    MAX-ACCESS      read-only
    STATUS          current
    DESCRIPTION     
            "The current number of minor alarms for the 
             policer."
    ::= { sonusServerPolicerCurrentEntry 37 }

sonusServerPolicerCurrentRogueMediaUnallocatedPortMinorAlarmDuration OBJECT-TYPE
    SYNTAX          PerfCurrentCount
    MAX-ACCESS      read-only
    STATUS          current
    DESCRIPTION     
            "The current duration of the minor alarms in seconds
             for the  policer."
    ::= { sonusServerPolicerCurrentEntry 38 }

sonusServerPolicerCurrentRogueMediaUnallocatedPortMajorAlarmCount OBJECT-TYPE
    SYNTAX          PerfCurrentCount
    MAX-ACCESS      read-only
    STATUS          current
    DESCRIPTION     
            "The current number of major alarms for the 
             policer."
    ::= { sonusServerPolicerCurrentEntry 39 }

sonusServerPolicerCurrentRogueMediaUnallocatedPortMajorAlarmDuration OBJECT-TYPE
    SYNTAX          PerfCurrentCount
    MAX-ACCESS      read-only
    STATUS          current
    DESCRIPTION     
            "The current duration of the major alarms in seconds
             for the  policer."
    ::= { sonusServerPolicerCurrentEntry 40 }

sonusServerPolicerCurrentRogueMediaMidCallBadDestDiscardPacketCount OBJECT-TYPE
    SYNTAX          Counter64
    MAX-ACCESS      read-only
    STATUS          current
    DESCRIPTION     
            "The current number of discarded packets for the 
             policer."
    ::= { sonusServerPolicerCurrentEntry 41 }

sonusServerPolicerCurrentRogueMediaMidCallBadDestPeakDiscardRate OBJECT-TYPE
    SYNTAX          PerfCurrentCount
    MAX-ACCESS      read-only
    STATUS          current
    DESCRIPTION     
            "The current peak discard rate for the 
             policer."
    ::= { sonusServerPolicerCurrentEntry 42 }

sonusServerPolicerCurrentRogueMediaMidCallBadDestMinorAlarmCount OBJECT-TYPE
    SYNTAX          PerfCurrentCount
    MAX-ACCESS      read-only
    STATUS          current
    DESCRIPTION     
            "The current number of minor alarms for the 
             policer."
    ::= { sonusServerPolicerCurrentEntry 43 }

sonusServerPolicerCurrentRogueMediaMidCallBadDestMinorAlarmDuration OBJECT-TYPE
    SYNTAX          PerfCurrentCount
    MAX-ACCESS      read-only
    STATUS          current
    DESCRIPTION     
            "The current duration of the minor alarms in seconds
             for the  policer."
    ::= { sonusServerPolicerCurrentEntry 44 }

sonusServerPolicerCurrentRogueMediaMidCallBadDestMajorAlarmCount OBJECT-TYPE
    SYNTAX          PerfCurrentCount
    MAX-ACCESS      read-only
    STATUS          current
    DESCRIPTION     
            "The current number of major alarms for the 
             policer."
    ::= { sonusServerPolicerCurrentEntry 45 }

sonusServerPolicerCurrentRogueMediaMidCallBadDestMajorAlarmDuration OBJECT-TYPE
    SYNTAX          PerfCurrentCount
    MAX-ACCESS      read-only
    STATUS          current
    DESCRIPTION     
            "The current duration of the major alarms in seconds
             for the  policer."
    ::= { sonusServerPolicerCurrentEntry 46 }

sonusServerPolicerCurrentRogueMediaMidCallBadSourceDiscardPacketCount OBJECT-TYPE
    SYNTAX          Counter64
    MAX-ACCESS      read-only
    STATUS          current
    DESCRIPTION     
            "The current number of discarded packets for the 
             policer."
    ::= { sonusServerPolicerCurrentEntry 47 }

sonusServerPolicerCurrentRogueMediaMidCallBadSourcePeakDiscardRate OBJECT-TYPE
    SYNTAX          PerfCurrentCount
    MAX-ACCESS      read-only
    STATUS          current
    DESCRIPTION     
            "The current peak discard rate for the 
             policer."
    ::= { sonusServerPolicerCurrentEntry 48 }

sonusServerPolicerCurrentRogueMediaMidCallBadSourceMinorAlarmCount OBJECT-TYPE
    SYNTAX          PerfCurrentCount
    MAX-ACCESS      read-only
    STATUS          current
    DESCRIPTION     
            "The current number of minor alarms for the 
             policer."
    ::= { sonusServerPolicerCurrentEntry 49 }

sonusServerPolicerCurrentRogueMediaMidCallBadSourceMinorAlarmDuration OBJECT-TYPE
    SYNTAX          PerfCurrentCount
    MAX-ACCESS      read-only
    STATUS          current
    DESCRIPTION     
            "The current duration of the minor alarms in seconds
             for the  policer."
    ::= { sonusServerPolicerCurrentEntry 50 }

sonusServerPolicerCurrentRogueMediaMidCallBadSourceMajorAlarmCount OBJECT-TYPE
    SYNTAX          PerfCurrentCount
    MAX-ACCESS      read-only
    STATUS          current
    DESCRIPTION     
            "The current number of major alarms for the 
             policer."
    ::= { sonusServerPolicerCurrentEntry 51 }

sonusServerPolicerCurrentRogueMediaMidCallBadSourceMajorAlarmDuration OBJECT-TYPE
    SYNTAX          PerfCurrentCount
    MAX-ACCESS      read-only
    STATUS          current
    DESCRIPTION     
            "The current duration of the major alarms in seconds
             for the  policer."
    ::= { sonusServerPolicerCurrentEntry 52 }

sonusServerPolicerCurrentRogueMediaMidCallBadVLanDiscardPacketCount OBJECT-TYPE
    SYNTAX          Counter64
    MAX-ACCESS      read-only
    STATUS          current
    DESCRIPTION     
            "The current number of discarded packets for the 
             policer."
    ::= { sonusServerPolicerCurrentEntry 53 }

sonusServerPolicerCurrentRogueMediaMidCallBadVLanPeakDiscardRate OBJECT-TYPE
    SYNTAX          PerfCurrentCount
    MAX-ACCESS      read-only
    STATUS          current
    DESCRIPTION     
            "The current peak discard rate for the 
             policer."
    ::= { sonusServerPolicerCurrentEntry 54 }

sonusServerPolicerCurrentRogueMediaMidCallBadVLanMinorAlarmCount OBJECT-TYPE
    SYNTAX          PerfCurrentCount
    MAX-ACCESS      read-only
    STATUS          current
    DESCRIPTION     
            "The current number of minor alarms for the 
             policer."
    ::= { sonusServerPolicerCurrentEntry 55 }

sonusServerPolicerCurrentRogueMediaMidCallBadVLanMinorAlarmDuration OBJECT-TYPE
    SYNTAX          PerfCurrentCount
    MAX-ACCESS      read-only
    STATUS          current
    DESCRIPTION     
            "The current duration of the minor alarms in seconds
             for the  policer."
    ::= { sonusServerPolicerCurrentEntry 56 }

sonusServerPolicerCurrentRogueMediaMidCallBadVLanMajorAlarmCount OBJECT-TYPE
    SYNTAX          PerfCurrentCount
    MAX-ACCESS      read-only
    STATUS          current
    DESCRIPTION     
            "The current number of major alarms for the 
             policer."
    ::= { sonusServerPolicerCurrentEntry 57 }

sonusServerPolicerCurrentRogueMediaMidCallBadVLanMajorAlarmDuration OBJECT-TYPE
    SYNTAX          PerfCurrentCount
    MAX-ACCESS      read-only
    STATUS          current
    DESCRIPTION     
            "The current duration of the major alarms in seconds
             for the  policer."
    ::= { sonusServerPolicerCurrentEntry 58 }

sonusServerPolicerCurrentRogueMediaInGracePeriodDiscardPacketCount OBJECT-TYPE
    SYNTAX          Counter64
    MAX-ACCESS      read-only
    STATUS          current
    DESCRIPTION     
            "The current number of discarded packets for the 
             policer."
    ::= { sonusServerPolicerCurrentEntry 59 }

sonusServerPolicerCurrentRogueMediaInGracePeriodPeakDiscardRate OBJECT-TYPE
    SYNTAX          PerfCurrentCount
    MAX-ACCESS      read-only
    STATUS          current
    DESCRIPTION     
            "The current peak discard rate for the 
             policer."
    ::= { sonusServerPolicerCurrentEntry 60 }

sonusServerPolicerCurrentLightGrayListDiscardPacketCount OBJECT-TYPE
    SYNTAX          Counter64
    MAX-ACCESS      read-only
    STATUS          current
    DESCRIPTION     
            "The current number of discarded packets for the 
             Light Gray List policer."
    ::= { sonusServerPolicerCurrentEntry 61 }

sonusServerPolicerCurrentLightGrayListPeakDiscardRate OBJECT-TYPE
    SYNTAX          PerfCurrentCount
    MAX-ACCESS      read-only
    STATUS          current
    DESCRIPTION     
            "The current peak discard rate for the 
             Light Gray List policer."
    ::= { sonusServerPolicerCurrentEntry 62 }

sonusServerPolicerCurrentLightGrayListMinorAlarmCount OBJECT-TYPE
    SYNTAX          PerfCurrentCount
    MAX-ACCESS      read-only
    STATUS          current
    DESCRIPTION     
            "The current number of minor alarms for the 
             Light Gray List policer."
    ::= { sonusServerPolicerCurrentEntry 63 }

sonusServerPolicerCurrentLightGrayListMinorAlarmDuration OBJECT-TYPE
    SYNTAX          PerfCurrentCount
    MAX-ACCESS      read-only
    STATUS          current
    DESCRIPTION     
            "The current duration of the minor alarms in seconds
             for the Light Gray List policer."
    ::= { sonusServerPolicerCurrentEntry 64 }

sonusServerPolicerCurrentLightGrayListMajorAlarmCount OBJECT-TYPE
    SYNTAX          PerfCurrentCount
    MAX-ACCESS      read-only
    STATUS          current
    DESCRIPTION     
            "The current number of major alarms for the 
             Light Gray List policer."
    ::= { sonusServerPolicerCurrentEntry 65 }

sonusServerPolicerCurrentLightGrayListMajorAlarmDuration OBJECT-TYPE
    SYNTAX          PerfCurrentCount
    MAX-ACCESS      read-only
    STATUS          current
    DESCRIPTION     
            "The current duration of the major alarms in seconds
             for the Light Gray List policer."
    ::= { sonusServerPolicerCurrentEntry 66 }

sonusServerPolicerCurrentVLanDiscardPacketCount OBJECT-TYPE
    SYNTAX          Counter64
    MAX-ACCESS      read-only
    STATUS          current
    DESCRIPTION     
            "The current number of discarded packets for the 
             VLAN policer."
    ::= { sonusServerPolicerCurrentEntry 67 }

sonusServerPolicerCurrentVLanPeakDiscardRate OBJECT-TYPE
    SYNTAX          PerfCurrentCount
    MAX-ACCESS      read-only
    STATUS          current
    DESCRIPTION     
            "The current peak discard rate for the 
             VLAN policer."
    ::= { sonusServerPolicerCurrentEntry 68 }

sonusServerPolicerCurrentVLanMinorAlarmCount OBJECT-TYPE
    SYNTAX          PerfCurrentCount
    MAX-ACCESS      read-only
    STATUS          current
    DESCRIPTION     
            "The current number of minor alarms for the 
             VLAN policer."
    ::= { sonusServerPolicerCurrentEntry 69 }

sonusServerPolicerCurrentVLanMinorAlarmDuration OBJECT-TYPE
    SYNTAX          PerfCurrentCount
    MAX-ACCESS      read-only
    STATUS          current
    DESCRIPTION     
            "The current duration of the minor alarms in seconds
             for the VLAN policer."
    ::= { sonusServerPolicerCurrentEntry 70 }

sonusServerPolicerCurrentVLanMajorAlarmCount OBJECT-TYPE
    SYNTAX          PerfCurrentCount
    MAX-ACCESS      read-only
    STATUS          current
    DESCRIPTION     
            "The current number of major alarms for the 
             VLAN policer."
    ::= { sonusServerPolicerCurrentEntry 71 }

sonusServerPolicerCurrentVLanMajorAlarmDuration OBJECT-TYPE
    SYNTAX          PerfCurrentCount
    MAX-ACCESS      read-only
    STATUS          current
    DESCRIPTION     
            "The current duration of the major alarms in seconds
             for the VLAN policer."
    ::= { sonusServerPolicerCurrentEntry 72 }

sonusServerPolicerIntervalTable OBJECT-TYPE
    SYNTAX          SEQUENCE OF SonusServerPolicerIntervalEntry
    MAX-ACCESS      not-accessible
    STATUS          current
    DESCRIPTION     
            "The Sonus Server Policer Interval table."
    ::= { sonusPolicerStatisticsObjects 4 }

sonusServerPolicerIntervalEntry OBJECT-TYPE
    SYNTAX          SonusServerPolicerIntervalEntry
    MAX-ACCESS      not-accessible
    STATUS          current
    DESCRIPTION     
            "An entry in the Sonus Server Policer Interval table."
    INDEX           { sonusServerPolicerIntervalShelfIndex, 
                      sonusServerPolicerIntervalSlotIndex, 
                      sonusServerPolicerIntervalNumber }
    ::= { sonusServerPolicerIntervalTable 1 }

SonusServerPolicerIntervalEntry ::=
    SEQUENCE {
        sonusServerPolicerIntervalShelfIndex    SonusShelfIndex,
        sonusServerPolicerIntervalSlotIndex   SonusSlotIndex,
        sonusServerPolicerIntervalNumber Integer32,
        sonusServerPolicerIntervalTime  TimeTicks,
        sonusServerPolicerIntervalValidData   TruthValue,
        sonusServerPolicerIntervalWhiteListDiscardPacketCount                     Counter64,
        sonusServerPolicerIntervalWhiteListPeakDiscardRate                  PerfIntervalCount,
        sonusServerPolicerIntervalWhiteListMinorAlarmCount                  PerfIntervalCount,
        sonusServerPolicerIntervalWhiteListMinorAlarmDuration                     PerfIntervalCount,
        sonusServerPolicerIntervalWhiteListMajorAlarmCount                  PerfIntervalCount,
        sonusServerPolicerIntervalWhiteListMajorAlarmDuration                     PerfIntervalCount,
        sonusServerPolicerIntervalBlackListDiscardPacketCount                     Counter64,
        sonusServerPolicerIntervalBlackListPeakDiscardRate                  PerfIntervalCount,
        sonusServerPolicerIntervalBlackListMinorAlarmCount                  PerfIntervalCount,
        sonusServerPolicerIntervalBlackListMinorAlarmDuration                     PerfIntervalCount,
        sonusServerPolicerIntervalBlackListMajorAlarmCount                  PerfIntervalCount,
        sonusServerPolicerIntervalBlackListMajorAlarmDuration                     PerfIntervalCount,
        sonusServerPolicerIntervalDarkGrayListDiscardPacketCount                        Counter64,
        sonusServerPolicerIntervalDarkGrayListAcceptPacketCount                       Counter64,
        sonusServerPolicerIntervalDarkGrayListPeakDiscardRate                     PerfIntervalCount,
        sonusServerPolicerIntervalDarkGrayListMinorAlarmCount                     PerfIntervalCount,
        sonusServerPolicerIntervalDarkGrayListMinorAlarmDuration                        PerfIntervalCount,
        sonusServerPolicerIntervalDarkGrayListMajorAlarmCount                     PerfIntervalCount,
        sonusServerPolicerIntervalDarkGrayListMajorAlarmDuration                        PerfIntervalCount,
        sonusServerPolicerIntervalServerProtectDiscardPacketCount                         Counter64,
        sonusServerPolicerIntervalServerProtectAcceptPacketCount                        Counter64,
        sonusServerPolicerIntervalServerProtectPeakDiscardRate                      PerfIntervalCount,
        sonusServerPolicerIntervalServerProtectMinorAlarmCount                      PerfIntervalCount,
        sonusServerPolicerIntervalServerProtectMinorAlarmDuration                         PerfIntervalCount,
        sonusServerPolicerIntervalServerProtectMajorAlarmCount                      PerfIntervalCount,
        sonusServerPolicerIntervalServerProtectMajorAlarmDuration                         PerfIntervalCount,
        sonusServerPolicerIntervalMediaDiscardPacketCount                 Counter64,
        sonusServerPolicerIntervalMediaPeakDiscardRate              PerfIntervalCount,
        sonusServerPolicerIntervalMediaMinorAlarmCount              PerfIntervalCount,
        sonusServerPolicerIntervalMediaMinorAlarmDuration                 PerfIntervalCount,
        sonusServerPolicerIntervalMediaMajorAlarmCount              PerfIntervalCount,
        sonusServerPolicerIntervalMediaMajorAlarmDuration                 PerfIntervalCount,
        sonusServerPolicerIntervalRogueMediaUnallocatedPortDiscardPacketCount                                     Counter64,
        sonusServerPolicerIntervalRogueMediaUnallocatedPortPeakDiscardRate                                  PerfIntervalCount,
        sonusServerPolicerIntervalRogueMediaUnallocatedPortMinorAlarmCount                                  PerfIntervalCount,
        sonusServerPolicerIntervalRogueMediaUnallocatedPortMinorAlarmDuration                                     PerfIntervalCount,
        sonusServerPolicerIntervalRogueMediaUnallocatedPortMajorAlarmCount                                  PerfIntervalCount,
        sonusServerPolicerIntervalRogueMediaUnallocatedPortMajorAlarmDuration                                     PerfIntervalCount,
        sonusServerPolicerIntervalRogueMediaMidCallBadDestDiscardPacketCount                                    Counter64,
        sonusServerPolicerIntervalRogueMediaMidCallBadDestPeakDiscardRate                                 PerfIntervalCount,
        sonusServerPolicerIntervalRogueMediaMidCallBadDestMinorAlarmCount                                 PerfIntervalCount,
        sonusServerPolicerIntervalRogueMediaMidCallBadDestMinorAlarmDuration                                    PerfIntervalCount,
        sonusServerPolicerIntervalRogueMediaMidCallBadDestMajorAlarmCount                                 PerfIntervalCount,
        sonusServerPolicerIntervalRogueMediaMidCallBadDestMajorAlarmDuration                                    PerfIntervalCount,
        sonusServerPolicerIntervalRogueMediaMidCallBadSourceDiscardPacketCount                                      Counter64,
        sonusServerPolicerIntervalRogueMediaMidCallBadSourcePeakDiscardRate                                   PerfIntervalCount,
        sonusServerPolicerIntervalRogueMediaMidCallBadSourceMinorAlarmCount                                   PerfIntervalCount,
        sonusServerPolicerIntervalRogueMediaMidCallBadSourceMinorAlarmDuration                                      PerfIntervalCount,
        sonusServerPolicerIntervalRogueMediaMidCallBadSourceMajorAlarmCount                                   PerfIntervalCount,
        sonusServerPolicerIntervalRogueMediaMidCallBadSourceMajorAlarmDuration                                      PerfIntervalCount,
        sonusServerPolicerIntervalRogueMediaMidCallBadVLanDiscardPacketCount                                    Counter64,
        sonusServerPolicerIntervalRogueMediaMidCallBadVLanPeakDiscardRate                                 PerfIntervalCount,
        sonusServerPolicerIntervalRogueMediaMidCallBadVLanMinorAlarmCount                                 PerfIntervalCount,
        sonusServerPolicerIntervalRogueMediaMidCallBadVLanMinorAlarmDuration                                    PerfIntervalCount,
        sonusServerPolicerIntervalRogueMediaMidCallBadVLanMajorAlarmCount                                 PerfIntervalCount,
        sonusServerPolicerIntervalRogueMediaMidCallBadVLanMajorAlarmDuration                                    PerfIntervalCount,
        sonusServerPolicerIntervalRogueMediaInGracePeriodDiscardPacketCount                                   Counter64,
        sonusServerPolicerIntervalRogueMediaInGracePeriodPeakDiscardRate                                PerfIntervalCount,
        sonusServerPolicerIntervalLightGrayListDiscardPacketCount                         Counter64,
        sonusServerPolicerIntervalLightGrayListPeakDiscardRate                      PerfIntervalCount,
        sonusServerPolicerIntervalLightGrayListMinorAlarmCount                      PerfIntervalCount,
        sonusServerPolicerIntervalLightGrayListMinorAlarmDuration                         PerfIntervalCount,
        sonusServerPolicerIntervalLightGrayListMajorAlarmCount                      PerfIntervalCount,
        sonusServerPolicerIntervalLightGrayListMajorAlarmDuration                         PerfIntervalCount,
        sonusServerPolicerIntervalVLanDiscardPacketCount                Counter64,
        sonusServerPolicerIntervalVLanPeakDiscardRate             PerfIntervalCount,
        sonusServerPolicerIntervalVLanMinorAlarmCount             PerfIntervalCount,
        sonusServerPolicerIntervalVLanMinorAlarmDuration                PerfIntervalCount,
        sonusServerPolicerIntervalVLanMajorAlarmCount             PerfIntervalCount,
        sonusServerPolicerIntervalVLanMajorAlarmDuration                PerfIntervalCount
    }

sonusServerPolicerIntervalShelfIndex OBJECT-TYPE
    SYNTAX          SonusShelfIndex
    MAX-ACCESS      read-only
    STATUS          current
    DESCRIPTION     
            "The shelf index into the sonusServerPolicerIntervalTable."
    ::= { sonusServerPolicerIntervalEntry 1 }

sonusServerPolicerIntervalSlotIndex OBJECT-TYPE
    SYNTAX          SonusSlotIndex
    MAX-ACCESS      read-only
    STATUS          current
    DESCRIPTION     
            "The slot index into the sonusServerPolicerIntervalTable."
    ::= { sonusServerPolicerIntervalEntry 2 }

sonusServerPolicerIntervalNumber OBJECT-TYPE
    SYNTAX          Integer32 (1..288)
    MAX-ACCESS      not-accessible
    STATUS          current
    DESCRIPTION     
            "A number between 1 and 288, which identifies the
             interval for which the set of statistics is available.
             The interval identified by 1 is the most recently
             completed interval, and the interval identified
             by N is the interval immediately preceding the
             one identified by N-1."
    ::= { sonusServerPolicerIntervalEntry 3 }

sonusServerPolicerIntervalTime OBJECT-TYPE
    SYNTAX          TimeTicks
    MAX-ACCESS      read-only
    STATUS          current
    DESCRIPTION     
            "This variable contains the end of interval time
             stamp for the specified interval."
    ::= { sonusServerPolicerIntervalEntry 4 }

sonusServerPolicerIntervalValidData OBJECT-TYPE
    SYNTAX          TruthValue
    MAX-ACCESS      read-only
    STATUS          current
    DESCRIPTION     
            "This variable indicates if the data for this
             interval is valid."
    ::= { sonusServerPolicerIntervalEntry 5 }

sonusServerPolicerIntervalWhiteListDiscardPacketCount OBJECT-TYPE
    SYNTAX          Counter64
    MAX-ACCESS      read-only
    STATUS          current
    DESCRIPTION     
            "The number of discarded packets for the 
             White List policer for the specified interval."
    ::= { sonusServerPolicerIntervalEntry 6 }

sonusServerPolicerIntervalWhiteListPeakDiscardRate OBJECT-TYPE
    SYNTAX          PerfIntervalCount
    MAX-ACCESS      read-only
    STATUS          current
    DESCRIPTION     
            "The peak discard rate for the  
             White List policer for the specified interval."
    ::= { sonusServerPolicerIntervalEntry 7 }

sonusServerPolicerIntervalWhiteListMinorAlarmCount OBJECT-TYPE
    SYNTAX          PerfIntervalCount
    MAX-ACCESS      read-only
    STATUS          current
    DESCRIPTION     
            "The number of minor alarms for the 
             White List policer for the specified interval."
    ::= { sonusServerPolicerIntervalEntry 8 }

sonusServerPolicerIntervalWhiteListMinorAlarmDuration OBJECT-TYPE
    SYNTAX          PerfIntervalCount
    MAX-ACCESS      read-only
    STATUS          current
    DESCRIPTION     
            "The duration of the minor alarms in seconds
             for the White List policer for the specified interval."
    ::= { sonusServerPolicerIntervalEntry 9 }

sonusServerPolicerIntervalWhiteListMajorAlarmCount OBJECT-TYPE
    SYNTAX          PerfIntervalCount
    MAX-ACCESS      read-only
    STATUS          current
    DESCRIPTION     
            "The number of of major alarms for the 
             White List policer for the specified interval."
    ::= { sonusServerPolicerIntervalEntry 10 }

sonusServerPolicerIntervalWhiteListMajorAlarmDuration OBJECT-TYPE
    SYNTAX          PerfIntervalCount
    MAX-ACCESS      read-only
    STATUS          current
    DESCRIPTION     
            "The duration of the major alarms in seconds
             for the White List policer for the specified interval."
    ::= { sonusServerPolicerIntervalEntry 11 }

sonusServerPolicerIntervalBlackListDiscardPacketCount OBJECT-TYPE
    SYNTAX          Counter64
    MAX-ACCESS      read-only
    STATUS          current
    DESCRIPTION     
            "The number of discarded packets for the 
             Black List policer for the specified interval."
    ::= { sonusServerPolicerIntervalEntry 12 }

sonusServerPolicerIntervalBlackListPeakDiscardRate OBJECT-TYPE
    SYNTAX          PerfIntervalCount
    MAX-ACCESS      read-only
    STATUS          current
    DESCRIPTION     
            "The peak discard rate for the  
             Black List policer for the specified interval."
    ::= { sonusServerPolicerIntervalEntry 13 }

sonusServerPolicerIntervalBlackListMinorAlarmCount OBJECT-TYPE
    SYNTAX          PerfIntervalCount
    MAX-ACCESS      read-only
    STATUS          current
    DESCRIPTION     
            "The number of minor alarms for the 
             Black List policer for the specified interval."
    ::= { sonusServerPolicerIntervalEntry 14 }

sonusServerPolicerIntervalBlackListMinorAlarmDuration OBJECT-TYPE
    SYNTAX          PerfIntervalCount
    MAX-ACCESS      read-only
    STATUS          current
    DESCRIPTION     
            "The duration of the minor alarms in seconds
             for the Black List policer for the specified interval."
    ::= { sonusServerPolicerIntervalEntry 15 }

sonusServerPolicerIntervalBlackListMajorAlarmCount OBJECT-TYPE
    SYNTAX          PerfIntervalCount
    MAX-ACCESS      read-only
    STATUS          current
    DESCRIPTION     
            "The number of of major alarms for the 
             Black List policer for the specified interval."
    ::= { sonusServerPolicerIntervalEntry 16 }

sonusServerPolicerIntervalBlackListMajorAlarmDuration OBJECT-TYPE
    SYNTAX          PerfIntervalCount
    MAX-ACCESS      read-only
    STATUS          current
    DESCRIPTION     
            "The duration of the major alarms in seconds
             for the Black List policer for the specified interval."
    ::= { sonusServerPolicerIntervalEntry 17 }

sonusServerPolicerIntervalDarkGrayListDiscardPacketCount OBJECT-TYPE
    SYNTAX          Counter64
    MAX-ACCESS      read-only
    STATUS          current
    DESCRIPTION     
            "The number of discarded packets for the 
             Dark Gray List policer for the specified interval."
    ::= { sonusServerPolicerIntervalEntry 18 }

sonusServerPolicerIntervalDarkGrayListAcceptPacketCount OBJECT-TYPE
    SYNTAX          Counter64
    MAX-ACCESS      read-only
    STATUS          current
    DESCRIPTION     
            "The number of accepted packets for the 
             Dark Gray List policer for the specified interval."
    ::= { sonusServerPolicerIntervalEntry 19 }

sonusServerPolicerIntervalDarkGrayListPeakDiscardRate OBJECT-TYPE
    SYNTAX          PerfIntervalCount
    MAX-ACCESS      read-only
    STATUS          current
    DESCRIPTION     
            "The peak discard rate for the  
             Dark Gray List policer for the specified interval."
    ::= { sonusServerPolicerIntervalEntry 20 }

sonusServerPolicerIntervalDarkGrayListMinorAlarmCount OBJECT-TYPE
    SYNTAX          PerfIntervalCount
    MAX-ACCESS      read-only
    STATUS          current
    DESCRIPTION     
            "The number of minor alarms for the 
             Dark Gray List policer for the specified interval."
    ::= { sonusServerPolicerIntervalEntry 21 }

sonusServerPolicerIntervalDarkGrayListMinorAlarmDuration OBJECT-TYPE
    SYNTAX          PerfIntervalCount
    MAX-ACCESS      read-only
    STATUS          current
    DESCRIPTION     
            "The duration of the minor alarms in seconds
             for the Dark Gray List policer for the specified interval."
    ::= { sonusServerPolicerIntervalEntry 22 }

sonusServerPolicerIntervalDarkGrayListMajorAlarmCount OBJECT-TYPE
    SYNTAX          PerfIntervalCount
    MAX-ACCESS      read-only
    STATUS          current
    DESCRIPTION     
            "The number of of major alarms for the 
             Dark Gray List policer for the specified interval."
    ::= { sonusServerPolicerIntervalEntry 23 }

sonusServerPolicerIntervalDarkGrayListMajorAlarmDuration OBJECT-TYPE
    SYNTAX          PerfIntervalCount
    MAX-ACCESS      read-only
    STATUS          current
    DESCRIPTION     
            "The duration of the major alarms in seconds
             for the Dark Gray List policer for the specified interval."
    ::= { sonusServerPolicerIntervalEntry 24 }

sonusServerPolicerIntervalServerProtectDiscardPacketCount OBJECT-TYPE
    SYNTAX          Counter64
    MAX-ACCESS      read-only
    STATUS          current
    DESCRIPTION     
            "The number of discarded packets for the 
             Server Protect policer for the specified interval."
    ::= { sonusServerPolicerIntervalEntry 25 }

sonusServerPolicerIntervalServerProtectAcceptPacketCount OBJECT-TYPE
    SYNTAX          Counter64
    MAX-ACCESS      read-only
    STATUS          current
    DESCRIPTION     
            "The number of accepted packets for the 
             Server Protect policer for the specified interval."
    ::= { sonusServerPolicerIntervalEntry 26 }

sonusServerPolicerIntervalServerProtectPeakDiscardRate OBJECT-TYPE
    SYNTAX          PerfIntervalCount
    MAX-ACCESS      read-only
    STATUS          current
    DESCRIPTION     
            "The peak discard rate for the  
             Server Protect policer for the specified interval."
    ::= { sonusServerPolicerIntervalEntry 27 }

sonusServerPolicerIntervalServerProtectMinorAlarmCount OBJECT-TYPE
    SYNTAX          PerfIntervalCount
    MAX-ACCESS      read-only
    STATUS          current
    DESCRIPTION     
            "The number of minor alarms for the 
             Server Protect policer for the specified interval."
    ::= { sonusServerPolicerIntervalEntry 28 }

sonusServerPolicerIntervalServerProtectMinorAlarmDuration OBJECT-TYPE
    SYNTAX          PerfIntervalCount
    MAX-ACCESS      read-only
    STATUS          current
    DESCRIPTION     
            "The duration of the minor alarms in seconds
             for the Server Protect policer for the specified interval."
    ::= { sonusServerPolicerIntervalEntry 29 }

sonusServerPolicerIntervalServerProtectMajorAlarmCount OBJECT-TYPE
    SYNTAX          PerfIntervalCount
    MAX-ACCESS      read-only
    STATUS          current
    DESCRIPTION     
            "The number of of major alarms for the 
             Server Protect policer for the specified interval."
    ::= { sonusServerPolicerIntervalEntry 30 }

sonusServerPolicerIntervalServerProtectMajorAlarmDuration OBJECT-TYPE
    SYNTAX          PerfIntervalCount
    MAX-ACCESS      read-only
    STATUS          current
    DESCRIPTION     
            "The duration of the major alarms in seconds
             for the  Protect policer for the specified interval."
    ::= { sonusServerPolicerIntervalEntry 31 }

sonusServerPolicerIntervalMediaDiscardPacketCount OBJECT-TYPE
    SYNTAX          Counter64
    MAX-ACCESS      read-only
    STATUS          current
    DESCRIPTION     
            "The number of discarded packets for the 
             Media policer for the specified interval."
    ::= { sonusServerPolicerIntervalEntry 32 }

sonusServerPolicerIntervalMediaPeakDiscardRate OBJECT-TYPE
    SYNTAX          PerfIntervalCount
    MAX-ACCESS      read-only
    STATUS          current
    DESCRIPTION     
            "The peak discard rate for the  
             Media policer for the specified interval."
    ::= { sonusServerPolicerIntervalEntry 33 }

sonusServerPolicerIntervalMediaMinorAlarmCount OBJECT-TYPE
    SYNTAX          PerfIntervalCount
    MAX-ACCESS      read-only
    STATUS          current
    DESCRIPTION     
            "The number of minor alarms for the 
             Media policer for the specified interval."
    ::= { sonusServerPolicerIntervalEntry 34 }

sonusServerPolicerIntervalMediaMinorAlarmDuration OBJECT-TYPE
    SYNTAX          PerfIntervalCount
    MAX-ACCESS      read-only
    STATUS          current
    DESCRIPTION     
            "The duration of the minor alarms in seconds
             for the Media policer for the specified interval."
    ::= { sonusServerPolicerIntervalEntry 35 }

sonusServerPolicerIntervalMediaMajorAlarmCount OBJECT-TYPE
    SYNTAX          PerfIntervalCount
    MAX-ACCESS      read-only
    STATUS          current
    DESCRIPTION     
            "The number of of major alarms for the 
             Media policer for the specified interval."
    ::= { sonusServerPolicerIntervalEntry 36 }

sonusServerPolicerIntervalMediaMajorAlarmDuration OBJECT-TYPE
    SYNTAX          PerfIntervalCount
    MAX-ACCESS      read-only
    STATUS          current
    DESCRIPTION     
            "The duration of the major alarms in seconds
             for the Media policer for the specified interval."
    ::= { sonusServerPolicerIntervalEntry 37 }

sonusServerPolicerIntervalRogueMediaUnallocatedPortDiscardPacketCount OBJECT-TYPE
    SYNTAX          Counter64
    MAX-ACCESS      read-only
    STATUS          current
    DESCRIPTION     
            "The number of discarded packets for the 
             Rogue Media Unallocated Port policer for the specified interval."
    ::= { sonusServerPolicerIntervalEntry 38 }

sonusServerPolicerIntervalRogueMediaUnallocatedPortPeakDiscardRate OBJECT-TYPE
    SYNTAX          PerfIntervalCount
    MAX-ACCESS      read-only
    STATUS          current
    DESCRIPTION     
            "The peak discard rate for the  
             Rogue Media Unallocated Port policer for the specified interval."
    ::= { sonusServerPolicerIntervalEntry 39 }

sonusServerPolicerIntervalRogueMediaUnallocatedPortMinorAlarmCount OBJECT-TYPE
    SYNTAX          PerfIntervalCount
    MAX-ACCESS      read-only
    STATUS          current
    DESCRIPTION     
            "The number of minor alarms for the 
             Rogue Media Unallocated Port policer for the specified interval."
    ::= { sonusServerPolicerIntervalEntry 40 }

sonusServerPolicerIntervalRogueMediaUnallocatedPortMinorAlarmDuration OBJECT-TYPE
    SYNTAX          PerfIntervalCount
    MAX-ACCESS      read-only
    STATUS          current
    DESCRIPTION     
            "The duration of the minor alarms in seconds
             for the Rogue Media Unallocated Port policer for the specified interval."
    ::= { sonusServerPolicerIntervalEntry 41 }

sonusServerPolicerIntervalRogueMediaUnallocatedPortMajorAlarmCount OBJECT-TYPE
    SYNTAX          PerfIntervalCount
    MAX-ACCESS      read-only
    STATUS          current
    DESCRIPTION     
            "The number of of major alarms for the 
             Rogue Media Unallocated Port policer for the specified interval."
    ::= { sonusServerPolicerIntervalEntry 42 }

sonusServerPolicerIntervalRogueMediaUnallocatedPortMajorAlarmDuration OBJECT-TYPE
    SYNTAX          PerfIntervalCount
    MAX-ACCESS      read-only
    STATUS          current
    DESCRIPTION     
            "The duration of the major alarms in seconds
             for the Rogue Media Unallocated Port policer for the specified interval."
    ::= { sonusServerPolicerIntervalEntry 43 }

sonusServerPolicerIntervalRogueMediaMidCallBadDestDiscardPacketCount OBJECT-TYPE
    SYNTAX          Counter64
    MAX-ACCESS      read-only
    STATUS          current
    DESCRIPTION     
            "The number of discarded packets for the 
             Rogue Media Unallocated Port policer for the specified interval."
    ::= { sonusServerPolicerIntervalEntry 44 }

sonusServerPolicerIntervalRogueMediaMidCallBadDestPeakDiscardRate OBJECT-TYPE
    SYNTAX          PerfIntervalCount
    MAX-ACCESS      read-only
    STATUS          current
    DESCRIPTION     
            "The peak discard rate for the  
             Rogue Media Unallocated Port policer for the specified interval."
    ::= { sonusServerPolicerIntervalEntry 45 }

sonusServerPolicerIntervalRogueMediaMidCallBadDestMinorAlarmCount OBJECT-TYPE
    SYNTAX          PerfIntervalCount
    MAX-ACCESS      read-only
    STATUS          current
    DESCRIPTION     
            "The number of minor alarms for the 
             Rogue Media Unallocated Port policer for the specified interval."
    ::= { sonusServerPolicerIntervalEntry 46 }

sonusServerPolicerIntervalRogueMediaMidCallBadDestMinorAlarmDuration OBJECT-TYPE
    SYNTAX          PerfIntervalCount
    MAX-ACCESS      read-only
    STATUS          current
    DESCRIPTION     
            "The duration of the minor alarms in seconds
             for the Rogue Media Unallocated Port policer for the specified interval."
    ::= { sonusServerPolicerIntervalEntry 47 }

sonusServerPolicerIntervalRogueMediaMidCallBadDestMajorAlarmCount OBJECT-TYPE
    SYNTAX          PerfIntervalCount
    MAX-ACCESS      read-only
    STATUS          current
    DESCRIPTION     
            "The number of of major alarms for the 
             Rogue Media Unallocated Port policer for the specified interval."
    ::= { sonusServerPolicerIntervalEntry 48 }

sonusServerPolicerIntervalRogueMediaMidCallBadDestMajorAlarmDuration OBJECT-TYPE
    SYNTAX          PerfIntervalCount
    MAX-ACCESS      read-only
    STATUS          current
    DESCRIPTION     
            "The duration of the major alarms in seconds
             for the Rogue Media Unallocated Port policer for the specified interval."
    ::= { sonusServerPolicerIntervalEntry 49 }

sonusServerPolicerIntervalRogueMediaMidCallBadSourceDiscardPacketCount OBJECT-TYPE
    SYNTAX          Counter64
    MAX-ACCESS      read-only
    STATUS          current
    DESCRIPTION     
            "The number of discarded packets for the 
             Rogue Media Unallocated Port policer for the specified interval."
    ::= { sonusServerPolicerIntervalEntry 50 }

sonusServerPolicerIntervalRogueMediaMidCallBadSourcePeakDiscardRate OBJECT-TYPE
    SYNTAX          PerfIntervalCount
    MAX-ACCESS      read-only
    STATUS          current
    DESCRIPTION     
            "The peak discard rate for the  
             Rogue Media Unallocated Port policer for the specified interval."
    ::= { sonusServerPolicerIntervalEntry 51 }

sonusServerPolicerIntervalRogueMediaMidCallBadSourceMinorAlarmCount OBJECT-TYPE
    SYNTAX          PerfIntervalCount
    MAX-ACCESS      read-only
    STATUS          current
    DESCRIPTION     
            "The number of minor alarms for the 
             Rogue Media Unallocated Port policer for the specified interval."
    ::= { sonusServerPolicerIntervalEntry 52 }

sonusServerPolicerIntervalRogueMediaMidCallBadSourceMinorAlarmDuration OBJECT-TYPE
    SYNTAX          PerfIntervalCount
    MAX-ACCESS      read-only
    STATUS          current
    DESCRIPTION     
            "The duration of the minor alarms in seconds
             for the Rogue Media Unallocated Port policer for the specified interval."
    ::= { sonusServerPolicerIntervalEntry 53 }

sonusServerPolicerIntervalRogueMediaMidCallBadSourceMajorAlarmCount OBJECT-TYPE
    SYNTAX          PerfIntervalCount
    MAX-ACCESS      read-only
    STATUS          current
    DESCRIPTION     
            "The number of of major alarms for the 
             Rogue Media Unallocated Port policer for the specified interval."
    ::= { sonusServerPolicerIntervalEntry 54 }

sonusServerPolicerIntervalRogueMediaMidCallBadSourceMajorAlarmDuration OBJECT-TYPE
    SYNTAX          PerfIntervalCount
    MAX-ACCESS      read-only
    STATUS          current
    DESCRIPTION     
            "The duration of the major alarms in seconds
             for the Rogue Media Unallocated Port policer for the specified interval."
    ::= { sonusServerPolicerIntervalEntry 55 }

sonusServerPolicerIntervalRogueMediaMidCallBadVLanDiscardPacketCount OBJECT-TYPE
    SYNTAX          Counter64
    MAX-ACCESS      read-only
    STATUS          current
    DESCRIPTION     
            "The number of discarded packets for the 
             Rogue Media Unallocated Port policer for the specified interval."
    ::= { sonusServerPolicerIntervalEntry 56 }

sonusServerPolicerIntervalRogueMediaMidCallBadVLanPeakDiscardRate OBJECT-TYPE
    SYNTAX          PerfIntervalCount
    MAX-ACCESS      read-only
    STATUS          current
    DESCRIPTION     
            "The peak discard rate for the  
             Rogue Media Unallocated Port policer for the specified interval."
    ::= { sonusServerPolicerIntervalEntry 57 }

sonusServerPolicerIntervalRogueMediaMidCallBadVLanMinorAlarmCount OBJECT-TYPE
    SYNTAX          PerfIntervalCount
    MAX-ACCESS      read-only
    STATUS          current
    DESCRIPTION     
            "The number of minor alarms for the 
             Rogue Media Unallocated Port policer for the specified interval."
    ::= { sonusServerPolicerIntervalEntry 58 }

sonusServerPolicerIntervalRogueMediaMidCallBadVLanMinorAlarmDuration OBJECT-TYPE
    SYNTAX          PerfIntervalCount
    MAX-ACCESS      read-only
    STATUS          current
    DESCRIPTION     
            "The duration of the minor alarms in seconds
             for the Rogue Media Unallocated Port policer for the specified interval."
    ::= { sonusServerPolicerIntervalEntry 59 }

sonusServerPolicerIntervalRogueMediaMidCallBadVLanMajorAlarmCount OBJECT-TYPE
    SYNTAX          PerfIntervalCount
    MAX-ACCESS      read-only
    STATUS          current
    DESCRIPTION     
            "The number of of major alarms for the 
             Rogue Media Unallocated Port policer for the specified interval."
    ::= { sonusServerPolicerIntervalEntry 60 }

sonusServerPolicerIntervalRogueMediaMidCallBadVLanMajorAlarmDuration OBJECT-TYPE
    SYNTAX          PerfIntervalCount
    MAX-ACCESS      read-only
    STATUS          current
    DESCRIPTION     
            "The duration of the major alarms in seconds
             for the Rogue Media Unallocated Port policer for the specified interval."
    ::= { sonusServerPolicerIntervalEntry 61 }

sonusServerPolicerIntervalRogueMediaInGracePeriodDiscardPacketCount OBJECT-TYPE
    SYNTAX          Counter64
    MAX-ACCESS      read-only
    STATUS          current
    DESCRIPTION     
            "The number of discarded packets for the 
             Rogue Media Unallocated Port policer for the specified interval."
    ::= { sonusServerPolicerIntervalEntry 62 }

sonusServerPolicerIntervalRogueMediaInGracePeriodPeakDiscardRate OBJECT-TYPE
    SYNTAX          PerfIntervalCount
    MAX-ACCESS      read-only
    STATUS          current
    DESCRIPTION     
            "The peak discard rate for the  
             Rogue Media Unallocated Port policer for the specified interval."
    ::= { sonusServerPolicerIntervalEntry 63 }

sonusServerPolicerIntervalLightGrayListDiscardPacketCount OBJECT-TYPE
    SYNTAX          Counter64
    MAX-ACCESS      read-only
    STATUS          current
    DESCRIPTION     
            "The number of discarded packets for the 
             Light Gray List policer for the specified interval."
    ::= { sonusServerPolicerIntervalEntry 64 }

sonusServerPolicerIntervalLightGrayListPeakDiscardRate OBJECT-TYPE
    SYNTAX          PerfIntervalCount
    MAX-ACCESS      read-only
    STATUS          current
    DESCRIPTION     
            "The peak discard rate for the  
             Light Gray List policer for the specified interval."
    ::= { sonusServerPolicerIntervalEntry 65 }

sonusServerPolicerIntervalLightGrayListMinorAlarmCount OBJECT-TYPE
    SYNTAX          PerfIntervalCount
    MAX-ACCESS      read-only
    STATUS          current
    DESCRIPTION     
            "The number of minor alarms for the 
             Light Gray List policer for the specified interval."
    ::= { sonusServerPolicerIntervalEntry 66 }

sonusServerPolicerIntervalLightGrayListMinorAlarmDuration OBJECT-TYPE
    SYNTAX          PerfIntervalCount
    MAX-ACCESS      read-only
    STATUS          current
    DESCRIPTION     
            "The duration of the minor alarms in seconds
             for the Light Gray List policer for the specified interval."
    ::= { sonusServerPolicerIntervalEntry 67 }

sonusServerPolicerIntervalLightGrayListMajorAlarmCount OBJECT-TYPE
    SYNTAX          PerfIntervalCount
    MAX-ACCESS      read-only
    STATUS          current
    DESCRIPTION     
            "The number of of major alarms for the 
             Light Gray List policer for the specified interval."
    ::= { sonusServerPolicerIntervalEntry 68 }

sonusServerPolicerIntervalLightGrayListMajorAlarmDuration OBJECT-TYPE
    SYNTAX          PerfIntervalCount
    MAX-ACCESS      read-only
    STATUS          current
    DESCRIPTION     
            "The duration of the major alarms in seconds
             for the Light Gray List policer for the specified interval."
    ::= { sonusServerPolicerIntervalEntry 69 }

sonusServerPolicerIntervalVLanDiscardPacketCount OBJECT-TYPE
    SYNTAX          Counter64
    MAX-ACCESS      read-only
    STATUS          current
    DESCRIPTION     
            "The number of discarded packets for the 
             VLAN policer for the specified interval."
    ::= { sonusServerPolicerIntervalEntry 70 }

sonusServerPolicerIntervalVLanPeakDiscardRate OBJECT-TYPE
    SYNTAX          PerfIntervalCount
    MAX-ACCESS      read-only
    STATUS          current
    DESCRIPTION     
            "The peak discard rate for the  
             VLAN policer for the specified interval."
    ::= { sonusServerPolicerIntervalEntry 71 }

sonusServerPolicerIntervalVLanMinorAlarmCount OBJECT-TYPE
    SYNTAX          PerfIntervalCount
    MAX-ACCESS      read-only
    STATUS          current
    DESCRIPTION     
            "The number of minor alarms for the 
             VLAN policer for the specified interval."
    ::= { sonusServerPolicerIntervalEntry 72 }

sonusServerPolicerIntervalVLanMinorAlarmDuration OBJECT-TYPE
    SYNTAX          PerfIntervalCount
    MAX-ACCESS      read-only
    STATUS          current
    DESCRIPTION     
            "The duration of the minor alarms in seconds
             for the VLAN policer for the specified interval."
    ::= { sonusServerPolicerIntervalEntry 73 }

sonusServerPolicerIntervalVLanMajorAlarmCount OBJECT-TYPE
    SYNTAX          PerfIntervalCount
    MAX-ACCESS      read-only
    STATUS          current
    DESCRIPTION     
            "The number of of major alarms for the 
             VLAN policer for the specified interval."
    ::= { sonusServerPolicerIntervalEntry 74 }

sonusServerPolicerIntervalVLanMajorAlarmDuration OBJECT-TYPE
    SYNTAX          PerfIntervalCount
    MAX-ACCESS      read-only
    STATUS          current
    DESCRIPTION     
            "The duration of the major alarms in seconds
             for the VLAN policer for the specified interval."
    ::= { sonusServerPolicerIntervalEntry 75 }

sonusSipStatisticsCurrentObjects OBJECT IDENTIFIER
    ::= { sonusPerformanceStatisticsObjects 4 }

sonusSipStatisticsCurrentTable OBJECT-TYPE
    SYNTAX          SEQUENCE OF SonusSipStatisticsCurrentEntry
    MAX-ACCESS      not-accessible
    STATUS          current
    DESCRIPTION     
            "This table presents SIP stack current statistics for a SIP SERVICE GROUP ."
    ::= { sonusSipStatisticsCurrentObjects 1 }

sonusSipStatisticsCurrentEntry OBJECT-TYPE
    SYNTAX          SonusSipStatisticsCurrentEntry
    MAX-ACCESS      not-accessible
    STATUS          current
    DESCRIPTION     
            ""
    INDEX           { sonusSipStatisticsCurrentIndex }
    ::= { sonusSipStatisticsCurrentTable 1 }

SonusSipStatisticsCurrentEntry ::=
    SEQUENCE {
        sonusSipStatisticsCurrentIndex  Integer32,
        sonusSipStatisticsCurrentGroupName  SonusName,
        sonusSipStatisticsCurrentValidData  TruthValue,
        sonusSipStatisticsCurrentRcvInvite  PerfCurrentCount,
        sonusSipStatisticsCurrentSndInvite  PerfCurrentCount,
        sonusSipStatisticsCurrentRcvAck PerfCurrentCount,
        sonusSipStatisticsCurrentSndAck PerfCurrentCount,
        sonusSipStatisticsCurrentRcvPrack PerfCurrentCount,
        sonusSipStatisticsCurrentSndPrack PerfCurrentCount,
        sonusSipStatisticsCurrentRcvInfo PerfCurrentCount,
        sonusSipStatisticsCurrentSndInfo PerfCurrentCount,
        sonusSipStatisticsCurrentRcvRefer PerfCurrentCount,
        sonusSipStatisticsCurrentSndRefer PerfCurrentCount,
        sonusSipStatisticsCurrentRcvBye PerfCurrentCount,
        sonusSipStatisticsCurrentSndBye PerfCurrentCount,
        sonusSipStatisticsCurrentRcvCancel  PerfCurrentCount,
        sonusSipStatisticsCurrentSndCancel  PerfCurrentCount,
        sonusSipStatisticsCurrentRcvRegister    PerfCurrentCount,
        sonusSipStatisticsCurrentSndRegister    PerfCurrentCount,
        sonusSipStatisticsCurrentRcvUpdate  PerfCurrentCount,
        sonusSipStatisticsCurrentSndUpdate  PerfCurrentCount,
        sonusSipStatisticsCurrentRcv18x PerfCurrentCount,
        sonusSipStatisticsCurrentSnd18x PerfCurrentCount,
        sonusSipStatisticsCurrentRcv1xx PerfCurrentCount,
        sonusSipStatisticsCurrentSnd1xx PerfCurrentCount,
        sonusSipStatisticsCurrentRcv2xx PerfCurrentCount,
        sonusSipStatisticsCurrentSnd2xx PerfCurrentCount,
        sonusSipStatisticsCurrentRcvNonInv2xx     PerfCurrentCount,
        sonusSipStatisticsCurrentSndNonInv2xx     PerfCurrentCount,
        sonusSipStatisticsCurrentRcv3xx PerfCurrentCount,
        sonusSipStatisticsCurrentSnd3xx PerfCurrentCount,
        sonusSipStatisticsCurrentRcv4xx PerfCurrentCount,
        sonusSipStatisticsCurrentSnd4xx PerfCurrentCount,
        sonusSipStatisticsCurrentRcv5xx PerfCurrentCount,
        sonusSipStatisticsCurrentSnd5xx PerfCurrentCount,
        sonusSipStatisticsCurrentRcv6xx PerfCurrentCount,
        sonusSipStatisticsCurrentSnd6xx PerfCurrentCount,
        sonusSipStatisticsCurrentRcvNonInvErr     PerfCurrentCount,
        sonusSipStatisticsCurrentSndNonInvErr     PerfCurrentCount,
        sonusSipStatisticsCurrentRcvUnknownMsg      PerfCurrentCount,
        sonusSipStatisticsCurrentRcvSubscriber      PerfCurrentCount,
        sonusSipStatisticsCurrentSndSubscriber      PerfCurrentCount,
        sonusSipStatisticsCurrentRcvNotify  PerfCurrentCount,
        sonusSipStatisticsCurrentSndNotify  PerfCurrentCount,
        sonusSipStatisticsCurrentRcvOption  PerfCurrentCount,
        sonusSipStatisticsCurrentSndOption  PerfCurrentCount,
        sonusSipStatisticsCurrentInvReTransmit      PerfCurrentCount,
        sonusSipStatisticsCurrentRegReTransmit      PerfCurrentCount,
        sonusSipStatisticsCurrentByeRetransmit      PerfCurrentCount,
        sonusSipStatisticsCurrentCancleReTransmit         PerfCurrentCount,
        sonusSipStatisticsCurrentOtherReTransmit        PerfCurrentCount,
        sonusSipStatisticsCurrentRcvMessage   PerfCurrentCount,
        sonusSipStatisticsCurrentSndMessage   PerfCurrentCount,
        sonusSipStatisticsCurrentRcvPublish   PerfCurrentCount,
        sonusSipStatisticsCurrentSndPublish   PerfCurrentCount,
        sonusSipStatisticsCurrentEmergencyAccept        PerfCurrentCount,
        sonusSipStatisticsCurrentEmergencyRejectBWCall              PerfCurrentCount,
        sonusSipStatisticsCurrentEmergencyRejectPolicer               PerfCurrentCount,
        sonusSipStatisticsCurrentHpcAccept  PerfCurrentCount,
        sonusSipStatisticsCurrentPcrfSndInitialAar          PerfCurrentCount,
        sonusSipStatisticsCurrentPcrfSndAar   PerfCurrentCount,
        sonusSipStatisticsCurrentPcrfRcvAaaFailure          PerfCurrentCount,
        sonusSipStatisticsCurrentPcrfAarTimeoutOrError              PerfCurrentCount
    }

sonusSipStatisticsCurrentIndex OBJECT-TYPE
    SYNTAX          Integer32 (1..2048)
    MAX-ACCESS      read-only
    STATUS          current
    DESCRIPTION     
            "The index of the CURRENT Sip Statistics entry."
    ::= { sonusSipStatisticsCurrentEntry 1 }

sonusSipStatisticsCurrentGroupName OBJECT-TYPE
    SYNTAX          SonusName
    MAX-ACCESS      read-only
    STATUS          current
    DESCRIPTION     
            "Sip Service Group Name that this Sip Statistics data refers to"
    ::= { sonusSipStatisticsCurrentEntry 2 }

sonusSipStatisticsCurrentValidData OBJECT-TYPE
    SYNTAX          TruthValue
    MAX-ACCESS      read-only
    STATUS          current
    DESCRIPTION     
            "Indicates if this current data is valid."
    ::= { sonusSipStatisticsCurrentEntry 3 }

sonusSipStatisticsCurrentRcvInvite OBJECT-TYPE
    SYNTAX          PerfCurrentCount
    MAX-ACCESS      read-only
    STATUS          current
    DESCRIPTION     
            "Indicates the total number of (current) received Invite messages."
    ::= { sonusSipStatisticsCurrentEntry 4 }

sonusSipStatisticsCurrentSndInvite OBJECT-TYPE
    SYNTAX          PerfCurrentCount
    MAX-ACCESS      read-only
    STATUS          current
    DESCRIPTION     
            "Indicates the total number of (current) sent Invite messages."
    ::= { sonusSipStatisticsCurrentEntry 5 }

sonusSipStatisticsCurrentRcvAck OBJECT-TYPE
    SYNTAX          PerfCurrentCount
    MAX-ACCESS      read-only
    STATUS          current
    DESCRIPTION     
            "Indicates the total number of (current) Received Ack"
    ::= { sonusSipStatisticsCurrentEntry 6 }

sonusSipStatisticsCurrentSndAck OBJECT-TYPE
    SYNTAX          PerfCurrentCount
    MAX-ACCESS      read-only
    STATUS          current
    DESCRIPTION     
            "Indicates the total number of (current) Sent Ack messages."
    ::= { sonusSipStatisticsCurrentEntry 7 }

sonusSipStatisticsCurrentRcvPrack OBJECT-TYPE
    SYNTAX          PerfCurrentCount
    MAX-ACCESS      read-only
    STATUS          current
    DESCRIPTION     
            "Indicates the total number of (current) received Prack messages."
    ::= { sonusSipStatisticsCurrentEntry 8 }

sonusSipStatisticsCurrentSndPrack OBJECT-TYPE
    SYNTAX          PerfCurrentCount
    MAX-ACCESS      read-only
    STATUS          current
    DESCRIPTION     
            "Indicates the total number of (current) sent Prack messages."
    ::= { sonusSipStatisticsCurrentEntry 9 }

sonusSipStatisticsCurrentRcvInfo OBJECT-TYPE
    SYNTAX          PerfCurrentCount
    MAX-ACCESS      read-only
    STATUS          current
    DESCRIPTION     
            "Indicates the total number of (current) received INFO messages."
    ::= { sonusSipStatisticsCurrentEntry 10 }

sonusSipStatisticsCurrentSndInfo OBJECT-TYPE
    SYNTAX          PerfCurrentCount
    MAX-ACCESS      read-only
    STATUS          current
    DESCRIPTION     
            "Indicates the total number of (current)  sent INFO messages."
    ::= { sonusSipStatisticsCurrentEntry 11 }

sonusSipStatisticsCurrentRcvRefer OBJECT-TYPE
    SYNTAX          PerfCurrentCount
    MAX-ACCESS      read-only
    STATUS          current
    DESCRIPTION     
            "Indicates the total number of (current) received Refer messages."
    ::= { sonusSipStatisticsCurrentEntry 12 }

sonusSipStatisticsCurrentSndRefer OBJECT-TYPE
    SYNTAX          PerfCurrentCount
    MAX-ACCESS      read-only
    STATUS          current
    DESCRIPTION     
            "Indicates the total number of (current) sent Refer messages."
    ::= { sonusSipStatisticsCurrentEntry 13 }

sonusSipStatisticsCurrentRcvBye OBJECT-TYPE
    SYNTAX          PerfCurrentCount
    MAX-ACCESS      read-only
    STATUS          current
    DESCRIPTION     
            "Indicates the total number of (current) Received Bye messages."
    ::= { sonusSipStatisticsCurrentEntry 14 }

sonusSipStatisticsCurrentSndBye OBJECT-TYPE
    SYNTAX          PerfCurrentCount
    MAX-ACCESS      read-only
    STATUS          current
    DESCRIPTION     
            "Indicates the total number of (current) sent Bye messages."
    ::= { sonusSipStatisticsCurrentEntry 15 }

sonusSipStatisticsCurrentRcvCancel OBJECT-TYPE
    SYNTAX          PerfCurrentCount
    MAX-ACCESS      read-only
    STATUS          current
    DESCRIPTION     
            "Indicates the total number of (current) received Cancel  messages."
    ::= { sonusSipStatisticsCurrentEntry 16 }

sonusSipStatisticsCurrentSndCancel OBJECT-TYPE
    SYNTAX          PerfCurrentCount
    MAX-ACCESS      read-only
    STATUS          current
    DESCRIPTION     
            "Indicates the total number of (current) sent Cancel messages."
    ::= { sonusSipStatisticsCurrentEntry 17 }

sonusSipStatisticsCurrentRcvRegister OBJECT-TYPE
    SYNTAX          PerfCurrentCount
    MAX-ACCESS      read-only
    STATUS          current
    DESCRIPTION     
            "Indicates the total number of (current) received Register messages."
    ::= { sonusSipStatisticsCurrentEntry 18 }

sonusSipStatisticsCurrentSndRegister OBJECT-TYPE
    SYNTAX          PerfCurrentCount
    MAX-ACCESS      read-only
    STATUS          current
    DESCRIPTION     
            "Indicates the total number of (current) sent Register messages."
    ::= { sonusSipStatisticsCurrentEntry 19 }

sonusSipStatisticsCurrentRcvUpdate OBJECT-TYPE
    SYNTAX          PerfCurrentCount
    MAX-ACCESS      read-only
    STATUS          current
    DESCRIPTION     
            "Indicates the total number of (current) received Update messages."
    ::= { sonusSipStatisticsCurrentEntry 20 }

sonusSipStatisticsCurrentSndUpdate OBJECT-TYPE
    SYNTAX          PerfCurrentCount
    MAX-ACCESS      read-only
    STATUS          current
    DESCRIPTION     
            "Indicates the total number of (current) sent Update messages."
    ::= { sonusSipStatisticsCurrentEntry 21 }

sonusSipStatisticsCurrentRcv18x OBJECT-TYPE
    SYNTAX          PerfCurrentCount
    MAX-ACCESS      read-only
    STATUS          current
    DESCRIPTION     
            "Indicates the total number of (current) received 18x messages."
    ::= { sonusSipStatisticsCurrentEntry 22 }

sonusSipStatisticsCurrentSnd18x OBJECT-TYPE
    SYNTAX          PerfCurrentCount
    MAX-ACCESS      read-only
    STATUS          current
    DESCRIPTION     
            "Indicates the total number of (current) sent 18x messages."
    ::= { sonusSipStatisticsCurrentEntry 23 }

sonusSipStatisticsCurrentRcv1xx OBJECT-TYPE
    SYNTAX          PerfCurrentCount
    MAX-ACCESS      read-only
    STATUS          current
    DESCRIPTION     
            "Indicates the total number of (current) received 1xx msg except 18x  messages."
    ::= { sonusSipStatisticsCurrentEntry 24 }

sonusSipStatisticsCurrentSnd1xx OBJECT-TYPE
    SYNTAX          PerfCurrentCount
    MAX-ACCESS      read-only
    STATUS          current
    DESCRIPTION     
            "Indicates the total number of (current) sent 1xx msg except 18x messages."
    ::= { sonusSipStatisticsCurrentEntry 25 }

sonusSipStatisticsCurrentRcv2xx OBJECT-TYPE
    SYNTAX          PerfCurrentCount
    MAX-ACCESS      read-only
    STATUS          current
    DESCRIPTION     
            "Indicates the total number of (current) received 2xx(Invite) messages."
    ::= { sonusSipStatisticsCurrentEntry 26 }

sonusSipStatisticsCurrentSnd2xx OBJECT-TYPE
    SYNTAX          PerfCurrentCount
    MAX-ACCESS      read-only
    STATUS          current
    DESCRIPTION     
            "Indicates the total number of (current) sent 2xx(Invite) messages."
    ::= { sonusSipStatisticsCurrentEntry 27 }

sonusSipStatisticsCurrentRcvNonInv2xx OBJECT-TYPE
    SYNTAX          PerfCurrentCount
    MAX-ACCESS      read-only
    STATUS          current
    DESCRIPTION     
            "Indicates the total number of (current) received 2xx(NonInvite) messages."
    ::= { sonusSipStatisticsCurrentEntry 28 }

sonusSipStatisticsCurrentSndNonInv2xx OBJECT-TYPE
    SYNTAX          PerfCurrentCount
    MAX-ACCESS      read-only
    STATUS          current
    DESCRIPTION     
            "Indicates the total number of (current) sent 2xx(NonInvite) messages."
    ::= { sonusSipStatisticsCurrentEntry 29 }

sonusSipStatisticsCurrentRcv3xx OBJECT-TYPE
    SYNTAX          PerfCurrentCount
    MAX-ACCESS      read-only
    STATUS          current
    DESCRIPTION     
            "Indicates the total number of (current) recieved 3xx messages."
    ::= { sonusSipStatisticsCurrentEntry 30 }

sonusSipStatisticsCurrentSnd3xx OBJECT-TYPE
    SYNTAX          PerfCurrentCount
    MAX-ACCESS      read-only
    STATUS          current
    DESCRIPTION     
            "Indicates the total number of (current) sent 3xx messages."
    ::= { sonusSipStatisticsCurrentEntry 31 }

sonusSipStatisticsCurrentRcv4xx OBJECT-TYPE
    SYNTAX          PerfCurrentCount
    MAX-ACCESS      read-only
    STATUS          current
    DESCRIPTION     
            "Indicates the total number of (current) received 4xx messages."
    ::= { sonusSipStatisticsCurrentEntry 32 }

sonusSipStatisticsCurrentSnd4xx OBJECT-TYPE
    SYNTAX          PerfCurrentCount
    MAX-ACCESS      read-only
    STATUS          current
    DESCRIPTION     
            "Indicates the total number of (current) sent 4xx messages."
    ::= { sonusSipStatisticsCurrentEntry 33 }

sonusSipStatisticsCurrentRcv5xx OBJECT-TYPE
    SYNTAX          PerfCurrentCount
    MAX-ACCESS      read-only
    STATUS          current
    DESCRIPTION     
            "Indicates the total number of (current) receive 5xx messages."
    ::= { sonusSipStatisticsCurrentEntry 34 }

sonusSipStatisticsCurrentSnd5xx OBJECT-TYPE
    SYNTAX          PerfCurrentCount
    MAX-ACCESS      read-only
    STATUS          current
    DESCRIPTION     
            "Indicates the total number of (current) sent 5xx messages."
    ::= { sonusSipStatisticsCurrentEntry 35 }

sonusSipStatisticsCurrentRcv6xx OBJECT-TYPE
    SYNTAX          PerfCurrentCount
    MAX-ACCESS      read-only
    STATUS          current
    DESCRIPTION     
            "Indicates the total number of (current) receive 6xx messages."
    ::= { sonusSipStatisticsCurrentEntry 36 }

sonusSipStatisticsCurrentSnd6xx OBJECT-TYPE
    SYNTAX          PerfCurrentCount
    MAX-ACCESS      read-only
    STATUS          current
    DESCRIPTION     
            "Indicates the total number of (current) sent 6xx messages."
    ::= { sonusSipStatisticsCurrentEntry 37 }

sonusSipStatisticsCurrentRcvNonInvErr OBJECT-TYPE
    SYNTAX          PerfCurrentCount
    MAX-ACCESS      read-only
    STATUS          current
    DESCRIPTION     
            "Indicates the total number of (current) receive NonIvite Error messages."
    ::= { sonusSipStatisticsCurrentEntry 38 }

sonusSipStatisticsCurrentSndNonInvErr OBJECT-TYPE
    SYNTAX          PerfCurrentCount
    MAX-ACCESS      read-only
    STATUS          current
    DESCRIPTION     
            "Indicates the total number of (current) sent  NonIvite Error messages."
    ::= { sonusSipStatisticsCurrentEntry 39 }

sonusSipStatisticsCurrentRcvUnknownMsg OBJECT-TYPE
    SYNTAX          PerfCurrentCount
    MAX-ACCESS      read-only
    STATUS          current
    DESCRIPTION     
            "Indicates the total number of (current) receive Unknown  messages."
    ::= { sonusSipStatisticsCurrentEntry 40 }

sonusSipStatisticsCurrentRcvSubscriber OBJECT-TYPE
    SYNTAX          PerfCurrentCount
    MAX-ACCESS      read-only
    STATUS          current
    DESCRIPTION     
            "Indicates the total number of (current) receive Subscriber messages."
    ::= { sonusSipStatisticsCurrentEntry 41 }

sonusSipStatisticsCurrentSndSubscriber OBJECT-TYPE
    SYNTAX          PerfCurrentCount
    MAX-ACCESS      read-only
    STATUS          current
    DESCRIPTION     
            "Indicates the total number of (current) sent Subscriber messages."
    ::= { sonusSipStatisticsCurrentEntry 42 }

sonusSipStatisticsCurrentRcvNotify OBJECT-TYPE
    SYNTAX          PerfCurrentCount
    MAX-ACCESS      read-only
    STATUS          current
    DESCRIPTION     
            "Indicates the total number of (current) receiveNotify messages."
    ::= { sonusSipStatisticsCurrentEntry 43 }

sonusSipStatisticsCurrentSndNotify OBJECT-TYPE
    SYNTAX          PerfCurrentCount
    MAX-ACCESS      read-only
    STATUS          current
    DESCRIPTION     
            "Indicates the total number of (current) sent Notify messages."
    ::= { sonusSipStatisticsCurrentEntry 44 }

sonusSipStatisticsCurrentRcvOption OBJECT-TYPE
    SYNTAX          PerfCurrentCount
    MAX-ACCESS      read-only
    STATUS          current
    DESCRIPTION     
            "Indicates the total number of (current) receive Option messages."
    ::= { sonusSipStatisticsCurrentEntry 45 }

sonusSipStatisticsCurrentSndOption OBJECT-TYPE
    SYNTAX          PerfCurrentCount
    MAX-ACCESS      read-only
    STATUS          current
    DESCRIPTION     
            "Indicates the total number of (current) sent Option messages."
    ::= { sonusSipStatisticsCurrentEntry 46 }

sonusSipStatisticsCurrentInvReTransmit OBJECT-TYPE
    SYNTAX          PerfCurrentCount
    MAX-ACCESS      read-only
    STATUS          current
    DESCRIPTION     
            "Indicates the total number of (current) Invite messages ReTransmitted."
    ::= { sonusSipStatisticsCurrentEntry 47 }

sonusSipStatisticsCurrentRegReTransmit OBJECT-TYPE
    SYNTAX          PerfCurrentCount
    MAX-ACCESS      read-only
    STATUS          current
    DESCRIPTION     
            "Indicates the total number of (current) Register messages ReTransmitted."
    ::= { sonusSipStatisticsCurrentEntry 48 }

sonusSipStatisticsCurrentByeRetransmit OBJECT-TYPE
    SYNTAX          PerfCurrentCount
    MAX-ACCESS      read-only
    STATUS          current
    DESCRIPTION     
            "Indicates the total number of (current) Bye messages ReTransmitted."
    ::= { sonusSipStatisticsCurrentEntry 49 }

sonusSipStatisticsCurrentCancleReTransmit OBJECT-TYPE
    SYNTAX          PerfCurrentCount
    MAX-ACCESS      read-only
    STATUS          current
    DESCRIPTION     
            "Indicates the total number of (current) Cancel messages ReTransmitted."
    ::= { sonusSipStatisticsCurrentEntry 50 }

sonusSipStatisticsCurrentOtherReTransmit OBJECT-TYPE
    SYNTAX          PerfCurrentCount
    MAX-ACCESS      read-only
    STATUS          current
    DESCRIPTION     
            "Indicates the total number of (current) Other messages ReTransmitted."
    ::= { sonusSipStatisticsCurrentEntry 51 }

sonusSipStatisticsCurrentRcvMessage OBJECT-TYPE
    SYNTAX          PerfCurrentCount
    MAX-ACCESS      read-only
    STATUS          current
    DESCRIPTION     
            "Indicates the total number of (current) received Message methods."
    ::= { sonusSipStatisticsCurrentEntry 52 }

sonusSipStatisticsCurrentSndMessage OBJECT-TYPE
    SYNTAX          PerfCurrentCount
    MAX-ACCESS      read-only
    STATUS          current
    DESCRIPTION     
            "Indicates the total number of (current) sent Message methods."
    ::= { sonusSipStatisticsCurrentEntry 53 }

sonusSipStatisticsCurrentRcvPublish OBJECT-TYPE
    SYNTAX          PerfCurrentCount
    MAX-ACCESS      read-only
    STATUS          current
    DESCRIPTION     
            "Indicates the total number of (current) received Publish methods."
    ::= { sonusSipStatisticsCurrentEntry 54 }

sonusSipStatisticsCurrentSndPublish OBJECT-TYPE
    SYNTAX          PerfCurrentCount
    MAX-ACCESS      read-only
    STATUS          current
    DESCRIPTION     
            "Indicates the total number of (current) sent Publish methods."
    ::= { sonusSipStatisticsCurrentEntry 55 }

sonusSipStatisticsCurrentEmergencyAccept OBJECT-TYPE
    SYNTAX          PerfCurrentCount
    MAX-ACCESS      read-only
    STATUS          current
    DESCRIPTION     
            "Indicates the total number of (current) emergency calls accepted."
    ::= { sonusSipStatisticsCurrentEntry 56 }

sonusSipStatisticsCurrentEmergencyRejectBWCall OBJECT-TYPE
    SYNTAX          PerfCurrentCount
    MAX-ACCESS      read-only
    STATUS          current
    DESCRIPTION     
            "Indicates the total number of (current) emergency calls rejected
             because of bandwidth limit or call limit."
    ::= { sonusSipStatisticsCurrentEntry 57 }

sonusSipStatisticsCurrentEmergencyRejectPolicer OBJECT-TYPE
    SYNTAX          PerfCurrentCount
    MAX-ACCESS      read-only
    STATUS          current
    DESCRIPTION     
            "Indicates the total number of (current) emergency calls rejected
             because of Priority Policer."
    ::= { sonusSipStatisticsCurrentEntry 58 }

sonusSipStatisticsCurrentHpcAccept OBJECT-TYPE
    SYNTAX          PerfCurrentCount
    MAX-ACCESS      read-only
    STATUS          current
    DESCRIPTION     
            "Indicates the total number of (current) HPC calls accepted."
    ::= { sonusSipStatisticsCurrentEntry 59 }

sonusSipStatisticsCurrentPcrfSndInitialAar OBJECT-TYPE
    SYNTAX          PerfCurrentCount
    MAX-ACCESS      read-only
    STATUS          current
    DESCRIPTION     
            "Indicates the total number of (current) initial AARs
             sent to the PCRF."
    ::= { sonusSipStatisticsCurrentEntry 60 }

sonusSipStatisticsCurrentPcrfSndAar OBJECT-TYPE
    SYNTAX          PerfCurrentCount
    MAX-ACCESS      read-only
    STATUS          current
    DESCRIPTION     
            "Indicates the total number of (current) AARs
             sent to the PCRF."
    ::= { sonusSipStatisticsCurrentEntry 61 }

sonusSipStatisticsCurrentPcrfRcvAaaFailure OBJECT-TYPE
    SYNTAX          PerfCurrentCount
    MAX-ACCESS      read-only
    STATUS          current
    DESCRIPTION     
            "Indicates the total number of (current) AARs
             answered wihtout Result-Code 2100 (DIAMETER Success)."
    ::= { sonusSipStatisticsCurrentEntry 62 }

sonusSipStatisticsCurrentPcrfAarTimeoutOrError OBJECT-TYPE
    SYNTAX          PerfCurrentCount
    MAX-ACCESS      read-only
    STATUS          current
    DESCRIPTION     
            "Indicates the total number of (current) AARs
             not answered (timeouts or errors)."
    ::= { sonusSipStatisticsCurrentEntry 63 }

sonusSipStatisticsIntervalObjects OBJECT IDENTIFIER
    ::= { sonusPerformanceStatisticsObjects 5 }

sonusSipStatisticsIntervalTable OBJECT-TYPE
    SYNTAX          SEQUENCE OF SonusSipStatisticsIntervalEntry
    MAX-ACCESS      not-accessible
    STATUS          current
    DESCRIPTION     
            "This table presents SIP stack interval statistics per service group."
    ::= { sonusSipStatisticsIntervalObjects 1 }

sonusSipStatisticsIntervalEntry OBJECT-TYPE
    SYNTAX          SonusSipStatisticsIntervalEntry
    MAX-ACCESS      not-accessible
    STATUS          current
    DESCRIPTION     
            ""
    INDEX           { sonusSipStatisticsIntervalIndex, 
                      sonusSipStatisticsIntervalNumber }
    ::= { sonusSipStatisticsIntervalTable 1 }

SonusSipStatisticsIntervalEntry ::=
    SEQUENCE {
        sonusSipStatisticsIntervalIndex Integer32,
        sonusSipStatisticsIntervalNumber Integer32,
        sonusSipStatisticsIntervalGroupName   SonusName,
        sonusSipStatisticsIntervalValidData   TruthValue,
        sonusSipStatisticsIntervalRcvInvite   PerfIntervalCount,
        sonusSipStatisticsIntervalSndInvite   PerfIntervalCount,
        sonusSipStatisticsIntervalRcvAck PerfIntervalCount,
        sonusSipStatisticsIntervalSndAck PerfIntervalCount,
        sonusSipStatisticsIntervalRcvPrack  PerfIntervalCount,
        sonusSipStatisticsIntervalSndPrack  PerfIntervalCount,
        sonusSipStatisticsIntervalRcvInfo PerfIntervalCount,
        sonusSipStatisticsIntervalSndInfo PerfIntervalCount,
        sonusSipStatisticsIntervalRcvRefer  PerfIntervalCount,
        sonusSipStatisticsIntervalSndRefer  PerfIntervalCount,
        sonusSipStatisticsIntervalRcvBye PerfIntervalCount,
        sonusSipStatisticsIntervalSndBye PerfIntervalCount,
        sonusSipStatisticsIntervalRcvCancel   PerfIntervalCount,
        sonusSipStatisticsIntervalSndCancel   PerfIntervalCount,
        sonusSipStatisticsIntervalRcvRegister     PerfIntervalCount,
        sonusSipStatisticsIntervalSndRegister     PerfIntervalCount,
        sonusSipStatisticsIntervalRcvUpdate   PerfIntervalCount,
        sonusSipStatisticsIntervalSndUpdate   PerfIntervalCount,
        sonusSipStatisticsIntervalRcv18x PerfIntervalCount,
        sonusSipStatisticsIntervalSnd18x PerfIntervalCount,
        sonusSipStatisticsIntervalRcv1xx PerfIntervalCount,
        sonusSipStatisticsIntervalSnd1xx PerfIntervalCount,
        sonusSipStatisticsIntervalRcv2xx PerfIntervalCount,
        sonusSipStatisticsIntervalSnd2xx PerfIntervalCount,
        sonusSipStatisticsIntervalRcvNonInv2xx      PerfIntervalCount,
        sonusSipStatisticsIntervalSndNonInv2xx      PerfIntervalCount,
        sonusSipStatisticsIntervalRcv3xx PerfIntervalCount,
        sonusSipStatisticsIntervalSnd3xx PerfIntervalCount,
        sonusSipStatisticsIntervalRcv4xx PerfIntervalCount,
        sonusSipStatisticsIntervalSnd4xx PerfIntervalCount,
        sonusSipStatisticsIntervalRcv5xx PerfIntervalCount,
        sonusSipStatisticsIntervalSnd5xx PerfIntervalCount,
        sonusSipStatisticsIntervalRcv6xx PerfIntervalCount,
        sonusSipStatisticsIntervalSnd6xx PerfIntervalCount,
        sonusSipStatisticsIntervalRcvNonInvErr      PerfIntervalCount,
        sonusSipStatisticsIntervalSndNonInvErr      PerfIntervalCount,
        sonusSipStatisticsIntervalRcvUnknownMsg       PerfIntervalCount,
        sonusSipStatisticsIntervalRcvSubscriber       PerfIntervalCount,
        sonusSipStatisticsIntervalSndSubscriber       PerfIntervalCount,
        sonusSipStatisticsIntervalRcvNotify   PerfIntervalCount,
        sonusSipStatisticsIntervalSndNotify   PerfIntervalCount,
        sonusSipStatisticsIntervalRcvOption   PerfIntervalCount,
        sonusSipStatisticsIntervalSndOption   PerfIntervalCount,
        sonusSipStatisticsIntervalInvReTransmit       PerfIntervalCount,
        sonusSipStatisticsIntervalRegReTransmit       PerfIntervalCount,
        sonusSipStatisticsIntervalByeRetransmit       PerfIntervalCount,
        sonusSipStatisticsIntervalCancleReTransmit          PerfIntervalCount,
        sonusSipStatisticsIntervalOtherReTransmit         PerfIntervalCount,
        sonusSipStatisticsIntervalRcvMessage    PerfIntervalCount,
        sonusSipStatisticsIntervalSndMessage    PerfIntervalCount,
        sonusSipStatisticsIntervalRcvPublish    PerfIntervalCount,
        sonusSipStatisticsIntervalSndPublish    PerfIntervalCount,
        sonusSipStatisticsIntervalEmergencyAccept         PerfIntervalCount,
        sonusSipStatisticsIntervalEmergencyRejectBWCall               PerfIntervalCount,
        sonusSipStatisticsIntervalEmergencyRejectPolicer                PerfIntervalCount,
        sonusSipStatisticsIntervalHpcAccept   PerfIntervalCount,
        sonusSipStatisticsIntervalPcrfSndInitialAar           PerfIntervalCount,
        sonusSipStatisticsIntervalPcrfSndAar    PerfIntervalCount,
        sonusSipStatisticsIntervalPcrfRcvAaaFailure           PerfIntervalCount,
        sonusSipStatisticsIntervalPcrfAarTimeoutOrError               PerfIntervalCount
    }

sonusSipStatisticsIntervalIndex OBJECT-TYPE
    SYNTAX          Integer32 (1..2048)
    MAX-ACCESS      read-only
    STATUS          current
    DESCRIPTION     
            "The index of the INTERVAL Sip Statistics entry."
    ::= { sonusSipStatisticsIntervalEntry 1 }

sonusSipStatisticsIntervalNumber OBJECT-TYPE
    SYNTAX          Integer32 (1..12)
    MAX-ACCESS      read-only
    STATUS          current
    DESCRIPTION     
            "The number of the INTERVAL Sip Statistics entry."
    ::= { sonusSipStatisticsIntervalEntry 2 }

sonusSipStatisticsIntervalGroupName OBJECT-TYPE
    SYNTAX          SonusName
    MAX-ACCESS      read-only
    STATUS          current
    DESCRIPTION     
            "Sip Service Group Name That this Statistics refers to"
    ::= { sonusSipStatisticsIntervalEntry 3 }

sonusSipStatisticsIntervalValidData OBJECT-TYPE
    SYNTAX          TruthValue
    MAX-ACCESS      read-only
    STATUS          current
    DESCRIPTION     
            "Indicates if this interval data is valid."
    ::= { sonusSipStatisticsIntervalEntry 4 }

sonusSipStatisticsIntervalRcvInvite OBJECT-TYPE
    SYNTAX          PerfIntervalCount
    MAX-ACCESS      read-only
    STATUS          current
    DESCRIPTION     
            "Indicates the total number of (interval) received Invite messages."
    ::= { sonusSipStatisticsIntervalEntry 5 }

sonusSipStatisticsIntervalSndInvite OBJECT-TYPE
    SYNTAX          PerfIntervalCount
    MAX-ACCESS      read-only
    STATUS          current
    DESCRIPTION     
            "Indicates the total number of (interval) sent Invite messages."
    ::= { sonusSipStatisticsIntervalEntry 6 }

sonusSipStatisticsIntervalRcvAck OBJECT-TYPE
    SYNTAX          PerfIntervalCount
    MAX-ACCESS      read-only
    STATUS          current
    DESCRIPTION     
            "Indicates the total number of (interval) Received Ack"
    ::= { sonusSipStatisticsIntervalEntry 7 }

sonusSipStatisticsIntervalSndAck OBJECT-TYPE
    SYNTAX          PerfIntervalCount
    MAX-ACCESS      read-only
    STATUS          current
    DESCRIPTION     
            "Indicates the total number of (interval) Sent Ack messages."
    ::= { sonusSipStatisticsIntervalEntry 8 }

sonusSipStatisticsIntervalRcvPrack OBJECT-TYPE
    SYNTAX          PerfIntervalCount
    MAX-ACCESS      read-only
    STATUS          current
    DESCRIPTION     
            "Indicates the total number of (interval) received Prack messages."
    ::= { sonusSipStatisticsIntervalEntry 9 }

sonusSipStatisticsIntervalSndPrack OBJECT-TYPE
    SYNTAX          PerfIntervalCount
    MAX-ACCESS      read-only
    STATUS          current
    DESCRIPTION     
            "Indicates the total number of (interval) sent Prack messages."
    ::= { sonusSipStatisticsIntervalEntry 10 }

sonusSipStatisticsIntervalRcvInfo OBJECT-TYPE
    SYNTAX          PerfIntervalCount
    MAX-ACCESS      read-only
    STATUS          current
    DESCRIPTION     
            "Indicates the total number of (interval) received INFO messages."
    ::= { sonusSipStatisticsIntervalEntry 11 }

sonusSipStatisticsIntervalSndInfo OBJECT-TYPE
    SYNTAX          PerfIntervalCount
    MAX-ACCESS      read-only
    STATUS          current
    DESCRIPTION     
            "Indicates the total number of (interval)  sent INFO messages."
    ::= { sonusSipStatisticsIntervalEntry 12 }

sonusSipStatisticsIntervalRcvRefer OBJECT-TYPE
    SYNTAX          PerfIntervalCount
    MAX-ACCESS      read-only
    STATUS          current
    DESCRIPTION     
            "Indicates the total number of (interval) received Refer messages."
    ::= { sonusSipStatisticsIntervalEntry 13 }

sonusSipStatisticsIntervalSndRefer OBJECT-TYPE
    SYNTAX          PerfIntervalCount
    MAX-ACCESS      read-only
    STATUS          current
    DESCRIPTION     
            "Indicates the total number of (interval) sent Refer messages."
    ::= { sonusSipStatisticsIntervalEntry 14 }

sonusSipStatisticsIntervalRcvBye OBJECT-TYPE
    SYNTAX          PerfIntervalCount
    MAX-ACCESS      read-only
    STATUS          current
    DESCRIPTION     
            "Indicates the total number of (interval) Received Bye messages."
    ::= { sonusSipStatisticsIntervalEntry 15 }

sonusSipStatisticsIntervalSndBye OBJECT-TYPE
    SYNTAX          PerfIntervalCount
    MAX-ACCESS      read-only
    STATUS          current
    DESCRIPTION     
            "Indicates the total number of (interval) sent Bye messages."
    ::= { sonusSipStatisticsIntervalEntry 16 }

sonusSipStatisticsIntervalRcvCancel OBJECT-TYPE
    SYNTAX          PerfIntervalCount
    MAX-ACCESS      read-only
    STATUS          current
    DESCRIPTION     
            "Indicates the total number of (interval) received Cancel  messages."
    ::= { sonusSipStatisticsIntervalEntry 17 }

sonusSipStatisticsIntervalSndCancel OBJECT-TYPE
    SYNTAX          PerfIntervalCount
    MAX-ACCESS      read-only
    STATUS          current
    DESCRIPTION     
            "Indicates the total number of (interval) sent Cancel messages."
    ::= { sonusSipStatisticsIntervalEntry 18 }

sonusSipStatisticsIntervalRcvRegister OBJECT-TYPE
    SYNTAX          PerfIntervalCount
    MAX-ACCESS      read-only
    STATUS          current
    DESCRIPTION     
            "Indicates the total number of (interval) received Register messages."
    ::= { sonusSipStatisticsIntervalEntry 19 }

sonusSipStatisticsIntervalSndRegister OBJECT-TYPE
    SYNTAX          PerfIntervalCount
    MAX-ACCESS      read-only
    STATUS          current
    DESCRIPTION     
            "Indicates the total number of (interval) sent Register messages."
    ::= { sonusSipStatisticsIntervalEntry 20 }

sonusSipStatisticsIntervalRcvUpdate OBJECT-TYPE
    SYNTAX          PerfIntervalCount
    MAX-ACCESS      read-only
    STATUS          current
    DESCRIPTION     
            "Indicates the total number of (interval) received Update messages."
    ::= { sonusSipStatisticsIntervalEntry 21 }

sonusSipStatisticsIntervalSndUpdate OBJECT-TYPE
    SYNTAX          PerfIntervalCount
    MAX-ACCESS      read-only
    STATUS          current
    DESCRIPTION     
            "Indicates the total number of (interval) sent Update messages."
    ::= { sonusSipStatisticsIntervalEntry 22 }

sonusSipStatisticsIntervalRcv18x OBJECT-TYPE
    SYNTAX          PerfIntervalCount
    MAX-ACCESS      read-only
    STATUS          current
    DESCRIPTION     
            "Indicates the total number of (interval) received 18x messages."
    ::= { sonusSipStatisticsIntervalEntry 23 }

sonusSipStatisticsIntervalSnd18x OBJECT-TYPE
    SYNTAX          PerfIntervalCount
    MAX-ACCESS      read-only
    STATUS          current
    DESCRIPTION     
            "Indicates the total number of (interval) sent 18x messages."
    ::= { sonusSipStatisticsIntervalEntry 24 }

sonusSipStatisticsIntervalRcv1xx OBJECT-TYPE
    SYNTAX          PerfIntervalCount
    MAX-ACCESS      read-only
    STATUS          current
    DESCRIPTION     
            "Indicates the total number of (interval) received 1xx msg except 18x  messages."
    ::= { sonusSipStatisticsIntervalEntry 25 }

sonusSipStatisticsIntervalSnd1xx OBJECT-TYPE
    SYNTAX          PerfIntervalCount
    MAX-ACCESS      read-only
    STATUS          current
    DESCRIPTION     
            "Indicates the total number of (interval) sent 1xx msg except 18x messages."
    ::= { sonusSipStatisticsIntervalEntry 26 }

sonusSipStatisticsIntervalRcv2xx OBJECT-TYPE
    SYNTAX          PerfIntervalCount
    MAX-ACCESS      read-only
    STATUS          current
    DESCRIPTION     
            "Indicates the total number of (interval) received 2xx(Invite) messages."
    ::= { sonusSipStatisticsIntervalEntry 27 }

sonusSipStatisticsIntervalSnd2xx OBJECT-TYPE
    SYNTAX          PerfIntervalCount
    MAX-ACCESS      read-only
    STATUS          current
    DESCRIPTION     
            "Indicates the total number of (interval) sent 2xx(Invite) messages."
    ::= { sonusSipStatisticsIntervalEntry 28 }

sonusSipStatisticsIntervalRcvNonInv2xx OBJECT-TYPE
    SYNTAX          PerfIntervalCount
    MAX-ACCESS      read-only
    STATUS          current
    DESCRIPTION     
            "Indicates the total number of (interval) received 2xx(NonInvite) messages."
    ::= { sonusSipStatisticsIntervalEntry 29 }

sonusSipStatisticsIntervalSndNonInv2xx OBJECT-TYPE
    SYNTAX          PerfIntervalCount
    MAX-ACCESS      read-only
    STATUS          current
    DESCRIPTION     
            "Indicates the total number of (interval) sent 2xx(NonInvite) messages."
    ::= { sonusSipStatisticsIntervalEntry 30 }

sonusSipStatisticsIntervalRcv3xx OBJECT-TYPE
    SYNTAX          PerfIntervalCount
    MAX-ACCESS      read-only
    STATUS          current
    DESCRIPTION     
            "Indicates the total number of (interval) recieved 3xx messages."
    ::= { sonusSipStatisticsIntervalEntry 31 }

sonusSipStatisticsIntervalSnd3xx OBJECT-TYPE
    SYNTAX          PerfIntervalCount
    MAX-ACCESS      read-only
    STATUS          current
    DESCRIPTION     
            "Indicates the total number of (interval) sent 3xx messages."
    ::= { sonusSipStatisticsIntervalEntry 32 }

sonusSipStatisticsIntervalRcv4xx OBJECT-TYPE
    SYNTAX          PerfIntervalCount
    MAX-ACCESS      read-only
    STATUS          current
    DESCRIPTION     
            "Indicates the total number of (interval) received 4xx messages."
    ::= { sonusSipStatisticsIntervalEntry 33 }

sonusSipStatisticsIntervalSnd4xx OBJECT-TYPE
    SYNTAX          PerfIntervalCount
    MAX-ACCESS      read-only
    STATUS          current
    DESCRIPTION     
            "Indicates the total number of (interval) sent 4xx messages."
    ::= { sonusSipStatisticsIntervalEntry 34 }

sonusSipStatisticsIntervalRcv5xx OBJECT-TYPE
    SYNTAX          PerfIntervalCount
    MAX-ACCESS      read-only
    STATUS          current
    DESCRIPTION     
            "Indicates the total number of (interval) receive 5xx messages."
    ::= { sonusSipStatisticsIntervalEntry 35 }

sonusSipStatisticsIntervalSnd5xx OBJECT-TYPE
    SYNTAX          PerfIntervalCount
    MAX-ACCESS      read-only
    STATUS          current
    DESCRIPTION     
            "Indicates the total number of (interval) sent 5xx messages."
    ::= { sonusSipStatisticsIntervalEntry 36 }

sonusSipStatisticsIntervalRcv6xx OBJECT-TYPE
    SYNTAX          PerfIntervalCount
    MAX-ACCESS      read-only
    STATUS          current
    DESCRIPTION     
            "Indicates the total number of (interval) receive 6xx messages."
    ::= { sonusSipStatisticsIntervalEntry 37 }

sonusSipStatisticsIntervalSnd6xx OBJECT-TYPE
    SYNTAX          PerfIntervalCount
    MAX-ACCESS      read-only
    STATUS          current
    DESCRIPTION     
            "Indicates the total number of (interval) sent 6xx messages."
    ::= { sonusSipStatisticsIntervalEntry 38 }

sonusSipStatisticsIntervalRcvNonInvErr OBJECT-TYPE
    SYNTAX          PerfIntervalCount
    MAX-ACCESS      read-only
    STATUS          current
    DESCRIPTION     
            "Indicates the total number of (interval) receive NonIvite Error messages."
    ::= { sonusSipStatisticsIntervalEntry 39 }

sonusSipStatisticsIntervalSndNonInvErr OBJECT-TYPE
    SYNTAX          PerfIntervalCount
    MAX-ACCESS      read-only
    STATUS          current
    DESCRIPTION     
            "Indicates the total number of (interval) sent  NonIvite Error messages."
    ::= { sonusSipStatisticsIntervalEntry 40 }

sonusSipStatisticsIntervalRcvUnknownMsg OBJECT-TYPE
    SYNTAX          PerfIntervalCount
    MAX-ACCESS      read-only
    STATUS          current
    DESCRIPTION     
            "Indicates the total number of (interval) receive Unknown  messages."
    ::= { sonusSipStatisticsIntervalEntry 41 }

sonusSipStatisticsIntervalRcvSubscriber OBJECT-TYPE
    SYNTAX          PerfIntervalCount
    MAX-ACCESS      read-only
    STATUS          current
    DESCRIPTION     
            "Indicates the total number of (interval) receive Subscriber messages."
    ::= { sonusSipStatisticsIntervalEntry 42 }

sonusSipStatisticsIntervalSndSubscriber OBJECT-TYPE
    SYNTAX          PerfIntervalCount
    MAX-ACCESS      read-only
    STATUS          current
    DESCRIPTION     
            "Indicates the total number of (interval) sent Subscriber messages."
    ::= { sonusSipStatisticsIntervalEntry 43 }

sonusSipStatisticsIntervalRcvNotify OBJECT-TYPE
    SYNTAX          PerfIntervalCount
    MAX-ACCESS      read-only
    STATUS          current
    DESCRIPTION     
            "Indicates the total number of (interval) receiveNotify messages."
    ::= { sonusSipStatisticsIntervalEntry 44 }

sonusSipStatisticsIntervalSndNotify OBJECT-TYPE
    SYNTAX          PerfIntervalCount
    MAX-ACCESS      read-only
    STATUS          current
    DESCRIPTION     
            "Indicates the total number of (interval) sent Notify messages."
    ::= { sonusSipStatisticsIntervalEntry 45 }

sonusSipStatisticsIntervalRcvOption OBJECT-TYPE
    SYNTAX          PerfIntervalCount
    MAX-ACCESS      read-only
    STATUS          current
    DESCRIPTION     
            "Indicates the total number of (interval) receive Option messages."
    ::= { sonusSipStatisticsIntervalEntry 46 }

sonusSipStatisticsIntervalSndOption OBJECT-TYPE
    SYNTAX          PerfIntervalCount
    MAX-ACCESS      read-only
    STATUS          current
    DESCRIPTION     
            "Indicates the total number of (interval) sent Option messages."
    ::= { sonusSipStatisticsIntervalEntry 47 }

sonusSipStatisticsIntervalInvReTransmit OBJECT-TYPE
    SYNTAX          PerfIntervalCount
    MAX-ACCESS      read-only
    STATUS          current
    DESCRIPTION     
            "Indicates the total number of (interval) Invite messages ReTransmitted."
    ::= { sonusSipStatisticsIntervalEntry 48 }

sonusSipStatisticsIntervalRegReTransmit OBJECT-TYPE
    SYNTAX          PerfIntervalCount
    MAX-ACCESS      read-only
    STATUS          current
    DESCRIPTION     
            "Indicates the total number of (interval) Register messages ReTransmitted."
    ::= { sonusSipStatisticsIntervalEntry 49 }

sonusSipStatisticsIntervalByeRetransmit OBJECT-TYPE
    SYNTAX          PerfIntervalCount
    MAX-ACCESS      read-only
    STATUS          current
    DESCRIPTION     
            "Indicates the total number of (interval) Bye messages ReTransmitted."
    ::= { sonusSipStatisticsIntervalEntry 50 }

sonusSipStatisticsIntervalCancleReTransmit OBJECT-TYPE
    SYNTAX          PerfIntervalCount
    MAX-ACCESS      read-only
    STATUS          current
    DESCRIPTION     
            "Indicates the total number of (interval) Cancel messages ReTransmitted."
    ::= { sonusSipStatisticsIntervalEntry 51 }

sonusSipStatisticsIntervalOtherReTransmit OBJECT-TYPE
    SYNTAX          PerfIntervalCount
    MAX-ACCESS      read-only
    STATUS          current
    DESCRIPTION     
            "Indicates the total number of (interval) Other messages ReTransmitted."
    ::= { sonusSipStatisticsIntervalEntry 52 }

sonusSipStatisticsIntervalRcvMessage OBJECT-TYPE
    SYNTAX          PerfIntervalCount
    MAX-ACCESS      read-only
    STATUS          current
    DESCRIPTION     
            "Indicates the total number of (interval) received Message method."
    ::= { sonusSipStatisticsIntervalEntry 53 }

sonusSipStatisticsIntervalSndMessage OBJECT-TYPE
    SYNTAX          PerfIntervalCount
    MAX-ACCESS      read-only
    STATUS          current
    DESCRIPTION     
            "Indicates the total number of (interval) sent Message method."
    ::= { sonusSipStatisticsIntervalEntry 54 }

sonusSipStatisticsIntervalRcvPublish OBJECT-TYPE
    SYNTAX          PerfIntervalCount
    MAX-ACCESS      read-only
    STATUS          current
    DESCRIPTION     
            "Indicates the total number of (interval) received Publish method."
    ::= { sonusSipStatisticsIntervalEntry 55 }

sonusSipStatisticsIntervalSndPublish OBJECT-TYPE
    SYNTAX          PerfIntervalCount
    MAX-ACCESS      read-only
    STATUS          current
    DESCRIPTION     
            "Indicates the total number of (interval) sent Publish method."
    ::= { sonusSipStatisticsIntervalEntry 56 }

sonusSipStatisticsIntervalEmergencyAccept OBJECT-TYPE
    SYNTAX          PerfIntervalCount
    MAX-ACCESS      read-only
    STATUS          current
    DESCRIPTION     
            "Indicates the total number of (interval) emergency calls accepted."
    ::= { sonusSipStatisticsIntervalEntry 57 }

sonusSipStatisticsIntervalEmergencyRejectBWCall OBJECT-TYPE
    SYNTAX          PerfIntervalCount
    MAX-ACCESS      read-only
    STATUS          current
    DESCRIPTION     
            "Indicates the total number of (interval) emergency calls rejected
             because of bandwidth limit or call limit."
    ::= { sonusSipStatisticsIntervalEntry 58 }

sonusSipStatisticsIntervalEmergencyRejectPolicer OBJECT-TYPE
    SYNTAX          PerfIntervalCount
    MAX-ACCESS      read-only
    STATUS          current
    DESCRIPTION     
            "Indicates the total number of (interval) emergency calls rejected
             because of Priority Policer."
    ::= { sonusSipStatisticsIntervalEntry 59 }

sonusSipStatisticsIntervalHpcAccept OBJECT-TYPE
    SYNTAX          PerfIntervalCount
    MAX-ACCESS      read-only
    STATUS          current
    DESCRIPTION     
            "Indicates the total number of (interval) HPC calls accepted."
    ::= { sonusSipStatisticsIntervalEntry 60 }

sonusSipStatisticsIntervalPcrfSndInitialAar OBJECT-TYPE
    SYNTAX          PerfIntervalCount
    MAX-ACCESS      read-only
    STATUS          current
    DESCRIPTION     
            "Indicates the total number of (interval) initial AARs
             sent to the PCRF."
    ::= { sonusSipStatisticsIntervalEntry 61 }

sonusSipStatisticsIntervalPcrfSndAar OBJECT-TYPE
    SYNTAX          PerfIntervalCount
    MAX-ACCESS      read-only
    STATUS          current
    DESCRIPTION     
            "Indicates the total number of (interval) AARs
             sent to the PCRF."
    ::= { sonusSipStatisticsIntervalEntry 62 }

sonusSipStatisticsIntervalPcrfRcvAaaFailure OBJECT-TYPE
    SYNTAX          PerfIntervalCount
    MAX-ACCESS      read-only
    STATUS          current
    DESCRIPTION     
            "Indicates the total number of (interval) AARs
             answered wihtout Result-Code 2100 (DIAMETER Success)."
    ::= { sonusSipStatisticsIntervalEntry 63 }

sonusSipStatisticsIntervalPcrfAarTimeoutOrError OBJECT-TYPE
    SYNTAX          PerfIntervalCount
    MAX-ACCESS      read-only
    STATUS          current
    DESCRIPTION     
            "Indicates the total number of (interval) AARs
             not answered (timeouts or errors)."
    ::= { sonusSipStatisticsIntervalEntry 64 }

sonusSipHpcStatisticsObjects OBJECT IDENTIFIER
    ::= { sonusPerformanceStatisticsObjects 6 }

sonusSipHpcStatisticsCurrentTable OBJECT-TYPE
    SYNTAX          SEQUENCE OF SonusSipHpcStatisticsCurrentEntry
    MAX-ACCESS      not-accessible
    STATUS          current
    DESCRIPTION     
            "This table presents SIP stack HPC current statistics for each shelf."
    ::= { sonusSipHpcStatisticsObjects 1 }

sonusSipHpcStatisticsCurrentEntry OBJECT-TYPE
    SYNTAX          SonusSipHpcStatisticsCurrentEntry
    MAX-ACCESS      not-accessible
    STATUS          current
    DESCRIPTION     
            ""
    INDEX           { sonusSipHpcStatisticsCurrentShelfIndex }
    ::= { sonusSipHpcStatisticsCurrentTable 1 }

SonusSipHpcStatisticsCurrentEntry ::=
    SEQUENCE {
        sonusSipHpcStatisticsCurrentShelfIndex      SonusShelfIndex,
        sonusSipHpcStatisticsCurrentValidData     TruthValue,
        sonusSipHpcStatisticsCurrentEtsInvitesOut         PerfCurrentCount,
        sonusSipHpcStatisticsCurrentEtsRinging      PerfCurrentCount,
        sonusSipHpcStatisticsCurrentEtsQueued     PerfCurrentCount,
        sonusSipHpcStatisticsCurrentEtsSuccess      PerfCurrentCount,
        sonusSipHpcStatisticsCurrentEtsFailure      PerfCurrentCount,
        sonusSipHpcStatisticsCurrentEtsBadRequestOut            PerfCurrentCount,
        sonusSipHpcStatisticsCurrentEtsTimeout      PerfCurrentCount,
        sonusSipHpcStatisticsCurrentEtsUnknownRp        PerfCurrentCount,
        sonusSipHpcStatisticsCurrentEtsBusyHere       PerfCurrentCount,
        sonusSipHpcStatisticsCurrentEtsInvitesIn        PerfCurrentCount,
        sonusSipHpcStatisticsCurrentEtsInvitesEtsDn           PerfCurrentCount,
        sonusSipHpcStatisticsCurrentEtsBadRequestIn           PerfCurrentCount,
        sonusSipHpcStatisticsCurrentEtsUnknownRpIn          PerfCurrentCount,
        sonusSipHpcStatisticsCurrentEtsBadExtnIn        PerfCurrentCount,
        sonusSipHpcStatisticsCurrentEtsForbiddenIn          PerfCurrentCount,
        sonusSipHpcStatisticsCurrentEtsLogsGenerated            PerfCurrentCount,
        sonusSipHpcStatisticsCurrentEtsProgress       PerfCurrentCount,
        sonusSipHpcStatisticsCurrentEtsBusyEverywhereOut                PerfCurrentCount,
        sonusSipHpcStatisticsCurrentEtsBusyEverywhereIn               PerfCurrentCount,
        sonusSipHpcStatisticsCurrentEtsForbiddenOut           PerfCurrentCount
    }

sonusSipHpcStatisticsCurrentShelfIndex OBJECT-TYPE
    SYNTAX          SonusShelfIndex
    MAX-ACCESS      read-only
    STATUS          current
    DESCRIPTION     
            "The shelf index into the sonusSipHpcStatisticsCurrentTable."
    ::= { sonusSipHpcStatisticsCurrentEntry 1 }

sonusSipHpcStatisticsCurrentValidData OBJECT-TYPE
    SYNTAX          TruthValue
    MAX-ACCESS      read-only
    STATUS          current
    DESCRIPTION     
            "Indicates if this current data is valid."
    ::= { sonusSipHpcStatisticsCurrentEntry 2 }

sonusSipHpcStatisticsCurrentEtsInvitesOut OBJECT-TYPE
    SYNTAX          PerfCurrentCount
    MAX-ACCESS      read-only
    STATUS          current
    DESCRIPTION     
            "Generated INVITEs containing RPH with ETS."
    ::= { sonusSipHpcStatisticsCurrentEntry 3 }

sonusSipHpcStatisticsCurrentEtsRinging OBJECT-TYPE
    SYNTAX          PerfCurrentCount
    MAX-ACCESS      read-only
    STATUS          current
    DESCRIPTION     
            "Generated 180 INVITE responses containing RPH with ETS."
    ::= { sonusSipHpcStatisticsCurrentEntry 4 }

sonusSipHpcStatisticsCurrentEtsQueued OBJECT-TYPE
    SYNTAX          PerfCurrentCount
    MAX-ACCESS      read-only
    STATUS          current
    DESCRIPTION     
            "Generated 182 INVITE responses containing RPH with ETS."
    ::= { sonusSipHpcStatisticsCurrentEntry 5 }

sonusSipHpcStatisticsCurrentEtsSuccess OBJECT-TYPE
    SYNTAX          PerfCurrentCount
    MAX-ACCESS      read-only
    STATUS          current
    DESCRIPTION     
            "Generated 200 INVITE responses containing RPH with ETS."
    ::= { sonusSipHpcStatisticsCurrentEntry 6 }

sonusSipHpcStatisticsCurrentEtsFailure OBJECT-TYPE
    SYNTAX          PerfCurrentCount
    MAX-ACCESS      read-only
    STATUS          current
    DESCRIPTION     
            "Generated 4xx INVITE responses containing RPH with ETS."
    ::= { sonusSipHpcStatisticsCurrentEntry 7 }

sonusSipHpcStatisticsCurrentEtsBadRequestOut OBJECT-TYPE
    SYNTAX          PerfCurrentCount
    MAX-ACCESS      read-only
    STATUS          current
    DESCRIPTION     
            "Generated 400 responses (with 417 reason) containing RPH with ETS."
    ::= { sonusSipHpcStatisticsCurrentEntry 8 }

sonusSipHpcStatisticsCurrentEtsTimeout OBJECT-TYPE
    SYNTAX          PerfCurrentCount
    MAX-ACCESS      read-only
    STATUS          current
    DESCRIPTION     
            "Generated 408 INVITE responses containing RPH with ETS."
    ::= { sonusSipHpcStatisticsCurrentEntry 9 }

sonusSipHpcStatisticsCurrentEtsUnknownRp OBJECT-TYPE
    SYNTAX          PerfCurrentCount
    MAX-ACCESS      read-only
    STATUS          current
    DESCRIPTION     
            "Generated 417 INVITE responses containing RPH with ETS."
    ::= { sonusSipHpcStatisticsCurrentEntry 10 }

sonusSipHpcStatisticsCurrentEtsBusyHere OBJECT-TYPE
    SYNTAX          PerfCurrentCount
    MAX-ACCESS      read-only
    STATUS          current
    DESCRIPTION     
            "Generated 486 INVITE responses containing RPH with ETS."
    ::= { sonusSipHpcStatisticsCurrentEntry 11 }

sonusSipHpcStatisticsCurrentEtsInvitesIn OBJECT-TYPE
    SYNTAX          PerfCurrentCount
    MAX-ACCESS      read-only
    STATUS          current
    DESCRIPTION     
            "Received INVITEs containing RPH with ETS."
    ::= { sonusSipHpcStatisticsCurrentEntry 12 }

sonusSipHpcStatisticsCurrentEtsInvitesEtsDn OBJECT-TYPE
    SYNTAX          PerfCurrentCount
    MAX-ACCESS      read-only
    STATUS          current
    DESCRIPTION     
            "Received INVITEs with ETS-DN but no RPH with ETS."
    ::= { sonusSipHpcStatisticsCurrentEntry 13 }

sonusSipHpcStatisticsCurrentEtsBadRequestIn OBJECT-TYPE
    SYNTAX          PerfCurrentCount
    MAX-ACCESS      read-only
    STATUS          current
    DESCRIPTION     
            "Receive 400 INVITE responses (with 417 reason) containing RPH with ETS."
    ::= { sonusSipHpcStatisticsCurrentEntry 14 }

sonusSipHpcStatisticsCurrentEtsUnknownRpIn OBJECT-TYPE
    SYNTAX          PerfCurrentCount
    MAX-ACCESS      read-only
    STATUS          current
    DESCRIPTION     
            "Received 417 INVITE responses containing RPH with ETS."
    ::= { sonusSipHpcStatisticsCurrentEntry 15 }

sonusSipHpcStatisticsCurrentEtsBadExtnIn OBJECT-TYPE
    SYNTAX          PerfCurrentCount
    MAX-ACCESS      read-only
    STATUS          current
    DESCRIPTION     
            "Received 420 INVITE responses containing RPH with ETS."
    ::= { sonusSipHpcStatisticsCurrentEntry 16 }

sonusSipHpcStatisticsCurrentEtsForbiddenIn OBJECT-TYPE
    SYNTAX          PerfCurrentCount
    MAX-ACCESS      read-only
    STATUS          current
    DESCRIPTION     
            "Received 403 INVITE responses containing RPH with ETS."
    ::= { sonusSipHpcStatisticsCurrentEntry 17 }

sonusSipHpcStatisticsCurrentEtsLogsGenerated OBJECT-TYPE
    SYNTAX          PerfCurrentCount
    MAX-ACCESS      read-only
    STATUS          current
    DESCRIPTION     
            "Number of ETS-related logs generated"
    ::= { sonusSipHpcStatisticsCurrentEntry 18 }

sonusSipHpcStatisticsCurrentEtsProgress OBJECT-TYPE
    SYNTAX          PerfCurrentCount
    MAX-ACCESS      read-only
    STATUS          current
    DESCRIPTION     
            "Generated 183 INVITE responses containing RPH with ETS."
    ::= { sonusSipHpcStatisticsCurrentEntry 19 }

sonusSipHpcStatisticsCurrentEtsBusyEverywhereOut OBJECT-TYPE
    SYNTAX          PerfCurrentCount
    MAX-ACCESS      read-only
    STATUS          current
    DESCRIPTION     
            "Generated 600 INVITE responses containing RPH with ETS."
    ::= { sonusSipHpcStatisticsCurrentEntry 20 }

sonusSipHpcStatisticsCurrentEtsBusyEverywhereIn OBJECT-TYPE
    SYNTAX          PerfCurrentCount
    MAX-ACCESS      read-only
    STATUS          current
    DESCRIPTION     
            "Received 600 INVITE responses containing RPH with ETS."
    ::= { sonusSipHpcStatisticsCurrentEntry 21 }

sonusSipHpcStatisticsCurrentEtsForbiddenOut OBJECT-TYPE
    SYNTAX          PerfCurrentCount
    MAX-ACCESS      read-only
    STATUS          current
    DESCRIPTION     
            "Sending 403 reject responses for HPC call."
    ::= { sonusSipHpcStatisticsCurrentEntry 22 }

sonusSipHpcStatisticsIntervalTable OBJECT-TYPE
    SYNTAX          SEQUENCE OF SonusSipHpcStatisticsIntervalEntry
    MAX-ACCESS      not-accessible
    STATUS          current
    DESCRIPTION     
            "This table presents SIP stack HPC interval statistics for each shelf."
    ::= { sonusSipHpcStatisticsObjects 2 }

sonusSipHpcStatisticsIntervalEntry OBJECT-TYPE
    SYNTAX          SonusSipHpcStatisticsIntervalEntry
    MAX-ACCESS      not-accessible
    STATUS          current
    DESCRIPTION     
            ""
    INDEX           { sonusSipHpcStatisticsIntervalShelfIndex, 
                      sonusSipHpcStatisticsIntervalNumber }
    ::= { sonusSipHpcStatisticsIntervalTable 1 }

SonusSipHpcStatisticsIntervalEntry ::=
    SEQUENCE {
        sonusSipHpcStatisticsIntervalShelfIndex       SonusShelfIndex,
        sonusSipHpcStatisticsIntervalNumber   Integer32,
        sonusSipHpcStatisticsIntervalValidData      TruthValue,
        sonusSipHpcStatisticsIntervalEtsInvitesOut          PerfIntervalCount,
        sonusSipHpcStatisticsIntervalEtsRinging       PerfIntervalCount,
        sonusSipHpcStatisticsIntervalEtsQueued      PerfIntervalCount,
        sonusSipHpcStatisticsIntervalEtsSuccess       PerfIntervalCount,
        sonusSipHpcStatisticsIntervalEtsFailure       PerfIntervalCount,
        sonusSipHpcStatisticsIntervalEtsBadRequestOut             PerfIntervalCount,
        sonusSipHpcStatisticsIntervalEtsTimeout       PerfIntervalCount,
        sonusSipHpcStatisticsIntervalEtsUnknownRp         PerfIntervalCount,
        sonusSipHpcStatisticsIntervalEtsBusyHere        PerfIntervalCount,
        sonusSipHpcStatisticsIntervalEtsInvitesIn         PerfIntervalCount,
        sonusSipHpcStatisticsIntervalEtsInvitesEtsDn            PerfIntervalCount,
        sonusSipHpcStatisticsIntervalEtsBadRequestIn            PerfIntervalCount,
        sonusSipHpcStatisticsIntervalEtsUnknownRpIn           PerfIntervalCount,
        sonusSipHpcStatisticsIntervalEtsBadExtnIn         PerfIntervalCount,
        sonusSipHpcStatisticsIntervalEtsForbiddenIn           PerfIntervalCount,
        sonusSipHpcStatisticsIntervalEtsLogsGenerated             PerfIntervalCount,
        sonusSipHpcStatisticsIntervalTime TimeTicks,
        sonusSipHpcStatisticsIntervalEtsProgress        PerfIntervalCount,
        sonusSipHpcStatisticsIntervalEtsBusyEverywhereOut                 PerfIntervalCount,
        sonusSipHpcStatisticsIntervalEtsBusyEverywhereIn                PerfIntervalCount,
        sonusSipHpcStatisticsIntervalEtsForbiddenOut            PerfIntervalCount
    }

sonusSipHpcStatisticsIntervalShelfIndex OBJECT-TYPE
    SYNTAX          SonusShelfIndex
    MAX-ACCESS      read-only
    STATUS          current
    DESCRIPTION     
            "The shelf index into the sonusSipHpcStatisticsIntervalTable."
    ::= { sonusSipHpcStatisticsIntervalEntry 1 }

sonusSipHpcStatisticsIntervalNumber OBJECT-TYPE
    SYNTAX          Integer32 (1..288)
    MAX-ACCESS      not-accessible
    STATUS          current
    DESCRIPTION     
            "A number between 1 and 288, which identifies the
             interval for which the set of statistics is available.
             The interval identified by 1 is the most recently
             completed interval, and the interval identified
             by N is the interval immediately preceding the
             one identified by N-1."
    ::= { sonusSipHpcStatisticsIntervalEntry 2 }

sonusSipHpcStatisticsIntervalValidData OBJECT-TYPE
    SYNTAX          TruthValue
    MAX-ACCESS      read-only
    STATUS          current
    DESCRIPTION     
            "Indicates if this current data is valid."
    ::= { sonusSipHpcStatisticsIntervalEntry 3 }

sonusSipHpcStatisticsIntervalEtsInvitesOut OBJECT-TYPE
    SYNTAX          PerfIntervalCount
    MAX-ACCESS      read-only
    STATUS          current
    DESCRIPTION     
            "Generated INVITEs containing RPH with ETS."
    ::= { sonusSipHpcStatisticsIntervalEntry 4 }

sonusSipHpcStatisticsIntervalEtsRinging OBJECT-TYPE
    SYNTAX          PerfIntervalCount
    MAX-ACCESS      read-only
    STATUS          current
    DESCRIPTION     
            "Generated 180 INVITE responses containing RPH with ETS."
    ::= { sonusSipHpcStatisticsIntervalEntry 5 }

sonusSipHpcStatisticsIntervalEtsQueued OBJECT-TYPE
    SYNTAX          PerfIntervalCount
    MAX-ACCESS      read-only
    STATUS          current
    DESCRIPTION     
            "Generated 182 INVITE responses containing RPH with ETS."
    ::= { sonusSipHpcStatisticsIntervalEntry 6 }

sonusSipHpcStatisticsIntervalEtsSuccess OBJECT-TYPE
    SYNTAX          PerfIntervalCount
    MAX-ACCESS      read-only
    STATUS          current
    DESCRIPTION     
            "Generated 200 INVITE responses containing RPH with ETS."
    ::= { sonusSipHpcStatisticsIntervalEntry 7 }

sonusSipHpcStatisticsIntervalEtsFailure OBJECT-TYPE
    SYNTAX          PerfIntervalCount
    MAX-ACCESS      read-only
    STATUS          current
    DESCRIPTION     
            "Generated 4xx INVITE responses containing RPH with ETS."
    ::= { sonusSipHpcStatisticsIntervalEntry 8 }

sonusSipHpcStatisticsIntervalEtsBadRequestOut OBJECT-TYPE
    SYNTAX          PerfIntervalCount
    MAX-ACCESS      read-only
    STATUS          current
    DESCRIPTION     
            "Generated 400 responses (with 417 reason) containing RPH with ETS."
    ::= { sonusSipHpcStatisticsIntervalEntry 9 }

sonusSipHpcStatisticsIntervalEtsTimeout OBJECT-TYPE
    SYNTAX          PerfIntervalCount
    MAX-ACCESS      read-only
    STATUS          current
    DESCRIPTION     
            "Generated 408 INVITE responses containing RPH with ETS."
    ::= { sonusSipHpcStatisticsIntervalEntry 10 }

sonusSipHpcStatisticsIntervalEtsUnknownRp OBJECT-TYPE
    SYNTAX          PerfIntervalCount
    MAX-ACCESS      read-only
    STATUS          current
    DESCRIPTION     
            "Generated 417 INVITE responses containing RPH with ETS."
    ::= { sonusSipHpcStatisticsIntervalEntry 11 }

sonusSipHpcStatisticsIntervalEtsBusyHere OBJECT-TYPE
    SYNTAX          PerfIntervalCount
    MAX-ACCESS      read-only
    STATUS          current
    DESCRIPTION     
            "Generated 486 INVITE responses containing RPH with ETS."
    ::= { sonusSipHpcStatisticsIntervalEntry 12 }

sonusSipHpcStatisticsIntervalEtsInvitesIn OBJECT-TYPE
    SYNTAX          PerfIntervalCount
    MAX-ACCESS      read-only
    STATUS          current
    DESCRIPTION     
            "Received INVITEs containing RPH with ETS."
    ::= { sonusSipHpcStatisticsIntervalEntry 13 }

sonusSipHpcStatisticsIntervalEtsInvitesEtsDn OBJECT-TYPE
    SYNTAX          PerfIntervalCount
    MAX-ACCESS      read-only
    STATUS          current
    DESCRIPTION     
            "Received INVITEs with ETS-DN but no RPH with ETS."
    ::= { sonusSipHpcStatisticsIntervalEntry 14 }

sonusSipHpcStatisticsIntervalEtsBadRequestIn OBJECT-TYPE
    SYNTAX          PerfIntervalCount
    MAX-ACCESS      read-only
    STATUS          current
    DESCRIPTION     
            "Received 400 INVITE responses (with 417 reason) containing RPH with ETS."
    ::= { sonusSipHpcStatisticsIntervalEntry 15 }

sonusSipHpcStatisticsIntervalEtsUnknownRpIn OBJECT-TYPE
    SYNTAX          PerfIntervalCount
    MAX-ACCESS      read-only
    STATUS          current
    DESCRIPTION     
            "Received 417 INVITE responses containing RPH with ETS."
    ::= { sonusSipHpcStatisticsIntervalEntry 16 }

sonusSipHpcStatisticsIntervalEtsBadExtnIn OBJECT-TYPE
    SYNTAX          PerfIntervalCount
    MAX-ACCESS      read-only
    STATUS          current
    DESCRIPTION     
            "Received 420 INVITE responses containing RPH with ETS."
    ::= { sonusSipHpcStatisticsIntervalEntry 17 }

sonusSipHpcStatisticsIntervalEtsForbiddenIn OBJECT-TYPE
    SYNTAX          PerfIntervalCount
    MAX-ACCESS      read-only
    STATUS          current
    DESCRIPTION     
            "Indicates the received 403 INVITE responses for HPC calls."
    ::= { sonusSipHpcStatisticsIntervalEntry 18 }

sonusSipHpcStatisticsIntervalEtsLogsGenerated OBJECT-TYPE
    SYNTAX          PerfIntervalCount
    MAX-ACCESS      read-only
    STATUS          current
    DESCRIPTION     
            "Number of ETS-related logs generated"
    ::= { sonusSipHpcStatisticsIntervalEntry 19 }

sonusSipHpcStatisticsIntervalTime OBJECT-TYPE
    SYNTAX          TimeTicks
    MAX-ACCESS      read-only
    STATUS          current
    DESCRIPTION     
            "This variable contains the end of interval time
             stamp for the specified interval."
    ::= { sonusSipHpcStatisticsIntervalEntry 20 }

sonusSipHpcStatisticsIntervalEtsProgress OBJECT-TYPE
    SYNTAX          PerfIntervalCount
    MAX-ACCESS      read-only
    STATUS          current
    DESCRIPTION     
            "Generated 183 INVITE responses containing RPH with ETS."
    ::= { sonusSipHpcStatisticsIntervalEntry 21 }

sonusSipHpcStatisticsIntervalEtsBusyEverywhereOut OBJECT-TYPE
    SYNTAX          PerfIntervalCount
    MAX-ACCESS      read-only
    STATUS          current
    DESCRIPTION     
            "Generated 600 INVITE responses containing RPH with ETS."
    ::= { sonusSipHpcStatisticsIntervalEntry 22 }

sonusSipHpcStatisticsIntervalEtsBusyEverywhereIn OBJECT-TYPE
    SYNTAX          PerfIntervalCount
    MAX-ACCESS      read-only
    STATUS          current
    DESCRIPTION     
            "Indicates the received 600 INVITE responses for HPC calls."
    ::= { sonusSipHpcStatisticsIntervalEntry 23 }

sonusSipHpcStatisticsIntervalEtsForbiddenOut OBJECT-TYPE
    SYNTAX          PerfIntervalCount
    MAX-ACCESS      read-only
    STATUS          current
    DESCRIPTION     
            "Indicates the sending 403 reject responses for HPC calls."
    ::= { sonusSipHpcStatisticsIntervalEntry 24 }

sonusHpcStatisticsObjects OBJECT IDENTIFIER
    ::= { sonusPerformanceStatisticsObjects 7 }

sonusHpcCurrentTable OBJECT-TYPE
    SYNTAX          SEQUENCE OF SonusHpcCurrentEntry
    MAX-ACCESS      not-accessible
    STATUS          current
    DESCRIPTION     
            "The Sonus High Probability of Completion  Statistics
             Current table."
    ::= { sonusHpcStatisticsObjects 1 }

sonusHpcCurrentEntry OBJECT-TYPE
    SYNTAX          SonusHpcCurrentEntry
    MAX-ACCESS      not-accessible
    STATUS          current
    DESCRIPTION     
            "An entry in the Sonus High Probability of Completion Statistics
             Current table."
    INDEX           { sonusHpcCurrentShelfIndex }
    ::= { sonusHpcCurrentTable 1 }

SonusHpcCurrentEntry ::=
    SEQUENCE {
        sonusHpcCurrentShelfIndex       SonusShelfIndex,
        sonusHpcCurrentPstnIngressCalls PerfCurrentCount,
        sonusHpcCurrentPstnEgressCalls  PerfCurrentCount,
        sonusHpcCurrentIpInternalIngressCalls     PerfCurrentCount,
        sonusHpcCurrentIpInternalEgressCalls    PerfCurrentCount,
        sonusHpcCurrentIpExternalIngressCalls     PerfCurrentCount,
        sonusHpcCurrentIpExternalEgressCalls    PerfCurrentCount,
        sonusHpcCurrentNoRouteCalls     PerfCurrentCount,
        sonusHpcCurrentCqQueueAttempts  PerfCurrentCount,
        sonusHpcCurrentCqQueueOverflows PerfCurrentCount,
        sonusHpcCurrentCqQueueAbandons  PerfCurrentCount,
        sonusHpcCurrentCqQueueTimeouts  PerfCurrentCount,
        sonusHpcCurrentEqQueueAttempts  PerfCurrentCount,
        sonusHpcCurrentEqQueueOverflows PerfCurrentCount,
        sonusHpcCurrentEqQueueAbandons  PerfCurrentCount,
        sonusHpcCurrentEqQueueTimeouts  PerfCurrentCount,
        sonusHpcCurrentIqInternalQueueAttempts      PerfCurrentCount,
        sonusHpcCurrentIqInternalQueueOverflows       PerfCurrentCount,
        sonusHpcCurrentIqInternalQueueAbandons      PerfCurrentCount,
        sonusHpcCurrentIqInternalQueueTimeouts      PerfCurrentCount,
        sonusHpcCurrentIqInternalOversubscribeAttempts              PerfCurrentCount,
        sonusHpcCurrentIqInternalOversubscribedCalls            PerfCurrentCount,
        sonusHpcCurrentIqExternalQueueAttempts      PerfCurrentCount,
        sonusHpcCurrentIqExternalQueueOverflows       PerfCurrentCount,
        sonusHpcCurrentIqExternalQueueAbandons      PerfCurrentCount,
        sonusHpcCurrentIqExternalQueueTimeouts      PerfCurrentCount,
        sonusHpcCurrentIqExternalOversubscribeAttempts              PerfCurrentCount,
        sonusHpcCurrentIqExternalOversubscribedCalls            PerfCurrentCount,
        sonusHpcCurrentTrafficControlExemptions       PerfCurrentCount,
        sonusHpcCurrentIptgOversubscriptions    PerfCurrentCount
    }

sonusHpcCurrentShelfIndex OBJECT-TYPE
    SYNTAX          SonusShelfIndex
    MAX-ACCESS      read-only
    STATUS          current
    DESCRIPTION     
            "The index into the sonusHpcCurrentTable."
    ::= { sonusHpcCurrentEntry 1 }

sonusHpcCurrentPstnIngressCalls OBJECT-TYPE
    SYNTAX          PerfCurrentCount
    MAX-ACCESS      read-only
    STATUS          obsolete
    DESCRIPTION     
            "The current number of HPC calls coming in from PSTN trunks.
             This field became obsolete in release 6.4"
    ::= { sonusHpcCurrentEntry 2 }

sonusHpcCurrentPstnEgressCalls OBJECT-TYPE
    SYNTAX          PerfCurrentCount
    MAX-ACCESS      read-only
    STATUS          current
    DESCRIPTION     
            "The current number of HPC calls going out to PSTN trunks."
    ::= { sonusHpcCurrentEntry 3 }

sonusHpcCurrentIpInternalIngressCalls OBJECT-TYPE
    SYNTAX          PerfCurrentCount
    MAX-ACCESS      read-only
    STATUS          current
    DESCRIPTION     
            "The current number of HPC calls going out on internal IPTGs
             (Inbound IPTGs)."
    ::= { sonusHpcCurrentEntry 4 }

sonusHpcCurrentIpInternalEgressCalls OBJECT-TYPE
    SYNTAX          PerfCurrentCount
    MAX-ACCESS      read-only
    STATUS          current
    DESCRIPTION     
            "The current number of HPC calls coming in on internal IPTGs
             (Outbound IPTGs)."
    ::= { sonusHpcCurrentEntry 5 }

sonusHpcCurrentIpExternalIngressCalls OBJECT-TYPE
    SYNTAX          PerfCurrentCount
    MAX-ACCESS      read-only
    STATUS          current
    DESCRIPTION     
            "The current number of HPC calls going out on external IPTGs
             (Inbound IPTGs)."
    ::= { sonusHpcCurrentEntry 6 }

sonusHpcCurrentIpExternalEgressCalls OBJECT-TYPE
    SYNTAX          PerfCurrentCount
    MAX-ACCESS      read-only
    STATUS          current
    DESCRIPTION     
            "The current number of HPC calls coming in on external IPTGs
             (Outbound IPTGs)."
    ::= { sonusHpcCurrentEntry 7 }

sonusHpcCurrentNoRouteCalls OBJECT-TYPE
    SYNTAX          PerfCurrentCount
    MAX-ACCESS      read-only
    STATUS          current
    DESCRIPTION     
            "The current number of HPC calls that cannot be connected to
             any route in the route list."
    ::= { sonusHpcCurrentEntry 8 }

sonusHpcCurrentCqQueueAttempts OBJECT-TYPE
    SYNTAX          PerfCurrentCount
    MAX-ACCESS      read-only
    STATUS          current
    DESCRIPTION     
            "The current number of HPC calls that were successfully placed
             on HPC Call Queuing queues."
    ::= { sonusHpcCurrentEntry 9 }

sonusHpcCurrentCqQueueOverflows OBJECT-TYPE
    SYNTAX          PerfCurrentCount
    MAX-ACCESS      read-only
    STATUS          current
    DESCRIPTION     
            "The current number of HPC calls for which HPC call queuing attempts
             were unsuccessful because queues were full."
    ::= { sonusHpcCurrentEntry 10 }

sonusHpcCurrentCqQueueAbandons OBJECT-TYPE
    SYNTAX          PerfCurrentCount
    MAX-ACCESS      read-only
    STATUS          current
    DESCRIPTION     
            "The current number of HPC calls that were placed in HPC Call Queuing queues,
             but were subsequently abandoned before they could be completed."
    ::= { sonusHpcCurrentEntry 11 }

sonusHpcCurrentCqQueueTimeouts OBJECT-TYPE
    SYNTAX          PerfCurrentCount
    MAX-ACCESS      read-only
    STATUS          current
    DESCRIPTION     
            "The current number of HPC calls removed from HPC Call Queuing queues due to
             expiration of the queue timeout timer."
    ::= { sonusHpcCurrentEntry 12 }

sonusHpcCurrentEqQueueAttempts OBJECT-TYPE
    SYNTAX          PerfCurrentCount
    MAX-ACCESS      read-only
    STATUS          current
    DESCRIPTION     
            "The current number of HPC calls that were successfully placed on
             HPC Egress Queuing queues."
    ::= { sonusHpcCurrentEntry 13 }

sonusHpcCurrentEqQueueOverflows OBJECT-TYPE
    SYNTAX          PerfCurrentCount
    MAX-ACCESS      read-only
    STATUS          current
    DESCRIPTION     
            "The current number of HPC calls for which HPC egress queuing attempts
             were unsuccessful because the queue was full."
    ::= { sonusHpcCurrentEntry 14 }

sonusHpcCurrentEqQueueAbandons OBJECT-TYPE
    SYNTAX          PerfCurrentCount
    MAX-ACCESS      read-only
    STATUS          current
    DESCRIPTION     
            "The current number of HPC calls that were placed in the HPC Egress Queuing queue,
             but were subsequently abandoned before the could be completed."
    ::= { sonusHpcCurrentEntry 15 }

sonusHpcCurrentEqQueueTimeouts OBJECT-TYPE
    SYNTAX          PerfCurrentCount
    MAX-ACCESS      read-only
    STATUS          current
    DESCRIPTION     
            "The current number of HPC calls removed from the HPC Egress Queuing queue due
             to expiration of the queue timeout timer."
    ::= { sonusHpcCurrentEntry 16 }

sonusHpcCurrentIqInternalQueueAttempts OBJECT-TYPE
    SYNTAX          PerfCurrentCount
    MAX-ACCESS      read-only
    STATUS          current
    DESCRIPTION     
            "The current number of HPC calls that were successfully placed on
             internal HPC IP Queuing queues."
    ::= { sonusHpcCurrentEntry 17 }

sonusHpcCurrentIqInternalQueueOverflows OBJECT-TYPE
    SYNTAX          PerfCurrentCount
    MAX-ACCESS      read-only
    STATUS          current
    DESCRIPTION     
            "The current number of HPC calls for which HPC IP Queuing internal queuing
             attempts were unsuccessful because the queue was full."
    ::= { sonusHpcCurrentEntry 18 }

sonusHpcCurrentIqInternalQueueAbandons OBJECT-TYPE
    SYNTAX          PerfCurrentCount
    MAX-ACCESS      read-only
    STATUS          current
    DESCRIPTION     
            "The current number of HPC calls that were placed in internal HPC
             IP Queuing queues, but were subsequently abandoned before the could be completed."
    ::= { sonusHpcCurrentEntry 19 }

sonusHpcCurrentIqInternalQueueTimeouts OBJECT-TYPE
    SYNTAX          PerfCurrentCount
    MAX-ACCESS      read-only
    STATUS          current
    DESCRIPTION     
            "The current number of HPC calls removed from internal HPC IP Queuing queues
             due to expiration of the queue timeout timer."
    ::= { sonusHpcCurrentEntry 20 }

sonusHpcCurrentIqInternalOversubscribeAttempts OBJECT-TYPE
    SYNTAX          PerfCurrentCount
    MAX-ACCESS      read-only
    STATUS          current
    DESCRIPTION     
            "The current number of HPC calls that encountered internal IPTGs
             that are over their normal resource allocations."
    ::= { sonusHpcCurrentEntry 21 }

sonusHpcCurrentIqInternalOversubscribedCalls OBJECT-TYPE
    SYNTAX          PerfCurrentCount
    MAX-ACCESS      read-only
    STATUS          current
    DESCRIPTION     
            "The current number of HPC calls connected on internal IPTGs
             that are over their normal resource allocations."
    ::= { sonusHpcCurrentEntry 22 }

sonusHpcCurrentIqExternalQueueAttempts OBJECT-TYPE
    SYNTAX          PerfCurrentCount
    MAX-ACCESS      read-only
    STATUS          current
    DESCRIPTION     
            "The current number of HPC calls that were successfully placed
             on external HPC IP Queuing queues."
    ::= { sonusHpcCurrentEntry 23 }

sonusHpcCurrentIqExternalQueueOverflows OBJECT-TYPE
    SYNTAX          PerfCurrentCount
    MAX-ACCESS      read-only
    STATUS          current
    DESCRIPTION     
            "The current number of HPC calls for which HPC IP Queuing external
             queuing attempts were unsuccessful because the queue was full."
    ::= { sonusHpcCurrentEntry 24 }

sonusHpcCurrentIqExternalQueueAbandons OBJECT-TYPE
    SYNTAX          PerfCurrentCount
    MAX-ACCESS      read-only
    STATUS          current
    DESCRIPTION     
            "The current number of HPC calls that were placed in external HPC
             IP Queuing queues, but were subsequently abandoned before the could be completed."
    ::= { sonusHpcCurrentEntry 25 }

sonusHpcCurrentIqExternalQueueTimeouts OBJECT-TYPE
    SYNTAX          PerfCurrentCount
    MAX-ACCESS      read-only
    STATUS          current
    DESCRIPTION     
            "The current number of HPC calls removed from external HPC IP Queuing
             queues due to expiration of the queue timeout timer."
    ::= { sonusHpcCurrentEntry 26 }

sonusHpcCurrentIqExternalOversubscribeAttempts OBJECT-TYPE
    SYNTAX          PerfCurrentCount
    MAX-ACCESS      read-only
    STATUS          current
    DESCRIPTION     
            "The current number of HPC calls that encountered external IPTGs
             that are over their normal resource allocations."
    ::= { sonusHpcCurrentEntry 27 }

sonusHpcCurrentIqExternalOversubscribedCalls OBJECT-TYPE
    SYNTAX          PerfCurrentCount
    MAX-ACCESS      read-only
    STATUS          current
    DESCRIPTION     
            "The current number of HPC calls connected on external IPTGs that
             are over their normal resource allocations."
    ::= { sonusHpcCurrentEntry 28 }

sonusHpcCurrentTrafficControlExemptions OBJECT-TYPE
    SYNTAX          PerfCurrentCount
    MAX-ACCESS      read-only
    STATUS          current
    DESCRIPTION     
            "The current number of HPC calls that were exempted from traffic controls."
    ::= { sonusHpcCurrentEntry 29 }

sonusHpcCurrentIptgOversubscriptions OBJECT-TYPE
    SYNTAX          PerfCurrentCount
    MAX-ACCESS      read-only
    STATUS          current
    DESCRIPTION     
            "The current number of HPC calls that were placed on IPTGs over their
             normal resource allocations."
    ::= { sonusHpcCurrentEntry 30 }

sonusHpcIntervalTable OBJECT-TYPE
    SYNTAX          SEQUENCE OF SonusHpcIntervalEntry
    MAX-ACCESS      not-accessible
    STATUS          current
    DESCRIPTION     
            "The Sonus High Probability of Completion  Statistics
             Interval table."
    ::= { sonusHpcStatisticsObjects 2 }

sonusHpcIntervalEntry OBJECT-TYPE
    SYNTAX          SonusHpcIntervalEntry
    MAX-ACCESS      not-accessible
    STATUS          current
    DESCRIPTION     
            "An entry in the Sonus High Probability of Completion  Statistics
             Interval table."
    INDEX           { sonusHpcIntervalShelfIndex, sonusHpcIntervalNumber }
    ::= { sonusHpcIntervalTable 1 }

SonusHpcIntervalEntry ::=
    SEQUENCE {
        sonusHpcIntervalShelfIndex      SonusShelfIndex,
        sonusHpcIntervalNumber          Integer32,
        sonusHpcIntervalTime            TimeTicks,
        sonusHpcIntervalValidData       TruthValue,
        sonusHpcIntervalPstnIngressCalls PerfIntervalCount,
        sonusHpcIntervalPstnEgressCalls PerfIntervalCount,
        sonusHpcIntervalIpInternalIngressCalls      PerfIntervalCount,
        sonusHpcIntervalIpInternalEgressCalls     PerfIntervalCount,
        sonusHpcIntervalIpExternalIngressCalls      PerfIntervalCount,
        sonusHpcIntervalIpExternalEgressCalls     PerfIntervalCount,
        sonusHpcIntervalNoRouteCalls    PerfIntervalCount,
        sonusHpcIntervalCqQueueAttempts PerfIntervalCount,
        sonusHpcIntervalCqQueueOverflows PerfIntervalCount,
        sonusHpcIntervalCqQueueAbandons PerfIntervalCount,
        sonusHpcIntervalCqQueueTimeouts PerfIntervalCount,
        sonusHpcIntervalEqQueueAttempts PerfIntervalCount,
        sonusHpcIntervalEqQueueOverflows PerfIntervalCount,
        sonusHpcIntervalEqQueueAbandons PerfIntervalCount,
        sonusHpcIntervalEqQueueTimeouts PerfIntervalCount,
        sonusHpcIntervalIqInternalQueueAttempts       PerfIntervalCount,
        sonusHpcIntervalIqInternalQueueOverflows        PerfIntervalCount,
        sonusHpcIntervalIqInternalQueueAbandons       PerfIntervalCount,
        sonusHpcIntervalIqInternalQueueTimeouts       PerfIntervalCount,
        sonusHpcIntervalIqInternalOversubscribeAttempts               PerfIntervalCount,
        sonusHpcIntervalIqInternalOversubscribedCalls             PerfIntervalCount,
        sonusHpcIntervalIqExternalQueueAttempts       PerfIntervalCount,
        sonusHpcIntervalIqExternalQueueOverflows        PerfIntervalCount,
        sonusHpcIntervalIqExternalQueueAbandons       PerfIntervalCount,
        sonusHpcIntervalIqExternalQueueTimeouts       PerfIntervalCount,
        sonusHpcIntervalIqExternalOversubscribeAttempts               PerfIntervalCount,
        sonusHpcIntervalIqExternalOversubscribedCalls             PerfIntervalCount,
        sonusHpcIntervalTrafficControlExemptions        PerfIntervalCount,
        sonusHpcIntervalIptgOversubscriptions     PerfIntervalCount
    }

sonusHpcIntervalShelfIndex OBJECT-TYPE
    SYNTAX          SonusShelfIndex
    MAX-ACCESS      read-only
    STATUS          current
    DESCRIPTION     
            "The index into the sonusHpcIntervalTable."
    ::= { sonusHpcIntervalEntry 1 }

sonusHpcIntervalNumber OBJECT-TYPE
    SYNTAX          Integer32 (1..288)
    MAX-ACCESS      not-accessible
    STATUS          current
    DESCRIPTION     
            "A number between 1 and 288, which identifies the
             interval for which the set of statistics is available.
             The interval identified by 1 is the most recently
             completed interval, and the interval identified
             by N is the interval immediately preceding the
             one identified by N-1."
    ::= { sonusHpcIntervalEntry 2 }

sonusHpcIntervalTime OBJECT-TYPE
    SYNTAX          TimeTicks
    MAX-ACCESS      read-only
    STATUS          current
    DESCRIPTION     
            "This variable contains the end of interval time
             stamp for the specified interval."
    ::= { sonusHpcIntervalEntry 3 }

sonusHpcIntervalValidData OBJECT-TYPE
    SYNTAX          TruthValue
    MAX-ACCESS      read-only
    STATUS          current
    DESCRIPTION     
            "This variable indicates if the data for this
             interval is valid."
    ::= { sonusHpcIntervalEntry 4 }

sonusHpcIntervalPstnIngressCalls OBJECT-TYPE
    SYNTAX          PerfIntervalCount
    MAX-ACCESS      read-only
    STATUS          obsolete
    DESCRIPTION     
            "The number of HPC calls coming in from PSTN trunks for the specified interval.
             This field became obsolete in release 6.4"
    ::= { sonusHpcIntervalEntry 6 }

sonusHpcIntervalPstnEgressCalls OBJECT-TYPE
    SYNTAX          PerfIntervalCount
    MAX-ACCESS      read-only
    STATUS          current
    DESCRIPTION     
            "The number of HPC calls going out to PSTN trunks for the specified interval."
    ::= { sonusHpcIntervalEntry 7 }

sonusHpcIntervalIpInternalIngressCalls OBJECT-TYPE
    SYNTAX          PerfIntervalCount
    MAX-ACCESS      read-only
    STATUS          current
    DESCRIPTION     
            "The number of HPC calls going out on internal IPTGs
             (Inbound IPTGs) for the specified interval."
    ::= { sonusHpcIntervalEntry 8 }

sonusHpcIntervalIpInternalEgressCalls OBJECT-TYPE
    SYNTAX          PerfIntervalCount
    MAX-ACCESS      read-only
    STATUS          current
    DESCRIPTION     
            "The number of HPC calls coming in on internal IPTGs
             (Outbound IPTGs) for the specified interval."
    ::= { sonusHpcIntervalEntry 9 }

sonusHpcIntervalIpExternalIngressCalls OBJECT-TYPE
    SYNTAX          PerfIntervalCount
    MAX-ACCESS      read-only
    STATUS          current
    DESCRIPTION     
            "The number of HPC calls going out on external IPTGs
             (Inbound IPTGs) for the specified interval."
    ::= { sonusHpcIntervalEntry 10 }

sonusHpcIntervalIpExternalEgressCalls OBJECT-TYPE
    SYNTAX          PerfIntervalCount
    MAX-ACCESS      read-only
    STATUS          current
    DESCRIPTION     
            "The number of HPC calls coming in on external IPTGs
             (Outbound IPTGs) for the specified interval."
    ::= { sonusHpcIntervalEntry 11 }

sonusHpcIntervalNoRouteCalls OBJECT-TYPE
    SYNTAX          PerfIntervalCount
    MAX-ACCESS      read-only
    STATUS          current
    DESCRIPTION     
            "The number of HPC calls that cannot be connected to
             any route in the route list for the specified interval."
    ::= { sonusHpcIntervalEntry 12 }

sonusHpcIntervalCqQueueAttempts OBJECT-TYPE
    SYNTAX          PerfIntervalCount
    MAX-ACCESS      read-only
    STATUS          current
    DESCRIPTION     
            "The number of HPC calls that were successfully placed
             on HPC Call Queuing queues for the specified interval."
    ::= { sonusHpcIntervalEntry 13 }

sonusHpcIntervalCqQueueOverflows OBJECT-TYPE
    SYNTAX          PerfIntervalCount
    MAX-ACCESS      read-only
    STATUS          current
    DESCRIPTION     
            "The number of HPC calls for which HPC call queuing attempts
             were unsuccessful because queues were full for the specified interval."
    ::= { sonusHpcIntervalEntry 14 }

sonusHpcIntervalCqQueueAbandons OBJECT-TYPE
    SYNTAX          PerfIntervalCount
    MAX-ACCESS      read-only
    STATUS          current
    DESCRIPTION     
            "The number of HPC calls that were placed in HPC Call Queuing queues,
             but were subsequently abandoned before they could be completed for the specified interval."
    ::= { sonusHpcIntervalEntry 15 }

sonusHpcIntervalCqQueueTimeouts OBJECT-TYPE
    SYNTAX          PerfIntervalCount
    MAX-ACCESS      read-only
    STATUS          current
    DESCRIPTION     
            "The number of HPC calls removed from HPC Call Queuing queues due to
             expiration of the queue timeout timer for the specified interval."
    ::= { sonusHpcIntervalEntry 16 }

sonusHpcIntervalEqQueueAttempts OBJECT-TYPE
    SYNTAX          PerfIntervalCount
    MAX-ACCESS      read-only
    STATUS          current
    DESCRIPTION     
            "The number of HPC calls that were successfully placed on
             HPC Egress Queuing queues for the specified interval."
    ::= { sonusHpcIntervalEntry 17 }

sonusHpcIntervalEqQueueOverflows OBJECT-TYPE
    SYNTAX          PerfIntervalCount
    MAX-ACCESS      read-only
    STATUS          current
    DESCRIPTION     
            "The number of HPC calls for which HPC egress queuing attempts
             were unsuccessful because the queue was full for the specified interval."
    ::= { sonusHpcIntervalEntry 18 }

sonusHpcIntervalEqQueueAbandons OBJECT-TYPE
    SYNTAX          PerfIntervalCount
    MAX-ACCESS      read-only
    STATUS          current
    DESCRIPTION     
            "The number of HPC calls that were placed in the HPC Egress Queuing queue,
             but were subsequently abandoned before the could be completed for the specified interval."
    ::= { sonusHpcIntervalEntry 19 }

sonusHpcIntervalEqQueueTimeouts OBJECT-TYPE
    SYNTAX          PerfIntervalCount
    MAX-ACCESS      read-only
    STATUS          current
    DESCRIPTION     
            "The number of HPC calls removed from the HPC Egress Queuing queue due
             to expiration of the queue timeout timer for the specified interval."
    ::= { sonusHpcIntervalEntry 20 }

sonusHpcIntervalIqInternalQueueAttempts OBJECT-TYPE
    SYNTAX          PerfIntervalCount
    MAX-ACCESS      read-only
    STATUS          current
    DESCRIPTION     
            "The number of HPC calls that were successfully placed on
             internal HPC IP Queuing queues for the specified interval."
    ::= { sonusHpcIntervalEntry 21 }

sonusHpcIntervalIqInternalQueueOverflows OBJECT-TYPE
    SYNTAX          PerfIntervalCount
    MAX-ACCESS      read-only
    STATUS          current
    DESCRIPTION     
            "The number of HPC calls for which HPC IP Queuing internal queuing
             attempts were unsuccessful because the queue was full for the specified interval."
    ::= { sonusHpcIntervalEntry 22 }

sonusHpcIntervalIqInternalQueueAbandons OBJECT-TYPE
    SYNTAX          PerfIntervalCount
    MAX-ACCESS      read-only
    STATUS          current
    DESCRIPTION     
            "The number of HPC calls that were placed in internal HPC
             IP Queuing queues, but were subsequently abandoned before the could be completed for the specified interval."
    ::= { sonusHpcIntervalEntry 23 }

sonusHpcIntervalIqInternalQueueTimeouts OBJECT-TYPE
    SYNTAX          PerfIntervalCount
    MAX-ACCESS      read-only
    STATUS          current
    DESCRIPTION     
            "The number of HPC calls removed from internal HPC IP Queuing queues
             due to expiration of the queue timeout timer for the specified interval."
    ::= { sonusHpcIntervalEntry 24 }

sonusHpcIntervalIqInternalOversubscribeAttempts OBJECT-TYPE
    SYNTAX          PerfIntervalCount
    MAX-ACCESS      read-only
    STATUS          current
    DESCRIPTION     
            "The number of HPC calls that encountered internal IPTGs
             that are over their normal resource allocations for the specified interval."
    ::= { sonusHpcIntervalEntry 25 }

sonusHpcIntervalIqInternalOversubscribedCalls OBJECT-TYPE
    SYNTAX          PerfIntervalCount
    MAX-ACCESS      read-only
    STATUS          current
    DESCRIPTION     
            "The number of HPC calls connected on internal IPTGs
             that are over their normal resource allocations for the specified interval."
    ::= { sonusHpcIntervalEntry 26 }

sonusHpcIntervalIqExternalQueueAttempts OBJECT-TYPE
    SYNTAX          PerfIntervalCount
    MAX-ACCESS      read-only
    STATUS          current
    DESCRIPTION     
            "The number of HPC calls that were successfully placed
             on external HPC IP Queuing queues for the specified interval."
    ::= { sonusHpcIntervalEntry 27 }

sonusHpcIntervalIqExternalQueueOverflows OBJECT-TYPE
    SYNTAX          PerfIntervalCount
    MAX-ACCESS      read-only
    STATUS          current
    DESCRIPTION     
            "The number of HPC calls for which HPC IP Queuing external
             queuing attempts were unsuccessful because the queue was full for the specified interval."
    ::= { sonusHpcIntervalEntry 28 }

sonusHpcIntervalIqExternalQueueAbandons OBJECT-TYPE
    SYNTAX          PerfIntervalCount
    MAX-ACCESS      read-only
    STATUS          current
    DESCRIPTION     
            "The number of HPC calls that were placed in external HPC
             IP Queuing queues, but were subsequently abandoned before the could be completed for the specified interval."
    ::= { sonusHpcIntervalEntry 29 }

sonusHpcIntervalIqExternalQueueTimeouts OBJECT-TYPE
    SYNTAX          PerfIntervalCount
    MAX-ACCESS      read-only
    STATUS          current
    DESCRIPTION     
            "The number of HPC calls removed from external HPC IP Queuing
             queues due to expiration of the queue timeout timer for the specified interval."
    ::= { sonusHpcIntervalEntry 30 }

sonusHpcIntervalIqExternalOversubscribeAttempts OBJECT-TYPE
    SYNTAX          PerfIntervalCount
    MAX-ACCESS      read-only
    STATUS          current
    DESCRIPTION     
            "The number of HPC calls that encountered external IPTGs
             that are over their normal resource allocations for the specified interval."
    ::= { sonusHpcIntervalEntry 31 }

sonusHpcIntervalIqExternalOversubscribedCalls OBJECT-TYPE
    SYNTAX          PerfIntervalCount
    MAX-ACCESS      read-only
    STATUS          current
    DESCRIPTION     
            "The number of HPC calls connected on external IPTGs that
             are over their normal resource allocations for the specified interval."
    ::= { sonusHpcIntervalEntry 32 }

sonusHpcIntervalTrafficControlExemptions OBJECT-TYPE
    SYNTAX          PerfIntervalCount
    MAX-ACCESS      read-only
    STATUS          current
    DESCRIPTION     
            "The number of HPC calls that were exempted from traffic controls for the specified interval."
    ::= { sonusHpcIntervalEntry 33 }

sonusHpcIntervalIptgOversubscriptions OBJECT-TYPE
    SYNTAX          PerfIntervalCount
    MAX-ACCESS      read-only
    STATUS          current
    DESCRIPTION     
            "The number of HPC calls that were placed on IPTGs over their
             normal resource allocations for the specified interval."
    ::= { sonusHpcIntervalEntry 34 }

sonusDspPadResStatisticsObjects OBJECT IDENTIFIER
    ::= { sonusPerformanceStatisticsObjects 8 }

sonusSysCallDspResCurrentTable OBJECT-TYPE
    SYNTAX          SEQUENCE OF SonusSysCallDspResCurrentEntry
    MAX-ACCESS      not-accessible
    STATUS          current
    DESCRIPTION     
            "The Sonus System Call DSP Resource Current table."
    ::= { sonusDspPadResStatisticsObjects 1 }

sonusSysCallDspResCurrentEntry OBJECT-TYPE
    SYNTAX          SonusSysCallDspResCurrentEntry
    MAX-ACCESS      not-accessible
    STATUS          current
    DESCRIPTION     
            "An entry in the Sonus System Call DSP Resource Current table."
    INDEX           { sonusSysCallDspResCurrentShelfIndex }
    ::= { sonusSysCallDspResCurrentTable 1 }

SonusSysCallDspResCurrentEntry ::=
    SEQUENCE {
        sonusSysCallDspResCurrentShelfIndex   SonusShelfIndex,
        sonusSysCallDspResCurrentNumCallSuccessNoDspAllocFailure                        PerfCurrentCount,
        sonusSysCallDspResCurrentNumCallSuccessWithDspAllocFailure                          PerfCurrentCount,
        sonusSysCallDspResCurrentNumCallFailNoG711Circuit                 PerfCurrentCount,
        sonusSysCallDspResCurrentNumCallFailOtherOnG711Circuit                      PerfCurrentCount,
        sonusSysCallDspResCurrentNumCallSuccessNoG711Circuit                    PerfCurrentCount,
        sonusSysCallDspResCurrentNumCallFailNoTone          PerfCurrentCount,
        sonusSysCallDspResCurrentNumCallFailOtherOnTone               PerfCurrentCount,
        sonusSysCallDspResCurrentNumCallSuccessNoTone             PerfCurrentCount,
        sonusSysCallDspResCurrentNumCallFailNoBridgePort                PerfCurrentCount,
        sonusSysCallDspResCurrentNumCallFailOtherOnBridgePort                     PerfCurrentCount,
        sonusSysCallDspResCurrentNumCallSuccessNoBridgePort                   PerfCurrentCount,
        sonusSysCallDspResCurrentNumCallFailNoG729          PerfCurrentCount,
        sonusSysCallDspResCurrentNumCallFailOtherOnG729               PerfCurrentCount,
        sonusSysCallDspResCurrentNumCallSuccessNoG729             PerfCurrentCount,
        sonusSysCallDspResCurrentNumCallFailNoG726          PerfCurrentCount,
        sonusSysCallDspResCurrentNumCallFailOtherOnG726               PerfCurrentCount,
        sonusSysCallDspResCurrentNumCallSuccessNoG726             PerfCurrentCount,
        sonusSysCallDspResCurrentNumCallFailNoG723          PerfCurrentCount,
        sonusSysCallDspResCurrentNumCallFailOtherOnG723               PerfCurrentCount,
        sonusSysCallDspResCurrentNumCallSuccessNoG723             PerfCurrentCount,
        sonusSysCallDspResCurrentNumCallFailNoG711Packet                PerfCurrentCount,
        sonusSysCallDspResCurrentNumCallFailOtherOnG711Packet                     PerfCurrentCount,
        sonusSysCallDspResCurrentNumCallSuccessNoG711Packet                   PerfCurrentCount,
        sonusSysCallDspResCurrentNumCallFailNoT38         PerfCurrentCount,
        sonusSysCallDspResCurrentNumCallFailOtherOnT38              PerfCurrentCount,
        sonusSysCallDspResCurrentNumCallSuccessNoT38            PerfCurrentCount,
        sonusSysCallDspResCurrentNumCallFailNoEvrc          PerfCurrentCount,
        sonusSysCallDspResCurrentNumCallFailOtherOnEvrc               PerfCurrentCount,
        sonusSysCallDspResCurrentNumCallSuccessNoEvrc             PerfCurrentCount,
        sonusSysCallDspResCurrentNumCallFailNoGsm         PerfCurrentCount,
        sonusSysCallDspResCurrentNumCallFailOtherOnGsm              PerfCurrentCount,
        sonusSysCallDspResCurrentNumCallSuccessNoGsm            PerfCurrentCount,
        sonusSysCallDspResCurrentNumCallFailNoT38Ecm            PerfCurrentCount,
        sonusSysCallDspResCurrentNumCallFailOtherOnT38Ecm                 PerfCurrentCount,
        sonusSysCallDspResCurrentNumCallSuccessNoT38Ecm               PerfCurrentCount,
        sonusSysCallDspResCurrentNumCallFailNoG722          PerfCurrentCount,
        sonusSysCallDspResCurrentNumCallFailOtherOnG722               PerfCurrentCount,
        sonusSysCallDspResCurrentNumCallSuccessNoG722             PerfCurrentCount,
        sonusSysCallDspResCurrentNumCallFailNoAmrwb           PerfCurrentCount,
        sonusSysCallDspResCurrentNumCallFailOtherOnAmrwb                PerfCurrentCount,
        sonusSysCallDspResCurrentNumCallSuccessNoAmrwb              PerfCurrentCount
    }

sonusSysCallDspResCurrentShelfIndex OBJECT-TYPE
    SYNTAX          SonusShelfIndex
    MAX-ACCESS      read-only
    STATUS          current
    DESCRIPTION     
            "The index into the sonusSysCallDspResCurrentTable."
    ::= { sonusSysCallDspResCurrentEntry 1 }

sonusSysCallDspResCurrentNumCallSuccessNoDspAllocFailure OBJECT-TYPE
    SYNTAX          PerfCurrentCount
    MAX-ACCESS      read-only
    STATUS          current
    DESCRIPTION     
            "number of call was successful without DSP resource allocation failure during the current interval time."
    ::= { sonusSysCallDspResCurrentEntry 2 }

sonusSysCallDspResCurrentNumCallSuccessWithDspAllocFailure OBJECT-TYPE
    SYNTAX          PerfCurrentCount
    MAX-ACCESS      read-only
    STATUS          current
    DESCRIPTION     
            "number of call was successful with DSP resource allocation failure during the current interval time."
    ::= { sonusSysCallDspResCurrentEntry 3 }

sonusSysCallDspResCurrentNumCallFailNoG711Circuit OBJECT-TYPE
    SYNTAX          PerfCurrentCount
    MAX-ACCESS      read-only
    STATUS          current
    DESCRIPTION     
            "number of call failed due to lack of G711 Circuit DSP resource during the current interval time."
    ::= { sonusSysCallDspResCurrentEntry 4 }

sonusSysCallDspResCurrentNumCallFailOtherOnG711Circuit OBJECT-TYPE
    SYNTAX          PerfCurrentCount
    MAX-ACCESS      read-only
    STATUS          current
    DESCRIPTION     
            "number of call fails due to reason other than lack G711 Circuit DSP resource during the current interval time."
    ::= { sonusSysCallDspResCurrentEntry 5 }

sonusSysCallDspResCurrentNumCallSuccessNoG711Circuit OBJECT-TYPE
    SYNTAX          PerfCurrentCount
    MAX-ACCESS      read-only
    STATUS          current
    DESCRIPTION     
            "number of call was successful even though lack of G711 Circuit DSP resource during the current interval time."
    ::= { sonusSysCallDspResCurrentEntry 6 }

sonusSysCallDspResCurrentNumCallFailNoTone OBJECT-TYPE
    SYNTAX          PerfCurrentCount
    MAX-ACCESS      read-only
    STATUS          current
    DESCRIPTION     
            "number of call failed due to lack of Tone DSP resource during the current interval time."
    ::= { sonusSysCallDspResCurrentEntry 7 }

sonusSysCallDspResCurrentNumCallFailOtherOnTone OBJECT-TYPE
    SYNTAX          PerfCurrentCount
    MAX-ACCESS      read-only
    STATUS          current
    DESCRIPTION     
            "number of call fails due to reason other than lack Tone DSP resource during the current interval time."
    ::= { sonusSysCallDspResCurrentEntry 8 }

sonusSysCallDspResCurrentNumCallSuccessNoTone OBJECT-TYPE
    SYNTAX          PerfCurrentCount
    MAX-ACCESS      read-only
    STATUS          current
    DESCRIPTION     
            "number of call was successful even though lack of Tone DSP resource during the current interval time."
    ::= { sonusSysCallDspResCurrentEntry 9 }

sonusSysCallDspResCurrentNumCallFailNoBridgePort OBJECT-TYPE
    SYNTAX          PerfCurrentCount
    MAX-ACCESS      read-only
    STATUS          current
    DESCRIPTION     
            "number of call failed due to lack of BridgePort DSP resource during the current interval time."
    ::= { sonusSysCallDspResCurrentEntry 10 }

sonusSysCallDspResCurrentNumCallFailOtherOnBridgePort OBJECT-TYPE
    SYNTAX          PerfCurrentCount
    MAX-ACCESS      read-only
    STATUS          current
    DESCRIPTION     
            "number of call fails due to reason other than lack BridgePort DSP resource during the current interval time."
    ::= { sonusSysCallDspResCurrentEntry 11 }

sonusSysCallDspResCurrentNumCallSuccessNoBridgePort OBJECT-TYPE
    SYNTAX          PerfCurrentCount
    MAX-ACCESS      read-only
    STATUS          current
    DESCRIPTION     
            "number of call was successful even though lack of BridgePort DSP resource during the current interval time."
    ::= { sonusSysCallDspResCurrentEntry 12 }

sonusSysCallDspResCurrentNumCallFailNoG729 OBJECT-TYPE
    SYNTAX          PerfCurrentCount
    MAX-ACCESS      read-only
    STATUS          current
    DESCRIPTION     
            "number of call failed due to lack of G729 DSP resource during the current interval time."
    ::= { sonusSysCallDspResCurrentEntry 13 }

sonusSysCallDspResCurrentNumCallFailOtherOnG729 OBJECT-TYPE
    SYNTAX          PerfCurrentCount
    MAX-ACCESS      read-only
    STATUS          current
    DESCRIPTION     
            "number of call fails due to reason other than lack G729 DSP resource during the current interval time."
    ::= { sonusSysCallDspResCurrentEntry 14 }

sonusSysCallDspResCurrentNumCallSuccessNoG729 OBJECT-TYPE
    SYNTAX          PerfCurrentCount
    MAX-ACCESS      read-only
    STATUS          current
    DESCRIPTION     
            "number of call was successful even though lack of G729 DSP resource during the current interval time."
    ::= { sonusSysCallDspResCurrentEntry 15 }

sonusSysCallDspResCurrentNumCallFailNoG726 OBJECT-TYPE
    SYNTAX          PerfCurrentCount
    MAX-ACCESS      read-only
    STATUS          current
    DESCRIPTION     
            "number of call failed due to lack of G726 DSP resource during the current interval time."
    ::= { sonusSysCallDspResCurrentEntry 16 }

sonusSysCallDspResCurrentNumCallFailOtherOnG726 OBJECT-TYPE
    SYNTAX          PerfCurrentCount
    MAX-ACCESS      read-only
    STATUS          current
    DESCRIPTION     
            "number of call fails due to reason other than lack G726 DSP resource during the current interval time."
    ::= { sonusSysCallDspResCurrentEntry 17 }

sonusSysCallDspResCurrentNumCallSuccessNoG726 OBJECT-TYPE
    SYNTAX          PerfCurrentCount
    MAX-ACCESS      read-only
    STATUS          current
    DESCRIPTION     
            "number of call was successful even though lack of G726 DSP resource during the current interval time."
    ::= { sonusSysCallDspResCurrentEntry 18 }

sonusSysCallDspResCurrentNumCallFailNoG723 OBJECT-TYPE
    SYNTAX          PerfCurrentCount
    MAX-ACCESS      read-only
    STATUS          current
    DESCRIPTION     
            "number of call failed due to lack of G723 DSP resource during the current interval time."
    ::= { sonusSysCallDspResCurrentEntry 19 }

sonusSysCallDspResCurrentNumCallFailOtherOnG723 OBJECT-TYPE
    SYNTAX          PerfCurrentCount
    MAX-ACCESS      read-only
    STATUS          current
    DESCRIPTION     
            "number of call fails due to reason other than lack G723 DSP resource during the current interval time."
    ::= { sonusSysCallDspResCurrentEntry 20 }

sonusSysCallDspResCurrentNumCallSuccessNoG723 OBJECT-TYPE
    SYNTAX          PerfCurrentCount
    MAX-ACCESS      read-only
    STATUS          current
    DESCRIPTION     
            "number of call was successful even though lack of G723 DSP resource during the current interval time."
    ::= { sonusSysCallDspResCurrentEntry 21 }

sonusSysCallDspResCurrentNumCallFailNoG711Packet OBJECT-TYPE
    SYNTAX          PerfCurrentCount
    MAX-ACCESS      read-only
    STATUS          current
    DESCRIPTION     
            "number of call failed due to lack of G711 Packet DSP resource during the current interval time."
    ::= { sonusSysCallDspResCurrentEntry 22 }

sonusSysCallDspResCurrentNumCallFailOtherOnG711Packet OBJECT-TYPE
    SYNTAX          PerfCurrentCount
    MAX-ACCESS      read-only
    STATUS          current
    DESCRIPTION     
            "number of call fails due to reason other than lack G711 Packet DSP resource during the current interval time."
    ::= { sonusSysCallDspResCurrentEntry 23 }

sonusSysCallDspResCurrentNumCallSuccessNoG711Packet OBJECT-TYPE
    SYNTAX          PerfCurrentCount
    MAX-ACCESS      read-only
    STATUS          current
    DESCRIPTION     
            "number of call was successful even though lack of G711 Packet DSP resource during the current interval time."
    ::= { sonusSysCallDspResCurrentEntry 24 }

sonusSysCallDspResCurrentNumCallFailNoT38 OBJECT-TYPE
    SYNTAX          PerfCurrentCount
    MAX-ACCESS      read-only
    STATUS          current
    DESCRIPTION     
            "number of call failed due to lack of T38 DSP resource during the current interval time."
    ::= { sonusSysCallDspResCurrentEntry 25 }

sonusSysCallDspResCurrentNumCallFailOtherOnT38 OBJECT-TYPE
    SYNTAX          PerfCurrentCount
    MAX-ACCESS      read-only
    STATUS          current
    DESCRIPTION     
            "number of call fails due to reason other than lack T38 DSP resource during the current interval time."
    ::= { sonusSysCallDspResCurrentEntry 26 }

sonusSysCallDspResCurrentNumCallSuccessNoT38 OBJECT-TYPE
    SYNTAX          PerfCurrentCount
    MAX-ACCESS      read-only
    STATUS          current
    DESCRIPTION     
            "number of call was successful even though lack of T38 DSP resource during the current interval time."
    ::= { sonusSysCallDspResCurrentEntry 27 }

sonusSysCallDspResCurrentNumCallFailNoEvrc OBJECT-TYPE
    SYNTAX          PerfCurrentCount
    MAX-ACCESS      read-only
    STATUS          current
    DESCRIPTION     
            "number of call failed due to lack of EVRC DSP resource during the current interval time."
    ::= { sonusSysCallDspResCurrentEntry 28 }

sonusSysCallDspResCurrentNumCallFailOtherOnEvrc OBJECT-TYPE
    SYNTAX          PerfCurrentCount
    MAX-ACCESS      read-only
    STATUS          current
    DESCRIPTION     
            "number of call fails due to reason other than lack EVRC DSP resource during the current interval time."
    ::= { sonusSysCallDspResCurrentEntry 29 }

sonusSysCallDspResCurrentNumCallSuccessNoEvrc OBJECT-TYPE
    SYNTAX          PerfCurrentCount
    MAX-ACCESS      read-only
    STATUS          current
    DESCRIPTION     
            "number of call was successful even though lack of EVRC DSP resource during the current interval time."
    ::= { sonusSysCallDspResCurrentEntry 30 }

sonusSysCallDspResCurrentNumCallFailNoGsm OBJECT-TYPE
    SYNTAX          PerfCurrentCount
    MAX-ACCESS      read-only
    STATUS          current
    DESCRIPTION     
            "number of call failed due to lack of GSM DSP resource during the current interval time."
    ::= { sonusSysCallDspResCurrentEntry 31 }

sonusSysCallDspResCurrentNumCallFailOtherOnGsm OBJECT-TYPE
    SYNTAX          PerfCurrentCount
    MAX-ACCESS      read-only
    STATUS          current
    DESCRIPTION     
            "number of call fails due to reason other than lack GSM DSP resource during the current interval time."
    ::= { sonusSysCallDspResCurrentEntry 32 }

sonusSysCallDspResCurrentNumCallSuccessNoGsm OBJECT-TYPE
    SYNTAX          PerfCurrentCount
    MAX-ACCESS      read-only
    STATUS          current
    DESCRIPTION     
            "number of call was successful even though lack of GSM DSP resource during the current interval time."
    ::= { sonusSysCallDspResCurrentEntry 33 }

sonusSysCallDspResCurrentNumCallFailNoT38Ecm OBJECT-TYPE
    SYNTAX          PerfCurrentCount
    MAX-ACCESS      read-only
    STATUS          current
    DESCRIPTION     
            "number of call failed due to lack of T38 ECM capable DSP resource during the current interval time."
    ::= { sonusSysCallDspResCurrentEntry 34 }

sonusSysCallDspResCurrentNumCallFailOtherOnT38Ecm OBJECT-TYPE
    SYNTAX          PerfCurrentCount
    MAX-ACCESS      read-only
    STATUS          current
    DESCRIPTION     
            "number of call fails due to reason other than lack T38
             ECM capable DSP resource during the current interval time."
    ::= { sonusSysCallDspResCurrentEntry 35 }

sonusSysCallDspResCurrentNumCallSuccessNoT38Ecm OBJECT-TYPE
    SYNTAX          PerfCurrentCount
    MAX-ACCESS      read-only
    STATUS          current
    DESCRIPTION     
            "number of call was successful even though lack of T38 ECM
             capable DSP resource during the current interval time."
    ::= { sonusSysCallDspResCurrentEntry 36 }

sonusSysCallDspResCurrentNumCallFailNoG722 OBJECT-TYPE
    SYNTAX          PerfCurrentCount
    MAX-ACCESS      read-only
    STATUS          current
    DESCRIPTION     
            "number of call failed due to lack of G722 DSP resource during the current interval time."
    ::= { sonusSysCallDspResCurrentEntry 37 }

sonusSysCallDspResCurrentNumCallFailOtherOnG722 OBJECT-TYPE
    SYNTAX          PerfCurrentCount
    MAX-ACCESS      read-only
    STATUS          current
    DESCRIPTION     
            "number of call fails due to reason other than lack G722 DSP resource during the current interval time."
    ::= { sonusSysCallDspResCurrentEntry 38 }

sonusSysCallDspResCurrentNumCallSuccessNoG722 OBJECT-TYPE
    SYNTAX          PerfCurrentCount
    MAX-ACCESS      read-only
    STATUS          current
    DESCRIPTION     
            "number of call was successful even though lack of G722 DSP resource during the current interval time."
    ::= { sonusSysCallDspResCurrentEntry 39 }

sonusSysCallDspResCurrentNumCallFailNoAmrwb OBJECT-TYPE
    SYNTAX          PerfCurrentCount
    MAX-ACCESS      read-only
    STATUS          current
    DESCRIPTION     
            "number of call failed due to lack of AMRWB DSP resource during the current interval time."
    ::= { sonusSysCallDspResCurrentEntry 40 }

sonusSysCallDspResCurrentNumCallFailOtherOnAmrwb OBJECT-TYPE
    SYNTAX          PerfCurrentCount
    MAX-ACCESS      read-only
    STATUS          current
    DESCRIPTION     
            "number of call fails due to reason other than lack AMRWB DSP resource during the current interval time."
    ::= { sonusSysCallDspResCurrentEntry 41 }

sonusSysCallDspResCurrentNumCallSuccessNoAmrwb OBJECT-TYPE
    SYNTAX          PerfCurrentCount
    MAX-ACCESS      read-only
    STATUS          current
    DESCRIPTION     
            "number of call was successful even though lack of AMRWB DSP resource during the current interval time."
    ::= { sonusSysCallDspResCurrentEntry 42 }

sonusSysCallDspResIntervalTable OBJECT-TYPE
    SYNTAX          SEQUENCE OF SonusSysCallDspResIntervalEntry
    MAX-ACCESS      not-accessible
    STATUS          current
    DESCRIPTION     
            "The Sonus System Call DSP Resource Interval table."
    ::= { sonusDspPadResStatisticsObjects 2 }

sonusSysCallDspResIntervalEntry OBJECT-TYPE
    SYNTAX          SonusSysCallDspResIntervalEntry
    MAX-ACCESS      not-accessible
    STATUS          current
    DESCRIPTION     
            "An entry in the Sonus System Call DSP Resource Interval table."
    INDEX           { sonusSysCallDspResIntervalShelfIndex, 
                      sonusSysCallDspResIntervalNumber }
    ::= { sonusSysCallDspResIntervalTable 1 }

SonusSysCallDspResIntervalEntry ::=
    SEQUENCE {
        sonusSysCallDspResIntervalShelfIndex    SonusShelfIndex,
        sonusSysCallDspResIntervalNumber Integer32,
        sonusSysCallDspResIntervalTime  TimeTicks,
        sonusSysCallDspResIntervalValidData   TruthValue,
        sonusSysCallDspResIntervalNumCallSuccessNoDspAllocFailure                         PerfIntervalCount,
        sonusSysCallDspResIntervalNumCallSuccessWithDspAllocFailure                           PerfIntervalCount,
        sonusSysCallDspResIntervalNumCallFailNoG711Circuit                  PerfIntervalCount,
        sonusSysCallDspResIntervalNumCallFailOtherOnG711Circuit                       PerfIntervalCount,
        sonusSysCallDspResIntervalNumCallSuccessNoG711Circuit                     PerfIntervalCount,
        sonusSysCallDspResIntervalNumCallFailNoTone           PerfIntervalCount,
        sonusSysCallDspResIntervalNumCallFailOtherOnTone                PerfIntervalCount,
        sonusSysCallDspResIntervalNumCallSuccessNoTone              PerfIntervalCount,
        sonusSysCallDspResIntervalNumCallFailNoBridgePort                 PerfIntervalCount,
        sonusSysCallDspResIntervalNumCallFailOtherOnBridgePort                      PerfIntervalCount,
        sonusSysCallDspResIntervalNumCallSuccessNoBridgePort                    PerfIntervalCount,
        sonusSysCallDspResIntervalNumCallFailNoG729           PerfIntervalCount,
        sonusSysCallDspResIntervalNumCallFailOtherOnG729                PerfIntervalCount,
        sonusSysCallDspResIntervalNumCallSuccessNoG729              PerfIntervalCount,
        sonusSysCallDspResIntervalNumCallFailNoG726           PerfIntervalCount,
        sonusSysCallDspResIntervalNumCallFailOtherOnG726                PerfIntervalCount,
        sonusSysCallDspResIntervalNumCallSuccessNoG726              PerfIntervalCount,
        sonusSysCallDspResIntervalNumCallFailNoG723           PerfIntervalCount,
        sonusSysCallDspResIntervalNumCallFailOtherOnG723                PerfIntervalCount,
        sonusSysCallDspResIntervalNumCallSuccessNoG723              PerfIntervalCount,
        sonusSysCallDspResIntervalNumCallFailNoG711Packet                 PerfIntervalCount,
        sonusSysCallDspResIntervalNumCallFailOtherOnG711Packet                      PerfIntervalCount,
        sonusSysCallDspResIntervalNumCallSuccessNoG711Packet                    PerfIntervalCount,
        sonusSysCallDspResIntervalNumCallFailNoT38          PerfIntervalCount,
        sonusSysCallDspResIntervalNumCallFailOtherOnT38               PerfIntervalCount,
        sonusSysCallDspResIntervalNumCallSuccessNoT38             PerfIntervalCount,
        sonusSysCallDspResIntervalNumCallFailNoEvrc           PerfIntervalCount,
        sonusSysCallDspResIntervalNumCallFailOtherOnEvrc                PerfIntervalCount,
        sonusSysCallDspResIntervalNumCallSuccessNoEvrc              PerfIntervalCount,
        sonusSysCallDspResIntervalNumCallFailNoGsm          PerfIntervalCount,
        sonusSysCallDspResIntervalNumCallFailOtherOnGsm               PerfIntervalCount,
        sonusSysCallDspResIntervalNumCallSuccessNoGsm             PerfIntervalCount,
        sonusSysCallDspResIntervalNumCallFailNoT38Ecm             PerfIntervalCount,
        sonusSysCallDspResIntervalNumCallFailOtherOnT38Ecm                  PerfIntervalCount,
        sonusSysCallDspResIntervalNumCallSuccessNoT38Ecm                PerfIntervalCount,
        sonusSysCallDspResIntervalNumCallFailNoG722           PerfIntervalCount,
        sonusSysCallDspResIntervalNumCallFailOtherOnG722                PerfIntervalCount,
        sonusSysCallDspResIntervalNumCallSuccessNoG722              PerfIntervalCount,
        sonusSysCallDspResIntervalNumCallFailNoAmrwb            PerfIntervalCount,
        sonusSysCallDspResIntervalNumCallFailOtherOnAmrwb                 PerfIntervalCount,
        sonusSysCallDspResIntervalNumCallSuccessNoAmrwb               PerfIntervalCount
    }

sonusSysCallDspResIntervalShelfIndex OBJECT-TYPE
    SYNTAX          SonusShelfIndex
    MAX-ACCESS      read-only
    STATUS          current
    DESCRIPTION     
            "The index into the sonusSysCallDspResIntervalTable."
    ::= { sonusSysCallDspResIntervalEntry 1 }

sonusSysCallDspResIntervalNumber OBJECT-TYPE
    SYNTAX          Integer32 (1..288)
    MAX-ACCESS      not-accessible
    STATUS          current
    DESCRIPTION     
            "A number between 1 and 288, which identifies the
             interval for which the set of statistics is available.
             The interval identified by 1 is the most recently
             completed interval, and the interval identified
             by N is the interval immediately preceding the
             one identified by N-1."
    ::= { sonusSysCallDspResIntervalEntry 2 }

sonusSysCallDspResIntervalTime OBJECT-TYPE
    SYNTAX          TimeTicks
    MAX-ACCESS      read-only
    STATUS          current
    DESCRIPTION     
            "This variable contains the end of interval time
             stamp for the specified interval."
    ::= { sonusSysCallDspResIntervalEntry 3 }

sonusSysCallDspResIntervalValidData OBJECT-TYPE
    SYNTAX          TruthValue
    MAX-ACCESS      read-only
    STATUS          current
    DESCRIPTION     
            "This variable indicates if the data for this
             interval is valid."
    ::= { sonusSysCallDspResIntervalEntry 4 }

sonusSysCallDspResIntervalNumCallSuccessNoDspAllocFailure OBJECT-TYPE
    SYNTAX          PerfIntervalCount
    MAX-ACCESS      read-only
    STATUS          current
    DESCRIPTION     
            "number of call was successful without DSP resource allocation failure during a interval time."
    ::= { sonusSysCallDspResIntervalEntry 5 }

sonusSysCallDspResIntervalNumCallSuccessWithDspAllocFailure OBJECT-TYPE
    SYNTAX          PerfIntervalCount
    MAX-ACCESS      read-only
    STATUS          current
    DESCRIPTION     
            "number of call was successful with DSP resource allocation failure during a interval time."
    ::= { sonusSysCallDspResIntervalEntry 6 }

sonusSysCallDspResIntervalNumCallFailNoG711Circuit OBJECT-TYPE
    SYNTAX          PerfIntervalCount
    MAX-ACCESS      read-only
    STATUS          current
    DESCRIPTION     
            "number of call failed due to lack of G711 Circuit DSP resource during a interval time."
    ::= { sonusSysCallDspResIntervalEntry 7 }

sonusSysCallDspResIntervalNumCallFailOtherOnG711Circuit OBJECT-TYPE
    SYNTAX          PerfIntervalCount
    MAX-ACCESS      read-only
    STATUS          current
    DESCRIPTION     
            "number of call fails due to reason other than lack G711 Circuit DSP resource during a interval time."
    ::= { sonusSysCallDspResIntervalEntry 8 }

sonusSysCallDspResIntervalNumCallSuccessNoG711Circuit OBJECT-TYPE
    SYNTAX          PerfIntervalCount
    MAX-ACCESS      read-only
    STATUS          current
    DESCRIPTION     
            "number of call was successful even though lack of G711 Circuit DSP resource during a interval time."
    ::= { sonusSysCallDspResIntervalEntry 9 }

sonusSysCallDspResIntervalNumCallFailNoTone OBJECT-TYPE
    SYNTAX          PerfIntervalCount
    MAX-ACCESS      read-only
    STATUS          current
    DESCRIPTION     
            "number of call failed due to lack of Tone DSP resource during a interval time."
    ::= { sonusSysCallDspResIntervalEntry 10 }

sonusSysCallDspResIntervalNumCallFailOtherOnTone OBJECT-TYPE
    SYNTAX          PerfIntervalCount
    MAX-ACCESS      read-only
    STATUS          current
    DESCRIPTION     
            "number of call fails due to reason other than lack Tone DSP resource during a interval time."
    ::= { sonusSysCallDspResIntervalEntry 11 }

sonusSysCallDspResIntervalNumCallSuccessNoTone OBJECT-TYPE
    SYNTAX          PerfIntervalCount
    MAX-ACCESS      read-only
    STATUS          current
    DESCRIPTION     
            "number of call was successful even though lack of Tone DSP resource during a interval time."
    ::= { sonusSysCallDspResIntervalEntry 12 }

sonusSysCallDspResIntervalNumCallFailNoBridgePort OBJECT-TYPE
    SYNTAX          PerfIntervalCount
    MAX-ACCESS      read-only
    STATUS          current
    DESCRIPTION     
            "number of call failed due to lack of BridgePort DSP resource during a interval time."
    ::= { sonusSysCallDspResIntervalEntry 13 }

sonusSysCallDspResIntervalNumCallFailOtherOnBridgePort OBJECT-TYPE
    SYNTAX          PerfIntervalCount
    MAX-ACCESS      read-only
    STATUS          current
    DESCRIPTION     
            "number of call fails due to reason other than lack BridgePort DSP resource during a interval time."
    ::= { sonusSysCallDspResIntervalEntry 14 }

sonusSysCallDspResIntervalNumCallSuccessNoBridgePort OBJECT-TYPE
    SYNTAX          PerfIntervalCount
    MAX-ACCESS      read-only
    STATUS          current
    DESCRIPTION     
            "number of call was successful even though lack of BridgePort DSP resource during a interval time."
    ::= { sonusSysCallDspResIntervalEntry 15 }

sonusSysCallDspResIntervalNumCallFailNoG729 OBJECT-TYPE
    SYNTAX          PerfIntervalCount
    MAX-ACCESS      read-only
    STATUS          current
    DESCRIPTION     
            "number of call failed due to lack of G729 DSP resource during a interval time."
    ::= { sonusSysCallDspResIntervalEntry 16 }

sonusSysCallDspResIntervalNumCallFailOtherOnG729 OBJECT-TYPE
    SYNTAX          PerfIntervalCount
    MAX-ACCESS      read-only
    STATUS          current
    DESCRIPTION     
            "number of call fails due to reason other than lack G729 DSP resource during a interval time."
    ::= { sonusSysCallDspResIntervalEntry 17 }

sonusSysCallDspResIntervalNumCallSuccessNoG729 OBJECT-TYPE
    SYNTAX          PerfIntervalCount
    MAX-ACCESS      read-only
    STATUS          current
    DESCRIPTION     
            "number of call was successful even though lack of G729 DSP resource during a interval time."
    ::= { sonusSysCallDspResIntervalEntry 18 }

sonusSysCallDspResIntervalNumCallFailNoG726 OBJECT-TYPE
    SYNTAX          PerfIntervalCount
    MAX-ACCESS      read-only
    STATUS          current
    DESCRIPTION     
            "number of call failed due to lack of G726 DSP resource during a interval time."
    ::= { sonusSysCallDspResIntervalEntry 19 }

sonusSysCallDspResIntervalNumCallFailOtherOnG726 OBJECT-TYPE
    SYNTAX          PerfIntervalCount
    MAX-ACCESS      read-only
    STATUS          current
    DESCRIPTION     
            "number of call fails due to reason other than lack G726 DSP resource during a interval time."
    ::= { sonusSysCallDspResIntervalEntry 20 }

sonusSysCallDspResIntervalNumCallSuccessNoG726 OBJECT-TYPE
    SYNTAX          PerfIntervalCount
    MAX-ACCESS      read-only
    STATUS          current
    DESCRIPTION     
            "number of call was successful even though lack of G726 DSP resource during a interval time."
    ::= { sonusSysCallDspResIntervalEntry 21 }

sonusSysCallDspResIntervalNumCallFailNoG723 OBJECT-TYPE
    SYNTAX          PerfIntervalCount
    MAX-ACCESS      read-only
    STATUS          current
    DESCRIPTION     
            "number of call failed due to lack of G723 DSP resource during a interval time."
    ::= { sonusSysCallDspResIntervalEntry 22 }

sonusSysCallDspResIntervalNumCallFailOtherOnG723 OBJECT-TYPE
    SYNTAX          PerfIntervalCount
    MAX-ACCESS      read-only
    STATUS          current
    DESCRIPTION     
            "number of call fails due to reason other than lack G723 DSP resource during a interval time."
    ::= { sonusSysCallDspResIntervalEntry 23 }

sonusSysCallDspResIntervalNumCallSuccessNoG723 OBJECT-TYPE
    SYNTAX          PerfIntervalCount
    MAX-ACCESS      read-only
    STATUS          current
    DESCRIPTION     
            "number of call was successful even though lack of G723 DSP resource during a interval time."
    ::= { sonusSysCallDspResIntervalEntry 24 }

sonusSysCallDspResIntervalNumCallFailNoG711Packet OBJECT-TYPE
    SYNTAX          PerfIntervalCount
    MAX-ACCESS      read-only
    STATUS          current
    DESCRIPTION     
            "number of call failed due to lack of G711 Packet DSP resource during a interval time."
    ::= { sonusSysCallDspResIntervalEntry 25 }

sonusSysCallDspResIntervalNumCallFailOtherOnG711Packet OBJECT-TYPE
    SYNTAX          PerfIntervalCount
    MAX-ACCESS      read-only
    STATUS          current
    DESCRIPTION     
            "number of call fails due to reason other than lack G711 Packet DSP resource during a interval time."
    ::= { sonusSysCallDspResIntervalEntry 26 }

sonusSysCallDspResIntervalNumCallSuccessNoG711Packet OBJECT-TYPE
    SYNTAX          PerfIntervalCount
    MAX-ACCESS      read-only
    STATUS          current
    DESCRIPTION     
            "number of call was successful even though lack of G711 Packet DSP resource during a interval time."
    ::= { sonusSysCallDspResIntervalEntry 27 }

sonusSysCallDspResIntervalNumCallFailNoT38 OBJECT-TYPE
    SYNTAX          PerfIntervalCount
    MAX-ACCESS      read-only
    STATUS          current
    DESCRIPTION     
            "number of call failed due to lack of T38 DSP resource during a interval time."
    ::= { sonusSysCallDspResIntervalEntry 28 }

sonusSysCallDspResIntervalNumCallFailOtherOnT38 OBJECT-TYPE
    SYNTAX          PerfIntervalCount
    MAX-ACCESS      read-only
    STATUS          current
    DESCRIPTION     
            "number of call fails due to reason other than lack T38 DSP resource during a interval time."
    ::= { sonusSysCallDspResIntervalEntry 29 }

sonusSysCallDspResIntervalNumCallSuccessNoT38 OBJECT-TYPE
    SYNTAX          PerfIntervalCount
    MAX-ACCESS      read-only
    STATUS          current
    DESCRIPTION     
            "number of call was successful even though lack of T38 DSP resource during a interval time."
    ::= { sonusSysCallDspResIntervalEntry 30 }

sonusSysCallDspResIntervalNumCallFailNoEvrc OBJECT-TYPE
    SYNTAX          PerfIntervalCount
    MAX-ACCESS      read-only
    STATUS          current
    DESCRIPTION     
            "number of call failed due to lack of EVRC DSP resource during a interval time."
    ::= { sonusSysCallDspResIntervalEntry 31 }

sonusSysCallDspResIntervalNumCallFailOtherOnEvrc OBJECT-TYPE
    SYNTAX          PerfIntervalCount
    MAX-ACCESS      read-only
    STATUS          current
    DESCRIPTION     
            "number of call fails due to reason other than lack EVRC DSP resource during a interval time."
    ::= { sonusSysCallDspResIntervalEntry 32 }

sonusSysCallDspResIntervalNumCallSuccessNoEvrc OBJECT-TYPE
    SYNTAX          PerfIntervalCount
    MAX-ACCESS      read-only
    STATUS          current
    DESCRIPTION     
            "number of call was successful even though lack of EVRC DSP resource during a interval time."
    ::= { sonusSysCallDspResIntervalEntry 33 }

sonusSysCallDspResIntervalNumCallFailNoGsm OBJECT-TYPE
    SYNTAX          PerfIntervalCount
    MAX-ACCESS      read-only
    STATUS          current
    DESCRIPTION     
            "number of call failed due to lack of GSM DSP resource during a interval time."
    ::= { sonusSysCallDspResIntervalEntry 34 }

sonusSysCallDspResIntervalNumCallFailOtherOnGsm OBJECT-TYPE
    SYNTAX          PerfIntervalCount
    MAX-ACCESS      read-only
    STATUS          current
    DESCRIPTION     
            "number of call fails due to reason other than lack GSM DSP resource during a interval time."
    ::= { sonusSysCallDspResIntervalEntry 35 }

sonusSysCallDspResIntervalNumCallSuccessNoGsm OBJECT-TYPE
    SYNTAX          PerfIntervalCount
    MAX-ACCESS      read-only
    STATUS          current
    DESCRIPTION     
            "number of call was successful even though lack of GSM DSP resource during a interval time."
    ::= { sonusSysCallDspResIntervalEntry 36 }

sonusSysCallDspResIntervalNumCallFailNoT38Ecm OBJECT-TYPE
    SYNTAX          PerfIntervalCount
    MAX-ACCESS      read-only
    STATUS          current
    DESCRIPTION     
            "number of call failed due to lack of T38 ECM capable DSP resource during a interval time."
    ::= { sonusSysCallDspResIntervalEntry 37 }

sonusSysCallDspResIntervalNumCallFailOtherOnT38Ecm OBJECT-TYPE
    SYNTAX          PerfIntervalCount
    MAX-ACCESS      read-only
    STATUS          current
    DESCRIPTION     
            "number of call fails due to reason other than lack T38
             ECM capable DSP resource during a interval time."
    ::= { sonusSysCallDspResIntervalEntry 38 }

sonusSysCallDspResIntervalNumCallSuccessNoT38Ecm OBJECT-TYPE
    SYNTAX          PerfIntervalCount
    MAX-ACCESS      read-only
    STATUS          current
    DESCRIPTION     
            "number of call was successful even though lack of T38 ECM
             capable DSP resource during a interval time."
    ::= { sonusSysCallDspResIntervalEntry 39 }

sonusSysCallDspResIntervalNumCallFailNoG722 OBJECT-TYPE
    SYNTAX          PerfIntervalCount
    MAX-ACCESS      read-only
    STATUS          current
    DESCRIPTION     
            "number of call failed due to lack of G722 DSP resource during a interval time."
    ::= { sonusSysCallDspResIntervalEntry 40 }

sonusSysCallDspResIntervalNumCallFailOtherOnG722 OBJECT-TYPE
    SYNTAX          PerfIntervalCount
    MAX-ACCESS      read-only
    STATUS          current
    DESCRIPTION     
            "number of call fails due to reason other than lack G722 DSP resource during a interval time."
    ::= { sonusSysCallDspResIntervalEntry 41 }

sonusSysCallDspResIntervalNumCallSuccessNoG722 OBJECT-TYPE
    SYNTAX          PerfIntervalCount
    MAX-ACCESS      read-only
    STATUS          current
    DESCRIPTION     
            "number of call was successful even though lack of G722 DSP resource during a interval time."
    ::= { sonusSysCallDspResIntervalEntry 42 }

sonusSysCallDspResIntervalNumCallFailNoAmrwb OBJECT-TYPE
    SYNTAX          PerfIntervalCount
    MAX-ACCESS      read-only
    STATUS          current
    DESCRIPTION     
            "number of call failed due to lack of AMRWB DSP resource during a interval time."
    ::= { sonusSysCallDspResIntervalEntry 43 }

sonusSysCallDspResIntervalNumCallFailOtherOnAmrwb OBJECT-TYPE
    SYNTAX          PerfIntervalCount
    MAX-ACCESS      read-only
    STATUS          current
    DESCRIPTION     
            "number of call fails due to reason other than lack AMRWB DSP resource during a interval time."
    ::= { sonusSysCallDspResIntervalEntry 44 }

sonusSysCallDspResIntervalNumCallSuccessNoAmrwb OBJECT-TYPE
    SYNTAX          PerfIntervalCount
    MAX-ACCESS      read-only
    STATUS          current
    DESCRIPTION     
            "number of call was successful even though lack of AMRWB DSP resource during a interval time."
    ::= { sonusSysCallDspResIntervalEntry 45 }

sonusSysDspResCurrentTable OBJECT-TYPE
    SYNTAX          SEQUENCE OF SonusSysDspResCurrentEntry
    MAX-ACCESS      not-accessible
    STATUS          current
    DESCRIPTION     
            "The Sonus DSP Resource Current table."
    ::= { sonusDspPadResStatisticsObjects 3 }

sonusSysDspResCurrentEntry OBJECT-TYPE
    SYNTAX          SonusSysDspResCurrentEntry
    MAX-ACCESS      not-accessible
    STATUS          current
    DESCRIPTION     
            "An entry in the Sonus DSP Resource Current table."
    INDEX           { sonusSysDspResCurrentShelfIndex }
    ::= { sonusSysDspResCurrentTable 1 }

SonusSysDspResCurrentEntry ::=
    SEQUENCE {
        sonusSysDspResCurrentShelfIndex SonusShelfIndex,
        sonusSysDspResCurrentG711CircuitPeakUsedCount             PerfCurrentCount,
        sonusSysDspResCurrentG711CircuitAverageUsedCount                PerfCurrentCount,
        sonusSysDspResCurrentG711CircuitAverageAvailCount                 PerfCurrentCount,
        sonusSysDspResCurrentTonePeakUsedCount      PerfCurrentCount,
        sonusSysDspResCurrentToneAverageUsedCount         PerfCurrentCount,
        sonusSysDspResCurrentToneAverageAvailCount          PerfCurrentCount,
        sonusSysDspResCurrentBridgePortPeakUsedCount            PerfCurrentCount,
        sonusSysDspResCurrentBridgePortAverageUsedCount               PerfCurrentCount,
        sonusSysDspResCurrentBridgePortAverageAvailCount                PerfCurrentCount,
        sonusSysDspResCurrentG729PeakUsedCount      PerfCurrentCount,
        sonusSysDspResCurrentG729AverageUsedCount         PerfCurrentCount,
        sonusSysDspResCurrentG729AverageAvailCount          PerfCurrentCount,
        sonusSysDspResCurrentG726PeakUsedCount      PerfCurrentCount,
        sonusSysDspResCurrentG726AverageUsedCount         PerfCurrentCount,
        sonusSysDspResCurrentG726AverageAvailCount          PerfCurrentCount,
        sonusSysDspResCurrentG723PeakUsedCount      PerfCurrentCount,
        sonusSysDspResCurrentG723AverageUsedCount         PerfCurrentCount,
        sonusSysDspResCurrentG723AverageAvailCount          PerfCurrentCount,
        sonusSysDspResCurrentG711PacketPeakUsedCount            PerfCurrentCount,
        sonusSysDspResCurrentG711PacketAverageUsedCount               PerfCurrentCount,
        sonusSysDspResCurrentG711PacketAverageAvailCount                PerfCurrentCount,
        sonusSysDspResCurrentT38PeakUsedCount     PerfCurrentCount,
        sonusSysDspResCurrentT38AverageUsedCount        PerfCurrentCount,
        sonusSysDspResCurrentT38AverageAvailCount         PerfCurrentCount,
        sonusSysDspResCurrentEvrcPeakUsedCount      PerfCurrentCount,
        sonusSysDspResCurrentEvrcAverageUsedCount         PerfCurrentCount,
        sonusSysDspResCurrentEvrcAverageAvailCount          PerfCurrentCount,
        sonusSysDspResCurrentGsmPeakUsedCount     PerfCurrentCount,
        sonusSysDspResCurrentGsmAverageUsedCount        PerfCurrentCount,
        sonusSysDspResCurrentGsmAverageAvailCount         PerfCurrentCount,
        sonusSysDspResCurrentT38EcmPeakUsedCount        PerfCurrentCount,
        sonusSysDspResCurrentT38EcmAverageUsedCount           PerfCurrentCount,
        sonusSysDspResCurrentT38EcmAverageAvailCount            PerfCurrentCount,
        sonusSysDspResCurrentEvrcb0PeakUsedCount        PerfCurrentCount,
        sonusSysDspResCurrentEvrcb0AverageUsedCount           PerfCurrentCount,
        sonusSysDspResCurrentEvrcb0AverageAvailCount            PerfCurrentCount,
        sonusSysDspResCurrentiLBCPeakUsedCount      PerfCurrentCount,
        sonusSysDspResCurrentiLBCAverageUsedCount         PerfCurrentCount,
        sonusSysDspResCurrentiLBCAverageAvailCount          PerfCurrentCount,
        sonusSysDspResCurrentG722PeakUsedCount      PerfCurrentCount,
        sonusSysDspResCurrentG722AverageUsedCount         PerfCurrentCount,
        sonusSysDspResCurrentG722AverageAvailCount          PerfCurrentCount,
        sonusSysDspResCurrentAmrwbPeakUsedCount       PerfCurrentCount,
        sonusSysDspResCurrentAmrwbAverageUsedCount          PerfCurrentCount,
        sonusSysDspResCurrentAmrwbAverageAvailCount           PerfCurrentCount
    }

sonusSysDspResCurrentShelfIndex OBJECT-TYPE
    SYNTAX          SonusShelfIndex
    MAX-ACCESS      read-only
    STATUS          current
    DESCRIPTION     
            "The index into the sonusSysDspResCurrentTable."
    ::= { sonusSysDspResCurrentEntry 1 }

sonusSysDspResCurrentG711CircuitPeakUsedCount OBJECT-TYPE
    SYNTAX          PerfCurrentCount
    MAX-ACCESS      read-only
    STATUS          current
    DESCRIPTION     
            "The current  Peak usage of type G711Circuit DSP PAD."
    ::= { sonusSysDspResCurrentEntry 2 }

sonusSysDspResCurrentG711CircuitAverageUsedCount OBJECT-TYPE
    SYNTAX          PerfCurrentCount
    MAX-ACCESS      read-only
    STATUS          current
    DESCRIPTION     
            "The current average usage of type G711Circuit DSP PAD."
    ::= { sonusSysDspResCurrentEntry 3 }

sonusSysDspResCurrentG711CircuitAverageAvailCount OBJECT-TYPE
    SYNTAX          PerfCurrentCount
    MAX-ACCESS      read-only
    STATUS          current
    DESCRIPTION     
            "The current average availability of type G711Circuit DSP PAD."
    ::= { sonusSysDspResCurrentEntry 4 }

sonusSysDspResCurrentTonePeakUsedCount OBJECT-TYPE
    SYNTAX          PerfCurrentCount
    MAX-ACCESS      read-only
    STATUS          current
    DESCRIPTION     
            "The current  Peak usage of type Tone DSP PAD."
    ::= { sonusSysDspResCurrentEntry 5 }

sonusSysDspResCurrentToneAverageUsedCount OBJECT-TYPE
    SYNTAX          PerfCurrentCount
    MAX-ACCESS      read-only
    STATUS          current
    DESCRIPTION     
            "The current average usage of type Tone DSP PAD."
    ::= { sonusSysDspResCurrentEntry 6 }

sonusSysDspResCurrentToneAverageAvailCount OBJECT-TYPE
    SYNTAX          PerfCurrentCount
    MAX-ACCESS      read-only
    STATUS          current
    DESCRIPTION     
            "The current average availability of type Tone DSP PAD."
    ::= { sonusSysDspResCurrentEntry 7 }

sonusSysDspResCurrentBridgePortPeakUsedCount OBJECT-TYPE
    SYNTAX          PerfCurrentCount
    MAX-ACCESS      read-only
    STATUS          current
    DESCRIPTION     
            "The current  peak usage of type Bridge  Port DSP PAD."
    ::= { sonusSysDspResCurrentEntry 8 }

sonusSysDspResCurrentBridgePortAverageUsedCount OBJECT-TYPE
    SYNTAX          PerfCurrentCount
    MAX-ACCESS      read-only
    STATUS          current
    DESCRIPTION     
            "The current average usage of type Bridge  Port DSP PAD."
    ::= { sonusSysDspResCurrentEntry 9 }

sonusSysDspResCurrentBridgePortAverageAvailCount OBJECT-TYPE
    SYNTAX          PerfCurrentCount
    MAX-ACCESS      read-only
    STATUS          current
    DESCRIPTION     
            "The current average availability of type Bridge Port DSP PAD."
    ::= { sonusSysDspResCurrentEntry 10 }

sonusSysDspResCurrentG729PeakUsedCount OBJECT-TYPE
    SYNTAX          PerfCurrentCount
    MAX-ACCESS      read-only
    STATUS          current
    DESCRIPTION     
            "The current  Peak usage of type G729 DSP PAD."
    ::= { sonusSysDspResCurrentEntry 11 }

sonusSysDspResCurrentG729AverageUsedCount OBJECT-TYPE
    SYNTAX          PerfCurrentCount
    MAX-ACCESS      read-only
    STATUS          current
    DESCRIPTION     
            "The current average usage of type G729 DSP PAD."
    ::= { sonusSysDspResCurrentEntry 12 }

sonusSysDspResCurrentG729AverageAvailCount OBJECT-TYPE
    SYNTAX          PerfCurrentCount
    MAX-ACCESS      read-only
    STATUS          current
    DESCRIPTION     
            "The current average availability of type G729 DSP PAD."
    ::= { sonusSysDspResCurrentEntry 13 }

sonusSysDspResCurrentG726PeakUsedCount OBJECT-TYPE
    SYNTAX          PerfCurrentCount
    MAX-ACCESS      read-only
    STATUS          current
    DESCRIPTION     
            "The current peak usage of type G726 DSP PAD."
    ::= { sonusSysDspResCurrentEntry 14 }

sonusSysDspResCurrentG726AverageUsedCount OBJECT-TYPE
    SYNTAX          PerfCurrentCount
    MAX-ACCESS      read-only
    STATUS          current
    DESCRIPTION     
            "The current average usage of type G726 DSP PAD."
    ::= { sonusSysDspResCurrentEntry 15 }

sonusSysDspResCurrentG726AverageAvailCount OBJECT-TYPE
    SYNTAX          PerfCurrentCount
    MAX-ACCESS      read-only
    STATUS          current
    DESCRIPTION     
            "The current average availability of type G726 DSP PAD."
    ::= { sonusSysDspResCurrentEntry 16 }

sonusSysDspResCurrentG723PeakUsedCount OBJECT-TYPE
    SYNTAX          PerfCurrentCount
    MAX-ACCESS      read-only
    STATUS          current
    DESCRIPTION     
            "The current peak usage of type G723 DSP PAD."
    ::= { sonusSysDspResCurrentEntry 17 }

sonusSysDspResCurrentG723AverageUsedCount OBJECT-TYPE
    SYNTAX          PerfCurrentCount
    MAX-ACCESS      read-only
    STATUS          current
    DESCRIPTION     
            "The current average usage of type G723 DSP PAD."
    ::= { sonusSysDspResCurrentEntry 18 }

sonusSysDspResCurrentG723AverageAvailCount OBJECT-TYPE
    SYNTAX          PerfCurrentCount
    MAX-ACCESS      read-only
    STATUS          current
    DESCRIPTION     
            "The current average availability of type G723 DSP PAD."
    ::= { sonusSysDspResCurrentEntry 19 }

sonusSysDspResCurrentG711PacketPeakUsedCount OBJECT-TYPE
    SYNTAX          PerfCurrentCount
    MAX-ACCESS      read-only
    STATUS          current
    DESCRIPTION     
            "The current peak usage of type G711Packet DSP PAD."
    ::= { sonusSysDspResCurrentEntry 20 }

sonusSysDspResCurrentG711PacketAverageUsedCount OBJECT-TYPE
    SYNTAX          PerfCurrentCount
    MAX-ACCESS      read-only
    STATUS          current
    DESCRIPTION     
            "The current average usage of type G711Packet DSP PAD."
    ::= { sonusSysDspResCurrentEntry 21 }

sonusSysDspResCurrentG711PacketAverageAvailCount OBJECT-TYPE
    SYNTAX          PerfCurrentCount
    MAX-ACCESS      read-only
    STATUS          current
    DESCRIPTION     
            "The current average availability of type G711Packet DSP PAD."
    ::= { sonusSysDspResCurrentEntry 22 }

sonusSysDspResCurrentT38PeakUsedCount OBJECT-TYPE
    SYNTAX          PerfCurrentCount
    MAX-ACCESS      read-only
    STATUS          current
    DESCRIPTION     
            "The current peak usage of type T38 DSP PAD."
    ::= { sonusSysDspResCurrentEntry 23 }

sonusSysDspResCurrentT38AverageUsedCount OBJECT-TYPE
    SYNTAX          PerfCurrentCount
    MAX-ACCESS      read-only
    STATUS          current
    DESCRIPTION     
            "The current average usage of type T38 DSP PAD."
    ::= { sonusSysDspResCurrentEntry 24 }

sonusSysDspResCurrentT38AverageAvailCount OBJECT-TYPE
    SYNTAX          PerfCurrentCount
    MAX-ACCESS      read-only
    STATUS          current
    DESCRIPTION     
            "The current average availability of type T38 DSP PAD."
    ::= { sonusSysDspResCurrentEntry 25 }

sonusSysDspResCurrentEvrcPeakUsedCount OBJECT-TYPE
    SYNTAX          PerfCurrentCount
    MAX-ACCESS      read-only
    STATUS          current
    DESCRIPTION     
            "The current peak usage of type EVRC DSP PAD."
    ::= { sonusSysDspResCurrentEntry 26 }

sonusSysDspResCurrentEvrcAverageUsedCount OBJECT-TYPE
    SYNTAX          PerfCurrentCount
    MAX-ACCESS      read-only
    STATUS          current
    DESCRIPTION     
            "The current average usage of type EVRC DSP PAD."
    ::= { sonusSysDspResCurrentEntry 27 }

sonusSysDspResCurrentEvrcAverageAvailCount OBJECT-TYPE
    SYNTAX          PerfCurrentCount
    MAX-ACCESS      read-only
    STATUS          current
    DESCRIPTION     
            "The current average availability of type EVRC DSP PAD."
    ::= { sonusSysDspResCurrentEntry 28 }

sonusSysDspResCurrentGsmPeakUsedCount OBJECT-TYPE
    SYNTAX          PerfCurrentCount
    MAX-ACCESS      read-only
    STATUS          current
    DESCRIPTION     
            "The current peak usage of type GSM DSP PAD."
    ::= { sonusSysDspResCurrentEntry 29 }

sonusSysDspResCurrentGsmAverageUsedCount OBJECT-TYPE
    SYNTAX          PerfCurrentCount
    MAX-ACCESS      read-only
    STATUS          current
    DESCRIPTION     
            "The current average usage of type GSM DSP PAD."
    ::= { sonusSysDspResCurrentEntry 30 }

sonusSysDspResCurrentGsmAverageAvailCount OBJECT-TYPE
    SYNTAX          PerfCurrentCount
    MAX-ACCESS      read-only
    STATUS          current
    DESCRIPTION     
            "The current average availability of type GSM DSP PAD."
    ::= { sonusSysDspResCurrentEntry 31 }

sonusSysDspResCurrentT38EcmPeakUsedCount OBJECT-TYPE
    SYNTAX          PerfCurrentCount
    MAX-ACCESS      read-only
    STATUS          current
    DESCRIPTION     
            "The current peak usage of type T38 ECM capable DSP PAD."
    ::= { sonusSysDspResCurrentEntry 32 }

sonusSysDspResCurrentT38EcmAverageUsedCount OBJECT-TYPE
    SYNTAX          PerfCurrentCount
    MAX-ACCESS      read-only
    STATUS          current
    DESCRIPTION     
            "The current average usage of type T38 ECM capable DSP PAD."
    ::= { sonusSysDspResCurrentEntry 33 }

sonusSysDspResCurrentT38EcmAverageAvailCount OBJECT-TYPE
    SYNTAX          PerfCurrentCount
    MAX-ACCESS      read-only
    STATUS          current
    DESCRIPTION     
            "The current average availability of type T38 ECM capable DSP PAD."
    ::= { sonusSysDspResCurrentEntry 34 }

sonusSysDspResCurrentEvrcb0PeakUsedCount OBJECT-TYPE
    SYNTAX          PerfCurrentCount
    MAX-ACCESS      read-only
    STATUS          current
    DESCRIPTION     
            "The current peak usage of type EVRCB0 DSP PAD."
    ::= { sonusSysDspResCurrentEntry 35 }

sonusSysDspResCurrentEvrcb0AverageUsedCount OBJECT-TYPE
    SYNTAX          PerfCurrentCount
    MAX-ACCESS      read-only
    STATUS          current
    DESCRIPTION     
            "The current average usage of type EVRCB0 DSP PAD."
    ::= { sonusSysDspResCurrentEntry 36 }

sonusSysDspResCurrentEvrcb0AverageAvailCount OBJECT-TYPE
    SYNTAX          PerfCurrentCount
    MAX-ACCESS      read-only
    STATUS          current
    DESCRIPTION     
            "The current average availability of type EVRCB0 DSP PAD."
    ::= { sonusSysDspResCurrentEntry 37 }

sonusSysDspResCurrentiLBCPeakUsedCount OBJECT-TYPE
    SYNTAX          PerfCurrentCount
    MAX-ACCESS      read-only
    STATUS          current
    DESCRIPTION     
            "The current peak usage of type EVRCB0 DSP PAD."
    ::= { sonusSysDspResCurrentEntry 38 }

sonusSysDspResCurrentiLBCAverageUsedCount OBJECT-TYPE
    SYNTAX          PerfCurrentCount
    MAX-ACCESS      read-only
    STATUS          current
    DESCRIPTION     
            "The current average usage of type EVRCB0 DSP PAD."
    ::= { sonusSysDspResCurrentEntry 39 }

sonusSysDspResCurrentiLBCAverageAvailCount OBJECT-TYPE
    SYNTAX          PerfCurrentCount
    MAX-ACCESS      read-only
    STATUS          current
    DESCRIPTION     
            "The current average availability of type EVRCB0 DSP PAD."
    ::= { sonusSysDspResCurrentEntry 40 }

sonusSysDspResCurrentG722PeakUsedCount OBJECT-TYPE
    SYNTAX          PerfCurrentCount
    MAX-ACCESS      read-only
    STATUS          current
    DESCRIPTION     
            "The current peak usage of type G722 DSP PAD."
    ::= { sonusSysDspResCurrentEntry 41 }

sonusSysDspResCurrentG722AverageUsedCount OBJECT-TYPE
    SYNTAX          PerfCurrentCount
    MAX-ACCESS      read-only
    STATUS          current
    DESCRIPTION     
            "The current average usage of type G722 DSP PAD."
    ::= { sonusSysDspResCurrentEntry 42 }

sonusSysDspResCurrentG722AverageAvailCount OBJECT-TYPE
    SYNTAX          PerfCurrentCount
    MAX-ACCESS      read-only
    STATUS          current
    DESCRIPTION     
            "The current average availability of type G722 DSP PAD."
    ::= { sonusSysDspResCurrentEntry 43 }

sonusSysDspResCurrentAmrwbPeakUsedCount OBJECT-TYPE
    SYNTAX          PerfCurrentCount
    MAX-ACCESS      read-only
    STATUS          current
    DESCRIPTION     
            "The current peak usage of type AMRWB DSP PAD."
    ::= { sonusSysDspResCurrentEntry 44 }

sonusSysDspResCurrentAmrwbAverageUsedCount OBJECT-TYPE
    SYNTAX          PerfCurrentCount
    MAX-ACCESS      read-only
    STATUS          current
    DESCRIPTION     
            "The current average usage of type AMRWB DSP PAD."
    ::= { sonusSysDspResCurrentEntry 45 }

sonusSysDspResCurrentAmrwbAverageAvailCount OBJECT-TYPE
    SYNTAX          PerfCurrentCount
    MAX-ACCESS      read-only
    STATUS          current
    DESCRIPTION     
            "The current average availability of type AMRWB DSP PAD."
    ::= { sonusSysDspResCurrentEntry 46 }

sonusSysDspResIntervalTable OBJECT-TYPE
    SYNTAX          SEQUENCE OF SonusSysDspResIntervalEntry
    MAX-ACCESS      not-accessible
    STATUS          current
    DESCRIPTION     
            "The Sonus DSP Resource Interval table."
    ::= { sonusDspPadResStatisticsObjects 4 }

sonusSysDspResIntervalEntry OBJECT-TYPE
    SYNTAX          SonusSysDspResIntervalEntry
    MAX-ACCESS      not-accessible
    STATUS          current
    DESCRIPTION     
            "An entry in the Sonus DSP Resource Interval table."
    INDEX           { sonusSysDspResIntervalShelfIndex, 
                      sonusSysDspResIntervalNumber }
    ::= { sonusSysDspResIntervalTable 1 }

SonusSysDspResIntervalEntry ::=
    SEQUENCE {
        sonusSysDspResIntervalShelfIndex SonusShelfIndex,
        sonusSysDspResIntervalNumber    Integer32,
        sonusSysDspResIntervalTime      TimeTicks,
        sonusSysDspResIntervalValidData TruthValue,
        sonusSysDspResIntervalG711CircuitPeakUsedCount              PerfIntervalCount,
        sonusSysDspResIntervalG711CircuitAverageUsedCount                 PerfIntervalCount,
        sonusSysDspResIntervalG711CircuitAverageAvailCount                  PerfIntervalCount,
        sonusSysDspResIntervalTonePeakUsedCount       PerfIntervalCount,
        sonusSysDspResIntervalToneAverageUsedCount          PerfIntervalCount,
        sonusSysDspResIntervalToneAverageAvailCount           PerfIntervalCount,
        sonusSysDspResIntervalBridgePortPeakUsedCount             PerfIntervalCount,
        sonusSysDspResIntervalBridgePortAverageUsedCount                PerfIntervalCount,
        sonusSysDspResIntervalBridgePortAverageAvailCount                 PerfIntervalCount,
        sonusSysDspResIntervalG729PeakUsedCount       PerfIntervalCount,
        sonusSysDspResIntervalG729AverageUsedCount          PerfIntervalCount,
        sonusSysDspResIntervalG729AverageAvailCount           PerfIntervalCount,
        sonusSysDspResIntervalG726PeakUsedCount       PerfIntervalCount,
        sonusSysDspResIntervalG726AverageUsedCount          PerfIntervalCount,
        sonusSysDspResIntervalG726AverageAvailCount           PerfIntervalCount,
        sonusSysDspResIntervalG723PeakUsedCount       PerfIntervalCount,
        sonusSysDspResIntervalG723AverageUsedCount          PerfIntervalCount,
        sonusSysDspResIntervalG723AverageAvailCount           PerfIntervalCount,
        sonusSysDspResIntervalG711PacketPeakUsedCount             PerfIntervalCount,
        sonusSysDspResIntervalG711PacketAverageUsedCount                PerfIntervalCount,
        sonusSysDspResIntervalG711PacketAverageAvailCount                 PerfIntervalCount,
        sonusSysDspResIntervalT38PeakUsedCount      PerfIntervalCount,
        sonusSysDspResIntervalT38AverageUsedCount         PerfIntervalCount,
        sonusSysDspResIntervalT38AverageAvailCount          PerfIntervalCount,
        sonusSysDspResIntervalEvrcPeakUsedCount       PerfIntervalCount,
        sonusSysDspResIntervalEvrcAverageUsedCount          PerfIntervalCount,
        sonusSysDspResIntervalEvrcAverageAvailCount           PerfIntervalCount,
        sonusSysDspResIntervalGsmPeakUsedCount      PerfIntervalCount,
        sonusSysDspResIntervalGsmAverageUsedCount         PerfIntervalCount,
        sonusSysDspResIntervalGsmAverageAvailCount          PerfIntervalCount,
        sonusSysDspResIntervalT38EcmPeakUsedCount         PerfIntervalCount,
        sonusSysDspResIntervalT38EcmAverageUsedCount            PerfIntervalCount,
        sonusSysDspResIntervalT38EcmAverageAvailCount             PerfIntervalCount,
        sonusSysDspResIntervalEvrcb0PeakUsedCount         PerfIntervalCount,
        sonusSysDspResIntervalEvrcb0AverageUsedCount            PerfIntervalCount,
        sonusSysDspResIntervalEvrcb0AverageAvailCount             PerfIntervalCount,
        sonusSysDspResIntervaliLBCPeakUsedCount       PerfIntervalCount,
        sonusSysDspResIntervaliLBCAverageUsedCount          PerfIntervalCount,
        sonusSysDspResIntervaliLBCAverageAvailCount           PerfIntervalCount,
        sonusSysDspResIntervalG722PeakUsedCount       PerfIntervalCount,
        sonusSysDspResIntervalG722AverageUsedCount          PerfIntervalCount,
        sonusSysDspResIntervalG722AverageAvailCount           PerfIntervalCount,
        sonusSysDspResIntervalAmrwbPeakUsedCount        PerfIntervalCount,
        sonusSysDspResIntervalAmrwbAverageUsedCount           PerfIntervalCount,
        sonusSysDspResIntervalAmrwbAverageAvailCount            PerfIntervalCount
    }

sonusSysDspResIntervalShelfIndex OBJECT-TYPE
    SYNTAX          SonusShelfIndex
    MAX-ACCESS      read-only
    STATUS          current
    DESCRIPTION     
            "The index into the sonusSysDspResIntervalTable."
    ::= { sonusSysDspResIntervalEntry 1 }

sonusSysDspResIntervalNumber OBJECT-TYPE
    SYNTAX          Integer32 (1..288)
    MAX-ACCESS      not-accessible
    STATUS          current
    DESCRIPTION     
            "A number between 1 and 288, which identifies the
             interval for which the set of statistics is available.
             The interval identified by 1 is the most recently
             completed interval, and the interval identified
             by N is the interval immediately preceding the
             one identified by N-1."
    ::= { sonusSysDspResIntervalEntry 2 }

sonusSysDspResIntervalTime OBJECT-TYPE
    SYNTAX          TimeTicks
    MAX-ACCESS      read-only
    STATUS          current
    DESCRIPTION     
            "This variable contains the end of interval time stamp for the specified interval."
    ::= { sonusSysDspResIntervalEntry 3 }

sonusSysDspResIntervalValidData OBJECT-TYPE
    SYNTAX          TruthValue
    MAX-ACCESS      read-only
    STATUS          current
    DESCRIPTION     
            "This variable indicates if the data for this interval is valid."
    ::= { sonusSysDspResIntervalEntry 4 }

sonusSysDspResIntervalG711CircuitPeakUsedCount OBJECT-TYPE
    SYNTAX          PerfIntervalCount
    MAX-ACCESS      read-only
    STATUS          current
    DESCRIPTION     
            "The peak usage of type G711Circuit DSP pad during an interval time."
    ::= { sonusSysDspResIntervalEntry 5 }

sonusSysDspResIntervalG711CircuitAverageUsedCount OBJECT-TYPE
    SYNTAX          PerfIntervalCount
    MAX-ACCESS      read-only
    STATUS          current
    DESCRIPTION     
            "The the average usage of type G711Circuit DSP pad during an interval time."
    ::= { sonusSysDspResIntervalEntry 6 }

sonusSysDspResIntervalG711CircuitAverageAvailCount OBJECT-TYPE
    SYNTAX          PerfIntervalCount
    MAX-ACCESS      read-only
    STATUS          current
    DESCRIPTION     
            "The average availability of type G711Circuit DSP pad during an interval time."
    ::= { sonusSysDspResIntervalEntry 7 }

sonusSysDspResIntervalTonePeakUsedCount OBJECT-TYPE
    SYNTAX          PerfIntervalCount
    MAX-ACCESS      read-only
    STATUS          current
    DESCRIPTION     
            "The Interval number of Peak usage of type Tone DSP pad during an interval time."
    ::= { sonusSysDspResIntervalEntry 8 }

sonusSysDspResIntervalToneAverageUsedCount OBJECT-TYPE
    SYNTAX          PerfIntervalCount
    MAX-ACCESS      read-only
    STATUS          current
    DESCRIPTION     
            "The average usage of type Tone DSP pad during an interval time."
    ::= { sonusSysDspResIntervalEntry 9 }

sonusSysDspResIntervalToneAverageAvailCount OBJECT-TYPE
    SYNTAX          PerfIntervalCount
    MAX-ACCESS      read-only
    STATUS          current
    DESCRIPTION     
            "The average availability of type Tone DSP pad during an interval time."
    ::= { sonusSysDspResIntervalEntry 10 }

sonusSysDspResIntervalBridgePortPeakUsedCount OBJECT-TYPE
    SYNTAX          PerfIntervalCount
    MAX-ACCESS      read-only
    STATUS          current
    DESCRIPTION     
            "The peak usage of type Bridge  Port DSP pad during an interval time."
    ::= { sonusSysDspResIntervalEntry 11 }

sonusSysDspResIntervalBridgePortAverageUsedCount OBJECT-TYPE
    SYNTAX          PerfIntervalCount
    MAX-ACCESS      read-only
    STATUS          current
    DESCRIPTION     
            "The average usage of type Bridge  Port DSP pad during an interval time."
    ::= { sonusSysDspResIntervalEntry 12 }

sonusSysDspResIntervalBridgePortAverageAvailCount OBJECT-TYPE
    SYNTAX          PerfIntervalCount
    MAX-ACCESS      read-only
    STATUS          current
    DESCRIPTION     
            "The average availability of type Bridge Port DSP pad during an interval time."
    ::= { sonusSysDspResIntervalEntry 13 }

sonusSysDspResIntervalG729PeakUsedCount OBJECT-TYPE
    SYNTAX          PerfIntervalCount
    MAX-ACCESS      read-only
    STATUS          current
    DESCRIPTION     
            "The peak usage of type G729 DSP pad during an interval time."
    ::= { sonusSysDspResIntervalEntry 14 }

sonusSysDspResIntervalG729AverageUsedCount OBJECT-TYPE
    SYNTAX          PerfIntervalCount
    MAX-ACCESS      read-only
    STATUS          current
    DESCRIPTION     
            "The average usage of type G729 DSP pad during an interval time."
    ::= { sonusSysDspResIntervalEntry 15 }

sonusSysDspResIntervalG729AverageAvailCount OBJECT-TYPE
    SYNTAX          PerfIntervalCount
    MAX-ACCESS      read-only
    STATUS          current
    DESCRIPTION     
            "The average availability of type G729 DSP pad during an interval time."
    ::= { sonusSysDspResIntervalEntry 16 }

sonusSysDspResIntervalG726PeakUsedCount OBJECT-TYPE
    SYNTAX          PerfIntervalCount
    MAX-ACCESS      read-only
    STATUS          current
    DESCRIPTION     
            "The Interval number of Peak usage of type G726 DSP pad during an interval time."
    ::= { sonusSysDspResIntervalEntry 17 }

sonusSysDspResIntervalG726AverageUsedCount OBJECT-TYPE
    SYNTAX          PerfIntervalCount
    MAX-ACCESS      read-only
    STATUS          current
    DESCRIPTION     
            "The average usage of type G726 DSP pad during an interval time."
    ::= { sonusSysDspResIntervalEntry 18 }

sonusSysDspResIntervalG726AverageAvailCount OBJECT-TYPE
    SYNTAX          PerfIntervalCount
    MAX-ACCESS      read-only
    STATUS          current
    DESCRIPTION     
            "The average availability of type G726 DSP pad during an interval time."
    ::= { sonusSysDspResIntervalEntry 19 }

sonusSysDspResIntervalG723PeakUsedCount OBJECT-TYPE
    SYNTAX          PerfIntervalCount
    MAX-ACCESS      read-only
    STATUS          current
    DESCRIPTION     
            "The peak usage of type G723 DSP pad during an interval time."
    ::= { sonusSysDspResIntervalEntry 20 }

sonusSysDspResIntervalG723AverageUsedCount OBJECT-TYPE
    SYNTAX          PerfIntervalCount
    MAX-ACCESS      read-only
    STATUS          current
    DESCRIPTION     
            "The average usage of type G723 DSP pad during an interval time."
    ::= { sonusSysDspResIntervalEntry 21 }

sonusSysDspResIntervalG723AverageAvailCount OBJECT-TYPE
    SYNTAX          PerfIntervalCount
    MAX-ACCESS      read-only
    STATUS          current
    DESCRIPTION     
            "The average availability of type G723 DSP pad during an interval time."
    ::= { sonusSysDspResIntervalEntry 22 }

sonusSysDspResIntervalG711PacketPeakUsedCount OBJECT-TYPE
    SYNTAX          PerfIntervalCount
    MAX-ACCESS      read-only
    STATUS          current
    DESCRIPTION     
            "The peak usage of type G711Packet DSP pad during an interval time."
    ::= { sonusSysDspResIntervalEntry 23 }

sonusSysDspResIntervalG711PacketAverageUsedCount OBJECT-TYPE
    SYNTAX          PerfIntervalCount
    MAX-ACCESS      read-only
    STATUS          current
    DESCRIPTION     
            "The average usage of type G711Packet DSP pad during an interval time."
    ::= { sonusSysDspResIntervalEntry 24 }

sonusSysDspResIntervalG711PacketAverageAvailCount OBJECT-TYPE
    SYNTAX          PerfIntervalCount
    MAX-ACCESS      read-only
    STATUS          current
    DESCRIPTION     
            "The average availability of type G711Packet DSP pad during an interval time."
    ::= { sonusSysDspResIntervalEntry 25 }

sonusSysDspResIntervalT38PeakUsedCount OBJECT-TYPE
    SYNTAX          PerfIntervalCount
    MAX-ACCESS      read-only
    STATUS          current
    DESCRIPTION     
            "The peak usage of type T38 DSP pad during an interval time."
    ::= { sonusSysDspResIntervalEntry 26 }

sonusSysDspResIntervalT38AverageUsedCount OBJECT-TYPE
    SYNTAX          PerfIntervalCount
    MAX-ACCESS      read-only
    STATUS          current
    DESCRIPTION     
            "The average usage of type T38 DSP pad during an interval time."
    ::= { sonusSysDspResIntervalEntry 27 }

sonusSysDspResIntervalT38AverageAvailCount OBJECT-TYPE
    SYNTAX          PerfIntervalCount
    MAX-ACCESS      read-only
    STATUS          current
    DESCRIPTION     
            "The average availability of type T38 DSP pad during an interval time."
    ::= { sonusSysDspResIntervalEntry 28 }

sonusSysDspResIntervalEvrcPeakUsedCount OBJECT-TYPE
    SYNTAX          PerfIntervalCount
    MAX-ACCESS      read-only
    STATUS          current
    DESCRIPTION     
            "The peak usage of type EVRC DSP pad during an interval time."
    ::= { sonusSysDspResIntervalEntry 29 }

sonusSysDspResIntervalEvrcAverageUsedCount OBJECT-TYPE
    SYNTAX          PerfIntervalCount
    MAX-ACCESS      read-only
    STATUS          current
    DESCRIPTION     
            "The average usage of type EVRC DSP pad during an interval time."
    ::= { sonusSysDspResIntervalEntry 30 }

sonusSysDspResIntervalEvrcAverageAvailCount OBJECT-TYPE
    SYNTAX          PerfIntervalCount
    MAX-ACCESS      read-only
    STATUS          current
    DESCRIPTION     
            "The average availability of type EVRC DSP pad during an interval time."
    ::= { sonusSysDspResIntervalEntry 31 }

sonusSysDspResIntervalGsmPeakUsedCount OBJECT-TYPE
    SYNTAX          PerfIntervalCount
    MAX-ACCESS      read-only
    STATUS          current
    DESCRIPTION     
            "The peak usage of type GSM DSP pad during an interval time."
    ::= { sonusSysDspResIntervalEntry 32 }

sonusSysDspResIntervalGsmAverageUsedCount OBJECT-TYPE
    SYNTAX          PerfIntervalCount
    MAX-ACCESS      read-only
    STATUS          current
    DESCRIPTION     
            "The average usage of type GSM DSP pad during an interval time."
    ::= { sonusSysDspResIntervalEntry 33 }

sonusSysDspResIntervalGsmAverageAvailCount OBJECT-TYPE
    SYNTAX          PerfIntervalCount
    MAX-ACCESS      read-only
    STATUS          current
    DESCRIPTION     
            "The average availability of type GSM DSP pad during an interval time."
    ::= { sonusSysDspResIntervalEntry 34 }

sonusSysDspResIntervalT38EcmPeakUsedCount OBJECT-TYPE
    SYNTAX          PerfIntervalCount
    MAX-ACCESS      read-only
    STATUS          current
    DESCRIPTION     
            "The peak usage of type T38 ECM capable DSP pad during an interval time."
    ::= { sonusSysDspResIntervalEntry 35 }

sonusSysDspResIntervalT38EcmAverageUsedCount OBJECT-TYPE
    SYNTAX          PerfIntervalCount
    MAX-ACCESS      read-only
    STATUS          current
    DESCRIPTION     
            "The average usage of type T38 ECM capable DSP pad during an interval time."
    ::= { sonusSysDspResIntervalEntry 36 }

sonusSysDspResIntervalT38EcmAverageAvailCount OBJECT-TYPE
    SYNTAX          PerfIntervalCount
    MAX-ACCESS      read-only
    STATUS          current
    DESCRIPTION     
            "The average availability of type T38 ECM capable DSP pad during an interval time."
    ::= { sonusSysDspResIntervalEntry 37 }

sonusSysDspResIntervalEvrcb0PeakUsedCount OBJECT-TYPE
    SYNTAX          PerfIntervalCount
    MAX-ACCESS      read-only
    STATUS          current
    DESCRIPTION     
            "The peak usage of type EVRCB0 DSP pad during an interval time."
    ::= { sonusSysDspResIntervalEntry 38 }

sonusSysDspResIntervalEvrcb0AverageUsedCount OBJECT-TYPE
    SYNTAX          PerfIntervalCount
    MAX-ACCESS      read-only
    STATUS          current
    DESCRIPTION     
            "The average usage of type EVRCB0 DSP pad during an interval time."
    ::= { sonusSysDspResIntervalEntry 39 }

sonusSysDspResIntervalEvrcb0AverageAvailCount OBJECT-TYPE
    SYNTAX          PerfIntervalCount
    MAX-ACCESS      read-only
    STATUS          current
    DESCRIPTION     
            "The average availability of type EVRCB0 DSP pad during an interval time."
    ::= { sonusSysDspResIntervalEntry 40 }

sonusSysDspResIntervaliLBCPeakUsedCount OBJECT-TYPE
    SYNTAX          PerfIntervalCount
    MAX-ACCESS      read-only
    STATUS          current
    DESCRIPTION     
            "The peak usage of type iLBC DSP pad during an interval time."
    ::= { sonusSysDspResIntervalEntry 41 }

sonusSysDspResIntervaliLBCAverageUsedCount OBJECT-TYPE
    SYNTAX          PerfIntervalCount
    MAX-ACCESS      read-only
    STATUS          current
    DESCRIPTION     
            "The average usage of type iLBC DSP pad during an interval time."
    ::= { sonusSysDspResIntervalEntry 42 }

sonusSysDspResIntervaliLBCAverageAvailCount OBJECT-TYPE
    SYNTAX          PerfIntervalCount
    MAX-ACCESS      read-only
    STATUS          current
    DESCRIPTION     
            "The average availability of type iLBC DSP pad during an interval time."
    ::= { sonusSysDspResIntervalEntry 43 }

sonusSysDspResIntervalG722PeakUsedCount OBJECT-TYPE
    SYNTAX          PerfIntervalCount
    MAX-ACCESS      read-only
    STATUS          current
    DESCRIPTION     
            "The peak usage of type G722 DSP pad during an interval time."
    ::= { sonusSysDspResIntervalEntry 44 }

sonusSysDspResIntervalG722AverageUsedCount OBJECT-TYPE
    SYNTAX          PerfIntervalCount
    MAX-ACCESS      read-only
    STATUS          current
    DESCRIPTION     
            "The average usage of type G722 DSP pad during an interval time."
    ::= { sonusSysDspResIntervalEntry 45 }

sonusSysDspResIntervalG722AverageAvailCount OBJECT-TYPE
    SYNTAX          PerfIntervalCount
    MAX-ACCESS      read-only
    STATUS          current
    DESCRIPTION     
            "The average availability of type G722 DSP pad during an interval time."
    ::= { sonusSysDspResIntervalEntry 46 }

sonusSysDspResIntervalAmrwbPeakUsedCount OBJECT-TYPE
    SYNTAX          PerfIntervalCount
    MAX-ACCESS      read-only
    STATUS          current
    DESCRIPTION     
            "The peak usage of type Amrwb DSP pad during an interval time."
    ::= { sonusSysDspResIntervalEntry 47 }

sonusSysDspResIntervalAmrwbAverageUsedCount OBJECT-TYPE
    SYNTAX          PerfIntervalCount
    MAX-ACCESS      read-only
    STATUS          current
    DESCRIPTION     
            "The average usage of type Amrwb DSP pad during an interval time."
    ::= { sonusSysDspResIntervalEntry 48 }

sonusSysDspResIntervalAmrwbAverageAvailCount OBJECT-TYPE
    SYNTAX          PerfIntervalCount
    MAX-ACCESS      read-only
    STATUS          current
    DESCRIPTION     
            "The average availability of type Amrwb DSP pad during an interval time."
    ::= { sonusSysDspResIntervalEntry 49 }

sonusSlotDspResCurrentTable OBJECT-TYPE
    SYNTAX          SEQUENCE OF SonusSlotDspResCurrentEntry
    MAX-ACCESS      not-accessible
    STATUS          current
    DESCRIPTION     
            "The Sonus DSP Resource Current table."
    ::= { sonusDspPadResStatisticsObjects 5 }

sonusSlotDspResCurrentEntry OBJECT-TYPE
    SYNTAX          SonusSlotDspResCurrentEntry
    MAX-ACCESS      not-accessible
    STATUS          current
    DESCRIPTION     
            "An entry in the Sonus DSP Resource Current table."
    INDEX           { sonusSlotDspResCurrentSlotIndex, 
                      sonusSlotDspResCurrentSlotIndex }
    ::= { sonusSlotDspResCurrentTable 1 }

SonusSlotDspResCurrentEntry ::=
    SEQUENCE {
        sonusSlotDspResCurrentShelfIndex SonusShelfIndex,
        sonusSlotDspResCurrentSlotIndex SonusSlotIndex,
        sonusSlotDspResCurrentG711CircuitPeakUsedCount              PerfCurrentCount,
        sonusSlotDspResCurrentG711CircuitAverageUsedCount                 PerfCurrentCount,
        sonusSlotDspResCurrentG711CircuitAverageAvailCount                  PerfCurrentCount,
        sonusSlotDspResCurrentTonePeakUsedCount       PerfCurrentCount,
        sonusSlotDspResCurrentToneAverageUsedCount          PerfCurrentCount,
        sonusSlotDspResCurrentToneAverageAvailCount           PerfCurrentCount,
        sonusSlotDspResCurrentBridgePortPeakUsedCount             PerfCurrentCount,
        sonusSlotDspResCurrentBridgePortAverageUsedCount                PerfCurrentCount,
        sonusSlotDspResCurrentBridgePortAverageAvailCount                 PerfCurrentCount,
        sonusSlotDspResCurrentG729PeakUsedCount       PerfCurrentCount,
        sonusSlotDspResCurrentG729AverageUsedCount          PerfCurrentCount,
        sonusSlotDspResCurrentG729AverageAvailCount           PerfCurrentCount,
        sonusSlotDspResCurrentG726PeakUsedCount       PerfCurrentCount,
        sonusSlotDspResCurrentG726AverageUsedCount          PerfCurrentCount,
        sonusSlotDspResCurrentG726AverageAvailCount           PerfCurrentCount,
        sonusSlotDspResCurrentG723PeakUsedCount       PerfCurrentCount,
        sonusSlotDspResCurrentG723AverageUsedCount          PerfCurrentCount,
        sonusSlotDspResCurrentG723AverageAvailCount           PerfCurrentCount,
        sonusSlotDspResCurrentG711PacketPeakUsedCount             PerfCurrentCount,
        sonusSlotDspResCurrentG711PacketAverageUsedCount                PerfCurrentCount,
        sonusSlotDspResCurrentG711PacketAverageAvailCount                 PerfCurrentCount,
        sonusSlotDspResCurrentT38PeakUsedCount      PerfCurrentCount,
        sonusSlotDspResCurrentT38AverageUsedCount         PerfCurrentCount,
        sonusSlotDspResCurrentT38AverageAvailCount          PerfCurrentCount,
        sonusSlotDspResCurrentEvrcPeakUsedCount       PerfCurrentCount,
        sonusSlotDspResCurrentEvrcAverageUsedCount          PerfCurrentCount,
        sonusSlotDspResCurrentEvrcAverageAvailCount           PerfCurrentCount,
        sonusSlotDspResCurrentGsmPeakUsedCount      PerfCurrentCount,
        sonusSlotDspResCurrentGsmAverageUsedCount         PerfCurrentCount,
        sonusSlotDspResCurrentGsmAverageAvailCount          PerfCurrentCount,
        sonusSlotDspResCurrentT38EcmPeakUsedCount         PerfCurrentCount,
        sonusSlotDspResCurrentT38EcmAverageUsedCount            PerfCurrentCount,
        sonusSlotDspResCurrentT38EcmAverageAvailCount             PerfCurrentCount,
        sonusSlotDspResCurrentEvrcb0PeakUsedCount         PerfCurrentCount,
        sonusSlotDspResCurrentEvrcb0AverageUsedCount            PerfCurrentCount,
        sonusSlotDspResCurrentEvrcb0AverageAvailCount             PerfCurrentCount,
        sonusSlotDspResCurrentiLBCPeakUsedCount       PerfCurrentCount,
        sonusSlotDspResCurrentiLBCAverageUsedCount          PerfCurrentCount,
        sonusSlotDspResCurrentiLBCAverageAvailCount           PerfCurrentCount,
        sonusSlotDspResCurrentG722PeakUsedCount       PerfCurrentCount,
        sonusSlotDspResCurrentG722AverageUsedCount          PerfCurrentCount,
        sonusSlotDspResCurrentG722AverageAvailCount           PerfCurrentCount,
        sonusSlotDspResCurrentAmrwbPeakUsedCount        PerfCurrentCount,
        sonusSlotDspResCurrentAmrwbAverageUsedCount           PerfCurrentCount,
        sonusSlotDspResCurrentAmrwbAverageAvailCount            PerfCurrentCount
    }

sonusSlotDspResCurrentShelfIndex OBJECT-TYPE
    SYNTAX          SonusShelfIndex
    MAX-ACCESS      read-only
    STATUS          current
    DESCRIPTION     
            "The index into the sonusSlotDspResCurrentTable."
    ::= { sonusSlotDspResCurrentEntry 1 }

sonusSlotDspResCurrentSlotIndex OBJECT-TYPE
    SYNTAX          SonusSlotIndex
    MAX-ACCESS      read-only
    STATUS          current
    DESCRIPTION     
            "Identifies the target card."
    ::= { sonusSlotDspResCurrentEntry 2 }

sonusSlotDspResCurrentG711CircuitPeakUsedCount OBJECT-TYPE
    SYNTAX          PerfCurrentCount
    MAX-ACCESS      read-only
    STATUS          current
    DESCRIPTION     
            "The current  Peak usage of type G711Circuit DSP PAD."
    ::= { sonusSlotDspResCurrentEntry 3 }

sonusSlotDspResCurrentG711CircuitAverageUsedCount OBJECT-TYPE
    SYNTAX          PerfCurrentCount
    MAX-ACCESS      read-only
    STATUS          current
    DESCRIPTION     
            "The current average usage of type G711Circuit DSP PAD."
    ::= { sonusSlotDspResCurrentEntry 4 }

sonusSlotDspResCurrentG711CircuitAverageAvailCount OBJECT-TYPE
    SYNTAX          PerfCurrentCount
    MAX-ACCESS      read-only
    STATUS          current
    DESCRIPTION     
            "The current average availability of type G711Circuit DSP PAD."
    ::= { sonusSlotDspResCurrentEntry 5 }

sonusSlotDspResCurrentTonePeakUsedCount OBJECT-TYPE
    SYNTAX          PerfCurrentCount
    MAX-ACCESS      read-only
    STATUS          current
    DESCRIPTION     
            "The current  Peak usage of type Tone DSP PAD."
    ::= { sonusSlotDspResCurrentEntry 6 }

sonusSlotDspResCurrentToneAverageUsedCount OBJECT-TYPE
    SYNTAX          PerfCurrentCount
    MAX-ACCESS      read-only
    STATUS          current
    DESCRIPTION     
            "The current average usage of type Tone DSP PAD."
    ::= { sonusSlotDspResCurrentEntry 7 }

sonusSlotDspResCurrentToneAverageAvailCount OBJECT-TYPE
    SYNTAX          PerfCurrentCount
    MAX-ACCESS      read-only
    STATUS          current
    DESCRIPTION     
            "The current average availability of type Tone DSP PAD."
    ::= { sonusSlotDspResCurrentEntry 8 }

sonusSlotDspResCurrentBridgePortPeakUsedCount OBJECT-TYPE
    SYNTAX          PerfCurrentCount
    MAX-ACCESS      read-only
    STATUS          current
    DESCRIPTION     
            "The current  peak usage of type Bridge  Port DSP PAD."
    ::= { sonusSlotDspResCurrentEntry 9 }

sonusSlotDspResCurrentBridgePortAverageUsedCount OBJECT-TYPE
    SYNTAX          PerfCurrentCount
    MAX-ACCESS      read-only
    STATUS          current
    DESCRIPTION     
            "The current average usage of type Bridge  Port DSP PAD."
    ::= { sonusSlotDspResCurrentEntry 10 }

sonusSlotDspResCurrentBridgePortAverageAvailCount OBJECT-TYPE
    SYNTAX          PerfCurrentCount
    MAX-ACCESS      read-only
    STATUS          current
    DESCRIPTION     
            "The current average availability of type Bridge Port DSP PAD."
    ::= { sonusSlotDspResCurrentEntry 11 }

sonusSlotDspResCurrentG729PeakUsedCount OBJECT-TYPE
    SYNTAX          PerfCurrentCount
    MAX-ACCESS      read-only
    STATUS          current
    DESCRIPTION     
            "The current  Peak usage of type G729 DSP PAD."
    ::= { sonusSlotDspResCurrentEntry 12 }

sonusSlotDspResCurrentG729AverageUsedCount OBJECT-TYPE
    SYNTAX          PerfCurrentCount
    MAX-ACCESS      read-only
    STATUS          current
    DESCRIPTION     
            "The current average usage of type G729 DSP PAD."
    ::= { sonusSlotDspResCurrentEntry 13 }

sonusSlotDspResCurrentG729AverageAvailCount OBJECT-TYPE
    SYNTAX          PerfCurrentCount
    MAX-ACCESS      read-only
    STATUS          current
    DESCRIPTION     
            "The current average availability of type G729 DSP PAD."
    ::= { sonusSlotDspResCurrentEntry 14 }

sonusSlotDspResCurrentG726PeakUsedCount OBJECT-TYPE
    SYNTAX          PerfCurrentCount
    MAX-ACCESS      read-only
    STATUS          current
    DESCRIPTION     
            "The current peak usage of type G726 DSP PAD."
    ::= { sonusSlotDspResCurrentEntry 15 }

sonusSlotDspResCurrentG726AverageUsedCount OBJECT-TYPE
    SYNTAX          PerfCurrentCount
    MAX-ACCESS      read-only
    STATUS          current
    DESCRIPTION     
            "The current average usage of type G726 DSP PAD."
    ::= { sonusSlotDspResCurrentEntry 16 }

sonusSlotDspResCurrentG726AverageAvailCount OBJECT-TYPE
    SYNTAX          PerfCurrentCount
    MAX-ACCESS      read-only
    STATUS          current
    DESCRIPTION     
            "The current average availability of type G726 DSP PAD."
    ::= { sonusSlotDspResCurrentEntry 17 }

sonusSlotDspResCurrentG723PeakUsedCount OBJECT-TYPE
    SYNTAX          PerfCurrentCount
    MAX-ACCESS      read-only
    STATUS          current
    DESCRIPTION     
            "The current peak usage of type G723 DSP PAD."
    ::= { sonusSlotDspResCurrentEntry 18 }

sonusSlotDspResCurrentG723AverageUsedCount OBJECT-TYPE
    SYNTAX          PerfCurrentCount
    MAX-ACCESS      read-only
    STATUS          current
    DESCRIPTION     
            "The current average usage of type G723 DSP PAD."
    ::= { sonusSlotDspResCurrentEntry 19 }

sonusSlotDspResCurrentG723AverageAvailCount OBJECT-TYPE
    SYNTAX          PerfCurrentCount
    MAX-ACCESS      read-only
    STATUS          current
    DESCRIPTION     
            "The current average availability of type G723 DSP PAD."
    ::= { sonusSlotDspResCurrentEntry 20 }

sonusSlotDspResCurrentG711PacketPeakUsedCount OBJECT-TYPE
    SYNTAX          PerfCurrentCount
    MAX-ACCESS      read-only
    STATUS          current
    DESCRIPTION     
            "The current peak usage of type G711Packet DSP PAD."
    ::= { sonusSlotDspResCurrentEntry 21 }

sonusSlotDspResCurrentG711PacketAverageUsedCount OBJECT-TYPE
    SYNTAX          PerfCurrentCount
    MAX-ACCESS      read-only
    STATUS          current
    DESCRIPTION     
            "The current average usage of type G711Packet DSP PAD."
    ::= { sonusSlotDspResCurrentEntry 22 }

sonusSlotDspResCurrentG711PacketAverageAvailCount OBJECT-TYPE
    SYNTAX          PerfCurrentCount
    MAX-ACCESS      read-only
    STATUS          current
    DESCRIPTION     
            "The current average availability of type G711Packet DSP PAD."
    ::= { sonusSlotDspResCurrentEntry 23 }

sonusSlotDspResCurrentT38PeakUsedCount OBJECT-TYPE
    SYNTAX          PerfCurrentCount
    MAX-ACCESS      read-only
    STATUS          current
    DESCRIPTION     
            "The current peak usage of type T38 DSP PAD."
    ::= { sonusSlotDspResCurrentEntry 24 }

sonusSlotDspResCurrentT38AverageUsedCount OBJECT-TYPE
    SYNTAX          PerfCurrentCount
    MAX-ACCESS      read-only
    STATUS          current
    DESCRIPTION     
            "The current average usage of type T38 DSP PAD."
    ::= { sonusSlotDspResCurrentEntry 25 }

sonusSlotDspResCurrentT38AverageAvailCount OBJECT-TYPE
    SYNTAX          PerfCurrentCount
    MAX-ACCESS      read-only
    STATUS          current
    DESCRIPTION     
            "The current average availability of type T38 DSP PAD."
    ::= { sonusSlotDspResCurrentEntry 26 }

sonusSlotDspResCurrentEvrcPeakUsedCount OBJECT-TYPE
    SYNTAX          PerfCurrentCount
    MAX-ACCESS      read-only
    STATUS          current
    DESCRIPTION     
            "The current peak usage of type EVRC DSP PAD."
    ::= { sonusSlotDspResCurrentEntry 27 }

sonusSlotDspResCurrentEvrcAverageUsedCount OBJECT-TYPE
    SYNTAX          PerfCurrentCount
    MAX-ACCESS      read-only
    STATUS          current
    DESCRIPTION     
            "The current average usage of type EVRC DSP PAD."
    ::= { sonusSlotDspResCurrentEntry 28 }

sonusSlotDspResCurrentEvrcAverageAvailCount OBJECT-TYPE
    SYNTAX          PerfCurrentCount
    MAX-ACCESS      read-only
    STATUS          current
    DESCRIPTION     
            "The current average availability of type EVRC DSP PAD."
    ::= { sonusSlotDspResCurrentEntry 29 }

sonusSlotDspResCurrentGsmPeakUsedCount OBJECT-TYPE
    SYNTAX          PerfCurrentCount
    MAX-ACCESS      read-only
    STATUS          current
    DESCRIPTION     
            "The current peak usage of type GSM DSP PAD."
    ::= { sonusSlotDspResCurrentEntry 30 }

sonusSlotDspResCurrentGsmAverageUsedCount OBJECT-TYPE
    SYNTAX          PerfCurrentCount
    MAX-ACCESS      read-only
    STATUS          current
    DESCRIPTION     
            "The current average usage of type GSM DSP PAD."
    ::= { sonusSlotDspResCurrentEntry 31 }

sonusSlotDspResCurrentGsmAverageAvailCount OBJECT-TYPE
    SYNTAX          PerfCurrentCount
    MAX-ACCESS      read-only
    STATUS          current
    DESCRIPTION     
            "The current average availability of type GSM DSP PAD."
    ::= { sonusSlotDspResCurrentEntry 32 }

sonusSlotDspResCurrentT38EcmPeakUsedCount OBJECT-TYPE
    SYNTAX          PerfCurrentCount
    MAX-ACCESS      read-only
    STATUS          current
    DESCRIPTION     
            "The current peak usage of type T38 ECM capable DSP PAD."
    ::= { sonusSlotDspResCurrentEntry 33 }

sonusSlotDspResCurrentT38EcmAverageUsedCount OBJECT-TYPE
    SYNTAX          PerfCurrentCount
    MAX-ACCESS      read-only
    STATUS          current
    DESCRIPTION     
            "The current average usage of type T38 ECM capable DSP PAD."
    ::= { sonusSlotDspResCurrentEntry 34 }

sonusSlotDspResCurrentT38EcmAverageAvailCount OBJECT-TYPE
    SYNTAX          PerfCurrentCount
    MAX-ACCESS      read-only
    STATUS          current
    DESCRIPTION     
            "The current average availability of type T38 ECM capable DSP PAD."
    ::= { sonusSlotDspResCurrentEntry 35 }

sonusSlotDspResCurrentEvrcb0PeakUsedCount OBJECT-TYPE
    SYNTAX          PerfCurrentCount
    MAX-ACCESS      read-only
    STATUS          current
    DESCRIPTION     
            "The current peak usage of type EVRCB0 DSP PAD."
    ::= { sonusSlotDspResCurrentEntry 36 }

sonusSlotDspResCurrentEvrcb0AverageUsedCount OBJECT-TYPE
    SYNTAX          PerfCurrentCount
    MAX-ACCESS      read-only
    STATUS          current
    DESCRIPTION     
            "The current average usage of type EVRCB0 DSP PAD."
    ::= { sonusSlotDspResCurrentEntry 37 }

sonusSlotDspResCurrentEvrcb0AverageAvailCount OBJECT-TYPE
    SYNTAX          PerfCurrentCount
    MAX-ACCESS      read-only
    STATUS          current
    DESCRIPTION     
            "The current average availability of type EVRCB0 DSP PAD."
    ::= { sonusSlotDspResCurrentEntry 38 }

sonusSlotDspResCurrentiLBCPeakUsedCount OBJECT-TYPE
    SYNTAX          PerfCurrentCount
    MAX-ACCESS      read-only
    STATUS          current
    DESCRIPTION     
            "The current peak usage of type iLBC DSP PAD."
    ::= { sonusSlotDspResCurrentEntry 39 }

sonusSlotDspResCurrentiLBCAverageUsedCount OBJECT-TYPE
    SYNTAX          PerfCurrentCount
    MAX-ACCESS      read-only
    STATUS          current
    DESCRIPTION     
            "The current average usage of type iLBC DSP PAD."
    ::= { sonusSlotDspResCurrentEntry 40 }

sonusSlotDspResCurrentiLBCAverageAvailCount OBJECT-TYPE
    SYNTAX          PerfCurrentCount
    MAX-ACCESS      read-only
    STATUS          current
    DESCRIPTION     
            "The current average availability of type iLBC DSP PAD."
    ::= { sonusSlotDspResCurrentEntry 41 }

sonusSlotDspResCurrentG722PeakUsedCount OBJECT-TYPE
    SYNTAX          PerfCurrentCount
    MAX-ACCESS      read-only
    STATUS          current
    DESCRIPTION     
            "The current peak usage of type G722 DSP PAD."
    ::= { sonusSlotDspResCurrentEntry 42 }

sonusSlotDspResCurrentG722AverageUsedCount OBJECT-TYPE
    SYNTAX          PerfCurrentCount
    MAX-ACCESS      read-only
    STATUS          current
    DESCRIPTION     
            "The current average usage of type G722 DSP PAD."
    ::= { sonusSlotDspResCurrentEntry 43 }

sonusSlotDspResCurrentG722AverageAvailCount OBJECT-TYPE
    SYNTAX          PerfCurrentCount
    MAX-ACCESS      read-only
    STATUS          current
    DESCRIPTION     
            "The current average availability of type G722 DSP PAD."
    ::= { sonusSlotDspResCurrentEntry 44 }

sonusSlotDspResCurrentAmrwbPeakUsedCount OBJECT-TYPE
    SYNTAX          PerfCurrentCount
    MAX-ACCESS      read-only
    STATUS          current
    DESCRIPTION     
            "The current peak usage of type AMRWBiLBC DSP PAD."
    ::= { sonusSlotDspResCurrentEntry 45 }

sonusSlotDspResCurrentAmrwbAverageUsedCount OBJECT-TYPE
    SYNTAX          PerfCurrentCount
    MAX-ACCESS      read-only
    STATUS          current
    DESCRIPTION     
            "The current average usage of type AMRWB DSP PAD."
    ::= { sonusSlotDspResCurrentEntry 46 }

sonusSlotDspResCurrentAmrwbAverageAvailCount OBJECT-TYPE
    SYNTAX          PerfCurrentCount
    MAX-ACCESS      read-only
    STATUS          current
    DESCRIPTION     
            "The current average availability of type AMRWB DSP PAD."
    ::= { sonusSlotDspResCurrentEntry 47 }

sonusSlotDspResIntervalTable OBJECT-TYPE
    SYNTAX          SEQUENCE OF SonusSlotDspResIntervalEntry
    MAX-ACCESS      not-accessible
    STATUS          current
    DESCRIPTION     
            "The Sonus DSP Resource Interval table."
    ::= { sonusDspPadResStatisticsObjects 6 }

sonusSlotDspResIntervalEntry OBJECT-TYPE
    SYNTAX          SonusSlotDspResIntervalEntry
    MAX-ACCESS      not-accessible
    STATUS          current
    DESCRIPTION     
            "An entry in the Sonus DSP Resource Interval table."
    INDEX           { sonusSlotDspResIntervalShelfIndex, 
                      sonusSlotDspResIntervalSlotIndex, 
                      sonusSlotDspResIntervalNumber }
    ::= { sonusSlotDspResIntervalTable 1 }

SonusSlotDspResIntervalEntry ::=
    SEQUENCE {
        sonusSlotDspResIntervalShelfIndex SonusShelfIndex,
        sonusSlotDspResIntervalSlotIndex SonusSlotIndex,
        sonusSlotDspResIntervalNumber   Integer32,
        sonusSlotDspResIntervalTime     TimeTicks,
        sonusSlotDspResIntervalValidData TruthValue,
        sonusSlotDspResIntervalG711CircuitPeakUsedCount               PerfIntervalCount,
        sonusSlotDspResIntervalG711CircuitAverageUsedCount                  PerfIntervalCount,
        sonusSlotDspResIntervalG711CircuitAverageAvailCount                   PerfIntervalCount,
        sonusSlotDspResIntervalTonePeakUsedCount        PerfIntervalCount,
        sonusSlotDspResIntervalToneAverageUsedCount           PerfIntervalCount,
        sonusSlotDspResIntervalToneAverageAvailCount            PerfIntervalCount,
        sonusSlotDspResIntervalBridgePortPeakUsedCount              PerfIntervalCount,
        sonusSlotDspResIntervalBridgePortAverageUsedCount                 PerfIntervalCount,
        sonusSlotDspResIntervalBridgePortAverageAvailCount                  PerfIntervalCount,
        sonusSlotDspResIntervalG729PeakUsedCount        PerfIntervalCount,
        sonusSlotDspResIntervalG729AverageUsedCount           PerfIntervalCount,
        sonusSlotDspResIntervalG729AverageAvailCount            PerfIntervalCount,
        sonusSlotDspResIntervalG726PeakUsedCount        PerfIntervalCount,
        sonusSlotDspResIntervalG726AverageUsedCount           PerfIntervalCount,
        sonusSlotDspResIntervalG726AverageAvailCount            PerfIntervalCount,
        sonusSlotDspResIntervalG723PeakUsedCount        PerfIntervalCount,
        sonusSlotDspResIntervalG723AverageUsedCount           PerfIntervalCount,
        sonusSlotDspResIntervalG723AverageAvailCount            PerfIntervalCount,
        sonusSlotDspResIntervalG711PacketPeakUsedCount              PerfIntervalCount,
        sonusSlotDspResIntervalG711PacketAverageUsedCount                 PerfIntervalCount,
        sonusSlotDspResIntervalG711PacketAverageAvailCount                  PerfIntervalCount,
        sonusSlotDspResIntervalT38PeakUsedCount       PerfIntervalCount,
        sonusSlotDspResIntervalT38AverageUsedCount          PerfIntervalCount,
        sonusSlotDspResIntervalT38AverageAvailCount           PerfIntervalCount,
        sonusSlotDspResIntervalEvrcPeakUsedCount        PerfIntervalCount,
        sonusSlotDspResIntervalEvrcAverageUsedCount           PerfIntervalCount,
        sonusSlotDspResIntervalEvrcAverageAvailCount            PerfIntervalCount,
        sonusSlotDspResIntervalGsmPeakUsedCount       PerfIntervalCount,
        sonusSlotDspResIntervalGsmAverageUsedCount          PerfIntervalCount,
        sonusSlotDspResIntervalGsmAverageAvailCount           PerfIntervalCount,
        sonusSlotDspResIntervalT38EcmPeakUsedCount          PerfIntervalCount,
        sonusSlotDspResIntervalT38EcmAverageUsedCount             PerfIntervalCount,
        sonusSlotDspResIntervalT38EcmAverageAvailCount              PerfIntervalCount,
        sonusSlotDspResIntervalEvrcb0PeakUsedCount          PerfIntervalCount,
        sonusSlotDspResIntervalEvrcb0AverageUsedCount             PerfIntervalCount,
        sonusSlotDspResIntervalEvrcb0AverageAvailCount              PerfIntervalCount,
        sonusSlotDspResIntervaliLBCPeakUsedCount        PerfIntervalCount,
        sonusSlotDspResIntervaliLBCAverageUsedCount           PerfIntervalCount,
        sonusSlotDspResIntervaliLBCAverageAvailCount            PerfIntervalCount,
        sonusSlotDspResIntervalG722PeakUsedCount        PerfIntervalCount,
        sonusSlotDspResIntervalG722AverageUsedCount           PerfIntervalCount,
        sonusSlotDspResIntervalG722AverageAvailCount            PerfIntervalCount,
        sonusSlotDspResIntervalAmrwbPeakUsedCount         PerfIntervalCount,
        sonusSlotDspResIntervalAmrwbAverageUsedCount            PerfIntervalCount,
        sonusSlotDspResIntervalAmrwbAverageAvailCount             PerfIntervalCount
    }

sonusSlotDspResIntervalShelfIndex OBJECT-TYPE
    SYNTAX          SonusShelfIndex
    MAX-ACCESS      read-only
    STATUS          current
    DESCRIPTION     
            "The index into the sonusSlotDspResIntervalTable."
    ::= { sonusSlotDspResIntervalEntry 1 }

sonusSlotDspResIntervalSlotIndex OBJECT-TYPE
    SYNTAX          SonusSlotIndex
    MAX-ACCESS      read-only
    STATUS          current
    DESCRIPTION     
            "Identifies the target card."
    ::= { sonusSlotDspResIntervalEntry 2 }

sonusSlotDspResIntervalNumber OBJECT-TYPE
    SYNTAX          Integer32 (1..288)
    MAX-ACCESS      not-accessible
    STATUS          current
    DESCRIPTION     
            "A number between 1 and 288, which identifies the
             interval for which the set of statistics is available.
             The interval identified by 1 is the most recently
             completed interval, and the interval identified
             by N is the interval immediately preceding the
             one identified by N-1."
    ::= { sonusSlotDspResIntervalEntry 3 }

sonusSlotDspResIntervalTime OBJECT-TYPE
    SYNTAX          TimeTicks
    MAX-ACCESS      read-only
    STATUS          current
    DESCRIPTION     
            "This variable contains the end of interval time stamp for the specified interval."
    ::= { sonusSlotDspResIntervalEntry 4 }

sonusSlotDspResIntervalValidData OBJECT-TYPE
    SYNTAX          TruthValue
    MAX-ACCESS      read-only
    STATUS          current
    DESCRIPTION     
            "This variable indicates if the data for this interval is valid."
    ::= { sonusSlotDspResIntervalEntry 5 }

sonusSlotDspResIntervalG711CircuitPeakUsedCount OBJECT-TYPE
    SYNTAX          PerfIntervalCount
    MAX-ACCESS      read-only
    STATUS          current
    DESCRIPTION     
            "The peak usage of type G711 Circuit DSP pad during an interval time."
    ::= { sonusSlotDspResIntervalEntry 6 }

sonusSlotDspResIntervalG711CircuitAverageUsedCount OBJECT-TYPE
    SYNTAX          PerfIntervalCount
    MAX-ACCESS      read-only
    STATUS          current
    DESCRIPTION     
            "The the average usage of type G711Circuit DSP pad during an interval time."
    ::= { sonusSlotDspResIntervalEntry 7 }

sonusSlotDspResIntervalG711CircuitAverageAvailCount OBJECT-TYPE
    SYNTAX          PerfIntervalCount
    MAX-ACCESS      read-only
    STATUS          current
    DESCRIPTION     
            "The average availability of type G711Circuit DSP pad during an interval time."
    ::= { sonusSlotDspResIntervalEntry 8 }

sonusSlotDspResIntervalTonePeakUsedCount OBJECT-TYPE
    SYNTAX          PerfIntervalCount
    MAX-ACCESS      read-only
    STATUS          current
    DESCRIPTION     
            "The Interval number of Peak usage of type Tone DSP pad during an interval time."
    ::= { sonusSlotDspResIntervalEntry 9 }

sonusSlotDspResIntervalToneAverageUsedCount OBJECT-TYPE
    SYNTAX          PerfIntervalCount
    MAX-ACCESS      read-only
    STATUS          current
    DESCRIPTION     
            "The average usage of type Tone DSP pad during an interval time."
    ::= { sonusSlotDspResIntervalEntry 10 }

sonusSlotDspResIntervalToneAverageAvailCount OBJECT-TYPE
    SYNTAX          PerfIntervalCount
    MAX-ACCESS      read-only
    STATUS          current
    DESCRIPTION     
            "The average availability of type Tone DSP pad during an interval time."
    ::= { sonusSlotDspResIntervalEntry 11 }

sonusSlotDspResIntervalBridgePortPeakUsedCount OBJECT-TYPE
    SYNTAX          PerfIntervalCount
    MAX-ACCESS      read-only
    STATUS          current
    DESCRIPTION     
            "The peak usage of type Bridge  Port DSP pad during an interval time."
    ::= { sonusSlotDspResIntervalEntry 12 }

sonusSlotDspResIntervalBridgePortAverageUsedCount OBJECT-TYPE
    SYNTAX          PerfIntervalCount
    MAX-ACCESS      read-only
    STATUS          current
    DESCRIPTION     
            "The average usage of type Bridge  Port DSP pad during an interval time."
    ::= { sonusSlotDspResIntervalEntry 13 }

sonusSlotDspResIntervalBridgePortAverageAvailCount OBJECT-TYPE
    SYNTAX          PerfIntervalCount
    MAX-ACCESS      read-only
    STATUS          current
    DESCRIPTION     
            "The average availability of type Bridge Port DSP pad during an interval time."
    ::= { sonusSlotDspResIntervalEntry 14 }

sonusSlotDspResIntervalG729PeakUsedCount OBJECT-TYPE
    SYNTAX          PerfIntervalCount
    MAX-ACCESS      read-only
    STATUS          current
    DESCRIPTION     
            "The peak usage of type G729 DSP pad during an interval time."
    ::= { sonusSlotDspResIntervalEntry 15 }

sonusSlotDspResIntervalG729AverageUsedCount OBJECT-TYPE
    SYNTAX          PerfIntervalCount
    MAX-ACCESS      read-only
    STATUS          current
    DESCRIPTION     
            "The average usage of type G729 DSP pad during an interval time."
    ::= { sonusSlotDspResIntervalEntry 16 }

sonusSlotDspResIntervalG729AverageAvailCount OBJECT-TYPE
    SYNTAX          PerfIntervalCount
    MAX-ACCESS      read-only
    STATUS          current
    DESCRIPTION     
            "The average availability of type G729 DSP pad during an interval time."
    ::= { sonusSlotDspResIntervalEntry 17 }

sonusSlotDspResIntervalG726PeakUsedCount OBJECT-TYPE
    SYNTAX          PerfIntervalCount
    MAX-ACCESS      read-only
    STATUS          current
    DESCRIPTION     
            "The Interval number of Peak usage of type G726 DSP pad during an interval time."
    ::= { sonusSlotDspResIntervalEntry 18 }

sonusSlotDspResIntervalG726AverageUsedCount OBJECT-TYPE
    SYNTAX          PerfIntervalCount
    MAX-ACCESS      read-only
    STATUS          current
    DESCRIPTION     
            "The average usage of type G726 DSP pad during an interval time."
    ::= { sonusSlotDspResIntervalEntry 19 }

sonusSlotDspResIntervalG726AverageAvailCount OBJECT-TYPE
    SYNTAX          PerfIntervalCount
    MAX-ACCESS      read-only
    STATUS          current
    DESCRIPTION     
            "The average availability of type G726 DSP pad during an interval time."
    ::= { sonusSlotDspResIntervalEntry 20 }

sonusSlotDspResIntervalG723PeakUsedCount OBJECT-TYPE
    SYNTAX          PerfIntervalCount
    MAX-ACCESS      read-only
    STATUS          current
    DESCRIPTION     
            "The peak usage of type G723 DSP pad during an interval time."
    ::= { sonusSlotDspResIntervalEntry 21 }

sonusSlotDspResIntervalG723AverageUsedCount OBJECT-TYPE
    SYNTAX          PerfIntervalCount
    MAX-ACCESS      read-only
    STATUS          current
    DESCRIPTION     
            "The average usage of type G723 DSP pad during an interval time."
    ::= { sonusSlotDspResIntervalEntry 22 }

sonusSlotDspResIntervalG723AverageAvailCount OBJECT-TYPE
    SYNTAX          PerfIntervalCount
    MAX-ACCESS      read-only
    STATUS          current
    DESCRIPTION     
            "The average availability of type G723 DSP pad during an interval time."
    ::= { sonusSlotDspResIntervalEntry 23 }

sonusSlotDspResIntervalG711PacketPeakUsedCount OBJECT-TYPE
    SYNTAX          PerfIntervalCount
    MAX-ACCESS      read-only
    STATUS          current
    DESCRIPTION     
            "The peak usage of type G711Packet DSP pad during an interval time."
    ::= { sonusSlotDspResIntervalEntry 24 }

sonusSlotDspResIntervalG711PacketAverageUsedCount OBJECT-TYPE
    SYNTAX          PerfIntervalCount
    MAX-ACCESS      read-only
    STATUS          current
    DESCRIPTION     
            "The average usage of type G711Packet DSP pad during an interval time."
    ::= { sonusSlotDspResIntervalEntry 25 }

sonusSlotDspResIntervalG711PacketAverageAvailCount OBJECT-TYPE
    SYNTAX          PerfIntervalCount
    MAX-ACCESS      read-only
    STATUS          current
    DESCRIPTION     
            "The average availability of type G711Packet DSP pad during an interval time."
    ::= { sonusSlotDspResIntervalEntry 26 }

sonusSlotDspResIntervalT38PeakUsedCount OBJECT-TYPE
    SYNTAX          PerfIntervalCount
    MAX-ACCESS      read-only
    STATUS          current
    DESCRIPTION     
            "The peak usage of type T38 DSP pad during an interval time."
    ::= { sonusSlotDspResIntervalEntry 27 }

sonusSlotDspResIntervalT38AverageUsedCount OBJECT-TYPE
    SYNTAX          PerfIntervalCount
    MAX-ACCESS      read-only
    STATUS          current
    DESCRIPTION     
            "The average usage of type T38 DSP pad during an interval time."
    ::= { sonusSlotDspResIntervalEntry 28 }

sonusSlotDspResIntervalT38AverageAvailCount OBJECT-TYPE
    SYNTAX          PerfIntervalCount
    MAX-ACCESS      read-only
    STATUS          current
    DESCRIPTION     
            "The average availability of type T38 DSP pad during an interval time."
    ::= { sonusSlotDspResIntervalEntry 29 }

sonusSlotDspResIntervalEvrcPeakUsedCount OBJECT-TYPE
    SYNTAX          PerfIntervalCount
    MAX-ACCESS      read-only
    STATUS          current
    DESCRIPTION     
            "The peak usage of type EVRC DSP pad during an interval time."
    ::= { sonusSlotDspResIntervalEntry 30 }

sonusSlotDspResIntervalEvrcAverageUsedCount OBJECT-TYPE
    SYNTAX          PerfIntervalCount
    MAX-ACCESS      read-only
    STATUS          current
    DESCRIPTION     
            "The average usage of type EVRC DSP pad during an interval time."
    ::= { sonusSlotDspResIntervalEntry 31 }

sonusSlotDspResIntervalEvrcAverageAvailCount OBJECT-TYPE
    SYNTAX          PerfIntervalCount
    MAX-ACCESS      read-only
    STATUS          current
    DESCRIPTION     
            "The average availability of type EVRC DSP pad during an interval time."
    ::= { sonusSlotDspResIntervalEntry 32 }

sonusSlotDspResIntervalGsmPeakUsedCount OBJECT-TYPE
    SYNTAX          PerfIntervalCount
    MAX-ACCESS      read-only
    STATUS          current
    DESCRIPTION     
            "The peak usage of type GSM DSP pad during an interval time."
    ::= { sonusSlotDspResIntervalEntry 33 }

sonusSlotDspResIntervalGsmAverageUsedCount OBJECT-TYPE
    SYNTAX          PerfIntervalCount
    MAX-ACCESS      read-only
    STATUS          current
    DESCRIPTION     
            "The average usage of type GSM DSP pad during an interval time."
    ::= { sonusSlotDspResIntervalEntry 34 }

sonusSlotDspResIntervalGsmAverageAvailCount OBJECT-TYPE
    SYNTAX          PerfIntervalCount
    MAX-ACCESS      read-only
    STATUS          current
    DESCRIPTION     
            "The average availability of type GSM DSP pad during an interval time."
    ::= { sonusSlotDspResIntervalEntry 35 }

sonusSlotDspResIntervalT38EcmPeakUsedCount OBJECT-TYPE
    SYNTAX          PerfIntervalCount
    MAX-ACCESS      read-only
    STATUS          current
    DESCRIPTION     
            "The peak usage of type T38 ECM capable DSP pad during an interval time."
    ::= { sonusSlotDspResIntervalEntry 36 }

sonusSlotDspResIntervalT38EcmAverageUsedCount OBJECT-TYPE
    SYNTAX          PerfIntervalCount
    MAX-ACCESS      read-only
    STATUS          current
    DESCRIPTION     
            "The average usage of type T38 ECM capable DSP pad during an interval time."
    ::= { sonusSlotDspResIntervalEntry 37 }

sonusSlotDspResIntervalT38EcmAverageAvailCount OBJECT-TYPE
    SYNTAX          PerfIntervalCount
    MAX-ACCESS      read-only
    STATUS          current
    DESCRIPTION     
            "The average availability of type T38 ECM capable DSP pad during an interval time."
    ::= { sonusSlotDspResIntervalEntry 38 }

sonusSlotDspResIntervalEvrcb0PeakUsedCount OBJECT-TYPE
    SYNTAX          PerfIntervalCount
    MAX-ACCESS      read-only
    STATUS          current
    DESCRIPTION     
            "The peak usage of type EVRCB0 DSP pad during an interval time."
    ::= { sonusSlotDspResIntervalEntry 39 }

sonusSlotDspResIntervalEvrcb0AverageUsedCount OBJECT-TYPE
    SYNTAX          PerfIntervalCount
    MAX-ACCESS      read-only
    STATUS          current
    DESCRIPTION     
            "The average usage of type EVRCB0 DSP pad during an interval time."
    ::= { sonusSlotDspResIntervalEntry 40 }

sonusSlotDspResIntervalEvrcb0AverageAvailCount OBJECT-TYPE
    SYNTAX          PerfIntervalCount
    MAX-ACCESS      read-only
    STATUS          current
    DESCRIPTION     
            "The average availability of type EVRCB0 DSP pad during an interval time."
    ::= { sonusSlotDspResIntervalEntry 41 }

sonusSlotDspResIntervaliLBCPeakUsedCount OBJECT-TYPE
    SYNTAX          PerfIntervalCount
    MAX-ACCESS      read-only
    STATUS          current
    DESCRIPTION     
            "The peak usage of type iLBC DSP pad during an interval time."
    ::= { sonusSlotDspResIntervalEntry 42 }

sonusSlotDspResIntervaliLBCAverageUsedCount OBJECT-TYPE
    SYNTAX          PerfIntervalCount
    MAX-ACCESS      read-only
    STATUS          current
    DESCRIPTION     
            "The average usage of type iLBC DSP pad during an interval time."
    ::= { sonusSlotDspResIntervalEntry 43 }

sonusSlotDspResIntervaliLBCAverageAvailCount OBJECT-TYPE
    SYNTAX          PerfIntervalCount
    MAX-ACCESS      read-only
    STATUS          current
    DESCRIPTION     
            "The average availability of type iLBC DSP pad during an interval time."
    ::= { sonusSlotDspResIntervalEntry 44 }

sonusSlotDspResIntervalG722PeakUsedCount OBJECT-TYPE
    SYNTAX          PerfIntervalCount
    MAX-ACCESS      read-only
    STATUS          current
    DESCRIPTION     
            "The peak usage of type G722 DSP pad during an interval time."
    ::= { sonusSlotDspResIntervalEntry 45 }

sonusSlotDspResIntervalG722AverageUsedCount OBJECT-TYPE
    SYNTAX          PerfIntervalCount
    MAX-ACCESS      read-only
    STATUS          current
    DESCRIPTION     
            "The average usage of type G722 DSP pad during an interval time."
    ::= { sonusSlotDspResIntervalEntry 46 }

sonusSlotDspResIntervalG722AverageAvailCount OBJECT-TYPE
    SYNTAX          PerfIntervalCount
    MAX-ACCESS      read-only
    STATUS          current
    DESCRIPTION     
            "The average availability of type G722 DSP pad during an interval time."
    ::= { sonusSlotDspResIntervalEntry 47 }

sonusSlotDspResIntervalAmrwbPeakUsedCount OBJECT-TYPE
    SYNTAX          PerfIntervalCount
    MAX-ACCESS      read-only
    STATUS          current
    DESCRIPTION     
            "The peak usage of type AMRWB DSP pad during an interval time."
    ::= { sonusSlotDspResIntervalEntry 48 }

sonusSlotDspResIntervalAmrwbAverageUsedCount OBJECT-TYPE
    SYNTAX          PerfIntervalCount
    MAX-ACCESS      read-only
    STATUS          current
    DESCRIPTION     
            "The average usage of type AMRWB DSP pad during an interval time."
    ::= { sonusSlotDspResIntervalEntry 49 }

sonusSlotDspResIntervalAmrwbAverageAvailCount OBJECT-TYPE
    SYNTAX          PerfIntervalCount
    MAX-ACCESS      read-only
    STATUS          current
    DESCRIPTION     
            "The average availability of type AMRWB DSP pad during an interval time."
    ::= { sonusSlotDspResIntervalEntry 50 }

sonusIgStatisticsObjects OBJECT IDENTIFIER
    ::= { sonusPerformanceStatisticsObjects 9 }

sonusIgCallCurrentTable OBJECT-TYPE
    SYNTAX          SEQUENCE OF SonusIgCallCurrentEntry
    MAX-ACCESS      not-accessible
    STATUS          current
    DESCRIPTION     
            "The Sonus GR303 Interface Group Call Statistics Current table."
    ::= { sonusIgStatisticsObjects 1 }

sonusIgCallCurrentEntry OBJECT-TYPE
    SYNTAX          SonusIgCallCurrentEntry
    MAX-ACCESS      not-accessible
    STATUS          current
    DESCRIPTION     
            "An entry in the Sonus Interface Group Call Statistics
             Current table."
    INDEX           { sonusIgCallCurrentIgIndex }
    ::= { sonusIgCallCurrentTable 1 }

SonusIgCallCurrentEntry ::=
    SEQUENCE {
        sonusIgCallCurrentIgIndex       Integer32,
        sonusIgCallCurrentTrafficHourlyProratedCallSeconds                  PerfCurrentCount,
        sonusIgCallCurrentTrafficPercentageUtilizationOfPeakCapacity                            PerfCurrentCount,
        sonusIgCallCurrentTrafficMaximumSimultaneousAssignments2Ds0                           PerfCurrentCount,
        sonusIgCallCurrentCc27DestOosShoweringLine          PerfCurrentCount,
        sonusIgCallCurrentCc27DestOosAdminOos     PerfCurrentCount,
        sonusIgCallCurrentCc27DestOosPsc PerfCurrentCount,
        sonusIgCallCurrentCc34IdtChanUnavail    PerfCurrentCount,
        sonusIgCallCurrentCc34RdtChanUnavail    PerfCurrentCount,
        sonusIgCallCurrentCc41IdtTempFailure    PerfCurrentCount,
        sonusIgCallCurrentCc41RdtTempFailure    PerfCurrentCount,
        sonusIgCallCurrentCc44LineUnitUnavail     PerfCurrentCount,
        sonusIgCallCurrentCc47RingFailure PerfCurrentCount,
        sonusIgCallCurrentCc81IdtInvalidCallRef       PerfCurrentCount,
        sonusIgCallCurrentCc81RdtInvalidCallRef       PerfCurrentCount,
        sonusIgCallCurrentCcOtherIdt    PerfCurrentCount,
        sonusIgCallCurrentCcOtherRdt    PerfCurrentCount,
        sonusIgCallCurrentTimeAllChanBusy PerfCurrentCount,
        sonusIgCallCurrentNumIngressCalls PerfCurrentCount,
        sonusIgCallCurrentNumEgressCalls PerfCurrentCount,
        sonusIgCallCurrentIngressAssignments2Ds0Port1             PerfCurrentCount,
        sonusIgCallCurrentEgressAssignments2Ds0Port1            PerfCurrentCount,
        sonusIgCallCurrentIngressAssignments2Ds0Port2             PerfCurrentCount,
        sonusIgCallCurrentEgressAssignments2Ds0Port2            PerfCurrentCount,
        sonusIgCallCurrentIngressAssignments2Ds0Port3             PerfCurrentCount,
        sonusIgCallCurrentEgressAssignments2Ds0Port3            PerfCurrentCount,
        sonusIgCallCurrentIngressAssignments2Ds0Port4             PerfCurrentCount,
        sonusIgCallCurrentEgressAssignments2Ds0Port4            PerfCurrentCount,
        sonusIgCallCurrentIngressAssignments2Ds0Port5             PerfCurrentCount,
        sonusIgCallCurrentEgressAssignments2Ds0Port5            PerfCurrentCount,
        sonusIgCallCurrentIngressAssignments2Ds0Port6             PerfCurrentCount,
        sonusIgCallCurrentEgressAssignments2Ds0Port6            PerfCurrentCount,
        sonusIgCallCurrentIngressAssignments2Ds0Port7             PerfCurrentCount,
        sonusIgCallCurrentEgressAssignments2Ds0Port7            PerfCurrentCount,
        sonusIgCallCurrentIngressAssignments2Ds0Port8             PerfCurrentCount,
        sonusIgCallCurrentEgressAssignments2Ds0Port8            PerfCurrentCount,
        sonusIgCallCurrentIngressAssignments2Ds0Port9             PerfCurrentCount,
        sonusIgCallCurrentEgressAssignments2Ds0Port9            PerfCurrentCount,
        sonusIgCallCurrentIngressAssignments2Ds0Port10              PerfCurrentCount,
        sonusIgCallCurrentEgressAssignments2Ds0Port10             PerfCurrentCount,
        sonusIgCallCurrentIngressAssignments2Ds0Port11              PerfCurrentCount,
        sonusIgCallCurrentEgressAssignments2Ds0Port11             PerfCurrentCount,
        sonusIgCallCurrentIngressAssignments2Ds0Port12              PerfCurrentCount,
        sonusIgCallCurrentEgressAssignments2Ds0Port12             PerfCurrentCount,
        sonusIgCallCurrentIngressAssignments2Ds0Port13              PerfCurrentCount,
        sonusIgCallCurrentEgressAssignments2Ds0Port13             PerfCurrentCount,
        sonusIgCallCurrentIngressAssignments2Ds0Port14              PerfCurrentCount,
        sonusIgCallCurrentEgressAssignments2Ds0Port14             PerfCurrentCount,
        sonusIgCallCurrentIngressAssignments2Ds0Port15              PerfCurrentCount,
        sonusIgCallCurrentEgressAssignments2Ds0Port15             PerfCurrentCount,
        sonusIgCallCurrentIngressAssignments2Ds0Port16              PerfCurrentCount,
        sonusIgCallCurrentEgressAssignments2Ds0Port16             PerfCurrentCount,
        sonusIgCallCurrentIngressAssignments2Ds0Port17              PerfCurrentCount,
        sonusIgCallCurrentEgressAssignments2Ds0Port17             PerfCurrentCount,
        sonusIgCallCurrentIngressAssignments2Ds0Port18              PerfCurrentCount,
        sonusIgCallCurrentEgressAssignments2Ds0Port18             PerfCurrentCount,
        sonusIgCallCurrentIngressAssignments2Ds0Port19              PerfCurrentCount,
        sonusIgCallCurrentEgressAssignments2Ds0Port19             PerfCurrentCount,
        sonusIgCallCurrentIngressAssignments2Ds0Port20              PerfCurrentCount,
        sonusIgCallCurrentEgressAssignments2Ds0Port20             PerfCurrentCount,
        sonusIgCallCurrentIngressAssignments2Ds0Port21              PerfCurrentCount,
        sonusIgCallCurrentEgressAssignments2Ds0Port21             PerfCurrentCount,
        sonusIgCallCurrentIngressAssignments2Ds0Port22              PerfCurrentCount,
        sonusIgCallCurrentEgressAssignments2Ds0Port22             PerfCurrentCount,
        sonusIgCallCurrentIngressAssignments2Ds0Port23              PerfCurrentCount,
        sonusIgCallCurrentEgressAssignments2Ds0Port23             PerfCurrentCount,
        sonusIgCallCurrentIngressAssignments2Ds0Port24              PerfCurrentCount,
        sonusIgCallCurrentEgressAssignments2Ds0Port24             PerfCurrentCount,
        sonusIgCallCurrentIngressAssignments2Ds0Port25              PerfCurrentCount,
        sonusIgCallCurrentEgressAssignments2Ds0Port25             PerfCurrentCount,
        sonusIgCallCurrentIngressAssignments2Ds0Port26              PerfCurrentCount,
        sonusIgCallCurrentEgressAssignments2Ds0Port26             PerfCurrentCount,
        sonusIgCallCurrentIngressAssignments2Ds0Port27              PerfCurrentCount,
        sonusIgCallCurrentEgressAssignments2Ds0Port27             PerfCurrentCount,
        sonusIgCallCurrentIngressAssignments2Ds0Port28              PerfCurrentCount,
        sonusIgCallCurrentEgressAssignments2Ds0Port28             PerfCurrentCount,
        sonusIgCallCurrentCc27RdtDestOos PerfCurrentCount,
        sonusIgCallCurrentNumIngressCallsBlocked        PerfCurrentCount,
        sonusIgCallCurrentNumEgressCallsBlocked       PerfCurrentCount,
        sonusIgCallCurrentCc16IdtNormalClearing       PerfCurrentCount,
        sonusIgCallCurrentCc16RdtNormalClearing       PerfCurrentCount
    }

sonusIgCallCurrentIgIndex OBJECT-TYPE
    SYNTAX          Integer32
    MAX-ACCESS      read-only
    STATUS          current
    DESCRIPTION     
            "The index of the GR303 Interface Group."
    ::= { sonusIgCallCurrentEntry 1 }

sonusIgCallCurrentTrafficHourlyProratedCallSeconds OBJECT-TYPE
    SYNTAX          PerfCurrentCount
    MAX-ACCESS      read-only
    STATUS          current
    DESCRIPTION     
            "The traffic in Call Seconds on this GR303 Interface Group
             prorated from the current interval to a hourly basis."
    ::= { sonusIgCallCurrentEntry 2 }

sonusIgCallCurrentTrafficPercentageUtilizationOfPeakCapacity OBJECT-TYPE
    SYNTAX          PerfCurrentCount
    MAX-ACCESS      read-only
    STATUS          current
    DESCRIPTION     
            "The percentage utilization of this GR303 Interface Group
             relative to its peak capacity during the current interval."
    ::= { sonusIgCallCurrentEntry 3 }

sonusIgCallCurrentTrafficMaximumSimultaneousAssignments2Ds0 OBJECT-TYPE
    SYNTAX          PerfCurrentCount
    MAX-ACCESS      read-only
    STATUS          current
    DESCRIPTION     
            "The maximum number of DS0 channels in use simultaneously
             on this GR303 Interface Group during the current interval."
    ::= { sonusIgCallCurrentEntry 4 }

sonusIgCallCurrentCc27DestOosShoweringLine OBJECT-TYPE
    SYNTAX          PerfCurrentCount
    MAX-ACCESS      read-only
    STATUS          current
    DESCRIPTION     
            "The number of calls cleared by IDT as destination out-of-service (cause code 27)
             due to a showering line condition."
    ::= { sonusIgCallCurrentEntry 5 }

sonusIgCallCurrentCc27DestOosAdminOos OBJECT-TYPE
    SYNTAX          PerfCurrentCount
    MAX-ACCESS      read-only
    STATUS          current
    DESCRIPTION     
            "The number of calls cleared by IDT as destination out-of-service (cause code 27)
             due to administrative out-of-service."
    ::= { sonusIgCallCurrentEntry 6 }

sonusIgCallCurrentCc27DestOosPsc OBJECT-TYPE
    SYNTAX          PerfCurrentCount
    MAX-ACCESS      read-only
    STATUS          current
    DESCRIPTION     
            "The number of calls cleared by IDT as destination out-of-service (cause code 27)
             due to a permanent signaling condition."
    ::= { sonusIgCallCurrentEntry 7 }

sonusIgCallCurrentCc34IdtChanUnavail OBJECT-TYPE
    SYNTAX          PerfCurrentCount
    MAX-ACCESS      read-only
    STATUS          current
    DESCRIPTION     
            "The number of calls cleared by IDT as channel unavailable (cause code 34)."
    ::= { sonusIgCallCurrentEntry 8 }

sonusIgCallCurrentCc34RdtChanUnavail OBJECT-TYPE
    SYNTAX          PerfCurrentCount
    MAX-ACCESS      read-only
    STATUS          current
    DESCRIPTION     
            "The number of calls cleared by RDT as channel unavailable (cause code 34)."
    ::= { sonusIgCallCurrentEntry 9 }

sonusIgCallCurrentCc41IdtTempFailure OBJECT-TYPE
    SYNTAX          PerfCurrentCount
    MAX-ACCESS      read-only
    STATUS          current
    DESCRIPTION     
            "The number of calls cleared by IDT as temporay failure (cause code 41)."
    ::= { sonusIgCallCurrentEntry 10 }

sonusIgCallCurrentCc41RdtTempFailure OBJECT-TYPE
    SYNTAX          PerfCurrentCount
    MAX-ACCESS      read-only
    STATUS          current
    DESCRIPTION     
            "The number of calls cleared by RDT as temporay failure (cause code 41)."
    ::= { sonusIgCallCurrentEntry 11 }

sonusIgCallCurrentCc44LineUnitUnavail OBJECT-TYPE
    SYNTAX          PerfCurrentCount
    MAX-ACCESS      read-only
    STATUS          current
    DESCRIPTION     
            "The number of calls cleared by RDT as line unit unavailable (cause code 44)."
    ::= { sonusIgCallCurrentEntry 12 }

sonusIgCallCurrentCc47RingFailure OBJECT-TYPE
    SYNTAX          PerfCurrentCount
    MAX-ACCESS      read-only
    STATUS          current
    DESCRIPTION     
            "The number of calls cleared by RDT as ring failure (cause code 47)."
    ::= { sonusIgCallCurrentEntry 13 }

sonusIgCallCurrentCc81IdtInvalidCallRef OBJECT-TYPE
    SYNTAX          PerfCurrentCount
    MAX-ACCESS      read-only
    STATUS          current
    DESCRIPTION     
            "The number of calls cleared by IDT as invalid call reference (cause code 81)."
    ::= { sonusIgCallCurrentEntry 14 }

sonusIgCallCurrentCc81RdtInvalidCallRef OBJECT-TYPE
    SYNTAX          PerfCurrentCount
    MAX-ACCESS      read-only
    STATUS          current
    DESCRIPTION     
            "The number of calls cleared by RDT as invalid call reference (cause code 81)."
    ::= { sonusIgCallCurrentEntry 15 }

sonusIgCallCurrentCcOtherIdt OBJECT-TYPE
    SYNTAX          PerfCurrentCount
    MAX-ACCESS      read-only
    STATUS          current
    DESCRIPTION     
            "The number of calls cleared by IDT for other reasons (cause code none of the above)."
    ::= { sonusIgCallCurrentEntry 16 }

sonusIgCallCurrentCcOtherRdt OBJECT-TYPE
    SYNTAX          PerfCurrentCount
    MAX-ACCESS      read-only
    STATUS          current
    DESCRIPTION     
            "The number of calls cleared by RDT for other reasons (cause code none of the above)."
    ::= { sonusIgCallCurrentEntry 17 }

sonusIgCallCurrentTimeAllChanBusy OBJECT-TYPE
    SYNTAX          PerfCurrentCount
    MAX-ACCESS      read-only
    STATUS          current
    DESCRIPTION     
            "The length of time (seconds) all available DS0 channels of this
             GR303 Interface Group were busy during the current interval.
             Any additional calls would have been refused."
    ::= { sonusIgCallCurrentEntry 18 }

sonusIgCallCurrentNumIngressCalls OBJECT-TYPE
    SYNTAX          PerfCurrentCount
    MAX-ACCESS      read-only
    STATUS          current
    DESCRIPTION     
            "The number of ingress assignments to DS0 channels on this GR303 Interface Group."
    ::= { sonusIgCallCurrentEntry 19 }

sonusIgCallCurrentNumEgressCalls OBJECT-TYPE
    SYNTAX          PerfCurrentCount
    MAX-ACCESS      read-only
    STATUS          current
    DESCRIPTION     
            "The number of egress assignments to DS0 channels on this GR303 Interface Group."
    ::= { sonusIgCallCurrentEntry 20 }

sonusIgCallCurrentIngressAssignments2Ds0Port1 OBJECT-TYPE
    SYNTAX          PerfCurrentCount
    MAX-ACCESS      read-only
    STATUS          current
    DESCRIPTION     
            "The number of ingress assignments to a DS0 channel on logical DS1 number 1."
    ::= { sonusIgCallCurrentEntry 21 }

sonusIgCallCurrentEgressAssignments2Ds0Port1 OBJECT-TYPE
    SYNTAX          PerfCurrentCount
    MAX-ACCESS      read-only
    STATUS          current
    DESCRIPTION     
            "The number of egress assignments to a DS0 channel on logical DS1 number 1."
    ::= { sonusIgCallCurrentEntry 22 }

sonusIgCallCurrentIngressAssignments2Ds0Port2 OBJECT-TYPE
    SYNTAX          PerfCurrentCount
    MAX-ACCESS      read-only
    STATUS          current
    DESCRIPTION     
            "The number of ingress assignments to a DS0 channel on logical DS1 number 2."
    ::= { sonusIgCallCurrentEntry 23 }

sonusIgCallCurrentEgressAssignments2Ds0Port2 OBJECT-TYPE
    SYNTAX          PerfCurrentCount
    MAX-ACCESS      read-only
    STATUS          current
    DESCRIPTION     
            "The number of egress assignments to a DS0 channel on logical DS1 number 2."
    ::= { sonusIgCallCurrentEntry 24 }

sonusIgCallCurrentIngressAssignments2Ds0Port3 OBJECT-TYPE
    SYNTAX          PerfCurrentCount
    MAX-ACCESS      read-only
    STATUS          current
    DESCRIPTION     
            "The number of ingress assignments to a DS0 channel on logical DS1 number 3."
    ::= { sonusIgCallCurrentEntry 25 }

sonusIgCallCurrentEgressAssignments2Ds0Port3 OBJECT-TYPE
    SYNTAX          PerfCurrentCount
    MAX-ACCESS      read-only
    STATUS          current
    DESCRIPTION     
            "The number of egress assignments to a DS0 channel on logical DS1 number 3."
    ::= { sonusIgCallCurrentEntry 26 }

sonusIgCallCurrentIngressAssignments2Ds0Port4 OBJECT-TYPE
    SYNTAX          PerfCurrentCount
    MAX-ACCESS      read-only
    STATUS          current
    DESCRIPTION     
            "The number of ingress assignments to a DS0 channel on logical DS1 number 4."
    ::= { sonusIgCallCurrentEntry 27 }

sonusIgCallCurrentEgressAssignments2Ds0Port4 OBJECT-TYPE
    SYNTAX          PerfCurrentCount
    MAX-ACCESS      read-only
    STATUS          current
    DESCRIPTION     
            "The number of egress assignments to a DS0 channel on logical DS1 number 4."
    ::= { sonusIgCallCurrentEntry 28 }

sonusIgCallCurrentIngressAssignments2Ds0Port5 OBJECT-TYPE
    SYNTAX          PerfCurrentCount
    MAX-ACCESS      read-only
    STATUS          current
    DESCRIPTION     
            "The number of ingress assignments to a DS0 channel on logical DS1 number 5."
    ::= { sonusIgCallCurrentEntry 29 }

sonusIgCallCurrentEgressAssignments2Ds0Port5 OBJECT-TYPE
    SYNTAX          PerfCurrentCount
    MAX-ACCESS      read-only
    STATUS          current
    DESCRIPTION     
            "The number of egress assignments to a DS0 channel on logical DS1 number 5."
    ::= { sonusIgCallCurrentEntry 30 }

sonusIgCallCurrentIngressAssignments2Ds0Port6 OBJECT-TYPE
    SYNTAX          PerfCurrentCount
    MAX-ACCESS      read-only
    STATUS          current
    DESCRIPTION     
            "The number of ingress assignments to a DS0 channel on logical DS1 number 6."
    ::= { sonusIgCallCurrentEntry 31 }

sonusIgCallCurrentEgressAssignments2Ds0Port6 OBJECT-TYPE
    SYNTAX          PerfCurrentCount
    MAX-ACCESS      read-only
    STATUS          current
    DESCRIPTION     
            "The number of egress assignments to a DS0 channel on logical DS1 number 6."
    ::= { sonusIgCallCurrentEntry 32 }

sonusIgCallCurrentIngressAssignments2Ds0Port7 OBJECT-TYPE
    SYNTAX          PerfCurrentCount
    MAX-ACCESS      read-only
    STATUS          current
    DESCRIPTION     
            "The number of ingress assignments to a DS0 channel on logical DS1 number 7."
    ::= { sonusIgCallCurrentEntry 33 }

sonusIgCallCurrentEgressAssignments2Ds0Port7 OBJECT-TYPE
    SYNTAX          PerfCurrentCount
    MAX-ACCESS      read-only
    STATUS          current
    DESCRIPTION     
            "The number of egress assignments to a DS0 channel on logical DS1 number 7."
    ::= { sonusIgCallCurrentEntry 34 }

sonusIgCallCurrentIngressAssignments2Ds0Port8 OBJECT-TYPE
    SYNTAX          PerfCurrentCount
    MAX-ACCESS      read-only
    STATUS          current
    DESCRIPTION     
            "The number of ingress assignments to a DS0 channel on logical DS1 number 8."
    ::= { sonusIgCallCurrentEntry 35 }

sonusIgCallCurrentEgressAssignments2Ds0Port8 OBJECT-TYPE
    SYNTAX          PerfCurrentCount
    MAX-ACCESS      read-only
    STATUS          current
    DESCRIPTION     
            "The number of egress assignments to a DS0 channel on logical DS1 number 8."
    ::= { sonusIgCallCurrentEntry 36 }

sonusIgCallCurrentIngressAssignments2Ds0Port9 OBJECT-TYPE
    SYNTAX          PerfCurrentCount
    MAX-ACCESS      read-only
    STATUS          current
    DESCRIPTION     
            "The number of ingress assignments to a DS0 channel on logical DS1 number 9."
    ::= { sonusIgCallCurrentEntry 37 }

sonusIgCallCurrentEgressAssignments2Ds0Port9 OBJECT-TYPE
    SYNTAX          PerfCurrentCount
    MAX-ACCESS      read-only
    STATUS          current
    DESCRIPTION     
            "The number of egress assignments to a DS0 channel on logical DS1 number 9."
    ::= { sonusIgCallCurrentEntry 38 }

sonusIgCallCurrentIngressAssignments2Ds0Port10 OBJECT-TYPE
    SYNTAX          PerfCurrentCount
    MAX-ACCESS      read-only
    STATUS          current
    DESCRIPTION     
            "The number of ingress assignments to a DS0 channel on logical DS1 number 10."
    ::= { sonusIgCallCurrentEntry 39 }

sonusIgCallCurrentEgressAssignments2Ds0Port10 OBJECT-TYPE
    SYNTAX          PerfCurrentCount
    MAX-ACCESS      read-only
    STATUS          current
    DESCRIPTION     
            "The number of egress assignments to a DS0 channel on logical DS1 number 10."
    ::= { sonusIgCallCurrentEntry 40 }

sonusIgCallCurrentIngressAssignments2Ds0Port11 OBJECT-TYPE
    SYNTAX          PerfCurrentCount
    MAX-ACCESS      read-only
    STATUS          current
    DESCRIPTION     
            "The number of ingress assignments to a DS0 channel on logical DS1 number 11."
    ::= { sonusIgCallCurrentEntry 41 }

sonusIgCallCurrentEgressAssignments2Ds0Port11 OBJECT-TYPE
    SYNTAX          PerfCurrentCount
    MAX-ACCESS      read-only
    STATUS          current
    DESCRIPTION     
            "The number of egress assignments to a DS0 channel on logical DS1 number 11."
    ::= { sonusIgCallCurrentEntry 42 }

sonusIgCallCurrentIngressAssignments2Ds0Port12 OBJECT-TYPE
    SYNTAX          PerfCurrentCount
    MAX-ACCESS      read-only
    STATUS          current
    DESCRIPTION     
            "The number of ingress assignments to a DS0 channel on logical DS1 number 12."
    ::= { sonusIgCallCurrentEntry 43 }

sonusIgCallCurrentEgressAssignments2Ds0Port12 OBJECT-TYPE
    SYNTAX          PerfCurrentCount
    MAX-ACCESS      read-only
    STATUS          current
    DESCRIPTION     
            "The number of egress assignments to a DS0 channel on logical DS1 number 12."
    ::= { sonusIgCallCurrentEntry 44 }

sonusIgCallCurrentIngressAssignments2Ds0Port13 OBJECT-TYPE
    SYNTAX          PerfCurrentCount
    MAX-ACCESS      read-only
    STATUS          current
    DESCRIPTION     
            "The number of ingress assignments to a DS0 channel on logical DS1 number 13."
    ::= { sonusIgCallCurrentEntry 45 }

sonusIgCallCurrentEgressAssignments2Ds0Port13 OBJECT-TYPE
    SYNTAX          PerfCurrentCount
    MAX-ACCESS      read-only
    STATUS          current
    DESCRIPTION     
            "The number of egress assignments to a DS0 channel on logical DS1 number 13."
    ::= { sonusIgCallCurrentEntry 46 }

sonusIgCallCurrentIngressAssignments2Ds0Port14 OBJECT-TYPE
    SYNTAX          PerfCurrentCount
    MAX-ACCESS      read-only
    STATUS          current
    DESCRIPTION     
            "The number of ingress assignments to a DS0 channel on logical DS1 number 14."
    ::= { sonusIgCallCurrentEntry 47 }

sonusIgCallCurrentEgressAssignments2Ds0Port14 OBJECT-TYPE
    SYNTAX          PerfCurrentCount
    MAX-ACCESS      read-only
    STATUS          current
    DESCRIPTION     
            "The number of egress assignments to a DS0 channel on logical DS1 number 14."
    ::= { sonusIgCallCurrentEntry 48 }

sonusIgCallCurrentIngressAssignments2Ds0Port15 OBJECT-TYPE
    SYNTAX          PerfCurrentCount
    MAX-ACCESS      read-only
    STATUS          current
    DESCRIPTION     
            "The number of ingress assignments to a DS0 channel on logical DS1 number 15."
    ::= { sonusIgCallCurrentEntry 49 }

sonusIgCallCurrentEgressAssignments2Ds0Port15 OBJECT-TYPE
    SYNTAX          PerfCurrentCount
    MAX-ACCESS      read-only
    STATUS          current
    DESCRIPTION     
            "The number of egress assignments to a DS0 channel on logical DS1 number 15."
    ::= { sonusIgCallCurrentEntry 50 }

sonusIgCallCurrentIngressAssignments2Ds0Port16 OBJECT-TYPE
    SYNTAX          PerfCurrentCount
    MAX-ACCESS      read-only
    STATUS          current
    DESCRIPTION     
            "The number of ingress assignments to a DS0 channel on logical DS1 number 16."
    ::= { sonusIgCallCurrentEntry 51 }

sonusIgCallCurrentEgressAssignments2Ds0Port16 OBJECT-TYPE
    SYNTAX          PerfCurrentCount
    MAX-ACCESS      read-only
    STATUS          current
    DESCRIPTION     
            "The number of egress assignments to a DS0 channel on logical DS1 number 16."
    ::= { sonusIgCallCurrentEntry 52 }

sonusIgCallCurrentIngressAssignments2Ds0Port17 OBJECT-TYPE
    SYNTAX          PerfCurrentCount
    MAX-ACCESS      read-only
    STATUS          current
    DESCRIPTION     
            "The number of ingress assignments to a DS0 channel on logical DS1 number 17."
    ::= { sonusIgCallCurrentEntry 53 }

sonusIgCallCurrentEgressAssignments2Ds0Port17 OBJECT-TYPE
    SYNTAX          PerfCurrentCount
    MAX-ACCESS      read-only
    STATUS          current
    DESCRIPTION     
            "The number of egress assignments to a DS0 channel on logical DS1 number 17."
    ::= { sonusIgCallCurrentEntry 54 }

sonusIgCallCurrentIngressAssignments2Ds0Port18 OBJECT-TYPE
    SYNTAX          PerfCurrentCount
    MAX-ACCESS      read-only
    STATUS          current
    DESCRIPTION     
            "The number of ingress assignments to a DS0 channel on logical DS1 number 18."
    ::= { sonusIgCallCurrentEntry 55 }

sonusIgCallCurrentEgressAssignments2Ds0Port18 OBJECT-TYPE
    SYNTAX          PerfCurrentCount
    MAX-ACCESS      read-only
    STATUS          current
    DESCRIPTION     
            "The number of egress assignments to a DS0 channel on logical DS1 number 18."
    ::= { sonusIgCallCurrentEntry 56 }

sonusIgCallCurrentIngressAssignments2Ds0Port19 OBJECT-TYPE
    SYNTAX          PerfCurrentCount
    MAX-ACCESS      read-only
    STATUS          current
    DESCRIPTION     
            "The number of ingress assignments to a DS0 channel on logical DS1 number 19."
    ::= { sonusIgCallCurrentEntry 57 }

sonusIgCallCurrentEgressAssignments2Ds0Port19 OBJECT-TYPE
    SYNTAX          PerfCurrentCount
    MAX-ACCESS      read-only
    STATUS          current
    DESCRIPTION     
            "The number of egress assignments to a DS0 channel on logical DS1 number 19."
    ::= { sonusIgCallCurrentEntry 58 }

sonusIgCallCurrentIngressAssignments2Ds0Port20 OBJECT-TYPE
    SYNTAX          PerfCurrentCount
    MAX-ACCESS      read-only
    STATUS          current
    DESCRIPTION     
            "The number of ingress assignments to a DS0 channel on logical DS1 number 20."
    ::= { sonusIgCallCurrentEntry 59 }

sonusIgCallCurrentEgressAssignments2Ds0Port20 OBJECT-TYPE
    SYNTAX          PerfCurrentCount
    MAX-ACCESS      read-only
    STATUS          current
    DESCRIPTION     
            "The number of egress assignments to a DS0 channel on logical DS1 number 20."
    ::= { sonusIgCallCurrentEntry 60 }

sonusIgCallCurrentIngressAssignments2Ds0Port21 OBJECT-TYPE
    SYNTAX          PerfCurrentCount
    MAX-ACCESS      read-only
    STATUS          current
    DESCRIPTION     
            "The number of ingress assignments to a DS0 channel on logical DS1 number 21."
    ::= { sonusIgCallCurrentEntry 61 }

sonusIgCallCurrentEgressAssignments2Ds0Port21 OBJECT-TYPE
    SYNTAX          PerfCurrentCount
    MAX-ACCESS      read-only
    STATUS          current
    DESCRIPTION     
            "The number of egress assignments to a DS0 channel on logical DS1 number 21."
    ::= { sonusIgCallCurrentEntry 62 }

sonusIgCallCurrentIngressAssignments2Ds0Port22 OBJECT-TYPE
    SYNTAX          PerfCurrentCount
    MAX-ACCESS      read-only
    STATUS          current
    DESCRIPTION     
            "The number of ingress assignments to a DS0 channel on logical DS1 number 22."
    ::= { sonusIgCallCurrentEntry 63 }

sonusIgCallCurrentEgressAssignments2Ds0Port22 OBJECT-TYPE
    SYNTAX          PerfCurrentCount
    MAX-ACCESS      read-only
    STATUS          current
    DESCRIPTION     
            "The number of egress assignments to a DS0 channel on logical DS1 number 22."
    ::= { sonusIgCallCurrentEntry 64 }

sonusIgCallCurrentIngressAssignments2Ds0Port23 OBJECT-TYPE
    SYNTAX          PerfCurrentCount
    MAX-ACCESS      read-only
    STATUS          current
    DESCRIPTION     
            "The number of ingress assignments to a DS0 channel on logical DS1 number 23."
    ::= { sonusIgCallCurrentEntry 65 }

sonusIgCallCurrentEgressAssignments2Ds0Port23 OBJECT-TYPE
    SYNTAX          PerfCurrentCount
    MAX-ACCESS      read-only
    STATUS          current
    DESCRIPTION     
            "The number of egress assignments to a DS0 channel on logical DS1 number 23."
    ::= { sonusIgCallCurrentEntry 66 }

sonusIgCallCurrentIngressAssignments2Ds0Port24 OBJECT-TYPE
    SYNTAX          PerfCurrentCount
    MAX-ACCESS      read-only
    STATUS          current
    DESCRIPTION     
            "The number of ingress assignments to a DS0 channel on logical DS1 number 24."
    ::= { sonusIgCallCurrentEntry 67 }

sonusIgCallCurrentEgressAssignments2Ds0Port24 OBJECT-TYPE
    SYNTAX          PerfCurrentCount
    MAX-ACCESS      read-only
    STATUS          current
    DESCRIPTION     
            "The number of egress assignments to a DS0 channel on logical DS1 number 24."
    ::= { sonusIgCallCurrentEntry 68 }

sonusIgCallCurrentIngressAssignments2Ds0Port25 OBJECT-TYPE
    SYNTAX          PerfCurrentCount
    MAX-ACCESS      read-only
    STATUS          current
    DESCRIPTION     
            "The number of ingress assignments to a DS0 channel on logical DS1 number 25."
    ::= { sonusIgCallCurrentEntry 69 }

sonusIgCallCurrentEgressAssignments2Ds0Port25 OBJECT-TYPE
    SYNTAX          PerfCurrentCount
    MAX-ACCESS      read-only
    STATUS          current
    DESCRIPTION     
            "The number of egress assignments to a DS0 channel on logical DS1 number 25."
    ::= { sonusIgCallCurrentEntry 70 }

sonusIgCallCurrentIngressAssignments2Ds0Port26 OBJECT-TYPE
    SYNTAX          PerfCurrentCount
    MAX-ACCESS      read-only
    STATUS          current
    DESCRIPTION     
            "The number of ingress assignments to a DS0 channel on logical DS1 number 26."
    ::= { sonusIgCallCurrentEntry 71 }

sonusIgCallCurrentEgressAssignments2Ds0Port26 OBJECT-TYPE
    SYNTAX          PerfCurrentCount
    MAX-ACCESS      read-only
    STATUS          current
    DESCRIPTION     
            "The number of egress assignments to a DS0 channel on logical DS1 number 26."
    ::= { sonusIgCallCurrentEntry 72 }

sonusIgCallCurrentIngressAssignments2Ds0Port27 OBJECT-TYPE
    SYNTAX          PerfCurrentCount
    MAX-ACCESS      read-only
    STATUS          current
    DESCRIPTION     
            "The number of ingress assignments to a DS0 channel on logical DS1 number 27."
    ::= { sonusIgCallCurrentEntry 73 }

sonusIgCallCurrentEgressAssignments2Ds0Port27 OBJECT-TYPE
    SYNTAX          PerfCurrentCount
    MAX-ACCESS      read-only
    STATUS          current
    DESCRIPTION     
            "The number of egress assignments to a DS0 channel on logical DS1 number 27."
    ::= { sonusIgCallCurrentEntry 74 }

sonusIgCallCurrentIngressAssignments2Ds0Port28 OBJECT-TYPE
    SYNTAX          PerfCurrentCount
    MAX-ACCESS      read-only
    STATUS          current
    DESCRIPTION     
            "The number of ingress assignments to a DS0 channel on logical DS1 number 28."
    ::= { sonusIgCallCurrentEntry 75 }

sonusIgCallCurrentEgressAssignments2Ds0Port28 OBJECT-TYPE
    SYNTAX          PerfCurrentCount
    MAX-ACCESS      read-only
    STATUS          current
    DESCRIPTION     
            "The number of egress assignments to a DS0 channel on logical DS1 number 28."
    ::= { sonusIgCallCurrentEntry 76 }

sonusIgCallCurrentCc27RdtDestOos OBJECT-TYPE
    SYNTAX          PerfCurrentCount
    MAX-ACCESS      read-only
    STATUS          current
    DESCRIPTION     
            "The number of calls cleared by RDT as destination out-of-service (cause code 27)."
    ::= { sonusIgCallCurrentEntry 77 }

sonusIgCallCurrentNumIngressCallsBlocked OBJECT-TYPE
    SYNTAX          PerfCurrentCount
    MAX-ACCESS      read-only
    STATUS          current
    DESCRIPTION     
            "The number of ingress attempts blocked on this GR303 Interface Group."
    ::= { sonusIgCallCurrentEntry 78 }

sonusIgCallCurrentNumEgressCallsBlocked OBJECT-TYPE
    SYNTAX          PerfCurrentCount
    MAX-ACCESS      read-only
    STATUS          current
    DESCRIPTION     
            "The number of egress attempts blocked on this GR303 Interface Group."
    ::= { sonusIgCallCurrentEntry 79 }

sonusIgCallCurrentCc16IdtNormalClearing OBJECT-TYPE
    SYNTAX          PerfCurrentCount
    MAX-ACCESS      read-only
    STATUS          current
    DESCRIPTION     
            "The number of calls cleared normally by IDT (cause code 16)."
    ::= { sonusIgCallCurrentEntry 80 }

sonusIgCallCurrentCc16RdtNormalClearing OBJECT-TYPE
    SYNTAX          PerfCurrentCount
    MAX-ACCESS      read-only
    STATUS          current
    DESCRIPTION     
            "The number of calls cleared normally by RDT (cause code 16)."
    ::= { sonusIgCallCurrentEntry 81 }

sonusIgCallIntervalTable OBJECT-TYPE
    SYNTAX          SEQUENCE OF SonusIgCallIntervalEntry
    MAX-ACCESS      not-accessible
    STATUS          current
    DESCRIPTION     
            "The Sonus GR303 Interface Group Call Statistics Interval table."
    ::= { sonusIgStatisticsObjects 6 }

sonusIgCallIntervalEntry OBJECT-TYPE
    SYNTAX          SonusIgCallIntervalEntry
    MAX-ACCESS      not-accessible
    STATUS          current
    DESCRIPTION     
            "An entry in the Sonus Interface Group Call Statistics
             Interval table."
    INDEX           { sonusIgCallIntervalIgIndex, 
                      sonusIgCallIntervalNumber }
    ::= { sonusIgCallIntervalTable 1 }

SonusIgCallIntervalEntry ::=
    SEQUENCE {
        sonusIgCallIntervalIgIndex      Integer32,
        sonusIgCallIntervalNumber       Integer32,
        sonusIgCallIntervalTime         TimeTicks,
        sonusIgCallIntervalValidData    TruthValue,
        sonusIgCallIntervalTrafficHourlyProratedCallSeconds                   PerfIntervalCount,
        sonusIgCallIntervalTrafficPercentageUtilizationOfPeakCapacity                             PerfIntervalCount,
        sonusIgCallIntervalTrafficMaximumSimultaneousAssignments2Ds0                            PerfIntervalCount,
        sonusIgCallIntervalCc27DestOosShoweringLine           PerfIntervalCount,
        sonusIgCallIntervalCc27DestOosAdminOos      PerfIntervalCount,
        sonusIgCallIntervalCc27DestOosPsc PerfIntervalCount,
        sonusIgCallIntervalCc34IdtChanUnavail     PerfIntervalCount,
        sonusIgCallIntervalCc34RdtChanUnavail     PerfIntervalCount,
        sonusIgCallIntervalCc41IdtTempFailure     PerfIntervalCount,
        sonusIgCallIntervalCc41RdtTempFailure     PerfIntervalCount,
        sonusIgCallIntervalCc44LineUnitUnavail      PerfIntervalCount,
        sonusIgCallIntervalCc47RingFailure  PerfIntervalCount,
        sonusIgCallIntervalCc81IdtInvalidCallRef        PerfIntervalCount,
        sonusIgCallIntervalCc81RdtInvalidCallRef        PerfIntervalCount,
        sonusIgCallIntervalCcOtherIdt   PerfIntervalCount,
        sonusIgCallIntervalCcOtherRdt   PerfIntervalCount,
        sonusIgCallIntervalTimeAllChanBusy  PerfIntervalCount,
        sonusIgCallIntervalNumIngressCalls  PerfIntervalCount,
        sonusIgCallIntervalNumEgressCalls PerfIntervalCount,
        sonusIgCallIntervalIngressAssignments2Ds0Port1              PerfIntervalCount,
        sonusIgCallIntervalEgressAssignments2Ds0Port1             PerfIntervalCount,
        sonusIgCallIntervalIngressAssignments2Ds0Port2              PerfIntervalCount,
        sonusIgCallIntervalEgressAssignments2Ds0Port2             PerfIntervalCount,
        sonusIgCallIntervalIngressAssignments2Ds0Port3              PerfIntervalCount,
        sonusIgCallIntervalEgressAssignments2Ds0Port3             PerfIntervalCount,
        sonusIgCallIntervalIngressAssignments2Ds0Port4              PerfIntervalCount,
        sonusIgCallIntervalEgressAssignments2Ds0Port4             PerfIntervalCount,
        sonusIgCallIntervalIngressAssignments2Ds0Port5              PerfIntervalCount,
        sonusIgCallIntervalEgressAssignments2Ds0Port5             PerfIntervalCount,
        sonusIgCallIntervalIngressAssignments2Ds0Port6              PerfIntervalCount,
        sonusIgCallIntervalEgressAssignments2Ds0Port6             PerfIntervalCount,
        sonusIgCallIntervalIngressAssignments2Ds0Port7              PerfIntervalCount,
        sonusIgCallIntervalEgressAssignments2Ds0Port7             PerfIntervalCount,
        sonusIgCallIntervalIngressAssignments2Ds0Port8              PerfIntervalCount,
        sonusIgCallIntervalEgressAssignments2Ds0Port8             PerfIntervalCount,
        sonusIgCallIntervalIngressAssignments2Ds0Port9              PerfIntervalCount,
        sonusIgCallIntervalEgressAssignments2Ds0Port9             PerfIntervalCount,
        sonusIgCallIntervalIngressAssignments2Ds0Port10               PerfIntervalCount,
        sonusIgCallIntervalEgressAssignments2Ds0Port10              PerfIntervalCount,
        sonusIgCallIntervalIngressAssignments2Ds0Port11               PerfIntervalCount,
        sonusIgCallIntervalEgressAssignments2Ds0Port11              PerfIntervalCount,
        sonusIgCallIntervalIngressAssignments2Ds0Port12               PerfIntervalCount,
        sonusIgCallIntervalEgressAssignments2Ds0Port12              PerfIntervalCount,
        sonusIgCallIntervalIngressAssignments2Ds0Port13               PerfIntervalCount,
        sonusIgCallIntervalEgressAssignments2Ds0Port13              PerfIntervalCount,
        sonusIgCallIntervalIngressAssignments2Ds0Port14               PerfIntervalCount,
        sonusIgCallIntervalEgressAssignments2Ds0Port14              PerfIntervalCount,
        sonusIgCallIntervalIngressAssignments2Ds0Port15               PerfIntervalCount,
        sonusIgCallIntervalEgressAssignments2Ds0Port15              PerfIntervalCount,
        sonusIgCallIntervalIngressAssignments2Ds0Port16               PerfIntervalCount,
        sonusIgCallIntervalEgressAssignments2Ds0Port16              PerfIntervalCount,
        sonusIgCallIntervalIngressAssignments2Ds0Port17               PerfIntervalCount,
        sonusIgCallIntervalEgressAssignments2Ds0Port17              PerfIntervalCount,
        sonusIgCallIntervalIngressAssignments2Ds0Port18               PerfIntervalCount,
        sonusIgCallIntervalEgressAssignments2Ds0Port18              PerfIntervalCount,
        sonusIgCallIntervalIngressAssignments2Ds0Port19               PerfIntervalCount,
        sonusIgCallIntervalEgressAssignments2Ds0Port19              PerfIntervalCount,
        sonusIgCallIntervalIngressAssignments2Ds0Port20               PerfIntervalCount,
        sonusIgCallIntervalEgressAssignments2Ds0Port20              PerfIntervalCount,
        sonusIgCallIntervalIngressAssignments2Ds0Port21               PerfIntervalCount,
        sonusIgCallIntervalEgressAssignments2Ds0Port21              PerfIntervalCount,
        sonusIgCallIntervalIngressAssignments2Ds0Port22               PerfIntervalCount,
        sonusIgCallIntervalEgressAssignments2Ds0Port22              PerfIntervalCount,
        sonusIgCallIntervalIngressAssignments2Ds0Port23               PerfIntervalCount,
        sonusIgCallIntervalEgressAssignments2Ds0Port23              PerfIntervalCount,
        sonusIgCallIntervalIngressAssignments2Ds0Port24               PerfIntervalCount,
        sonusIgCallIntervalEgressAssignments2Ds0Port24              PerfIntervalCount,
        sonusIgCallIntervalIngressAssignments2Ds0Port25               PerfIntervalCount,
        sonusIgCallIntervalEgressAssignments2Ds0Port25              PerfIntervalCount,
        sonusIgCallIntervalIngressAssignments2Ds0Port26               PerfIntervalCount,
        sonusIgCallIntervalEgressAssignments2Ds0Port26              PerfIntervalCount,
        sonusIgCallIntervalIngressAssignments2Ds0Port27               PerfIntervalCount,
        sonusIgCallIntervalEgressAssignments2Ds0Port27              PerfIntervalCount,
        sonusIgCallIntervalIngressAssignments2Ds0Port28               PerfIntervalCount,
        sonusIgCallIntervalEgressAssignments2Ds0Port28              PerfIntervalCount,
        sonusIgCallIntervalCc27RdtDestOos PerfIntervalCount,
        sonusIgCallIntervalNumIngressCallsBlocked         PerfIntervalCount,
        sonusIgCallIntervalNumEgressCallsBlocked        PerfIntervalCount,
        sonusIgCallIntervalCc16IdtNormalClearing        PerfIntervalCount,
        sonusIgCallIntervalCc16RdtNormalClearing        PerfIntervalCount
    }

sonusIgCallIntervalIgIndex OBJECT-TYPE
    SYNTAX          Integer32
    MAX-ACCESS      read-only
    STATUS          current
    DESCRIPTION     
            "The index of the GR303 Interface Group."
    ::= { sonusIgCallIntervalEntry 1 }

sonusIgCallIntervalNumber OBJECT-TYPE
    SYNTAX          Integer32 (1..288)
    MAX-ACCESS      not-accessible
    STATUS          current
    DESCRIPTION     
            "A number between 1 and 288, which identifies the
             interval for which the set of statistics is available.
             The interval identified by 1 is the most recently
             completed interval, and the interval identified
             by N is the interval immediately preceding the
             one identified by N-1."
    ::= { sonusIgCallIntervalEntry 2 }

sonusIgCallIntervalTime OBJECT-TYPE
    SYNTAX          TimeTicks
    MAX-ACCESS      read-only
    STATUS          current
    DESCRIPTION     
            "This variable contains the end of interval time
             stamp for the specified interval."
    ::= { sonusIgCallIntervalEntry 3 }

sonusIgCallIntervalValidData OBJECT-TYPE
    SYNTAX          TruthValue
    MAX-ACCESS      read-only
    STATUS          current
    DESCRIPTION     
            "This variable indicates if the data for this interval is valid."
    ::= { sonusIgCallIntervalEntry 4 }

sonusIgCallIntervalTrafficHourlyProratedCallSeconds OBJECT-TYPE
    SYNTAX          PerfIntervalCount
    MAX-ACCESS      read-only
    STATUS          current
    DESCRIPTION     
            "The traffic in Call Seconds on this GR303 Interface Group
             prorated from the measurement interval to a hourly basis."
    ::= { sonusIgCallIntervalEntry 5 }

sonusIgCallIntervalTrafficPercentageUtilizationOfPeakCapacity OBJECT-TYPE
    SYNTAX          PerfIntervalCount
    MAX-ACCESS      read-only
    STATUS          current
    DESCRIPTION     
            "The percentage utilization of this GR303 Interface Group
             relative to its peak capacity during the measurement interval."
    ::= { sonusIgCallIntervalEntry 6 }

sonusIgCallIntervalTrafficMaximumSimultaneousAssignments2Ds0 OBJECT-TYPE
    SYNTAX          PerfIntervalCount
    MAX-ACCESS      read-only
    STATUS          current
    DESCRIPTION     
            "The maximum number of DS0 channels in use simultaneously
             on this GR303 Interface Group during the measurment interval."
    ::= { sonusIgCallIntervalEntry 7 }

sonusIgCallIntervalCc27DestOosShoweringLine OBJECT-TYPE
    SYNTAX          PerfIntervalCount
    MAX-ACCESS      read-only
    STATUS          current
    DESCRIPTION     
            "The number of calls cleared by IDT as destination out-of-service (cause code 27)
             due to a showering line condition."
    ::= { sonusIgCallIntervalEntry 8 }

sonusIgCallIntervalCc27DestOosAdminOos OBJECT-TYPE
    SYNTAX          PerfIntervalCount
    MAX-ACCESS      read-only
    STATUS          current
    DESCRIPTION     
            "The number of calls cleared by IDT as destination out-of-service (cause code 27)
             due to administrative out-of-service."
    ::= { sonusIgCallIntervalEntry 9 }

sonusIgCallIntervalCc27DestOosPsc OBJECT-TYPE
    SYNTAX          PerfIntervalCount
    MAX-ACCESS      read-only
    STATUS          current
    DESCRIPTION     
            "The number of calls cleared by IDT as destination out-of-service (cause code 27)
             due to a permanent signaling condition."
    ::= { sonusIgCallIntervalEntry 10 }

sonusIgCallIntervalCc34IdtChanUnavail OBJECT-TYPE
    SYNTAX          PerfIntervalCount
    MAX-ACCESS      read-only
    STATUS          current
    DESCRIPTION     
            "The number of calls cleared by IDT as channel unavailable (cause code 34)."
    ::= { sonusIgCallIntervalEntry 11 }

sonusIgCallIntervalCc34RdtChanUnavail OBJECT-TYPE
    SYNTAX          PerfIntervalCount
    MAX-ACCESS      read-only
    STATUS          current
    DESCRIPTION     
            "The number of calls cleared by RDT as channel unavailable (cause code 34)."
    ::= { sonusIgCallIntervalEntry 12 }

sonusIgCallIntervalCc41IdtTempFailure OBJECT-TYPE
    SYNTAX          PerfIntervalCount
    MAX-ACCESS      read-only
    STATUS          current
    DESCRIPTION     
            "The number of calls cleared by IDT as temporay failure (cause code 41)."
    ::= { sonusIgCallIntervalEntry 13 }

sonusIgCallIntervalCc41RdtTempFailure OBJECT-TYPE
    SYNTAX          PerfIntervalCount
    MAX-ACCESS      read-only
    STATUS          current
    DESCRIPTION     
            "The number of calls cleared by RDT as temporay failure (cause code 41)."
    ::= { sonusIgCallIntervalEntry 14 }

sonusIgCallIntervalCc44LineUnitUnavail OBJECT-TYPE
    SYNTAX          PerfIntervalCount
    MAX-ACCESS      read-only
    STATUS          current
    DESCRIPTION     
            "The number of calls cleared by RDT as line unit unavailable (cause code 44)."
    ::= { sonusIgCallIntervalEntry 15 }

sonusIgCallIntervalCc47RingFailure OBJECT-TYPE
    SYNTAX          PerfIntervalCount
    MAX-ACCESS      read-only
    STATUS          current
    DESCRIPTION     
            "The number of calls cleared by RDT as ring failure (cause code 47)."
    ::= { sonusIgCallIntervalEntry 16 }

sonusIgCallIntervalCc81IdtInvalidCallRef OBJECT-TYPE
    SYNTAX          PerfIntervalCount
    MAX-ACCESS      read-only
    STATUS          current
    DESCRIPTION     
            "The number of calls cleared by IDT as invalid call reference (cause code 81)."
    ::= { sonusIgCallIntervalEntry 17 }

sonusIgCallIntervalCc81RdtInvalidCallRef OBJECT-TYPE
    SYNTAX          PerfIntervalCount
    MAX-ACCESS      read-only
    STATUS          current
    DESCRIPTION     
            "The number of calls cleared by RDT as invalid call reference (cause code 81)."
    ::= { sonusIgCallIntervalEntry 18 }

sonusIgCallIntervalCcOtherIdt OBJECT-TYPE
    SYNTAX          PerfIntervalCount
    MAX-ACCESS      read-only
    STATUS          current
    DESCRIPTION     
            "The number of calls cleared by IDT for other reasons (cause code none of the above)."
    ::= { sonusIgCallIntervalEntry 19 }

sonusIgCallIntervalCcOtherRdt OBJECT-TYPE
    SYNTAX          PerfIntervalCount
    MAX-ACCESS      read-only
    STATUS          current
    DESCRIPTION     
            "The number of calls cleared by RDT for other reasons (cause code none of the above)."
    ::= { sonusIgCallIntervalEntry 20 }

sonusIgCallIntervalTimeAllChanBusy OBJECT-TYPE
    SYNTAX          PerfIntervalCount
    MAX-ACCESS      read-only
    STATUS          current
    DESCRIPTION     
            "The length of time (seconds) all available DS0 channels of this
             GR303 Interface Group were busy during the current interval.
             Any additional calls would have been refused."
    ::= { sonusIgCallIntervalEntry 21 }

sonusIgCallIntervalNumIngressCalls OBJECT-TYPE
    SYNTAX          PerfIntervalCount
    MAX-ACCESS      read-only
    STATUS          current
    DESCRIPTION     
            "The number of ingress assignments to DS0 channels on this GR303 Interface Group."
    ::= { sonusIgCallIntervalEntry 22 }

sonusIgCallIntervalNumEgressCalls OBJECT-TYPE
    SYNTAX          PerfIntervalCount
    MAX-ACCESS      read-only
    STATUS          current
    DESCRIPTION     
            "The number of egress assignments to DS0  on this GR303 Interface Group."
    ::= { sonusIgCallIntervalEntry 23 }

sonusIgCallIntervalIngressAssignments2Ds0Port1 OBJECT-TYPE
    SYNTAX          PerfIntervalCount
    MAX-ACCESS      read-only
    STATUS          current
    DESCRIPTION     
            "The number of ingress assignments to a DS0 channel on logical DS1 number 1."
    ::= { sonusIgCallIntervalEntry 24 }

sonusIgCallIntervalEgressAssignments2Ds0Port1 OBJECT-TYPE
    SYNTAX          PerfIntervalCount
    MAX-ACCESS      read-only
    STATUS          current
    DESCRIPTION     
            "The number of egress assignments to a DS0 channel on logical DS1 number 1."
    ::= { sonusIgCallIntervalEntry 25 }

sonusIgCallIntervalIngressAssignments2Ds0Port2 OBJECT-TYPE
    SYNTAX          PerfIntervalCount
    MAX-ACCESS      read-only
    STATUS          current
    DESCRIPTION     
            "The number of ingress assignments to a DS0 channel on logical DS1 number 2."
    ::= { sonusIgCallIntervalEntry 26 }

sonusIgCallIntervalEgressAssignments2Ds0Port2 OBJECT-TYPE
    SYNTAX          PerfIntervalCount
    MAX-ACCESS      read-only
    STATUS          current
    DESCRIPTION     
            "The number of egress assignments to a DS0 channel on logical DS1 number 2."
    ::= { sonusIgCallIntervalEntry 27 }

sonusIgCallIntervalIngressAssignments2Ds0Port3 OBJECT-TYPE
    SYNTAX          PerfIntervalCount
    MAX-ACCESS      read-only
    STATUS          current
    DESCRIPTION     
            "The number of ingress assignments to a DS0 channel on logical DS1 number 3."
    ::= { sonusIgCallIntervalEntry 28 }

sonusIgCallIntervalEgressAssignments2Ds0Port3 OBJECT-TYPE
    SYNTAX          PerfIntervalCount
    MAX-ACCESS      read-only
    STATUS          current
    DESCRIPTION     
            "The number of egress assignments to a DS0 channel on logical DS1 number 3."
    ::= { sonusIgCallIntervalEntry 29 }

sonusIgCallIntervalIngressAssignments2Ds0Port4 OBJECT-TYPE
    SYNTAX          PerfIntervalCount
    MAX-ACCESS      read-only
    STATUS          current
    DESCRIPTION     
            "The number of ingress assignments to a DS0 channel on logical DS1 number 4."
    ::= { sonusIgCallIntervalEntry 30 }

sonusIgCallIntervalEgressAssignments2Ds0Port4 OBJECT-TYPE
    SYNTAX          PerfIntervalCount
    MAX-ACCESS      read-only
    STATUS          current
    DESCRIPTION     
            "The number of egress assignments to a DS0 channel on logical DS1 number 4."
    ::= { sonusIgCallIntervalEntry 31 }

sonusIgCallIntervalIngressAssignments2Ds0Port5 OBJECT-TYPE
    SYNTAX          PerfIntervalCount
    MAX-ACCESS      read-only
    STATUS          current
    DESCRIPTION     
            "The number of ingress assignments to a DS0 channel on logical DS1 number 5."
    ::= { sonusIgCallIntervalEntry 32 }

sonusIgCallIntervalEgressAssignments2Ds0Port5 OBJECT-TYPE
    SYNTAX          PerfIntervalCount
    MAX-ACCESS      read-only
    STATUS          current
    DESCRIPTION     
            "The number of egress assignments to a DS0 channel on logical DS1 number 5."
    ::= { sonusIgCallIntervalEntry 33 }

sonusIgCallIntervalIngressAssignments2Ds0Port6 OBJECT-TYPE
    SYNTAX          PerfIntervalCount
    MAX-ACCESS      read-only
    STATUS          current
    DESCRIPTION     
            "The number of ingress assignments to a DS0 channel on logical DS1 number 6."
    ::= { sonusIgCallIntervalEntry 34 }

sonusIgCallIntervalEgressAssignments2Ds0Port6 OBJECT-TYPE
    SYNTAX          PerfIntervalCount
    MAX-ACCESS      read-only
    STATUS          current
    DESCRIPTION     
            "The number of egress assignments to a DS0 channel on logical DS1 number 6."
    ::= { sonusIgCallIntervalEntry 35 }

sonusIgCallIntervalIngressAssignments2Ds0Port7 OBJECT-TYPE
    SYNTAX          PerfIntervalCount
    MAX-ACCESS      read-only
    STATUS          current
    DESCRIPTION     
            "The number of ingress assignments to a DS0 channel on logical DS1 number 7."
    ::= { sonusIgCallIntervalEntry 36 }

sonusIgCallIntervalEgressAssignments2Ds0Port7 OBJECT-TYPE
    SYNTAX          PerfIntervalCount
    MAX-ACCESS      read-only
    STATUS          current
    DESCRIPTION     
            "The number of egress assignments to a DS0 channel on logical DS1 number 7."
    ::= { sonusIgCallIntervalEntry 37 }

sonusIgCallIntervalIngressAssignments2Ds0Port8 OBJECT-TYPE
    SYNTAX          PerfIntervalCount
    MAX-ACCESS      read-only
    STATUS          current
    DESCRIPTION     
            "The number of ingress assignments to a DS0 channel on logical DS1 number 8."
    ::= { sonusIgCallIntervalEntry 38 }

sonusIgCallIntervalEgressAssignments2Ds0Port8 OBJECT-TYPE
    SYNTAX          PerfIntervalCount
    MAX-ACCESS      read-only
    STATUS          current
    DESCRIPTION     
            "The number of egress assignments to a DS0 channel on logical DS1 number 8."
    ::= { sonusIgCallIntervalEntry 39 }

sonusIgCallIntervalIngressAssignments2Ds0Port9 OBJECT-TYPE
    SYNTAX          PerfIntervalCount
    MAX-ACCESS      read-only
    STATUS          current
    DESCRIPTION     
            "The number of ingress assignments to a DS0 channel on logical DS1 number 9."
    ::= { sonusIgCallIntervalEntry 40 }

sonusIgCallIntervalEgressAssignments2Ds0Port9 OBJECT-TYPE
    SYNTAX          PerfIntervalCount
    MAX-ACCESS      read-only
    STATUS          current
    DESCRIPTION     
            "The number of egress assignments to a DS0 channel on logical DS1 number 9."
    ::= { sonusIgCallIntervalEntry 41 }

sonusIgCallIntervalIngressAssignments2Ds0Port10 OBJECT-TYPE
    SYNTAX          PerfIntervalCount
    MAX-ACCESS      read-only
    STATUS          current
    DESCRIPTION     
            "The number of ingress assignments to a DS0 channel on logical DS1 number 10."
    ::= { sonusIgCallIntervalEntry 42 }

sonusIgCallIntervalEgressAssignments2Ds0Port10 OBJECT-TYPE
    SYNTAX          PerfIntervalCount
    MAX-ACCESS      read-only
    STATUS          current
    DESCRIPTION     
            "The number of egress assignments to a DS0 channel on logical DS1 number 10."
    ::= { sonusIgCallIntervalEntry 43 }

sonusIgCallIntervalIngressAssignments2Ds0Port11 OBJECT-TYPE
    SYNTAX          PerfIntervalCount
    MAX-ACCESS      read-only
    STATUS          current
    DESCRIPTION     
            "The number of ingress assignments to a DS0 channel on logical DS1 number 11."
    ::= { sonusIgCallIntervalEntry 44 }

sonusIgCallIntervalEgressAssignments2Ds0Port11 OBJECT-TYPE
    SYNTAX          PerfIntervalCount
    MAX-ACCESS      read-only
    STATUS          current
    DESCRIPTION     
            "The number of egress assignments to a DS0 channel on logical DS1 number 11."
    ::= { sonusIgCallIntervalEntry 45 }

sonusIgCallIntervalIngressAssignments2Ds0Port12 OBJECT-TYPE
    SYNTAX          PerfIntervalCount
    MAX-ACCESS      read-only
    STATUS          current
    DESCRIPTION     
            "The number of ingress assignments to a DS0 channel on logical DS1 number 12."
    ::= { sonusIgCallIntervalEntry 46 }

sonusIgCallIntervalEgressAssignments2Ds0Port12 OBJECT-TYPE
    SYNTAX          PerfIntervalCount
    MAX-ACCESS      read-only
    STATUS          current
    DESCRIPTION     
            "The number of egress assignments to a DS0 channel on logical DS1 number 12."
    ::= { sonusIgCallIntervalEntry 47 }

sonusIgCallIntervalIngressAssignments2Ds0Port13 OBJECT-TYPE
    SYNTAX          PerfIntervalCount
    MAX-ACCESS      read-only
    STATUS          current
    DESCRIPTION     
            "The number of ingress assignments to a DS0 channel on logical DS1 number 13."
    ::= { sonusIgCallIntervalEntry 48 }

sonusIgCallIntervalEgressAssignments2Ds0Port13 OBJECT-TYPE
    SYNTAX          PerfIntervalCount
    MAX-ACCESS      read-only
    STATUS          current
    DESCRIPTION     
            "The number of egress assignments to a DS0 channel on logical DS1 number 13."
    ::= { sonusIgCallIntervalEntry 49 }

sonusIgCallIntervalIngressAssignments2Ds0Port14 OBJECT-TYPE
    SYNTAX          PerfIntervalCount
    MAX-ACCESS      read-only
    STATUS          current
    DESCRIPTION     
            "The number of ingress assignments to a DS0 channel on logical DS1 number 14."
    ::= { sonusIgCallIntervalEntry 50 }

sonusIgCallIntervalEgressAssignments2Ds0Port14 OBJECT-TYPE
    SYNTAX          PerfIntervalCount
    MAX-ACCESS      read-only
    STATUS          current
    DESCRIPTION     
            "The number of egress assignments to a DS0 channel on logical DS1 number 14."
    ::= { sonusIgCallIntervalEntry 51 }

sonusIgCallIntervalIngressAssignments2Ds0Port15 OBJECT-TYPE
    SYNTAX          PerfIntervalCount
    MAX-ACCESS      read-only
    STATUS          current
    DESCRIPTION     
            "The number of ingress assignments to a DS0 channel on logical DS1 number 15."
    ::= { sonusIgCallIntervalEntry 52 }

sonusIgCallIntervalEgressAssignments2Ds0Port15 OBJECT-TYPE
    SYNTAX          PerfIntervalCount
    MAX-ACCESS      read-only
    STATUS          current
    DESCRIPTION     
            "The number of egress assignments to a DS0 channel on logical DS1 number 15."
    ::= { sonusIgCallIntervalEntry 53 }

sonusIgCallIntervalIngressAssignments2Ds0Port16 OBJECT-TYPE
    SYNTAX          PerfIntervalCount
    MAX-ACCESS      read-only
    STATUS          current
    DESCRIPTION     
            "The number of ingress assignments to a DS0 channel on logical DS1 number 16."
    ::= { sonusIgCallIntervalEntry 54 }

sonusIgCallIntervalEgressAssignments2Ds0Port16 OBJECT-TYPE
    SYNTAX          PerfIntervalCount
    MAX-ACCESS      read-only
    STATUS          current
    DESCRIPTION     
            "The number of egress assignments to a DS0 channel on logical DS1 number 16."
    ::= { sonusIgCallIntervalEntry 55 }

sonusIgCallIntervalIngressAssignments2Ds0Port17 OBJECT-TYPE
    SYNTAX          PerfIntervalCount
    MAX-ACCESS      read-only
    STATUS          current
    DESCRIPTION     
            "The number of ingress assignments to a DS0 channel on logical DS1 number 17."
    ::= { sonusIgCallIntervalEntry 56 }

sonusIgCallIntervalEgressAssignments2Ds0Port17 OBJECT-TYPE
    SYNTAX          PerfIntervalCount
    MAX-ACCESS      read-only
    STATUS          current
    DESCRIPTION     
            "The number of egress assignments to a DS0 channel on logical DS1 number 17."
    ::= { sonusIgCallIntervalEntry 57 }

sonusIgCallIntervalIngressAssignments2Ds0Port18 OBJECT-TYPE
    SYNTAX          PerfIntervalCount
    MAX-ACCESS      read-only
    STATUS          current
    DESCRIPTION     
            "The number of ingress assignments to a DS0 channel on logical DS1 number 18."
    ::= { sonusIgCallIntervalEntry 58 }

sonusIgCallIntervalEgressAssignments2Ds0Port18 OBJECT-TYPE
    SYNTAX          PerfIntervalCount
    MAX-ACCESS      read-only
    STATUS          current
    DESCRIPTION     
            "The number of egress assignments to a DS0 channel on logical DS1 number 18."
    ::= { sonusIgCallIntervalEntry 59 }

sonusIgCallIntervalIngressAssignments2Ds0Port19 OBJECT-TYPE
    SYNTAX          PerfIntervalCount
    MAX-ACCESS      read-only
    STATUS          current
    DESCRIPTION     
            "The number of ingress assignments to a DS0 channel on logical DS1 number 19."
    ::= { sonusIgCallIntervalEntry 60 }

sonusIgCallIntervalEgressAssignments2Ds0Port19 OBJECT-TYPE
    SYNTAX          PerfIntervalCount
    MAX-ACCESS      read-only
    STATUS          current
    DESCRIPTION     
            "The number of egress assignments to a DS0 channel on logical DS1 number 19."
    ::= { sonusIgCallIntervalEntry 61 }

sonusIgCallIntervalIngressAssignments2Ds0Port20 OBJECT-TYPE
    SYNTAX          PerfIntervalCount
    MAX-ACCESS      read-only
    STATUS          current
    DESCRIPTION     
            "The number of ingress assignments to a DS0 channel on logical DS1 number 20."
    ::= { sonusIgCallIntervalEntry 62 }

sonusIgCallIntervalEgressAssignments2Ds0Port20 OBJECT-TYPE
    SYNTAX          PerfIntervalCount
    MAX-ACCESS      read-only
    STATUS          current
    DESCRIPTION     
            "The number of egress assignments to a DS0 channel on logical DS1 number 20."
    ::= { sonusIgCallIntervalEntry 63 }

sonusIgCallIntervalIngressAssignments2Ds0Port21 OBJECT-TYPE
    SYNTAX          PerfIntervalCount
    MAX-ACCESS      read-only
    STATUS          current
    DESCRIPTION     
            "The number of ingress assignments to a DS0 channel on logical DS1 number 21."
    ::= { sonusIgCallIntervalEntry 64 }

sonusIgCallIntervalEgressAssignments2Ds0Port21 OBJECT-TYPE
    SYNTAX          PerfIntervalCount
    MAX-ACCESS      read-only
    STATUS          current
    DESCRIPTION     
            "The number of egress assignments to a DS0 channel on logical DS1 number 21."
    ::= { sonusIgCallIntervalEntry 65 }

sonusIgCallIntervalIngressAssignments2Ds0Port22 OBJECT-TYPE
    SYNTAX          PerfIntervalCount
    MAX-ACCESS      read-only
    STATUS          current
    DESCRIPTION     
            "The number of ingress assignments to a DS0 channel on logical DS1 number 22."
    ::= { sonusIgCallIntervalEntry 66 }

sonusIgCallIntervalEgressAssignments2Ds0Port22 OBJECT-TYPE
    SYNTAX          PerfIntervalCount
    MAX-ACCESS      read-only
    STATUS          current
    DESCRIPTION     
            "The number of egress assignments to a DS0 channel on logical DS1 number 22."
    ::= { sonusIgCallIntervalEntry 67 }

sonusIgCallIntervalIngressAssignments2Ds0Port23 OBJECT-TYPE
    SYNTAX          PerfIntervalCount
    MAX-ACCESS      read-only
    STATUS          current
    DESCRIPTION     
            "The number of ingress assignments to a DS0 channel on logical DS1 number 23."
    ::= { sonusIgCallIntervalEntry 68 }

sonusIgCallIntervalEgressAssignments2Ds0Port23 OBJECT-TYPE
    SYNTAX          PerfIntervalCount
    MAX-ACCESS      read-only
    STATUS          current
    DESCRIPTION     
            "The number of egress assignments to a DS0 channel on logical DS1 number 23."
    ::= { sonusIgCallIntervalEntry 69 }

sonusIgCallIntervalIngressAssignments2Ds0Port24 OBJECT-TYPE
    SYNTAX          PerfIntervalCount
    MAX-ACCESS      read-only
    STATUS          current
    DESCRIPTION     
            "The number of ingress assignments to a DS0 channel on logical DS1 number 24."
    ::= { sonusIgCallIntervalEntry 70 }

sonusIgCallIntervalEgressAssignments2Ds0Port24 OBJECT-TYPE
    SYNTAX          PerfIntervalCount
    MAX-ACCESS      read-only
    STATUS          current
    DESCRIPTION     
            "The number of egress assignments to a DS0 channel on logical DS1 number 24."
    ::= { sonusIgCallIntervalEntry 71 }

sonusIgCallIntervalIngressAssignments2Ds0Port25 OBJECT-TYPE
    SYNTAX          PerfIntervalCount
    MAX-ACCESS      read-only
    STATUS          current
    DESCRIPTION     
            "The number of ingress assignments to a DS0 channel on logical DS1 number 25."
    ::= { sonusIgCallIntervalEntry 72 }

sonusIgCallIntervalEgressAssignments2Ds0Port25 OBJECT-TYPE
    SYNTAX          PerfIntervalCount
    MAX-ACCESS      read-only
    STATUS          current
    DESCRIPTION     
            "The number of egress assignments to a DS0 channel on logical DS1 number 25."
    ::= { sonusIgCallIntervalEntry 73 }

sonusIgCallIntervalIngressAssignments2Ds0Port26 OBJECT-TYPE
    SYNTAX          PerfIntervalCount
    MAX-ACCESS      read-only
    STATUS          current
    DESCRIPTION     
            "The number of ingress assignments to a DS0 channel on logical DS1 number 26."
    ::= { sonusIgCallIntervalEntry 74 }

sonusIgCallIntervalEgressAssignments2Ds0Port26 OBJECT-TYPE
    SYNTAX          PerfIntervalCount
    MAX-ACCESS      read-only
    STATUS          current
    DESCRIPTION     
            "The number of egress assignments to a DS0 channel on logical DS1 number 26."
    ::= { sonusIgCallIntervalEntry 75 }

sonusIgCallIntervalIngressAssignments2Ds0Port27 OBJECT-TYPE
    SYNTAX          PerfIntervalCount
    MAX-ACCESS      read-only
    STATUS          current
    DESCRIPTION     
            "The number of ingress assignments to a DS0 channel on logical DS1 number 27."
    ::= { sonusIgCallIntervalEntry 76 }

sonusIgCallIntervalEgressAssignments2Ds0Port27 OBJECT-TYPE
    SYNTAX          PerfIntervalCount
    MAX-ACCESS      read-only
    STATUS          current
    DESCRIPTION     
            "The number of egress assignments to a DS0 channel on logical DS1 number 27."
    ::= { sonusIgCallIntervalEntry 77 }

sonusIgCallIntervalIngressAssignments2Ds0Port28 OBJECT-TYPE
    SYNTAX          PerfIntervalCount
    MAX-ACCESS      read-only
    STATUS          current
    DESCRIPTION     
            "The number of ingress assignments to a DS0 channel on logical DS1 number 28."
    ::= { sonusIgCallIntervalEntry 78 }

sonusIgCallIntervalEgressAssignments2Ds0Port28 OBJECT-TYPE
    SYNTAX          PerfIntervalCount
    MAX-ACCESS      read-only
    STATUS          current
    DESCRIPTION     
            "The number of egress assignments to a DS0 channel on logical DS1 number 28."
    ::= { sonusIgCallIntervalEntry 79 }

sonusIgCallIntervalCc27RdtDestOos OBJECT-TYPE
    SYNTAX          PerfIntervalCount
    MAX-ACCESS      read-only
    STATUS          current
    DESCRIPTION     
            "The number of calls cleared by RDT as destination out-of-service (cause code 27)."
    ::= { sonusIgCallIntervalEntry 80 }

sonusIgCallIntervalNumIngressCallsBlocked OBJECT-TYPE
    SYNTAX          PerfIntervalCount
    MAX-ACCESS      read-only
    STATUS          current
    DESCRIPTION     
            "The number of ingress attempts blocked on this GR303 Interface Group."
    ::= { sonusIgCallIntervalEntry 81 }

sonusIgCallIntervalNumEgressCallsBlocked OBJECT-TYPE
    SYNTAX          PerfIntervalCount
    MAX-ACCESS      read-only
    STATUS          current
    DESCRIPTION     
            "The number of egress attempts blocked on this GR303 Interface Group."
    ::= { sonusIgCallIntervalEntry 82 }

sonusIgCallIntervalCc16IdtNormalClearing OBJECT-TYPE
    SYNTAX          PerfIntervalCount
    MAX-ACCESS      read-only
    STATUS          current
    DESCRIPTION     
            "The number of calls cleared normally by IDT (cause code 16)."
    ::= { sonusIgCallIntervalEntry 83 }

sonusIgCallIntervalCc16RdtNormalClearing OBJECT-TYPE
    SYNTAX          PerfIntervalCount
    MAX-ACCESS      read-only
    STATUS          current
    DESCRIPTION     
            "The number of calls cleared normally by RDT (cause code 16)."
    ::= { sonusIgCallIntervalEntry 84 }

sonusDsStatisticsObjects OBJECT IDENTIFIER
    ::= { sonusPerformanceStatisticsObjects 10 }

sonusDsCurrentTable OBJECT-TYPE
    SYNTAX          SEQUENCE OF SonusDsCurrentEntry
    MAX-ACCESS      not-accessible
    STATUS          current
    DESCRIPTION     
            "This table presents DS current statistics."
    ::= { sonusDsStatisticsObjects 1 }

sonusDsCurrentEntry OBJECT-TYPE
    SYNTAX          SonusDsCurrentEntry
    MAX-ACCESS      not-accessible
    STATUS          current
    DESCRIPTION     
            "An entry in the DS Statistics Current table."
    INDEX           { sonusDsCurrentShelfIndex }
    ::= { sonusDsCurrentTable 1 }

SonusDsCurrentEntry ::=
    SEQUENCE {
        sonusDsCurrentShelfIndex        SonusShelfIndex,
        sonusDsStatusCurrentLocalPolicyRequestAttempted               PerfCurrentCount,
        sonusDsStatusCurrentLocalPolicyRequestSuccessfulResponse                        PerfCurrentCount,
        sonusDsStatusCurrentLocalPolicyRequestRedirectedResponse                        PerfCurrentCount,
        sonusDsStatusCurrentLocalPolicyRequestFailureResponse                     PerfCurrentCount,
        sonusDsStatusCurrentPsxPolicyRequestAttempted             PerfCurrentCount,
        sonusDsStatusCurrentPsxPolicyRequestSuccessfulResponse                      PerfCurrentCount,
        sonusDsStatusCurrentPsxPolicyRequestFailureResponse                   PerfCurrentCount
    }

sonusDsCurrentShelfIndex OBJECT-TYPE
    SYNTAX          SonusShelfIndex
    MAX-ACCESS      read-only
    STATUS          current
    DESCRIPTION     
            "The shelf index into the sonusDsCurrentTable."
    ::= { sonusDsCurrentEntry 1 }

sonusDsStatusCurrentLocalPolicyRequestAttempted OBJECT-TYPE
    SYNTAX          PerfCurrentCount
    MAX-ACCESS      read-only
    STATUS          current
    DESCRIPTION     
            "The number of Policy Requests to Local Policy Server."
    ::= { sonusDsCurrentEntry 2 }

sonusDsStatusCurrentLocalPolicyRequestSuccessfulResponse OBJECT-TYPE
    SYNTAX          PerfCurrentCount
    MAX-ACCESS      read-only
    STATUS          current
    DESCRIPTION     
            "The number of Sussessful Policy Responses from Local Policy Server."
    ::= { sonusDsCurrentEntry 3 }

sonusDsStatusCurrentLocalPolicyRequestRedirectedResponse OBJECT-TYPE
    SYNTAX          PerfCurrentCount
    MAX-ACCESS      read-only
    STATUS          current
    DESCRIPTION     
            "The number of Redirected Responses from Local Policy Server to PSX."
    ::= { sonusDsCurrentEntry 4 }

sonusDsStatusCurrentLocalPolicyRequestFailureResponse OBJECT-TYPE
    SYNTAX          PerfCurrentCount
    MAX-ACCESS      read-only
    STATUS          current
    DESCRIPTION     
            "The number of Failure Responses from Local Policy Server."
    ::= { sonusDsCurrentEntry 5 }

sonusDsStatusCurrentPsxPolicyRequestAttempted OBJECT-TYPE
    SYNTAX          PerfCurrentCount
    MAX-ACCESS      read-only
    STATUS          current
    DESCRIPTION     
            "The number of Policy Requests to PSX."
    ::= { sonusDsCurrentEntry 6 }

sonusDsStatusCurrentPsxPolicyRequestSuccessfulResponse OBJECT-TYPE
    SYNTAX          PerfCurrentCount
    MAX-ACCESS      read-only
    STATUS          current
    DESCRIPTION     
            "The number of Sussessful Policy Responses from PSX."
    ::= { sonusDsCurrentEntry 7 }

sonusDsStatusCurrentPsxPolicyRequestFailureResponse OBJECT-TYPE
    SYNTAX          PerfCurrentCount
    MAX-ACCESS      read-only
    STATUS          current
    DESCRIPTION     
            "The number of Failure Responses from PSX."
    ::= { sonusDsCurrentEntry 8 }

sonusDsIntervalTable OBJECT-TYPE
    SYNTAX          SEQUENCE OF SonusDsIntervalEntry
    MAX-ACCESS      not-accessible
    STATUS          current
    DESCRIPTION     
            "This table presents DS interval statistics."
    ::= { sonusDsStatisticsObjects 2 }

sonusDsIntervalEntry OBJECT-TYPE
    SYNTAX          SonusDsIntervalEntry
    MAX-ACCESS      not-accessible
    STATUS          current
    DESCRIPTION     
            ""
    INDEX           { sonusDsIntervalShelfIndex, sonusDsIntervalNumber }
    ::= { sonusDsIntervalTable 1 }

SonusDsIntervalEntry ::=
    SEQUENCE {
        sonusDsIntervalShelfIndex       SonusShelfIndex,
        sonusDsIntervalNumber           Integer32,
        sonusDsIntervalValidData        TruthValue,
        sonusDsStatusIntervalLocalPolicyRequestAttempted                PerfIntervalCount,
        sonusDsStatusIntervalLocalPolicyRequestSuccessfulResponse                         PerfIntervalCount,
        sonusDsStatusIntervalLocalPolicyRequestRedirectedResponse                         PerfIntervalCount,
        sonusDsStatusIntervalLocalPolicyRequestFailureResponse                      PerfIntervalCount,
        sonusDsStatusIntervalPsxPolicyRequestAttempted              PerfIntervalCount,
        sonusDsStatusIntervalPsxPolicyRequestSuccessfulResponse                       PerfIntervalCount,
        sonusDsStatusIntervalPsxPolicyRequestFailureResponse                    PerfIntervalCount,
        sonusDsIntervalTime             TimeTicks
    }

sonusDsIntervalShelfIndex OBJECT-TYPE
    SYNTAX          SonusShelfIndex
    MAX-ACCESS      read-only
    STATUS          current
    DESCRIPTION     
            "The shelf index into the sonusDsIntervalTable."
    ::= { sonusDsIntervalEntry 1 }

sonusDsIntervalNumber OBJECT-TYPE
    SYNTAX          Integer32 (1..288)
    MAX-ACCESS      read-only
    STATUS          current
    DESCRIPTION     
            "A number between 1 and 288, which identifies the
             one identified by N-1."
    ::= { sonusDsIntervalEntry 2 }

sonusDsIntervalValidData OBJECT-TYPE
    SYNTAX          TruthValue
    MAX-ACCESS      read-only
    STATUS          current
    DESCRIPTION     
            "Indicates if this current data is valid."
    ::= { sonusDsIntervalEntry 3 }

sonusDsStatusIntervalLocalPolicyRequestAttempted OBJECT-TYPE
    SYNTAX          PerfIntervalCount
    MAX-ACCESS      read-only
    STATUS          current
    DESCRIPTION     
            "The number of Policy Requests to Local Policy Server."
    ::= { sonusDsIntervalEntry 4 }

sonusDsStatusIntervalLocalPolicyRequestSuccessfulResponse OBJECT-TYPE
    SYNTAX          PerfIntervalCount
    MAX-ACCESS      read-only
    STATUS          current
    DESCRIPTION     
            "The number of Sussessful Policy Responses from Local Policy Server."
    ::= { sonusDsIntervalEntry 5 }

sonusDsStatusIntervalLocalPolicyRequestRedirectedResponse OBJECT-TYPE
    SYNTAX          PerfIntervalCount
    MAX-ACCESS      read-only
    STATUS          current
    DESCRIPTION     
            "The number of Redirected Responses from Local Policy Server to PSX."
    ::= { sonusDsIntervalEntry 6 }

sonusDsStatusIntervalLocalPolicyRequestFailureResponse OBJECT-TYPE
    SYNTAX          PerfIntervalCount
    MAX-ACCESS      read-only
    STATUS          current
    DESCRIPTION     
            "The number of Failure Responses from Local Policy Server."
    ::= { sonusDsIntervalEntry 7 }

sonusDsStatusIntervalPsxPolicyRequestAttempted OBJECT-TYPE
    SYNTAX          PerfIntervalCount
    MAX-ACCESS      read-only
    STATUS          current
    DESCRIPTION     
            "The number of Policy Requests to PSX."
    ::= { sonusDsIntervalEntry 8 }

sonusDsStatusIntervalPsxPolicyRequestSuccessfulResponse OBJECT-TYPE
    SYNTAX          PerfIntervalCount
    MAX-ACCESS      read-only
    STATUS          current
    DESCRIPTION     
            "The number of Sussessful Policy Responses from PSX."
    ::= { sonusDsIntervalEntry 9 }

sonusDsStatusIntervalPsxPolicyRequestFailureResponse OBJECT-TYPE
    SYNTAX          PerfIntervalCount
    MAX-ACCESS      read-only
    STATUS          current
    DESCRIPTION     
            "The number of Failure Responses from PSX."
    ::= { sonusDsIntervalEntry 10 }

sonusDsIntervalTime OBJECT-TYPE
    SYNTAX          TimeTicks
    MAX-ACCESS      read-only
    STATUS          current
    DESCRIPTION     
            "This variable contains the end of interval time stamp for the specified interval."
    ::= { sonusDsIntervalEntry 11 }

sonusMlppStatisticsObjects OBJECT IDENTIFIER
    ::= { sonusPerformanceStatisticsObjects 11 }

sonusMlppCurrentTable OBJECT-TYPE
    SYNTAX          SEQUENCE OF SonusMlppCurrentEntry
    MAX-ACCESS      not-accessible
    STATUS          current
    DESCRIPTION     
            "The Multi-Level Precedence and Preemption current statistics table."
    ::= { sonusMlppStatisticsObjects 1 }

sonusMlppCurrentEntry OBJECT-TYPE
    SYNTAX          SonusMlppCurrentEntry
    MAX-ACCESS      not-accessible
    STATUS          current
    DESCRIPTION     
            "An entry in the Multi-Level Precedence and Preemption current
             statistics table."
    INDEX           { sonusMlppCurrentShelfIndex }
    ::= { sonusMlppCurrentTable 1 }

SonusMlppCurrentEntry ::=
    SEQUENCE {
        sonusMlppCurrentShelfIndex      SonusShelfIndex,
        sonusMlppCurrentValidData       TruthValue,
        sonusMlppCurrentEgressPstnTgPreemptedCalls          PerfCurrentCount,
        sonusMlppCurrentEgressIpTgPreemptedCalls        PerfCurrentCount,
        sonusMlppCurrentIngressIpTgPreemptedCalls         PerfCurrentCount,
        sonusMlppCurrentEgressPstnTgPrecedenceCallsBlocked                  PerfCurrentCount,
        sonusMlppCurrentEgressIpTgPrecedenceCallsBlocked                PerfCurrentCount,
        sonusMlppCurrentIngressIpTgPrecedenceCallsBlocked                 PerfCurrentCount,
        sonusMlppCurrentPrecedenceCallsExemptFromTrafficCtrl                    PerfCurrentCount
    }

sonusMlppCurrentShelfIndex OBJECT-TYPE
    SYNTAX          SonusShelfIndex
    MAX-ACCESS      read-only
    STATUS          current
    DESCRIPTION     
            "The shelf index into the sonusMlppCurrentTable."
    ::= { sonusMlppCurrentEntry 1 }

sonusMlppCurrentValidData OBJECT-TYPE
    SYNTAX          TruthValue
    MAX-ACCESS      read-only
    STATUS          current
    DESCRIPTION     
            "Indicates if this current data is valid."
    ::= { sonusMlppCurrentEntry 2 }

sonusMlppCurrentEgressPstnTgPreemptedCalls OBJECT-TYPE
    SYNTAX          PerfCurrentCount
    MAX-ACCESS      read-only
    STATUS          current
    DESCRIPTION     
            "Current number of preempted calls on all Egress PSTN Trunks."
    ::= { sonusMlppCurrentEntry 3 }

sonusMlppCurrentEgressIpTgPreemptedCalls OBJECT-TYPE
    SYNTAX          PerfCurrentCount
    MAX-ACCESS      read-only
    STATUS          current
    DESCRIPTION     
            "Current number of preempted calls on all Egress IP Trunks."
    ::= { sonusMlppCurrentEntry 4 }

sonusMlppCurrentIngressIpTgPreemptedCalls OBJECT-TYPE
    SYNTAX          PerfCurrentCount
    MAX-ACCESS      read-only
    STATUS          current
    DESCRIPTION     
            "Current number of preempted calls on all Ingress IP Trunks."
    ::= { sonusMlppCurrentEntry 5 }

sonusMlppCurrentEgressPstnTgPrecedenceCallsBlocked OBJECT-TYPE
    SYNTAX          PerfCurrentCount
    MAX-ACCESS      read-only
    STATUS          current
    DESCRIPTION     
            "Current number of precedence calls blocked on all Egress PSTN Trunks."
    ::= { sonusMlppCurrentEntry 6 }

sonusMlppCurrentEgressIpTgPrecedenceCallsBlocked OBJECT-TYPE
    SYNTAX          PerfCurrentCount
    MAX-ACCESS      read-only
    STATUS          current
    DESCRIPTION     
            "Current number of precedence calls blocked on all Egress IP Trunks."
    ::= { sonusMlppCurrentEntry 7 }

sonusMlppCurrentIngressIpTgPrecedenceCallsBlocked OBJECT-TYPE
    SYNTAX          PerfCurrentCount
    MAX-ACCESS      read-only
    STATUS          current
    DESCRIPTION     
            "Current number of precedence calls blocked on all Ingress IP Trunks."
    ::= { sonusMlppCurrentEntry 8 }

sonusMlppCurrentPrecedenceCallsExemptFromTrafficCtrl OBJECT-TYPE
    SYNTAX          PerfCurrentCount
    MAX-ACCESS      read-only
    STATUS          current
    DESCRIPTION     
            "Current number of precedence calls exempt from traffic controls
             on all Trunks."
    ::= { sonusMlppCurrentEntry 9 }

sonusMlppIntervalTable OBJECT-TYPE
    SYNTAX          SEQUENCE OF SonusMlppIntervalEntry
    MAX-ACCESS      not-accessible
    STATUS          current
    DESCRIPTION     
            "The Multi-Level Precedence and Preemption interval statistics table."
    ::= { sonusMlppStatisticsObjects 2 }

sonusMlppIntervalEntry OBJECT-TYPE
    SYNTAX          SonusMlppIntervalEntry
    MAX-ACCESS      not-accessible
    STATUS          current
    DESCRIPTION     
            "An entry in the Multi-Level Precedence and Preemption interval
             statistics table."
    INDEX           { sonusMlppIntervalShelfIndex, 
                      sonusMlppIntervalNumber }
    ::= { sonusMlppIntervalTable 1 }

SonusMlppIntervalEntry ::=
    SEQUENCE {
        sonusMlppIntervalShelfIndex     SonusShelfIndex,
        sonusMlppIntervalNumber         Integer32,
        sonusMlppIntervalTime           TimeTicks,
        sonusMlppIntervalValidData      TruthValue,
        sonusMlppIntervalEgressPstnTgPreemptedCalls           PerfIntervalCount,
        sonusMlppIntervalEgressIpTgPreemptedCalls         PerfIntervalCount,
        sonusMlppIntervalIngressIpTgPreemptedCalls          PerfIntervalCount,
        sonusMlppIntervalEgressPstnTgPrecedenceCallsBlocked                   PerfIntervalCount,
        sonusMlppIntervalEgressIpTgPrecedenceCallsBlocked                 PerfIntervalCount,
        sonusMlppIntervalIngressIpTgPrecedenceCallsBlocked                  PerfIntervalCount,
        sonusMlppIntervalPrecedenceCallsExemptFromTrafficCtrl                     PerfIntervalCount
    }

sonusMlppIntervalShelfIndex OBJECT-TYPE
    SYNTAX          SonusShelfIndex
    MAX-ACCESS      read-only
    STATUS          current
    DESCRIPTION     
            "The index into the sonusMlppIntervalTable."
    ::= { sonusMlppIntervalEntry 1 }

sonusMlppIntervalNumber OBJECT-TYPE
    SYNTAX          Integer32 (1..288)
    MAX-ACCESS      read-only
    STATUS          current
    DESCRIPTION     
            "A number between 1 and 288, which identifies the
             interval for which the set of statistics is available.
             The interval identified by 1 is the most recently
             completed interval, and the interval identified
             by N is the interval immediately preceding the
             one identified by N-1."
    ::= { sonusMlppIntervalEntry 2 }

sonusMlppIntervalTime OBJECT-TYPE
    SYNTAX          TimeTicks
    MAX-ACCESS      read-only
    STATUS          current
    DESCRIPTION     
            "This variable contains the end of interval time
             stamp for the specified interval."
    ::= { sonusMlppIntervalEntry 3 }

sonusMlppIntervalValidData OBJECT-TYPE
    SYNTAX          TruthValue
    MAX-ACCESS      read-only
    STATUS          current
    DESCRIPTION     
            "This variable indicates if the data for this
             interval is valid."
    ::= { sonusMlppIntervalEntry 4 }

sonusMlppIntervalEgressPstnTgPreemptedCalls OBJECT-TYPE
    SYNTAX          PerfIntervalCount
    MAX-ACCESS      read-only
    STATUS          current
    DESCRIPTION     
            "Number of preempted calls on all Egress PSTN Trunks for
             the specified interval."
    ::= { sonusMlppIntervalEntry 5 }

sonusMlppIntervalEgressIpTgPreemptedCalls OBJECT-TYPE
    SYNTAX          PerfIntervalCount
    MAX-ACCESS      read-only
    STATUS          current
    DESCRIPTION     
            "Number of preempted calls on all Egress IP Trunks for
             the specified interval."
    ::= { sonusMlppIntervalEntry 6 }

sonusMlppIntervalIngressIpTgPreemptedCalls OBJECT-TYPE
    SYNTAX          PerfIntervalCount
    MAX-ACCESS      read-only
    STATUS          current
    DESCRIPTION     
            "Number of preempted calls on all Ingress IP Trunks for
             the specified interval."
    ::= { sonusMlppIntervalEntry 7 }

sonusMlppIntervalEgressPstnTgPrecedenceCallsBlocked OBJECT-TYPE
    SYNTAX          PerfIntervalCount
    MAX-ACCESS      read-only
    STATUS          current
    DESCRIPTION     
            "Number of precedence calls blocked on all Egress PSTN Trunks for
             the specified interval."
    ::= { sonusMlppIntervalEntry 8 }

sonusMlppIntervalEgressIpTgPrecedenceCallsBlocked OBJECT-TYPE
    SYNTAX          PerfIntervalCount
    MAX-ACCESS      read-only
    STATUS          current
    DESCRIPTION     
            "Number of precedence calls blocked on all Egress IP Trunks for
             the specified interval."
    ::= { sonusMlppIntervalEntry 9 }

sonusMlppIntervalIngressIpTgPrecedenceCallsBlocked OBJECT-TYPE
    SYNTAX          PerfIntervalCount
    MAX-ACCESS      read-only
    STATUS          current
    DESCRIPTION     
            "Number of precedence calls blocked on all Ingress IP Trunks for
             the specified interval."
    ::= { sonusMlppIntervalEntry 10 }

sonusMlppIntervalPrecedenceCallsExemptFromTrafficCtrl OBJECT-TYPE
    SYNTAX          PerfIntervalCount
    MAX-ACCESS      read-only
    STATUS          current
    DESCRIPTION     
            "Number of of precedence calls exempt from traffic controls on
             all trunks for the specified interval."
    ::= { sonusMlppIntervalEntry 11 }

sonusPerformanceStatisticsConfigObjects OBJECT IDENTIFIER
    ::= { sonusPerformanceStatisticsObjects 12 }

sonusPfmProfileTable OBJECT-TYPE
    SYNTAX          SEQUENCE OF SonusPfmProfileEntry
    MAX-ACCESS      not-accessible
    STATUS          current
    DESCRIPTION     
            "This contains the details of  PFM profile "
    ::= { sonusPerformanceStatisticsConfigObjects 1 }

sonusPfmProfileEntry OBJECT-TYPE
    SYNTAX          SonusPfmProfileEntry
    MAX-ACCESS      not-accessible
    STATUS          current
    DESCRIPTION     
            "An entry in the Sonus PFM proofile stats table."
    INDEX           { sonusPfmProfileIndex }
    ::= { sonusPfmProfileTable 1 }

SonusPfmProfileEntry ::=
    SEQUENCE {
        sonusPfmProfileIndex            Integer32,
        sonusPfmProfileName             SonusName,
        sonusPfmProfileNodeId           Integer32,
        sonusPfmProfileGranularity      Integer32,
        sonusPfmProfileState            SonusAdminState,
        sonusPfmProfileFileNameUniqueId Integer32,
        sonusPfmProfileRowStatus        RowStatus
    }

sonusPfmProfileIndex OBJECT-TYPE
    SYNTAX          Integer32
    MAX-ACCESS      read-only
    STATUS          current
    DESCRIPTION     
            "index to the profile table "
    ::= { sonusPfmProfileEntry 1 }

sonusPfmProfileName OBJECT-TYPE
    SYNTAX          SonusName
    MAX-ACCESS      read-write
    STATUS          current
    DESCRIPTION     
            "This configures PFM profile name"
    ::= { sonusPfmProfileEntry 2 }

sonusPfmProfileNodeId OBJECT-TYPE
    SYNTAX          Integer32
    MAX-ACCESS      read-write
    STATUS          current
    DESCRIPTION     
            "This configures node id for PFM profile configuration"
    ::= { sonusPfmProfileEntry 3 }

sonusPfmProfileGranularity OBJECT-TYPE
    SYNTAX          Integer32 (5..1440)
    MAX-ACCESS      read-write
    STATUS          current
    DESCRIPTION     
            "This configures the PFM profile granularity period in minutes "
    DEFVAL          { 15 }
    ::= { sonusPfmProfileEntry 4 }

sonusPfmProfileState OBJECT-TYPE
    SYNTAX          SonusAdminState
    MAX-ACCESS      read-write
    STATUS          current
    DESCRIPTION     
            "This configures whether PFM profile is Enabled or 
             Disabled for the Node"
    DEFVAL          { disabled }
    ::= { sonusPfmProfileEntry 5 }

sonusPfmProfileFileNameUniqueId OBJECT-TYPE
    SYNTAX          Integer32
    MAX-ACCESS      read-only
    STATUS          current
    DESCRIPTION     
            "This contains the number of stats which can be requested "
    DEFVAL          { 678 }
    ::= { sonusPfmProfileEntry 6 }

sonusPfmProfileRowStatus OBJECT-TYPE
    SYNTAX          RowStatus
    MAX-ACCESS      read-write
    STATUS          current
    DESCRIPTION     
            "This is for SNMP use."
    ::= { sonusPfmProfileEntry 7 }

sonusPfmProfileStatsTable OBJECT-TYPE
    SYNTAX          SEQUENCE OF SonusPfmProfileStatsEntry
    MAX-ACCESS      not-accessible
    STATUS          current
    DESCRIPTION     
            "This contains the details of stats tables in PFM profile "
    ::= { sonusPerformanceStatisticsConfigObjects 2 }

sonusPfmProfileStatsEntry OBJECT-TYPE
    SYNTAX          SonusPfmProfileStatsEntry
    MAX-ACCESS      not-accessible
    STATUS          current
    DESCRIPTION     
            "An entry in the Sonus PFM proofile stats table."
    INDEX           { sonusPfmProfileNameIndex, 
                      sonusPfmProfileStatsIndex }
    ::= { sonusPfmProfileStatsTable 1 }

SonusPfmProfileStatsEntry ::=
    SEQUENCE {
        sonusPfmProfileNameIndex        Integer32,
        sonusPfmProfileStatsIndex       INTEGER,
        sonusPfmProfileStatsGranularity Integer32,
        sonusPfmProfileStatsState       SonusAdminState,
        sonusPfmProfileStatsRowStatus   RowStatus
    }

sonusPfmProfileNameIndex OBJECT-TYPE
    SYNTAX          Integer32
    MAX-ACCESS      read-only
    STATUS          current
    DESCRIPTION     
            "This identifies all the stats belonging to one profile"
    ::= { sonusPfmProfileStatsEntry 1 }

sonusPfmProfileStatsIndex OBJECT-TYPE
    SYNTAX          INTEGER { systemcongestionstats(1), gsxhpcstats(2), 
                        gsxsyscalldspresstats(3), gsxsysdspresstats(4), 
                        gsxmlppstatusstats(5), accountingsummarystats(6), 
                        callcountstats(7), gatewaycallstats(8), 
                        systemstats(9), gsxdspslotstats(10), 
                        gsxslotdspresstats(11), gsximstatusstats(12), 
                        pnsenetstats(13), softswitchstats(14), 
                        sonetstats(15), gsxsiphpcstats(16), 
                        trunkgroupstats(17), gsxsipsigporttlsstats(18), 
                        gsxsipsigportlsstatusstats(19), 
                        trunkgroupcurrentstats(20), 
                        sonicbususagestats(21), ss7linkstats(22), 
                        ss7routestats(23), ss7destinationstats(24), 
                        gsxsyslicenseusagestats(25) }
    MAX-ACCESS      read-write
    STATUS          current
    DESCRIPTION     
            "This contais stats name index for PFM profile"
    ::= { sonusPfmProfileStatsEntry 2 }

sonusPfmProfileStatsGranularity OBJECT-TYPE
    SYNTAX          Integer32 (1..1440)
    MAX-ACCESS      read-write
    STATUS          current
    DESCRIPTION     
            "This configures the stats granularity period in minutes "
    DEFVAL          { 5 }
    ::= { sonusPfmProfileStatsEntry 3 }

sonusPfmProfileStatsState OBJECT-TYPE
    SYNTAX          SonusAdminState
    MAX-ACCESS      read-write
    STATUS          current
    DESCRIPTION     
            "This indicates whether the stats is Enabled or Disabled for a PFM profile "
    DEFVAL          { disabled }
    ::= { sonusPfmProfileStatsEntry 4 }

sonusPfmProfileStatsRowStatus OBJECT-TYPE
    SYNTAX          RowStatus
    MAX-ACCESS      read-write
    STATUS          current
    DESCRIPTION     
            "This is for SNMP use."
    ::= { sonusPfmProfileStatsEntry 5 }

sonusSonicBusUsageStatisticsObjects OBJECT IDENTIFIER
    ::= { sonusPerformanceStatisticsObjects 13 }

sonusSonicBusUsageStatCurrentTable OBJECT-TYPE
    SYNTAX          SEQUENCE OF SonusSonicBusUsageStatCurrentEntry
    MAX-ACCESS      not-accessible
    STATUS          current
    DESCRIPTION     
            "The Sonic Bus Usage current statistics table."
    ::= { sonusSonicBusUsageStatisticsObjects 1 }

sonusSonicBusUsageStatCurrentEntry OBJECT-TYPE
    SYNTAX          SonusSonicBusUsageStatCurrentEntry
    MAX-ACCESS      not-accessible
    STATUS          current
    DESCRIPTION     
            "An entry in the Sonic Bus usage current statistics table."
    INDEX           { sonusSonicBusUsageStatCurrentShelfIndex }
    ::= { sonusSonicBusUsageStatCurrentTable 1 }

SonusSonicBusUsageStatCurrentEntry ::=
    SEQUENCE {
        sonusSonicBusUsageStatCurrentShelfIndex       SonusShelfIndex,
        sonusSonicBusUsageStatCurrentValidData      TruthValue,
        sonusStatCurrentSonicBusUsage   PerfCurrentCount,
        sonusStatCurrentSonicBusPeakUsage PerfCurrentCount,
        sonusStatCurrentSonicBusAvgUsage PerfCurrentCount
    }

sonusSonicBusUsageStatCurrentShelfIndex OBJECT-TYPE
    SYNTAX          SonusShelfIndex
    MAX-ACCESS      read-only
    STATUS          current
    DESCRIPTION     
            "The shelf index into the sonusSonicBusUsageStatsCurrentTable."
    ::= { sonusSonicBusUsageStatCurrentEntry 1 }

sonusSonicBusUsageStatCurrentValidData OBJECT-TYPE
    SYNTAX          TruthValue
    MAX-ACCESS      read-only
    STATUS          current
    DESCRIPTION     
            "Indicates if this current data is valid."
    ::= { sonusSonicBusUsageStatCurrentEntry 2 }

sonusStatCurrentSonicBusUsage OBJECT-TYPE
    SYNTAX          PerfCurrentCount
    MAX-ACCESS      read-only
    STATUS          current
    DESCRIPTION     
            "Current sonic Bus usage in the midplane"
    ::= { sonusSonicBusUsageStatCurrentEntry 3 }

sonusStatCurrentSonicBusPeakUsage OBJECT-TYPE
    SYNTAX          PerfCurrentCount
    MAX-ACCESS      read-only
    STATUS          current
    DESCRIPTION     
            "SonicBus Usage in the midplane for the specified interval."
    ::= { sonusSonicBusUsageStatCurrentEntry 4 }

sonusStatCurrentSonicBusAvgUsage OBJECT-TYPE
    SYNTAX          PerfCurrentCount
    MAX-ACCESS      read-only
    STATUS          current
    DESCRIPTION     
            "SonicBus Usage in the midplane for the specified interval."
    ::= { sonusSonicBusUsageStatCurrentEntry 5 }

sonusSonicBusUsageStatIntervalTable OBJECT-TYPE
    SYNTAX          SEQUENCE OF SonusSonicBusUsageStatIntervalEntry
    MAX-ACCESS      not-accessible
    STATUS          current
    DESCRIPTION     
            "The Midplane Usage interval statistics table."
    ::= { sonusSonicBusUsageStatisticsObjects 2 }

sonusSonicBusUsageStatIntervalEntry OBJECT-TYPE
    SYNTAX          SonusSonicBusUsageStatIntervalEntry
    MAX-ACCESS      not-accessible
    STATUS          current
    DESCRIPTION     
            "An entry in the SonicBus Usage interval
             statistics table."
    INDEX           { sonusSonicBusUsageStatIntervalShelfIndex, 
                      sonusSonicBusUsageStatIntervalNumber }
    ::= { sonusSonicBusUsageStatIntervalTable 1 }

SonusSonicBusUsageStatIntervalEntry ::=
    SEQUENCE {
        sonusSonicBusUsageStatIntervalShelfIndex        SonusShelfIndex,
        sonusSonicBusUsageStatIntervalNumber    Integer32,
        sonusSonicBusUsageStatIntervalTime  TimeTicks,
        sonusSonicBusUsageStatIntervalValidData       TruthValue,
        sonusStatIntervalSonicBusUsage  PerfIntervalCount,
        sonusStatIntervalSonicBusPeakUsage  PerfIntervalCount,
        sonusStatIntervalSonicBusAvgUsage PerfIntervalCount
    }

sonusSonicBusUsageStatIntervalShelfIndex OBJECT-TYPE
    SYNTAX          SonusShelfIndex
    MAX-ACCESS      read-only
    STATUS          current
    DESCRIPTION     
            "The index into the sonusSonicBusUsageStatIntervalTable."
    ::= { sonusSonicBusUsageStatIntervalEntry 1 }

sonusSonicBusUsageStatIntervalNumber OBJECT-TYPE
    SYNTAX          Integer32 (1..288)
    MAX-ACCESS      read-only
    STATUS          current
    DESCRIPTION     
            "A number between 1 and 288, which identifies the
             interval for which the set of statistics is available.
             The interval identified by 1 is the most recently
             completed interval, and the interval identified
             by N is the interval immediately preceding the
             one identified by N-1."
    ::= { sonusSonicBusUsageStatIntervalEntry 2 }

sonusSonicBusUsageStatIntervalTime OBJECT-TYPE
    SYNTAX          TimeTicks
    MAX-ACCESS      read-only
    STATUS          current
    DESCRIPTION     
            "This variable contains the end of interval time
             stamp for the specified interval."
    ::= { sonusSonicBusUsageStatIntervalEntry 3 }

sonusSonicBusUsageStatIntervalValidData OBJECT-TYPE
    SYNTAX          TruthValue
    MAX-ACCESS      read-only
    STATUS          current
    DESCRIPTION     
            "This variable indicates if the data for this
             interval is valid."
    ::= { sonusSonicBusUsageStatIntervalEntry 4 }

sonusStatIntervalSonicBusUsage OBJECT-TYPE
    SYNTAX          PerfIntervalCount
    MAX-ACCESS      read-only
    STATUS          current
    DESCRIPTION     
            "Current sonic Bus usage in the midplane"
    ::= { sonusSonicBusUsageStatIntervalEntry 5 }

sonusStatIntervalSonicBusPeakUsage OBJECT-TYPE
    SYNTAX          PerfIntervalCount
    MAX-ACCESS      read-only
    STATUS          current
    DESCRIPTION     
            "SonicBus Usage in the midplane for the specified interval."
    ::= { sonusSonicBusUsageStatIntervalEntry 6 }

sonusStatIntervalSonicBusAvgUsage OBJECT-TYPE
    SYNTAX          PerfIntervalCount
    MAX-ACCESS      read-only
    STATUS          current
    DESCRIPTION     
            "SonicBus Usage in the midplane for the specified interval."
    ::= { sonusSonicBusUsageStatIntervalEntry 7 }

sonusPeakCallStatisticsObjects OBJECT IDENTIFIER
    ::= { sonusPerformanceStatisticsObjects 14 }

sonusPeakCallStatCurrentTable OBJECT-TYPE
    SYNTAX          SEQUENCE OF SonusPeakCallStatCurrentEntry
    MAX-ACCESS      not-accessible
    STATUS          current
    DESCRIPTION     
            "The peak stable call current statistics table."
    ::= { sonusPeakCallStatisticsObjects 1 }

sonusPeakCallStatCurrentEntry OBJECT-TYPE
    SYNTAX          SonusPeakCallStatCurrentEntry
    MAX-ACCESS      not-accessible
    STATUS          current
    DESCRIPTION     
            "An entry in the Peak call count current statistics table."
    INDEX           { sonusNRMPeakCurrentShelfIndex }
    ::= { sonusPeakCallStatCurrentTable 1 }

SonusPeakCallStatCurrentEntry ::=
    SEQUENCE {
        sonusNRMPeakCurrentShelfIndex   SonusShelfIndex,
        sonusCurrentPeakPSTNtoSIPcalls  PerfCurrentCount,
        sonusCurrentPeakPSTNtoH323calls PerfCurrentCount,
        sonusCurrentPeakPSTNtoSIPTcalls PerfCurrentCount,
        sonusCurrentPeakPSTNtoGWcalls   PerfCurrentCount,
        sonusCurrentPeakPSTNtoPSTNcalls PerfCurrentCount,
        sonusCurrentPeakSIPtoSIPcalls   PerfCurrentCount,
        sonusCurrentPeakSIPtoGWcalls    PerfCurrentCount,
        sonusCurrentPeakSIPtoH323calls  PerfCurrentCount,
        sonusCurrentPeakH323toH323calls PerfCurrentCount,
        sonusCurrentPeakH323toGWcalls   PerfCurrentCount,
        sonusCurrentPeakP2Pcalls        PerfCurrentCount,
        sonusCurrentPeakSIPTtoSIPcalls  PerfCurrentCount,
        sonusCurrentPeakSIPTtoGWcalls   PerfCurrentCount,
        sonusCurrentPeakSIPTtoH323calls PerfCurrentCount,
        sonusCurrentPeakSIPTtoSIPTcalls PerfCurrentCount
    }

sonusNRMPeakCurrentShelfIndex OBJECT-TYPE
    SYNTAX          SonusShelfIndex
    MAX-ACCESS      read-only
    STATUS          current
    DESCRIPTION     
            "The shelf index into the sonusPeakCallStatCurrentTable."
    ::= { sonusPeakCallStatCurrentEntry 1 }

sonusCurrentPeakPSTNtoSIPcalls OBJECT-TYPE
    SYNTAX          PerfCurrentCount
    MAX-ACCESS      read-only
    STATUS          current
    DESCRIPTION     
            "Current Peak Count for PSTN to SIP"
    ::= { sonusPeakCallStatCurrentEntry 2 }

sonusCurrentPeakPSTNtoH323calls OBJECT-TYPE
    SYNTAX          PerfCurrentCount
    MAX-ACCESS      read-only
    STATUS          current
    DESCRIPTION     
            "Current Peak Count for PSTN to H323"
    ::= { sonusPeakCallStatCurrentEntry 3 }

sonusCurrentPeakPSTNtoSIPTcalls OBJECT-TYPE
    SYNTAX          PerfCurrentCount
    MAX-ACCESS      read-only
    STATUS          current
    DESCRIPTION     
            "Current Peak Count for PSTN to SIPT"
    ::= { sonusPeakCallStatCurrentEntry 4 }

sonusCurrentPeakPSTNtoGWcalls OBJECT-TYPE
    SYNTAX          PerfCurrentCount
    MAX-ACCESS      read-only
    STATUS          current
    DESCRIPTION     
            "Current Peak Count for PSTN to GW"
    ::= { sonusPeakCallStatCurrentEntry 5 }

sonusCurrentPeakPSTNtoPSTNcalls OBJECT-TYPE
    SYNTAX          PerfCurrentCount
    MAX-ACCESS      read-only
    STATUS          current
    DESCRIPTION     
            "Current Peak Count for PSTN to PSTN"
    ::= { sonusPeakCallStatCurrentEntry 6 }

sonusCurrentPeakSIPtoSIPcalls OBJECT-TYPE
    SYNTAX          PerfCurrentCount
    MAX-ACCESS      read-only
    STATUS          current
    DESCRIPTION     
            "Current Peak Count for SIP to SIP"
    ::= { sonusPeakCallStatCurrentEntry 7 }

sonusCurrentPeakSIPtoGWcalls OBJECT-TYPE
    SYNTAX          PerfCurrentCount
    MAX-ACCESS      read-only
    STATUS          current
    DESCRIPTION     
            "Current Peak Count for SIP to GW"
    ::= { sonusPeakCallStatCurrentEntry 8 }

sonusCurrentPeakSIPtoH323calls OBJECT-TYPE
    SYNTAX          PerfCurrentCount
    MAX-ACCESS      read-only
    STATUS          current
    DESCRIPTION     
            "Current Peak Count for SIP to H323"
    ::= { sonusPeakCallStatCurrentEntry 9 }

sonusCurrentPeakH323toH323calls OBJECT-TYPE
    SYNTAX          PerfCurrentCount
    MAX-ACCESS      read-only
    STATUS          current
    DESCRIPTION     
            "Current Peak Count for H323 to H323"
    ::= { sonusPeakCallStatCurrentEntry 10 }

sonusCurrentPeakH323toGWcalls OBJECT-TYPE
    SYNTAX          PerfCurrentCount
    MAX-ACCESS      read-only
    STATUS          current
    DESCRIPTION     
            "Current Peak Count for H323 to GW"
    ::= { sonusPeakCallStatCurrentEntry 11 }

sonusCurrentPeakP2Pcalls OBJECT-TYPE
    SYNTAX          PerfCurrentCount
    MAX-ACCESS      read-only
    STATUS          current
    DESCRIPTION     
            "Current Peak Count for P2P calls"
    ::= { sonusPeakCallStatCurrentEntry 12 }

sonusCurrentPeakSIPTtoSIPcalls OBJECT-TYPE
    SYNTAX          PerfCurrentCount
    MAX-ACCESS      read-only
    STATUS          current
    DESCRIPTION     
            "Current Peak Count for SIPT to SIP"
    ::= { sonusPeakCallStatCurrentEntry 13 }

sonusCurrentPeakSIPTtoGWcalls OBJECT-TYPE
    SYNTAX          PerfCurrentCount
    MAX-ACCESS      read-only
    STATUS          current
    DESCRIPTION     
            "Current Peak Count for SIPT to GW"
    ::= { sonusPeakCallStatCurrentEntry 14 }

sonusCurrentPeakSIPTtoH323calls OBJECT-TYPE
    SYNTAX          PerfCurrentCount
    MAX-ACCESS      read-only
    STATUS          current
    DESCRIPTION     
            "Current Peak Count for SIPT to H323"
    ::= { sonusPeakCallStatCurrentEntry 15 }

sonusCurrentPeakSIPTtoSIPTcalls OBJECT-TYPE
    SYNTAX          PerfCurrentCount
    MAX-ACCESS      read-only
    STATUS          current
    DESCRIPTION     
            "Current Peak Count for SIPT to SIPT"
    ::= { sonusPeakCallStatCurrentEntry 16 }

sonusPeakCallStatIntervalTable OBJECT-TYPE
    SYNTAX          SEQUENCE OF SonusPeakCallStatIntervalEntry
    MAX-ACCESS      not-accessible
    STATUS          current
    DESCRIPTION     
            "The peak stable call Interval statistics table."
    ::= { sonusPeakCallStatisticsObjects 2 }

sonusPeakCallStatIntervalEntry OBJECT-TYPE
    SYNTAX          SonusPeakCallStatIntervalEntry
    MAX-ACCESS      not-accessible
    STATUS          current
    DESCRIPTION     
            "An entry in the Peak call count Interval statistics table."
    INDEX           { sonusNRMPeakIntervalShelfIndex, 
                      sonusPeakCallIntervalNumber }
    ::= { sonusPeakCallStatIntervalTable 1 }

SonusPeakCallStatIntervalEntry ::=
    SEQUENCE {
        sonusNRMPeakIntervalShelfIndex  SonusShelfIndex,
        sonusPeakCallIntervalNumber     Integer32,
        sonusPeakCallsStatIntervalTime  TimeTicks,
        sonusLicenseUsageIntervalValidData  TruthValue,
        sonusIntervalPeakPSTNtoSIPcalls PerfIntervalCount,
        sonusIntervalPeakPSTNtoH323calls PerfIntervalCount,
        sonusIntervalPeakPSTNtoSIPTcalls PerfIntervalCount,
        sonusIntervalPeakPSTNtoGWcalls  PerfIntervalCount,
        sonusIntervalPeakPSTNtoPSTNcalls PerfIntervalCount,
        sonusIntervalPeakSIPtoSIPcalls  PerfIntervalCount,
        sonusIntervalPeakSIPtoGWcalls   PerfIntervalCount,
        sonusIntervalPeakSIPtoH323calls PerfIntervalCount,
        sonusIntervalPeakH323toH323calls PerfIntervalCount,
        sonusIntervalPeakH323toGWcalls  PerfIntervalCount,
        sonusIntervalPeakP2Pcalls       PerfIntervalCount,
        sonusIntervalPeakSIPTtoSIPcalls PerfIntervalCount,
        sonusIntervalPeakSIPTtoGWcalls  PerfIntervalCount,
        sonusIntervalPeakSIPTtoH323calls PerfIntervalCount,
        sonusIntervalPeakSIPTtoSIPTcalls PerfIntervalCount
    }

sonusNRMPeakIntervalShelfIndex OBJECT-TYPE
    SYNTAX          SonusShelfIndex
    MAX-ACCESS      read-only
    STATUS          current
    DESCRIPTION     
            "The shelf index into the sonusPeakCallStatIntervalTable."
    ::= { sonusPeakCallStatIntervalEntry 1 }

sonusPeakCallIntervalNumber OBJECT-TYPE
    SYNTAX          Integer32 (1..288)
    MAX-ACCESS      read-only
    STATUS          current
    DESCRIPTION     
            "A number between 1 and 288, which identifies the
             interval for which the set of statistics is available.
             The interval identified by 1 is the most recently
             completed interval, and the interval identified
             by N is the interval immediately preceding the
             one identified by N-1."
    ::= { sonusPeakCallStatIntervalEntry 2 }

sonusPeakCallsStatIntervalTime OBJECT-TYPE
    SYNTAX          TimeTicks
    MAX-ACCESS      read-only
    STATUS          current
    DESCRIPTION     
            "This variable contains the end of interval time
             stamp for the specified interval"
    ::= { sonusPeakCallStatIntervalEntry 3 }

sonusLicenseUsageIntervalValidData OBJECT-TYPE
    SYNTAX          TruthValue
    MAX-ACCESS      read-only
    STATUS          current
    DESCRIPTION     
            "This variable indicates if the data for this interval is valid."
    ::= { sonusPeakCallStatIntervalEntry 4 }

sonusIntervalPeakPSTNtoSIPcalls OBJECT-TYPE
    SYNTAX          PerfIntervalCount
    MAX-ACCESS      read-only
    STATUS          current
    DESCRIPTION     
            "Interval Peak Count for PSTN to SIP"
    ::= { sonusPeakCallStatIntervalEntry 5 }

sonusIntervalPeakPSTNtoH323calls OBJECT-TYPE
    SYNTAX          PerfIntervalCount
    MAX-ACCESS      read-only
    STATUS          current
    DESCRIPTION     
            "Interval Peak Count for PSTN to H323"
    ::= { sonusPeakCallStatIntervalEntry 6 }

sonusIntervalPeakPSTNtoSIPTcalls OBJECT-TYPE
    SYNTAX          PerfIntervalCount
    MAX-ACCESS      read-only
    STATUS          current
    DESCRIPTION     
            "Interval Peak Count for PSTN to SIPT"
    ::= { sonusPeakCallStatIntervalEntry 7 }

sonusIntervalPeakPSTNtoGWcalls OBJECT-TYPE
    SYNTAX          PerfIntervalCount
    MAX-ACCESS      read-only
    STATUS          current
    DESCRIPTION     
            "Interval Peak Count for PSTN to GW"
    ::= { sonusPeakCallStatIntervalEntry 8 }

sonusIntervalPeakPSTNtoPSTNcalls OBJECT-TYPE
    SYNTAX          PerfIntervalCount
    MAX-ACCESS      read-only
    STATUS          current
    DESCRIPTION     
            "Interval Peak Count for PSTN to PSTN"
    ::= { sonusPeakCallStatIntervalEntry 9 }

sonusIntervalPeakSIPtoSIPcalls OBJECT-TYPE
    SYNTAX          PerfIntervalCount
    MAX-ACCESS      read-only
    STATUS          current
    DESCRIPTION     
            "Interval Peak Count for SIP to SIP"
    ::= { sonusPeakCallStatIntervalEntry 10 }

sonusIntervalPeakSIPtoGWcalls OBJECT-TYPE
    SYNTAX          PerfIntervalCount
    MAX-ACCESS      read-only
    STATUS          current
    DESCRIPTION     
            "Interval Peak Count for SIP to GW"
    ::= { sonusPeakCallStatIntervalEntry 11 }

sonusIntervalPeakSIPtoH323calls OBJECT-TYPE
    SYNTAX          PerfIntervalCount
    MAX-ACCESS      read-only
    STATUS          current
    DESCRIPTION     
            "Interval Peak Count for SIP to H323"
    ::= { sonusPeakCallStatIntervalEntry 12 }

sonusIntervalPeakH323toH323calls OBJECT-TYPE
    SYNTAX          PerfIntervalCount
    MAX-ACCESS      read-only
    STATUS          current
    DESCRIPTION     
            "Interval Peak Count for H323 to H323"
    ::= { sonusPeakCallStatIntervalEntry 13 }

sonusIntervalPeakH323toGWcalls OBJECT-TYPE
    SYNTAX          PerfIntervalCount
    MAX-ACCESS      read-only
    STATUS          current
    DESCRIPTION     
            "Interval Peak Count for H323 to GW"
    ::= { sonusPeakCallStatIntervalEntry 14 }

sonusIntervalPeakP2Pcalls OBJECT-TYPE
    SYNTAX          PerfIntervalCount
    MAX-ACCESS      read-only
    STATUS          current
    DESCRIPTION     
            "Interval Peak Count for P2P calls"
    ::= { sonusPeakCallStatIntervalEntry 15 }

sonusIntervalPeakSIPTtoSIPcalls OBJECT-TYPE
    SYNTAX          PerfIntervalCount
    MAX-ACCESS      read-only
    STATUS          current
    DESCRIPTION     
            "Interval Peak Count for SIPT to SIP"
    ::= { sonusPeakCallStatIntervalEntry 16 }

sonusIntervalPeakSIPTtoGWcalls OBJECT-TYPE
    SYNTAX          PerfIntervalCount
    MAX-ACCESS      read-only
    STATUS          current
    DESCRIPTION     
            "Interval Peak Count for SIPT to GW"
    ::= { sonusPeakCallStatIntervalEntry 17 }

sonusIntervalPeakSIPTtoH323calls OBJECT-TYPE
    SYNTAX          PerfIntervalCount
    MAX-ACCESS      read-only
    STATUS          current
    DESCRIPTION     
            "Interval Peak Count for SIPT to H323"
    ::= { sonusPeakCallStatIntervalEntry 18 }

sonusIntervalPeakSIPTtoSIPTcalls OBJECT-TYPE
    SYNTAX          PerfIntervalCount
    MAX-ACCESS      read-only
    STATUS          current
    DESCRIPTION     
            "Interval Peak Count for SIPT to SIPT"
    ::= { sonusPeakCallStatIntervalEntry 19 }

END -- end of module SONUS-PERFORMANCE-STATISTICS-MIB.
