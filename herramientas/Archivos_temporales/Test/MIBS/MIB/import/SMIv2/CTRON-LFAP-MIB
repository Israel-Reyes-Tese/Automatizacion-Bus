--
-- This SMIv2 module has been generated by smidump 0.2-cvs. Do not edit.
--

CTRON-LFAP-MIB DEFINITIONS ::= BEGIN

IMPORTS
    ctSystem
        FROM CTRON-MIB-NAMES
    MODULE-COMPLIANCE, OBJECT-GROUP
        FROM SNMPv2-CONF
    Counter32, Gauge32, Integer32, MODULE-IDENTITY, OBJECT-TYPE
        FROM SNMPv2-SMI
    PhysAddress
        FROM SNMPv2-TC;

ctLFAP MODULE-IDENTITY
    LAST-UPDATED    "200006270000Z"
    ORGANIZATION    
            "Cabletron Systems, Inc"
    CONTACT-INFO    
            "Riverstone Networks, Inc
             5200 Great America Parkway
             Santa Clara, CA 95054
             (408) 878-6500
             nms-eng@riverstonenet.com
             http://www.riverstonenet.com"
    DESCRIPTION     
            "This mib module defines an SNMP enterprise MIB under Cabletron
             Enterprise. Initially described in Informational RFC 2124 
             Light-weight Flow Admission Protocol, this mib manages
             a proprietary IP accounting subsystem found on Enterasys SSR
             and Riverstone RS product lines."
    REVISION        "200006270000Z"
    DESCRIPTION     
            "Update contact information, fix name collision with flowPolicyPolling
             object found in ctron-mib-names.txt"
    REVISION        "199912290000Z"
    DESCRIPTION     
            "Upgrade LFAP to version 4. Enhance configuration options."
    REVISION        "199709250000Z"
    DESCRIPTION     
            "First implementation on SSR. LFAP Protocol version 3."
    ::= { ctSystem 11 }


flowPolicy OBJECT IDENTIFIER
    ::= { ctLFAP 1 }

flowPolicyControl OBJECT-TYPE
    SYNTAX          INTEGER { disable(1), enable(2) }
    MAX-ACCESS      read-write
    STATUS          current
    DESCRIPTION     
            "This object allows flow policy to be enabled or disabled on each switch.
             Setting this object to disable(1) disables flow policy functionality on
             the switch. Setting this object to enable(2) enables the flow policy
             function."
    ::= { flowPolicy 1 }

flowPolicyStatus OBJECT-TYPE
    SYNTAX          INTEGER { disabled(1), enabled(2), active(3), 
                        error(4) }
    MAX-ACCESS      read-only
    STATUS          current
    DESCRIPTION     
            "This object gives the status of flow policy processing on each switch.
             The value of disabled(1) indicates that the flow policy function has
             been totally disabled. The value of enabled(2) indicates that the flow
             policy functions have been enabled and is searching for a policy server.
             The value of active(3) indicates that the flow policy function is fully
             operational. The value of error(4) indicates that the flow policy function
             has experienced some fatal error and has disabled itself."
    ::= { flowPolicy 2 }

flowPolicyActiveServer OBJECT-TYPE
    SYNTAX          PhysAddress
    MAX-ACCESS      read-only
    STATUS          current
    DESCRIPTION     
            "This object reflects the IP address of the remote policy server currently
             being used."
    ::= { flowPolicy 3 }

flowPolicyServerAddrTable OBJECT-TYPE
    SYNTAX          SEQUENCE OF FlowPolicyServerAddrEntry
    MAX-ACCESS      not-accessible
    STATUS          current
    DESCRIPTION     
            "An ordered list of flow policy server addresses with which flow policy
             processing will attempt to establish contact."
    ::= { flowPolicy 4 }

flowPolicyServerAddrEntry OBJECT-TYPE
    SYNTAX          FlowPolicyServerAddrEntry
    MAX-ACCESS      not-accessible
    STATUS          current
    DESCRIPTION     
            "A component entry containing objects for a particular server."
    INDEX           { flowPolicyServerAddrIndex }
    ::= { flowPolicyServerAddrTable 1 }

FlowPolicyServerAddrEntry ::=
    SEQUENCE {
        flowPolicyServerAddrIndex       Integer32,
        flowPolicyServerAddr            PhysAddress
    }

flowPolicyServerAddrIndex OBJECT-TYPE
    SYNTAX          Integer32 (1..65535)
    MAX-ACCESS      read-only
    STATUS          current
    DESCRIPTION     
            "A unique value for each flow policy server address that indexes the table."
    ::= { flowPolicyServerAddrEntry 1 }

flowPolicyServerAddr OBJECT-TYPE
    SYNTAX          PhysAddress
    MAX-ACCESS      read-write
    STATUS          current
    DESCRIPTION     
            "This object contains the address of a flow policy server."
    ::= { flowPolicyServerAddrEntry 2 }

flowPolicyConfig OBJECT IDENTIFIER
    ::= { flowPolicy 6 }

flowPolicyConfigPolicy OBJECT-TYPE
    SYNTAX          INTEGER { available(1), unavailable(2) }
    MAX-ACCESS      read-only
    STATUS          current
    DESCRIPTION     
            "This object indicates whether or not the CCE supports connection policy.
             A value of available(1) indicates that connection policy support is
             available from this CCE.  A value of unavailable(2) indicates that this
             CCE is incapable of supporting connection policy."
    ::= { flowPolicyConfig 1 }

flowPolicyConfigStatistics OBJECT-TYPE
    SYNTAX          INTEGER { available(1), unavailable(2) }
    MAX-ACCESS      read-only
    STATUS          current
    DESCRIPTION     
            "This object indicates whether or not the CCE supports connection
             statistics.  A value of available(1) indicates that connection
             statistics are supported from this CCE. A value of unavailable(2)
             indicates that this CCE is incapable of supporting connection
             statistics."
    ::= { flowPolicyConfig 2 }

monLfap OBJECT IDENTIFIER
    ::= { ctLFAP 2 }

monLfapCounts OBJECT IDENTIFIER
    ::= { monLfap 1 }

monLfapFARsSent OBJECT-TYPE
    SYNTAX          Counter32
    MAX-ACCESS      read-only
    STATUS          current
    DESCRIPTION     
            "This object contains the number of LFAP FARs sent from the flow control
             entity (CCE)"
    ::= { monLfapCounts 1 }

monLfapFARsReceived OBJECT-TYPE
    SYNTAX          Counter32
    MAX-ACCESS      read-only
    STATUS          current
    DESCRIPTION     
            "This object contains the number of LFAP FARs received by the CCE."
    ::= { monLfapCounts 2 }

monLfapFAAsSent OBJECT-TYPE
    SYNTAX          Counter32
    MAX-ACCESS      read-only
    STATUS          current
    DESCRIPTION     
            "This object contains the number of LFAP FAAs sent from the CCE."
    ::= { monLfapCounts 3 }

monLfapFAAsReceived OBJECT-TYPE
    SYNTAX          Counter32
    MAX-ACCESS      read-only
    STATUS          current
    DESCRIPTION     
            "This object contains the number of LFAP FAAs received by the CCE."
    ::= { monLfapCounts 4 }

monLfapFAUsSent OBJECT-TYPE
    SYNTAX          Counter32
    MAX-ACCESS      read-only
    STATUS          current
    DESCRIPTION     
            "This object contains the number of LFAP FAUs sent from the CCE."
    ::= { monLfapCounts 5 }

monLfapFAUsReceived OBJECT-TYPE
    SYNTAX          Counter32
    MAX-ACCESS      read-only
    STATUS          current
    DESCRIPTION     
            "This object contains the number of LFAP FAUs received by the CCE."
    ::= { monLfapCounts 6 }

monLfapFUNsSent OBJECT-TYPE
    SYNTAX          Counter32
    MAX-ACCESS      read-only
    STATUS          current
    DESCRIPTION     
            "This object contains the number of LFAP FUNs sent from the CCE."
    ::= { monLfapCounts 7 }

monLfapFUNsReceived OBJECT-TYPE
    SYNTAX          Counter32
    MAX-ACCESS      read-only
    STATUS          current
    DESCRIPTION     
            "This object contains the number of LFAP FUNs received by the CCE."
    ::= { monLfapCounts 8 }

monLfapFUAsSent OBJECT-TYPE
    SYNTAX          Counter32
    MAX-ACCESS      read-only
    STATUS          current
    DESCRIPTION     
            "This object contains the number of LFAP FUAs sent from the CCE."
    ::= { monLfapCounts 9 }

monLfapFUAsReceived OBJECT-TYPE
    SYNTAX          Counter32
    MAX-ACCESS      read-only
    STATUS          current
    DESCRIPTION     
            "This object contains the number of LFAP FUAs received by the CCE."
    ::= { monLfapCounts 10 }

monLfapFCRsSent OBJECT-TYPE
    SYNTAX          Counter32
    MAX-ACCESS      read-only
    STATUS          current
    DESCRIPTION     
            "This object contains the number of LFAP FCRs sent from the CCE."
    ::= { monLfapCounts 11 }

monLfapFCRsReceived OBJECT-TYPE
    SYNTAX          Counter32
    MAX-ACCESS      read-only
    STATUS          current
    DESCRIPTION     
            "This object contains the number of LFAP FCRs received by the CCE."
    ::= { monLfapCounts 12 }

monLfapFCAsSent OBJECT-TYPE
    SYNTAX          Counter32
    MAX-ACCESS      read-only
    STATUS          current
    DESCRIPTION     
            "This object contains the number of LFAP FCAs sent from the CCE."
    ::= { monLfapCounts 13 }

monLfapFCAsReceived OBJECT-TYPE
    SYNTAX          Counter32
    MAX-ACCESS      read-only
    STATUS          current
    DESCRIPTION     
            "This object contains the number of LFAP FCAs received by the CCE."
    ::= { monLfapCounts 14 }

monLfapARsSent OBJECT-TYPE
    SYNTAX          Counter32
    MAX-ACCESS      read-only
    STATUS          current
    DESCRIPTION     
            "This object contains the number of LFAP ARs sent from the CCE."
    ::= { monLfapCounts 15 }

monLfapARsReceived OBJECT-TYPE
    SYNTAX          Counter32
    MAX-ACCESS      read-only
    STATUS          current
    DESCRIPTION     
            "This object contains the number of LFAP ARs received by the CCE."
    ::= { monLfapCounts 16 }

monLfapARAsSent OBJECT-TYPE
    SYNTAX          Counter32
    MAX-ACCESS      read-only
    STATUS          current
    DESCRIPTION     
            "This object contains the number of LFAP ARAs sent from the CCE."
    ::= { monLfapCounts 17 }

monLfapARAsReceived OBJECT-TYPE
    SYNTAX          Counter32
    MAX-ACCESS      read-only
    STATUS          current
    DESCRIPTION     
            "This object contains the number of LFAP ARAs received by the CCE."
    ::= { monLfapCounts 18 }

monLfapFSNsSent OBJECT-TYPE
    SYNTAX          Counter32
    MAX-ACCESS      read-only
    STATUS          current
    DESCRIPTION     
            "This object contains the number of LFAP FSNs sent from the CCE."
    ::= { monLfapCounts 19 }

monLfapFSNsReceived OBJECT-TYPE
    SYNTAX          Counter32
    MAX-ACCESS      read-only
    STATUS          current
    DESCRIPTION     
            "This object contains the number of LFAP FSNs received by the CCE."
    ::= { monLfapCounts 20 }

monLfapFSAsSent OBJECT-TYPE
    SYNTAX          Counter32
    MAX-ACCESS      read-only
    STATUS          current
    DESCRIPTION     
            "This object contains the number of LFAP FSAs sent from the CCE."
    ::= { monLfapCounts 21 }

monLfapFSAsReceived OBJECT-TYPE
    SYNTAX          Counter32
    MAX-ACCESS      read-only
    STATUS          current
    DESCRIPTION     
            "This object contains the number of LFAP FSAs received by the CCE."
    ::= { monLfapCounts 22 }

monLfapDroppedMessages OBJECT-TYPE
    SYNTAX          Counter32
    MAX-ACCESS      read-only
    STATUS          current
    DESCRIPTION     
            "This object contains the number of Lfap messages which were dropped by the 
             CCE and not sent to the FAS."
    ::= { monLfapCounts 23 }

monLfapVRsSent OBJECT-TYPE
    SYNTAX          Counter32
    MAX-ACCESS      read-only
    STATUS          current
    DESCRIPTION     
            "This object contains the number of LFAP VRs sent from the CCE."
    ::= { monLfapCounts 24 }

monLfapVRAsReceived OBJECT-TYPE
    SYNTAX          Counter32
    MAX-ACCESS      read-only
    STATUS          current
    DESCRIPTION     
            "This object contains the number of LFAP VRAs received by the CCE."
    ::= { monLfapCounts 25 }

monLfapConnSuccess OBJECT-TYPE
    SYNTAX          Counter32
    MAX-ACCESS      read-only
    STATUS          current
    DESCRIPTION     
            "This object contains the number of successful connections made from the CCE
             to server(s)."
    ::= { monLfapCounts 26 }

monLfapConnFailure OBJECT-TYPE
    SYNTAX          Counter32
    MAX-ACCESS      read-only
    STATUS          current
    DESCRIPTION     
            "This object contains the number of unsuccessful attempts to connect from the
             CCE to the server(s)."
    ::= { monLfapCounts 27 }

monLfapBytesSent OBJECT-TYPE
    SYNTAX          Counter32
    MAX-ACCESS      read-only
    STATUS          current
    DESCRIPTION     
            "This object contains the total number of bytes sent in messages from the
             CCE to the server(s)."
    ::= { monLfapCounts 28 }

monLfapBytesReceived OBJECT-TYPE
    SYNTAX          Counter32
    MAX-ACCESS      read-only
    STATUS          current
    DESCRIPTION     
            "This object contains the total number of bytes received in messages from the
             server(s) to the CCE."
    ::= { monLfapCounts 29 }

monLfapMsgsSent OBJECT-TYPE
    SYNTAX          Counter32
    MAX-ACCESS      read-only
    STATUS          current
    DESCRIPTION     
            "This object contains the total number of messages sent from the CCE to the
             server(s)."
    ::= { monLfapCounts 30 }

monLfapMsgsReceived OBJECT-TYPE
    SYNTAX          Counter32
    MAX-ACCESS      read-only
    STATUS          current
    DESCRIPTION     
            "This object contains the total number of messages received from the server(s)
             to the CCE."
    ::= { monLfapCounts 31 }

monLfapMsgsReceivedError OBJECT-TYPE
    SYNTAX          Counter32
    MAX-ACCESS      read-only
    STATUS          current
    DESCRIPTION     
            "This object contains the total number of messages received in error from the
             server(s) to the CCE."
    ::= { monLfapCounts 32 }

monLfapMsgsSendQueue OBJECT-TYPE
    SYNTAX          Integer32
    MAX-ACCESS      read-only
    STATUS          current
    DESCRIPTION     
            "This object contains the number of messages currently in the send queue."
    ::= { monLfapCounts 33 }

monLfapMsgsSendQueuePeak OBJECT-TYPE
    SYNTAX          Gauge32
    MAX-ACCESS      read-only
    STATUS          current
    DESCRIPTION     
            "This object contains the peak number of messages in the send queue."
    ::= { monLfapCounts 34 }

monLfapMsgsReceiveQueue OBJECT-TYPE
    SYNTAX          Integer32
    MAX-ACCESS      read-only
    STATUS          current
    DESCRIPTION     
            "This object contains the number of messages currently in the receive queue."
    ::= { monLfapCounts 35 }

monLfapDroppedMessagesConnected OBJECT-TYPE
    SYNTAX          Counter32
    MAX-ACCESS      read-only
    STATUS          current
    DESCRIPTION     
            "This object contains the number of LFAP messages which were dropped by the
             CCE and not sent to the server while the CCE was connected to the server."
    ::= { monLfapCounts 36 }

monLfapDroppedFARs OBJECT-TYPE
    SYNTAX          Counter32
    MAX-ACCESS      read-only
    STATUS          current
    DESCRIPTION     
            "This object contains the number of LFAP FARs which were dropped by the CCE
             and not sent to the server."
    ::= { monLfapCounts 37 }

monLfapDroppedFUNIs OBJECT-TYPE
    SYNTAX          Counter32
    MAX-ACCESS      read-only
    STATUS          current
    DESCRIPTION     
            "This object contains the number of LFAP FUN-Inactives which were dropped by
             the CCE and not sent to the server."
    ::= { monLfapCounts 38 }

monLfapDroppedFUNs OBJECT-TYPE
    SYNTAX          Counter32
    MAX-ACCESS      read-only
    STATUS          current
    DESCRIPTION     
            "This object contains the number of LFAP FUN-Updates which were dropped by
             the CCE and not sent to the server."
    ::= { monLfapCounts 39 }

monLfapDroppedARs OBJECT-TYPE
    SYNTAX          Counter32
    MAX-ACCESS      read-only
    STATUS          current
    DESCRIPTION     
            "This object contains the number of LFAP ARs which were dropped by the CCE
             and not sent to the server."
    ::= { monLfapCounts 40 }

monLfapDroppedARAs OBJECT-TYPE
    SYNTAX          Counter32
    MAX-ACCESS      read-only
    STATUS          current
    DESCRIPTION     
            "This object contains the number of LFAP ARAs which were dropped by the CCE
             and not sent to the server."
    ::= { monLfapCounts 41 }

monLfapDroppedVRs OBJECT-TYPE
    SYNTAX          Counter32
    MAX-ACCESS      read-only
    STATUS          current
    DESCRIPTION     
            "This object contains the number of LFAP VRs which were dropped by the CCE
             and not sent to the server."
    ::= { monLfapCounts 42 }

monCxnCounts OBJECT IDENTIFIER
    ::= { monLfap 2 }

monLfapYesRespCnt OBJECT-TYPE
    SYNTAX          Counter32
    MAX-ACCESS      read-only
    STATUS          current
    DESCRIPTION     
            "This object contains the number of positive LFAP responses received from the
             FAS."
    ::= { monCxnCounts 1 }

monLfapNoRespCnt OBJECT-TYPE
    SYNTAX          Counter32
    MAX-ACCESS      read-only
    STATUS          current
    DESCRIPTION     
            "This object contains the number of negative LFAP responses received from the
             FAS."
    ::= { monCxnCounts 2 }

monLfapFlowSetups OBJECT-TYPE
    SYNTAX          Counter32
    MAX-ACCESS      read-only
    STATUS          current
    DESCRIPTION     
            "This object contains the number of flow setups."
    ::= { monCxnCounts 3 }

monLfapFlowTeardowns OBJECT-TYPE
    SYNTAX          Counter32
    MAX-ACCESS      read-only
    STATUS          current
    DESCRIPTION     
            "This object contains the number of flow teardowns."
    ::= { monCxnCounts 4 }

monLfapFlowActivePeak OBJECT-TYPE
    SYNTAX          Gauge32
    MAX-ACCESS      read-only
    STATUS          current
    DESCRIPTION     
            "This object contains the peak number of active flows."
    ::= { monCxnCounts 5 }

monActiveCxnCnt OBJECT-TYPE
    SYNTAX          Counter32
    MAX-ACCESS      read-only
    STATUS          current
    DESCRIPTION     
            "This object contains the number of connections on which statistics are being
             reported."
    ::= { monCxnCounts 8 }

lfapFlowPolicyPolling OBJECT IDENTIFIER
    ::= { ctLFAP 3 }

flowPolicyPollingTimerInterval OBJECT-TYPE
    SYNTAX          Integer32 (1..1440)
    MAX-ACCESS      read-write
    STATUS          current
    DESCRIPTION     
            "This object contains the number of minutes between statistics polling
             periods."
    DEFVAL          { 10 }
    ::= { lfapFlowPolicyPolling 1 }

flowPolicyPollingBatchSize OBJECT-TYPE
    SYNTAX          Integer32 (1..2000)
    MAX-ACCESS      read-write
    STATUS          current
    DESCRIPTION     
            "This object specifies the number of connections that comprise a batch for
             polling purposes."
    DEFVAL          { 32 }
    ::= { lfapFlowPolicyPolling 2 }

flowPolicyPollingBatchInterval OBJECT-TYPE
    SYNTAX          Integer32
    MAX-ACCESS      read-only
    STATUS          current
    DESCRIPTION     
            "This object contains the current number of milliseconds between statistics
             polling batches.  A polling period is divided into polling batches, the
             duration between which is calculated by dividing the value of
             flowPolicyPollingTimerInterval times 60,000 by the number of batches.
             The number of polling batches is calculated by dividing the actual number
             of connections by the value of flowPolicyPollingBatchSize.  Between batches,
             the statistics polling mechanism pauses this number of milliseconds."
    ::= { lfapFlowPolicyPolling 3 }

flowPolicyPollingBatchUpdateInterval OBJECT-TYPE
    SYNTAX          Integer32 (1..2000)
    MAX-ACCESS      read-write
    STATUS          current
    DESCRIPTION     
            "This object specifies the time in seconds to send flow create and delete
             information to the server."
    DEFVAL          { 1 }
    ::= { lfapFlowPolicyPolling 4 }

flowPolicyPollingLostContactInterval OBJECT-TYPE
    SYNTAX          Integer32 (10..2000)
    MAX-ACCESS      read-write
    STATUS          current
    DESCRIPTION     
            "This object specifies the time to wait in seconds until the CCE realizes it
             has lost contact with a server."
    DEFVAL          { 60 }
    ::= { lfapFlowPolicyPolling 5 }

flowPolicyPollingServerRetryInterval OBJECT-TYPE
    SYNTAX          Integer32 (1..2000)
    MAX-ACCESS      read-write
    STATUS          current
    DESCRIPTION     
            "This object specifies the time in seconds to wait before trying to connect
             to the server(s) in the list after being unable to connect to any of the
             server(s)."
    DEFVAL          { 60 }
    ::= { lfapFlowPolicyPolling 6 }

flowPolicyPollingSendQueueMaxSize OBJECT-TYPE
    SYNTAX          Integer32 (100..2000000)
    MAX-ACCESS      read-write
    STATUS          current
    DESCRIPTION     
            "This object specifies the maximum number of messages the send queue can hold
             before messages are dropped."
    DEFVAL          { 50000 }
    ::= { lfapFlowPolicyPolling 7 }

flowPolicyPollingTaskPriority OBJECT-TYPE
    SYNTAX          Integer32 (50..250)
    MAX-ACCESS      read-write
    STATUS          current
    DESCRIPTION     
            "This object specifies the task priority of LFAP."
    DEFVAL          { 230 }
    ::= { lfapFlowPolicyPolling 8 }

lfapConformance OBJECT IDENTIFIER
    ::= { ctLFAP 4 }

lfapCompliances OBJECT IDENTIFIER
    ::= { lfapConformance 1 }

lfapGroups OBJECT IDENTIFIER
    ::= { lfapConformance 2 }

lfapConfGroupV10 OBJECT-GROUP
    OBJECTS         { flowPolicyControl, flowPolicyStatus, 
                      flowPolicyActiveServer, flowPolicyServerAddrIndex, 
                      flowPolicyServerAddr, flowPolicyConfigPolicy, 
                      flowPolicyConfigStatistics, monLfapFARsSent, 
                      monLfapFARsReceived, monLfapFAAsSent, 
                      monLfapFAAsReceived, monLfapFAUsSent, 
                      monLfapFAUsReceived, monLfapFUNsSent, 
                      monLfapFUNsReceived, monLfapFUAsSent, 
                      monLfapFUAsReceived, monLfapFCRsSent, 
                      monLfapFCRsReceived, monLfapFCAsSent, 
                      monLfapFCAsReceived, monLfapARsSent, 
                      monLfapARsReceived, monLfapARAsSent, 
                      monLfapARAsReceived, monLfapFSNsSent, 
                      monLfapFSNsReceived, monLfapFSAsSent, 
                      monLfapFSAsReceived, monLfapDroppedMessages, 
                      monLfapYesRespCnt, monLfapNoRespCnt, 
                      monActiveCxnCnt, flowPolicyPollingTimerInterval, 
                      flowPolicyPollingBatchSize, 
                      flowPolicyPollingBatchInterval }
    STATUS          deprecated
    DESCRIPTION     
            "A set of managed objects that make up version 1.0 of the CTRON LFAP MIB."
    ::= { lfapGroups 3 }

lfapConfGroupV40 OBJECT-GROUP
    OBJECTS         { flowPolicyControl, flowPolicyStatus, 
                      flowPolicyActiveServer, flowPolicyServerAddrIndex, 
                      flowPolicyServerAddr, flowPolicyConfigPolicy, 
                      flowPolicyConfigStatistics, monLfapFARsSent, 
                      monLfapFARsReceived, monLfapFAAsSent, 
                      monLfapFAAsReceived, monLfapFAUsSent, 
                      monLfapFAUsReceived, monLfapFUNsSent, 
                      monLfapFUNsReceived, monLfapFUAsSent, 
                      monLfapFUAsReceived, monLfapFCRsSent, 
                      monLfapFCRsReceived, monLfapFCAsSent, 
                      monLfapFCAsReceived, monLfapARsSent, 
                      monLfapARsReceived, monLfapARAsSent, 
                      monLfapARAsReceived, monLfapFSNsSent, 
                      monLfapFSNsReceived, monLfapFSAsSent, 
                      monLfapFSAsReceived, monLfapDroppedMessages, 
                      monLfapVRsSent, monLfapVRAsReceived, 
                      monLfapConnSuccess, monLfapConnFailure, 
                      monLfapBytesSent, monLfapBytesReceived, 
                      monLfapMsgsSent, monLfapMsgsReceived, 
                      monLfapMsgsReceivedError, monLfapMsgsSendQueue, 
                      monLfapMsgsSendQueuePeak, monLfapMsgsReceiveQueue, 
                      monLfapDroppedMessagesConnected, 
                      monLfapDroppedFARs, monLfapDroppedFUNIs, 
                      monLfapDroppedFUNs, monLfapDroppedARs, 
                      monLfapDroppedARAs, monLfapDroppedVRs, 
                      monLfapYesRespCnt, monLfapNoRespCnt, 
                      monLfapFlowSetups, monLfapFlowTeardowns, 
                      monLfapFlowActivePeak, monActiveCxnCnt, 
                      flowPolicyPollingTimerInterval, 
                      flowPolicyPollingBatchSize, 
                      flowPolicyPollingBatchInterval, 
                      flowPolicyPollingBatchUpdateInterval, 
                      flowPolicyPollingLostContactInterval, 
                      flowPolicyPollingServerRetryInterval, 
                      flowPolicyPollingSendQueueMaxSize, 
                      flowPolicyPollingTaskPriority }
    STATUS          current
    DESCRIPTION     
            "A set of managed objects that make up version 4.0 of the CTRON LFAP MIB."
    ::= { lfapGroups 4 }

lfapComplianceV10 MODULE-COMPLIANCE
    STATUS          deprecated
    DESCRIPTION     
            "The compliance statement for the CTRON-LFAP-MIB."

    MODULE          -- this module

        MANDATORY-GROUPS    { lfapConfGroupV10 }

    ::= { lfapConfGroupV10 1 }

lfapComplianceV40 MODULE-COMPLIANCE
    STATUS          current
    DESCRIPTION     
            "The compliance statement for the CTRON-LFAP-MIB."

    MODULE          -- this module

        MANDATORY-GROUPS    { lfapConfGroupV40 }

    ::= { lfapConfGroupV40 1 }

END -- end of module CTRON-LFAP-MIB.
