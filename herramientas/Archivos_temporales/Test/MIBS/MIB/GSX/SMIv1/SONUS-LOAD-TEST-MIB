--
-- This SMIv1 module has been generated by smidump 0.2-cvs. Do not edit.
--

SONUS-LOAD-TEST-MIB DEFINITIONS ::= BEGIN

IMPORTS
    OBJECT-TYPE
        FROM RFC-1212
    Counter
        FROM RFC1155-SMI
    RowStatus
        FROM SNMPv2-TC
    sonusToolsMIBs
        FROM SONUS-SMI
    SonusAdminState, SonusName, SonusNameReference
        FROM SONUS-TC;

sonusLoadTestMIB OBJECT IDENTIFIER
    ::= { sonusToolsMIBs 2 }

-- sonusLoadTestMIB MODULE-IDENTITY
--     LAST-UPDATED    "201105240000Z"
--     ORGANIZATION    
--             "Sonus Networks, Inc."
--     CONTACT-INFO    
--             "   Customer Support    
--              Sonus Networks, Inc.
--              7 Technology Park Drive
--              Westford, MA 01886
--              USA
--              
--              Tel: 978-614-8100
--              Fax: 978-614-8609"
--     DESCRIPTION     
--             "The MIB Module for Load Test Configuration."
--     ::= { sonusToolsMIBs 2 }


sonusLoadTestMIBObjects OBJECT IDENTIFIER
    ::= { sonusLoadTestMIB 1 }

sonusLoadTestTable OBJECT-TYPE
    SYNTAX          SEQUENCE OF SonusLoadTestEntry
    ACCESS          not-accessible
    STATUS          mandatory
    DESCRIPTION     
            "This table specifies the Load Test Table."
    ::= { sonusLoadTestMIBObjects 1 }

sonusLoadTestEntry OBJECT-TYPE
    SYNTAX          SonusLoadTestEntry
    ACCESS          not-accessible
    STATUS          mandatory
    DESCRIPTION     
            ""
    INDEX           { sonusLoadTestIndex }
    ::= { sonusLoadTestTable 1 }

SonusLoadTestEntry ::=
    SEQUENCE {
        sonusLoadTestIndex              INTEGER,
        sonusLoadTestName               SonusName,
        sonusLoadTestCallAttempt        INTEGER,
        sonusLoadTestCallDuration       INTEGER,
        sonusLoadTestVoiceTraffic       INTEGER,
        sonusLoadTestBurstCalls         INTEGER,
        sonusLoadTestBurstDuration      INTEGER,
        sonusLoadTestBurstState         INTEGER,
        sonusLoadTestTrunkGroupName     SonusNameReference,
        sonusLoadTestCircuitServiceProfile  SonusNameReference,
        sonusLoadTestNodePointCode      INTEGER,
        sonusLoadTestMode               INTEGER,
        sonusLoadTestState              INTEGER,
        sonusLoadTestRowStatus          RowStatus,
        sonusLoadTestNodeName           SonusName,
        sonusLoadTestNodeHandle         INTEGER
    }

sonusLoadTestIndex OBJECT-TYPE
    SYNTAX          INTEGER
    ACCESS          read-only
    STATUS          mandatory
    DESCRIPTION     
            "The index of the Load Test entry."
    ::= { sonusLoadTestEntry 1 }

sonusLoadTestName OBJECT-TYPE
    SYNTAX          SonusName
    ACCESS          read-write
    STATUS          mandatory
    DESCRIPTION     
            "The name of this Load Test entry."
    ::= { sonusLoadTestEntry 2 }

sonusLoadTestCallAttempt OBJECT-TYPE
    SYNTAX          INTEGER (1..1000)
    ACCESS          read-write
    STATUS          mandatory
    DESCRIPTION     
            "The call attempt (calls/second) of this Load Test Entry."
    DEFVAL          { 1 }
    ::= { sonusLoadTestEntry 3 }

sonusLoadTestCallDuration OBJECT-TYPE
    SYNTAX          INTEGER
    ACCESS          read-write
    STATUS          mandatory
    DESCRIPTION     
            "The call duration (second) of this Load Test Entry."
    DEFVAL          { 15 }
    ::= { sonusLoadTestEntry 4 }

sonusLoadTestVoiceTraffic OBJECT-TYPE
    SYNTAX          INTEGER { disabled(1), enabled(2) }
    ACCESS          read-write
    STATUS          mandatory
    DESCRIPTION     
            "The voice traffic option of this Load Test entry."
    DEFVAL          { enabled }
    ::= { sonusLoadTestEntry 5 }

sonusLoadTestBurstCalls OBJECT-TYPE
    SYNTAX          INTEGER (0..1000)
    ACCESS          read-write
    STATUS          mandatory
    DESCRIPTION     
            "The Burst Calls of this Load Test Entry."
    DEFVAL          { 0 }
    ::= { sonusLoadTestEntry 6 }

sonusLoadTestBurstDuration OBJECT-TYPE
    SYNTAX          INTEGER (1..100)
    ACCESS          read-write
    STATUS          mandatory
    DESCRIPTION     
            "The Burst Duration (second) of this Load Test Entry."
    DEFVAL          { 1 }
    ::= { sonusLoadTestEntry 7 }

sonusLoadTestBurstState OBJECT-TYPE
    SYNTAX          INTEGER { disabled(1), enabled(2) }
    ACCESS          read-write
    STATUS          mandatory
    DESCRIPTION     
            "The administrative call burst state of this Load Test entry."
    DEFVAL          { disabled }
    ::= { sonusLoadTestEntry 8 }

sonusLoadTestTrunkGroupName OBJECT-TYPE
    SYNTAX          SonusNameReference
    ACCESS          read-write
    STATUS          mandatory
    DESCRIPTION     
            "The name of the Trunk Group Name to to be used by the Load Test to hunt for available DS0."
    ::= { sonusLoadTestEntry 9 }

sonusLoadTestCircuitServiceProfile OBJECT-TYPE
    SYNTAX          SonusNameReference
    ACCESS          read-write
    STATUS          mandatory
    DESCRIPTION     
            "The name of the Circuit Service Profile used by the Load Test."
    ::= { sonusLoadTestEntry 10 }

sonusLoadTestNodePointCode OBJECT-TYPE
    SYNTAX          INTEGER
    ACCESS          read-write
    STATUS          mandatory
    DESCRIPTION     
            "The SS7 point code assigned to this Load Test Node entry."
    ::= { sonusLoadTestEntry 11 }

sonusLoadTestMode OBJECT-TYPE
    SYNTAX          INTEGER { paced(1), burst(2) }
    ACCESS          read-write
    STATUS          mandatory
    DESCRIPTION     
            "The administrative mode of this Load Test entry."
    DEFVAL          { paced }
    ::= { sonusLoadTestEntry 12 }

sonusLoadTestState OBJECT-TYPE
    SYNTAX          INTEGER { disabled(1), enabled(2) }
    ACCESS          read-write
    STATUS          mandatory
    DESCRIPTION     
            "The administrative state of this Load Test entry."
    DEFVAL          { disabled }
    ::= { sonusLoadTestEntry 13 }

sonusLoadTestRowStatus OBJECT-TYPE
    SYNTAX          RowStatus
    ACCESS          read-write
    STATUS          mandatory
    DESCRIPTION     
            ""
    ::= { sonusLoadTestEntry 14 }

sonusLoadTestNodeName OBJECT-TYPE
    SYNTAX          SonusName
    ACCESS          read-only
    STATUS          mandatory
    DESCRIPTION     
            "SS7 Node name ."
    ::= { sonusLoadTestEntry 15 }

sonusLoadTestNodeHandle OBJECT-TYPE
    SYNTAX          INTEGER
    ACCESS          read-write
    STATUS          mandatory
    DESCRIPTION     
            "The SS7 node handle assigned to this Load Test Node entry."
    ::= { sonusLoadTestEntry 16 }

sonusLoadTestDestNumberTable OBJECT-TYPE
    SYNTAX          SEQUENCE OF SonusLoadTestDestNumberEntry
    ACCESS          not-accessible
    STATUS          mandatory
    DESCRIPTION     
            "This table specifies the destination numbers for Load Test Table"
    ::= { sonusLoadTestMIBObjects 2 }

sonusLoadTestDestNumberEntry OBJECT-TYPE
    SYNTAX          SonusLoadTestDestNumberEntry
    ACCESS          not-accessible
    STATUS          mandatory
    DESCRIPTION     
            ""
    INDEX           { sonusLoadTestEntryIndex, 
                      sonusLoadTestDestNumberIndex }
    ::= { sonusLoadTestDestNumberTable 1 }

SonusLoadTestDestNumberEntry ::=
    SEQUENCE {
        sonusLoadTestEntryIndex         INTEGER,
        sonusLoadTestDestNumberIndex    INTEGER,
        sonusLoadTestDestNumber         SonusNameReference,
        sonusLoadTestDestNumberPercentage INTEGER,
        sonusLoadTestDestNumberBurstFlag INTEGER,
        sonusLoadTestDestNumberState    INTEGER,
        sonusLoadTestDestNumberRowStatus RowStatus,
        sonusLoadTestDestNumberIamRef   INTEGER
    }

sonusLoadTestEntryIndex OBJECT-TYPE
    SYNTAX          INTEGER
    ACCESS          read-only
    STATUS          mandatory
    DESCRIPTION     
            "The index of Load Test entry of this destination number belongs to."
    ::= { sonusLoadTestDestNumberEntry 1 }

sonusLoadTestDestNumberIndex OBJECT-TYPE
    SYNTAX          INTEGER
    ACCESS          read-only
    STATUS          mandatory
    DESCRIPTION     
            "The index of this Load Test destination number entry."
    ::= { sonusLoadTestDestNumberEntry 2 }

sonusLoadTestDestNumber OBJECT-TYPE
    SYNTAX          SonusNameReference
    ACCESS          read-write
    STATUS          mandatory
    DESCRIPTION     
            "The number of this Load Test destination number entry."
    ::= { sonusLoadTestDestNumberEntry 3 }

sonusLoadTestDestNumberPercentage OBJECT-TYPE
    SYNTAX          INTEGER (1..100)
    ACCESS          read-write
    STATUS          mandatory
    DESCRIPTION     
            "The percentage (10% for each increment) of the total call attempt of this Load Test destination number Entry."
    ::= { sonusLoadTestDestNumberEntry 4 }

sonusLoadTestDestNumberBurstFlag OBJECT-TYPE
    SYNTAX          INTEGER { disabled(1), enabled(2) }
    ACCESS          read-write
    STATUS          mandatory
    DESCRIPTION     
            "The burst flag of this Load Test destination number Entry."
    DEFVAL          { disabled }
    ::= { sonusLoadTestDestNumberEntry 5 }

sonusLoadTestDestNumberState OBJECT-TYPE
    SYNTAX          INTEGER { disabled(1), enabled(2) }
    ACCESS          read-write
    STATUS          mandatory
    DESCRIPTION     
            "The administrative state of this Load Test destination number entry."
    DEFVAL          { disabled }
    ::= { sonusLoadTestDestNumberEntry 6 }

sonusLoadTestDestNumberRowStatus OBJECT-TYPE
    SYNTAX          RowStatus
    ACCESS          read-write
    STATUS          mandatory
    DESCRIPTION     
            ""
    ::= { sonusLoadTestDestNumberEntry 7 }

sonusLoadTestDestNumberIamRef OBJECT-TYPE
    SYNTAX          INTEGER (0..25)
    ACCESS          read-write
    STATUS          mandatory
    DESCRIPTION     
            "Reference to an IAM entry to associate with this Load Test destination number entry."
    ::= { sonusLoadTestDestNumberEntry 8 }

sonusLoadTestStatusTable OBJECT-TYPE
    SYNTAX          SEQUENCE OF SonusLoadTestStatusEntry
    ACCESS          not-accessible
    STATUS          mandatory
    DESCRIPTION     
            "This table contains status of the load test."
    ::= { sonusLoadTestMIBObjects 3 }

sonusLoadTestStatusEntry OBJECT-TYPE
    SYNTAX          SonusLoadTestStatusEntry
    ACCESS          not-accessible
    STATUS          mandatory
    DESCRIPTION     
            "Status of loadtest."
    INDEX           { sonusLoadTestStatusIndex }
    ::= { sonusLoadTestStatusTable 1 }

SonusLoadTestStatusEntry ::=
    SEQUENCE {
        sonusLoadTestStatusIndex        INTEGER,
        sonusLoadTestNumCallInitiated   INTEGER,
        sonusLoadTestNumCallFailed      INTEGER,
        sonusLoadTestNumTrmAlloFailed   INTEGER,
        sonusLoadTestNumTrmAlloTimedOut INTEGER,
        sonusLoadTestNumCallEstablished INTEGER,
        sonusLoadTestNumCallReleased    INTEGER,
        sonusLoadTestNumUnexpected      INTEGER,
        sonusLoadTestNumAcmTimeOutRcvd  INTEGER,
        sonusLoadTestNumLocalAcmTimeOut INTEGER,
        sonusLoadTestNumAnmTimeOutRcvd  INTEGER,
        sonusLoadTestNumLocalAnmTimeOut INTEGER,
        sonusLoadTestNumLocalRelTimeOut INTEGER,
        sonusLoadTestNumUnexpectedRelRcvdGen    INTEGER,
        sonusLoadTestNumUnexpectedRelRcvdRcvr     INTEGER,
        sonusLoadTestNumIamSent         INTEGER,
        sonusLoadTestNumAcmRcvd         INTEGER,
        sonusLoadTestNumAnmRcvd         INTEGER,
        sonusLoadTestNumRelRcvd         INTEGER,
        sonusLoadTestNumUcicRcvd        INTEGER,
        sonusLoadTestNumRelSent         INTEGER,
        sonusLoadTestNumRlcRcvd         INTEGER,
        sonusLoadTestNumTotalTestUpdate INTEGER,
        sonusLoadTestNumDsTestPassed    INTEGER,
        sonusLoadTestNumUsTestPassed    INTEGER,
        sonusLoadTestNumCallAboveBenchMark  INTEGER,
        sonusLoadTestTotalCallLatency   INTEGER,
        sonusLoadTestAverageCallLatency INTEGER,
        sonusLoadTestMinCallLatency     INTEGER,
        sonusLoadTestMaxCallLatency     INTEGER,
        sonusLoadTestLastCallLatency    INTEGER,
        sonusLoadTestMaxCallLatencyAboveBenchMark         INTEGER,
        sonusLoadTestCallLatencyBenchMark INTEGER,
        sonusLoadTestElapsedTime        INTEGER,
        sonusLoadTestBusyHourCall       INTEGER,
        sonusLoadTestNumRscRcvd         INTEGER,
        sonusLoadTestNumRcvrIamTimeOut  INTEGER
    }

sonusLoadTestStatusIndex OBJECT-TYPE
    SYNTAX          INTEGER
    ACCESS          read-only
    STATUS          mandatory
    DESCRIPTION     
            "The index of the load test instance."
    ::= { sonusLoadTestStatusEntry 1 }

sonusLoadTestNumCallInitiated OBJECT-TYPE
    SYNTAX          INTEGER
    ACCESS          read-only
    STATUS          mandatory
    DESCRIPTION     
            "Number of calls initiated."
    ::= { sonusLoadTestStatusEntry 2 }

sonusLoadTestNumCallFailed OBJECT-TYPE
    SYNTAX          INTEGER
    ACCESS          read-only
    STATUS          mandatory
    DESCRIPTION     
            "Number of calls failed."
    ::= { sonusLoadTestStatusEntry 3 }

sonusLoadTestNumTrmAlloFailed OBJECT-TYPE
    SYNTAX          INTEGER
    ACCESS          read-only
    STATUS          mandatory
    DESCRIPTION     
            "Number of TRM allocation failed."
    ::= { sonusLoadTestStatusEntry 4 }

sonusLoadTestNumTrmAlloTimedOut OBJECT-TYPE
    SYNTAX          INTEGER
    ACCESS          read-only
    STATUS          mandatory
    DESCRIPTION     
            "Number of TRM allocation timed out."
    ::= { sonusLoadTestStatusEntry 5 }

sonusLoadTestNumCallEstablished OBJECT-TYPE
    SYNTAX          INTEGER
    ACCESS          read-only
    STATUS          mandatory
    DESCRIPTION     
            "Number of calls established."
    ::= { sonusLoadTestStatusEntry 6 }

sonusLoadTestNumCallReleased OBJECT-TYPE
    SYNTAX          INTEGER
    ACCESS          read-only
    STATUS          mandatory
    DESCRIPTION     
            "Number of calls released."
    ::= { sonusLoadTestStatusEntry 7 }

sonusLoadTestNumUnexpected OBJECT-TYPE
    SYNTAX          INTEGER
    ACCESS          read-only
    STATUS          mandatory
    DESCRIPTION     
            "Number of unexpected messages received."
    ::= { sonusLoadTestStatusEntry 8 }

sonusLoadTestNumAcmTimeOutRcvd OBJECT-TYPE
    SYNTAX          INTEGER
    ACCESS          read-only
    STATUS          mandatory
    DESCRIPTION     
            "Number of ACM timeout received."
    ::= { sonusLoadTestStatusEntry 9 }

sonusLoadTestNumLocalAcmTimeOut OBJECT-TYPE
    SYNTAX          INTEGER
    ACCESS          read-only
    STATUS          mandatory
    DESCRIPTION     
            "Number of local ACM timed out."
    ::= { sonusLoadTestStatusEntry 10 }

sonusLoadTestNumAnmTimeOutRcvd OBJECT-TYPE
    SYNTAX          INTEGER
    ACCESS          read-only
    STATUS          mandatory
    DESCRIPTION     
            "Number of ANM timeout received."
    ::= { sonusLoadTestStatusEntry 11 }

sonusLoadTestNumLocalAnmTimeOut OBJECT-TYPE
    SYNTAX          INTEGER
    ACCESS          read-only
    STATUS          mandatory
    DESCRIPTION     
            "Number of local ANM timed out."
    ::= { sonusLoadTestStatusEntry 12 }

sonusLoadTestNumLocalRelTimeOut OBJECT-TYPE
    SYNTAX          INTEGER
    ACCESS          read-only
    STATUS          mandatory
    DESCRIPTION     
            "Number of local release timed out."
    ::= { sonusLoadTestStatusEntry 13 }

sonusLoadTestNumUnexpectedRelRcvdGen OBJECT-TYPE
    SYNTAX          INTEGER
    ACCESS          read-only
    STATUS          mandatory
    DESCRIPTION     
            "Number of unexpected REL received by Call Generator."
    ::= { sonusLoadTestStatusEntry 14 }

sonusLoadTestNumUnexpectedRelRcvdRcvr OBJECT-TYPE
    SYNTAX          INTEGER
    ACCESS          read-only
    STATUS          mandatory
    DESCRIPTION     
            "Number of unexpected REL received by Call Receiver."
    ::= { sonusLoadTestStatusEntry 15 }

sonusLoadTestNumIamSent OBJECT-TYPE
    SYNTAX          INTEGER
    ACCESS          read-only
    STATUS          mandatory
    DESCRIPTION     
            "Number of IAM sent."
    ::= { sonusLoadTestStatusEntry 16 }

sonusLoadTestNumAcmRcvd OBJECT-TYPE
    SYNTAX          INTEGER
    ACCESS          read-only
    STATUS          mandatory
    DESCRIPTION     
            "Number of ACM received."
    ::= { sonusLoadTestStatusEntry 17 }

sonusLoadTestNumAnmRcvd OBJECT-TYPE
    SYNTAX          INTEGER
    ACCESS          read-only
    STATUS          mandatory
    DESCRIPTION     
            "Number of ANM received."
    ::= { sonusLoadTestStatusEntry 18 }

sonusLoadTestNumRelRcvd OBJECT-TYPE
    SYNTAX          INTEGER
    ACCESS          read-only
    STATUS          mandatory
    DESCRIPTION     
            "Number of REL received."
    ::= { sonusLoadTestStatusEntry 19 }

sonusLoadTestNumUcicRcvd OBJECT-TYPE
    SYNTAX          INTEGER
    ACCESS          read-only
    STATUS          mandatory
    DESCRIPTION     
            "Number of UCIC received."
    ::= { sonusLoadTestStatusEntry 20 }

sonusLoadTestNumRelSent OBJECT-TYPE
    SYNTAX          INTEGER
    ACCESS          read-only
    STATUS          mandatory
    DESCRIPTION     
            "Number of REL sent."
    ::= { sonusLoadTestStatusEntry 21 }

sonusLoadTestNumRlcRcvd OBJECT-TYPE
    SYNTAX          INTEGER
    ACCESS          read-only
    STATUS          mandatory
    DESCRIPTION     
            "Number of RLC received."
    ::= { sonusLoadTestStatusEntry 22 }

sonusLoadTestNumTotalTestUpdate OBJECT-TYPE
    SYNTAX          INTEGER
    ACCESS          read-only
    STATUS          mandatory
    DESCRIPTION     
            "Number of data verification updates received."
    ::= { sonusLoadTestStatusEntry 23 }

sonusLoadTestNumDsTestPassed OBJECT-TYPE
    SYNTAX          INTEGER
    ACCESS          read-only
    STATUS          mandatory
    DESCRIPTION     
            "Number of Downstream test passed."
    ::= { sonusLoadTestStatusEntry 24 }

sonusLoadTestNumUsTestPassed OBJECT-TYPE
    SYNTAX          INTEGER
    ACCESS          read-only
    STATUS          mandatory
    DESCRIPTION     
            "Number of Upstream test passed."
    ::= { sonusLoadTestStatusEntry 25 }

sonusLoadTestNumCallAboveBenchMark OBJECT-TYPE
    SYNTAX          INTEGER
    ACCESS          read-only
    STATUS          mandatory
    DESCRIPTION     
            "Number of calls above benchmark."
    ::= { sonusLoadTestStatusEntry 26 }

sonusLoadTestTotalCallLatency OBJECT-TYPE
    SYNTAX          INTEGER
    ACCESS          read-only
    STATUS          mandatory
    DESCRIPTION     
            "Total Number of call latency (in milliseconds)."
    ::= { sonusLoadTestStatusEntry 27 }

sonusLoadTestAverageCallLatency OBJECT-TYPE
    SYNTAX          INTEGER
    ACCESS          read-only
    STATUS          mandatory
    DESCRIPTION     
            "Average call latency (in milliseconds)."
    ::= { sonusLoadTestStatusEntry 28 }

sonusLoadTestMinCallLatency OBJECT-TYPE
    SYNTAX          INTEGER
    ACCESS          read-only
    STATUS          mandatory
    DESCRIPTION     
            "Minimum call latency (in milliseconds)."
    ::= { sonusLoadTestStatusEntry 29 }

sonusLoadTestMaxCallLatency OBJECT-TYPE
    SYNTAX          INTEGER
    ACCESS          read-only
    STATUS          mandatory
    DESCRIPTION     
            "Maximum call latency (in milliseconds)."
    ::= { sonusLoadTestStatusEntry 30 }

sonusLoadTestLastCallLatency OBJECT-TYPE
    SYNTAX          INTEGER
    ACCESS          read-only
    STATUS          mandatory
    DESCRIPTION     
            "Last call latency (in milliseconds)."
    ::= { sonusLoadTestStatusEntry 31 }

sonusLoadTestMaxCallLatencyAboveBenchMark OBJECT-TYPE
    SYNTAX          INTEGER
    ACCESS          read-only
    STATUS          mandatory
    DESCRIPTION     
            "Maximum call latency above benchmark (in milliseconds)."
    ::= { sonusLoadTestStatusEntry 32 }

sonusLoadTestCallLatencyBenchMark OBJECT-TYPE
    SYNTAX          INTEGER
    ACCESS          read-only
    STATUS          mandatory
    DESCRIPTION     
            "Call latency benchmark (in milliseconds)."
    ::= { sonusLoadTestStatusEntry 33 }

sonusLoadTestElapsedTime OBJECT-TYPE
    SYNTAX          INTEGER
    ACCESS          read-only
    STATUS          mandatory
    DESCRIPTION     
            "Loadtest elapsed time (in seconds)."
    ::= { sonusLoadTestStatusEntry 34 }

sonusLoadTestBusyHourCall OBJECT-TYPE
    SYNTAX          INTEGER
    ACCESS          read-only
    STATUS          mandatory
    DESCRIPTION     
            "Busy hour calls."
    ::= { sonusLoadTestStatusEntry 35 }

sonusLoadTestNumRscRcvd OBJECT-TYPE
    SYNTAX          INTEGER
    ACCESS          read-only
    STATUS          mandatory
    DESCRIPTION     
            "Number of RSC received."
    ::= { sonusLoadTestStatusEntry 36 }

sonusLoadTestNumRcvrIamTimeOut OBJECT-TYPE
    SYNTAX          INTEGER
    ACCESS          read-only
    STATUS          mandatory
    DESCRIPTION     
            "Number of IAM timeouts for 2 stage calls"
    ::= { sonusLoadTestStatusEntry 37 }

sonusLoadTestIamTable OBJECT-TYPE
    SYNTAX          SEQUENCE OF SonusLoadTestIamEntry
    ACCESS          not-accessible
    STATUS          mandatory
    DESCRIPTION     
            "This table specifies the IAM information for Load Test Table"
    ::= { sonusLoadTestMIBObjects 4 }

sonusLoadTestIamEntry OBJECT-TYPE
    SYNTAX          SonusLoadTestIamEntry
    ACCESS          not-accessible
    STATUS          mandatory
    DESCRIPTION     
            ""
    INDEX           { sonusLoadTestIamTestIndex, 
                      sonusLoadTestIamEntryIndex }
    ::= { sonusLoadTestIamTable 1 }

SonusLoadTestIamEntry ::=
    SEQUENCE {
        sonusLoadTestIamTestIndex       INTEGER,
        sonusLoadTestIamEntryIndex      INTEGER,
        sonusLoadTestIamCmdParams       OCTET STRING,
        sonusLoadTestIamCmdVerify       OCTET STRING,
        sonusLoadTestIamCmdMask         OCTET STRING,
        sonusLoadTestIamRowStatus       RowStatus
    }

sonusLoadTestIamTestIndex OBJECT-TYPE
    SYNTAX          INTEGER
    ACCESS          read-only
    STATUS          mandatory
    DESCRIPTION     
            "The index of Load Test entry of this IAM information belongs to."
    ::= { sonusLoadTestIamEntry 1 }

sonusLoadTestIamEntryIndex OBJECT-TYPE
    SYNTAX          INTEGER
    ACCESS          read-only
    STATUS          mandatory
    DESCRIPTION     
            "The index of this Load Test IAM information entry."
    ::= { sonusLoadTestIamEntry 2 }

sonusLoadTestIamCmdParams OBJECT-TYPE
    SYNTAX          OCTET STRING (SIZE(0..400))
    ACCESS          read-write
    STATUS          mandatory
    DESCRIPTION     
            "Octet string that represents IAM command message parameters."
    ::= { sonusLoadTestIamEntry 3 }

sonusLoadTestIamCmdVerify OBJECT-TYPE
    SYNTAX          OCTET STRING (SIZE(0..400))
    ACCESS          read-write
    STATUS          mandatory
    DESCRIPTION     
            "Octet string that represents IAM message verification parameters."
    ::= { sonusLoadTestIamEntry 4 }

sonusLoadTestIamCmdMask OBJECT-TYPE
    SYNTAX          OCTET STRING (SIZE(0..400))
    ACCESS          read-write
    STATUS          mandatory
    DESCRIPTION     
            "Octet string that represents IAM message verification mask."
    ::= { sonusLoadTestIamEntry 5 }

sonusLoadTestIamRowStatus OBJECT-TYPE
    SYNTAX          RowStatus
    ACCESS          read-write
    STATUS          mandatory
    DESCRIPTION     
            ""
    ::= { sonusLoadTestIamEntry 6 }

sonusLt303Objects OBJECT IDENTIFIER
    ::= { sonusLoadTestMIBObjects 5 }

sonusLt303AdmnObjects OBJECT IDENTIFIER
    ::= { sonusLt303Objects 1 }

sonusLt303GenerationRate OBJECT-TYPE
    SYNTAX          Gauge (0..999)
    ACCESS          read-write
    STATUS          mandatory
    DESCRIPTION     
            "The target number of calls generated per second."
    DEFVAL          { 0 }
    ::= { sonusLt303AdmnObjects 1 }

sonusLt303GenerationInterval OBJECT-TYPE
    SYNTAX          Gauge (10..65535)
    ACCESS          read-write
    STATUS          mandatory
    DESCRIPTION     
            "The interval (in milliseconds) between bursts of call generation."
    DEFVAL          { 100 }
    ::= { sonusLt303AdmnObjects 2 }

sonusLt303GenerationLimit OBJECT-TYPE
    SYNTAX          Gauge (0..20000)
    ACCESS          read-write
    STATUS          mandatory
    DESCRIPTION     
            "The maximum number of simultaneous calls generated."
    DEFVAL          { 20000 }
    ::= { sonusLt303AdmnObjects 3 }

sonusLt303GenerateIfChannelsExist OBJECT-TYPE
    SYNTAX          SonusAdminState
    ACCESS          read-write
    STATUS          mandatory
    DESCRIPTION     
            "If enabled, a call is generated only if free channels exist
             at the originating and terminating Interface Groups."
    DEFVAL          { enabled }
    ::= { sonusLt303AdmnObjects 4 }

sonusLt303ConnectedDurationMin OBJECT-TYPE
    SYNTAX          Gauge (1..3600)
    ACCESS          read-write
    STATUS          mandatory
    DESCRIPTION     
            "The minimum time (in seconds) a generated call stays connected.
             For each call, a random value is chosen between Min and Max."
    DEFVAL          { 30 }
    ::= { sonusLt303AdmnObjects 5 }

sonusLt303ConnectedDurationMax OBJECT-TYPE
    SYNTAX          Gauge (1..3600)
    ACCESS          read-write
    STATUS          mandatory
    DESCRIPTION     
            "The maximum time (in seconds) a generated call stays connected.
             For each call, a random value is chosen between Min and Max."
    DEFVAL          { 30 }
    ::= { sonusLt303AdmnObjects 6 }

sonusLt303CircuitServiceProfile OBJECT-TYPE
    SYNTAX          SonusNameReference
    ACCESS          read-write
    STATUS          mandatory
    DESCRIPTION     
            "CAS and other channels with this profile name will receive media path testing."
    ::= { sonusLt303AdmnObjects 7 }

sonusLt303MediaPathTest OBJECT-TYPE
    SYNTAX          INTEGER { none(0), downThenUp(1), upThenDown(2), 
                        downOnly(3), upOnly(4) }
    ACCESS          read-write
    STATUS          mandatory
    DESCRIPTION     
            "The kind of media path testing applied to load test calls,
             a choice of upstream and/or downstream tones."
    DEFVAL          { none }
    ::= { sonusLt303AdmnObjects 8 }

sonusLt303DisconnectSequence OBJECT-TYPE
    SYNTAX          INTEGER { random(0), originator(1), terminator(2), 
                        together(3) }
    ACCESS          read-write
    STATUS          mandatory
    DESCRIPTION     
            "Which party goes on hook to end a call normally."
    DEFVAL          { random }
    ::= { sonusLt303AdmnObjects 9 }

sonusLt303SetupTimer OBJECT-TYPE
    SYNTAX          Gauge (0..300)
    ACCESS          read-write
    STATUS          mandatory
    DESCRIPTION     
            "The time allowed (in seconds) to connect a load test call.
             If this timer expires, the call will be aborted."
    DEFVAL          { 120 }
    ::= { sonusLt303AdmnObjects 10 }

sonusLt303ReleaseTimer OBJECT-TYPE
    SYNTAX          Gauge (0..300)
    ACCESS          read-write
    STATUS          mandatory
    DESCRIPTION     
            "The time allowed (in seconds) to release a load test call.
             If this timer expires, the call will be aborted."
    DEFVAL          { 120 }
    ::= { sonusLt303AdmnObjects 11 }

sonusLt303StopOnFailureSequence OBJECT-TYPE
    SYNTAX          INTEGER { nothing(0), rateZero(1), stopCalls(2) }
    ACCESS          read-write
    STATUS          mandatory
    DESCRIPTION     
            "What to do when call failure detected."
    DEFVAL          { nothing }
    ::= { sonusLt303AdmnObjects 12 }

END -- end of module SONUS-LOAD-TEST-MIB.
