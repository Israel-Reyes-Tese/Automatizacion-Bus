--
-- This SMIv1 module has been generated by smidump 0.2-cvs. Do not edit.
--

SONUS-COMMON-TC DEFINITIONS ::= BEGIN

IMPORTS
    sonusCommonSoftwarePlatformServicesMIBs
        FROM SONUS-SMI;

sonusCommonTextualConventions OBJECT IDENTIFIER
    ::= { sonusCommonSoftwarePlatformServicesMIBs 2 }

-- sonusCommonTextualConventions MODULE-IDENTITY
--     LAST-UPDATED    "201310070000Z"
--     ORGANIZATION    
--             "Sonus Networks, Inc."
--     CONTACT-INFO    
--             "   Customer Support    
--              Sonus Networks, Inc.
--              4 Technology Park Drive
--              Westford, MA 01886
--              USA
--              
--              Tel: 978-614-8100
--              Fax: 978-614-8609"
--     DESCRIPTION     
--             "This module defines textual conventions used throughout
--              sonus enterprise mibs."
--     ::= { sonusCommonSoftwarePlatformServicesMIBs 2 }


SonusAlarmLevel ::=
    INTEGER { critical(1), major(2), minor(3), info(4) }

-- SonusAlarmLevel ::= TEXTUAL-CONVENTION
--     STATUS          mandatory
--     DESCRIPTION     
--             "The severity level of events."
--     SYNTAX          INTEGER
--                       { critical(1), major(2), minor(3), info(4) }

SonusAlarmFilterLevel ::=
    INTEGER { noevents(0), critical(1), major(2), minor(3), info(4) }

-- SonusAlarmFilterLevel ::= TEXTUAL-CONVENTION
--     STATUS          mandatory
--     DESCRIPTION     
--             "The filter severity level of events."
--     SYNTAX          INTEGER
--                       { noevents(0), critical(1), major(2), minor(3), 
--                         info(4) }

SonusName ::=
    OCTET STRING (SIZE(1..23))

-- SonusName ::= TEXTUAL-CONVENTION
--     DISPLAY-HINT    "255a"
--     STATUS          mandatory
--     DESCRIPTION     
--             "This data type is used to model textual information taken
--              from the NVT ASCII character set.  The SonusName type is used
--              to label Sonus Named objects."
--     SYNTAX          OCTET STRING (SIZE(1..23))

SonusNameReference ::=
    OCTET STRING (SIZE(0..23))

-- SonusNameReference ::= TEXTUAL-CONVENTION
--     DISPLAY-HINT    "255a"
--     STATUS          mandatory
--     DESCRIPTION     
--             "This data type is used to model textual information taken
--              from the NVT ASCII character set.  The SonusNameReference
--              type is used to refer to Sonus Named objects."
--     SYNTAX          OCTET STRING (SIZE(0..23))

SonusServiceState ::=
    INTEGER { outOfService(1), inService(2) }

-- SonusServiceState ::= TEXTUAL-CONVENTION
--     STATUS          mandatory
--     DESCRIPTION     
--             "The service state of a resource."
--     SYNTAX          INTEGER
--                       { outOfService(1), inService(2) }

SonusAdminState ::=
    INTEGER { disabled(1), enabled(2) }

-- SonusAdminState ::= TEXTUAL-CONVENTION
--     STATUS          mandatory
--     DESCRIPTION     
--             "The administrative state of a resource."
--     SYNTAX          INTEGER
--                       { disabled(1), enabled(2) }

SonusAdminAction ::=
    INTEGER { dryUp(1), force(2) }

-- SonusAdminAction ::= TEXTUAL-CONVENTION
--     STATUS          mandatory
--     DESCRIPTION     
--             "The action assignment of a resource."
--     SYNTAX          INTEGER
--                       { dryUp(1), force(2) }

SonusSoftwareVersion ::=
    OCTET STRING (SIZE(6))

-- SonusSoftwareVersion ::= TEXTUAL-CONVENTION
--     DISPLAY-HINT    "1d.1d.1d.1d.2d"
--     STATUS          mandatory
--     DESCRIPTION     
--             "Octet string that identifies the version of the runtime
--              software application:
--              
--              Byte(s)  Code
--              -------  ----
--              0        major version
--              1        minor version
--              2        release version
--              3        type (1:alpha, 2:beta, 3:release, 4:special)
--              4-5      type build number"
--     SYNTAX          OCTET STRING (SIZE(6))

SonusGMTTime ::=
    OCTET STRING (SIZE(4))

-- SonusGMTTime ::= TEXTUAL-CONVENTION
--     DISPLAY-HINT    "1d:1d:1d.1d"
--     STATUS          mandatory
--     DESCRIPTION     
--             "The pure GMT time specification ( without YY-MM-DD ) 
--              for daily reoccurring events.
--              
--              field  octets  contents                  range
--              -----  ------  --------                  -----
--                1       1    hour                      0..23
--                2       2    minutes                   0..59
--                3       3    seconds                   0..60
--                             (use 60 for leap-second)
--                4       4    deci-seconds              0..9
--              "
--     SYNTAX          OCTET STRING (SIZE(4))

SonusAcctRecordType ::=
    INTEGER { start(1), stop(2), attempt(3), intermediate(4), reboot(5), 
                        switchover(6) }

-- SonusAcctRecordType ::= TEXTUAL-CONVENTION
--     STATUS          mandatory
--     DESCRIPTION     
--             "Represents the different types of call accounting records
--              that are available in Sonus Products."
--     SYNTAX          INTEGER
--                       { start(1), stop(2), attempt(3), 
--                         intermediate(4), reboot(5), switchover(6) }

SonusIpAddress ::=
    OCTET STRING (SIZE(16))

-- SonusIpAddress ::= TEXTUAL-CONVENTION
--     STATUS          mandatory
--     DESCRIPTION     
--             "The IPv6 address."
--     SYNTAX          OCTET STRING (SIZE(16))

SonusIpPrefix ::=
    Gauge (0..128)

-- SonusIpPrefix ::= TEXTUAL-CONVENTION
--     STATUS          mandatory
--     DESCRIPTION     
--             "The prefix of IP address."
--     SYNTAX          Gauge (0..128)

SonusIpPort ::=
    Gauge (0..65535)

-- SonusIpPort ::= TEXTUAL-CONVENTION
--     STATUS          mandatory
--     DESCRIPTION     
--             "The index for a Sonus shelf."
--     SYNTAX          Gauge (0..65535)

SonusShelfIndex ::=
    INTEGER (1..6)

-- SonusShelfIndex ::= TEXTUAL-CONVENTION
--     STATUS          mandatory
--     DESCRIPTION     
--             "The index for a Sonus shelf."
--     SYNTAX          INTEGER (1..6)

SonusSlotIndex ::=
    INTEGER (1..18)

-- SonusSlotIndex ::= TEXTUAL-CONVENTION
--     STATUS          mandatory
--     DESCRIPTION     
--             "The index for a Sonus slot."
--     SYNTAX          INTEGER (1..18)

END -- end of module SONUS-COMMON-TC.
