--
-- This SMIv2 module has been generated by smidump 0.2-cvs. Do not edit.
--

UX-TRAP-MIB DEFINITIONS ::= BEGIN

IMPORTS
    Counter32, Counter64, IpAddress, MODULE-IDENTITY, NOTIFICATION-TYPE, 
    OBJECT-TYPE, enterprises
        FROM SNMPv2-SMI
    DisplayString, TEXTUAL-CONVENTION
        FROM SNMPv2-TC
    uxAlarmActiveCancelType, uxAlarmActiveCategory, 
    uxAlarmActiveClrEvtID, uxAlarmActiveClrEvtSubID, 
    uxAlarmActiveCondition, uxAlarmActiveCount, uxAlarmActiveDecodeKey, 
    uxAlarmActiveDescription, uxAlarmActiveFirstOccur, 
    uxAlarmActiveHardWareID, uxAlarmActiveHighestSeverityAlarm, 
    uxAlarmActiveID, uxAlarmActiveIndex, uxAlarmActiveLastOccur, 
    uxAlarmActiveSeverity, uxAlarmActiveSourceInstance, 
    uxAlarmActiveState, uxAlarmActiveSubID, uxAlarmConfigIndex
        FROM UX-OBJECTS-MIB;

ux MODULE-IDENTITY
    LAST-UPDATED    "201807241735Z"
    ORGANIZATION    
            "Ribbon Communications"
    CONTACT-INFO    
            "Ribbon Service
             E-mail: TAC_VA@rbbn.com"
    DESCRIPTION     
            "The MIB module for Ribbon Communications SBC Edge entities. 
             This MIB module describes the enterprise traps for the SBC Edge."
    ::= { enterprises 177 15 }


net OBJECT IDENTIFIER
    ::= { enterprises 177 }

uxObjects OBJECT IDENTIFIER
    ::= { enterprises 177 15 1 }

uxTraps OBJECT IDENTIFIER
    ::= { enterprises 177 15 2 }

uxAlmADcachingfailed NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Failed to cache attributes from AD in memory. Suggested action - try again later. This alarm will be cleared by event AD caching successful."
    ::= { enterprises 177 15 2 65537 }

uxAlmOnlineADqueryfailed NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Failed to execute AD query. Suggested action - confirm that AD is network reachable, check the AD configuration as well as AD access credentials."
    ::= { enterprises 177 15 2 65538 }

uxAlmUserloggedin NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "New user 'username' logged in from 'ip address'."
    ::= { enterprises 177 15 2 65540 }

uxAlmUserloginfailed NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "User 'username' login failed from 'ip' at 'time'. This alarm will be cleared by event User logged in."
    ::= { enterprises 177 15 2 65541 }

uxAlmADUnreachable NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Either AD is network unreachable, or the AD credentials are invalid. This alarm will be cleared by 'AD Reachable' event."
    ::= { enterprises 177 15 2 65542 }

uxAlmADReachable NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Active directory is now reachable."
    ::= { enterprises 177 15 2 65543 }

uxAlmADcachingsuccessful NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "AD caching was successful."
    ::= { enterprises 177 15 2 65544 }

uxAlmADbackupfailed NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Failed to backup cached values from AD to storage device. Either the storage device is not present, or it is full. Contact Ribbon Service for further assistance."
    ::= { enterprises 177 15 2 65545 }

uxAlmADsuccessfullybackedup NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Successful backup of cached values from AD to storage device."
    ::= { enterprises 177 15 2 65546 }

uxAlmADcachetruncated NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "AD Cache is truncated, AD cache results have exceeded the maximum cache size. Consider caching only the required attributes. If the query is not found in cache, Online query will be performed, while affecting performance."
    ::= { enterprises 177 15 2 65547 }

uxAlmRADIUSServerUnreachable NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Either the RADIUS server is network unreachable, the configuration is incorrect, or due to service impacting change.  Suggested action - check shared secret, listening port, RADIUS server IP. This alarm will be cleared by 'RADIUS Reachable' event."
    ::= { enterprises 177 15 2 65548 }

uxAlmRADIUSReachable NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "RADIUS server is online."
    ::= { enterprises 177 15 2 65549 }

uxAlmCDRloggingfailed NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "SBC Edge failed to send CDR to RADIUS based accounting server. Either the server is network unreachable, or the configuration is incorrect.  Suggested action - check shared secret, listening port, RADIUS server IP."
    ::= { enterprises 177 15 2 65550 }

uxAlmCDRbackupfailed NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "SBC Edge failed to backup CDR in local file. Either running with low disk space or CDR backup maximum limit is crossed. Suggested action - Free up the disk space or save the CDR Queued file for future reference."
    ::= { enterprises 177 15 2 65551 }

uxAlmUserpasswordchangedsuccessfully NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Password changed successfully by 'username' from 'ip address'."
    ::= { enterprises 177 15 2 65553 }

uxAlmUserpasswordchangefailed NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Password change attempted by 'username' from 'ip address' failed."
    ::= { enterprises 177 15 2 65554 }

uxAlmUseraccountdisabled NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Account has been disabled by 'username' from 'ip address'."
    ::= { enterprises 177 15 2 65555 }

uxAlmUseraccountactivated NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Account has been activated by 'username' from 'ip address'."
    ::= { enterprises 177 15 2 65556 }

uxAlmGlobalsecurityoptionschanged NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Global security options changed."
    ::= { enterprises 177 15 2 65557 }

uxAlmUserloginblocked NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "User attempting to log in from 'ip' blocked due to excessive incorrect login attempts."
    ::= { enterprises 177 15 2 65558 }

uxAlmUserloginunblocked NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "User login is unblocked."
    ::= { enterprises 177 15 2 65559 }

uxAlmUserpasswordexpired NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Password has expired. User 'username' logging in from 'ip' password is expired."
    ::= { enterprises 177 15 2 65560 }

uxAlmADMaximumThreadsExceeded NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "AD has reached maximum threads. Please inform your service representative."
    ::= { enterprises 177 15 2 65561 }

uxAlmADcachingtimedout NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Timed out caching attributes due to lack of response from AD. Suggested action - try again later. The SBC will attempt to load the last successful cache from backup."
    ::= { enterprises 177 15 2 65562 }

uxAlmADCacheEncryptionFailed NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "AD Cache encryption failed. Cache will not be saved."
    ::= { enterprises 177 15 2 65563 }

uxAlmADCacheEncryptionSuccessful NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "AD Cache encryption successful."
    ::= { enterprises 177 15 2 65564 }

uxAlmInvalidCardIDEEPROMData NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "A Card was detected with invalid Card ID EEPROM (failed CRC-CCITT check). Suggested action - provide the entire alarm message including the numbers at the end to Ribbon Service for further assistance."
    ::= { enterprises 177 15 2 131073 }

uxAlmCardHealthCheckFailed NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "During Line Card activation, a Card Fault was detected after power was applied to the card. The Card will remain out-of-service.  Suggested action - reboot system. If issue persists, contact Ribbon Service with the alarm information."
    ::= { enterprises 177 15 2 131074 }

uxAlmCardnotSupported NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "A Card was detected which can be identified, but the SBC Edge software is unable to support. The Card will remain out-of-service. Suggested action - reboot system. If issue persists, contact Ribbon Service with the alarm information."
    ::= { enterprises 177 15 2 131075 }

uxAlmPowerSupplyinputfailure NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "A Power supply module has indicated a failure of input power. The SBC Edge has lost Power Supply redundancy. Suggested action - Verify that the power cable is connected and that the PS is functioning properly."
    ::= { enterprises 177 15 2 131076 }

uxAlmPowerSupplyinputrestored NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "A Power Supply module has indicated that input power has been restored. This event clears the 'Power Supply Input Failure' Alarm."
    ::= { enterprises 177 15 2 131077 }

uxAlmPowerSupplyoutputfailure NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "A Power Supply module has indicated a failure of output power. The SBC Edge has lost Power Supply redundancy. Suggested action - Verify that the PS is functioning properly."
    ::= { enterprises 177 15 2 131078 }

uxAlmSingleFanfailure NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Check the System tab to find the Fan ID of the failed fan. Contact Ribbon Service with this information."
    ::= { enterprises 177 15 2 131079 }

uxAlmMultipleFanFailures NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Check the System tab to find the Fan ID's of the failed fans. Contact Ribbon Service with this information."
    ::= { enterprises 177 15 2 131080 }

uxAlmSystemTemperatureWarm NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "The temperature sensors have indicated that the system is running warm (55 degrees C threshold)."
    ::= { enterprises 177 15 2 131081 }

uxAlmSystemTemperatureWarmCleared NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "The temperature sensors have indicated that the system is no longer running warm (55 degrees C threshold). This event clears the 'System Temperature Warm' Alarm."
    ::= { enterprises 177 15 2 131082 }

uxAlmSystemTemperatureHot NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "The temperature sensors have indicated that system is running hot (65 degrees C threshold)."
    ::= { enterprises 177 15 2 131083 }

uxAlmSystemTemperatureHotCleared NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "The temperature sensors have indicated that the system is no longer running hot (65 degrees C threshold). This event clears the 'System Temperature Hot' Alarm."
    ::= { enterprises 177 15 2 131084 }

uxAlmLicensesexpired NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "License of the node has expired, all the licensed features would fail to work. Contact Ribbon Enterprise Sales."
    ::= { enterprises 177 15 2 196609 }

uxAlmLicenseexpiresin2weeks NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "License of the node will expire in 2 weeks."
    ::= { enterprises 177 15 2 196610 }

uxAlmNewLicenseapplied NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "New License is applied on the node."
    ::= { enterprises 177 15 2 196611 }

uxAlmFailedtoApplyLicense NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Either an invalid key is used, or the license key applies to a different node, or the license key expiry is past the present date. Contact Ribbon Sales to obtain a new license."
    ::= { enterprises 177 15 2 196612 }

uxAlmFailedtoacquirelicense NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "License(s) for 'license type' has been exhausted or is not licensed."
    ::= { enterprises 177 15 2 196613 }

uxAlmLicensedDS1portsexceedsinstalledports NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "The alarm is generated when the license key applied has more DS1 ports licensed than are installed in the system. The number of BRI ports installed will get activated. As a fix, obtain a license with correct number of DS1 ports."
    ::= { enterprises 177 15 2 196614 }

uxAlmLicensedBRIportsexceedsinstalledports NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "The alarm is generated when the license key applied has more BRI ports licensed than are installed in the system. The number of BRI ports installed will get activated. As a fix, obtain a license with correct number of BRI ports."
    ::= { enterprises 177 15 2 196615 }

uxAlmLicensedFXSportsexceedsinstalledports NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "The alarm is generated when the license key applied has more FXS ports licensed than are installed in the system. The number of FXS ports installed will get activated. As a fix, obtain a license with correct number of FXS ports."
    ::= { enterprises 177 15 2 196616 }

uxAlmLicensedFXOportsexceedsinstalledports NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "The alarm is generated when the license key applied has more FXO ports licensed than are installed in the system. The number of FXO ports installed will get activated. As a fix, obtain a license with correct number of FXO ports."
    ::= { enterprises 177 15 2 196617 }

uxAlmFailedtogetkeyforLicensegeneration NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Failed to get key for license generation."
    ::= { enterprises 177 15 2 196618 }

uxAlmLicensedSIPSignalingSessionsexceedssystemcapability NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "The alarm is generated when the license key applied has more SIP Signaling Sessions licensed than the system is capable of. Extra licenses will not be used. As a fix, obtain a license with correct number of SIP Signaling Sessions."
    ::= { enterprises 177 15 2 196619 }

uxAlmLicensedSIPRegistrationsexceedssystemcapability NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "The alarm is generated when the license key applied has more SIP Registrations licensed than the system is capable of. Extra licenses will not be used. As a fix, obtain a license with correct number of SIP Registrations."
    ::= { enterprises 177 15 2 196620 }

uxAlmLicensedSIPMediaSessionsexceedssystemcapability NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "The alarm is generated when the license key applied has more SIP Media Sessions licensed than the system is capable of. Extra licenses will not be used. As a fix, obtain a license with correct number of SIP Media Sessions."
    ::= { enterprises 177 15 2 196621 }

uxAlmLicensedProxyLocalSRTPMediaSessionsexceedssystemcapability NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "The alarm is generated when the license key applied has more SIP Proxy Encrypted Media Sessions licensed than the system is capable of. Extra licenses will not be used. As a fix, obtain a license with correct number of SIP Media Sessions."
    ::= { enterprises 177 15 2 196622 }

uxAlmLicensedRTPProxysessionsexceedsystemcapability NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "SIP RTP Proxy Sessions of 'number' licenses exceeds the capability of the system of 'number' licenses. As a fix, obtain a license with correct number of SIP RTP Proxy Sessions."
    ::= { enterprises 177 15 2 196623 }

uxAlmLicensedVideosessionsexceedsystemcapability NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "SIP Video Sessions of 'number' licenses exceeds the capability of the system of 'number' licenses. As a fix, obtain a license with correct number of SIP Video Sessions."
    ::= { enterprises 177 15 2 196624 }

uxAlmLicensedHighCapacity250sessionsexceedsystemcapability NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "SIP High Capacity (250+) Sessions of 'number' licenses exceeds the capability of the system of 'number' licenses. As a fix, obtain a license with correct number of SIP High Capacity Sessions."
    ::= { enterprises 177 15 2 196625 }

uxAlmSIPHighCapacity250Licenserequired NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "The SIP Signal Sessions of 'number' licenses exceeds the SIP High Capability (250+) Sessions of 'number' licenses. As a fix, obtain a license with correct number of SIP High Capacity Sessions."
    ::= { enterprises 177 15 2 196626 }

uxAlmASMUnreachable NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "ASM system can not be reached, system is down. Check whether the ASM is rebooting."
    ::= { enterprises 177 15 2 327681 }

uxAlmClearASMUnreachable NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Clears alarm 'ASM Unreachable'."
    ::= { enterprises 177 15 2 327682 }

uxAlmASMFailureRecovered NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "ASM system was previously unreachable, but has come up. This alarm doesn't autoclear so the user can investigate the cause, but the system should be working correctly now."
    ::= { enterprises 177 15 2 327683 }

uxAlmASMServicesNotRunning NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "ASM services are not running, calls through the ASM cannot be placed."
    ::= { enterprises 177 15 2 327684 }

uxAlmClearASMServicesNotRunning NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Clears alarm 'ASM Services Not Running'."
    ::= { enterprises 177 15 2 327685 }

uxAlmASMServicesRestarted NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "ASM Services was previously stopped, but has started. This alarm doesn't autoclear so the user can investigate the cause, but ASM Services should be working correctly now."
    ::= { enterprises 177 15 2 327686 }

uxAlmASMServiceRestartFailed NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "The system attempted to restart a failed service on the ASM, service did not start successfully. User interaction is required."
    ::= { enterprises 177 15 2 327687 }

uxAlmASMSystemStarted NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "This event is set when the SBA communication system is first established, and usually indicates that the Application Solution Module (ASM) has finished booting. It should come up at system startup, it may come again if the ASM hardware is rebooted."
    ::= { enterprises 177 15 2 327688 }

uxAlmASMSystemShuttingdown NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "A planned or deliberate shut down is taking place on the Application Solution Module (ASM)."
    ::= { enterprises 177 15 2 327689 }

uxAlmEthernetLinkDown NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Ethernet port specified has lost link. Source Instance: Eth0/Eth1 via SBA Monitor."
    ::= { enterprises 177 15 2 327690 }

uxAlmEthernetLinkUp NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Ethernet port specific has recovered link. "
    ::= { enterprises 177 15 2 327691 }

uxAlmASMSBCIPSubnetMismatch NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "The ASM and SBC Edge IP interfaces are in different subnets and cannot communicate."
    ::= { enterprises 177 15 2 327692 }

uxAlmASMSBCIPSubnetMatch NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "The ASM and SBC Edge IP interfaces are in the same subnet and can now communicate."
    ::= { enterprises 177 15 2 327693 }

uxAlmASMQoESQLdatabaseisunreachable NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "The QoE database is unreachable from ASM, make sure Skype for Business Server or Lync Server 2013 is deployed and Monitoring database is running"
    ::= { enterprises 177 15 2 327694 }

uxAlmClearASMQoESQLdatabaseisunreachable NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "The QoE database is now reachable from ASM."
    ::= { enterprises 177 15 2 327695 }

uxAlmASMfailedtostoreQoEinformation NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Failed to store the QoE information from ASM."
    ::= { enterprises 177 15 2 327696 }

uxAlmASMSBCCACUpdatefailed NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "The ASM hasn't been able to apply the CAC update."
    ::= { enterprises 177 15 2 327697 }

uxAlmASMSBCCACUpdateapplied NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "ASM-SBC CAC Update applied."
    ::= { enterprises 177 15 2 327698 }

uxAlmThiscopyofASMOperatingSystemisnotgenuine NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "ASM Windows Server is not able to activate as genuine Microsoft product."
    ::= { enterprises 177 15 2 327699 }

uxAlmASMdriveNFSmountfailure NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "NFS mounting of ASM drive failed, make sure ASM module is up and NFS service is running on the ASM module"
    ::= { enterprises 177 15 2 327700 }

uxAlmClearASMdriveNFSmountfailure NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "ASM hard drive is NFS mounted and available."
    ::= { enterprises 177 15 2 327701 }

uxAlmASMOperatingSystemSuccessfullyActivated NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "ASM Windows Server is activate as genuine Microsoft product."
    ::= { enterprises 177 15 2 327702 }

uxAlmASMIPaddressconflict NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "The current ASM IP 'IP address' is in use by a 'Device' ('MAC address'), Change the 'Device' IP 'Is PowerCycle required' and retry"
    ::= { enterprises 177 15 2 327703 }

uxAlmClearASMIPaddressconflict NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "ASM IP address conflict cleared."
    ::= { enterprises 177 15 2 327704 }

uxAlmASMEthernetPortDown NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "ASM Ethernet Port have been detected down"
    ::= { enterprises 177 15 2 327705 }

uxAlmClearASMEthernetPortDown NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "ASM Ethernet Port have been detected down is cleared."
    ::= { enterprises 177 15 2 327706 }

uxAlmActiveCCEMaintenanceMode NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Cloud Connector Edition entered Maintenance mode due to 'Update Type'"
    ::= { enterprises 177 15 2 327707 }

uxAlmClearActiveCCEMaintenanceMode NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Cloud Connector Edition exited maintenance mode."
    ::= { enterprises 177 15 2 327708 }

uxAlmCCEWindowsProductKeyismissing NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Cloud Connector Edition Windows Product Key is missing."
    ::= { enterprises 177 15 2 327709 }

uxAlmClearCCEWindowsProductKeyismissingorfailedtoactivate NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Cloud Connector Edition Windows Product Key has been found."
    ::= { enterprises 177 15 2 327710 }

uxAlmCCEWindowsProductfailedtoactivate NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Cloud Connector Edition Windows Product failed to activate"
    ::= { enterprises 177 15 2 327711 }

uxAlmASMandSBCFirmwaremismatch NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "ASM('SbcComms version') and SBC('SBC version') firmware version does not match"
    ::= { enterprises 177 15 2 327712 }

uxAlmClearASMandSBCFirmwaremismatch NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "ASM and SBC firmware version does not match is cleared."
    ::= { enterprises 177 15 2 327713 }

uxAlmFailedtoincreasetheCCEMediationVMressource NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "From the ASM Hyper-V Manager, assign 9 vCPU to the CCE Mediation Server VM."
    ::= { enterprises 177 15 2 327714 }

uxAlmConfigurationchangeoccurredonActionSet NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Action set modified 'id'."
    ::= { enterprises 177 15 2 458753 }

uxAlmConfigurationchangeoccurredonNormalizationTable NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "There is a normalization table number/name that should be printed with this event."
    ::= { enterprises 177 15 2 458754 }

uxAlmConfigurationchangeoccurredonRouteTable NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Routing table modified 'id'."
    ::= { enterprises 177 15 2 458755 }

uxAlmConfigurationchangeoccurredonTransformationTables NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Transformation table modified 'id'."
    ::= { enterprises 177 15 2 458756 }

uxAlmRoutetemporarilydisabled NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Route temporarily disabled due to signaling group(s) down."
    ::= { enterprises 177 15 2 458757 }

uxAlmRouteenabled NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Route enabled as the signaling group is up."
    ::= { enterprises 177 15 2 458758 }

uxAlmACallexceededthelimitfornumberofdestinations NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Maximum(8) call forks exceeded, no more forks for this destination"
    ::= { enterprises 177 15 2 458759 }

uxAlmCallforkingusedwithnoforkinglicense NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Call forking used with no forking license."
    ::= { enterprises 177 15 2 458760 }

uxAlmInvocationofInvokeActionSetexceededthemaximumnestinglimit NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Maximum(10) nested InvokeActionSet exceeded."
    ::= { enterprises 177 15 2 458761 }

uxAlmConfigurationchangeoccurredonCallbackTables NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Callback table 'id' modified."
    ::= { enterprises 177 15 2 458762 }

uxAlmChannelisinservice NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Channel is up and is in service. This clears the 'Channel out of service' alarm."
    ::= { enterprises 177 15 2 524289 }

uxAlmChannelisoutofservice NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Channel Out Of Service Alarm. This alarm is automatically cleared when Channel is in service."
    ::= { enterprises 177 15 2 524290 }

uxAlmEmergencyCallAttempted NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Emergency Call is attempted from Calling Number, Calling Extension, Caller IP address."
    ::= { enterprises 177 15 2 524291 }

uxAlmEmergencyCallCompleted NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Emergency Call completed. The alarm will be cleared after expiry time in emergency status table."
    ::= { enterprises 177 15 2 524292 }

uxAlmQoEReportNotSentDuetoRTCPMediaList NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "QoE Report for the Signaling Group not sent. To enable QoE report for this Signaling Group, check the Media List associated with the SG and set RTCP Mode to RTCP-XR."
    ::= { enterprises 177 15 2 524293 }

uxAlmCallTransferfailedduetocallnotbeinginDSPmode NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "The call is not in DSP mode - hence the call transfer could not be honored. Set Agent Type as Access Mode to pass through the SIP REFER."
    ::= { enterprises 177 15 2 524294 }

uxAlmCallAttemptfailedduetoMediaModemismatch NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "The call failed due to Media Mode mismatch across SG and Call Route configuration."
    ::= { enterprises 177 15 2 524295 }

uxAlmSGDrained NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "SG set to Drain Mode, all channels are idle"
    ::= { enterprises 177 15 2 524296 }

uxAlmNonEmergencyCallPreemptedduetoanEmergencyCallAttempt NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Non-Emergency Call Preempted due to an Emergency Call Attempt."
    ::= { enterprises 177 15 2 524297 }

uxAlmLicensedSIPMediaSessioncountreached NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Number of licensed SIP Media Sessions has been reached."
    ::= { enterprises 177 15 2 524298 }

uxAlmLicensedProxyLocalSRTPcountreached NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Number of licensed Proxy Local SRTP has been reached."
    ::= { enterprises 177 15 2 524299 }

uxAlmNoAMRWidebandlicense NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "AMR Wideband call attempted but not licensed."
    ::= { enterprises 177 15 2 524300 }

uxAlmMaximumCallDurationExceeded NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Maximum call duration exceeded for call and call has been disconnected."
    ::= { enterprises 177 15 2 524301 }

uxAlmSIPServerNotResponding NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "SIP server has failed to respond and has been taken out of service. This alarm will be cleared by the event 'SIP server became responsive'."
    ::= { enterprises 177 15 2 589825 }

uxAlmSignalingGroupTakenoutofService NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "All servers in SG have failed. This alarm will be cleared by 'SIP Signaling group enabled' event."
    ::= { enterprises 177 15 2 589826 }

uxAlmSignalingGroupDisabled NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Configuration action has changed this Signaling Group from Enabled to Disabled."
    ::= { enterprises 177 15 2 589827 }

uxAlmSIPTLSServerHandshakeFailure NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "TLS server handshake failed with alert code. Action: Refer to Error Alerts in RFC 5246 for the problem."
    ::= { enterprises 177 15 2 589828 }

uxAlmSIPTLSHandshakeInactivityTimeoutFailure NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Handshake failed due to no response from peer within specified timeout. Action: Increase the Handshake Inactivity Timeout in TLS Profile."
    ::= { enterprises 177 15 2 589829 }

uxAlmConfiguredPortNumberMismatch NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Discrepancy of an FQDN/Port configured in the SipServer object that is different than the DNS SRV lookup. A DNS SRV record can return the port number for the selected protocol. The DNS SRV port value will take priority over the configured port."
    ::= { enterprises 177 15 2 589830 }

uxAlmSIPServerBecameResponsive NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "SIP server came up."
    ::= { enterprises 177 15 2 589831 }

uxAlmSIPclusterwentdown NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "SIP cluster went down. This is due to all the servers in the clusters being unresponsive. This alarm will be cleared by the event 'SIP Cluster Enabled'. "
    ::= { enterprises 177 15 2 589832 }

uxAlmSIPClusterEnabled NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "SIP cluster enabled."
    ::= { enterprises 177 15 2 589833 }

uxAlmSIPSignalingGroupEnabled NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "SIP Signaling group enabled."
    ::= { enterprises 177 15 2 589834 }

uxAlmSIPSignalingGroupDNSFailure NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Failed to resolve the FQDN entries in the SIP Signaling Group. Suggested action - confirm the FQDNs, and confirm DNS access."
    ::= { enterprises 177 15 2 589835 }

uxAlmSIPSignalingGroupFQDNResolved NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Successfully resolved the FQDN of the SIP Signaling group."
    ::= { enterprises 177 15 2 589836 }

uxAlmSIPServerDNSFailure NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Failed to resolve the SIP server FQDN entries in the SIP Server table. Suggested action - check the FQDN syntax."
    ::= { enterprises 177 15 2 589837 }

uxAlmSIPServerFQDNResolved NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "SIP Server config FQDN resolved."
    ::= { enterprises 177 15 2 589838 }

uxAlmSIPCallSessionDNSFailure NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Failed to resolve an FQDN with DNS server during a SIP call session."
    ::= { enterprises 177 15 2 589839 }

uxAlmAcquiringLicenseforRegisterFailed NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Failed to acquire license from License Manager"
    ::= { enterprises 177 15 2 589840 }

uxAlmSessionorOtherResourceLeak NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "SIP performs self-check for leaks. Please enable logging for sip and issue 'show resources' command."
    ::= { enterprises 177 15 2 589841 }

uxAlmFailedtoBindtoNetworkInterface NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Failed to bind to network interface due to dynamic IP address not available."
    ::= { enterprises 177 15 2 589842 }

uxAlmSuccessfullyBoundtoNetworkInterface NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Successfully bound to network interface. DHCP lease renewed."
    ::= { enterprises 177 15 2 589843 }

uxAlmSIPRegisterServerNotResponding NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "SIP Register server has failed to respond. This alarm will be cleared by the event 'SIP Register server became responsive'."
    ::= { enterprises 177 15 2 589844 }

uxAlmSIPRegisterServerBecameResponsive NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "SIP Register server came up."
    ::= { enterprises 177 15 2 589845 }

uxAlmRegistrationNotValidReceivedstalefalse NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Stale=false/Registration no longer valid due to Incorrect Credentials."
    ::= { enterprises 177 15 2 589846 }

uxAlmConfigChangeforSIPEndpointThatReceivedstalefalse NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Config has changed, clear StaleIsFalse Alarm."
    ::= { enterprises 177 15 2 589847 }

uxAlmQoENotifyMessageResponseWasNotSuccessful NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "QoE Notify Message received a no response or a failed response. This alarm will be cleared by the event 'QoE Notify Message received a successful response'."
    ::= { enterprises 177 15 2 589848 }

uxAlmQoENotifyMessageResponseWasSuccessful NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "QoE Notify Message received a successful response."
    ::= { enterprises 177 15 2 589849 }

uxAlmSystemOverloadDetected NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "System processing is overloaded"
    ::= { enterprises 177 15 2 589850 }

uxAlmSystemOverloadCleared NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "System processing  resumes normal operation, overload cleared"
    ::= { enterprises 177 15 2 589851 }

uxAlmMaximumNumberofSIPSessionsReached NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "The maximum number of SIP sessions (calls/register/subscribe) has been reached on the signaling group. Increase the number of SIP Channels for the signaling group."
    ::= { enterprises 177 15 2 589852 }

uxAlmMaximumNumberofSIPSessionsAlarmCleared NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "SIP sessions per signaling group is under the maximum limit"
    ::= { enterprises 177 15 2 589853 }

uxAlmErrorresolvingSRVrecord NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Failed to execute SRV record query.  Suggested action - confirm that DNS server network is reachable, check SRV and DNS server configuration."
    ::= { enterprises 177 15 2 589854 }

uxAlmSRVrecordresolved NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "DNS server returned valid SRV record(s)."
    ::= { enterprises 177 15 2 589855 }

uxAlmSIPTLSHandshakeNegotiationStartFailure NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "'server' handshake failed to start with invalid certificate; 'connection ID', 'port ID'. Action: confirm that both signed Ribbon SBC Edge Certificate and Trusted CA Certificate exist."
    ::= { enterprises 177 15 2 589856 }

uxAlmSIPTLSHandshakeNegotiationStartSuccessful NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Handshake response was started with valid certificate on local and remote gateway. This event clears the 'SIP-TLS Handshake Negotiation Start Failure' alarm. "
    ::= { enterprises 177 15 2 589857 }

uxAlmMaximumsupportedSIPSGsreached NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "SIP signaling group Count Reached maximum Supported Limit. "
    ::= { enterprises 177 15 2 589858 }

uxAlmMaximumsupportedSIPSGscleared NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "SIP signaling group Count is under the maximum Supported"
    ::= { enterprises 177 15 2 589859 }

uxAlmMaximumnonSIPCallSessionsreached NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Number of SIP Non Call Sessions is over the system capacity"
    ::= { enterprises 177 15 2 589860 }

uxAlmMaximumnonSIPCallSessionscleared NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Number of SIP Non Call Sessions is under the system capacity"
    ::= { enterprises 177 15 2 589861 }

uxAlmMaximumSIPCallSessionsreached NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Number of SIP Call Sessions is over the system capacity"
    ::= { enterprises 177 15 2 589862 }

uxAlmMaximumSIPCallSessionscleared NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Number of SIP Call Sessions is under the system capacity"
    ::= { enterprises 177 15 2 589863 }

uxAlmBroadsoftSIPCallrerouted NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Broadsoft SIP Call re-routed"
    ::= { enterprises 177 15 2 589864 }

uxAlmBroadsoftSIPCallReroutedcleared NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Broadsoft SIP call re-routed cleared"
    ::= { enterprises 177 15 2 589865 }

uxAlmSIPSGListenProtocolandSIPServerHostProtocolmismatch NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Verify that the Listen Ports and Protocols for the SG match those in the Server Table"
    ::= { enterprises 177 15 2 589866 }

uxAlmConfigurationErrorSIPSGandServerProtocolMismatch NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Verify that the Listen Ports and Protocols for the SG match those in the Server Table"
    ::= { enterprises 177 15 2 589867 }

uxAlmSIPTLSClientHandshakeFailure NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "TLS client handshake failed with alert code. Action: Refer to Error Alerts in RFC 5246 for the problem."
    ::= { enterprises 177 15 2 589868 }

uxAlmSIPTLSHandshakeInactivityTimeoutCleared NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Handshake response was received within specified timeout. This event clears the 'SIP-TLS Handshake Inactivity Timeout Failure' alarm. "
    ::= { enterprises 177 15 2 589869 }

uxAlmSIPTLSServerHandshakeFailureCleared NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Handshake failure error alert condition was cleared. This event clears the 'SIP-TLS Server Handshake Failure' alarm. "
    ::= { enterprises 177 15 2 589870 }

uxAlmSIPTLSClientHandshakeFailureCleared NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Handshake failure error alert condition was cleared. This event clears the 'SIP-TLS Client Handshake Failure' alarm. "
    ::= { enterprises 177 15 2 589871 }

uxAlmSkypeLyncPresenceServerResponseFailure NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "A Presence Publish Request has been sent to the configured Lync Presence Front End and has received no response or a failed response."
    ::= { enterprises 177 15 2 589872 }

uxAlmSkypeLyncPresenceServerResponseFailureCleared NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "A presence server that previously was unreachable has successfully sent a message that the SBC has received. "
    ::= { enterprises 177 15 2 589873 }

uxAlmSIPRequestfromUntrustedIP NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "An INVITE message was received from a host without a matching Federated IP"
    ::= { enterprises 177 15 2 589874 }

uxAlmSIPRequestfromUntrustedIPCleared NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Source IP is added to the list of federated IP Addresses."
    ::= { enterprises 177 15 2 589875 }

uxAlmReSyncmessagereceivedonSGnotselectedforAutoConfigtask NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Check Auto Configuration Task settings and verify that the Signalling Group selected is correct."
    ::= { enterprises 177 15 2 589876 }

uxAlmMaximumNumberofSkypeLyncPresenceSessionsReached NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "The maximum number of 500 concurrent SIP Publish sessions for Presence has been reached. Skype/Lync Presence processing will be suspended until the number of concurrent sessions drops below 500 limit. "
    ::= { enterprises 177 15 2 589877 }

uxAlmMaximumNumberofS4BPresencePublishSessionsAlarmCleared NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "SIP Publish sessions for S4B Presence is under the maximum limit"
    ::= { enterprises 177 15 2 589878 }

uxAlmEnableMonitoringonSkypePresenceServerforbetterreliability NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Enable Monitoring on Skype Presence Server for better reliability."
    ::= { enterprises 177 15 2 589879 }

uxAlmMonitoringonSkypePresenceServerhasbeenenabled NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Monitoring on Skype Presence Server has been enabled."
    ::= { enterprises 177 15 2 589880 }

uxAlmTheSIPVoiceQualityServerConnectionisBroken NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Suggested Action: Verifying the IP, Port, Protocol, and Certificate (if TLS) are Correct."
    ::= { enterprises 177 15 2 589881 }

uxAlmTheSIPVoiceQualityServerConnectionisResumed NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "The SIP Voice Quality Server Connection is Resumed."
    ::= { enterprises 177 15 2 589882 }

uxAlmTheVoiceQualityNotifyRejectedbytheSIPVoiceQualityServer NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Suggested Action: Examining the Notify Response Code and the Reason Header (if Included) to Understand Why it was Rejected."
    ::= { enterprises 177 15 2 589883 }

uxAlmTheVoiceQualityNotifyAcceptbyTheSIPVoiceQualityServer NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "The Voice Quality Notify has been Accept by The SIP Voice Quality Server."
    ::= { enterprises 177 15 2 589884 }

uxAlmFailedtoResolvetheFQDNoftheSIPVoiceQualityServer NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Failed to Resolve FQDN of the SIP Voice Quality Server. Suggested action - confirm the DNS access and FQDN."
    ::= { enterprises 177 15 2 589885 }

uxAlmtheSIPVoiceQualityServerFQDNhasbeenResolved NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "the SIP Voice Quality Server FQDN has been Resolved."
    ::= { enterprises 177 15 2 589886 }

uxAlmConfiguredRegistrationLimitreached NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Configured Registration Limit reached. New SIP Registrations will be rejected until the number of registered users drops below maximum number of users configured for the Registrar."
    ::= { enterprises 177 15 2 589887 }

uxAlmConfiguredRegistrationLimitCleared NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Configured Registration Limit Cleared."
    ::= { enterprises 177 15 2 589888 }

uxAlmDChanneldown NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "The D-channel(layer 2) is out of service."
    ::= { enterprises 177 15 2 655361 }

uxAlmDChannelup NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "The D-channel(layer 2) is in service. "
    ::= { enterprises 177 15 2 655362 }

uxAlmCallreleasedduetochannelrestartbyfarend NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Call released as the ISDN channel has been restarted by far end."
    ::= { enterprises 177 15 2 655363 }

uxAlmPortdisabledbyoperator NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Port is placed Out of Service by operator."
    ::= { enterprises 177 15 2 720897 }

uxAlmPortenabledbyoperator NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Port is placed back in Service by operator."
    ::= { enterprises 177 15 2 720898 }

uxAlmDS1LoopbackEnter NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "The physical layer is in loopback state."
    ::= { enterprises 177 15 2 720899 }

uxAlmDS1LoopbackExit NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "The physical layer is out of loopback state."
    ::= { enterprises 177 15 2 720900 }

uxAlmRedAlarmLossofSignal NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "The physical layer has detected a RED (LOS) alarm."
    ::= { enterprises 177 15 2 720901 }

uxAlmRedAlarmLossofSignalcleared NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "The physical layer RED alarm (LOS) is cleared."
    ::= { enterprises 177 15 2 720902 }

uxAlmRedAlarmLossofFrame NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "The physical layer has detected a Red (LOF) alarm."
    ::= { enterprises 177 15 2 720903 }

uxAlmRedAlarmLossofFramecleared NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "The physical layer RED alarm (LOF) is cleared."
    ::= { enterprises 177 15 2 720904 }

uxAlmBlueAlarm NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "The physical layer has detected a BLUE alarm."
    ::= { enterprises 177 15 2 720905 }

uxAlmBlueAlarmCleared NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "The physical layer BLUE alarm is cleared."
    ::= { enterprises 177 15 2 720906 }

uxAlmYellowAlarm NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "The physical layer has detected a YELLOW alarm"
    ::= { enterprises 177 15 2 720907 }

uxAlmYellowAlarmCleared NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "The physical layer YELLOW alarm is cleared."
    ::= { enterprises 177 15 2 720908 }

uxAlmPortdisabledasportnotfoundonDS1 NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Port is now marked as disabled because the corresponding port was not present on the DS1 physical hardware."
    ::= { enterprises 177 15 2 720909 }

uxAlmClockrecoveryswitchedtoportconfiguredassecondary NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "System has switched over to secondary clock recovery port as primary is lost."
    ::= { enterprises 177 15 2 720910 }

uxAlmClockrecoveryswitchovertosecondaryportcleared NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Secondary clock recovery alarm is being cleared as primary clock is recovered."
    ::= { enterprises 177 15 2 720911 }

uxAlmClockrecoveryswitchedtofreerunclock NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "System has switched over to QF free-run clock as both primary/secondary recovery clocks are invalid."
    ::= { enterprises 177 15 2 720912 }

uxAlmClockrecoveryswitchovertofreerunclockcleared NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Free-run clock recovery alarm is being cleared as primary clock is recovered."
    ::= { enterprises 177 15 2 720913 }

uxAlmLinecardnotdetected NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Line card not detected."
    ::= { enterprises 177 15 2 720914 }

uxAlmLinecarddetected NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Line card is detected."
    ::= { enterprises 177 15 2 720915 }

uxAlmPortdisabledforrelaypassthroughstateactivation NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Port is now marked as disabled for activated relay passthrough state."
    ::= { enterprises 177 15 2 720916 }

uxAlmPortenabledforrelayonlinestateactivation NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Port is now marked as enabled for activated relay online state."
    ::= { enterprises 177 15 2 720917 }

uxAlmLayer1down NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "The physical layer has detected layer 1 down due to state conditions that results in nonoperational state of the BRI port."
    ::= { enterprises 177 15 2 720918 }

uxAlmLayer1up NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "The physical layer 1 down alarm is cleared with operational state of the BRI port."
    ::= { enterprises 177 15 2 720919 }

uxAlmPortdisabledasportnotfoundonanalogcard NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Port is now marked as disabled because the corresponding port was not present on the analog physical hardware."
    ::= { enterprises 177 15 2 720920 }

uxAlmPortsdisabledforrelaypassthrustatechgonanalogrelaycards NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Ports are now marked as disabled for activated relay passthrough state on analog FXS/FXO card pair."
    ::= { enterprises 177 15 2 720921 }

uxAlmPortsenabledforrelayonlinestatechangeonanalogrelaycardpairs NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Ports are now marked as enabled for activated relay passthrough state on analog FXS/FXO card pair."
    ::= { enterprises 177 15 2 720922 }

uxAlmPortstatusdowndetected NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Line down condition detected due to no battery."
    ::= { enterprises 177 15 2 720923 }

uxAlmPortstatusup NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Line down condition is cleared."
    ::= { enterprises 177 15 2 720924 }

uxAlmPortdisabledasportnotfoundonBRI NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Port is now marked as disabled because the corresponding port was not present on the BRI physical hardware."
    ::= { enterprises 177 15 2 720925 }

uxAlmSystemnotoperational NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "System not operational because DSP cannot be initialized. Contact Ribbon Service with the information in this alarm."
    ::= { enterprises 177 15 2 720926 }

uxAlmDS1syncfailure NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "DS1 sync failure could be due to mismatching line configuration. Suggested Action: Disable 'Admin State' of unused ports to avoid performance impact."
    ::= { enterprises 177 15 2 720927 }

uxAlmDS1syncfailurecleared NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "DS1 sync failure cleared."
    ::= { enterprises 177 15 2 720928 }

uxAlmDSPnotcomingup NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "DSP board 'board type' could not be brought up. If the DSP does not come up, contact Ribbon Service with the information in this alarm."
    ::= { enterprises 177 15 2 786433 }

uxAlmDSPreset NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "This alarm will be generated if a DSP encounters a fatal error condition and has to be reinitialized."
    ::= { enterprises 177 15 2 786434 }

uxAlmDSPCardisUP NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "This event will clear the 'DSP not coming up' and 'DSP reset' alarms."
    ::= { enterprises 177 15 2 786435 }

uxAlmDSPeventfailure NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Call related command on Connection ID 'value' failed wtih error code 'value'."
    ::= { enterprises 177 15 2 786436 }

uxAlmRTPRTCPPortRangeInvalid NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "This alarm is generated if a RTP/RTCP port range is found to be invalid. This condition should be resolved by reconfiguring the RTP/RTCP Port Range under Media System Configuration."
    ::= { enterprises 177 15 2 786437 }

uxAlmRTPRTCPPortRangeInvalidCleared NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "This event will clear the 'RTP/RTCP Port Range Invalid' alarm."
    ::= { enterprises 177 15 2 786438 }

uxAlmMSCMediaStreamModeMismatch NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "This alarm is generated when there is a mismatch in media stream mode of the two call legs. Suggested Action: Match 'Audio/Fax Stream Mode' settings and clear alarm."
    ::= { enterprises 177 15 2 786439 }

uxAlmMusicOnHoldfailedduetoimproperlyconfiguredsource NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Music-On-Hold enabled; source is not properly configured. If source is set to File: upload a file, disable music on hold or switch source to an FXS port"
    ::= { enterprises 177 15 2 786440 }

uxAlmFailedtoAllocateRTPports NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "This alarm is generated if we exceed the configured number of RTP/RTCP port pairs. This condition should be resolved by increasing the 'Number of Port Pairs' in Media System Configuration."
    ::= { enterprises 177 15 2 786441 }

uxAlmVirtDSPeventfailure NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Virt DSP Command Failure: Conf='conf' Type='type' Error='error'"
    ::= { enterprises 177 15 2 786442 }

uxAlmMSCDTLSServerHandshakeFailure NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "DTLS server handshake failed with alert code. Action: Refer to Error Alerts in RFC 5246 for the problem."
    ::= { enterprises 177 15 2 786443 }

uxAlmMSCDTLSServerHandshakeFailureCleared NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Handshake failure error alert condition was cleared. This event clears the 'MSC-DTLS Server Handshake Failure' alarm. "
    ::= { enterprises 177 15 2 786444 }

uxAlmMSCDTLSHandshakeInactivityTimeoutFailure NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "DTLS handshake failed due to no response from peer within specified timeout. Action: Increase the Handshake Inactivity Timeout in DTLS Profile."
    ::= { enterprises 177 15 2 786445 }

uxAlmMSCDTLSHandshakeInactivityTimeoutCleared NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Handshake response was received within specified timeout. This event clears the 'MSC-DTLS Handshake Inactivity Timeout Failure' alarm. "
    ::= { enterprises 177 15 2 786446 }

uxAlmMSCDTLSHandshakeNegotiationStartFailure NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "'server' handshake failed to start with invalid certificate; 'connection ID', 'port ID'. Action: confirm that both signed Ribbon SBC Edge Certificate and Trusted CA Certificate exist."
    ::= { enterprises 177 15 2 786447 }

uxAlmMSCDTLSHandshakeNegotiationStartSuccessful NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "DTLS Handshake response was started with valid certificate on local and remote gateway. This event clears the 'MSC-DTLS Handshake Negotiation Start Failure' alarm. "
    ::= { enterprises 177 15 2 786448 }

uxAlmMSCDTLSClientHandshakeFailure NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "DTLS client handshake failed with alert code. Action: Refer to Error Alerts in RFC 5246 for the problem."
    ::= { enterprises 177 15 2 786449 }

uxAlmMSCDTLSClientHandshakeFailureCleared NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Handshake failure error alert condition was cleared. This event clears the 'MSC-DTLS Client Handshake Failure' alarm. "
    ::= { enterprises 177 15 2 786450 }

uxAlmTLSOwnServerCertificatewillExpire NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "CommonName: 'name' StartDate: 'startdate' EndDate: 'enddata' will expire in a window time. Action: Generate, Export CSR and Import a new signed certificate."
    ::= { enterprises 177 15 2 851969 }

uxAlmTLSOwnServerCertificatehasExpired NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "CommonName: 'name' StartDate: 'startdate' EndDate: 'enddata' has expired. Action: Generate, Export CSR and Import a new signed certificate."
    ::= { enterprises 177 15 2 851970 }

uxAlmTLSOwnServerCertificateismissing NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "This Server certificate is found to be missing or has failed validations. Suggested Action. Generate, Export CSR and Import a new signed certificate."
    ::= { enterprises 177 15 2 851971 }

uxAlmTLSSelfSignCertificateGenerationFailed NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Failed to create a default self signed certificate on the system."
    ::= { enterprises 177 15 2 851972 }

uxAlmNewandValidTLSOwnServerCertificateDetected NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Imported and validated common name: 'name' StartDate: 'start date' EndDate: 'end date'. This event clears the Server Certificate Expiring, Expired and Missing alarms."
    ::= { enterprises 177 15 2 851973 }

uxAlmTLSTrustedCertificateAuthoritywillExpire NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "CommonName: 'name' StartDate: 'start date' EndDate: 'end date' will expire in a window time. Action: Obtain and Import a new valid certificate from the CA vendor."
    ::= { enterprises 177 15 2 851974 }

uxAlmTLSTrustedCertificateAuthorityhasExpired NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "'CommonName: 'name' StartDate: 'start date' EndDate: 'end date' has expired. Action: Obtain and Import a new valid certificate from the CA vendor."
    ::= { enterprises 177 15 2 851975 }

uxAlmTLSTrustedCertificateAuthoritywasDeleted NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "The Trusted Certificate Authority is successfully deleted due to the expired or expiring soon validity status."
    ::= { enterprises 177 15 2 851976 }

uxAlmTLSOwnServerCertificateExpiryNotice NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "CommonName: 'name' StartDate: 'start date' EndDate: 'end date' will expire in a window time. Action: Obtain and Import a new valid certificate from the CA vendor."
    ::= { enterprises 177 15 2 851977 }

uxAlmTLSTrustedCertificateAuthorityExpiryNotice NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "CommonName: 'name' StartDate: 'start date' EndDate: 'end date' has expired. Action: Obtain and Import a new valid certificate from the CA vendor."
    ::= { enterprises 177 15 2 851978 }

uxAlmInvalidSessionforattemptedrealtimeconnection NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "If a web-client tries to open a realtime monitor connection with invalid session ID, BMP will generate this alarm."
    ::= { enterprises 177 15 2 917505 }

uxAlmBMPTLSHandshakeAlertFailure NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "This alarm will be generated if TLS Connection failed with an Alert. The connection associated with a TLS Connection ID is aborted."
    ::= { enterprises 177 15 2 917506 }

uxAlmBMPTLSHandshakeInactivityTimeoutFailure NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "This alarm will be generated if there was long period of inactivity during exchange of handshake messages for an associated TLS Connection ID."
    ::= { enterprises 177 15 2 917507 }

uxAlmInterfaceoperdown NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Occurs when an Ethernet port (of ports 1, 2, 3 and 4) is operationally down (e.g. cable unplugged, mismatched speed/duplexity settings) and if administrative state is enabled. Is generated only on the SBC 2000."
    ::= { enterprises 177 15 2 983041 }

uxAlmInterfaceoperup NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Is generated when an Ethernet port (of ports 1, 2, 3 and 4) becomes operationally up. This event automatically clears the 'Interface oper down' alarm."
    ::= { enterprises 177 15 2 983042 }

uxAlmInterfaceadminup NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Is generated when the administrative state of the Logical Interface is configured to be enabled. Is applicable to SBC 2000 and SWe Lite platforms only."
    ::= { enterprises 177 15 2 983043 }

uxAlmInterfaceadmindown NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Is generated when the administrative state of the Logical Interface is configured to be disabled. Is applicable to SBC 2000 and SWe Lite platforms only. "
    ::= { enterprises 177 15 2 983044 }

uxAlmAdminPortoperdown NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Is generated when the Admin Port is operationally down (e.g. cable unplugged, mismatched duplex/speed settings). Is applicable to the SBC 2000 only."
    ::= { enterprises 177 15 2 983045 }

uxAlmAdminPortoperup NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Is generated with the port becomes operational after being in an *Admin port oper down* state. Is applicable to the SBC 2000 only"
    ::= { enterprises 177 15 2 983046 }

uxAlmPortoperdown NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "This event is generated when the port is operationally down. It is generated for the SBC 1000 only."
    ::= { enterprises 177 15 2 983047 }

uxAlmRIPlicensenotenabled NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            " RIP feature license is not enabled."
    ::= { enterprises 177 15 2 983048 }

uxAlmOSPFlicensenotenabled NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            " OSPF feature license is not enabled."
    ::= { enterprises 177 15 2 983049 }

uxAlmLinkMonitorPeerDown NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Connection to the monitored host or gateway is down."
    ::= { enterprises 177 15 2 983050 }

uxAlmLinkMonitorPeerReady NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Connection to the monitored host or gateway is established."
    ::= { enterprises 177 15 2 983051 }

uxAlmTunnelconnectiondisabledbyoperator NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Tunnel connection is placed Out of Service by operator."
    ::= { enterprises 177 15 2 983052 }

uxAlmTunnelconnectionenabledbyoperator NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Tunnel connection is placed back in Service by operator."
    ::= { enterprises 177 15 2 983053 }

uxAlmTunnellinklost NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Tunnel lost communication with the peer. This alarm will be cleared by event 'Tunnel link restored'."
    ::= { enterprises 177 15 2 983054 }

uxAlmTunnellinkrestored NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Tunnel is successfully established with the peer"
    ::= { enterprises 177 15 2 983055 }

uxAlmIPseclicensenotenabled NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "IPsec feature license is not enabled."
    ::= { enterprises 177 15 2 983056 }

uxAlmNegotiatedDuplexityHalf NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Port negotiated duplexity is half. This degrades the performance."
    ::= { enterprises 177 15 2 983057 }

uxAlmNegotiatedDuplexityFull NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Port negotiated duplexity is back to full."
    ::= { enterprises 177 15 2 983058 }

uxAlmPreferredlinkdown NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "This event is generated when the preferred link is down."
    ::= { enterprises 177 15 2 983059 }

uxAlmPreferredlinkready NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "This event is generated when the the preferred link is ready for service. This event automatically clears the 'preferred Link down' alarm."
    ::= { enterprises 177 15 2 983060 }

uxAlmTunnelnotificationfailure NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Tunnel negotiation failed. Suggested Action: Look up the 'Failure Reason' attribute details for the Source in the IPsec Tunnel Table."
    ::= { enterprises 177 15 2 983061 }

uxAlmTunnellocalsubnetsarenonnegotiable NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Local subnets 'subnets' failed negotiation as a result of peer config mismatch."
    ::= { enterprises 177 15 2 983062 }

uxAlmTunnelremotesubnetsarenonnegotiable NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Remote subnets 'subnets' failed negotiation as a result of peer config mismatch."
    ::= { enterprises 177 15 2 983063 }

uxAlmPortStateLearning NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "MSTP port is in learning state."
    ::= { enterprises 177 15 2 983064 }

uxAlmPortStateForwarding NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "MSTP port is in forwarding state."
    ::= { enterprises 177 15 2 983065 }

uxAlmPortStateDiscarding NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "MSTP port is in discarding state."
    ::= { enterprises 177 15 2 983066 }

uxAlmPacketCaptureStarted NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Packet capture has started."
    ::= { enterprises 177 15 2 983067 }

uxAlmPacketCaptureStopped NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Packet capture has stopped due to 'reason'."
    ::= { enterprises 177 15 2 983068 }

uxAlmDuplicateIPv6addressdetected NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "The indicated IPv6 address has been detected as a duplicate address."
    ::= { enterprises 177 15 2 983069 }

uxAlmIPaddressconfigured NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "This event is generated when an IP address is configured on the node."
    ::= { enterprises 177 15 2 983070 }

uxAlmIPaddressremoved NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "This event is generated when an IP address is removed from the node."
    ::= { enterprises 177 15 2 983071 }

uxAlmLinkfailoverdetected NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Link failover detected, the indicated Ethernet port became active."
    ::= { enterprises 177 15 2 983072 }

uxAlmMACaddresseshavechanged NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Some MAC addresses have changed since the last time the system was up. It is recommended to log into console as 'netconfig' user and remap the interfaces as desired."
    ::= { enterprises 177 15 2 983073 }

uxAlmDomainNameEmpty NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Domain Name for Split DNS should not be empty."
    ::= { enterprises 177 15 2 983074 }

uxAlmApplicationServicerestarted NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "An SBC Edge Application service was restarted. Contact Ribbon Service with the information in this alarm and any core files present. These can be found in Diagnostics->Restart Report under the 'Core Files' tab."
    ::= { enterprises 177 15 2 1048577 }

uxAlmActivepartitionswitched NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "System detected a problem during previous boot cycle, active partition has switched automatically. Suggested action - backup the configuration and re-apply the upgrade to the currently inactive partition."
    ::= { enterprises 177 15 2 1048578 }

uxAlmFailedtomountpartition NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Mounting failed for partition 'number'."
    ::= { enterprises 177 15 2 1048579 }

uxAlmFailedtosetactivepartition NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Failed to set active partition. Contact Ribbon Service with the information in this alarm."
    ::= { enterprises 177 15 2 1048580 }

uxAlmAttempttorepairbootparametermismatchfailed NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Attempt to auto repair boot parmeters failed. Contact Ribbon Service with the information in this alarm."
    ::= { enterprises 177 15 2 1048581 }

uxAlmBootparametermismatchdetected NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Boot parameter mismatch was detected.Attempting to auto repair."
    ::= { enterprises 177 15 2 1048582 }

uxAlmFailedPoweronmemoryselftest NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Power-on self test failure."
    ::= { enterprises 177 15 2 1048583 }

uxAlmFailedPoweronCoreSwitchtest NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Power-on self test failure."
    ::= { enterprises 177 15 2 1048584 }

uxAlmFailedPoweronSecondarySwitchtest NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Power-on self test failure."
    ::= { enterprises 177 15 2 1048585 }

uxAlmFailedPoweronexternalQuadPHYtest NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Power-on self test failure."
    ::= { enterprises 177 15 2 1048586 }

uxAlmFailedPoweronexternalSinglePHYtest NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Power-on self test failure."
    ::= { enterprises 177 15 2 1048587 }

uxAlmFailedPoweronCPUPHYtest NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Power-on self test failure."
    ::= { enterprises 177 15 2 1048588 }

uxAlmFailedPoweronTSItest NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Power-on self test failure."
    ::= { enterprises 177 15 2 1048589 }

uxAlmFailedPoweroninternal5PortPHYtest NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Power-on self test failure."
    ::= { enterprises 177 15 2 1048590 }

uxAlmSystemUpAfterPlannedRestart NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "System up after planned restart."
    ::= { enterprises 177 15 2 1048591 }

uxAlmSystemUpAfterUnplannedRestart NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "System up after unplanned restart."
    ::= { enterprises 177 15 2 1048592 }

uxAlmEnteredpasswordrecoverymode NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "SBC has entered password recovery mode."
    ::= { enterprises 177 15 2 1048593 }

uxAlmExitedpasswordrecoverymode NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "SBC has exited password recovery mode."
    ::= { enterprises 177 15 2 1048594 }

uxAlmFailedtomountUSBstoragedevice NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "SBC discovered USB storage. SBC can mount flash drives formatted with FAT32 file system only."
    ::= { enterprises 177 15 2 1048595 }

uxAlmUSBstoragedeviceconnected NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "USB storge device is connected."
    ::= { enterprises 177 15 2 1048596 }

uxAlmUSBstoragedevicedisconnected NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "USB storge device is disconnected. This alarm will be cleared when USB drive is connected."
    ::= { enterprises 177 15 2 1048597 }

uxAlmCriticalapplicationcrash NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "A critical SBC Edge application has crashed, and the system will be restarted. Contact Ribbon Service with the information in this alarm and any core files present. These can be found in Diagnostics->Restart Report under the 'Core Files' tab."
    ::= { enterprises 177 15 2 1048598 }

uxAlmOlderfirmwaredetected NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "A USB firmware update is available. To perform upgrade, please first load SW release v4.1.1"
    ::= { enterprises 177 15 2 1048599 }

uxAlmAutoConfigurationsuccessful NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Auto Configuration successful after receiving SIP NOTIFY message."
    ::= { enterprises 177 15 2 1048600 }

uxAlmAutoConfigurationfailed NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Failed to perform Auto Configuration after receiving SIP NOTIFY message."
    ::= { enterprises 177 15 2 1048601 }

uxAlmSoftwareUpdateinprogress NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Current SIP NOTIFY message cannot be processed as software update is in progress"
    ::= { enterprises 177 15 2 1048602 }

uxAlmNodeReboot NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Node Reboot requested by user 'Username' from 'IP address'."
    ::= { enterprises 177 15 2 1048603 }

uxAlmFactoryDefault NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Full factory default requested by user 'Username' from 'IP address'."
    ::= { enterprises 177 15 2 1048604 }

uxAlmInvalidSystemMemory NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Unexpected memory size for virtual CPU detected. Please consult documentation for memory requirement."
    ::= { enterprises 177 15 2 1048605 }

uxAlmResetButtonFactoryDefault NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Full factory default requested via hardware reset button."
    ::= { enterprises 177 15 2 1048606 }

uxAlmNoresponse NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "No response to seizure."
    ::= { enterprises 177 15 2 1114113 }

uxAlmRemoteenddidnotbackoffinglare NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Remote end did not back off in glare."
    ::= { enterprises 177 15 2 1114114 }

uxAlmWinkexpecteddidnotarrive NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Wink expected, did not arrive."
    ::= { enterprises 177 15 2 1114115 }

uxAlmNodialtone NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Event of off-hook did not produce dial tone as expected."
    ::= { enterprises 177 15 2 1114116 }

uxAlmCASsignalinggroupdisabled NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "CAS signaling group is disabled."
    ::= { enterprises 177 15 2 1114117 }

uxAlmCASlicensenotenabled NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Call attempted but CAS feature is not enabled. This alarm is cleared by CAS license enabled event."
    ::= { enterprises 177 15 2 1114118 }

uxAlmCASlicenseenabled NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "License manager notify CAS that license is enabled."
    ::= { enterprises 177 15 2 1114119 }

uxAlmWinkReceived NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Wink failure had occurred, but wink is received now."
    ::= { enterprises 177 15 2 1114120 }

uxAlmDialToneReceived NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "No Dial Tone was received, but Dial Tone is received now."
    ::= { enterprises 177 15 2 1114121 }

uxAlmResponseReceived NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "No Response to seizure was received, but Response is received now."
    ::= { enterprises 177 15 2 1114122 }

uxAlmInvalidcharactersincallingnumber NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Invalid character(s) removed, correct issue and delete warning."
    ::= { enterprises 177 15 2 1114123 }

uxAlmInvalidcharactersincallednumber NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Invalid character(s) removed, correct issue and delete warning."
    ::= { enterprises 177 15 2 1114124 }

uxAlmCASsignalinggroupenabled NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "CAS signaling group enabled."
    ::= { enterprises 177 15 2 1114125 }

uxAlmCASR2CDBiterror NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "CAS-R2 CD-Bits are mismatched on the span, this alarm is cleared when all channels match."
    ::= { enterprises 177 15 2 1114126 }

uxAlmCASR2CDBiterrorclear NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "CAS-R2 CD-Bits now match on this span for all channels."
    ::= { enterprises 177 15 2 1114127 }

uxAlmNetworkGlareoccured NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Network glare occured on this interface."
    ::= { enterprises 177 15 2 1114128 }

uxAlmConfigvalidationfailure NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Config validation failure during startup. Please check the configuration."
    ::= { enterprises 177 15 2 1179649 }

uxAlmNewerConfigLoaded NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Configuration loaded from newer release than currently running release."
    ::= { enterprises 177 15 2 1179650 }

uxAlmPassworddecryptionfailed NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Password decryption failed on configuration import operation."
    ::= { enterprises 177 15 2 1179651 }

uxAlmPartialFactoryDefault NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Partial 'factory default or configuration import' requested by 'Username' from 'IP address'."
    ::= { enterprises 177 15 2 1179652 }

uxAlmConfigurationRestore NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Configuration restore requested by 'Username' from 'IP address'."
    ::= { enterprises 177 15 2 1179653 }

uxAlmSGChannelUsageexceededTCAthreshold NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Signaling Group channel usage exceeded configured TCA threshold."
    ::= { enterprises 177 15 2 1245185 }

uxAlmSGChannelUsagebelowTCAthreshold NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Signaling Group channel usage fell below configured TCA threshold."
    ::= { enterprises 177 15 2 1245186 }

uxAlmSIPCallLicenseUsageexceededTCAthreshold NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "SIP Call license usage exceeded configured TCA threshold."
    ::= { enterprises 177 15 2 1245187 }

uxAlmSIPCallLicenseUsagebelowTCAthreshold NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "SIP Call license usage fell below configured TCA threshold."
    ::= { enterprises 177 15 2 1245188 }

uxAlmSIPRegistrationUsageexceededTCAthreshold NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "SIP Registration usage exceeded configured TCA threshold."
    ::= { enterprises 177 15 2 1245189 }

uxAlmSIPRegistrationUsagebelowTCAthreshold NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "SIP Registration usage fell below configured TCA threshold."
    ::= { enterprises 177 15 2 1245190 }

uxAlmDSPUsageexceededTCAthreshold NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "DSP usage exceeded configured TCA threshold."
    ::= { enterprises 177 15 2 1245191 }

uxAlmDSPUsagebelowTCAthreshold NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "DSP usage fell below configured TCA threshold."
    ::= { enterprises 177 15 2 1245192 }

uxAlmCPUUsageexceededTCAthreshold NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "CPU usage exceeded configured TCA threshold."
    ::= { enterprises 177 15 2 1245193 }

uxAlmCPUUsagebelowTCAthreshold NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "CPU usage fell below configured TCA threshold."
    ::= { enterprises 177 15 2 1245194 }

uxAlmMemoryUsageexceededTCAthreshold NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Memory usage exceeded configured TCA threshold."
    ::= { enterprises 177 15 2 1245195 }

uxAlmMemoryUsagebelowTCAthreshold NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Memory usage fell below configured TCA threshold."
    ::= { enterprises 177 15 2 1245196 }

uxAlmFileDescriptorUsageexceededTCAthreshold NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "File Descriptor Usage exceeded TCA threshold."
    ::= { enterprises 177 15 2 1245197 }

uxAlmFileDescriptorUsagebelowTCAthreshold NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "File Descriptor Usage fell below TCA threshold."
    ::= { enterprises 177 15 2 1245198 }

uxAlmCPUloadaverageinpast1minuteexceededTCAthreshold NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "CPU load average in past 1 minute exceeded TCA threshold."
    ::= { enterprises 177 15 2 1245199 }

uxAlmCPUloadaverageinpast1minutefellbelowTCAthreshold NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "CPU load average in past 1 minute fell below TCA threshold."
    ::= { enterprises 177 15 2 1245200 }

uxAlmCPUloadaverageinpast5minutesexceededTCAthreshold NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "CPU load average in past 5 minutes exceeded TCA threshold."
    ::= { enterprises 177 15 2 1245201 }

uxAlmCPUloadaverageinpast5minutesfellbelowTCAthreshold NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "CPU load average in past 5 minutes fell below TCA threshold."
    ::= { enterprises 177 15 2 1245202 }

uxAlmCPUloadaverageinpast15minutesexceededTCAthreshold NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "CPU load average in past 15 minutes exceeded TCA threshold."
    ::= { enterprises 177 15 2 1245203 }

uxAlmCPUloadaverageinpast15minutesfellbelowTCAthreshold NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "CPU load average in past 15 minutes fell below TCA threshold."
    ::= { enterprises 177 15 2 1245204 }

uxAlmTemporarypartitionusageexceededTCAthreshold NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Temporary partition usage exceeded TCA threshold."
    ::= { enterprises 177 15 2 1245205 }

uxAlmTemporarypartitionusagefellbelowTCAthreshold NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Temporary partition usage fell below TCA threshold."
    ::= { enterprises 177 15 2 1245206 }

uxAlmLoggingpartitionusageexceededTCAthreshold NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Logging partition usage exceeded TCA threshold."
    ::= { enterprises 177 15 2 1245207 }

uxAlmLoggingpartitionusagefellbelowTCAthreshold NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "Logging partition usage fell below TCA threshold."
    ::= { enterprises 177 15 2 1245208 }

uxAlmFailedtoresolveFQDN NOTIFICATION-TYPE
    OBJECTS         { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
    STATUS          current
    DESCRIPTION     
            "Failed to resolve IP address. Ensure that FQDN and DNS server is configured properly."
    ::= { enterprises 177 15 2 1310721 }

uxAlmFQDNresolved NOTIFICATION-TYPE
    OBJECTS         { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
    STATUS          current
    DESCRIPTION     
            "IP address successfully resolved."
    ::= { enterprises 177 15 2 1310722 }

END -- end of module UX-TRAP-MIB.
