--
-- This SMIv1 module has been generated by smidump 0.2-cvs. Do not edit.
--

SONUS-CAS-MIB DEFINITIONS ::= BEGIN

IMPORTS
    OBJECT-TYPE
        FROM RFC-1212
    TRAP-TYPE
        FROM RFC-1215
    RowStatus
        FROM SNMPv2-TC
    sonusEventClass, sonusEventDescription, sonusEventLevel, 
    sonusEventTime, sonusSequenceId
        FROM SONUS-COMMON-MIB
    sonusSignallingMIBs
        FROM SONUS-SMI
    SonusAdminAction, SonusAdminState, SonusName, SonusNameReference, 
    SonusServiceState, SonusShelfIndex, SonusSlotIndex
        FROM SONUS-TC;

sonusCasMIB OBJECT IDENTIFIER
    ::= { sonusSignallingMIBs 5 }

-- sonusCasMIB MODULE-IDENTITY
--     LAST-UPDATED    "201007260000Z"
--     ORGANIZATION    
--             "Sonus Networks, Inc."
--     CONTACT-INFO    
--             "   Customer Support    
--              Sonus Networks, Inc.
--              7 Technology Park Drive
--              Westford, MA 01886
--              USA
--              
--              Tel: 978-614-8100
--              Fax: 978-614-8609"
--     DESCRIPTION     
--             "The MIB Module for CAS Service Group Management."
--     ::= { sonusSignallingMIBs 5 }


sonusCasMIBObjects OBJECT IDENTIFIER
    ::= { sonusCasMIB 1 }

sonusCasServiceGroup OBJECT IDENTIFIER
    ::= { sonusCasMIBObjects 1 }

sonusCasServiceGroupNextIndex OBJECT-TYPE
    SYNTAX          INTEGER
    ACCESS          read-only
    STATUS          mandatory
    DESCRIPTION     
            "The next valid index to use when creating a new sonusCasServiceGroupAdmnEntry"
    ::= { sonusCasServiceGroup 1 }

sonusCasServiceGroupAdmnTable OBJECT-TYPE
    SYNTAX          SEQUENCE OF SonusCasServiceGroupAdmnEntry
    ACCESS          not-accessible
    STATUS          mandatory
    DESCRIPTION     
            ""
    ::= { sonusCasServiceGroup 2 }

sonusCasServiceGroupAdmnEntry OBJECT-TYPE
    SYNTAX          SonusCasServiceGroupAdmnEntry
    ACCESS          not-accessible
    STATUS          mandatory
    DESCRIPTION     
            ""
    INDEX           { sonusCassgServiceGroupIndex }
    ::= { sonusCasServiceGroupAdmnTable 1 }

SonusCasServiceGroupAdmnEntry ::=
    SEQUENCE {
        sonusCassgServiceGroupIndex     INTEGER,
        sonusCassgServiceGroupName      SonusName,
        sonusCassgServiceGroupProfileName SonusNameReference,
        sonusCassgServiceGroupTG        SonusNameReference,
        sonusCassgServiceGroupHuntAlgorithm   INTEGER,
        sonusCassgServiceGroupCost      INTEGER,
        sonusCassgServiceGroupSignalType INTEGER,
        sonusCassgServiceGroupIngressSSP SonusNameReference,
        sonusCassgServiceGroupEgressSSP SonusNameReference,
        sonusCassgServiceGroupHookflashSSP  SonusNameReference,
        sonusCassgServiceGroupPscSSP    SonusNameReference,
        sonusCassgServiceGroupMaintBusy SonusAdminState,
        sonusCassgServiceGroupAutoBusyThreshold       INTEGER,
        sonusCassgServiceGroupRequiresCPTone    SonusAdminState,
        sonusCassgServiceGroupProvidesCPTone    SonusAdminState,
        sonusCassgServiceGroupDTMFProfileName     SonusNameReference,
        sonusCassgServiceGroupMFProfileName   SonusNameReference,
        sonusCassgServiceGroupCPTonePkgName   SonusNameReference,
        sonusCassgServiceGroupMinRxWinkTime   INTEGER,
        sonusCassgServiceGroupMaxRxWinkTime   INTEGER,
        sonusCassgServiceGroupMinRxFlashTime    INTEGER,
        sonusCassgServiceGroupMaxRxFlashTime    INTEGER,
        sonusCassgServiceGroupTxWinkTime INTEGER,
        sonusCassgServiceGroupTxFlashTime INTEGER,
        sonusCassgServiceGroupGuardTime INTEGER,
        sonusCassgServiceGroupOperation INTEGER,
        sonusCassgServiceGroupAdminState SonusAdminState,
        sonusCassgServiceGroupMode      SonusServiceState,
        sonusCassgServiceGroupAction    SonusAdminAction,
        sonusCassgServiceGroupTimeout   INTEGER,
        sonusCassgServiceGroupAlertToneName   SonusNameReference,
        sonusCassgServiceGroupRowStatus RowStatus,
        sonusCassgServiceGroupDTProfileName   SonusNameReference,
        sonusCassgServiceGroupSuspendTime INTEGER,
        sonusCassgServiceGroupSwitchSide INTEGER,
        sonusCassgServiceGroupSigVariant INTEGER,
        sonusCassgServiceGroupBNUMEndDigit  SonusAdminState,
        sonusCassgServiceGroupMFCR2ProfileName      SonusNameReference,
        sonusCassgServiceGroupRxClrToIdleTime     INTEGER,
        sonusCassgServiceGroupE1Cbit    INTEGER,
        sonusCassgServiceGroupE1Dbit    INTEGER,
        sonusCassgServiceGroupMGCPackage INTEGER,
        sonusCassgServiceGroupLsGsAnswerSupv    SonusAdminState,
        sonusCassgServiceGroupRxSeizeRingTime     INTEGER,
        sonusCassgServiceGroupRxFxsAnswerTime     INTEGER,
        sonusCassgServiceGroupRxFxsDiscTime   INTEGER,
        sonusCassgServiceGroupRxLsFxsRingCess     INTEGER,
        sonusCassgServiceGroupTxLsFxoDiscTime     INTEGER,
        sonusCassgServiceGroupTxFxoRingOnTime     INTEGER,
        sonusCassgServiceGroupTxFxoRingOffTime      INTEGER,
        sonusCassgServiceGroupAnsSupervisionTimeout           INTEGER,
        sonusCassgServiceGroupCrankBackProfile      INTEGER,
        sonusCassgServiceGroupANUMLength INTEGER,
        sonusCassgServiceGroupTxR2EndDigit  INTEGER,
        sonusCassgServiceGroupRxR2SeizeTime   INTEGER,
        sonusCassgServiceGroupRxR2SeizeAckTime      INTEGER,
        sonusCassgServiceGroupRxR2AnswerTime    INTEGER,
        sonusCassgServiceGroupRxR2ClearBackTime       INTEGER,
        sonusCassgServiceGroupRxR2ClearFwdTime      INTEGER,
        sonusCassgServiceGroupRxR2IdleBackTime      INTEGER,
        sonusCassgServiceGroupRxR2BlockTime   INTEGER,
        sonusCassgServiceGroupCongRelTimeout    INTEGER,
        sonusCassgServiceGroupLdcTimeout INTEGER,
        sonusCassgServiceGroupLdcAction INTEGER,
        sonusCassgServiceGroupLdcRelCause INTEGER,
        sonusCassgServiceGroupLdcEmergencyCalls       INTEGER,
        sonusCassgServiceGroupTxOsiTime INTEGER,
        sonusCassgServiceGroupCwCidSSP  SonusNameReference,
        sonusCassgServiceGroupSkipCrankBackProfile          Gauge
    }

sonusCassgServiceGroupIndex OBJECT-TYPE
    SYNTAX          INTEGER (1..2048)
    ACCESS          read-only
    STATUS          mandatory
    DESCRIPTION     
            "The index for the CAS Service Group"
    ::= { sonusCasServiceGroupAdmnEntry 1 }

sonusCassgServiceGroupName OBJECT-TYPE
    SYNTAX          SonusName
    ACCESS          read-write
    STATUS          mandatory
    DESCRIPTION     
            "The name of this CAS Service Group."
    ::= { sonusCasServiceGroupAdmnEntry 2 }

sonusCassgServiceGroupProfileName OBJECT-TYPE
    SYNTAX          SonusNameReference
    ACCESS          read-write
    STATUS          mandatory
    DESCRIPTION     
            "The last CAS Service Group profile applied"
    ::= { sonusCasServiceGroupAdmnEntry 3 }

sonusCassgServiceGroupTG OBJECT-TYPE
    SYNTAX          SonusNameReference
    ACCESS          read-write
    STATUS          mandatory
    DESCRIPTION     
            "The trunk group that the CAS Service Group in contained"
    ::= { sonusCasServiceGroupAdmnEntry 4 }

sonusCassgServiceGroupHuntAlgorithm OBJECT-TYPE
    SYNTAX          INTEGER { bottom2Top(1), top2Bottom(2), 
                        circularBottom2Top(3), circularTop2Bottom(4), 
                        mostIdle(5), leastIdle(6) }
    ACCESS          read-write
    STATUS          mandatory
    DESCRIPTION     
            "The method in which channels are hunted for outgoing calls"
    DEFVAL          { bottom2Top }
    ::= { sonusCasServiceGroupAdmnEntry 5 }

sonusCassgServiceGroupCost OBJECT-TYPE
    SYNTAX          INTEGER (0..100)
    ACCESS          read-write
    STATUS          mandatory
    DESCRIPTION     
            "Relative cost parameter used to augment the hunt algorithm"
    DEFVAL          { 50 }
    ::= { sonusCasServiceGroupAdmnEntry 6 }

sonusCassgServiceGroupSignalType OBJECT-TYPE
    SYNTAX          INTEGER { eM(1), gsFxo(2), gsFxs(3), lsFxo(4), 
                        lsFxs(5), mfcr2(6), xecho(7), gr303(8) }
    ACCESS          read-write
    STATUS          mandatory
    DESCRIPTION     
            "The channel associated signaling type"
    DEFVAL          { eM }
    ::= { sonusCasServiceGroupAdmnEntry 7 }

sonusCassgServiceGroupIngressSSP OBJECT-TYPE
    SYNTAX          SonusNameReference
    ACCESS          read-write
    STATUS          mandatory
    DESCRIPTION     
            "The SSP which defines the protocol for ingress calls"
    ::= { sonusCasServiceGroupAdmnEntry 8 }

sonusCassgServiceGroupEgressSSP OBJECT-TYPE
    SYNTAX          SonusNameReference
    ACCESS          read-write
    STATUS          mandatory
    DESCRIPTION     
            "The SSP which defines the protocol for egress calls"
    ::= { sonusCasServiceGroupAdmnEntry 9 }

sonusCassgServiceGroupHookflashSSP OBJECT-TYPE
    SYNTAX          SonusNameReference
    ACCESS          read-write
    STATUS          mandatory
    DESCRIPTION     
            "The SSP which defines the protocol when a hookflash is received on an egress call"
    ::= { sonusCasServiceGroupAdmnEntry 10 }

sonusCassgServiceGroupPscSSP OBJECT-TYPE
    SYNTAX          SonusNameReference
    ACCESS          read-write
    STATUS          mandatory
    DESCRIPTION     
            "The SSP which defines Permenant Signal Condition actions to perform to force a call onhook"
    ::= { sonusCasServiceGroupAdmnEntry 11 }

sonusCassgServiceGroupMaintBusy OBJECT-TYPE
    SYNTAX          SonusAdminState
    ACCESS          read-write
    STATUS          mandatory
    DESCRIPTION     
            "Determines if a channel is taken offhook when it is removed from service"
    DEFVAL          { enabled }
    ::= { sonusCasServiceGroupAdmnEntry 12 }

sonusCassgServiceGroupAutoBusyThreshold OBJECT-TYPE
    SYNTAX          INTEGER (0..255)
    ACCESS          read-write
    STATUS          mandatory
    DESCRIPTION     
            "Determines the number of signaling errors which can occur before the channel is removed from service"
    DEFVAL          { 0 }
    ::= { sonusCasServiceGroupAdmnEntry 13 }

sonusCassgServiceGroupRequiresCPTone OBJECT-TYPE
    SYNTAX          SonusAdminState
    ACCESS          read-write
    STATUS          mandatory
    DESCRIPTION     
            "Determines if ingress calls require call progress tones"
    DEFVAL          { disabled }
    ::= { sonusCasServiceGroupAdmnEntry 14 }

sonusCassgServiceGroupProvidesCPTone OBJECT-TYPE
    SYNTAX          SonusAdminState
    ACCESS          read-write
    STATUS          mandatory
    DESCRIPTION     
            "Determines if the far end switch will provide call progress tones"
    DEFVAL          { disabled }
    ::= { sonusCasServiceGroupAdmnEntry 15 }

sonusCassgServiceGroupDTMFProfileName OBJECT-TYPE
    SYNTAX          SonusNameReference
    ACCESS          read-write
    STATUS          mandatory
    DESCRIPTION     
            "Name reference to DTMF collection/generation profile"
    ::= { sonusCasServiceGroupAdmnEntry 16 }

sonusCassgServiceGroupMFProfileName OBJECT-TYPE
    SYNTAX          SonusNameReference
    ACCESS          read-write
    STATUS          mandatory
    DESCRIPTION     
            "Name reference to MF collection/generation profile"
    ::= { sonusCasServiceGroupAdmnEntry 17 }

sonusCassgServiceGroupCPTonePkgName OBJECT-TYPE
    SYNTAX          SonusNameReference
    ACCESS          read-write
    STATUS          mandatory
    DESCRIPTION     
            "Name reference to Call Progress tone package"
    ::= { sonusCasServiceGroupAdmnEntry 18 }

sonusCassgServiceGroupMinRxWinkTime OBJECT-TYPE
    SYNTAX          INTEGER (100..800)
    ACCESS          read-write
    STATUS          mandatory
    DESCRIPTION     
            "Minimum duration for a receive wink event"
    DEFVAL          { 100 }
    ::= { sonusCasServiceGroupAdmnEntry 19 }

sonusCassgServiceGroupMaxRxWinkTime OBJECT-TYPE
    SYNTAX          INTEGER (100..2000)
    ACCESS          read-write
    STATUS          mandatory
    DESCRIPTION     
            "Maximum duration for a receive wink event"
    DEFVAL          { 700 }
    ::= { sonusCasServiceGroupAdmnEntry 20 }

sonusCassgServiceGroupMinRxFlashTime OBJECT-TYPE
    SYNTAX          INTEGER (100..1100)
    ACCESS          read-write
    STATUS          mandatory
    DESCRIPTION     
            "Minimum duration for a receive flash event"
    DEFVAL          { 300 }
    ::= { sonusCasServiceGroupAdmnEntry 21 }

sonusCassgServiceGroupMaxRxFlashTime OBJECT-TYPE
    SYNTAX          INTEGER (100..1100)
    ACCESS          read-write
    STATUS          mandatory
    DESCRIPTION     
            "Maximum duration for a receive flash event"
    DEFVAL          { 700 }
    ::= { sonusCasServiceGroupAdmnEntry 22 }

sonusCassgServiceGroupTxWinkTime OBJECT-TYPE
    SYNTAX          INTEGER (100..800)
    ACCESS          read-write
    STATUS          mandatory
    DESCRIPTION     
            "Duration for a transmit wink"
    DEFVAL          { 200 }
    ::= { sonusCasServiceGroupAdmnEntry 23 }

sonusCassgServiceGroupTxFlashTime OBJECT-TYPE
    SYNTAX          INTEGER (300..1100)
    ACCESS          read-write
    STATUS          mandatory
    DESCRIPTION     
            "Duration for a transmit flash"
    DEFVAL          { 500 }
    ::= { sonusCasServiceGroupAdmnEntry 24 }

sonusCassgServiceGroupGuardTime OBJECT-TYPE
    SYNTAX          INTEGER (100..1500)
    ACCESS          read-write
    STATUS          mandatory
    DESCRIPTION     
            "Duration for the line to clear after disconnect"
    DEFVAL          { 800 }
    ::= { sonusCasServiceGroupAdmnEntry 25 }

sonusCassgServiceGroupOperation OBJECT-TYPE
    SYNTAX          INTEGER { noAction(1), resetStats(2) }
    ACCESS          read-write
    STATUS          mandatory
    DESCRIPTION     
            "This objects always reads as noAction(1).  Setting this object to
             resetStats(2) causes the statistics for the channels in the Service Group to be reset."
    DEFVAL          { noAction }
    ::= { sonusCasServiceGroupAdmnEntry 26 }

sonusCassgServiceGroupAdminState OBJECT-TYPE
    SYNTAX          SonusAdminState
    ACCESS          read-write
    STATUS          mandatory
    DESCRIPTION     
            "The admin state of the CAS Service Group"
    DEFVAL          { disabled }
    ::= { sonusCasServiceGroupAdmnEntry 27 }

sonusCassgServiceGroupMode OBJECT-TYPE
    SYNTAX          SonusServiceState
    ACCESS          read-write
    STATUS          mandatory
    DESCRIPTION     
            "The mode of operation of channels in the CAS Service Group"
    DEFVAL          { inService }
    ::= { sonusCasServiceGroupAdmnEntry 28 }

sonusCassgServiceGroupAction OBJECT-TYPE
    SYNTAX          SonusAdminAction
    ACCESS          read-write
    STATUS          mandatory
    DESCRIPTION     
            "The action taken on the channels in the CAS Service Group"
    DEFVAL          { force }
    ::= { sonusCasServiceGroupAdmnEntry 29 }

sonusCassgServiceGroupTimeout OBJECT-TYPE
    SYNTAX          INTEGER (1..1440)
    ACCESS          read-write
    STATUS          mandatory
    DESCRIPTION     
            "The timeout value in minutes for dryup action on the CAS Service Group"
    DEFVAL          { 1 }
    ::= { sonusCasServiceGroupAdmnEntry 30 }

sonusCassgServiceGroupAlertToneName OBJECT-TYPE
    SYNTAX          SonusNameReference
    ACCESS          read-write
    STATUS          obsolete
    DESCRIPTION     
            "Specifies a named reference to a tone to play for ring back.
             This object is not used and was made obsolete in GSX
             release 6.0. Local Ring Back Tone Configuration has
             now moved to PSX."
    ::= { sonusCasServiceGroupAdmnEntry 31 }

sonusCassgServiceGroupRowStatus OBJECT-TYPE
    SYNTAX          RowStatus
    ACCESS          read-write
    STATUS          mandatory
    DESCRIPTION     
            ""
    ::= { sonusCasServiceGroupAdmnEntry 32 }

sonusCassgServiceGroupDTProfileName OBJECT-TYPE
    SYNTAX          SonusNameReference
    ACCESS          read-write
    STATUS          mandatory
    DESCRIPTION     
            "Name reference to Disconnect Treatment profile"
    ::= { sonusCasServiceGroupAdmnEntry 33 }

sonusCassgServiceGroupSuspendTime OBJECT-TYPE
    SYNTAX          INTEGER (0..60000)
    ACCESS          read-write
    STATUS          mandatory
    DESCRIPTION     
            "The timeout value in milliseconds before a call in which the called party disconnected first is terminated"
    DEFVAL          { 0 }
    ::= { sonusCasServiceGroupAdmnEntry 34 }

sonusCassgServiceGroupSwitchSide OBJECT-TYPE
    SYNTAX          INTEGER { network(1), user(2) }
    ACCESS          read-write
    STATUS          mandatory
    DESCRIPTION     
            "The switch side the CAS Service Group should emulate."
    DEFVAL          { network }
    ::= { sonusCasServiceGroupAdmnEntry 35 }

sonusCassgServiceGroupSigVariant OBJECT-TYPE
    SYNTAX          INTEGER { none(1), mexicoR2V1(2), mexicoR2V2(3), 
                        itu(4), indiaScheme5(5), indiaScheme6Out(6), 
                        indiaScheme6In(7), indiaScheme7Out(8), 
                        indiaScheme7In(9), brazil(10) }
    ACCESS          read-write
    STATUS          mandatory
    DESCRIPTION     
            "The signaling variant the CAS Service Group should emulate."
    DEFVAL          { none }
    ::= { sonusCasServiceGroupAdmnEntry 36 }

sonusCassgServiceGroupBNUMEndDigit OBJECT-TYPE
    SYNTAX          SonusAdminState
    ACCESS          read-write
    STATUS          mandatory
    DESCRIPTION     
            "For R2, determines if the the called party number should be terminated with an end of digits signal."
    DEFVAL          { disabled }
    ::= { sonusCasServiceGroupAdmnEntry 37 }

sonusCassgServiceGroupMFCR2ProfileName OBJECT-TYPE
    SYNTAX          SonusNameReference
    ACCESS          read-write
    STATUS          mandatory
    DESCRIPTION     
            "Name reference to MFCR2 collection/generation profile"
    ::= { sonusCasServiceGroupAdmnEntry 38 }

sonusCassgServiceGroupRxClrToIdleTime OBJECT-TYPE
    SYNTAX          INTEGER (0..500)
    ACCESS          read-write
    STATUS          mandatory
    DESCRIPTION     
            "For R2, time in milliseconds after a clear forward is received before a channel is considered idle."
    DEFVAL          { 100 }
    ::= { sonusCasServiceGroupAdmnEntry 39 }

sonusCassgServiceGroupE1Cbit OBJECT-TYPE
    SYNTAX          INTEGER (0..1)
    ACCESS          read-write
    STATUS          mandatory
    DESCRIPTION     
            "For E1, the binary state of the C bit"
    DEFVAL          { 0 }
    ::= { sonusCasServiceGroupAdmnEntry 40 }

sonusCassgServiceGroupE1Dbit OBJECT-TYPE
    SYNTAX          INTEGER (0..1)
    ACCESS          read-write
    STATUS          mandatory
    DESCRIPTION     
            "For E1, the binary state of the D bit"
    DEFVAL          { 1 }
    ::= { sonusCasServiceGroupAdmnEntry 41 }

sonusCassgServiceGroupMGCPackage OBJECT-TYPE
    SYNTAX          INTEGER { none(1), ms(2), dt(3), md(4), mo(5), r2(6), 
                        h248MFR1(7), h248OSSR1(8), h248MFR2(9), 
                        h248XEcho(10), h248GR303(11) }
    ACCESS          read-write
    STATUS          mandatory
    DESCRIPTION     
            "MGC CAS package for the CAS service group."
    DEFVAL          { none }
    ::= { sonusCasServiceGroupAdmnEntry 42 }

sonusCassgServiceGroupLsGsAnswerSupv OBJECT-TYPE
    SYNTAX          SonusAdminState
    ACCESS          read-write
    STATUS          mandatory
    DESCRIPTION     
            "For LS ans GS, determines if line side answer supervision is supported."
    DEFVAL          { disabled }
    ::= { sonusCasServiceGroupAdmnEntry 43 }

sonusCassgServiceGroupRxSeizeRingTime OBJECT-TYPE
    SYNTAX          INTEGER (20..2000)
    ACCESS          read-write
    STATUS          mandatory
    DESCRIPTION     
            "For LS and GS, time in milliseconds before a seizure is detected (LC for LS FXO, RG for GS FXO, Ring for LS/GS FXS)."
    DEFVAL          { 150 }
    ::= { sonusCasServiceGroupAdmnEntry 44 }

sonusCassgServiceGroupRxFxsAnswerTime OBJECT-TYPE
    SYNTAX          INTEGER (20..2000)
    ACCESS          read-write
    STATUS          mandatory
    DESCRIPTION     
            "For LS and GS FXS, time in milliseconds before an answer is detected."
    DEFVAL          { 100 }
    ::= { sonusCasServiceGroupAdmnEntry 45 }

sonusCassgServiceGroupRxFxsDiscTime OBJECT-TYPE
    SYNTAX          INTEGER (100..2000)
    ACCESS          read-write
    STATUS          mandatory
    DESCRIPTION     
            "For LS and GS FXS, time in milliseconds before a disconnect is detected."
    DEFVAL          { 600 }
    ::= { sonusCasServiceGroupAdmnEntry 46 }

sonusCassgServiceGroupRxLsFxsRingCess OBJECT-TYPE
    SYNTAX          INTEGER (100..30000)
    ACCESS          read-write
    STATUS          mandatory
    DESCRIPTION     
            "For LS FXS, time in milliseconds before ring cessation is detected."
    DEFVAL          { 8000 }
    ::= { sonusCasServiceGroupAdmnEntry 47 }

sonusCassgServiceGroupTxLsFxoDiscTime OBJECT-TYPE
    SYNTAX          INTEGER (0..2000)
    ACCESS          read-write
    STATUS          mandatory
    DESCRIPTION     
            "For LS FXO, time in milliseconds that the LCFO disconnect signal is sent."
    DEFVAL          { 800 }
    ::= { sonusCasServiceGroupAdmnEntry 48 }

sonusCassgServiceGroupTxFxoRingOnTime OBJECT-TYPE
    SYNTAX          INTEGER (100..10000)
    ACCESS          read-write
    STATUS          mandatory
    DESCRIPTION     
            "For LS and GS FXO, time in milliseconds that the ring on signal is sent."
    DEFVAL          { 2000 }
    ::= { sonusCasServiceGroupAdmnEntry 49 }

sonusCassgServiceGroupTxFxoRingOffTime OBJECT-TYPE
    SYNTAX          INTEGER (100..10000)
    ACCESS          read-write
    STATUS          mandatory
    DESCRIPTION     
            "For LS and GS FXO, time in milliseconds that the ring off signal is sent."
    DEFVAL          { 4000 }
    ::= { sonusCasServiceGroupAdmnEntry 50 }

sonusCassgServiceGroupAnsSupervisionTimeout OBJECT-TYPE
    SYNTAX          INTEGER (0..1000)
    ACCESS          read-write
    STATUS          mandatory
    DESCRIPTION     
            "This is the time from egress call setup to egress receiving an answer used
             by the wait answer SSP."
    DEFVAL          { 0 }
    ::= { sonusCasServiceGroupAdmnEntry 51 }

sonusCassgServiceGroupCrankBackProfile OBJECT-TYPE
    SYNTAX          INTEGER (0..20)
    ACCESS          read-write
    STATUS          mandatory
    DESCRIPTION     
            "The Crankback Profile to be used for this service."
    DEFVAL          { 1 }
    ::= { sonusCasServiceGroupAdmnEntry 52 }

sonusCassgServiceGroupANUMLength OBJECT-TYPE
    SYNTAX          INTEGER (0..30)
    ACCESS          read-write
    STATUS          mandatory
    DESCRIPTION     
            "For R2, determines the length of transmitted calling party number.
             A value of 0 implies variable length terminated by an end of digits signal.
             Otherwise, the value specifies the fixed length of the calling party number."
    DEFVAL          { 0 }
    ::= { sonusCasServiceGroupAdmnEntry 53 }

sonusCassgServiceGroupTxR2EndDigit OBJECT-TYPE
    SYNTAX          INTEGER { r2Signal15(8), r2Signal14(9), 
                        r2Signal13(10), r2Signal12(11), r2Signal11(12) }
    ACCESS          read-write
    STATUS          mandatory
    DESCRIPTION     
            "For R2, specifies the transmit end of digits signal."
    DEFVAL          { r2Signal15 }
    ::= { sonusCasServiceGroupAdmnEntry 54 }

sonusCassgServiceGroupRxR2SeizeTime OBJECT-TYPE
    SYNTAX          INTEGER (20..2000)
    ACCESS          read-write
    STATUS          mandatory
    DESCRIPTION     
            "For R2, duration that a seize signal must be present before it is considered a valid signal."
    DEFVAL          { 20 }
    ::= { sonusCasServiceGroupAdmnEntry 55 }

sonusCassgServiceGroupRxR2SeizeAckTime OBJECT-TYPE
    SYNTAX          INTEGER (20..2000)
    ACCESS          read-write
    STATUS          mandatory
    DESCRIPTION     
            "For R2, duration that a seize ack signal must be present before it is considered a valid signal."
    DEFVAL          { 20 }
    ::= { sonusCasServiceGroupAdmnEntry 56 }

sonusCassgServiceGroupRxR2AnswerTime OBJECT-TYPE
    SYNTAX          INTEGER (20..2000)
    ACCESS          read-write
    STATUS          mandatory
    DESCRIPTION     
            "For R2, duration that an answer signal must be present before it is considered a valid signal."
    DEFVAL          { 20 }
    ::= { sonusCasServiceGroupAdmnEntry 57 }

sonusCassgServiceGroupRxR2ClearBackTime OBJECT-TYPE
    SYNTAX          INTEGER (20..2000)
    ACCESS          read-write
    STATUS          mandatory
    DESCRIPTION     
            "For R2, duration that a clear back signal must be present before it is considered a valid signal."
    DEFVAL          { 20 }
    ::= { sonusCasServiceGroupAdmnEntry 58 }

sonusCassgServiceGroupRxR2ClearFwdTime OBJECT-TYPE
    SYNTAX          INTEGER (20..2000)
    ACCESS          read-write
    STATUS          mandatory
    DESCRIPTION     
            "For R2, duration that a clear forward signal must be present before it is considered a valid signal."
    DEFVAL          { 20 }
    ::= { sonusCasServiceGroupAdmnEntry 59 }

sonusCassgServiceGroupRxR2IdleBackTime OBJECT-TYPE
    SYNTAX          INTEGER (20..2000)
    ACCESS          read-write
    STATUS          mandatory
    DESCRIPTION     
            "For R2, duration that an idle back signal must be present before it is considered a valid signal."
    DEFVAL          { 20 }
    ::= { sonusCasServiceGroupAdmnEntry 60 }

sonusCassgServiceGroupRxR2BlockTime OBJECT-TYPE
    SYNTAX          INTEGER (20..2000)
    ACCESS          read-write
    STATUS          mandatory
    DESCRIPTION     
            "For R2, duration that a block signal must be present before it is considered a valid signal."
    DEFVAL          { 20 }
    ::= { sonusCasServiceGroupAdmnEntry 61 }

sonusCassgServiceGroupCongRelTimeout OBJECT-TYPE
    SYNTAX          INTEGER (0..5)
    ACCESS          read-write
    STATUS          mandatory
    DESCRIPTION     
            "Time to delay sending of release during congestion."
    DEFVAL          { 0 }
    ::= { sonusCasServiceGroupAdmnEntry 62 }

sonusCassgServiceGroupLdcTimeout OBJECT-TYPE
    SYNTAX          INTEGER (0..2880)
    ACCESS          read-write
    STATUS          mandatory
    DESCRIPTION     
            "The timeout value of the long duration call timer in minutes.
             Allowed values are 0 to disable the timer, 60-2880 minutes to set the timer."
    DEFVAL          { 0 }
    ::= { sonusCasServiceGroupAdmnEntry 63 }

sonusCassgServiceGroupLdcAction OBJECT-TYPE
    SYNTAX          INTEGER { noAction(0), trap(1), release(2), 
                        trapAndRelease(3) }
    ACCESS          read-write
    STATUS          mandatory
    DESCRIPTION     
            "This is the action to take if the long duration call timer
             expires.  The call may be released or a trap fired, or both."
    DEFVAL          { noAction }
    ::= { sonusCasServiceGroupAdmnEntry 64 }

sonusCassgServiceGroupLdcRelCause OBJECT-TYPE
    SYNTAX          INTEGER (1..127)
    ACCESS          read-write
    STATUS          mandatory
    DESCRIPTION     
            "The Q.850 release value to use should the call be released 
             due to long duration call timer expiry"
    DEFVAL          { 41 }
    ::= { sonusCasServiceGroupAdmnEntry 65 }

sonusCassgServiceGroupLdcEmergencyCalls OBJECT-TYPE
    SYNTAX          INTEGER { include(0), exclude(1) }
    ACCESS          read-write
    STATUS          mandatory
    DESCRIPTION     
            "Whether Emergency Calls should be exluded from 
             or included in Long Duration Call disconnect procedures"
    DEFVAL          { exclude }
    ::= { sonusCasServiceGroupAdmnEntry 66 }

sonusCassgServiceGroupTxOsiTime OBJECT-TYPE
    SYNTAX          INTEGER (150..300)
    ACCESS          read-write
    STATUS          mandatory
    DESCRIPTION     
            "For Visual Message Waiting Indicator, time in milliseconds that the OSI signal is sent."
    DEFVAL          { 200 }
    ::= { sonusCasServiceGroupAdmnEntry 67 }

sonusCassgServiceGroupCwCidSSP OBJECT-TYPE
    SYNTAX          SonusNameReference
    ACCESS          read-write
    STATUS          mandatory
    DESCRIPTION     
            "The SSP which defines the protocol for call waiting caller id."
    ::= { sonusCasServiceGroupAdmnEntry 68 }

sonusCassgServiceGroupSkipCrankBackProfile OBJECT-TYPE
    SYNTAX          Gauge (0..20)
    ACCESS          read-write
    STATUS          mandatory
    DESCRIPTION     
            "The Skip Crankback Profile to be used for this service."
    DEFVAL          { 0 }
    ::= { sonusCasServiceGroupAdmnEntry 71 }

sonusCasSvcGrpProfileAdmn OBJECT IDENTIFIER
    ::= { sonusCasMIBObjects 2 }

sonusCasSvcGrpProfileNextIndex OBJECT-TYPE
    SYNTAX          INTEGER
    ACCESS          read-only
    STATUS          mandatory
    DESCRIPTION     
            "The next valid index to use when creating a new sonusCasSvcGrpProfileAdmnEntry"
    ::= { sonusCasSvcGrpProfileAdmn 1 }

sonusCasSvcGrpProfileAdmnTable OBJECT-TYPE
    SYNTAX          SEQUENCE OF SonusCasSvcGrpProfileAdmnEntry
    ACCESS          not-accessible
    STATUS          mandatory
    DESCRIPTION     
            ""
    ::= { sonusCasSvcGrpProfileAdmn 2 }

sonusCasSvcGrpProfileAdmnEntry OBJECT-TYPE
    SYNTAX          SonusCasSvcGrpProfileAdmnEntry
    ACCESS          not-accessible
    STATUS          mandatory
    DESCRIPTION     
            ""
    INDEX           { sonusCassgSvcGrpProfileIndex }
    ::= { sonusCasSvcGrpProfileAdmnTable 1 }

SonusCasSvcGrpProfileAdmnEntry ::=
    SEQUENCE {
        sonusCassgSvcGrpProfileIndex    INTEGER,
        sonusCassgSvcGrpProfileName     SonusName,
        sonusCassgSvcGrpProfileTG       SonusNameReference,
        sonusCassgSvcGrpProfileHuntAlgorithm    INTEGER,
        sonusCassgSvcGrpProfileCost     INTEGER,
        sonusCassgSvcGrpProfileSignalType INTEGER,
        sonusCassgSvcGrpProfileIngressSSP SonusNameReference,
        sonusCassgSvcGrpProfileEgressSSP SonusNameReference,
        sonusCassgSvcGrpProfileHookflashSSP   SonusNameReference,
        sonusCassgSvcGrpProfilePscSSP   SonusNameReference,
        sonusCassgSvcGrpProfileMaintBusy SonusAdminState,
        sonusCassgSvcGrpProfileAutoBusyThreshold        INTEGER,
        sonusCassgSvcGrpProfileRequiresCPTone     SonusAdminState,
        sonusCassgSvcGrpProfileProvidesCPTone     SonusAdminState,
        sonusCassgSvcGrpProfileDTMFProfileName      SonusNameReference,
        sonusCassgSvcGrpProfileMFProfileName    SonusNameReference,
        sonusCassgSvcGrpProfileCPTonePkgName    SonusNameReference,
        sonusCassgSvcGrpProfileMinRxWinkTime    INTEGER,
        sonusCassgSvcGrpProfileMaxRxWinkTime    INTEGER,
        sonusCassgSvcGrpProfileMinRxFlashTime     INTEGER,
        sonusCassgSvcGrpProfileMaxRxFlashTime     INTEGER,
        sonusCassgSvcGrpProfileTxWinkTime INTEGER,
        sonusCassgSvcGrpProfileTxFlashTime  INTEGER,
        sonusCassgSvcGrpProfileGuardTime INTEGER,
        sonusCassgSvcGrpProfileAdminState SonusAdminState,
        sonusCassgSvcGrpProfileAlertToneName    SonusNameReference,
        sonusCassgSvcGrpProfileRowStatus RowStatus,
        sonusCassgSvcGrpProfileDTProfileName    SonusNameReference,
        sonusCassgSvcGrpProfileSuspendTime  INTEGER,
        sonusCassgSvcGrpProfileSwitchSide INTEGER,
        sonusCassgSvcGrpProfileSigVariant INTEGER,
        sonusCassgSvcGrpProfileBNUMEndDigit   SonusAdminState,
        sonusCassgSvcGrpProfileMFCR2ProfileName       SonusNameReference,
        sonusCassgSvcGrpProfileRxClrToIdleTime      INTEGER,
        sonusCassgSvcGrpProfileE1Cbit   INTEGER,
        sonusCassgSvcGrpProfileE1Dbit   INTEGER,
        sonusCassgSvcGrpProfileMGCPackage INTEGER,
        sonusCassgSvcGrpProfileLsGsAnswerSupv     SonusAdminState,
        sonusCassgSvcGrpProfileRxSeizeRingTime      INTEGER,
        sonusCassgSvcGrpProfileRxFxsAnswerTime      INTEGER,
        sonusCassgSvcGrpProfileRxFxsDiscTime    INTEGER,
        sonusCassgSvcGrpProfileRxLsFxsRingCess      INTEGER,
        sonusCassgSvcGrpProfileTxLsFxoDiscTime      INTEGER,
        sonusCassgSvcGrpProfileTxFxoRingOnTime      INTEGER,
        sonusCassgSvcGrpProfileTxFxoRingOffTime       INTEGER,
        sonusCassgSvcGrpProfileAnsSupervisionTimeout            INTEGER,
        sonusCassgSvcGrpProfileCrankBackProfile       INTEGER,
        sonusCassgSvcGrpProfileANUMLength INTEGER,
        sonusCassgSvcGrpProfileTxR2EndDigit   INTEGER,
        sonusCassgSvcGrpProfileRxR2SeizeTime    INTEGER,
        sonusCassgSvcGrpProfileRxR2SeizeAckTime       INTEGER,
        sonusCassgSvcGrpProfileRxR2AnswerTime     INTEGER,
        sonusCassgSvcGrpProfileRxR2ClearBackTime        INTEGER,
        sonusCassgSvcGrpProfileRxR2ClearFwdTime       INTEGER,
        sonusCassgSvcGrpProfileRxR2IdleBackTime       INTEGER,
        sonusCassgSvcGrpProfileRxR2BlockTime    INTEGER,
        sonusCassgSvcGrpProfileCongRelTimeout     INTEGER,
        sonusCassgSvcGrpProfileLdcTimeout INTEGER,
        sonusCassgSvcGrpProfileLdcAction INTEGER,
        sonusCassgSvcGrpProfileLdcRelCause  INTEGER,
        sonusCassgSvcGrpProfileLdcEmergencyCalls        INTEGER,
        sonusCassgSvcGrpProfileTxOsiTime INTEGER,
        sonusCassgSvcGrpProfileCwCidSSP SonusNameReference,
        sonusCassgSvcGrpProfileSkipCrankBackProfile           Gauge
    }

sonusCassgSvcGrpProfileIndex OBJECT-TYPE
    SYNTAX          INTEGER (1..128)
    ACCESS          read-only
    STATUS          mandatory
    DESCRIPTION     
            "The index for the CAS Service Group Profile"
    ::= { sonusCasSvcGrpProfileAdmnEntry 1 }

sonusCassgSvcGrpProfileName OBJECT-TYPE
    SYNTAX          SonusName
    ACCESS          read-write
    STATUS          mandatory
    DESCRIPTION     
            "The name of this CAS Service Group profile."
    ::= { sonusCasSvcGrpProfileAdmnEntry 2 }

sonusCassgSvcGrpProfileTG OBJECT-TYPE
    SYNTAX          SonusNameReference
    ACCESS          read-write
    STATUS          mandatory
    DESCRIPTION     
            "The trunk group that the CAS Service Group in contained"
    ::= { sonusCasSvcGrpProfileAdmnEntry 3 }

sonusCassgSvcGrpProfileHuntAlgorithm OBJECT-TYPE
    SYNTAX          INTEGER { bottom2Top(1), top2Bottom(2), 
                        circularBottom2Top(3), circularTop2Bottom(4) }
    ACCESS          read-write
    STATUS          mandatory
    DESCRIPTION     
            "The method in which channels are hunted for outgoing calls"
    DEFVAL          { bottom2Top }
    ::= { sonusCasSvcGrpProfileAdmnEntry 4 }

sonusCassgSvcGrpProfileCost OBJECT-TYPE
    SYNTAX          INTEGER (0..100)
    ACCESS          read-write
    STATUS          mandatory
    DESCRIPTION     
            "Relative cost parameter used to augment the hunt algorithm"
    DEFVAL          { 50 }
    ::= { sonusCasSvcGrpProfileAdmnEntry 5 }

sonusCassgSvcGrpProfileSignalType OBJECT-TYPE
    SYNTAX          INTEGER { eM(1), gsFxo(2), gsFxs(3), lsFxo(4), 
                        lsFxs(5), mfcr2(6), xecho(7), gr303(8) }
    ACCESS          read-write
    STATUS          mandatory
    DESCRIPTION     
            "The channel associated signaling type"
    DEFVAL          { eM }
    ::= { sonusCasSvcGrpProfileAdmnEntry 6 }

sonusCassgSvcGrpProfileIngressSSP OBJECT-TYPE
    SYNTAX          SonusNameReference
    ACCESS          read-write
    STATUS          mandatory
    DESCRIPTION     
            "The SSP which defines the protocol for ingress calls"
    ::= { sonusCasSvcGrpProfileAdmnEntry 7 }

sonusCassgSvcGrpProfileEgressSSP OBJECT-TYPE
    SYNTAX          SonusNameReference
    ACCESS          read-write
    STATUS          mandatory
    DESCRIPTION     
            "The SSP which defines the protocol for egress calls"
    ::= { sonusCasSvcGrpProfileAdmnEntry 8 }

sonusCassgSvcGrpProfileHookflashSSP OBJECT-TYPE
    SYNTAX          SonusNameReference
    ACCESS          read-write
    STATUS          mandatory
    DESCRIPTION     
            "The SSP which defines the protocol when a hookflash is received on an egress call"
    ::= { sonusCasSvcGrpProfileAdmnEntry 9 }

sonusCassgSvcGrpProfilePscSSP OBJECT-TYPE
    SYNTAX          SonusNameReference
    ACCESS          read-write
    STATUS          mandatory
    DESCRIPTION     
            "The SSP which defines Permenant Signal Condition actions to perform to force a call onhook"
    ::= { sonusCasSvcGrpProfileAdmnEntry 10 }

sonusCassgSvcGrpProfileMaintBusy OBJECT-TYPE
    SYNTAX          SonusAdminState
    ACCESS          read-write
    STATUS          mandatory
    DESCRIPTION     
            "Determines if a channel is taken offhook when it is removed from service"
    DEFVAL          { enabled }
    ::= { sonusCasSvcGrpProfileAdmnEntry 11 }

sonusCassgSvcGrpProfileAutoBusyThreshold OBJECT-TYPE
    SYNTAX          INTEGER (0..255)
    ACCESS          read-write
    STATUS          mandatory
    DESCRIPTION     
            "Determines the number of signaling errors which can occur before the channel is removed from service"
    DEFVAL          { 0 }
    ::= { sonusCasSvcGrpProfileAdmnEntry 12 }

sonusCassgSvcGrpProfileRequiresCPTone OBJECT-TYPE
    SYNTAX          SonusAdminState
    ACCESS          read-write
    STATUS          mandatory
    DESCRIPTION     
            "Determines if ingress calls require call progress tones"
    DEFVAL          { disabled }
    ::= { sonusCasSvcGrpProfileAdmnEntry 13 }

sonusCassgSvcGrpProfileProvidesCPTone OBJECT-TYPE
    SYNTAX          SonusAdminState
    ACCESS          read-write
    STATUS          mandatory
    DESCRIPTION     
            "Determines if the far end switch will provide call progress tones"
    DEFVAL          { disabled }
    ::= { sonusCasSvcGrpProfileAdmnEntry 14 }

sonusCassgSvcGrpProfileDTMFProfileName OBJECT-TYPE
    SYNTAX          SonusNameReference
    ACCESS          read-write
    STATUS          mandatory
    DESCRIPTION     
            "Name reference to DTMF collection/generation profile"
    ::= { sonusCasSvcGrpProfileAdmnEntry 15 }

sonusCassgSvcGrpProfileMFProfileName OBJECT-TYPE
    SYNTAX          SonusNameReference
    ACCESS          read-write
    STATUS          mandatory
    DESCRIPTION     
            "Name reference to MF collection/generation profile"
    ::= { sonusCasSvcGrpProfileAdmnEntry 16 }

sonusCassgSvcGrpProfileCPTonePkgName OBJECT-TYPE
    SYNTAX          SonusNameReference
    ACCESS          read-write
    STATUS          mandatory
    DESCRIPTION     
            "Name reference to Call Progress tone package"
    ::= { sonusCasSvcGrpProfileAdmnEntry 17 }

sonusCassgSvcGrpProfileMinRxWinkTime OBJECT-TYPE
    SYNTAX          INTEGER (100..800)
    ACCESS          read-write
    STATUS          mandatory
    DESCRIPTION     
            "Minimum duration for a receive wink event"
    DEFVAL          { 100 }
    ::= { sonusCasSvcGrpProfileAdmnEntry 18 }

sonusCassgSvcGrpProfileMaxRxWinkTime OBJECT-TYPE
    SYNTAX          INTEGER (100..2000)
    ACCESS          read-write
    STATUS          mandatory
    DESCRIPTION     
            "Maximum duration for a receive wink event"
    DEFVAL          { 700 }
    ::= { sonusCasSvcGrpProfileAdmnEntry 19 }

sonusCassgSvcGrpProfileMinRxFlashTime OBJECT-TYPE
    SYNTAX          INTEGER (100..1100)
    ACCESS          read-write
    STATUS          mandatory
    DESCRIPTION     
            "Minimum duration for a receive flash event"
    DEFVAL          { 300 }
    ::= { sonusCasSvcGrpProfileAdmnEntry 20 }

sonusCassgSvcGrpProfileMaxRxFlashTime OBJECT-TYPE
    SYNTAX          INTEGER (100..1100)
    ACCESS          read-write
    STATUS          mandatory
    DESCRIPTION     
            "Maximum duration for a receive flash event"
    DEFVAL          { 700 }
    ::= { sonusCasSvcGrpProfileAdmnEntry 21 }

sonusCassgSvcGrpProfileTxWinkTime OBJECT-TYPE
    SYNTAX          INTEGER (100..800)
    ACCESS          read-write
    STATUS          mandatory
    DESCRIPTION     
            "Duration for a transmit wink"
    DEFVAL          { 200 }
    ::= { sonusCasSvcGrpProfileAdmnEntry 22 }

sonusCassgSvcGrpProfileTxFlashTime OBJECT-TYPE
    SYNTAX          INTEGER (300..1100)
    ACCESS          read-write
    STATUS          mandatory
    DESCRIPTION     
            "Duration for a transmit flash"
    DEFVAL          { 500 }
    ::= { sonusCasSvcGrpProfileAdmnEntry 23 }

sonusCassgSvcGrpProfileGuardTime OBJECT-TYPE
    SYNTAX          INTEGER (100..1500)
    ACCESS          read-write
    STATUS          mandatory
    DESCRIPTION     
            "Duration for the line to clear after disconnect"
    DEFVAL          { 800 }
    ::= { sonusCasSvcGrpProfileAdmnEntry 24 }

sonusCassgSvcGrpProfileAdminState OBJECT-TYPE
    SYNTAX          SonusAdminState
    ACCESS          read-write
    STATUS          mandatory
    DESCRIPTION     
            "The admin state of the CAS Service Group"
    DEFVAL          { disabled }
    ::= { sonusCasSvcGrpProfileAdmnEntry 25 }

sonusCassgSvcGrpProfileAlertToneName OBJECT-TYPE
    SYNTAX          SonusNameReference
    ACCESS          read-write
    STATUS          obsolete
    DESCRIPTION     
            "Specifies a named reference to a tone to play for ring back.
             This object is not used and was made obsolete in GSX
             release 6.0. Local Ring Back Tone Configuration has
             now moved to PSX."
    ::= { sonusCasSvcGrpProfileAdmnEntry 26 }

sonusCassgSvcGrpProfileRowStatus OBJECT-TYPE
    SYNTAX          RowStatus
    ACCESS          read-write
    STATUS          mandatory
    DESCRIPTION     
            ""
    ::= { sonusCasSvcGrpProfileAdmnEntry 27 }

sonusCassgSvcGrpProfileDTProfileName OBJECT-TYPE
    SYNTAX          SonusNameReference
    ACCESS          read-write
    STATUS          mandatory
    DESCRIPTION     
            "Name reference to Disconnect Treatment profile"
    ::= { sonusCasSvcGrpProfileAdmnEntry 28 }

sonusCassgSvcGrpProfileSuspendTime OBJECT-TYPE
    SYNTAX          INTEGER (0..60000)
    ACCESS          read-write
    STATUS          mandatory
    DESCRIPTION     
            "The timeout value in milliseconds before a call in which the called party disconnected first is terminated"
    DEFVAL          { 0 }
    ::= { sonusCasSvcGrpProfileAdmnEntry 29 }

sonusCassgSvcGrpProfileSwitchSide OBJECT-TYPE
    SYNTAX          INTEGER { network(1), user(2) }
    ACCESS          read-write
    STATUS          mandatory
    DESCRIPTION     
            "The switch side the CAS Service Group should emulate."
    DEFVAL          { network }
    ::= { sonusCasSvcGrpProfileAdmnEntry 30 }

sonusCassgSvcGrpProfileSigVariant OBJECT-TYPE
    SYNTAX          INTEGER { none(1), mexicoV1(2), mexicoV2(3), itu(4), 
                        indiaScheme5(5), indiaScheme6Out(6), 
                        indiaScheme6In(7), indiaScheme7Out(8), 
                        indiaScheme7In(9), brazil(10) }
    ACCESS          read-write
    STATUS          mandatory
    DESCRIPTION     
            "The signaling variant the CAS Service Group should emulate."
    DEFVAL          { none }
    ::= { sonusCasSvcGrpProfileAdmnEntry 31 }

sonusCassgSvcGrpProfileBNUMEndDigit OBJECT-TYPE
    SYNTAX          SonusAdminState
    ACCESS          read-write
    STATUS          mandatory
    DESCRIPTION     
            "For R2, determines if the the called party number should be terminated with and end of digits signal."
    DEFVAL          { disabled }
    ::= { sonusCasSvcGrpProfileAdmnEntry 32 }

sonusCassgSvcGrpProfileMFCR2ProfileName OBJECT-TYPE
    SYNTAX          SonusNameReference
    ACCESS          read-write
    STATUS          mandatory
    DESCRIPTION     
            "Name reference to MFCR2 collection/generation profile"
    ::= { sonusCasSvcGrpProfileAdmnEntry 33 }

sonusCassgSvcGrpProfileRxClrToIdleTime OBJECT-TYPE
    SYNTAX          INTEGER (0..500)
    ACCESS          read-write
    STATUS          mandatory
    DESCRIPTION     
            "For R2, time in milliseconds after a clear forward is received before a channel is considered idle."
    DEFVAL          { 100 }
    ::= { sonusCasSvcGrpProfileAdmnEntry 34 }

sonusCassgSvcGrpProfileE1Cbit OBJECT-TYPE
    SYNTAX          INTEGER (0..1)
    ACCESS          read-write
    STATUS          mandatory
    DESCRIPTION     
            "For E1, the binary state of the C bit"
    DEFVAL          { 0 }
    ::= { sonusCasSvcGrpProfileAdmnEntry 35 }

sonusCassgSvcGrpProfileE1Dbit OBJECT-TYPE
    SYNTAX          INTEGER (0..1)
    ACCESS          read-write
    STATUS          mandatory
    DESCRIPTION     
            "For E1, the binary state of the D bit"
    DEFVAL          { 1 }
    ::= { sonusCasSvcGrpProfileAdmnEntry 36 }

sonusCassgSvcGrpProfileMGCPackage OBJECT-TYPE
    SYNTAX          INTEGER { none(1), ms(2), dt(3), md(4), mo(5), r2(6), 
                        h248MFR1(7), h248OSSR1(8), h248MFR2(9), 
                        h248XEcho(10), h248GR303(11) }
    ACCESS          read-write
    STATUS          mandatory
    DESCRIPTION     
            "MGC CAS package for the CAS service group profile."
    DEFVAL          { none }
    ::= { sonusCasSvcGrpProfileAdmnEntry 37 }

sonusCassgSvcGrpProfileLsGsAnswerSupv OBJECT-TYPE
    SYNTAX          SonusAdminState
    ACCESS          read-write
    STATUS          mandatory
    DESCRIPTION     
            "For LS ans GS, determines if line side answer supervision is supported."
    DEFVAL          { disabled }
    ::= { sonusCasSvcGrpProfileAdmnEntry 38 }

sonusCassgSvcGrpProfileRxSeizeRingTime OBJECT-TYPE
    SYNTAX          INTEGER (20..2000)
    ACCESS          read-write
    STATUS          mandatory
    DESCRIPTION     
            "For LS and GS, time in milliseconds before a seizure is detected (LC for LS FXO, RG for GS FXO, Ring for FXS)."
    DEFVAL          { 150 }
    ::= { sonusCasSvcGrpProfileAdmnEntry 39 }

sonusCassgSvcGrpProfileRxFxsAnswerTime OBJECT-TYPE
    SYNTAX          INTEGER (20..2000)
    ACCESS          read-write
    STATUS          mandatory
    DESCRIPTION     
            "For LS and GS FXS, time in milliseconds before an answer is detected."
    DEFVAL          { 100 }
    ::= { sonusCasSvcGrpProfileAdmnEntry 40 }

sonusCassgSvcGrpProfileRxFxsDiscTime OBJECT-TYPE
    SYNTAX          INTEGER (100..2000)
    ACCESS          read-write
    STATUS          mandatory
    DESCRIPTION     
            "For LS and GS FXS, time in milliseconds before a disconnect is detected."
    DEFVAL          { 600 }
    ::= { sonusCasSvcGrpProfileAdmnEntry 41 }

sonusCassgSvcGrpProfileRxLsFxsRingCess OBJECT-TYPE
    SYNTAX          INTEGER (100..30000)
    ACCESS          read-write
    STATUS          mandatory
    DESCRIPTION     
            "For LS FXS, time in milliseconds before ring cessation is detected."
    DEFVAL          { 8000 }
    ::= { sonusCasSvcGrpProfileAdmnEntry 42 }

sonusCassgSvcGrpProfileTxLsFxoDiscTime OBJECT-TYPE
    SYNTAX          INTEGER (0..2000)
    ACCESS          read-write
    STATUS          mandatory
    DESCRIPTION     
            "For LS FXO, time in milliseconds that the LCFO disconnect signal is sent."
    DEFVAL          { 800 }
    ::= { sonusCasSvcGrpProfileAdmnEntry 43 }

sonusCassgSvcGrpProfileTxFxoRingOnTime OBJECT-TYPE
    SYNTAX          INTEGER (100..10000)
    ACCESS          read-write
    STATUS          mandatory
    DESCRIPTION     
            "For LS and GS FXO, time in milliseconds that the ring on signal is sent."
    DEFVAL          { 2000 }
    ::= { sonusCasSvcGrpProfileAdmnEntry 44 }

sonusCassgSvcGrpProfileTxFxoRingOffTime OBJECT-TYPE
    SYNTAX          INTEGER (100..10000)
    ACCESS          read-write
    STATUS          mandatory
    DESCRIPTION     
            "For LS and GS FXO, time in milliseconds that the ring off signal is sent."
    DEFVAL          { 4000 }
    ::= { sonusCasSvcGrpProfileAdmnEntry 45 }

sonusCassgSvcGrpProfileAnsSupervisionTimeout OBJECT-TYPE
    SYNTAX          INTEGER (0..1000)
    ACCESS          read-write
    STATUS          mandatory
    DESCRIPTION     
            "This is the time from egress call setup to egress receiving an answer used
             by the wait answer SSP."
    DEFVAL          { 0 }
    ::= { sonusCasSvcGrpProfileAdmnEntry 47 }

sonusCassgSvcGrpProfileCrankBackProfile OBJECT-TYPE
    SYNTAX          INTEGER (0..20)
    ACCESS          read-write
    STATUS          mandatory
    DESCRIPTION     
            "The Crank Back Profile to be used for this service."
    DEFVAL          { 1 }
    ::= { sonusCasSvcGrpProfileAdmnEntry 48 }

sonusCassgSvcGrpProfileANUMLength OBJECT-TYPE
    SYNTAX          INTEGER (0..30)
    ACCESS          read-write
    STATUS          mandatory
    DESCRIPTION     
            "For R2, determines the length of transmitted calling party number.
             A value of 0 implies variable length terminated by an end of digits signal.
             Otherwise, the value specifies the fixed length of the calling party number."
    DEFVAL          { 0 }
    ::= { sonusCasSvcGrpProfileAdmnEntry 49 }

sonusCassgSvcGrpProfileTxR2EndDigit OBJECT-TYPE
    SYNTAX          INTEGER { r2Signal15(8), r2Signal14(9), 
                        r2Signal13(10), r2Signal12(11), r2Signal11(12) }
    ACCESS          read-write
    STATUS          mandatory
    DESCRIPTION     
            "For R2, specifies the transmit end of digits signal."
    DEFVAL          { r2Signal15 }
    ::= { sonusCasSvcGrpProfileAdmnEntry 50 }

sonusCassgSvcGrpProfileRxR2SeizeTime OBJECT-TYPE
    SYNTAX          INTEGER (20..2000)
    ACCESS          read-write
    STATUS          mandatory
    DESCRIPTION     
            "For R2, duration that a seize signal must be present before it is considered a valid signal."
    DEFVAL          { 20 }
    ::= { sonusCasSvcGrpProfileAdmnEntry 51 }

sonusCassgSvcGrpProfileRxR2SeizeAckTime OBJECT-TYPE
    SYNTAX          INTEGER (20..2000)
    ACCESS          read-write
    STATUS          mandatory
    DESCRIPTION     
            "For R2, duration that a seize ack signal must be present before it is considered a valid signal."
    DEFVAL          { 20 }
    ::= { sonusCasSvcGrpProfileAdmnEntry 52 }

sonusCassgSvcGrpProfileRxR2AnswerTime OBJECT-TYPE
    SYNTAX          INTEGER (20..2000)
    ACCESS          read-write
    STATUS          mandatory
    DESCRIPTION     
            "For R2, duration that an answer signal must be present before it is considered a valid signal."
    DEFVAL          { 20 }
    ::= { sonusCasSvcGrpProfileAdmnEntry 53 }

sonusCassgSvcGrpProfileRxR2ClearBackTime OBJECT-TYPE
    SYNTAX          INTEGER (20..2000)
    ACCESS          read-write
    STATUS          mandatory
    DESCRIPTION     
            "For R2, duration that a clear back signal must be present before it is considered a valid signal."
    DEFVAL          { 20 }
    ::= { sonusCasSvcGrpProfileAdmnEntry 54 }

sonusCassgSvcGrpProfileRxR2ClearFwdTime OBJECT-TYPE
    SYNTAX          INTEGER (20..2000)
    ACCESS          read-write
    STATUS          mandatory
    DESCRIPTION     
            "For R2, duration that a clear forward signal must be present before it is considered a valid signal."
    DEFVAL          { 20 }
    ::= { sonusCasSvcGrpProfileAdmnEntry 55 }

sonusCassgSvcGrpProfileRxR2IdleBackTime OBJECT-TYPE
    SYNTAX          INTEGER (20..2000)
    ACCESS          read-write
    STATUS          mandatory
    DESCRIPTION     
            "For R2, duration that an idle back signal must be present before it is considered a valid signal."
    DEFVAL          { 20 }
    ::= { sonusCasSvcGrpProfileAdmnEntry 56 }

sonusCassgSvcGrpProfileRxR2BlockTime OBJECT-TYPE
    SYNTAX          INTEGER (20..2000)
    ACCESS          read-write
    STATUS          mandatory
    DESCRIPTION     
            "For R2, duration that a block signal must be present before it is considered a valid signal."
    DEFVAL          { 20 }
    ::= { sonusCasSvcGrpProfileAdmnEntry 57 }

sonusCassgSvcGrpProfileCongRelTimeout OBJECT-TYPE
    SYNTAX          INTEGER (0..5)
    ACCESS          read-write
    STATUS          mandatory
    DESCRIPTION     
            "Time to delay sending of release during congestion."
    DEFVAL          { 0 }
    ::= { sonusCasSvcGrpProfileAdmnEntry 58 }

sonusCassgSvcGrpProfileLdcTimeout OBJECT-TYPE
    SYNTAX          INTEGER (0..2880)
    ACCESS          read-write
    STATUS          mandatory
    DESCRIPTION     
            "The timeout value of the long duration call timer in minutes.
             Allowed values are 0 to disable the timer, 60-2880 minutes to set the timer."
    DEFVAL          { 0 }
    ::= { sonusCasSvcGrpProfileAdmnEntry 59 }

sonusCassgSvcGrpProfileLdcAction OBJECT-TYPE
    SYNTAX          INTEGER { noAction(0), trap(1), release(2), 
                        trapAndRelease(3) }
    ACCESS          read-write
    STATUS          mandatory
    DESCRIPTION     
            "This is the action to take if the long duration call timer
             expires.  The call may be released or a trap fired, or both."
    DEFVAL          { noAction }
    ::= { sonusCasSvcGrpProfileAdmnEntry 60 }

sonusCassgSvcGrpProfileLdcRelCause OBJECT-TYPE
    SYNTAX          INTEGER (1..127)
    ACCESS          read-write
    STATUS          mandatory
    DESCRIPTION     
            "The Q.850 release value to use should the call be released 
             due to long duration call timer expiry"
    DEFVAL          { 41 }
    ::= { sonusCasSvcGrpProfileAdmnEntry 61 }

sonusCassgSvcGrpProfileLdcEmergencyCalls OBJECT-TYPE
    SYNTAX          INTEGER { include(0), exclude(1) }
    ACCESS          read-write
    STATUS          mandatory
    DESCRIPTION     
            "Whether Emergency Calls should be excluded from 
             or included in Long Duration Call procedures"
    DEFVAL          { exclude }
    ::= { sonusCasSvcGrpProfileAdmnEntry 62 }

sonusCassgSvcGrpProfileTxOsiTime OBJECT-TYPE
    SYNTAX          INTEGER (150..300)
    ACCESS          read-write
    STATUS          mandatory
    DESCRIPTION     
            "For Visual Message Waiting Indicator, time in milliseconds that the OSI signal is sent."
    DEFVAL          { 200 }
    ::= { sonusCasSvcGrpProfileAdmnEntry 63 }

sonusCassgSvcGrpProfileCwCidSSP OBJECT-TYPE
    SYNTAX          SonusNameReference
    ACCESS          read-write
    STATUS          mandatory
    DESCRIPTION     
            "The SSP which defines the protocol for call waiting caller id."
    ::= { sonusCasSvcGrpProfileAdmnEntry 64 }

sonusCassgSvcGrpProfileSkipCrankBackProfile OBJECT-TYPE
    SYNTAX          Gauge (0..20)
    ACCESS          read-write
    STATUS          mandatory
    DESCRIPTION     
            "The SKIP Crankback Profile to be used for this service."
    DEFVAL          { 0 }
    ::= { sonusCasSvcGrpProfileAdmnEntry 67 }

sonusCasChannelAdmnTable OBJECT-TYPE
    SYNTAX          SEQUENCE OF SonusCasChannelAdmnEntry
    ACCESS          not-accessible
    STATUS          mandatory
    DESCRIPTION     
            ""
    ::= { sonusCasMIBObjects 3 }

sonusCasChannelAdmnEntry OBJECT-TYPE
    SYNTAX          SonusCasChannelAdmnEntry
    ACCESS          not-accessible
    STATUS          mandatory
    DESCRIPTION     
            ""
    INDEX           { sonusCassgChannelServiceIndex, 
                      sonusCassgChannelShelfIndex, 
                      sonusCassgChannelSlotIndex, 
                      sonusCassgChannelPortIndex, 
                      sonusCassgChannelDs3Index, 
                      sonusCassgChannelDs1Index, sonusCassgChannelIndex }
    ::= { sonusCasChannelAdmnTable 1 }

SonusCasChannelAdmnEntry ::=
    SEQUENCE {
        sonusCassgChannelServiceIndex   INTEGER,
        sonusCassgChannelShelfIndex     SonusShelfIndex,
        sonusCassgChannelSlotIndex      SonusSlotIndex,
        sonusCassgChannelPortIndex      INTEGER,
        sonusCassgChannelDs3Index       INTEGER,
        sonusCassgChannelDs1Index       INTEGER,
        sonusCassgChannelIndex          INTEGER,
        sonusCassgChannelCircuitProfileName   SonusNameReference,
        sonusCassgChannelDirection      INTEGER,
        sonusCassgChannelMode           SonusServiceState,
        sonusCassgChannelAction         SonusAdminAction,
        sonusCassgChannelTimeout        INTEGER,
        sonusCassgChannelAdminState     SonusAdminState,
        sonusCassgChannelRowStatus      RowStatus,
        sonusCassgChannelTrunkMember    INTEGER
    }

sonusCassgChannelServiceIndex OBJECT-TYPE
    SYNTAX          INTEGER
    ACCESS          read-only
    STATUS          mandatory
    DESCRIPTION     
            "The index of the CAS Service Group in which the channel is contained"
    ::= { sonusCasChannelAdmnEntry 1 }

sonusCassgChannelShelfIndex OBJECT-TYPE
    SYNTAX          SonusShelfIndex
    ACCESS          read-only
    STATUS          mandatory
    DESCRIPTION     
            "The shelf in which the channel is contained"
    ::= { sonusCasChannelAdmnEntry 2 }

sonusCassgChannelSlotIndex OBJECT-TYPE
    SYNTAX          SonusSlotIndex
    ACCESS          read-only
    STATUS          mandatory
    DESCRIPTION     
            "The slot in which the channel is contained"
    ::= { sonusCasChannelAdmnEntry 3 }

sonusCassgChannelPortIndex OBJECT-TYPE
    SYNTAX          INTEGER
    ACCESS          read-only
    STATUS          mandatory
    DESCRIPTION     
            "The port in which the channel is contained"
    ::= { sonusCasChannelAdmnEntry 4 }

sonusCassgChannelDs3Index OBJECT-TYPE
    SYNTAX          INTEGER
    ACCESS          read-only
    STATUS          mandatory
    DESCRIPTION     
            "The DS3 in which the channel is contained"
    ::= { sonusCasChannelAdmnEntry 5 }

sonusCassgChannelDs1Index OBJECT-TYPE
    SYNTAX          INTEGER
    ACCESS          read-only
    STATUS          mandatory
    DESCRIPTION     
            "The DS1 in which the channel is contained"
    ::= { sonusCasChannelAdmnEntry 6 }

sonusCassgChannelIndex OBJECT-TYPE
    SYNTAX          INTEGER (1..32)
    ACCESS          read-only
    STATUS          mandatory
    DESCRIPTION     
            "The relative channel number within the port"
    ::= { sonusCasChannelAdmnEntry 7 }

sonusCassgChannelCircuitProfileName OBJECT-TYPE
    SYNTAX          SonusNameReference
    ACCESS          read-write
    STATUS          mandatory
    DESCRIPTION     
            "Name reference to the circuit profile"
    ::= { sonusCasChannelAdmnEntry 8 }

sonusCassgChannelDirection OBJECT-TYPE
    SYNTAX          INTEGER { twoWay(1), oneWayIn(2), oneWayOut(3) }
    ACCESS          read-write
    STATUS          mandatory
    DESCRIPTION     
            "Direction of call traffic allowed on the channel"
    DEFVAL          { twoWay }
    ::= { sonusCasChannelAdmnEntry 9 }

sonusCassgChannelMode OBJECT-TYPE
    SYNTAX          SonusServiceState
    ACCESS          read-write
    STATUS          mandatory
    DESCRIPTION     
            "The mode of operation of the channel"
    DEFVAL          { inService }
    ::= { sonusCasChannelAdmnEntry 10 }

sonusCassgChannelAction OBJECT-TYPE
    SYNTAX          SonusAdminAction
    ACCESS          read-write
    STATUS          mandatory
    DESCRIPTION     
            "The action taken on the channel"
    DEFVAL          { dryUp }
    ::= { sonusCasChannelAdmnEntry 11 }

sonusCassgChannelTimeout OBJECT-TYPE
    SYNTAX          INTEGER (1..1440)
    ACCESS          read-write
    STATUS          mandatory
    DESCRIPTION     
            "The timeout in minutes for dryup action on the channel"
    ::= { sonusCasChannelAdmnEntry 12 }

sonusCassgChannelAdminState OBJECT-TYPE
    SYNTAX          SonusAdminState
    ACCESS          read-write
    STATUS          mandatory
    DESCRIPTION     
            "The administrative state of the object.  The object must
             be disabled in order to modify other objects in this row."
    DEFVAL          { disabled }
    ::= { sonusCasChannelAdmnEntry 13 }

sonusCassgChannelRowStatus OBJECT-TYPE
    SYNTAX          RowStatus
    ACCESS          read-write
    STATUS          mandatory
    DESCRIPTION     
            ""
    ::= { sonusCasChannelAdmnEntry 14 }

sonusCassgChannelTrunkMember OBJECT-TYPE
    SYNTAX          INTEGER (0..65536)
    ACCESS          read-write
    STATUS          mandatory
    DESCRIPTION     
            "Identifies the Trunk Member number assigned to the channel.
             The value 65536 indicates no trunk member number is assigned. "
    DEFVAL          { 65536 }
    ::= { sonusCasChannelAdmnEntry 15 }

sonusCasChannelStatTable OBJECT-TYPE
    SYNTAX          SEQUENCE OF SonusCasChannelStatEntry
    ACCESS          not-accessible
    STATUS          mandatory
    DESCRIPTION     
            ""
    ::= { sonusCasMIBObjects 4 }

sonusCasChannelStatEntry OBJECT-TYPE
    SYNTAX          SonusCasChannelStatEntry
    ACCESS          not-accessible
    STATUS          mandatory
    DESCRIPTION     
            ""
    INDEX           { sonusCassgChannelStatServiceIndex, 
                      sonusCassgChannelStatShelfIndex, 
                      sonusCassgChannelStatSlotIndex, 
                      sonusCassgChannelStatPortIndex, 
                      sonusCassgChannelStatIndex }
    ::= { sonusCasChannelStatTable 1 }

SonusCasChannelStatEntry ::=
    SEQUENCE {
        sonusCassgChannelStatServiceIndex INTEGER,
        sonusCassgChannelStatShelfIndex SonusShelfIndex,
        sonusCassgChannelStatSlotIndex  SonusSlotIndex,
        sonusCassgChannelStatPortIndex  INTEGER,
        sonusCassgChannelStatIndex      INTEGER,
        sonusCassgChannelStatUsage      INTEGER,
        sonusCassgChannelStatLocalMaint INTEGER,
        sonusCassgChannelStatLocalHw    INTEGER,
        sonusCassgChannelStatRemoteMaint INTEGER,
        sonusCassgChannelStatIngressAttempts    INTEGER,
        sonusCassgChannelStatIngressFailures    INTEGER,
        sonusCassgChannelStatEgressAttempts   INTEGER,
        sonusCassgChannelStatEgressFailures   INTEGER,
        sonusCassgChannelStatMakeBusyFailures     INTEGER,
        sonusCassgChannelStatIngressCompletions       INTEGER,
        sonusCassgChannelStatEgressCompletions      INTEGER
    }

sonusCassgChannelStatServiceIndex OBJECT-TYPE
    SYNTAX          INTEGER
    ACCESS          read-only
    STATUS          mandatory
    DESCRIPTION     
            "The index of the CAS Service Group in which the channel is contained"
    ::= { sonusCasChannelStatEntry 1 }

sonusCassgChannelStatShelfIndex OBJECT-TYPE
    SYNTAX          SonusShelfIndex
    ACCESS          read-only
    STATUS          mandatory
    DESCRIPTION     
            "The shelf in which the channel is contained"
    ::= { sonusCasChannelStatEntry 2 }

sonusCassgChannelStatSlotIndex OBJECT-TYPE
    SYNTAX          SonusSlotIndex
    ACCESS          read-only
    STATUS          mandatory
    DESCRIPTION     
            "The slot in which the channel is contained"
    ::= { sonusCasChannelStatEntry 3 }

sonusCassgChannelStatPortIndex OBJECT-TYPE
    SYNTAX          INTEGER
    ACCESS          read-only
    STATUS          mandatory
    DESCRIPTION     
            "The port in which the channel is contained"
    ::= { sonusCasChannelStatEntry 4 }

sonusCassgChannelStatIndex OBJECT-TYPE
    SYNTAX          INTEGER
    ACCESS          read-only
    STATUS          mandatory
    DESCRIPTION     
            "The relative channel number within the por"
    ::= { sonusCasChannelStatEntry 5 }

sonusCassgChannelStatUsage OBJECT-TYPE
    SYNTAX          INTEGER { unequipped(1), idle(2), inBusy(3), 
                        outBusy(4), transientSetup(5), 
                        transientRelease(6) }
    ACCESS          read-only
    STATUS          mandatory
    DESCRIPTION     
            "The usage state of the channel"
    ::= { sonusCasChannelStatEntry 6 }

sonusCassgChannelStatLocalMaint OBJECT-TYPE
    SYNTAX          INTEGER { outOfServiceManual(1), outOfServiceAuto(2), 
                        inService(3), outOfServiceMgc(4) }
    ACCESS          read-only
    STATUS          mandatory
    DESCRIPTION     
            "The local maintenance state of the channel"
    ::= { sonusCasChannelStatEntry 7 }

sonusCassgChannelStatLocalHw OBJECT-TYPE
    SYNTAX          INTEGER { outOfService(1), inService(2) }
    ACCESS          read-only
    STATUS          mandatory
    DESCRIPTION     
            "The local hardware state of the channel"
    ::= { sonusCasChannelStatEntry 8 }

sonusCassgChannelStatRemoteMaint OBJECT-TYPE
    SYNTAX          INTEGER { outOfService(1), inService(2) }
    ACCESS          read-only
    STATUS          mandatory
    DESCRIPTION     
            "The remote status of the channel"
    ::= { sonusCasChannelStatEntry 9 }

sonusCassgChannelStatIngressAttempts OBJECT-TYPE
    SYNTAX          INTEGER
    ACCESS          read-only
    STATUS          mandatory
    DESCRIPTION     
            "The number of incoming call attempts"
    ::= { sonusCasChannelStatEntry 10 }

sonusCassgChannelStatIngressFailures OBJECT-TYPE
    SYNTAX          INTEGER
    ACCESS          read-only
    STATUS          mandatory
    DESCRIPTION     
            "The number of incoming call failures"
    ::= { sonusCasChannelStatEntry 11 }

sonusCassgChannelStatEgressAttempts OBJECT-TYPE
    SYNTAX          INTEGER
    ACCESS          read-only
    STATUS          mandatory
    DESCRIPTION     
            "The number of outgoing call attempts"
    ::= { sonusCasChannelStatEntry 12 }

sonusCassgChannelStatEgressFailures OBJECT-TYPE
    SYNTAX          INTEGER
    ACCESS          read-only
    STATUS          mandatory
    DESCRIPTION     
            "The number of outgoing call failures"
    ::= { sonusCasChannelStatEntry 13 }

sonusCassgChannelStatMakeBusyFailures OBJECT-TYPE
    SYNTAX          INTEGER
    ACCESS          read-only
    STATUS          mandatory
    DESCRIPTION     
            "The number of failures which are considered in the auto busy threshold processing"
    ::= { sonusCasChannelStatEntry 14 }

sonusCassgChannelStatIngressCompletions OBJECT-TYPE
    SYNTAX          INTEGER
    ACCESS          read-only
    STATUS          mandatory
    DESCRIPTION     
            "The number of incoming calls which have completed the Ingress SSP"
    ::= { sonusCasChannelStatEntry 15 }

sonusCassgChannelStatEgressCompletions OBJECT-TYPE
    SYNTAX          INTEGER
    ACCESS          read-only
    STATUS          mandatory
    DESCRIPTION     
            "The number of outgoing calls which have completed the Egress SSP"
    ::= { sonusCasChannelStatEntry 16 }

sonusCasCollectionProfileAdmn OBJECT IDENTIFIER
    ::= { sonusCasMIBObjects 5 }

sonusCasCollectionProfileNextIndex OBJECT-TYPE
    SYNTAX          INTEGER
    ACCESS          read-only
    STATUS          mandatory
    DESCRIPTION     
            "The next valid index to use when creating a new sonusCasCollectionProfileAdmnEntry"
    ::= { sonusCasCollectionProfileAdmn 1 }

sonusCasCollectionProfileAdmnTable OBJECT-TYPE
    SYNTAX          SEQUENCE OF SonusCasCollectionProfileAdmnEntry
    ACCESS          not-accessible
    STATUS          mandatory
    DESCRIPTION     
            ""
    ::= { sonusCasCollectionProfileAdmn 2 }

sonusCasCollectionProfileAdmnEntry OBJECT-TYPE
    SYNTAX          SonusCasCollectionProfileAdmnEntry
    ACCESS          not-accessible
    STATUS          mandatory
    DESCRIPTION     
            ""
    INDEX           { sonusCassgCollectProfileIndex }
    ::= { sonusCasCollectionProfileAdmnTable 1 }

SonusCasCollectionProfileAdmnEntry ::=
    SEQUENCE {
        sonusCassgCollectProfileIndex   INTEGER,
        sonusCassgCollectProfileName    SonusName,
        sonusCassgCollectProfileCollectId INTEGER,
        sonusCassgCollectProfileCollectType   INTEGER,
        sonusCassgCollectProfileMinDigits INTEGER,
        sonusCassgCollectProfileMaxDigits INTEGER,
        sonusCassgCollectProfileFirstDigitTime      INTEGER,
        sonusCassgCollectProfileInterDigitTime      INTEGER,
        sonusCassgCollectProfileFieldTime INTEGER,
        sonusCassgCollectProfileTermDigit INTEGER,
        sonusCassgCollectProfileRestartDigit    DisplayString,
        sonusCassgCollectProfileReinputDigit    DisplayString,
        sonusCassgCollectProfileReportDigits    INTEGER,
        sonusCassgCollectProfileFirstDigitQuiet       SonusAdminState,
        sonusCassgCollectProfileAnnouncementPrompt          INTEGER,
        sonusCassgCollectProfileTonePrompt  DisplayString,
        sonusCassgCollectProfileRowStatus RowStatus,
        sonusCassgCollectProfileAppendDigits    SonusAdminState,
        sonusCassgCollectProfileAckSig1 INTEGER,
        sonusCassgCollectProfileAckSig2 INTEGER
    }

sonusCassgCollectProfileIndex OBJECT-TYPE
    SYNTAX          INTEGER
    ACCESS          read-only
    STATUS          mandatory
    DESCRIPTION     
            "The index of the collection profile"
    ::= { sonusCasCollectionProfileAdmnEntry 1 }

sonusCassgCollectProfileName OBJECT-TYPE
    SYNTAX          SonusName
    ACCESS          read-write
    STATUS          mandatory
    DESCRIPTION     
            "The name of the collection profile"
    ::= { sonusCasCollectionProfileAdmnEntry 2 }

sonusCassgCollectProfileCollectId OBJECT-TYPE
    SYNTAX          INTEGER { calledParty(1), callingParty(2), ani(3), 
                        iani(4), iiani(5), dnis(6), carrierId(7), 
                        internationalCountryCode(8), 
                        callingPartyCategory(9), chargeCategory(10), 
                        subscriberStatus(11), fgdStageOne(12), 
                        countryCodeIndicator(13), langDiscIndicator(14), 
                        natureOfConn(15), echoSupIndicator(16) }
    ACCESS          read-write
    STATUS          mandatory
    DESCRIPTION     
            "Identifies the collection and where to store digits"
    DEFVAL          { calledParty }
    ::= { sonusCasCollectionProfileAdmnEntry 3 }

sonusCassgCollectProfileCollectType OBJECT-TYPE
    SYNTAX          INTEGER { dtmf(1), mf(2), mfcr2(3) }
    ACCESS          read-write
    STATUS          mandatory
    DESCRIPTION     
            "Type of digits to be collected"
    DEFVAL          { dtmf }
    ::= { sonusCasCollectionProfileAdmnEntry 4 }

sonusCassgCollectProfileMinDigits OBJECT-TYPE
    SYNTAX          INTEGER (0..30)
    ACCESS          read-write
    STATUS          mandatory
    DESCRIPTION     
            "Minimum number of digits to collect"
    DEFVAL          { 0 }
    ::= { sonusCasCollectionProfileAdmnEntry 5 }

sonusCassgCollectProfileMaxDigits OBJECT-TYPE
    SYNTAX          INTEGER (1..30)
    ACCESS          read-write
    STATUS          mandatory
    DESCRIPTION     
            "Maximum number of digits to collect"
    DEFVAL          { 1 }
    ::= { sonusCasCollectionProfileAdmnEntry 6 }

sonusCassgCollectProfileFirstDigitTime OBJECT-TYPE
    SYNTAX          INTEGER (0..30000)
    ACCESS          read-write
    STATUS          mandatory
    DESCRIPTION     
            "Duration in milliseconds to allow for the first digit"
    DEFVAL          { 0 }
    ::= { sonusCasCollectionProfileAdmnEntry 7 }

sonusCassgCollectProfileInterDigitTime OBJECT-TYPE
    SYNTAX          INTEGER (0..30000)
    ACCESS          read-write
    STATUS          mandatory
    DESCRIPTION     
            "Duration in milliseconds allowed between digits"
    DEFVAL          { 0 }
    ::= { sonusCasCollectionProfileAdmnEntry 8 }

sonusCassgCollectProfileFieldTime OBJECT-TYPE
    SYNTAX          INTEGER (0..30000)
    ACCESS          read-write
    STATUS          mandatory
    DESCRIPTION     
            "The duration in milliseconds allowed for the complete collection"
    DEFVAL          { 0 }
    ::= { sonusCasCollectionProfileAdmnEntry 9 }

sonusCassgCollectProfileTermDigit OBJECT-TYPE
    SYNTAX          INTEGER { none(1), star(2), pound(3), dtmfA(4), 
                        dtmfB(5), dtmfC(6), dtmfD(7), r2Signal15(8), 
                        r2Signal14(9), r2Signal13(10), r2Signal12(11), 
                        r2Signal11(12) }
    ACCESS          read-write
    STATUS          mandatory
    DESCRIPTION     
            "Specifies a digit to terminate a DTMF or R2 collection"
    DEFVAL          { none }
    ::= { sonusCasCollectionProfileAdmnEntry 10 }

sonusCassgCollectProfileRestartDigit OBJECT-TYPE
    SYNTAX          DisplayString (SIZE(0..3))
    ACCESS          read-write
    STATUS          mandatory
    DESCRIPTION     
            "Specifies a digit sequence which will restart the collection and announcement prompt"
    ::= { sonusCasCollectionProfileAdmnEntry 11 }

sonusCassgCollectProfileReinputDigit OBJECT-TYPE
    SYNTAX          DisplayString (SIZE(0..3))
    ACCESS          read-write
    STATUS          mandatory
    DESCRIPTION     
            "Specifies a digit sequence which will restart the collection but not the announcement"
    ::= { sonusCasCollectionProfileAdmnEntry 12 }

sonusCassgCollectProfileReportDigits OBJECT-TYPE
    SYNTAX          INTEGER (0..23)
    ACCESS          read-write
    STATUS          mandatory
    DESCRIPTION     
            ""
    DEFVAL          { 0 }
    ::= { sonusCasCollectionProfileAdmnEntry 13 }

sonusCassgCollectProfileFirstDigitQuiet OBJECT-TYPE
    SYNTAX          SonusAdminState
    ACCESS          read-write
    STATUS          mandatory
    DESCRIPTION     
            "Determines if announcement should be terminated when the first digit is entered"
    DEFVAL          { disabled }
    ::= { sonusCasCollectionProfileAdmnEntry 14 }

sonusCassgCollectProfileAnnouncementPrompt OBJECT-TYPE
    SYNTAX          INTEGER (0..65535)
    ACCESS          read-write
    STATUS          mandatory
    DESCRIPTION     
            "Numeric identifier for the announcement"
    DEFVAL          { 0 }
    ::= { sonusCasCollectionProfileAdmnEntry 15 }

sonusCassgCollectProfileTonePrompt OBJECT-TYPE
    SYNTAX          DisplayString (SIZE(0..23))
    ACCESS          read-write
    STATUS          mandatory
    DESCRIPTION     
            "Named reference to the tone prompt"
    ::= { sonusCasCollectionProfileAdmnEntry 16 }

sonusCassgCollectProfileRowStatus OBJECT-TYPE
    SYNTAX          RowStatus
    ACCESS          read-write
    STATUS          mandatory
    DESCRIPTION     
            ""
    ::= { sonusCasCollectionProfileAdmnEntry 17 }

sonusCassgCollectProfileAppendDigits OBJECT-TYPE
    SYNTAX          SonusAdminState
    ACCESS          read-write
    STATUS          mandatory
    DESCRIPTION     
            "Determines if digits are appended to the requested field or overwrite it."
    DEFVAL          { disabled }
    ::= { sonusCasCollectionProfileAdmnEntry 18 }

sonusCassgCollectProfileAckSig1 OBJECT-TYPE
    SYNTAX          INTEGER (0..15)
    ACCESS          read-write
    STATUS          mandatory
    DESCRIPTION     
            "For R2 collections, specifies the backward signal to send up thru the last digit."
    DEFVAL          { 1 }
    ::= { sonusCasCollectionProfileAdmnEntry 19 }

sonusCassgCollectProfileAckSig2 OBJECT-TYPE
    SYNTAX          INTEGER (0..15)
    ACCESS          read-write
    STATUS          mandatory
    DESCRIPTION     
            "For R2 collections, specifies the backward signal to send after the last digit."
    DEFVAL          { 1 }
    ::= { sonusCasCollectionProfileAdmnEntry 20 }

sonusCasSspGroupAdmn OBJECT IDENTIFIER
    ::= { sonusCasMIBObjects 6 }

sonusCasSspNextIndex OBJECT-TYPE
    SYNTAX          INTEGER
    ACCESS          read-only
    STATUS          mandatory
    DESCRIPTION     
            "The next valid index to use when creating a new sonusCasSspGroupAdmnEntry"
    ::= { sonusCasSspGroupAdmn 1 }

sonusCasSspAdmnTable OBJECT-TYPE
    SYNTAX          SEQUENCE OF SonusCasSspAdmnEntry
    ACCESS          not-accessible
    STATUS          mandatory
    DESCRIPTION     
            ""
    ::= { sonusCasSspGroupAdmn 2 }

sonusCasSspAdmnEntry OBJECT-TYPE
    SYNTAX          SonusCasSspAdmnEntry
    ACCESS          not-accessible
    STATUS          mandatory
    DESCRIPTION     
            ""
    INDEX           { sonusCassgSigSeqProfileIndex }
    ::= { sonusCasSspAdmnTable 1 }

SonusCasSspAdmnEntry ::=
    SEQUENCE {
        sonusCassgSigSeqProfileIndex    INTEGER,
        sonusCassgSigSeqProfileName     SonusName,
        sonusCassgSigSeqProfileRowStatus RowStatus
    }

sonusCassgSigSeqProfileIndex OBJECT-TYPE
    SYNTAX          INTEGER
    ACCESS          read-only
    STATUS          mandatory
    DESCRIPTION     
            "The index of the SSP"
    ::= { sonusCasSspAdmnEntry 1 }

sonusCassgSigSeqProfileName OBJECT-TYPE
    SYNTAX          SonusName
    ACCESS          read-write
    STATUS          mandatory
    DESCRIPTION     
            "Name of the SSP"
    ::= { sonusCasSspAdmnEntry 2 }

sonusCassgSigSeqProfileRowStatus OBJECT-TYPE
    SYNTAX          RowStatus
    ACCESS          read-write
    STATUS          mandatory
    DESCRIPTION     
            ""
    ::= { sonusCasSspAdmnEntry 3 }

sonusCasSignalSeqAdmnTable OBJECT-TYPE
    SYNTAX          SEQUENCE OF SonusCasSignalSeqAdmnEntry
    ACCESS          not-accessible
    STATUS          mandatory
    DESCRIPTION     
            ""
    ::= { sonusCasMIBObjects 7 }

sonusCasSignalSeqAdmnEntry OBJECT-TYPE
    SYNTAX          SonusCasSignalSeqAdmnEntry
    ACCESS          not-accessible
    STATUS          mandatory
    DESCRIPTION     
            ""
    INDEX           { sonusCassgSigSequenceProfileIndex, 
                      sonusCassgSigSequenceIndex }
    ::= { sonusCasSignalSeqAdmnTable 1 }

SonusCasSignalSeqAdmnEntry ::=
    SEQUENCE {
        sonusCassgSigSequenceProfileIndex INTEGER,
        sonusCassgSigSequenceIndex      INTEGER,
        sonusCassgSigSequencePosition   INTEGER,
        sonusCassgSigSequenceToken      INTEGER,
        sonusCassgSigSequenceParam1     DisplayString,
        sonusCassgSigSequenceParam2     DisplayString,
        sonusCassgSigSequenceSigCondProfileName       SonusNameReference,
        sonusCassgSigSequenceAdminState SonusAdminState,
        sonusCassgSigSequenceRowStatus  RowStatus
    }

sonusCassgSigSequenceProfileIndex OBJECT-TYPE
    SYNTAX          INTEGER
    ACCESS          read-only
    STATUS          mandatory
    DESCRIPTION     
            "Index of SSP in which the Signal Sequence is contained"
    ::= { sonusCasSignalSeqAdmnEntry 1 }

sonusCassgSigSequenceIndex OBJECT-TYPE
    SYNTAX          INTEGER
    ACCESS          read-only
    STATUS          mandatory
    DESCRIPTION     
            "Index of the Signal Sequence"
    ::= { sonusCasSignalSeqAdmnEntry 2 }

sonusCassgSigSequencePosition OBJECT-TYPE
    SYNTAX          INTEGER (0..31)
    ACCESS          read-write
    STATUS          mandatory
    DESCRIPTION     
            "Relative position of the Signal Sequence"
    DEFVAL          { 0 }
    ::= { sonusCasSignalSeqAdmnEntry 3 }

sonusCassgSigSequenceToken OBJECT-TYPE
    SYNTAX          INTEGER { seize(1), wink(2), flash(3), dialMF(4), 
                        dialDTMF(5), dialDigit(6), playTone(7), 
                        playAnn(8), delay(9), waitWink(10), 
                        waitFlash(11), waitAnswer(12), collectField(13), 
                        collectDigit(14), report(15), clear(16), 
                        exec(17), matchDigits(18), seizeAck(19), 
                        waitSeizeAck(20), mfcFwdTimers(21), dialMFC(22), 
                        dialMFP(23), waitMFP(24), dialIndex(25), 
                        test(26), ring(27), ringGround(28), 
                        tipGround(29), waitTipGround(30), 
                        rxR2Translate(31), txR2Translate(32), 
                        testCgPn(33), testCdPn(34), testOutGw(35), 
                        testOutTg(36), testSlot(37), testChan(38), 
                        testCIC(39), testInTg(40), testOrigCarrier(41), 
                        testOrigCharge(42), testCpc(43), testTmr(44), 
                        testIsupPref(45), testIsdnAccess(46), 
                        testInGw(47), testCddn(48), fsk(49), 
                        waitTone(50) }
    ACCESS          read-write
    STATUS          mandatory
    DESCRIPTION     
            "Signaling action to perform"
    DEFVAL          { seize }
    ::= { sonusCasSignalSeqAdmnEntry 4 }

sonusCassgSigSequenceParam1 OBJECT-TYPE
    SYNTAX          DisplayString (SIZE(0..31))
    ACCESS          read-write
    STATUS          mandatory
    DESCRIPTION     
            "First general parameter field specific to the signaling token"
    ::= { sonusCasSignalSeqAdmnEntry 5 }

sonusCassgSigSequenceParam2 OBJECT-TYPE
    SYNTAX          DisplayString (SIZE(0..31))
    ACCESS          read-write
    STATUS          mandatory
    DESCRIPTION     
            "Second general parameter field specific to the signaling token"
    ::= { sonusCasSignalSeqAdmnEntry 6 }

sonusCassgSigSequenceSigCondProfileName OBJECT-TYPE
    SYNTAX          SonusNameReference
    ACCESS          read-write
    STATUS          mandatory
    DESCRIPTION     
            "Name reference to SCP to execute when an error occurs"
    ::= { sonusCasSignalSeqAdmnEntry 7 }

sonusCassgSigSequenceAdminState OBJECT-TYPE
    SYNTAX          SonusAdminState
    ACCESS          read-write
    STATUS          mandatory
    DESCRIPTION     
            "Admin state of the Signal Sequence"
    DEFVAL          { disabled }
    ::= { sonusCasSignalSeqAdmnEntry 8 }

sonusCassgSigSequenceRowStatus OBJECT-TYPE
    SYNTAX          RowStatus
    ACCESS          read-write
    STATUS          mandatory
    DESCRIPTION     
            ""
    ::= { sonusCasSignalSeqAdmnEntry 9 }

sonusCasScpAdmn OBJECT IDENTIFIER
    ::= { sonusCasMIBObjects 8 }

sonusCasScpNextIndex OBJECT-TYPE
    SYNTAX          INTEGER
    ACCESS          read-only
    STATUS          mandatory
    DESCRIPTION     
            "The next valid index to use when creating a new sonusCasScpAdmnEntry"
    ::= { sonusCasScpAdmn 1 }

sonusCasScpAdmnTable OBJECT-TYPE
    SYNTAX          SEQUENCE OF SonusCasScpAdmnEntry
    ACCESS          not-accessible
    STATUS          mandatory
    DESCRIPTION     
            ""
    ::= { sonusCasScpAdmn 2 }

sonusCasScpAdmnEntry OBJECT-TYPE
    SYNTAX          SonusCasScpAdmnEntry
    ACCESS          not-accessible
    STATUS          mandatory
    DESCRIPTION     
            ""
    INDEX           { sonusCassgSigCondProfileIndex }
    ::= { sonusCasScpAdmnTable 1 }

SonusCasScpAdmnEntry ::=
    SEQUENCE {
        sonusCassgSigCondProfileIndex   INTEGER,
        sonusCassgSigCondProfileName    SonusName,
        sonusCassgSigCondProfileRowStatus RowStatus
    }

sonusCassgSigCondProfileIndex OBJECT-TYPE
    SYNTAX          INTEGER
    ACCESS          read-only
    STATUS          mandatory
    DESCRIPTION     
            "The index of the SCP"
    ::= { sonusCasScpAdmnEntry 1 }

sonusCassgSigCondProfileName OBJECT-TYPE
    SYNTAX          SonusName
    ACCESS          read-write
    STATUS          mandatory
    DESCRIPTION     
            "Name of the SCP"
    ::= { sonusCasScpAdmnEntry 2 }

sonusCassgSigCondProfileRowStatus OBJECT-TYPE
    SYNTAX          RowStatus
    ACCESS          read-write
    STATUS          mandatory
    DESCRIPTION     
            ""
    ::= { sonusCasScpAdmnEntry 3 }

sonusCasSignalCondAdmnTable OBJECT-TYPE
    SYNTAX          SEQUENCE OF SonusCasSignalCondAdmnEntry
    ACCESS          not-accessible
    STATUS          mandatory
    DESCRIPTION     
            ""
    ::= { sonusCasScpAdmn 3 }

sonusCasSignalCondAdmnEntry OBJECT-TYPE
    SYNTAX          SonusCasSignalCondAdmnEntry
    ACCESS          not-accessible
    STATUS          mandatory
    DESCRIPTION     
            ""
    INDEX           { sonusCassgSigConditionProfileIndex, 
                      sonusCassgSigConditionIndex }
    ::= { sonusCasSignalCondAdmnTable 1 }

SonusCasSignalCondAdmnEntry ::=
    SEQUENCE {
        sonusCassgSigConditionProfileIndex  INTEGER,
        sonusCassgSigConditionIndex     INTEGER,
        sonusCassgSigConditionToken     INTEGER,
        sonusCassgSigConditionControl   INTEGER,
        sonusCassgSigConditionParam     DisplayString,
        sonusCassgSigConditionAdminState SonusAdminState,
        sonusCassgSigConditionRowStatus RowStatus
    }

sonusCassgSigConditionProfileIndex OBJECT-TYPE
    SYNTAX          INTEGER
    ACCESS          read-only
    STATUS          mandatory
    DESCRIPTION     
            "Index of the SCP in which the Signal Condition is contained"
    ::= { sonusCasSignalCondAdmnEntry 1 }

sonusCassgSigConditionIndex OBJECT-TYPE
    SYNTAX          INTEGER
    ACCESS          read-only
    STATUS          mandatory
    DESCRIPTION     
            "Index of the Signal Condition"
    ::= { sonusCasSignalCondAdmnEntry 2 }

sonusCassgSigConditionToken OBJECT-TYPE
    SYNTAX          INTEGER { default(1), firstDigitTimeout(2), 
                        interDigitTimeout(3), fieldTimeout(4), 
                        shortCollection(5), unexpectedDigit(6), 
                        rxWink(7), rxFlash(8), rxAnswer(9), 
                        winkTimeout(10), flashTimeout(11), 
                        answerTimeout(12), cutThrough(13), 
                        digitMatch(14), rxSeizeAck(15), 
                        seizeAckTimeout(16), bwdSignalTimeout(17), 
                        maxPulseRx(18), r2Signal1(19), r2Signal2(20), 
                        r2Signal3(21), r2Signal4(22), r2Signal5(23), 
                        r2Signal6(24), r2Signal7(25), r2Signal8(26), 
                        r2Signal9(27), r2Signal10(28), r2Signal11(29), 
                        r2Signal12(30), r2Signal13(31), r2Signal14(32), 
                        r2Signal15(33), rxRing(34), rxRingGround(35), 
                        rxTipGround(36), tipGroundTimeout(37), 
                        toneTimeout(38) }
    ACCESS          read-write
    STATUS          mandatory
    DESCRIPTION     
            "Token which defines error condition which occurred"
    DEFVAL          { default }
    ::= { sonusCasSignalCondAdmnEntry 3 }

sonusCassgSigConditionControl OBJECT-TYPE
    SYNTAX          INTEGER { proceed(1), exec(2), abort(3), abortMB(4) }
    ACCESS          read-write
    STATUS          mandatory
    DESCRIPTION     
            "Defines how processing of the SSP should continue"
    DEFVAL          { proceed }
    ::= { sonusCasSignalCondAdmnEntry 4 }

sonusCassgSigConditionParam OBJECT-TYPE
    SYNTAX          DisplayString (SIZE(0..31))
    ACCESS          read-write
    STATUS          mandatory
    DESCRIPTION     
            "General parameter for Signal Condition specific to token and control"
    ::= { sonusCasSignalCondAdmnEntry 5 }

sonusCassgSigConditionAdminState OBJECT-TYPE
    SYNTAX          SonusAdminState
    ACCESS          read-write
    STATUS          mandatory
    DESCRIPTION     
            "The admin state of the Signal Condition"
    DEFVAL          { disabled }
    ::= { sonusCasSignalCondAdmnEntry 6 }

sonusCassgSigConditionRowStatus OBJECT-TYPE
    SYNTAX          RowStatus
    ACCESS          read-write
    STATUS          mandatory
    DESCRIPTION     
            ""
    ::= { sonusCasSignalCondAdmnEntry 7 }

sonusCasDisconnectTreatAdmnTable OBJECT-TYPE
    SYNTAX          SEQUENCE OF SonusCasDisconnectTreatAdmnEntry
    ACCESS          not-accessible
    STATUS          deprecated
    DESCRIPTION     
            ""
    ::= { sonusCasMIBObjects 9 }

sonusCasDisconnectTreatAdmnEntry OBJECT-TYPE
    SYNTAX          SonusCasDisconnectTreatAdmnEntry
    ACCESS          not-accessible
    STATUS          deprecated
    DESCRIPTION     
            ""
    INDEX           { sonusCassgDiscTreatmentIndex }
    ::= { sonusCasDisconnectTreatAdmnTable 1 }

SonusCasDisconnectTreatAdmnEntry ::=
    SEQUENCE {
        sonusCassgDiscTreatmentIndex    INTEGER,
        sonusCassgDiscTreatmentReason   INTEGER,
        sonusCassgDiscTreatmentSigSeqProfileName        SonusNameReference,
        sonusCassgDiscTreatmentRowStatus RowStatus
    }

sonusCassgDiscTreatmentIndex OBJECT-TYPE
    SYNTAX          INTEGER
    ACCESS          read-only
    STATUS          deprecated
    DESCRIPTION     
            ""
    ::= { sonusCasDisconnectTreatAdmnEntry 1 }

sonusCassgDiscTreatmentReason OBJECT-TYPE
    SYNTAX          INTEGER (0..255)
    ACCESS          read-only
    STATUS          deprecated
    DESCRIPTION     
            ""
    ::= { sonusCasDisconnectTreatAdmnEntry 2 }

sonusCassgDiscTreatmentSigSeqProfileName OBJECT-TYPE
    SYNTAX          SonusNameReference
    ACCESS          read-write
    STATUS          deprecated
    DESCRIPTION     
            ""
    ::= { sonusCasDisconnectTreatAdmnEntry 3 }

sonusCassgDiscTreatmentRowStatus OBJECT-TYPE
    SYNTAX          RowStatus
    ACCESS          read-write
    STATUS          deprecated
    DESCRIPTION     
            ""
    ::= { sonusCasDisconnectTreatAdmnEntry 4 }

sonusCasServiceGroupMIBNotifications OBJECT IDENTIFIER
    ::= { sonusCasMIBObjects 10 }

sonusCasServiceGroupMIBNotificationsPrefix OBJECT IDENTIFIER
    ::= { sonusCasServiceGroupMIBNotifications 0 }

sonusCasServiceGroupMIBNotificationsObjects OBJECT IDENTIFIER
    ::= { sonusCasServiceGroupMIBNotifications 1 }

sonusCasSvcGrpName OBJECT-TYPE
    SYNTAX          DisplayString (SIZE(0..23))
    ACCESS          read-only
    STATUS          mandatory
    DESCRIPTION     
            "Name of the CAS service group."
    ::= { sonusCasServiceGroupMIBNotificationsObjects 1 }

sonusCasR2TransProfileAdmn OBJECT IDENTIFIER
    ::= { sonusCasMIBObjects 11 }

sonusCasR2TransProfileAdmnNextIndex OBJECT-TYPE
    SYNTAX          INTEGER
    ACCESS          read-only
    STATUS          mandatory
    DESCRIPTION     
            "The next valid index to use when creating a new sonusCasR2TransProfileAdmn"
    ::= { sonusCasR2TransProfileAdmn 1 }

sonusCasR2TransProfileAdmnTable OBJECT-TYPE
    SYNTAX          SEQUENCE OF SonusCasR2TransProfileAdmnEntry
    ACCESS          not-accessible
    STATUS          mandatory
    DESCRIPTION     
            "This mib table is used to create a name for an R2 Translation Profile."
    ::= { sonusCasR2TransProfileAdmn 2 }

sonusCasR2TransProfileAdmnEntry OBJECT-TYPE
    SYNTAX          SonusCasR2TransProfileAdmnEntry
    ACCESS          not-accessible
    STATUS          mandatory
    DESCRIPTION     
            ""
    INDEX           { sonusCassgR2TransProfileIndex }
    ::= { sonusCasR2TransProfileAdmnTable 1 }

SonusCasR2TransProfileAdmnEntry ::=
    SEQUENCE {
        sonusCassgR2TransProfileIndex   INTEGER,
        sonusCassgR2TransProfileName    SonusName,
        sonusCassgR2TransProfileRowStatus RowStatus
    }

sonusCassgR2TransProfileIndex OBJECT-TYPE
    SYNTAX          INTEGER
    ACCESS          read-only
    STATUS          mandatory
    DESCRIPTION     
            "The index of the R2 Translation Profile"
    ::= { sonusCasR2TransProfileAdmnEntry 1 }

sonusCassgR2TransProfileName OBJECT-TYPE
    SYNTAX          SonusName
    ACCESS          read-write
    STATUS          mandatory
    DESCRIPTION     
            "Name of the R2 Translation Profile"
    ::= { sonusCasR2TransProfileAdmnEntry 2 }

sonusCassgR2TransProfileRowStatus OBJECT-TYPE
    SYNTAX          RowStatus
    ACCESS          read-write
    STATUS          mandatory
    DESCRIPTION     
            ""
    ::= { sonusCasR2TransProfileAdmnEntry 3 }

sonusCasR2TransEntryAdmnTable OBJECT-TYPE
    SYNTAX          SEQUENCE OF SonusCasR2TransEntryAdmnEntry
    ACCESS          not-accessible
    STATUS          mandatory
    DESCRIPTION     
            "This mib table is used to create an entry in an R2 Translation Profile."
    ::= { sonusCasMIBObjects 12 }

sonusCasR2TransEntryAdmnEntry OBJECT-TYPE
    SYNTAX          SonusCasR2TransEntryAdmnEntry
    ACCESS          not-accessible
    STATUS          mandatory
    DESCRIPTION     
            ""
    INDEX           { sonusCassgR2TransEntryProfileIndex, 
                      sonusCassgR2TransEntryIndex }
    ::= { sonusCasR2TransEntryAdmnTable 1 }

SonusCasR2TransEntryAdmnEntry ::=
    SEQUENCE {
        sonusCassgR2TransEntryProfileIndex  INTEGER,
        sonusCassgR2TransEntryIndex     INTEGER,
        sonusCassgR2TransEntryR2Signal  INTEGER,
        sonusCassgR2TransEntryDigitField INTEGER,
        sonusCassgR2TransEntrySignalMeaning   INTEGER,
        sonusCassgR2TransEntryAdminState SonusAdminState,
        sonusCassgR2TransEntryRowStatus RowStatus
    }

sonusCassgR2TransEntryProfileIndex OBJECT-TYPE
    SYNTAX          INTEGER
    ACCESS          read-only
    STATUS          mandatory
    DESCRIPTION     
            "Index of R2 Translation Profile in which the entry is contained"
    ::= { sonusCasR2TransEntryAdmnEntry 1 }

sonusCassgR2TransEntryIndex OBJECT-TYPE
    SYNTAX          INTEGER
    ACCESS          read-only
    STATUS          mandatory
    DESCRIPTION     
            "Index of the R2 Translation Entry"
    ::= { sonusCasR2TransEntryAdmnEntry 2 }

sonusCassgR2TransEntryR2Signal OBJECT-TYPE
    SYNTAX          INTEGER (1..15)
    ACCESS          read-write
    STATUS          mandatory
    DESCRIPTION     
            "R2 digit 1 to 15.  10 is used for 0."
    DEFVAL          { 1 }
    ::= { sonusCasR2TransEntryAdmnEntry 3 }

sonusCassgR2TransEntryDigitField OBJECT-TYPE
    SYNTAX          INTEGER { callingPartyCategory(9), 
                        subscriberStatus(11), countryCodeIndicator(13), 
                        langDiscIndicator(14), natureOfConn(15), 
                        echoSupIndicator(16) }
    ACCESS          read-write
    STATUS          mandatory
    DESCRIPTION     
            "Source or destination of value being translated"
    DEFVAL          { callingPartyCategory }
    ::= { sonusCasR2TransEntryAdmnEntry 4 }

sonusCassgR2TransEntrySignalMeaning OBJECT-TYPE
    SYNTAX          INTEGER { unknown(1), scNnps(2), scNprs(3), 
                        scNmnt(4), scNopr(5), scNdt(6), scIsopr(7), 
                        scIoprf(8), scIdt(9), scIprs(10), scPaypn(11), 
                        scTest(12), scColl(13), scCoin(14), scResv1(15), 
                        scResv2(16), scResv3(17), scResv4(18), 
                        scResv5(19), scResv6(20), scResv7(21), slsUn(22), 
                        slsSlb(23), slsSlfc(24), slsSlfnoc(25), 
                        slsSoo(26), slsSit(27), slsNk(28), slsCng(29), 
                        slsChgn(30), slsResv1(31), slsResv2(32), 
                        slsResv3(33), slsResv4(34), slsResv5(35), 
                        slsResv6(36), slsResv7(37), lgdsFr(38), 
                        lgdsEn(39), lgdsGr(40), lgdsRu(41), lgdsSp(42), 
                        lgdsOt(43), lgdsDisc(44), lgdsTci(45), 
                        lgdsOt1(46), lgdsOt2(47), lgdsDisc1(48), 
                        ncInc(49), ncNoi(50), esOgrq(51), esNrq(52), 
                        esOgins(53), esIcrq(54) }
    ACCESS          read-write
    STATUS          mandatory
    DESCRIPTION     
            "Enumerated list of signal meanings"
    DEFVAL          { unknown }
    ::= { sonusCasR2TransEntryAdmnEntry 5 }

sonusCassgR2TransEntryAdminState OBJECT-TYPE
    SYNTAX          SonusAdminState
    ACCESS          read-write
    STATUS          mandatory
    DESCRIPTION     
            "Admin state of the Signal Sequence"
    DEFVAL          { disabled }
    ::= { sonusCasR2TransEntryAdmnEntry 6 }

sonusCassgR2TransEntryRowStatus OBJECT-TYPE
    SYNTAX          RowStatus
    ACCESS          read-write
    STATUS          mandatory
    DESCRIPTION     
            ""
    ::= { sonusCasR2TransEntryAdmnEntry 7 }

sonusCassgFsmStatusTable OBJECT-TYPE
    SYNTAX          SEQUENCE OF SonusCassgFsmStatusEntry
    ACCESS          not-accessible
    STATUS          mandatory
    DESCRIPTION     
            "This table contains FSM status information of a CAS trunk group.
             There may not be any SG registered to a trunk group in which
             case all statistics will be zero."
    ::= { sonusCasMIBObjects 13 }

sonusCassgFsmStatusEntry OBJECT-TYPE
    SYNTAX          SonusCassgFsmStatusEntry
    ACCESS          not-accessible
    STATUS          mandatory
    DESCRIPTION     
            "Each entry describes the current FSM status of a CAS trunk group."
    INDEX           { sonusCassgFsmStatusIndex, sonusCassgFsmShelfIndex, 
                      sonusCassgFsmSlotIndex, sonusCassgFsmPortIndex, 
                      sonusCassgFsmDs3Index, sonusCassgFsmDs1Index, 
                      sonusCassgFsmChanIndex }
    ::= { sonusCassgFsmStatusTable 1 }

SonusCassgFsmStatusEntry ::=
    SEQUENCE {
        sonusCassgFsmStatusIndex        INTEGER,
        sonusCassgFsmShelfIndex         INTEGER,
        sonusCassgFsmSlotIndex          INTEGER,
        sonusCassgFsmPortIndex          INTEGER,
        sonusCassgFsmDs3Index           INTEGER,
        sonusCassgFsmDs1Index           INTEGER,
        sonusCassgFsmChanIndex          INTEGER,
        sonusCassgFsmType               INTEGER,
        sonusCassgFsmState              INTEGER,
        sonusCassgSspState              INTEGER,
        sonusCassgRxSigState            INTEGER,
        sonusCassgTxSigState            INTEGER,
        sonusCassgRxBitA                INTEGER,
        sonusCassgRxBitB                INTEGER,
        sonusCassgRxBitC                INTEGER,
        sonusCassgRxBitD                INTEGER,
        sonusCassgTxBitA                INTEGER,
        sonusCassgTxBitB                INTEGER,
        sonusCassgTxBitC                INTEGER,
        sonusCassgTxBitD                INTEGER
    }

sonusCassgFsmStatusIndex OBJECT-TYPE
    SYNTAX          INTEGER
    ACCESS          read-only
    STATUS          mandatory
    DESCRIPTION     
            "A unique value for each trunk group between 1 and maximum 
             allowed."
    ::= { sonusCassgFsmStatusEntry 1 }

sonusCassgFsmShelfIndex OBJECT-TYPE
    SYNTAX          INTEGER
    ACCESS          read-only
    STATUS          mandatory
    DESCRIPTION     
            "The shelf in which the channel is contained"
    ::= { sonusCassgFsmStatusEntry 2 }

sonusCassgFsmSlotIndex OBJECT-TYPE
    SYNTAX          INTEGER
    ACCESS          read-only
    STATUS          mandatory
    DESCRIPTION     
            "Current slot number."
    ::= { sonusCassgFsmStatusEntry 3 }

sonusCassgFsmPortIndex OBJECT-TYPE
    SYNTAX          INTEGER
    ACCESS          read-only
    STATUS          mandatory
    DESCRIPTION     
            "Current port number."
    ::= { sonusCassgFsmStatusEntry 4 }

sonusCassgFsmDs3Index OBJECT-TYPE
    SYNTAX          INTEGER
    ACCESS          read-only
    STATUS          mandatory
    DESCRIPTION     
            "Current DS3 index."
    ::= { sonusCassgFsmStatusEntry 5 }

sonusCassgFsmDs1Index OBJECT-TYPE
    SYNTAX          INTEGER
    ACCESS          read-only
    STATUS          mandatory
    DESCRIPTION     
            "Current DS1 index."
    ::= { sonusCassgFsmStatusEntry 6 }

sonusCassgFsmChanIndex OBJECT-TYPE
    SYNTAX          INTEGER
    ACCESS          read-only
    STATUS          mandatory
    DESCRIPTION     
            "Current channel number."
    ::= { sonusCassgFsmStatusEntry 7 }

sonusCassgFsmType OBJECT-TYPE
    SYNTAX          INTEGER { ingress(1), egress(2) }
    ACCESS          read-only
    STATUS          mandatory
    DESCRIPTION     
            "Current type is either ingress or egress."
    ::= { sonusCassgFsmStatusEntry 8 }

sonusCassgFsmState OBJECT-TYPE
    SYNTAX          INTEGER { inull(1), ilookup(2), ialloc(3), 
                        iprocssp(4), iorig(5), ialert(6), iconn(7), 
                        irel(8), idiscTr(9), enull(10), ealloc(11), 
                        eprocssp(12), econn(13), etran(14), erel(15), 
                        edisctr(16) }
    ACCESS          read-only
    STATUS          mandatory
    DESCRIPTION     
            "Current FSM state."
    ::= { sonusCassgFsmStatusEntry 9 }

sonusCassgSspState OBJECT-TYPE
    SYNTAX          INTEGER { null(0), seize(1), wink(2), flash(3), 
                        collect(4), dial(5), playtone(6), announce(7), 
                        delay(8), waitwink(9), waitflash(10), 
                        waitanswer(11), seizeack(12), waitseizeack(13), 
                        waitalert(14), q422glare(15), waittipground(16), 
                        fsk(17), waittone(18) }
    ACCESS          read-only
    STATUS          mandatory
    DESCRIPTION     
            "Current SSP state."
    ::= { sonusCassgFsmStatusEntry 10 }

sonusCassgRxSigState OBJECT-TYPE
    SYNTAX          INTEGER { idle(0), seize(1), wink(2), flash(3), 
                        offhook(4), guard(5), seizeack(6), answered(7), 
                        clearbwd(8), clearfwd(9), blocked(10), 
                        ringgnd(11), ringon(12), ringoff(13), lcfo(14), 
                        osi(15), forcerel(16) }
    ACCESS          read-only
    STATUS          mandatory
    DESCRIPTION     
            "Current RX signal state."
    ::= { sonusCassgFsmStatusEntry 11 }

sonusCassgTxSigState OBJECT-TYPE
    SYNTAX          INTEGER { idle(0), seize(1), wink(2), flash(3), 
                        offhook(4), guard(5), seizeack(6), answered(7), 
                        clearbwd(8), clearfwd(9), blocked(10), 
                        ringgnd(11), ringon(12), ringoff(13), lcfo(14), 
                        osi(15), forcerel(16) }
    ACCESS          read-only
    STATUS          mandatory
    DESCRIPTION     
            "Current TX signal state."
    ::= { sonusCassgFsmStatusEntry 12 }

sonusCassgRxBitA OBJECT-TYPE
    SYNTAX          INTEGER (0..1)
    ACCESS          read-only
    STATUS          mandatory
    DESCRIPTION     
            "Current RX A bit."
    ::= { sonusCassgFsmStatusEntry 13 }

sonusCassgRxBitB OBJECT-TYPE
    SYNTAX          INTEGER (0..1)
    ACCESS          read-only
    STATUS          mandatory
    DESCRIPTION     
            "Current RX B bit."
    ::= { sonusCassgFsmStatusEntry 14 }

sonusCassgRxBitC OBJECT-TYPE
    SYNTAX          INTEGER (0..1)
    ACCESS          read-only
    STATUS          mandatory
    DESCRIPTION     
            "Current RX C bit."
    ::= { sonusCassgFsmStatusEntry 15 }

sonusCassgRxBitD OBJECT-TYPE
    SYNTAX          INTEGER (0..1)
    ACCESS          read-only
    STATUS          mandatory
    DESCRIPTION     
            "Current RX D bit."
    ::= { sonusCassgFsmStatusEntry 16 }

sonusCassgTxBitA OBJECT-TYPE
    SYNTAX          INTEGER (0..1)
    ACCESS          read-only
    STATUS          mandatory
    DESCRIPTION     
            "Current TX A bit."
    ::= { sonusCassgFsmStatusEntry 17 }

sonusCassgTxBitB OBJECT-TYPE
    SYNTAX          INTEGER (0..1)
    ACCESS          read-only
    STATUS          mandatory
    DESCRIPTION     
            "Current TX B bit."
    ::= { sonusCassgFsmStatusEntry 18 }

sonusCassgTxBitC OBJECT-TYPE
    SYNTAX          INTEGER (0..1)
    ACCESS          read-only
    STATUS          mandatory
    DESCRIPTION     
            "Current TX C bit."
    ::= { sonusCassgFsmStatusEntry 19 }

sonusCassgTxBitD OBJECT-TYPE
    SYNTAX          INTEGER (0..1)
    ACCESS          read-only
    STATUS          mandatory
    DESCRIPTION     
            "Current TX D bit."
    ::= { sonusCassgFsmStatusEntry 20 }

sonusCasSvcGrpInServiceNotification TRAP-TYPE
    ENTERPRISE      sonusCasServiceGroupMIBNotifications
    VARIABLES       { sonusCasSvcGrpName, sonusEventDescription, 
                      sonusEventClass, sonusEventLevel, sonusSequenceId, 
                      sonusEventTime }
--     STATUS          mandatory
    DESCRIPTION     
            "This trap indicates that the CAS Service Group was put in service 
             by maintenance staff."
    ::= 1

sonusCasSvcGrpOutOfServiceNotification TRAP-TYPE
    ENTERPRISE      sonusCasServiceGroupMIBNotifications
    VARIABLES       { sonusCasSvcGrpName, sonusEventDescription, 
                      sonusEventClass, sonusEventLevel, sonusSequenceId, 
                      sonusEventTime }
--     STATUS          mandatory
    DESCRIPTION     
            "This trap indicates that the CAS Service Group was taken out of 
             service by maintenance staff."
    ::= 2

sonusCasChannelInServiceNotification TRAP-TYPE
    ENTERPRISE      sonusCasServiceGroupMIBNotifications
    VARIABLES       { sonusCasSvcGrpName, sonusCassgChannelShelfIndex, 
                      sonusCassgChannelSlotIndex, 
                      sonusCassgChannelPortIndex, sonusCassgChannelIndex, 
                      sonusEventDescription, sonusEventClass, 
                      sonusEventLevel, sonusSequenceId, sonusEventTime }
--     STATUS          mandatory
    DESCRIPTION     
            "This trap indicates that a CAS channel was put in service by CAS."
    ::= 3

sonusCasChannelOutOfServiceNotification TRAP-TYPE
    ENTERPRISE      sonusCasServiceGroupMIBNotifications
    VARIABLES       { sonusCasSvcGrpName, sonusCassgChannelShelfIndex, 
                      sonusCassgChannelSlotIndex, 
                      sonusCassgChannelPortIndex, sonusCassgChannelIndex, 
                      sonusEventDescription, sonusEventClass, 
                      sonusEventLevel, sonusSequenceId, sonusEventTime }
--     STATUS          mandatory
    DESCRIPTION     
            "This trap indicates that a channel was taken out of service by 
             the CAS SG due to signaling errors exceeding a configured 
             threshold."
    ::= 4

END -- end of module SONUS-CAS-MIB.
