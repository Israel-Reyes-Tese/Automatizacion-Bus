--------------------------------------------------------------------------
-- File Name : ZTE-NET-EMS-MIB.mib
-- Date      : 2007-06-05
-- Author    : ZTE Nms dept.

--
-- Zte Mib for Access Node NMS
-- 
-- 
--------------------------------------------------------------------------

ZTE-NET-EMS-MIB DEFINITIONS ::= BEGIN

    IMPORTS
        enterprises                                         
	    FROM RFC1155-SMI
        MODULE-IDENTITY,NOTIFICATION-TYPE,OBJECT-TYPE,Integer32,Unsigned32,Counter32,Counter64,IpAddress   
	    FROM SNMPv2-SMI
        TEXTUAL-CONVENTION,DisplayString                    
	    FROM SNMPv2-TC
	OBJECT-GROUP,NOTIFICATION-GROUP
	    FROM SNMPv2-CONF;
        
    zxNetEmsMib MODULE-IDENTITY
    LAST-UPDATED "200908250900Z"
    ORGANIZATION "ZTE Corporation"
    CONTACT-INFO "ZTE NMS dept. 
                  Su Chunshan   68896292"
        DESCRIPTION
           "The MIB module which provides a ZTE access node nms mib."

        --Revision history

       ::= { zxNetEms 200 } 


    --.1.3.6.1.4.1.3902
    zte                     OBJECT IDENTIFIER ::= { enterprises 3902 }
    --.1.3.6.1.4.1.3902.701
    zteProducts             OBJECT IDENTIFIER ::= { zte 701}
    --.1.3.6.1.4.1.3902.701.1
    zteEmsProducts          OBJECT IDENTIFIER ::= { zteProducts 1}
    --.1.3.6.1.4.1.3902.701.1.1
    zxNetEms                OBJECT IDENTIFIER ::= { zteEmsProducts 1 } 
    
    --.1.3.6.1.4.1.3902.701.1.1.1
    zxNetEmsManagedObject   OBJECT IDENTIFIER ::= { zxNetEms 1 }
    
    --.1.3.6.1.4.1.3902.701.1.1.50
    zxNetEmsNbiTrapObject   OBJECT IDENTIFIER ::= { zxNetEms 50 }
    --.1.3.6.1.4.1.3902.701.1.1.52
    zxNetEmsNbiEventObject  OBJECT IDENTIFIER ::= { zxNetEms 52 }
    --.1.3.6.1.4.1.3902.701.1.1.55
    zxNetEmsNbiSyncObject   OBJECT IDENTIFIER ::= { zxNetEms 55 }
    
    --.1.3.6.1.4.1.3902.701.1.1.70
    zxNetEmsConformance     OBJECT IDENTIFIER ::= { zxNetEms 70 }
    --.1.3.6.1.4.1.3902.701.1.1.70.10
    zxNetEmsGroups          OBJECT IDENTIFIER ::= { zxNetEmsConformance 10 }


--------------------------------------------------------------------------------
-- 1. Event Trap Related ManagedObject 
--------------------------------------------------------------------------------


--Note:
-- zxEmsEventServerIP,zxEmsEventAid and zxEmsEventSource can identify an event uniquely.
-- There are two types of event,notification and alarm.
-- The trap type(event type) is identified by zxEmsEventSeverity.
-- If zxEmsEventSeverity is restored(5) or cleared(6),OSS should restore the 
-- raletive event(alarm),which have the same value of zxEmsEventServerIP,
-- zxEmsEventAid and zxEmsEventSource.

    --.1.3.6.1.4.1.3902.701.1.1.52.1
    zxEmsEventAid OBJECT-TYPE 
        SYNTAX          Counter32
        MAX-ACCESS      read-only
        STATUS          current
        DESCRIPTION     "Event ID."
        ::=  {  zxNetEmsNbiEventObject 1  }

    --.1.3.6.1.4.1.3902.701.1.1.52.2
    zxEmsEventNeType OBJECT-TYPE 
        SYNTAX          DisplayString
        MAX-ACCESS      read-only
        STATUS          current
        DESCRIPTION     "NE Type."
        ::=  {  zxNetEmsNbiEventObject 2  }
    
    --.1.3.6.1.4.1.3902.701.1.1.52.3
    zxEmsEventServerIP OBJECT-TYPE 
        SYNTAX          DisplayString
        MAX-ACCESS      read-only
        STATUS          current
        DESCRIPTION     "The IP address of NMS server which sends the event."
        ::=  {  zxNetEmsNbiEventObject 3  }

    --.1.3.6.1.4.1.3902.701.1.1.52.4
    zxEmsEventSource OBJECT-TYPE 
        SYNTAX          DisplayString
        MAX-ACCESS      read-only
        STATUS          current
        DESCRIPTION     "The NE ID which sends the event."
        ::=  {  zxNetEmsNbiEventObject 4  }
    
    --.1.3.6.1.4.1.3902.701.1.1.52.5
    zxEmsEventSourceName OBJECT-TYPE 
        SYNTAX          DisplayString
        MAX-ACCESS      read-only
        STATUS          current
        DESCRIPTION     "he NE Name which sends the event."
        ::=  {  zxNetEmsNbiEventObject 5  }
    
    --.1.3.6.1.4.1.3902.701.1.1.52.6
    zxEmsEventEntity OBJECT-TYPE 
        SYNTAX          DisplayString
        MAX-ACCESS      read-only
        STATUS          current
        DESCRIPTION     "The detail position information of the event."
        ::=  {  zxNetEmsNbiEventObject 6  }

    --.1.3.6.1.4.1.3902.701.1.1.52.7
    zxEmsEventHappenTime OBJECT-TYPE 
        SYNTAX          DisplayString
        MAX-ACCESS      read-only
        STATUS          current
        DESCRIPTION     "The happened time of the event.
                It is a string,for example,2005-09-15 11:13:54.428 ."
        ::=  {  zxNetEmsNbiEventObject 7  }
    
    --.1.3.6.1.4.1.3902.701.1.1.52.8
    zxEmsEventName OBJECT-TYPE 
        SYNTAX          DisplayString
        MAX-ACCESS      read-only
        STATUS          current
        DESCRIPTION     "The name of the event."
        ::=  {  zxNetEmsNbiEventObject 8  }

    --.1.3.6.1.4.1.3902.701.1.1.52.9
    zxEmsEventProbableCause OBJECT-TYPE 
        SYNTAX          DisplayString
        MAX-ACCESS      read-only
        STATUS          current
        DESCRIPTION     "The probable cause of the event.."
        ::=  {  zxNetEmsNbiEventObject 9  }

    --.1.3.6.1.4.1.3902.701.1.1.52.10
    zxEmsEventDescription OBJECT-TYPE 
        SYNTAX          DisplayString
        MAX-ACCESS      read-only
        STATUS          current
        DESCRIPTION     "The additional description of the event,which can 
            contain specific information of the type of NE."
        ::=  {  zxNetEmsNbiEventObject 10  }

    --.1.3.6.1.4.1.3902.701.1.1.52.11
    zxEmsEventSeverity OBJECT-TYPE 
        SYNTAX          INTEGER 
	{
            indeterminate(0), 
            critical(1), 
            major(2), 
            minor(3), 
            warning(4), 
            restored(5), 
            cleared(6),
            notification(7)
	} 
        MAX-ACCESS      read-only
	STATUS          current
	DESCRIPTION     "Severity of a event."
        ::=  {  zxNetEmsNbiEventObject 11  }
      
    
    --.1.3.6.1.4.1.3902.701.1.1.52.12
    zxEmsEventRestoreTime OBJECT-TYPE 
        SYNTAX          DisplayString
        MAX-ACCESS      read-only
        STATUS          current
        DESCRIPTION     "The restored time of the event."
        ::=  {  zxNetEmsNbiEventObject 12  }

    
    --.1.3.6.1.4.1.3902.701.1.1.52.13
    zxEmsEventType OBJECT-TYPE 
        SYNTAX          INTEGER
        {
            communications(0),
            qualityOfService(1),
            processingErrorr(2),
            equipment(3),
            environmental(4)
        }
        MAX-ACCESS      read-only
        STATUS          current
        DESCRIPTION     "event type."
        ::=  {  zxNetEmsNbiEventObject 13  }

    --.1.3.6.1.4.1.3902.701.1.1.52.14
    zxEmsEventConfirmType OBJECT-TYPE 
        SYNTAX          INTEGER
        {
            unacknowledge(0),
            acknowledge (1),
            invalid(2)
        }
        MAX-ACCESS      read-only
        STATUS          current
        DESCRIPTION     "Confirmation Type of the event."
        ::=  {  zxNetEmsNbiEventObject 14  }

    
    --.1.3.6.1.4.1.3902.701.1.1.52.15
    zxEmsEventConfirmTime OBJECT-TYPE 
        SYNTAX          DisplayString
        MAX-ACCESS      read-only
        STATUS          current
        DESCRIPTION     "The confirmed time.For example,2005-10-11 17:34:11.471"
        ::=  {  zxNetEmsNbiEventObject 15  }

    
    --.1.3.6.1.4.1.3902.701.1.1.52.16
    zxEmsEventConfirmer OBJECT-TYPE 
        SYNTAX          DisplayString
        MAX-ACCESS      read-only
        STATUS          current
        DESCRIPTION     "Confirmer of the event."
        ::=  {  zxNetEmsNbiEventObject 16  }

    
    --.1.3.6.1.4.1.3902.701.1.1.52.17
    zxEmsEventConfirmSystemIP OBJECT-TYPE 
        SYNTAX          DisplayString
        MAX-ACCESS      read-only
        STATUS          current
        DESCRIPTION     "The IP address of the NMS server,by which the user confirmed the event."
        ::=  {  zxNetEmsNbiEventObject 17  }

    
    --.1.3.6.1.4.1.3902.701.1.1.52.18
    zxEmsEventConfirmInfo OBJECT-TYPE 
        SYNTAX          DisplayString
        MAX-ACCESS      read-only
        STATUS          current
        DESCRIPTION     "Confirmation information."
        ::=  {  zxNetEmsNbiEventObject 18  }

    --.1.3.6.1.4.1.3902.701.1.1.52.19
    zxEmsEventAid64 OBJECT-TYPE 
        SYNTAX          Counter64
        MAX-ACCESS      read-only
        STATUS          current
        DESCRIPTION     "The whole Event ID.It is not be reported by default,and it can be reported by modifying the configuration file."
        ::=  {  zxNetEmsNbiEventObject 19  }
    
    --.1.3.6.1.4.1.3902.701.1.1.52.20
    zxEmsEventSystemType OBJECT-TYPE 
        SYNTAX          INTEGER
        MAX-ACCESS      read-only
        STATUS          current
        DESCRIPTION     "SystemType. It is not be reported by default,and it can be reported by modifying the configuration file."
        ::=  {  zxNetEmsNbiEventObject 20  }


--------------------------------------------------------------------------------
-- 2.Trap Definations
--------------------------------------------------------------------------------

--------------------------------------------------------------------------------
-- 2.1 zxEmsEventTrap
--------------------------------------------------------------------------------

    --.1.3.6.1.4.1.3902.701.1.1.50.4
    zxEmsEventTrap NOTIFICATION-TYPE
        OBJECTS 
        { 
            zxEmsEventAid ,
            zxEmsEventNeType ,
            zxEmsEventServerIP ,
            zxEmsEventSource ,
            zxEmsEventSourceName ,
            zxEmsEventEntity ,
            zxEmsEventHappenTime ,
            zxEmsEventName ,
            zxEmsEventProbableCause ,
            zxEmsEventDescription ,
            zxEmsEventSeverity ,
            zxEmsEventRestoreTime ,
            zxEmsEventType ,
            zxEmsEventConfirmType ,
            zxEmsEventConfirmTime ,
            zxEmsEventConfirmer ,
            zxEmsEventConfirmSystemIP ,
            zxEmsEventConfirmInfo,
	    zxEmsEventAid64,
	    zxEmsEventSystemType
        }
        STATUS  current
        DESCRIPTION
            "The event that is generated by the EMS of NetNumenN31."
        ::= { zxNetEmsNbiTrapObject 4 }

--------------------------------------------------------------------------------
-- 2.2 zxEmsHeartBeatTrap
--------------------------------------------------------------------------------
      --.1.3.6.1.4.1.3902.701.1.1.50.5
      zxEmsHeartBeatTrap NOTIFICATION-TYPE
	 STATUS current
	 DESCRIPTION
	      "The heartbeat trap that is generated by the EMS of NetNumenN31.
	      It is not be reported by default,and it can be reported by modifying the configuration file."
         ::= { zxNetEmsNbiTrapObject 5 }

--------------------------------------------------------------------------------
-- 2.3 zxEmsStartRealignmentTrap
--------------------------------------------------------------------------------       
       --.1.3.6.1.4.1.3902.701.1.1.50.6
       zxEmsStartRealignmentTrap NOTIFICATION-TYPE
	 STATUS current
	 DESCRIPTION
	      "The start realignment trap of alarm synchronization that is generated by the EMS of NetNumenN31.
	      It is not be reported by default,and it can be reported by modifying the configuration file."
	 ::= { zxNetEmsNbiTrapObject 6 }

--------------------------------------------------------------------------------
-- 2.4 zxEmsEndRealignmentTrap
--------------------------------------------------------------------------------
       --.1.3.6.1.4.1.3902.701.1.1.50.7
       zxEmsEndRealignmentTrap NOTIFICATION-TYPE
	 STATUS current
	 DESCRIPTION
	      "The end realignment trap of alarm synchronization that is generated by the EMS of NetNumenN31.
	      It is not be reported by default,and it can be reported by modifying the configuration file."
	 ::= { zxNetEmsNbiTrapObject 7 }

--------------------------------------------------------------------------------
-- 3.Alarm Synchronize Definations
--------------------------------------------------------------------------------

--------------------------------------------------------------------------------
-- 3.1 zxNetEmsNbiSyncObject
--------------------------------------------------------------------------------    
    
    --.1.3.6.1.4.1.3902.701.1.1.55.1
    zxEmsSyncTrapErrorCode OBJECT-TYPE 
        SYNTAX          Integer32
        MAX-ACCESS      read-only
        STATUS          current
        DESCRIPTION     "Operation error code of trap synchronization. 
                         3 means ne dos not exist,4 means program has internal error"
        ::=  {  zxNetEmsNbiSyncObject 1  }

    --.1.3.6.1.4.1.3902.701.1.1.55.2
    zxEmsSyncTrapByIP OBJECT-TYPE 
        SYNTAX          IpAddress
        MAX-ACCESS      read-write
        STATUS          current
        DESCRIPTION     "Synchronize trap of NE specified by NE ip.
                         If value is 0.0.0.0, it means to synchronize all NE's traps in the network."
        ::=  {  zxNetEmsNbiSyncObject 2  }
    
    --.1.3.6.1.4.1.3902.701.1.1.55.3
    zxEmsSyncTrapByName OBJECT-TYPE 
        SYNTAX          DisplayString
        MAX-ACCESS      read-write
        STATUS          current
        DESCRIPTION     "Synchronize trap of NE specified by NE name."
        ::=  {  zxNetEmsNbiSyncObject 3  }

--------------------------------------------------------------------------------
-- 4. zxNetEmsGroups Definations
--------------------------------------------------------------------------------

     --.1.3.6.1.4.1.3902.701.1.1.70.10.1
     zxNetEmsNbiEventGroup OBJECT-GROUP
         OBJECTS  
	 { 
	    zxEmsEventAid ,
            zxEmsEventNeType ,
            zxEmsEventServerIP ,
            zxEmsEventSource ,
            zxEmsEventSourceName ,
            zxEmsEventEntity ,
            zxEmsEventHappenTime ,
            zxEmsEventName ,
            zxEmsEventProbableCause ,
            zxEmsEventDescription ,
            zxEmsEventSeverity ,
            zxEmsEventRestoreTime ,
            zxEmsEventType ,
            zxEmsEventConfirmType ,
            zxEmsEventConfirmTime ,
            zxEmsEventConfirmer ,
            zxEmsEventConfirmSystemIP ,
            zxEmsEventConfirmInfo,
	    zxEmsEventAid64,
	    zxEmsEventSystemType
	 }
         STATUS        current
         DESCRIPTION
             "The Ems Nbi Event Group."
         ::= { zxNetEmsGroups 1 } 

      --.1.3.6.1.4.1.3902.701.1.1.70.10.2
      zxNetEmsNbiSyncGroup OBJECT-GROUP
         OBJECTS  
	 { 
	    zxEmsSyncTrapErrorCode,
	    zxEmsSyncTrapByIP,
	    zxEmsSyncTrapByName
	 }
         STATUS        current
         DESCRIPTION
             "The Ems Nbi Alarm Synchronization Group."
         ::= { zxNetEmsGroups 2 }


       --.1.3.6.1.4.1.3902.701.1.1.70.10.3
       zxNetEmsNbiTrapGroup NOTIFICATION-GROUP
         NOTIFICATIONS  
	 { 
	    zxEmsEventTrap,
	    zxEmsHeartBeatTrap,
	    zxEmsStartRealignmentTrap,
	    zxEmsEndRealignmentTrap
	 }
         STATUS        current
         DESCRIPTION
             "The Ems Event Trap Notification Group."
         ::= { zxNetEmsGroups 3 }

END
