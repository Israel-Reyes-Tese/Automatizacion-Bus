--
-- This SMIv2 module has been generated by smidump 0.2-cvs. Do not edit.
--

SONUS-SOFTSWITCH-ENUME-MIB DEFINITIONS ::= BEGIN

IMPORTS
    MODULE-IDENTITY, NOTIFICATION-TYPE
        FROM SNMPv2-SMI
    sonusEventClass, sonusEventDescription, sonusEventLevel, 
    sonusEventTime
        FROM SONUS-COMMON-MIB
    sonusServicesMIBs
        FROM SONUS-SMI;

sonusSoftSwitchEnumeMIB MODULE-IDENTITY
    LAST-UPDATED    "201008040000Z"
    ORGANIZATION    
            "Sonus Networks, Inc."
    CONTACT-INFO    
            "   Customer Support    
             Sonus Networks, Inc.
             7 Tech Park Dr
             Westford, MA 01886
             USA
             
             Tel: 978-614-8100
             Fax: 978-614-8609"
    DESCRIPTION     
            "The MIB Module for SoftSwitch Enume Management."
    ::= { sonusServicesMIBs 32 }


sonusSoftSwitchEnumeMIBObjects OBJECT IDENTIFIER
    ::= { sonusSoftSwitchEnumeMIB 1 }

sonusSoftSwitchEnumeMIBNotifications OBJECT IDENTIFIER
    ::= { sonusSoftSwitchEnumeMIB 2 }

sonusSoftSwitchEnumeMIBNotificationsPrefix OBJECT IDENTIFIER
    ::= { sonusSoftSwitchEnumeMIBNotifications 0 }

sonusSoftSwitchEnumeMIBNotificationsObjects OBJECT IDENTIFIER
    ::= { sonusSoftSwitchEnumeMIBNotifications 1 }

sonusSoftSwitchEnumeDownNotification NOTIFICATION-TYPE
    OBJECTS         { sonusEventDescription, sonusEventClass, 
                      sonusEventLevel, sonusEventTime }
    STATUS          current
    DESCRIPTION     
            "Enume is down"
    ::= { sonusSoftSwitchEnumeMIBNotificationsPrefix 1 }

sonusSoftSwitchEnumeUpNotification NOTIFICATION-TYPE
    OBJECTS         { sonusEventDescription, sonusEventClass, 
                      sonusEventLevel, sonusEventTime }
    STATUS          current
    DESCRIPTION     
            "Enume is up"
    ::= { sonusSoftSwitchEnumeMIBNotificationsPrefix 2 }

END -- end of module SONUS-SOFTSWITCH-ENUME-MIB.
