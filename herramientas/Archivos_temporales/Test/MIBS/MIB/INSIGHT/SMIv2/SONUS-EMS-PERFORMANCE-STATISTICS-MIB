--
-- This SMIv2 module has been generated by smidump 0.2-cvs. Do not edit.
--

SONUS-EMS-PERFORMANCE-STATISTICS-MIB DEFINITIONS ::= BEGIN

IMPORTS
    Integer32, IpAddress, MODULE-IDENTITY, NOTIFICATION-TYPE, 
    OBJECT-TYPE
        FROM SNMPv2-SMI
    sonusEmsNotificationsObjects
        FROM SONUS-EMS-MIB;

sonusEmsPMStatsMIB MODULE-IDENTITY
    LAST-UPDATED    "200403160000Z"
    ORGANIZATION    
            "Sonus Networks, Inc."
    CONTACT-INFO    
            "   Customer Support    
             Sonus Networks, Inc.
             250 Apollo Drive
             Chelmsford, MA 01824
             USA
             
             Tel: 978-614-8100
             Fax: 978-614-8609"
    DESCRIPTION     
            "Identifiers for performance statistics measures that are computed
             and therefore don't have an identifer established for them in
             any other Sonus MIB."
    ::= { sonusEmsNotificationsObjects 3 }


sonusEmsPMStatsObjects OBJECT IDENTIFIER
    ::= { sonusEmsPMStatsMIB 1 }

sonusEmsGSXPMStatsObjects OBJECT IDENTIFIER
    ::= { sonusEmsPMStatsObjects 1 }

sonusEmsGSXPMEnetStatsObjects OBJECT IDENTIFIER
    ::= { sonusEmsGSXPMStatsObjects 1 }

sonusEmsGSXPMEnetBandwidthUsage OBJECT-TYPE
    SYNTAX          OBJECT IDENTIFIER
    MAX-ACCESS      read-only
    STATUS          current
    DESCRIPTION     
            "GSX Ethernet Bandwidth Usage."
    ::= { sonusEmsGSXPMEnetStatsObjects 1 }

sonusEmsGSXPMGatewayStatsObjects OBJECT IDENTIFIER
    ::= { sonusEmsGSXPMStatsObjects 2 }

sonusEmsGSXPMGatewayBusyHourAttempts OBJECT-TYPE
    SYNTAX          OBJECT IDENTIFIER
    MAX-ACCESS      read-only
    STATUS          current
    DESCRIPTION     
            "Gateway Busy Hour Attempts."
    ::= { sonusEmsGSXPMGatewayStatsObjects 1 }

sonusEmsGSXPMTrunkGroupStatsObjects OBJECT IDENTIFIER
    ::= { sonusEmsGSXPMStatsObjects 3 }

sonusEmsGSXPMTrunkGroupInboundBHA OBJECT-TYPE
    SYNTAX          OBJECT IDENTIFIER
    MAX-ACCESS      read-only
    STATUS          current
    DESCRIPTION     
            "Trunk Group Inbound Busy Hour Attempts."
    ::= { sonusEmsGSXPMTrunkGroupStatsObjects 1 }

sonusEmsGSXPMTrunkGroupOutboundBHA OBJECT-TYPE
    SYNTAX          OBJECT IDENTIFIER
    MAX-ACCESS      read-only
    STATUS          current
    DESCRIPTION     
            "Trunk Group Outbound Busy Hour Attempts."
    ::= { sonusEmsGSXPMTrunkGroupStatsObjects 2 }

sonusEmsGSXPMTrunkGroupCallSetupTime OBJECT-TYPE
    SYNTAX          OBJECT IDENTIFIER
    MAX-ACCESS      read-only
    STATUS          current
    DESCRIPTION     
            "Trunk Group Call Setup Time."
    ::= { sonusEmsGSXPMTrunkGroupStatsObjects 3 }

sonusEmsGSXPMTrunkGroupUtilizationPercent OBJECT-TYPE
    SYNTAX          OBJECT IDENTIFIER
    MAX-ACCESS      read-only
    STATUS          current
    DESCRIPTION     
            "Trunk Group Utilization Percentage."
    ::= { sonusEmsGSXPMTrunkGroupStatsObjects 4 }

sonusEmsSGXPMStatsObjects OBJECT IDENTIFIER
    ::= { sonusEmsPMStatsObjects 2 }

sonusEmsPSXPMStatsObjects OBJECT IDENTIFIER
    ::= { sonusEmsPMStatsObjects 3 }

sonusEmsASXPMStatsObjects OBJECT IDENTIFIER
    ::= { sonusEmsPMStatsObjects 4 }

sonusEmsASXPMActiveCallStatsObjects OBJECT IDENTIFIER
    ::= { sonusEmsASXPMStatsObjects 1 }

sonusEmsASXPMOutboundActivePercent OBJECT-TYPE
    SYNTAX          OBJECT IDENTIFIER
    MAX-ACCESS      read-only
    STATUS          current
    DESCRIPTION     
            "ASX Basic Active outbound calls percent."
    ::= { sonusEmsASXPMActiveCallStatsObjects 1 }

sonusEmsASXPMInboundActivePercent OBJECT-TYPE
    SYNTAX          OBJECT IDENTIFIER
    MAX-ACCESS      read-only
    STATUS          current
    DESCRIPTION     
            "ASX Basic Active inbound calls percent."
    ::= { sonusEmsASXPMActiveCallStatsObjects 2 }

sonusEmsASXPMLocalActivePercent OBJECT-TYPE
    SYNTAX          OBJECT IDENTIFIER
    MAX-ACCESS      read-only
    STATUS          current
    DESCRIPTION     
            "ASX Basic Active local calls percent."
    ::= { sonusEmsASXPMActiveCallStatsObjects 3 }

END -- end of module SONUS-EMS-PERFORMANCE-STATISTICS-MIB.
