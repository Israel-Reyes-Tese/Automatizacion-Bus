NEXENTA-DATAPROTECTION-MIB DEFINITIONS ::= BEGIN
IMPORTS
    MODULE-IDENTITY FROM SNMPv2-SMI
    MODULE-COMPLIANCE FROM SNMPv2-CONF
    OBJECT-TYPE, Integer32 FROM SNMPv2-SMI
    OBJECT-GROUP FROM SNMPv2-CONF
    nexentaNef FROM NEXENTA-MIB
;
dataProtection MODULE-IDENTITY
    LAST-UPDATED "201810100000Z"
    ORGANIZATION "Nexenta Systems, Inc."
    CONTACT-INFO "postal: 2025 Gateway Place, Suite 160, San Jose, CA 95110 USA
email: support@nexenta.com"
    DESCRIPTION "MIB to support data protection services"
    REVISION "201810100000Z"
    DESCRIPTION "Initial revision"
    ::= { nexentaNef 5 }
dataProtectionNotifications OBJECT IDENTIFIER ::= { dataProtection 0 }
protectionServiceListTable OBJECT-TYPE
    SYNTAX SEQUENCE OF ProtectionServiceListSequence
    MAX-ACCESS not-accessible
    STATUS current
    DESCRIPTION "List of protection services on the appliance"
    ::= { dataProtection 1 }
protectionServiceListEntry OBJECT-TYPE
    SYNTAX ProtectionServiceListSequence
    MAX-ACCESS not-accessible
    STATUS current
    DESCRIPTION "Protection service entry"
    INDEX { protectionServiceName }
    ::= { protectionServiceListTable 1 }
ProtectionServiceListSequence ::= SEQUENCE {
    protectionServiceName OCTET STRING,
    protectionServiceState OCTET STRING,
    protectionServiceRunning Integer32,
    protectionServiceProgress Integer32,
    protectionServiceCommonSnapshot OCTET STRING,
    protectionServiceLastError OCTET STRING
}
protectionServiceName OBJECT-TYPE
    SYNTAX OCTET STRING (SIZE (1..255))
    MAX-ACCESS read-only
    STATUS current
    DESCRIPTION "Name of protection service"
    ::= { protectionServiceListEntry 1 }
protectionServiceState OBJECT-TYPE
    SYNTAX OCTET STRING
    MAX-ACCESS read-only
    STATUS current
    DESCRIPTION "Current state of protection service"
    ::= { protectionServiceListEntry 2 }
protectionServiceRunning OBJECT-TYPE
    SYNTAX Integer32
    MAX-ACCESS read-only
    STATUS current
    DESCRIPTION "Indicates whether protection service is currently running"
    ::= { protectionServiceListEntry 3 }
protectionServiceProgress OBJECT-TYPE
    SYNTAX Integer32
    MAX-ACCESS read-only
    STATUS current
    DESCRIPTION "Replication progress in %"
    ::= { protectionServiceListEntry 4 }
protectionServiceCommonSnapshot OBJECT-TYPE
    SYNTAX OCTET STRING
    MAX-ACCESS read-only
    STATUS current
    DESCRIPTION "Name of the last received snapshot"
    ::= { protectionServiceListEntry 5 }
protectionServiceLastError OBJECT-TYPE
    SYNTAX OCTET STRING
    MAX-ACCESS read-only
    STATUS current
    DESCRIPTION "Cause of faulted state"
    ::= { protectionServiceListEntry 6 }
protectionScheduleListTable OBJECT-TYPE
    SYNTAX SEQUENCE OF ProtectionScheduleListSequence
    MAX-ACCESS not-accessible
    STATUS current
    DESCRIPTION "List of protection schedules on the appliance"
    ::= { dataProtection 2 }
protectionScheduleListEntry OBJECT-TYPE
    SYNTAX ProtectionScheduleListSequence
    MAX-ACCESS not-accessible
    STATUS current
    DESCRIPTION "Protection schedule entry"
    INDEX { protectionServiceName, protectionScheduleName }
    ::= { protectionScheduleListTable 1 }
ProtectionScheduleListSequence ::= SEQUENCE {
    protectionServiceName OCTET STRING,
    protectionScheduleName OCTET STRING,
    protectionScheduleDisabled Integer32,
    protectionScheduleCron OCTET STRING,
    protectionScheduleKeepSource Integer32,
    protectionScheduleKeepDestination Integer32
}
protectionServiceName OBJECT-TYPE
    SYNTAX OCTET STRING (SIZE (1..255))
    MAX-ACCESS read-only
    STATUS current
    DESCRIPTION "Name of protection service"
    ::= { protectionScheduleListEntry 1 }
protectionScheduleName OBJECT-TYPE
    SYNTAX OCTET STRING
    MAX-ACCESS read-only
    STATUS current
    DESCRIPTION "Name of protection schedule"
    ::= { protectionScheduleListEntry 2 }
protectionScheduleDisabled OBJECT-TYPE
    SYNTAX Integer32
    MAX-ACCESS read-only
    STATUS current
    DESCRIPTION "Indicates whether protection schedule is disabled"
    ::= { protectionScheduleListEntry 3 }
protectionScheduleCron OBJECT-TYPE
    SYNTAX OCTET STRING
    MAX-ACCESS read-only
    STATUS current
    DESCRIPTION "Schedule cron expression"
    ::= { protectionScheduleListEntry 4 }
protectionScheduleKeepSource OBJECT-TYPE
    SYNTAX Integer32
    MAX-ACCESS read-only
    STATUS current
    DESCRIPTION "How many source snapshots to keep"
    ::= { protectionScheduleListEntry 5 }
protectionScheduleKeepDestination OBJECT-TYPE
    SYNTAX Integer32
    MAX-ACCESS read-only
    STATUS current
    DESCRIPTION "How many destination snapshots to keep"
    ::= { protectionScheduleListEntry 6 }
dataProtectionCompliances OBJECT IDENTIFIER ::= { dataProtection 1000 }
dataProtectionObjGrp OBJECT-GROUP
    OBJECTS { protectionServiceName, protectionServiceState, protectionServiceRunning, protectionServiceProgress, protectionServiceCommonSnapshot, protectionServiceLastError, protectionScheduleName, protectionScheduleDisabled, protectionScheduleCron, protectionScheduleKeepSource, protectionScheduleKeepDestination }
    STATUS current
    DESCRIPTION "Default objects conformance group for NEXENTA-DATAPROTECTION-MIB"
    ::= { dataProtectionCompliances 2 }
dataProtectionCompliance MODULE-COMPLIANCE
    STATUS current
    DESCRIPTION "Default compliance statement for NEXENTA-DATAPROTECTION-MIB"
    MODULE MANDATORY-GROUPS { dataProtectionObjGrp }
    ::= { dataProtectionCompliances 1 }
END
