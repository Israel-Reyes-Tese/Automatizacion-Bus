--
-- This SMIv2 module has been generated by smidump 0.2-cvs. Do not edit.
--

FOUNDRY-SN-TRAP-MIB DEFINITIONS ::= BEGIN

IMPORTS
    snAgGblTrapMessage, snAgentBrdIndex, snChasFanDescription, 
    snChasFanIndex, snChasPwrSupplyDescription, snChasPwrSupplyIndex, 
    snChasPwrSupplyStatus
        FROM FOUNDRY-SN-AGENT-MIB
    snOspfConfigErrorType, snOspfExtLsdbLimit, snOspfIfStatusIpAddress, 
    snOspfIfStatusState, snOspfLsdbAreaId, snOspfLsdbLsId, 
    snOspfLsdbRouterId, snOspfLsdbType, snOspfNbrIpAddr, snOspfNbrRtrId, 
    snOspfNbrState, snOspfPacketSrc, snOspfPacketType, snOspfRouterId, 
    snOspfVirtIfStatusAreaID, snOspfVirtIfStatusNeighbor, 
    snOspfVirtIfStatusState, snOspfVirtNbrArea, snOspfVirtNbrRtrId, 
    snOspfVirtNbrState
        FROM FOUNDRY-SN-OSPF-GROUP-MIB
    foundry
        FROM FOUNDRY-SN-ROOT-MIB
    snL4MaxSessionLimit, snL4TcpSynLimit, 
    snL4TrapRealServerCurConnections, snL4TrapRealServerIP, 
    snL4TrapRealServerName, snL4TrapRealServerPort
        FROM FOUNDRY-SN-SW-L4-SWITCH-GROUP-MIB
    snSwViolatorMacAddress, snSwViolatorPortNumber
        FROM FOUNDRY-SN-SWITCH-GROUP-MIB
    NOTIFICATION-TYPE
        FROM SNMPv2-SMI;

snTrapChasPwrSupply NOTIFICATION-TYPE
    OBJECTS         { snChasPwrSupplyStatus }
    STATUS          current
    DESCRIPTION     
            "The SNMP trap that is generated when a power supply fails
             to operate normally."
    ::= { foundry 0 1 }

snTrapLockedAddressViolation NOTIFICATION-TYPE
    OBJECTS         { snSwViolatorPortNumber, snSwViolatorMacAddress }
    STATUS          current
    DESCRIPTION     
            "The SNMP trap that is generated when more source MAC addresses
             are received from a port than the maximum number of addresses
             configured to that port."
    ::= { foundry 0 2 }

snTrapOspfIfStateChange NOTIFICATION-TYPE
    OBJECTS         { snOspfRouterId, snOspfIfStatusIpAddress, 
                      snOspfIfStatusState }
    STATUS          current
    DESCRIPTION     
            "An ospfIfStateChange trap signifies that there
             has been a change in the state of a non-virtual
             OSPF interface. This trap should  be  generated
             when  the interface state regresses (e.g., goes
             from Dr to Down) or progresses  to  a  terminal
             state  (i.e.,  Point-to-Point, DR Other, Dr, or
             Backup)."
    ::= { foundry 0 3 }

snTrapOspfVirtIfStateChange NOTIFICATION-TYPE
    OBJECTS         { snOspfRouterId, snOspfVirtIfStatusAreaID, 
                      snOspfVirtIfStatusNeighbor, 
                      snOspfVirtIfStatusState }
    STATUS          current
    DESCRIPTION     
            "An ospfIfStateChange trap signifies that there
             has  been a change in the state of an OSPF vir-
             tual interface.
             This trap should be generated when  the  inter-
             face  state  regresses  (e.g., goes from Point-
             to-Point to Down) or progresses to  a  terminal
             state (i.e., Point-to-Point)."
    ::= { foundry 0 4 }

snOspfNbrStateChange NOTIFICATION-TYPE
    OBJECTS         { snOspfRouterId, snOspfNbrIpAddr, snOspfNbrRtrId, 
                      snOspfNbrState }
    STATUS          current
    DESCRIPTION     
            "An  ospfNbrStateChange  trap  signifies   that
             there  has been a change in the state of a non-
             virtual OSPF neighbor.   This  trap  should  be
             generated  when  the  neighbor  state regresses
             (e.g., goes from Attempt or Full  to  1-Way  or
             Down)  or progresses to a terminal state (e.g.,
             2-Way or Full).  When an  neighbor  transitions
             from  or  to Full on non-broadcast multi-access
             and broadcast networks, the trap should be gen-
             erated  by the designated router.  A designated
             router transitioning to Down will be  noted  by
             ospfIfStateChange."
    ::= { foundry 0 5 }

snOspfVirtNbrStateChange NOTIFICATION-TYPE
    OBJECTS         { snOspfRouterId, snOspfVirtNbrArea, 
                      snOspfVirtNbrRtrId, snOspfVirtNbrState }
    STATUS          current
    DESCRIPTION     
            "An ospfIfStateChange trap signifies that there
             has  been a change in the state of an OSPF vir-
             tual neighbor.  This trap should  be  generated
             when  the  neighbor state regresses (e.g., goes
             from Attempt or  Full  to  1-Way  or  Down)  or
             progresses to a terminal state (e.g., Full)."
    ::= { foundry 0 6 }

snOspfIfConfigError NOTIFICATION-TYPE
    OBJECTS         { snOspfRouterId, snOspfIfStatusIpAddress, 
                      snOspfPacketSrc, snOspfConfigErrorType, 
                      snOspfPacketType }
    STATUS          current
    DESCRIPTION     
            "An ospfIfConfigError  trap  signifies  that  a
             packet  has  been received on a non-virtual in-
             terface  from  a  router  whose   configuration
             parameters  conflict  with this router's confi-
             guration parameters.  Note that the  event  op-
             tionMismatch  should  cause  a  trap only if it
             prevents an adjacency from forming."
    ::= { foundry 0 7 }

snOspfVirtIfConfigError NOTIFICATION-TYPE
    OBJECTS         { snOspfRouterId, snOspfVirtIfStatusAreaID, 
                      snOspfVirtIfStatusNeighbor, snOspfConfigErrorType, 
                      snOspfPacketType }
    STATUS          current
    DESCRIPTION     
            "An ospfConfigError trap signifies that a pack-
             et  has  been  received  on a virtual interface
             from a router  whose  configuration  parameters
             conflict   with   this  router's  configuration
             parameters.  Note that the event optionMismatch
             should  cause a trap only if it prevents an ad-
             jacency from forming."
    ::= { foundry 0 8 }

snOspfIfAuthFailure NOTIFICATION-TYPE
    OBJECTS         { snOspfRouterId, snOspfIfStatusIpAddress, 
                      snOspfPacketSrc, snOspfConfigErrorType, 
                      snOspfPacketType }
    STATUS          current
    DESCRIPTION     
            "An ospfIfAuthFailure  trap  signifies  that  a
             packet  has  been received on a non-virtual in-
             terface from a router whose authentication  key
             or  authentication  type  conflicts  with  this
             router's authentication key  or  authentication
             type."
    ::= { foundry 0 9 }

snOspfVirtIfAuthFailure NOTIFICATION-TYPE
    OBJECTS         { snOspfRouterId, snOspfVirtIfStatusAreaID, 
                      snOspfVirtIfStatusNeighbor, snOspfConfigErrorType, 
                      snOspfPacketType }
    STATUS          current
    DESCRIPTION     
            "An ospfVirtIfAuthFailure trap signifies that a
             packet has been received on a virtual interface
             from a router whose authentication key  or  au-
             thentication  type conflicts with this router's
             authentication key or authentication type."
    ::= { foundry 0 10 }

snOspfIfRxBadPacket NOTIFICATION-TYPE
    OBJECTS         { snOspfRouterId, snOspfIfStatusIpAddress, 
                      snOspfPacketSrc, snOspfPacketType }
    STATUS          current
    DESCRIPTION     
            "An ospfIfRxBadPacket trap  signifies  that  an
             OSPF  packet has been received on a non-virtual
             interface that cannot be parsed."
    ::= { foundry 0 11 }

snOspfVirtIfRxBadPacket NOTIFICATION-TYPE
    OBJECTS         { snOspfRouterId, snOspfVirtIfStatusAreaID, 
                      snOspfVirtIfStatusNeighbor, snOspfPacketType }
    STATUS          current
    DESCRIPTION     
            "An ospfRxBadPacket trap signifies that an OSPF
             packet has been received on a virtual interface
             that cannot be parsed."
    ::= { foundry 0 12 }

snOspfTxRetransmit NOTIFICATION-TYPE
    OBJECTS         { snOspfRouterId, snOspfIfStatusIpAddress, 
                      snOspfNbrRtrId, snOspfPacketType, snOspfLsdbType, 
                      snOspfLsdbLsId, snOspfLsdbRouterId }
    STATUS          current
    DESCRIPTION     
            "An ospfTxRetransmit  trap  signifies  than  an
             OSPF  packet  has  been retransmitted on a non-
             virtual interface.  All packets that may be re-
             transmitted  are associated with an LSDB entry.
             The LS type, LS ID, and Router ID are  used  to
             identify the LSDB entry."
    ::= { foundry 0 13 }

ospfVirtIfTxRetransmit NOTIFICATION-TYPE
    OBJECTS         { snOspfRouterId, snOspfVirtIfStatusAreaID, 
                      snOspfVirtIfStatusNeighbor, snOspfPacketType, 
                      snOspfLsdbType, snOspfLsdbLsId, snOspfLsdbRouterId }
    STATUS          current
    DESCRIPTION     
            "An ospfTxRetransmit  trap  signifies  than  an
             OSPF packet has been retransmitted on a virtual
             interface.  All packets that may be retransmit-
             ted  are  associated with an LSDB entry. The LS
             type, LS ID, and Router ID are used to identify
             the LSDB entry."
    ::= { foundry 0 14 }

snOspfOriginateLsa NOTIFICATION-TYPE
    OBJECTS         { snOspfRouterId, snOspfLsdbAreaId, snOspfLsdbType, 
                      snOspfLsdbLsId, snOspfLsdbRouterId }
    STATUS          current
    DESCRIPTION     
            "An ospfOriginateLsa trap signifies that a  new
             LSA  has  been originated by this router.  This
             trap should not be invoked for simple refreshes
             of  LSAs  (which happesn every 30 minutes), but
             instead will only be invoked  when  an  LSA  is
             (re)originated due to a topology change.  Addi-
             tionally, this trap does not include LSAs  that
             are  being  flushed  because  they have reached
             MaxAge."
    ::= { foundry 0 15 }

snOspfMaxAgeLsa NOTIFICATION-TYPE
    OBJECTS         { snOspfRouterId, snOspfLsdbAreaId, snOspfLsdbType, 
                      snOspfLsdbLsId, snOspfLsdbRouterId }
    STATUS          current
    DESCRIPTION     
            "An ospfMaxAgeLsa trap signifies  that  one  of
             the LSA in the router's link-state database has
             aged to MaxAge."
    ::= { foundry 0 16 }

snOspfLsdbOverflow NOTIFICATION-TYPE
    OBJECTS         { snOspfRouterId, snOspfExtLsdbLimit }
    STATUS          current
    DESCRIPTION     
            "An ospfLsdbOverflow trap  signifies  that  the
             number of LSAs in the router's link-state data-
             base has exceeded ospfExtLsdbLimit."
    ::= { foundry 0 17 }

snOspfLsdbApproachingOverflow NOTIFICATION-TYPE
    OBJECTS         { snOspfRouterId, snOspfExtLsdbLimit }
    STATUS          current
    DESCRIPTION     
            "An ospfLsdbApproachingOverflow trap  signifies
             that  the  number of LSAs in the router's link-
             state database has exceeded ninety  percent  of
             ospfExtLsdbLimit."
    ::= { foundry 0 18 }

snTrapL4MaxSessionLimitReached NOTIFICATION-TYPE
    OBJECTS         { snL4MaxSessionLimit }
    STATUS          current
    DESCRIPTION     
            "The SNMP trap that is generated when the maximum number
             of connections reached."
    ::= { foundry 0 19 }

snTrapL4TcpSynLimitReached NOTIFICATION-TYPE
    OBJECTS         { snL4TcpSynLimit }
    STATUS          current
    DESCRIPTION     
            "The SNMP trap that is generated when the number of TCP
             SYN limits reached."
    ::= { foundry 0 20 }

snTrapL4RealServerUp NOTIFICATION-TYPE
    OBJECTS         { snL4TrapRealServerIP, snL4TrapRealServerName }
    STATUS          current
    DESCRIPTION     
            "The SNMP trap that is generated when the load balancing
             real server is up."
    ::= { foundry 0 21 }

snTrapL4RealServerDown NOTIFICATION-TYPE
    OBJECTS         { snL4TrapRealServerIP, snL4TrapRealServerName }
    STATUS          current
    DESCRIPTION     
            "The SNMP trap that is generated when the load balancing
             real server is down."
    ::= { foundry 0 22 }

snTrapL4RealServerPortUp NOTIFICATION-TYPE
    OBJECTS         { snL4TrapRealServerIP, snL4TrapRealServerName, 
                      snL4TrapRealServerPort }
    STATUS          current
    DESCRIPTION     
            "The SNMP trap that is generated when the load balancing
             real server TCP port is up."
    ::= { foundry 0 23 }

snTrapL4RealServerPortDown NOTIFICATION-TYPE
    OBJECTS         { snL4TrapRealServerIP, snL4TrapRealServerName, 
                      snL4TrapRealServerPort }
    STATUS          current
    DESCRIPTION     
            "The SNMP trap that is generated when the load balancing
             real server TCP port is down."
    ::= { foundry 0 24 }

snTrapL4RealServerMaxConnectionLimitReached NOTIFICATION-TYPE
    OBJECTS         { snL4TrapRealServerIP, snL4TrapRealServerName, 
                      snL4TrapRealServerCurConnections }
    STATUS          current
    DESCRIPTION     
            "The SNMP trap that is generated when the real server reaches
             maximum number of connections."
    ::= { foundry 0 25 }

snTrapL4BecomeStandby NOTIFICATION-TYPE
    STATUS          current
    DESCRIPTION     
            "The SNMP trap that is generated when the server load
             balancing switch changes state from active to standby."
    ::= { foundry 0 26 }

snTrapL4BecomeActive NOTIFICATION-TYPE
    STATUS          current
    DESCRIPTION     
            "The SNMP trap that is generated when the server load
             balancing switch changes state from standby to active."
    ::= { foundry 0 27 }

snTrapModuleInserted NOTIFICATION-TYPE
    OBJECTS         { snAgentBrdIndex }
    STATUS          current
    DESCRIPTION     
            "The SNMP trap that is generated when a module was inserted
             to the chassis during system running."
    ::= { foundry 0 28 }

snTrapModuleRemoved NOTIFICATION-TYPE
    OBJECTS         { snAgentBrdIndex }
    STATUS          current
    DESCRIPTION     
            "The SNMP trap that is generated when a module was removed
             from the chassis during system running."
    ::= { foundry 0 29 }

snTrapChasPwrSupplyFailed NOTIFICATION-TYPE
    OBJECTS         { snChasPwrSupplyIndex, snChasPwrSupplyDescription }
    STATUS          current
    DESCRIPTION     
            "The SNMP trap that is generated when a power supply fails
             to operate normally."
    ::= { foundry 0 30 }

snTrapChasFanFailed NOTIFICATION-TYPE
    OBJECTS         { snChasFanIndex, snChasFanDescription }
    STATUS          current
    DESCRIPTION     
            "The SNMP trap that is generated when a fan fails
             to operate normally."
    ::= { foundry 0 31 }

snTrapLockedAddressViolation2 NOTIFICATION-TYPE
    OBJECTS         { snAgGblTrapMessage }
    STATUS          current
    DESCRIPTION     
            "The SNMP trap that is generated when more source MAC addresses
             are received from a port than the maximum number of addresses
             configured to that port."
    ::= { foundry 0 32 }

snTrapFsrpIfStateChange NOTIFICATION-TYPE
    OBJECTS         { snAgGblTrapMessage }
    STATUS          current
    DESCRIPTION     
            "The SNMP trap that is generated when a FSRP routing device
             changed state from active to standby or vice-versa."
    ::= { foundry 0 33 }

snTrapVrrpIfStateChange NOTIFICATION-TYPE
    OBJECTS         { snAgGblTrapMessage }
    STATUS          current
    DESCRIPTION     
            "The SNMP trap that is generated when a VRRP routing device
             changed state from master to backup or vice-versa."
    ::= { foundry 0 34 }

snTrapMgmtModuleRedunStateChange NOTIFICATION-TYPE
    OBJECTS         { snAgGblTrapMessage }
    STATUS          current
    DESCRIPTION     
            "The SNMP trap that is generated when the management module
             changes redundancy state."
    ::= { foundry 0 35 }

snTrapTemperatureWarning NOTIFICATION-TYPE
    OBJECTS         { snAgGblTrapMessage }
    STATUS          current
    DESCRIPTION     
            "The SNMP trap that is generated when the actual temperature
             reading is above the warning temperature threshold."
    ::= { foundry 0 36 }

snTrapAccessListDeny NOTIFICATION-TYPE
    OBJECTS         { snAgGblTrapMessage }
    STATUS          current
    DESCRIPTION     
            "The SNMP trap that is generated when a packet was denied
             by an access list."
    ::= { foundry 0 37 }

snTrapMacFilterDeny NOTIFICATION-TYPE
    OBJECTS         { snAgGblTrapMessage }
    STATUS          current
    DESCRIPTION     
            "The SNMP trap that is generated when a packet was denied
             by a MAC address filter."
    ::= { foundry 0 38 }

snTrapL4GslbRemoteUp NOTIFICATION-TYPE
    OBJECTS         { snAgGblTrapMessage }
    STATUS          current
    DESCRIPTION     
            "The SNMP trap that is generated when the connection to the remote SI is established."
    ::= { foundry 0 39 }

snTrapL4GslbRemoteDown NOTIFICATION-TYPE
    OBJECTS         { snAgGblTrapMessage }
    STATUS          current
    DESCRIPTION     
            "The SNMP trap that is generated when the connection to the remote SI is down."
    ::= { foundry 0 40 }

snTrapL4GslbRemoteControllerUp NOTIFICATION-TYPE
    OBJECTS         { snAgGblTrapMessage }
    STATUS          current
    DESCRIPTION     
            "The SNMP trap that is generated when the connection to the GSLB SI is established."
    ::= { foundry 0 41 }

snTrapL4GslbRemoteControllerDown NOTIFICATION-TYPE
    OBJECTS         { snAgGblTrapMessage }
    STATUS          current
    DESCRIPTION     
            "The SNMP trap that is generated when the connection to the GSLB SI is down."
    ::= { foundry 0 42 }

snTrapL4GslbHealthCheckIpUp NOTIFICATION-TYPE
    OBJECTS         { snAgGblTrapMessage }
    STATUS          current
    DESCRIPTION     
            "The SNMP trap that is generated when GSLB health check for an address transitions
             from down to active state."
    ::= { foundry 0 43 }

snTrapL4GslbHealthCheckIpDown NOTIFICATION-TYPE
    OBJECTS         { snAgGblTrapMessage }
    STATUS          current
    DESCRIPTION     
            "The SNMP trap that is generated when GSLB health check for an address transitions
             from active to down state."
    ::= { foundry 0 44 }

snTrapL4GslbHealthCheckIpPortUp NOTIFICATION-TYPE
    OBJECTS         { snAgGblTrapMessage }
    STATUS          current
    DESCRIPTION     
            "The SNMP trap that is generated when a given port for a health check address is up."
    ::= { foundry 0 45 }

snTrapL4GslbHealthCheckIpPortDown NOTIFICATION-TYPE
    OBJECTS         { snAgGblTrapMessage }
    STATUS          current
    DESCRIPTION     
            "The SNMP trap that is generated when a given port for a health check address is down."
    ::= { foundry 0 46 }

snTrapL4FirewallBecomeStandby NOTIFICATION-TYPE
    STATUS          current
    DESCRIPTION     
            "The SNMP trap that is generated when the server load
             balancing switch Firewall changes state from active to standby."
    ::= { foundry 0 47 }

snTrapL4FirewallBecomeActive NOTIFICATION-TYPE
    STATUS          current
    DESCRIPTION     
            "The SNMP trap that is generated when the server load
             balancing switch Firewall changes state from standby to active."
    ::= { foundry 0 48 }

snTrapL4FirewallPathUp NOTIFICATION-TYPE
    STATUS          current
    DESCRIPTION     
            "The SNMP trap that is generated when the server load
             balancing switch Firewall path is up."
    ::= { foundry 0 49 }

snTrapL4FirewallPathDown NOTIFICATION-TYPE
    STATUS          current
    DESCRIPTION     
            "The SNMP trap that is generated when the server load
             balancing switch Firewall path is down."
    ::= { foundry 0 50 }

snTrapIcmpLocalExceedBurst NOTIFICATION-TYPE
    OBJECTS         { snAgGblTrapMessage }
    STATUS          current
    DESCRIPTION     
            "The SNMP trap that is generated when incoming ICMP exceeds burst-MAX."
    ::= { foundry 0 51 }

snTrapIcmpTransitExceedBurst NOTIFICATION-TYPE
    OBJECTS         { snAgGblTrapMessage }
    STATUS          current
    DESCRIPTION     
            "The SNMP trap that is generated when transit ICMP exceeds burst-MAX."
    ::= { foundry 0 52 }

snTrapTcpLocalExceedBurst NOTIFICATION-TYPE
    OBJECTS         { snAgGblTrapMessage }
    STATUS          current
    DESCRIPTION     
            "The SNMP trap that is generated when incoming TCP SYN exceeds burst-MAX."
    ::= { foundry 0 53 }

snTrapTcpTransitExceedBurst NOTIFICATION-TYPE
    OBJECTS         { snAgGblTrapMessage }
    STATUS          current
    DESCRIPTION     
            "The SNMP trap that is generated when transit TCP exceeds burst-MAX."
    ::= { foundry 0 54 }

snTrapL4ContentVerification NOTIFICATION-TYPE
    STATUS          current
    DESCRIPTION     
            "The SNMP trap that is generated when the HTTP match-list pattern
             is found."
    ::= { foundry 0 55 }

snTrapDuplicateIp NOTIFICATION-TYPE
    STATUS          current
    DESCRIPTION     
            "Duplicate IP address detected."
    ::= { foundry 0 56 }

END -- end of module FOUNDRY-SN-TRAP-MIB.
