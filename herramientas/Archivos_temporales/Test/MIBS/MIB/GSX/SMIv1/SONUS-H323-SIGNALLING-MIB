--
-- This SMIv1 module has been generated by smidump 0.2-cvs. Do not edit.
--

SONUS-H323-SIGNALLING-MIB DEFINITIONS ::= BEGIN

IMPORTS
    Ipv6Address
        FROM IPV6-TC
    PerfCurrentCount
        FROM PerfHist-TC-MIB
    OBJECT-TYPE
        FROM RFC-1212
    TRAP-TYPE
        FROM RFC-1215
    IpAddress
        FROM RFC1155-SMI
    RowStatus
        FROM SNMPv2-TC
    sonusEventClass, sonusEventDescription, sonusEventLevel, 
    sonusEventTime, sonusSequenceId
        FROM SONUS-COMMON-MIB
    sonusSignallingMIBs
        FROM SONUS-SMI
    SonusAdminState, SonusName, SonusNameReference, SonusServiceState, 
    SonusShelfIndex, SonusSlotIndex
        FROM SONUS-TC;

sonusH323SignallingMIB OBJECT IDENTIFIER
    ::= { sonusSignallingMIBs 6 }

-- sonusH323SignallingMIB MODULE-IDENTITY
--     LAST-UPDATED    "201209180000Z"
--     ORGANIZATION    
--             "Sonus Networks, Inc."
--     CONTACT-INFO    
--             "   Customer Support    
--              Sonus Networks, Inc.
--              7 Technology Park Drive
--              Westford, MA 01886
--              USA
--              
--              Tel: 978-614-8100
--              Fax: 978-614-8609"
--     DESCRIPTION     
--             "The MIB Module for H323 IP Call Signal Channel Management."
--     ::= { sonusSignallingMIBs 6 }


sonusH323SignallingMIBObjects OBJECT IDENTIFIER
    ::= { sonusH323SignallingMIB 1 }

sonusH323SigTimerObjects OBJECT IDENTIFIER
    ::= { sonusH323SignallingMIBObjects 1 }

sonusH323SigSrvTimerT301 OBJECT-TYPE
    SYNTAX          INTEGER (0..65535)
    ACCESS          read-write
    STATUS          mandatory
    DESCRIPTION     
            "The T301 timer (in seconds). This value applies to all calls."
    DEFVAL          { 180 }
    ::= { sonusH323SigTimerObjects 1 }

sonusH323SigSrvTimerT303 OBJECT-TYPE
    SYNTAX          INTEGER (0..127)
    ACCESS          read-write
    STATUS          mandatory
    DESCRIPTION     
            "The T303 call timer (in seconds). This value applies to all calls."
    DEFVAL          { 4 }
    ::= { sonusH323SigTimerObjects 2 }

sonusH323SigSrvTimerT310 OBJECT-TYPE
    SYNTAX          INTEGER (0..127)
    ACCESS          read-write
    STATUS          mandatory
    DESCRIPTION     
            "The T310 timer (in seconds). This value applies to all calls."
    DEFVAL          { 10 }
    ::= { sonusH323SigTimerObjects 3 }

sonusH323SigTimerEstablish OBJECT-TYPE
    SYNTAX          INTEGER (0..127)
    ACCESS          read-write
    STATUS          mandatory
    DESCRIPTION     
            "The H225 signal channel establishment timer (in seconds.)  This value applies to all signal channels."
    DEFVAL          { 4 }
    ::= { sonusH323SigTimerObjects 4 }

sonusH323SigTimerTcpConnect OBJECT-TYPE
    SYNTAX          INTEGER (0..127)
    ACCESS          read-write
    STATUS          mandatory
    DESCRIPTION     
            "The TCP connect timer (in seconds). This applies to all signal channels."
    DEFVAL          { 3 }
    ::= { sonusH323SigTimerObjects 5 }

sonusH323SrvLocalRingbackState OBJECT-TYPE
    SYNTAX          INTEGER { disabled(1), enabled(2) }
    ACCESS          read-write
    STATUS          obsolete
    DESCRIPTION     
            "Controls playing of local ringback by GSX on PSTN side. As of Rel 5.1,
             this feature is controlled by PSX. Hence, this object is obsoleted from
             GSX Rel 5.1"
    DEFVAL          { enabled }
    ::= { sonusH323SigTimerObjects 6 }

sonusH323SigSrvTimerT302 OBJECT-TYPE
    SYNTAX          Gauge (0..127)
    ACCESS          read-write
    STATUS          mandatory
    DESCRIPTION     
            "The T302 call timer (in seconds). This value applies to all calls."
    DEFVAL          { 15 }
    ::= { sonusH323SigTimerObjects 7 }

sonusH323SigSrvTimerT304 OBJECT-TYPE
    SYNTAX          Gauge (0..127)
    ACCESS          read-write
    STATUS          mandatory
    DESCRIPTION     
            "The T304 call timer (in seconds). This value applies to all calls."
    DEFVAL          { 20 }
    ::= { sonusH323SigTimerObjects 8 }

sonusH323H225PortObjects OBJECT IDENTIFIER
    ::= { sonusH323SignallingMIBObjects 2 }

sonusH323H225PortIpAddress OBJECT-TYPE
    SYNTAX          IpAddress
    ACCESS          read-write
    STATUS          deprecated
    DESCRIPTION     
            "IP Address of the H225 call signaling port - this is a required parameter. This object deprecated as of GSX release V05.00.00"
    DEFVAL          { '00000000'H }
    ::= { sonusH323H225PortObjects 1 }

sonusH323H225PortNum OBJECT-TYPE
    SYNTAX          INTEGER (1..65535)
    ACCESS          read-write
    STATUS          deprecated
    DESCRIPTION     
            "TCP port number of the H225 call signaling port (default is H323 registered port 1720). This object deprecated as of GSX release V05.00.00"
    ::= { sonusH323H225PortObjects 2 }

sonusH323H225PortShelfId OBJECT-TYPE
    SYNTAX          SonusShelfIndex
    ACCESS          read-write
    STATUS          deprecated
    DESCRIPTION     
            "The shelf number of the PNS board providing the H225 connection service. This object deprecated as of GSX release V05.00.00"
    ::= { sonusH323H225PortObjects 3 }

sonusH323H225PortSlotNum OBJECT-TYPE
    SYNTAX          SonusSlotIndex
    ACCESS          read-write
    STATUS          deprecated
    DESCRIPTION     
            "The slot number of the PNS board providing the H225 connection service. This object deprecated as of GSX release V05.00.00"
    ::= { sonusH323H225PortObjects 4 }

sonusH323H245PortObjects OBJECT IDENTIFIER
    ::= { sonusH323SignallingMIBObjects 3 }

sonusH323H245PortIpAddress OBJECT-TYPE
    SYNTAX          IpAddress
    ACCESS          read-write
    STATUS          deprecated
    DESCRIPTION     
            "IP Address of the H245 port - this is a required parameter. This object deprecated as of GSX release V05.00.00"
    DEFVAL          { '00000000'H }
    ::= { sonusH323H245PortObjects 1 }

sonusH323H245PortShelfId OBJECT-TYPE
    SYNTAX          SonusShelfIndex
    ACCESS          read-write
    STATUS          deprecated
    DESCRIPTION     
            "The shelf number of the PNS board providing the H245 connection service. This object deprecated as of GSX release V05.00.00"
    ::= { sonusH323H245PortObjects 2 }

sonusH323H245PortSlotNum OBJECT-TYPE
    SYNTAX          SonusSlotIndex
    ACCESS          read-write
    STATUS          deprecated
    DESCRIPTION     
            "The slot number of the PNS board providing the H225 connection service. This object deprecated as of GSX release V05.00.00"
    ::= { sonusH323H245PortObjects 3 }

sonusH323SigControlObjects OBJECT IDENTIFIER
    ::= { sonusH323SignallingMIBObjects 4 }

sonusH323SignalingControlMode OBJECT-TYPE
    SYNTAX          SonusServiceState
    ACCESS          read-write
    STATUS          deprecated
    DESCRIPTION     
            "This object controls the mode of H323 service. This object deprecated as of GSX release V05.00.00"
    DEFVAL          { outOfService }
    ::= { sonusH323SigControlObjects 1 }

sonusH323SignalingControlState OBJECT-TYPE
    SYNTAX          SonusAdminState
    ACCESS          read-write
    STATUS          deprecated
    DESCRIPTION     
            "This object controls the state of H323 service. This object deprecated as of GSX release V05.00.00"
    DEFVAL          { disabled }
    ::= { sonusH323SigControlObjects 2 }

sonusH323SignalingControlAction OBJECT-TYPE
    SYNTAX          INTEGER { none(1), force(2), dryup(3) }
    ACCESS          read-write
    STATUS          deprecated
    DESCRIPTION     
            "This object controls to force all call drops or let the call  finish during a time period,
             which is controled by sonusH323SigTimerDryupTimeout. This object deprecated as of GSX release V05.00.00"
    DEFVAL          { none }
    ::= { sonusH323SigControlObjects 3 }

sonusH323SignalingControlDryupTimeout OBJECT-TYPE
    SYNTAX          INTEGER (0..1440)
    ACCESS          read-write
    STATUS          deprecated
    DESCRIPTION     
            "This timer controls the time (in minutes) to wait to place the H323 into out of
             service state, when the dryup command is issued. This object deprecated as of GSX release V05.00.00"
    DEFVAL          { 0 }
    ::= { sonusH323SigControlObjects 4 }

sonusH323FeObjects OBJECT IDENTIFIER
    ::= { sonusH323SignallingMIBObjects 5 }

sonusH323FeCurrentStatTable OBJECT-TYPE
    SYNTAX          SEQUENCE OF SonusH323FeCurrentStatEntry
    ACCESS          not-accessible
    STATUS          mandatory
    DESCRIPTION     
            "The Sonus H323 FE Group Current statistic table."
    ::= { sonusH323FeObjects 1 }

sonusH323FeCurrentStatEntry OBJECT-TYPE
    SYNTAX          SonusH323FeCurrentStatEntry
    ACCESS          not-accessible
    STATUS          mandatory
    DESCRIPTION     
            "An entry in the Sonus H323 FE current statistics table."
    INDEX           { sonusH323FeCurrentStatIndex }
    ::= { sonusH323FeCurrentStatTable 1 }

SonusH323FeCurrentStatEntry ::=
    SEQUENCE {
        sonusH323FeCurrentStatIndex     INTEGER,
        sonusH323FeCurrentStatStatus    INTEGER,
        sonusH323FeCurrentStatInCallsCompl  PerfCurrentCount,
        sonusH323FeCurrentStatEgCallsCompl  PerfCurrentCount,
        sonusH323FeCurrentStatInCallsAttemped     PerfCurrentCount,
        sonusH323FeCurrentStatEgCallsAttemped     PerfCurrentCount,
        sonusH323FeCurrentStatH225MsgNoSent   PerfCurrentCount,
        sonusH323FeCurrentStatH225MsgBytesSent      PerfCurrentCount,
        sonusH323FeCurrentStatH225MsgNoRcv  PerfCurrentCount,
        sonusH323FeCurrentStatH225MsgBytesRcv     PerfCurrentCount,
        sonusH323FeCurrentStatH245MsgNoSent   PerfCurrentCount,
        sonusH323FeCurrentStatH245MsgBytesSent      PerfCurrentCount,
        sonusH323FeCurrentStatH245MsgNoRcv  PerfCurrentCount,
        sonusH323FeCurrentStatH245MsgBytesRcv     PerfCurrentCount,
        sonusH323FeCurrentStatActiveCalls PerfCurrentCount,
        sonusH323FeCurrentStatH225TcpPortsOpened        PerfCurrentCount,
        sonusH323FeCurrentStatH245TcpPortsOpened        PerfCurrentCount,
        sonusH323FeCurrentStatH245TcpPortsAllocated           PerfCurrentCount
    }

sonusH323FeCurrentStatIndex OBJECT-TYPE
    SYNTAX          INTEGER
    ACCESS          read-only
    STATUS          mandatory
    DESCRIPTION     
            "The index into the Sonus H323 current table. "
    ::= { sonusH323FeCurrentStatEntry 1 }

sonusH323FeCurrentStatStatus OBJECT-TYPE
    SYNTAX          INTEGER { available(1), unavailable(2), dryup(3) }
    ACCESS          read-only
    STATUS          mandatory
    DESCRIPTION     
            "The state of this H323 port current status."
    ::= { sonusH323FeCurrentStatEntry 2 }

sonusH323FeCurrentStatInCallsCompl OBJECT-TYPE
    SYNTAX          PerfCurrentCount
    ACCESS          read-only
    STATUS          mandatory
    DESCRIPTION     
            "This object indicates the number of Ingress calls
             completed since system boots up. "
    ::= { sonusH323FeCurrentStatEntry 3 }

sonusH323FeCurrentStatEgCallsCompl OBJECT-TYPE
    SYNTAX          PerfCurrentCount
    ACCESS          read-only
    STATUS          mandatory
    DESCRIPTION     
            "This object indicates the number of Egress calls
             completed since system boots up. "
    ::= { sonusH323FeCurrentStatEntry 4 }

sonusH323FeCurrentStatInCallsAttemped OBJECT-TYPE
    SYNTAX          PerfCurrentCount
    ACCESS          read-only
    STATUS          mandatory
    DESCRIPTION     
            "This object indicates the number of Ingress calls
             attempted since system boots up. "
    ::= { sonusH323FeCurrentStatEntry 5 }

sonusH323FeCurrentStatEgCallsAttemped OBJECT-TYPE
    SYNTAX          PerfCurrentCount
    ACCESS          read-only
    STATUS          mandatory
    DESCRIPTION     
            "This object indicates the number of Egress calls
             attempted since system boots up. "
    ::= { sonusH323FeCurrentStatEntry 6 }

sonusH323FeCurrentStatH225MsgNoSent OBJECT-TYPE
    SYNTAX          PerfCurrentCount
    ACCESS          read-only
    STATUS          mandatory
    DESCRIPTION     
            "This object indicates the number of H225 messages 
             that have been sent since system boots up. "
    ::= { sonusH323FeCurrentStatEntry 7 }

sonusH323FeCurrentStatH225MsgBytesSent OBJECT-TYPE
    SYNTAX          PerfCurrentCount
    ACCESS          read-only
    STATUS          mandatory
    DESCRIPTION     
            "This object indicates the number of bytes of H225 messages 
             that have been sent since system boots up. "
    ::= { sonusH323FeCurrentStatEntry 8 }

sonusH323FeCurrentStatH225MsgNoRcv OBJECT-TYPE
    SYNTAX          PerfCurrentCount
    ACCESS          read-only
    STATUS          mandatory
    DESCRIPTION     
            "This object indicates the number of H225 messages 
             that have been received since system boots up. "
    ::= { sonusH323FeCurrentStatEntry 9 }

sonusH323FeCurrentStatH225MsgBytesRcv OBJECT-TYPE
    SYNTAX          PerfCurrentCount
    ACCESS          read-only
    STATUS          mandatory
    DESCRIPTION     
            "This object indicates the number of bytes of H225 messages 
             that have been received since system boots up. "
    ::= { sonusH323FeCurrentStatEntry 10 }

sonusH323FeCurrentStatH245MsgNoSent OBJECT-TYPE
    SYNTAX          PerfCurrentCount
    ACCESS          read-only
    STATUS          mandatory
    DESCRIPTION     
            "This object indicates the number of H245 messages 
             that have been sent since system boots up. "
    ::= { sonusH323FeCurrentStatEntry 11 }

sonusH323FeCurrentStatH245MsgBytesSent OBJECT-TYPE
    SYNTAX          PerfCurrentCount
    ACCESS          read-only
    STATUS          mandatory
    DESCRIPTION     
            "This object indicates the number of bytes of H245 messages 
             that have been sent since system boots up. "
    ::= { sonusH323FeCurrentStatEntry 12 }

sonusH323FeCurrentStatH245MsgNoRcv OBJECT-TYPE
    SYNTAX          PerfCurrentCount
    ACCESS          read-only
    STATUS          mandatory
    DESCRIPTION     
            "This object indicates the number of H245 messages 
             that have been received since system boots up. "
    ::= { sonusH323FeCurrentStatEntry 13 }

sonusH323FeCurrentStatH245MsgBytesRcv OBJECT-TYPE
    SYNTAX          PerfCurrentCount
    ACCESS          read-only
    STATUS          mandatory
    DESCRIPTION     
            "This object indicates the number of bytes of H245 messages 
             that have been received since system boots up. "
    ::= { sonusH323FeCurrentStatEntry 14 }

sonusH323FeCurrentStatActiveCalls OBJECT-TYPE
    SYNTAX          PerfCurrentCount
    ACCESS          read-only
    STATUS          mandatory
    DESCRIPTION     
            "This object indicates the number of active 
             calls at this moment."
    ::= { sonusH323FeCurrentStatEntry 15 }

sonusH323FeCurrentStatH225TcpPortsOpened OBJECT-TYPE
    SYNTAX          PerfCurrentCount
    ACCESS          read-only
    STATUS          mandatory
    DESCRIPTION     
            "This object indicates the number of H225 TCP ports 
             opened at this moment."
    ::= { sonusH323FeCurrentStatEntry 16 }

sonusH323FeCurrentStatH245TcpPortsOpened OBJECT-TYPE
    SYNTAX          PerfCurrentCount
    ACCESS          read-only
    STATUS          mandatory
    DESCRIPTION     
            "This object indicates the number of H245 TCP ports 
             opened at this moment."
    ::= { sonusH323FeCurrentStatEntry 17 }

sonusH323FeCurrentStatH245TcpPortsAllocated OBJECT-TYPE
    SYNTAX          PerfCurrentCount
    ACCESS          read-only
    STATUS          mandatory
    DESCRIPTION     
            "This object indicates the number of H245 TCP ports 
             allocated at this moment."
    ::= { sonusH323FeCurrentStatEntry 18 }

sonusH323SigPortTable OBJECT-TYPE
    SYNTAX          SEQUENCE OF SonusH323SigPortEntry
    ACCESS          not-accessible
    STATUS          mandatory
    DESCRIPTION     
            "Table of H323 Signaling Port configurations."
    ::= { sonusH323SignallingMIBObjects 6 }

sonusH323SigPortEntry OBJECT-TYPE
    SYNTAX          SonusH323SigPortEntry
    ACCESS          not-accessible
    STATUS          mandatory
    DESCRIPTION     
            "H323 signaling port configuration."
    INDEX           { sonusH323SigPortIndex }
    ::= { sonusH323SigPortTable 1 }

SonusH323SigPortEntry ::=
    SEQUENCE {
        sonusH323SigPortIndex           INTEGER,
        sonusH323SigPortSlot            SonusSlotIndex,
        sonusH323SigPortH225IpAddress   IpAddress,
        sonusH323SigPortH225PortNum     INTEGER,
        sonusH323SigPortH245IpAddress   IpAddress,
        sonusH323SigPortMode            SonusServiceState,
        sonusH323SigPortState           SonusAdminState,
        sonusH323SigPortAction          INTEGER,
        sonusH323SigPortDryupTimeout    INTEGER,
        sonusH323SigPortRowStatus       RowStatus,
        sonusH323SigPortNifGroupName    SonusNameReference,
        sonusH323SigPortSigZoneId       INTEGER,
        sonusH323SigPortSigZoneName     SonusNameReference,
        sonusH323SigPortH225Ip6Address  Ipv6Address,
        sonusH323SigPortH245Ip6Address  Ipv6Address,
        sonusH323SigPortH245IpVersion   INTEGER,
        sonusH323SigPortH225IpVersion   INTEGER
    }

sonusH323SigPortIndex OBJECT-TYPE
    SYNTAX          INTEGER
    ACCESS          read-only
    STATUS          mandatory
    DESCRIPTION     
            "Identifies the H323 signaling port entry."
    ::= { sonusH323SigPortEntry 1 }

sonusH323SigPortSlot OBJECT-TYPE
    SYNTAX          SonusSlotIndex
    ACCESS          read-write
    STATUS          mandatory
    DESCRIPTION     
            "The slot number of the PNS board providing the service."
    ::= { sonusH323SigPortEntry 2 }

sonusH323SigPortH225IpAddress OBJECT-TYPE
    SYNTAX          IpAddress
    ACCESS          read-write
    STATUS          mandatory
    DESCRIPTION     
            "IP Address of the H225 port."
    DEFVAL          { '00000000'H }
    ::= { sonusH323SigPortEntry 3 }

sonusH323SigPortH225PortNum OBJECT-TYPE
    SYNTAX          INTEGER (1..65535)
    ACCESS          read-write
    STATUS          mandatory
    DESCRIPTION     
            "Port number of H323 signaling port"
    DEFVAL          { 1720 }
    ::= { sonusH323SigPortEntry 4 }

sonusH323SigPortH245IpAddress OBJECT-TYPE
    SYNTAX          IpAddress
    ACCESS          read-write
    STATUS          mandatory
    DESCRIPTION     
            "IP Address of the H245 port."
    DEFVAL          { '00000000'H }
    ::= { sonusH323SigPortEntry 5 }

sonusH323SigPortMode OBJECT-TYPE
    SYNTAX          SonusServiceState
    ACCESS          read-write
    STATUS          mandatory
    DESCRIPTION     
            "Mode of the H323 signaling port."
    DEFVAL          { inService }
    ::= { sonusH323SigPortEntry 6 }

sonusH323SigPortState OBJECT-TYPE
    SYNTAX          SonusAdminState
    ACCESS          read-write
    STATUS          mandatory
    DESCRIPTION     
            "State of the H323 signaling port."
    DEFVAL          { disabled }
    ::= { sonusH323SigPortEntry 7 }

sonusH323SigPortAction OBJECT-TYPE
    SYNTAX          INTEGER { force(1), dryup(2) }
    ACCESS          read-write
    STATUS          mandatory
    DESCRIPTION     
            "This object controls whether calls are forced off or allowed to dryup upon a mode out-of-service."
    DEFVAL          { dryup }
    ::= { sonusH323SigPortEntry 8 }

sonusH323SigPortDryupTimeout OBJECT-TYPE
    SYNTAX          INTEGER (0..1440)
    ACCESS          read-write
    STATUS          mandatory
    DESCRIPTION     
            "This timer controls the time (in minutes) to dryup upon mode out-of-service with dryp."
    DEFVAL          { 0 }
    ::= { sonusH323SigPortEntry 9 }

sonusH323SigPortRowStatus OBJECT-TYPE
    SYNTAX          RowStatus
    ACCESS          read-write
    STATUS          mandatory
    DESCRIPTION     
            "This is for SNMP use."
    ::= { sonusH323SigPortEntry 10 }

sonusH323SigPortNifGroupName OBJECT-TYPE
    SYNTAX          SonusNameReference
    ACCESS          read-write
    STATUS          mandatory
    DESCRIPTION     
            "The NIF group associated with this signaling port."
    ::= { sonusH323SigPortEntry 11 }

sonusH323SigPortSigZoneId OBJECT-TYPE
    SYNTAX          INTEGER (0..32)
    ACCESS          read-only
    STATUS          obsolete
    DESCRIPTION     
            "The signaling zone to which this port belongs.
             This ID is automatically generated when a new signaling zone is created.
             Obsolete in release 6.5 by a new object: sonusZoneEntry."
    DEFVAL          { 0 }
    ::= { sonusH323SigPortEntry 12 }

sonusH323SigPortSigZoneName OBJECT-TYPE
    SYNTAX          SonusNameReference
    ACCESS          read-write
    STATUS          mandatory
    DESCRIPTION     
            "The signaling zone associated with this signaling port."
    ::= { sonusH323SigPortEntry 13 }

sonusH323SigPortH225Ip6Address OBJECT-TYPE
    SYNTAX          Ipv6Address
    ACCESS          read-write
    STATUS          mandatory
    DESCRIPTION     
            "IP6Address of the H225 port."
    ::= { sonusH323SigPortEntry 14 }

sonusH323SigPortH245Ip6Address OBJECT-TYPE
    SYNTAX          Ipv6Address
    ACCESS          read-write
    STATUS          mandatory
    DESCRIPTION     
            "IP Address of the H245 port."
    ::= { sonusH323SigPortEntry 15 }

sonusH323SigPortH245IpVersion OBJECT-TYPE
    SYNTAX          INTEGER { afInet(2), afInet6(24) }
    ACCESS          read-only
    STATUS          mandatory
    DESCRIPTION     
            "IP Address type for H225 "
    ::= { sonusH323SigPortEntry 16 }

sonusH323SigPortH225IpVersion OBJECT-TYPE
    SYNTAX          INTEGER { afInet(2), afInet6(24) }
    ACCESS          read-only
    STATUS          mandatory
    DESCRIPTION     
            "IP Address type for H225"
    ::= { sonusH323SigPortEntry 17 }

sonusH323SigServiceGroup OBJECT IDENTIFIER
    ::= { sonusH323SignallingMIBObjects 7 }

sonusH323SigServiceGroupNextIndex OBJECT-TYPE
    SYNTAX          INTEGER
    ACCESS          read-only
    STATUS          mandatory
    DESCRIPTION     
            "The next valid index to use when creating a new sonusH323SigServiceGroupEntry"
    ::= { sonusH323SigServiceGroup 1 }

sonusH323SigServiceGroupTable OBJECT-TYPE
    SYNTAX          SEQUENCE OF SonusH323SigServiceGroupEntry
    ACCESS          not-accessible
    STATUS          mandatory
    DESCRIPTION     
            "This table contains information about each H323 Service Group
             configured to be a member of the node. 
             A management entity may create rows for Service Group that are
             anticipated to be supported in the future."
    ::= { sonusH323SigServiceGroup 2 }

sonusH323SigServiceGroupEntry OBJECT-TYPE
    SYNTAX          SonusH323SigServiceGroupEntry
    ACCESS          not-accessible
    STATUS          mandatory
    DESCRIPTION     
            "This table describes the H323 Service Groups that interconnect
             GSX9000s"
    INDEX           { sonusH323SigServiceGroupListIndex }
    ::= { sonusH323SigServiceGroupTable 1 }

SonusH323SigServiceGroupEntry ::=
    SEQUENCE {
        sonusH323SigServiceGroupListIndex INTEGER,
        sonusH323SigServiceGroupName    SonusName,
        sonusH323SigServiceGroupRowStatus RowStatus,
        sonusH323SigServiceGroupAdminState  SonusAdminState,
        sonusH323SigServiceGroupMode    SonusServiceState,
        sonusH323SigServiceGroupAction  INTEGER,
        sonusH323SigServiceGroupDryupTimeout    INTEGER,
        sonusH323SigServiceGroupTG      SonusNameReference,
        sonusH323SigServiceGroupDiscTreatmentProfileName                SonusNameReference,
        sonusH323SigServiceGroupTonePackageName       SonusNameReference,
        sonusH323SigServiceGroupSourceAddressFiltering              SonusAdminState,
        sonusH323SigServiceGroupAnsSupervisionTimeout             INTEGER,
        sonusH323SigServiceGroupSigZoneId INTEGER,
        sonusH323SigServiceGroupMediaNifGroupName         SonusNameReference,
        sonusH323SigServiceGroupSigZoneName   SonusNameReference,
        sonusH323SigServiceGroupCongRelTimeout      INTEGER,
        sonusH323SigServiceGroupCrankBackProfile        INTEGER,
        sonusH323SigServiceGroupLdcTimeout  INTEGER,
        sonusH323SigServiceGroupLdcTimeoutAction        INTEGER,
        sonusH323SigServiceGroupLdcTimeoutCauseValue            INTEGER,
        sonusH323SigServiceGroupLdcEmergencyCalls         INTEGER,
        sonusH323SigServiceGroupMinDigitsForQuery         Gauge,
        sonusH323SigServiceGroupOverlapDialing      INTEGER,
        sonusH323SigServiceGroupRespectBearerCapability               SonusAdminState,
        sonusH323SigServiceGroupSkipCrankBackProfile            Gauge,
        sonusH323SigServiceGroupMediaZoneName     SonusNameReference,
        sonusH323SigServiceGroupDirectMediaAllowed          SonusAdminState,
        sonusH323SigServiceGroupMediaZoneId   Gauge,
        sonusH323SigServiceGroupPreallocateResPad         SonusAdminState,
        sonusH323SigServiceGroupSendingCompleteEnbloc             SonusAdminState,
        sonusH323SigServiceGroupArsProfileName      SonusNameReference,
        sonusH323SigServiceGroupSlowStartSupport        INTEGER,
        sonusH323SigServiceGroupForceTONState     SonusAdminState,
        sonusH323SigServiceGroupForceTONValue     INTEGER,
        sonusH323SigServiceGroupCallPreservation        SonusAdminState,
        sonusH323SigServiceGroupCallPreservationTimeout               INTEGER,
        sonusH323SigServiceGroupH245Tunneling     INTEGER
    }

sonusH323SigServiceGroupListIndex OBJECT-TYPE
    SYNTAX          INTEGER
    ACCESS          read-only
    STATUS          mandatory
    DESCRIPTION     
            "The index of the H323 Service Group entry."
    ::= { sonusH323SigServiceGroupEntry 1 }

sonusH323SigServiceGroupName OBJECT-TYPE
    SYNTAX          SonusName
    ACCESS          read-write
    STATUS          mandatory
    DESCRIPTION     
            "The name of this H323 Service Group."
    ::= { sonusH323SigServiceGroupEntry 2 }

sonusH323SigServiceGroupRowStatus OBJECT-TYPE
    SYNTAX          RowStatus
    ACCESS          read-write
    STATUS          mandatory
    DESCRIPTION     
            ""
    ::= { sonusH323SigServiceGroupEntry 3 }

sonusH323SigServiceGroupAdminState OBJECT-TYPE
    SYNTAX          SonusAdminState
    ACCESS          read-write
    STATUS          mandatory
    DESCRIPTION     
            "The admin state of the this H323 Service Group."
    ::= { sonusH323SigServiceGroupEntry 4 }

sonusH323SigServiceGroupMode OBJECT-TYPE
    SYNTAX          SonusServiceState
    ACCESS          read-write
    STATUS          mandatory
    DESCRIPTION     
            "The mode of operation of this H323 Service Group."
    ::= { sonusH323SigServiceGroupEntry 5 }

sonusH323SigServiceGroupAction OBJECT-TYPE
    SYNTAX          INTEGER { dryup(1), force(2), undefined(3) }
    ACCESS          read-write
    STATUS          mandatory
    DESCRIPTION     
            "The action taken on calls for this H323 Service Group."
    DEFVAL          { dryup }
    ::= { sonusH323SigServiceGroupEntry 6 }

sonusH323SigServiceGroupDryupTimeout OBJECT-TYPE
    SYNTAX          INTEGER (0..1440)
    ACCESS          read-write
    STATUS          mandatory
    DESCRIPTION     
            "The timeout value in minutes for dryup action for this
             H323 Service Group."
    DEFVAL          { 5 }
    ::= { sonusH323SigServiceGroupEntry 7 }

sonusH323SigServiceGroupTG OBJECT-TYPE
    SYNTAX          SonusNameReference
    ACCESS          read-write
    STATUS          mandatory
    DESCRIPTION     
            "The Trunk Group which this H323 Service Group belongs to."
    ::= { sonusH323SigServiceGroupEntry 8 }

sonusH323SigServiceGroupDiscTreatmentProfileName OBJECT-TYPE
    SYNTAX          SonusNameReference
    ACCESS          read-write
    STATUS          mandatory
    DESCRIPTION     
            "The disconnect treatment profile to be used for this service."
    ::= { sonusH323SigServiceGroupEntry 9 }

sonusH323SigServiceGroupTonePackageName OBJECT-TYPE
    SYNTAX          SonusNameReference
    ACCESS          read-write
    STATUS          mandatory
    DESCRIPTION     
            "The tone package to be used for this service."
    ::= { sonusH323SigServiceGroupEntry 10 }

sonusH323SigServiceGroupSourceAddressFiltering OBJECT-TYPE
    SYNTAX          SonusAdminState
    ACCESS          read-write
    STATUS          mandatory
    DESCRIPTION     
            "This object indicates whether or not the GSX will perform IP source
             address filtering on incoming media packets for this trunk group.
             When ENABLED, the SG will only accept incoming media packets whose
             source address matches the destination address of outbound packets.
             When DISABLED, the GSX does not filter the incoming media stream.
             The source address to filter on is supplied during call signaling."
    DEFVAL          { disabled }
    ::= { sonusH323SigServiceGroupEntry 11 }

sonusH323SigServiceGroupAnsSupervisionTimeout OBJECT-TYPE
    SYNTAX          INTEGER (0..1000)
    ACCESS          read-write
    STATUS          mandatory
    DESCRIPTION     
            "This is the time from egress call setup to egress receiving an answer."
    DEFVAL          { 300 }
    ::= { sonusH323SigServiceGroupEntry 12 }

sonusH323SigServiceGroupSigZoneId OBJECT-TYPE
    SYNTAX          INTEGER (0..32)
    ACCESS          read-only
    STATUS          mandatory
    DESCRIPTION     
            "The H.323 Signaling Zone ID."
    DEFVAL          { 0 }
    ::= { sonusH323SigServiceGroupEntry 13 }

sonusH323SigServiceGroupMediaNifGroupName OBJECT-TYPE
    SYNTAX          SonusNameReference
    ACCESS          read-write
    STATUS          mandatory
    DESCRIPTION     
            "The Media NIF Group associated with this H.323 Service Group."
    ::= { sonusH323SigServiceGroupEntry 14 }

sonusH323SigServiceGroupSigZoneName OBJECT-TYPE
    SYNTAX          SonusNameReference
    ACCESS          read-write
    STATUS          mandatory
    DESCRIPTION     
            "The Signaling Zone associated with this H.323 Service Group."
    ::= { sonusH323SigServiceGroupEntry 15 }

sonusH323SigServiceGroupCongRelTimeout OBJECT-TYPE
    SYNTAX          INTEGER (0..5)
    ACCESS          read-write
    STATUS          mandatory
    DESCRIPTION     
            "Time to delay sending of release during congestion"
    DEFVAL          { 0 }
    ::= { sonusH323SigServiceGroupEntry 16 }

sonusH323SigServiceGroupCrankBackProfile OBJECT-TYPE
    SYNTAX          INTEGER (1..20)
    ACCESS          read-write
    STATUS          mandatory
    DESCRIPTION     
            "The Crank Back Profile to be used for this Service Group."
    DEFVAL          { 1 }
    ::= { sonusH323SigServiceGroupEntry 17 }

sonusH323SigServiceGroupLdcTimeout OBJECT-TYPE
    SYNTAX          INTEGER (0..2880)
    ACCESS          read-write
    STATUS          mandatory
    DESCRIPTION     
            "The timeout value of the long duration call timer in minutes.
             Allowed values are 0 to disable the timer, 60-2880 minutes to set the timer."
    DEFVAL          { 0 }
    ::= { sonusH323SigServiceGroupEntry 18 }

sonusH323SigServiceGroupLdcTimeoutAction OBJECT-TYPE
    SYNTAX          INTEGER { noAction(0), trap(1), release(2), 
                        trapAndRelease(3) }
    ACCESS          read-write
    STATUS          mandatory
    DESCRIPTION     
            "This is the action to take if the long duration call timer
             expires.  The call may be released or a trap fired, or both."
    DEFVAL          { noAction }
    ::= { sonusH323SigServiceGroupEntry 19 }

sonusH323SigServiceGroupLdcTimeoutCauseValue OBJECT-TYPE
    SYNTAX          INTEGER (1..127)
    ACCESS          read-write
    STATUS          mandatory
    DESCRIPTION     
            "The Q.850 release value to use should the call be released 
             due to long duration call timer expiry"
    DEFVAL          { 41 }
    ::= { sonusH323SigServiceGroupEntry 20 }

sonusH323SigServiceGroupLdcEmergencyCalls OBJECT-TYPE
    SYNTAX          INTEGER { include(0), exclude(1) }
    ACCESS          read-write
    STATUS          mandatory
    DESCRIPTION     
            "Whether Emergency Calls should be exluded from 
             or included in Long Duration Call disconnect procedures"
    DEFVAL          { exclude }
    ::= { sonusH323SigServiceGroupEntry 21 }

sonusH323SigServiceGroupMinDigitsForQuery OBJECT-TYPE
    SYNTAX          Gauge (0..30)
    ACCESS          read-write
    STATUS          mandatory
    DESCRIPTION     
            "This parameter controls the number of called address digits
             to be collected before performing the 1st policy query during
             overlap receiving. If this is 0, then this parameter is
             irrelevant in controlling policy query."
    DEFVAL          { 0 }
    ::= { sonusH323SigServiceGroupEntry 22 }

sonusH323SigServiceGroupOverlapDialing OBJECT-TYPE
    SYNTAX          INTEGER { disabled(1), enabled(2), ingressonly(3), 
                        egressonly(4) }
    ACCESS          read-write
    STATUS          mandatory
    DESCRIPTION     
            "If ENABLED/INGRESSONLY, GSX supports ingress H.323 overlap dialing.
             If ENABLED/EGRESSONLY, GSX supports egress H.323 overlap dialing.
             If DISABLED, GSX expects a complete set of addressing digits in an incoming
             SETUP message and call address collection must be complete before 
             egressing an H.323 call."
    DEFVAL          { disabled }
    ::= { sonusH323SigServiceGroupEntry 23 }

sonusH323SigServiceGroupRespectBearerCapability OBJECT-TYPE
    SYNTAX          SonusAdminState
    ACCESS          read-write
    STATUS          mandatory
    DESCRIPTION     
            "If ENABLED, GSX accepts unchanged the Bearer Capability
             Information Element values received in H.225 SETUP.
             If DISABLED, GSX passes only the information transfer
             capabilities Speech or 3.1 kHz Audio unchanged and otherwise
             sets the fields of Bearer Capability to default values."
    DEFVAL          { disabled }
    ::= { sonusH323SigServiceGroupEntry 24 }

sonusH323SigServiceGroupSkipCrankBackProfile OBJECT-TYPE
    SYNTAX          Gauge (0..20)
    ACCESS          read-write
    STATUS          mandatory
    DESCRIPTION     
            "The Skip Crankback Profile to be used for this Service Group."
    DEFVAL          { 0 }
    ::= { sonusH323SigServiceGroupEntry 25 }

sonusH323SigServiceGroupMediaZoneName OBJECT-TYPE
    SYNTAX          SonusNameReference
    ACCESS          read-write
    STATUS          mandatory
    DESCRIPTION     
            "The Media Zone to which this H323 service group is bound."
    ::= { sonusH323SigServiceGroupEntry 26 }

sonusH323SigServiceGroupDirectMediaAllowed OBJECT-TYPE
    SYNTAX          SonusAdminState
    ACCESS          read-write
    STATUS          mandatory
    DESCRIPTION     
            "This indicates whether or not Direct Media should be attempted
             for calls to or from endpoints in this service group. If
             enabled, the GSX will attempt to set up the media path such
             that media flows directly between two Direct-Media-enabled 
             endpoints in the same media zone."
    DEFVAL          { disabled }
    ::= { sonusH323SigServiceGroupEntry 27 }

sonusH323SigServiceGroupMediaZoneId OBJECT-TYPE
    SYNTAX          Gauge (0..32)
    ACCESS          read-only
    STATUS          mandatory
    DESCRIPTION     
            "Identifies the Media Zone this H323 service group is bound to."
    ::= { sonusH323SigServiceGroupEntry 28 }

sonusH323SigServiceGroupPreallocateResPad OBJECT-TYPE
    SYNTAX          SonusAdminState
    ACCESS          read-write
    STATUS          mandatory
    DESCRIPTION     
            "This indicates whether or not a resource pad is pre-allocated 
             during an incoming fast start call procedure that results in 
             G.711 codec selected for the call. If subsequent Terminal Capability
             Set exchange deems resource pad not necessary, it will be released.
             It is advisable to turn on this setting to support DTMF digit collection, 
             such as for 2-stage dialing, when the selected codec for the call is 
             G.711. If enabled and no resource is available, the call will fail."
    DEFVAL          { disabled }
    ::= { sonusH323SigServiceGroupEntry 29 }

sonusH323SigServiceGroupSendingCompleteEnbloc OBJECT-TYPE
    SYNTAX          SonusAdminState
    ACCESS          read-write
    STATUS          mandatory
    DESCRIPTION     
            "This indicates whether or not to send sending complete IE 
             in enbloc setup message."
    DEFVAL          { disabled }
    ::= { sonusH323SigServiceGroupEntry 30 }

sonusH323SigServiceGroupArsProfileName OBJECT-TYPE
    SYNTAX          SonusNameReference
    ACCESS          read-write
    STATUS          mandatory
    DESCRIPTION     
            "The Address Reachability Service profile for this
             service group. None assigned means no reachability service
             enforced."
    ::= { sonusH323SigServiceGroupEntry 31 }

sonusH323SigServiceGroupSlowStartSupport OBJECT-TYPE
    SYNTAX          INTEGER { convert(1), passthru(2) }
    ACCESS          read-write
    STATUS          mandatory
    DESCRIPTION     
            "Determines whether an ingress H245 Slow Start should be
             converted to a forward offer at egress (e.g. Fast Start)
             or passed thru as a reverse offer (e.g. Slow Start)."
    DEFVAL          { convert }
    ::= { sonusH323SigServiceGroupEntry 32 }

sonusH323SigServiceGroupForceTONState OBJECT-TYPE
    SYNTAX          SonusAdminState
    ACCESS          read-write
    STATUS          mandatory
    DESCRIPTION     
            "This indicates status of Force Type of Number."
    DEFVAL          { disabled }
    ::= { sonusH323SigServiceGroupEntry 33 }

sonusH323SigServiceGroupForceTONValue OBJECT-TYPE
    SYNTAX          INTEGER (0..7)
    ACCESS          read-write
    STATUS          mandatory
    DESCRIPTION     
            "Identifies the Value of Force Type of Number."
    DEFVAL          { 0 }
    ::= { sonusH323SigServiceGroupEntry 34 }

sonusH323SigServiceGroupCallPreservation OBJECT-TYPE
    SYNTAX          SonusAdminState
    ACCESS          read-write
    STATUS          obsolete
    DESCRIPTION     
            "If enabled, a stable call's media is preserved
             despite the loss of a TCP signaling connection,
             H.225 or H.245 or both.  Attempts to transmit
             further on a lost connection, for supplementary
             services like hold/resume, will end the call.
             As of Rel 9.0, this feature is controlled by PSX. 
             Hence, this object is obsoleted from GSX Rel 9.0"
    DEFVAL          { disabled }
    ::= { sonusH323SigServiceGroupEntry 35 }

sonusH323SigServiceGroupCallPreservationTimeout OBJECT-TYPE
    SYNTAX          INTEGER (0..1440)
    ACCESS          read-write
    STATUS          obsolete
    DESCRIPTION     
            "A limit in minutes on how long a call may be
             preserved after loss of a TCP connection before
             it is forcibly terminated to reclaim resources.
             The value is in minutes.  Zero means unlimited.
             As of Rel 9.0, this feature is controlled by PSX. 
             Hence, this object is obsoleted from GSX Rel 9.0"
    DEFVAL          { 5 }
    ::= { sonusH323SigServiceGroupEntry 36 }

sonusH323SigServiceGroupH245Tunneling OBJECT-TYPE
    SYNTAX          INTEGER { version3(0), version4(1) }
    ACCESS          read-write
    STATUS          mandatory
    DESCRIPTION     
            "If set to VERSION3 (default), a H.245 message is
             sent in a H.225 FACILITY message with empty 
             facility-UUIE as mandated by the version 3 H.225 
             specification. If set to VERSION4, it is sent
             in a H.225 FACILITY message with non-empty
             facility-UUIE as mandated by the version 4
             specification. H.245 tunneling is always
             supported but the peer can disable this for
             the call leg rendering this setting irrelevant."
    DEFVAL          { 0 }
    ::= { sonusH323SigServiceGroupEntry 37 }

sonusH323SigServiceGroupStatTable OBJECT-TYPE
    SYNTAX          SEQUENCE OF SonusH323SigServiceGroupStatEntry
    ACCESS          not-accessible
    STATUS          mandatory
    DESCRIPTION     
            "This table contains status information about each H323 Service
             Group in the GSX9000 Switch node."
    ::= { sonusH323SigServiceGroup 3 }

sonusH323SigServiceGroupStatEntry OBJECT-TYPE
    SYNTAX          SonusH323SigServiceGroupStatEntry
    ACCESS          not-accessible
    STATUS          mandatory
    DESCRIPTION     
            "This table describes the status of the H323 Service Groups."
    INDEX           { sonusH323SigServiceGroupStatListIndex }
    ::= { sonusH323SigServiceGroupStatTable 1 }

SonusH323SigServiceGroupStatEntry ::=
    SEQUENCE {
        sonusH323SigServiceGroupStatListIndex     INTEGER,
        sonusH323SigServiceGroupStatStatus  INTEGER
    }

sonusH323SigServiceGroupStatListIndex OBJECT-TYPE
    SYNTAX          INTEGER (1..256)
    ACCESS          read-only
    STATUS          mandatory
    DESCRIPTION     
            "The index of the H323 Service Group."
    ::= { sonusH323SigServiceGroupStatEntry 1 }

sonusH323SigServiceGroupStatStatus OBJECT-TYPE
    SYNTAX          INTEGER { available(1), unavailable(2), dryup(3) }
    ACCESS          read-only
    STATUS          mandatory
    DESCRIPTION     
            "The state of the H323 Service Group."
    ::= { sonusH323SigServiceGroupStatEntry 2 }

sonusH323PreservedCallTable OBJECT-TYPE
    SYNTAX          SEQUENCE OF SonusH323PreservedCallEntry
    ACCESS          not-accessible
    STATUS          mandatory
    DESCRIPTION     
            "This table presents the H323 Preserved call data for the node."
    ::= { sonusH323SigServiceGroup 4 }

sonusH323PreservedCallEntry OBJECT-TYPE
    SYNTAX          SonusH323PreservedCallEntry
    ACCESS          not-accessible
    STATUS          mandatory
    DESCRIPTION     
            "This table describes the data of the H323 Preserved Call."
    INDEX           { sonusH323PreservedCallSlotIndex, 
                      sonusH323PreservedCallGcid, 
                      sonusH323PreservedCallLeg }
    ::= { sonusH323PreservedCallTable 1 }

SonusH323PreservedCallEntry ::=
    SEQUENCE {
        sonusH323PreservedCallShelfIndex SonusShelfIndex,
        sonusH323PreservedCallSlotIndex SonusSlotIndex,
        sonusH323PreservedCallGcid      INTEGER,
        sonusH323PreservedCallSigPort   INTEGER,
        sonusH323PreservedCallCrv       INTEGER,
        sonusH323PreservedCallLeg       INTEGER,
        sonusH323PreservedCallH225SockId INTEGER,
        sonusH323PreservedCallH245SockId INTEGER,
        sonusH323PreservedCallTimeUsed  INTEGER,
        sonusH323PreservedCallTimeLeft  INTEGER
    }

sonusH323PreservedCallShelfIndex OBJECT-TYPE
    SYNTAX          SonusShelfIndex
    ACCESS          read-only
    STATUS          mandatory
    DESCRIPTION     
            "Identifies the target shelf."
    ::= { sonusH323PreservedCallEntry 1 }

sonusH323PreservedCallSlotIndex OBJECT-TYPE
    SYNTAX          SonusSlotIndex
    ACCESS          read-only
    STATUS          mandatory
    DESCRIPTION     
            "Identifies the target slot."
    ::= { sonusH323PreservedCallEntry 2 }

sonusH323PreservedCallGcid OBJECT-TYPE
    SYNTAX          INTEGER
    ACCESS          read-only
    STATUS          mandatory
    DESCRIPTION     
            "Represents the global call identifier(GCID) for the call."
    ::= { sonusH323PreservedCallEntry 3 }

sonusH323PreservedCallSigPort OBJECT-TYPE
    SYNTAX          INTEGER
    ACCESS          read-only
    STATUS          mandatory
    DESCRIPTION     
            "Gives the signalling port for the preserved call."
    ::= { sonusH323PreservedCallEntry 4 }

sonusH323PreservedCallCrv OBJECT-TYPE
    SYNTAX          INTEGER
    ACCESS          read-only
    STATUS          mandatory
    DESCRIPTION     
            "Represents the Call Referece Value(CRV) for the call."
    ::= { sonusH323PreservedCallEntry 5 }

sonusH323PreservedCallLeg OBJECT-TYPE
    SYNTAX          INTEGER
    ACCESS          read-only
    STATUS          mandatory
    DESCRIPTION     
            "Represents the Call leg of the call."
    ::= { sonusH323PreservedCallEntry 6 }

sonusH323PreservedCallH225SockId OBJECT-TYPE
    SYNTAX          INTEGER
    ACCESS          read-only
    STATUS          mandatory
    DESCRIPTION     
            "H225 socket ID for the preserved call"
    ::= { sonusH323PreservedCallEntry 7 }

sonusH323PreservedCallH245SockId OBJECT-TYPE
    SYNTAX          INTEGER
    ACCESS          read-only
    STATUS          mandatory
    DESCRIPTION     
            "H245 socket ID for the preserved call"
    ::= { sonusH323PreservedCallEntry 8 }

sonusH323PreservedCallTimeUsed OBJECT-TYPE
    SYNTAX          INTEGER
    ACCESS          read-only
    STATUS          mandatory
    DESCRIPTION     
            "Time elapsed since the call is preserved"
    ::= { sonusH323PreservedCallEntry 9 }

sonusH323PreservedCallTimeLeft OBJECT-TYPE
    SYNTAX          INTEGER
    ACCESS          read-only
    STATUS          mandatory
    DESCRIPTION     
            "Time left for the preserved call to tear down"
    ::= { sonusH323PreservedCallEntry 10 }

sonusH323SigPortPerNifStatusTable OBJECT-TYPE
    SYNTAX          SEQUENCE OF SonusH323SigPortPerNifStatusEntry
    ACCESS          not-accessible
    STATUS          mandatory
    DESCRIPTION     
            "Table of H.323 Signalling Port Per-NIF status."
    ::= { sonusH323SignallingMIBObjects 8 }

sonusH323SigPortPerNifStatusEntry OBJECT-TYPE
    SYNTAX          SonusH323SigPortPerNifStatusEntry
    ACCESS          not-accessible
    STATUS          mandatory
    DESCRIPTION     
            "H.323 Signalling Port Per-NIF Status."
    INDEX           { sonusH323SigPortPerNifStatusIndex, 
                      sonusH323SigPortPerNifStatusIfNum }
    ::= { sonusH323SigPortPerNifStatusTable 1 }

SonusH323SigPortPerNifStatusEntry ::=
    SEQUENCE {
        sonusH323SigPortPerNifStatusIndex INTEGER,
        sonusH323SigPortPerNifStatusIfNum INTEGER,
        sonusH323SigPortPerNifStatusNifName   SonusNameReference,
        sonusH323SigPortPerNifStatusStatus  INTEGER
    }

sonusH323SigPortPerNifStatusIndex OBJECT-TYPE
    SYNTAX          INTEGER
    ACCESS          read-only
    STATUS          mandatory
    DESCRIPTION     
            "H.323 signaling port index number."
    ::= { sonusH323SigPortPerNifStatusEntry 1 }

sonusH323SigPortPerNifStatusIfNum OBJECT-TYPE
    SYNTAX          INTEGER
    ACCESS          read-only
    STATUS          mandatory
    DESCRIPTION     
            "The NIF's Interface number."
    ::= { sonusH323SigPortPerNifStatusEntry 2 }

sonusH323SigPortPerNifStatusNifName OBJECT-TYPE
    SYNTAX          SonusNameReference
    ACCESS          read-only
    STATUS          mandatory
    DESCRIPTION     
            "The NIF's name."
    ::= { sonusH323SigPortPerNifStatusEntry 3 }

sonusH323SigPortPerNifStatusStatus OBJECT-TYPE
    SYNTAX          INTEGER { unavailable(0), available(1), 
                        notApplicable(2) }
    ACCESS          read-only
    STATUS          mandatory
    DESCRIPTION     
            "The availability status of the local address allocated
             to the NIF of the NIF group bound to this signaling port."
    ::= { sonusH323SigPortPerNifStatusEntry 4 }

sonusH323SignallingMIBNotifications OBJECT IDENTIFIER
    ::= { sonusH323SignallingMIB 2 }

sonusH323SignallingMIBNotificationsPrefix OBJECT IDENTIFIER
    ::= { sonusH323SignallingMIBNotifications 0 }

sonusH323SignallingMIBNotificationsObjects OBJECT IDENTIFIER
    ::= { sonusH323SignallingMIBNotifications 1 }

sonusH323SigSvcGrpName OBJECT-TYPE
    SYNTAX          SonusNameReference
    ACCESS          read-only
    STATUS          mandatory
    DESCRIPTION     
            "Name of the H323 service group."
    ::= { sonusH323SignallingMIBNotificationsObjects 1 }

sonusH323SigSvcGrpInServiceNotification TRAP-TYPE
    ENTERPRISE      sonusH323SignallingMIBNotifications
    VARIABLES       { sonusH323SigSvcGrpName, sonusEventDescription, 
                      sonusEventClass, sonusEventLevel, sonusSequenceId, 
                      sonusEventTime }
--     STATUS          mandatory
    DESCRIPTION     
            "This trap indicates that the H323 Service Group was put
             into service by maintenance staff."
    ::= 1

sonusH323SigSvcGrpOutOfServiceNotification TRAP-TYPE
    ENTERPRISE      sonusH323SignallingMIBNotifications
    VARIABLES       { sonusH323SigSvcGrpName, sonusEventDescription, 
                      sonusEventClass, sonusEventLevel, sonusSequenceId, 
                      sonusEventTime }
--     STATUS          mandatory
    DESCRIPTION     
            "This trap indicates that the H323 Service Group was taken
             out of service by maintenance staff."
    ::= 2

END -- end of module SONUS-H323-SIGNALLING-MIB.
