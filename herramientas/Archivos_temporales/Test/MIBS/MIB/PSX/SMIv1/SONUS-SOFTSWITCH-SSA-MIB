--
-- This SMIv1 module has been generated by smidump 0.2-cvs. Do not edit.
--

SONUS-SOFTSWITCH-SSA-MIB DEFINITIONS ::= BEGIN

IMPORTS
    OBJECT-TYPE
        FROM RFC-1212
    TRAP-TYPE
        FROM RFC-1215
    Counter, Gauge, TimeTicks
        FROM RFC1155-SMI
    sonusEventClass, sonusEventDescription, sonusEventLevel, 
    sonusEventTime
        FROM SONUS-COMMON-MIB
    sonusServicesMIBs
        FROM SONUS-SMI
    SonusName
        FROM SONUS-TC;

sonusSoftSwitchSsaMIB OBJECT IDENTIFIER
    ::= { sonusServicesMIBs 45 }

sonusSoftSwitchSsaMIBObjects OBJECT IDENTIFIER
    ::= { sonusSoftSwitchSsaMIB 1 }

sonusSoftSwitchSsaStatistics OBJECT IDENTIFIER
    ::= { sonusSoftSwitchSsaMIBObjects 1 }

sonusSoftSwitchOutboundLicenseCounters OBJECT IDENTIFIER
    ::= { sonusSoftSwitchSsaStatistics 1 }

sonusSoftSwitchOutboundLicenseTable OBJECT-TYPE
    SYNTAX          SEQUENCE OF SonusSoftSwitchOutboundLicenseEntry
    ACCESS          not-accessible
    STATUS          mandatory
    DESCRIPTION     
            "Count Feature or on/off license enabled for the node"
    ::= { sonusSoftSwitchOutboundLicenseCounters 1 }

sonusSoftSwitchOutboundLicenseEntry OBJECT-TYPE
    SYNTAX          SonusSoftSwitchOutboundLicenseEntry
    ACCESS          not-accessible
    STATUS          mandatory
    DESCRIPTION     
            "An entry in the Outbound License table "
    INDEX           { sonusSoftSwitchOutboundLicenseName }
    ::= { sonusSoftSwitchOutboundLicenseTable 1 }

SonusSoftSwitchOutboundLicenseEntry ::=
    SEQUENCE {
        sonusSoftSwitchOutboundLicenseName  SonusName,
        sonusSoftSwitchOutboundLicenseUsageLimit        Gauge
    }

sonusSoftSwitchOutboundLicenseName OBJECT-TYPE
    SYNTAX          SonusName
    ACCESS          read-only
    STATUS          mandatory
    DESCRIPTION     
            "FeatureId (or SKU) for which usage limit is specified."
    ::= { sonusSoftSwitchOutboundLicenseEntry 1 }

sonusSoftSwitchOutboundLicenseUsageLimit OBJECT-TYPE
    SYNTAX          Gauge
    ACCESS          read-only
    STATUS          mandatory
    DESCRIPTION     
            "Provisioned total BASE Count for the license on the node"
    ::= { sonusSoftSwitchOutboundLicenseEntry 2 }

sonusSoftSwitchSsaMIBNotifications OBJECT IDENTIFIER
    ::= { sonusSoftSwitchSsaMIB 2 }

sonusSoftSwitchSsaMIBNotificationsPrefix OBJECT IDENTIFIER
    ::= { sonusSoftSwitchSsaMIBNotifications 0 }

sonusSoftSwitchSsmgrExitNotification TRAP-TYPE
    ENTERPRISE      sonusSoftSwitchSsaMIBNotifications
    VARIABLES       { sonusEventDescription, sonusEventClass, 
                      sonusEventLevel, sonusEventTime }
--     STATUS          mandatory
    DESCRIPTION     
            "The 'ssmgr' process is exited."
    ::= 1

END -- end of module SONUS-SOFTSWITCH-SSA-MIB.
