--
-- This SMIv2 module has been generated by smidump 0.2-cvs. Do not edit.
--

SONUS-DATANODE-TRAP-MIB DEFINITIONS ::= BEGIN

IMPORTS
    Counter32, Integer32, IpAddress, MODULE-IDENTITY, NOTIFICATION-TYPE, 
    OBJECT-TYPE, Unsigned32
        FROM SNMPv2-SMI
    DisplayString
        FROM SNMPv2-TC
    sonusAlarmDescription, sonusAlarmLevel, sonusAlarmNodeID, 
    sonusAlarmSequenceId, sonusAlarmTime
        FROM SONUS-COMMON-TRAP-MIB
    sonusDatanodeNotificationMIBs
        FROM SONUS-SMI;

sonusDatanodeTraps MODULE-IDENTITY
    LAST-UPDATED    "200911100000Z"
    ORGANIZATION    
            "Sonus Networks, Inc."
    CONTACT-INFO    
            "   Customer Support     
             Sonus Networks, Inc. 
             7 Technology Park Drive 
             Westford, MA 01886 
             USA     
             
             Tel: 978-614-8100 
             Fax: 978-614-8609"
    DESCRIPTION     
            "The MIB Module for Datanode notifications"
    REVISION        "200911100000Z"
    DESCRIPTION     
            "Last revision."
    ::= { sonusDatanodeNotificationMIBs 1 }


sonusDatanodeMIBNotifications OBJECT IDENTIFIER
    ::= { sonusDatanodeTraps 1 }

sonusDatanodeMIBNotificationsPrefix OBJECT IDENTIFIER
    ::= { sonusDatanodeMIBNotifications 0 }

sonusDatanodeProcessFailed NOTIFICATION-TYPE
    OBJECTS         { sonusAlarmNodeID, sonusAlarmLevel, 
                      sonusAlarmSequenceId, sonusAlarmTime, 
                      sonusAlarmDescription }
    STATUS          current
    DESCRIPTION     
            "Processes has stopped running"
    ::= { sonusDatanodeMIBNotifications 2 }

sonusDatanodeProcessClear NOTIFICATION-TYPE
    OBJECTS         { sonusAlarmNodeID, sonusAlarmLevel, 
                      sonusAlarmSequenceId, sonusAlarmTime, 
                      sonusAlarmDescription }
    STATUS          current
    DESCRIPTION     
            "Processes has stopped running"
    ::= { sonusDatanodeMIBNotifications 3 }

sonusDatanodeSystemFailed NOTIFICATION-TYPE
    OBJECTS         { sonusAlarmNodeID, sonusAlarmLevel, 
                      sonusAlarmSequenceId, sonusAlarmTime, 
                      sonusAlarmDescription }
    STATUS          current
    DESCRIPTION     
            "Processes has stopped running"
    ::= { sonusDatanodeMIBNotifications 4 }

sonusDatanodeSystemClear NOTIFICATION-TYPE
    OBJECTS         { sonusAlarmNodeID, sonusAlarmLevel, 
                      sonusAlarmSequenceId, sonusAlarmTime, 
                      sonusAlarmDescription }
    STATUS          current
    DESCRIPTION     
            "Processes has stopped running"
    ::= { sonusDatanodeMIBNotifications 5 }

sonusDatanodeThresholdCPUAbove NOTIFICATION-TYPE
    OBJECTS         { sonusAlarmNodeID, sonusAlarmLevel, 
                      sonusAlarmSequenceId, sonusAlarmTime, 
                      sonusAlarmDescription }
    STATUS          current
    DESCRIPTION     
            "Processes has stopped running"
    ::= { sonusDatanodeMIBNotifications 6 }

sonusDatanodeThresholdCPUClear NOTIFICATION-TYPE
    OBJECTS         { sonusAlarmNodeID, sonusAlarmLevel, 
                      sonusAlarmSequenceId, sonusAlarmTime, 
                      sonusAlarmDescription }
    STATUS          current
    DESCRIPTION     
            "Processes has stopped running"
    ::= { sonusDatanodeMIBNotifications 8 }

sonusDatanodeThresholdMemoryAbove NOTIFICATION-TYPE
    OBJECTS         { sonusAlarmNodeID, sonusAlarmLevel, 
                      sonusAlarmSequenceId, sonusAlarmTime, 
                      sonusAlarmDescription }
    STATUS          current
    DESCRIPTION     
            "Processes has stopped running"
    ::= { sonusDatanodeMIBNotifications 9 }

sonusDatanodeThresholdMemoryClear NOTIFICATION-TYPE
    OBJECTS         { sonusAlarmNodeID, sonusAlarmLevel, 
                      sonusAlarmSequenceId, sonusAlarmTime, 
                      sonusAlarmDescription }
    STATUS          current
    DESCRIPTION     
            "Processes has stopped running"
    ::= { sonusDatanodeMIBNotifications 11 }

sonusDatanodeClusterNameChange NOTIFICATION-TYPE
    OBJECTS         { sonusAlarmNodeID, sonusAlarmLevel, 
                      sonusAlarmSequenceId, sonusAlarmTime, 
                      sonusAlarmDescription }
    STATUS          current
    DESCRIPTION     
            "Failed to modify cluster name"
    ::= { sonusDatanodeMIBNotifications 12 }

sonusDatanodeThresholdDiskAbove NOTIFICATION-TYPE
    OBJECTS         { sonusAlarmNodeID, sonusAlarmLevel, 
                      sonusAlarmSequenceId, sonusAlarmTime, 
                      sonusAlarmDescription }
    STATUS          current
    DESCRIPTION     
            "Processes has stopped running"
    ::= { sonusDatanodeMIBNotifications 13 }

sonusDatanodeThresholdDiskClear NOTIFICATION-TYPE
    OBJECTS         { sonusAlarmNodeID, sonusAlarmLevel, 
                      sonusAlarmSequenceId, sonusAlarmTime, 
                      sonusAlarmDescription }
    STATUS          current
    DESCRIPTION     
            "Processes has stopped running"
    ::= { sonusDatanodeMIBNotifications 14 }

END -- end of module SONUS-DATANODE-TRAP-MIB.
