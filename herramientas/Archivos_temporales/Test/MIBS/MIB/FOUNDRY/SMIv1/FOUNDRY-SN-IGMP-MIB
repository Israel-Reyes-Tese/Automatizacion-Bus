--
-- This SMIv1 module has been generated by smidump 0.2-cvs. Do not edit.
--

FOUNDRY-SN-IGMP-MIB DEFINITIONS ::= BEGIN

IMPORTS
    snIgmp
        FROM FOUNDRY-SN-ROOT-MIB
    OBJECT-TYPE
        FROM RFC-1212
    IpAddress
        FROM RFC1155-SMI;

snIgmpMIBObjects OBJECT IDENTIFIER
    ::= { snIgmp 1 }

snIgmpQueryInterval OBJECT-TYPE
    SYNTAX          INTEGER (1..3600)
    ACCESS          read-write
    STATUS          mandatory
    DESCRIPTION     
            "This is the time interval at which this entity sends out
             IGMP host query packets. For a router, snDvmrpEnable must
             have been set to 'enabled' before this object is writen.
             For a switch, snSwGroupIpMcastMode must have been set to
             'enabled' and snSwIpMcastQuerierMode must have been set
             to 'querier' before this object is writen."
    DEFVAL          { 60 }
    ::= { snIgmpMIBObjects 1 }

snIgmpGroupMembershipTime OBJECT-TYPE
    SYNTAX          INTEGER (1..7200)
    ACCESS          read-write
    STATUS          mandatory
    DESCRIPTION     
            "This is the time interval after which a group is considered
             inactive. For a router, snDvmrpEnable must have been set to
             'enabled' before this object is writen. For a switch,
             snSwGroupIpMcastMode must have been set to 'enabled' before
             this object is writen."
    DEFVAL          { 140 }
    ::= { snIgmpMIBObjects 2 }

snIgmpIfTable OBJECT-TYPE
    SYNTAX          SEQUENCE OF SnIgmpIfEntry
    ACCESS          not-accessible
    STATUS          mandatory
    DESCRIPTION     
            "This table comprises of a list of IGMP interface entries."
    ::= { snIgmpMIBObjects 3 }

snIgmpIfEntry OBJECT-TYPE
    SYNTAX          SnIgmpIfEntry
    ACCESS          not-accessible
    STATUS          mandatory
    DESCRIPTION     
            "An entry (conceptual row) contains the group
             membership information for that port."
    INDEX           { snIgmpIfEntryIndex }
    ::= { snIgmpIfTable 1 }

SnIgmpIfEntry ::=
    SEQUENCE {
        snIgmpIfEntryIndex              INTEGER,
        snIgmpIfPortNumber              INTEGER,
        snIgmpIfGroupAddress            IpAddress,
        snIgmpIfGroupAge                INTEGER
    }

snIgmpIfEntryIndex OBJECT-TYPE
    SYNTAX          INTEGER
    ACCESS          read-only
    STATUS          mandatory
    DESCRIPTION     
            "The table entry index."
    ::= { snIgmpIfEntry 1 }

snIgmpIfPortNumber OBJECT-TYPE
    SYNTAX          INTEGER
    ACCESS          read-only
    STATUS          mandatory
    DESCRIPTION     
            "This is the interface on which the group was learnt."
    ::= { snIgmpIfEntry 2 }

snIgmpIfGroupAddress OBJECT-TYPE
    SYNTAX          IpAddress
    ACCESS          read-only
    STATUS          mandatory
    DESCRIPTION     
            "The group address learnt from the interface."
    ::= { snIgmpIfEntry 3 }

snIgmpIfGroupAge OBJECT-TYPE
    SYNTAX          INTEGER
    ACCESS          read-only
    STATUS          mandatory
    DESCRIPTION     
            "This is the interval (seconds) after which the group
             information will be aged out."
    ::= { snIgmpIfEntry 4 }

END -- end of module FOUNDRY-SN-IGMP-MIB.
