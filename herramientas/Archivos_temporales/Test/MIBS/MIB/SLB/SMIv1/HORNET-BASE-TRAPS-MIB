--
-- This SMIv1 module has been generated by smidump 0.2-cvs. Do not edit.
--

HORNET-BASE-TRAPS-MIB DEFINITIONS ::= BEGIN

IMPORTS
    OBJECT-TYPE
        FROM RFC-1212
    TRAP-TYPE
        FROM RFC-1215
    DisplayString
        FROM SNMPv2-TC
    sonusAlarmDescription, sonusAlarmLevel, sonusAlarmNodeID, 
    sonusAlarmSequenceId, sonusAlarmTime, sonusServerID
        FROM SONUS-COMMON-TRAP-MIB
    sonusEventLogTypeAdminFileCount, sonusEventLogTypeAdminFileSize, 
    sonusEventLogTypeAdminFilterLevel, 
    sonusEventLogTypeAdminMaxEventMemorySize, 
    sonusEventLogTypeAdminMessageQueueSize, sonusEventLogTypeAdminSaveTo, 
    sonusEventLogTypeStatusCurrentFile
        FROM SONUS-GEN2-EVENT-LOG-MIB
    sonusCspsNotificationMIBs
        FROM SONUS-SMI
    sonusSystemSoftwareUpgradeStatusReason
        FROM SONUS-SYSTEM-MIB;

sonusCpBaseTrapsMIB OBJECT IDENTIFIER
    ::= { sonusCspsNotificationMIBs 2 }

-- sonusCpBaseTrapsMIB MODULE-IDENTITY
--     LAST-UPDATED    "200807110000Z"
--     ORGANIZATION    
--             "Sonus Networks, Inc."
--     CONTACT-INFO    
--             "   Customer Support    
--              Sonus Networks, Inc.
--              4 Technology Park Drive
--              Westford, MA 01886
--              USA
--              
--              Tel: 978-614-8100
--              Fax: 978-614-8609"
--     DESCRIPTION     
--             "The MIB Module for Base Hornet Traps."
--     REVISION        "200807110000Z"
--     DESCRIPTION     
--             "Last revision."
--     ::= { sonusCspsNotificationMIBs 2 }


InetAddressIP ::=
    OCTET STRING (SIZE(4 | 16))

-- InetAddressIP ::= TEXTUAL-CONVENTION
--     STATUS          mandatory
--     DESCRIPTION     
--             "confd:inetAddressIP"
--     SYNTAX          OCTET STRING (SIZE(4 | 16))

sonusCpBaseTraps OBJECT IDENTIFIER
    ::= { sonusCpBaseTrapsMIB 1 }

sonusCpNtpServicesMIBNotifications OBJECT IDENTIFIER
    ::= { sonusCpBaseTraps 1 }

sonusCpNtpServicesMIBNotificationsPrefix OBJECT IDENTIFIER
    ::= { sonusCpNtpServicesMIBNotifications 0 }

sonusCpNtpServicesMIBNotificationsObjects OBJECT IDENTIFIER
    ::= { sonusCpNtpServicesMIBNotifications 1 }

sonusCpNtpServerOutOfServiceReason OBJECT-TYPE
    SYNTAX          INTEGER { ntpServerDisabled(1), 
                        ntpServerOutOfSync(2) }
    ACCESS          read-only
    STATUS          mandatory
    DESCRIPTION     
            "The reason why this Network Timing Protocol Server is out of service."
    ::= { sonusCpNtpServicesMIBNotificationsObjects 1 }

sonusCpNtpDownReason OBJECT-TYPE
    SYNTAX          INTEGER { noNtpServerConfigured(1), 
                        allNtpServersOutOfSync(2) }
    ACCESS          read-only
    STATUS          mandatory
    DESCRIPTION     
            "The reason why the Network Timing Protocol is down for this system."
    ::= { sonusCpNtpServicesMIBNotificationsObjects 2 }

sonusCpNtpIpAddress OBJECT-TYPE
    SYNTAX          InetAddressIP
    ACCESS          read-only
    STATUS          mandatory
    DESCRIPTION     
            "
             The IP address of this NTP Peer. 
             "
    ::= { sonusCpNtpServicesMIBNotificationsObjects 3 }

sonusCpRedundancyServicesMIBNotifications OBJECT IDENTIFIER
    ::= { sonusCpBaseTraps 2 }

sonusCpRedundancyServicesMIBNotificationsPrefix OBJECT IDENTIFIER
    ::= { sonusCpRedundancyServicesMIBNotifications 0 }

sonusCpRedundancyServicesMIBNotificationsObjects OBJECT IDENTIFIER
    ::= { sonusCpRedundancyServicesMIBNotifications 1 }

sonusCpRedundPrevActiveServerName OBJECT-TYPE
    SYNTAX          DisplayString
    ACCESS          read-only
    STATUS          mandatory
    DESCRIPTION     
            "The server identifier of the failed server module whose switchover
             generated this trap."
    ::= { sonusCpRedundancyServicesMIBNotificationsObjects 1 }

sonusCpRedundancyServicesGroupName OBJECT-TYPE
    SYNTAX          DisplayString
    ACCESS          read-only
    STATUS          mandatory
    DESCRIPTION     
            "
             The name of this redundancy group instance.
             "
    ::= { sonusCpRedundancyServicesMIBNotificationsObjects 2 }

sonusCpSoftwareUpgradeServicesMIBNotifications OBJECT IDENTIFIER
    ::= { sonusCpBaseTraps 3 }

sonusCpSoftwareUpgradeServicesMIBNotificationsPrefix OBJECT IDENTIFIER
    ::= { sonusCpSoftwareUpgradeServicesMIBNotifications 0 }

sonusCpSoftwareUpgradeServicesMIBNotificationsObjects OBJECT IDENTIFIER
    ::= { sonusCpSoftwareUpgradeServicesMIBNotifications 1 }

sonusSystemSoftwareUpgradeOldRelease OBJECT-TYPE
    SYNTAX          DisplayString
    ACCESS          read-only
    STATUS          mandatory
    DESCRIPTION     
            "
             Old software release.
             "
    ::= { sonusCpSoftwareUpgradeServicesMIBNotificationsObjects 1 }

sonusSystemSoftwareUpgradeNewRelease OBJECT-TYPE
    SYNTAX          DisplayString
    ACCESS          read-only
    STATUS          mandatory
    DESCRIPTION     
            "
             New software release.
             "
    ::= { sonusCpSoftwareUpgradeServicesMIBNotificationsObjects 2 }

sonusCpEventLogMIBNotifications OBJECT IDENTIFIER
    ::= { sonusCpBaseTraps 4 }

sonusCpEventLogMIBNotificationsPrefix OBJECT IDENTIFIER
    ::= { sonusCpEventLogMIBNotifications 0 }

sonusCpEventLogMIBNotificationsObjects OBJECT IDENTIFIER
    ::= { sonusCpEventLogMIBNotifications 1 }

sonusCpEvLogAdminState OBJECT-TYPE
    SYNTAX          INTEGER { disabled(1), enabled(2), rollfile(3) }
    ACCESS          read-only
    STATUS          mandatory
    DESCRIPTION     
            "The requested state of the given Event Log type.  Rollfile
             will close an enabled log file and reopen, incrementing the
             suffix.  If a file is disabled and rolled, the command is
             ignored."
    ::= { sonusCpEventLogMIBNotificationsObjects 1 }

sonusCpEvLogShutdownReason OBJECT-TYPE
    SYNTAX          INTEGER { fileWriteFailed(1), nfsError(2), 
                        createDirectoryFailed(3), 
                        maximumFileCountReached(4), fileRemoveFailed(5), 
                        fileOpenFailed(6), fileHeaderWriteFailed(7), 
                        memoryAllocationFailed(8), 
                        administrativeShutdown(9), 
                        localDiskUnavailable(10) }
    ACCESS          read-only
    STATUS          mandatory
    DESCRIPTION     
            "The reason that event file logging has been shutdown."
    ::= { sonusCpEventLogMIBNotificationsObjects 2 }

sonusCpEvLogDirName OBJECT-TYPE
    SYNTAX          DisplayString
    ACCESS          read-only
    STATUS          mandatory
    DESCRIPTION     
            "The event file log directory name."
    ::= { sonusCpEventLogMIBNotificationsObjects 3 }

sonusCpEvLogFilePercentage OBJECT-TYPE
    SYNTAX          INTEGER
    ACCESS          read-only
    STATUS          mandatory
    DESCRIPTION     
            "The percentage the event log directory is full based on file count."
    ::= { sonusCpEventLogMIBNotificationsObjects 4 }

sonusCpEvLogCurFileCount OBJECT-TYPE
    SYNTAX          INTEGER
    ACCESS          read-only
    STATUS          mandatory
    DESCRIPTION     
            "The current count of event files."
    ::= { sonusCpEventLogMIBNotificationsObjects 5 }

sonusCpEvLogErrorCode OBJECT-TYPE
    SYNTAX          INTEGER
    ACCESS          read-only
    STATUS          mandatory
    DESCRIPTION     
            "The evlog error code."
    ::= { sonusCpEventLogMIBNotificationsObjects 6 }

sonusEvLogTypeName OBJECT-TYPE
    SYNTAX          DisplayString
    ACCESS          read-only
    STATUS          mandatory
    DESCRIPTION     
            "The event file log type."
    ::= { sonusCpEventLogMIBNotificationsObjects 7 }

sonusCpEventLogType OBJECT-TYPE
    SYNTAX          INTEGER { memusage(8), packet(7), audit(6), 
                        security(5), acct(4), trace(3), debug(2), 
                        system(1) }
    ACCESS          read-only
    STATUS          mandatory
    DESCRIPTION     
            "
             The type of the event log.  Each type has separate
             configuration parameters and logs to a separate file.
             "
    ::= { sonusCpEventLogMIBNotificationsObjects 8 }

sonusAlarmMgrId OBJECT-TYPE
    SYNTAX          INTEGER
    ACCESS          read-only
    STATUS          mandatory
    DESCRIPTION     
            "
             The Alarm Manager Id.
             "
    ::= { sonusCpEventLogMIBNotificationsObjects 9 }

sonusEventLogRenameToFile OBJECT-TYPE
    SYNTAX          DisplayString
    ACCESS          read-only
    STATUS          mandatory
    DESCRIPTION     
            "
             The rename to file name
             "
    ::= { sonusCpEventLogMIBNotificationsObjects 10 }

sonusAlarmMgrAckState OBJECT-TYPE
    SYNTAX          DisplayString
    ACCESS          read-only
    STATUS          mandatory
    DESCRIPTION     
            "The current acknowledge state {unacknowledge/acknowledge}"
    ::= { sonusCpEventLogMIBNotificationsObjects 11 }

sonusAlarmMgrComment OBJECT-TYPE
    SYNTAX          DisplayString
    ACCESS          read-only
    STATUS          mandatory
    DESCRIPTION     
            "The current operator comment "
    ::= { sonusCpEventLogMIBNotificationsObjects 12 }

sonusCpSystemServicesMIBNotifications OBJECT IDENTIFIER
    ::= { sonusCpBaseTraps 5 }

sonusCpSystemServicesMIBNotificationsPrefix OBJECT IDENTIFIER
    ::= { sonusCpSystemServicesMIBNotifications 0 }

sonusCpSystemServicesMIBNotificationsObjects OBJECT IDENTIFIER
    ::= { sonusCpSystemServicesMIBNotifications 1 }

sonusCpSystemServerName OBJECT-TYPE
    SYNTAX          DisplayString
    ACCESS          read-only
    STATUS          mandatory
    DESCRIPTION     
            "
             The unique identifier assigned to this card or server.
             "
    ::= { sonusCpSystemServicesMIBNotificationsObjects 1 }

sonusCpSystemHardDiskNumber OBJECT-TYPE
    SYNTAX          INTEGER
    ACCESS          read-only
    STATUS          mandatory
    DESCRIPTION     
            "
             Hard disk number (typically 0 through 3)
             "
    ::= { sonusCpSystemServicesMIBNotificationsObjects 2 }

sonusCpSystemPowerSupplyId OBJECT-TYPE
    SYNTAX          DisplayString
    ACCESS          read-only
    STATUS          mandatory
    DESCRIPTION     
            "
             The name of the power supply (/SYS/VPS)
             "
    ::= { sonusCpSystemServicesMIBNotificationsObjects 3 }

sonusCpSystemFanId OBJECT-TYPE
    SYNTAX          DisplayString
    ACCESS          read-only
    STATUS          mandatory
    DESCRIPTION     
            "
             The name of the fan (usually /FT0/F0/ /FT0/F1/ etc).
             
             "
    ::= { sonusCpSystemServicesMIBNotificationsObjects 4 }

sonusCpSystemCoredumpFile OBJECT-TYPE
    SYNTAX          DisplayString
    ACCESS          read-only
    STATUS          mandatory
    DESCRIPTION     
            "
             File name of the coredump.
             "
    ::= { sonusCpSystemServicesMIBNotificationsObjects 5 }

sonusCpSystemCoredumpSpacePct OBJECT-TYPE
    SYNTAX          INTEGER
    ACCESS          read-only
    STATUS          mandatory
    DESCRIPTION     
            "
             Percentage of allowed coredump space occupied.
             "
    ::= { sonusCpSystemServicesMIBNotificationsObjects 6 }

sonusCpSystemServerTemperatureSensorId OBJECT-TYPE
    SYNTAX          DisplayString
    ACCESS          read-only
    STATUS          mandatory
    DESCRIPTION     
            "
             Id of the temperature sensor, MB/T_AMB0, MB/T_AMB1 etc.
             
             "
    ::= { sonusCpSystemServicesMIBNotificationsObjects 7 }

sonusCpSystemServerTemperature OBJECT-TYPE
    SYNTAX          INTEGER
    ACCESS          read-only
    STATUS          mandatory
    DESCRIPTION     
            "
             Temperature (in Degrees C)
             "
    ::= { sonusCpSystemServicesMIBNotificationsObjects 8 }

sonusCpSystemAdminName OBJECT-TYPE
    SYNTAX          DisplayString
    ACCESS          read-only
    STATUS          mandatory
    DESCRIPTION     
            "
             Name of the system
             "
    ::= { sonusCpSystemServicesMIBNotificationsObjects 9 }

sonusCpSystemDiskPartition OBJECT-TYPE
    SYNTAX          DisplayString
    ACCESS          read-only
    STATUS          mandatory
    DESCRIPTION     
            "
             Partition on the disk
             "
    ::= { sonusCpSystemServicesMIBNotificationsObjects 10 }

sonusCpSystemDiskSpaceUsedPct OBJECT-TYPE
    SYNTAX          INTEGER
    ACCESS          read-only
    STATUS          mandatory
    DESCRIPTION     
            "
             Percentage of the disk space used.
             "
    ::= { sonusCpSystemServicesMIBNotificationsObjects 11 }

sonusCpSystemPortName OBJECT-TYPE
    SYNTAX          DisplayString
    ACCESS          read-only
    STATUS          mandatory
    DESCRIPTION     
            "
             The name of the port.
             "
    ::= { sonusCpSystemServicesMIBNotificationsObjects 12 }

sonusCpSystemConfigFileName OBJECT-TYPE
    SYNTAX          DisplayString
    ACCESS          read-only
    STATUS          mandatory
    DESCRIPTION     
            "
             File name of the configuration file.
             "
    ::= { sonusCpSystemServicesMIBNotificationsObjects 13 }

sonusCpSelfBaseMacAddress OBJECT-TYPE
    SYNTAX          DisplayString
    ACCESS          read-only
    STATUS          mandatory
    DESCRIPTION     
            "
             Local base MAC addresss.
             "
    ::= { sonusCpSystemServicesMIBNotificationsObjects 14 }

sonusCpPeerBaseMacAddress OBJECT-TYPE
    SYNTAX          DisplayString
    ACCESS          read-only
    STATUS          mandatory
    DESCRIPTION     
            "
             Peer base MAC addresss.
             "
    ::= { sonusCpSystemServicesMIBNotificationsObjects 15 }

sonusCpActiveBaseMacAddress OBJECT-TYPE
    SYNTAX          DisplayString
    ACCESS          read-only
    STATUS          mandatory
    DESCRIPTION     
            "
             Active MAC addresss of the system.
             "
    ::= { sonusCpSystemServicesMIBNotificationsObjects 16 }

sonusNodeOverloadType OBJECT-TYPE
    SYNTAX          DisplayString (SIZE(0..3))
    ACCESS          read-only
    STATUS          mandatory
    DESCRIPTION     
            "Overload Resource Type"
    ::= { sonusCpSystemServicesMIBNotificationsObjects 17 }

sonusNodeOverloadLevel OBJECT-TYPE
    SYNTAX          INTEGER (0..3)
    ACCESS          read-only
    STATUS          mandatory
    DESCRIPTION     
            "The Overload Level"
    ::= { sonusCpSystemServicesMIBNotificationsObjects 18 }

sonusNodeOverloadThresholdCurrent OBJECT-TYPE
    SYNTAX          INTEGER (0..100)
    ACCESS          read-only
    STATUS          mandatory
    DESCRIPTION     
            "The current calculated value of this resource"
    ::= { sonusCpSystemServicesMIBNotificationsObjects 19 }

sonusNodeOverloadThresholdConfigured OBJECT-TYPE
    SYNTAX          INTEGER (0..100)
    ACCESS          read-only
    STATUS          mandatory
    DESCRIPTION     
            "The configured threshold level for this resource"
    ::= { sonusCpSystemServicesMIBNotificationsObjects 20 }

sonusCpProductCapabilityName OBJECT-TYPE
    SYNTAX          DisplayString
    ACCESS          read-only
    STATUS          mandatory
    DESCRIPTION     
            "
             Product capability type.
             "
    ::= { sonusCpSystemServicesMIBNotificationsObjects 21 }

sonusCpProductCapabilityValue OBJECT-TYPE
    SYNTAX          DisplayString
    ACCESS          read-only
    STATUS          mandatory
    DESCRIPTION     
            "
             Product Capability value of local server.
             "
    ::= { sonusCpSystemServicesMIBNotificationsObjects 22 }

sonusCpProductPeerCapabilityValue OBJECT-TYPE
    SYNTAX          DisplayString
    ACCESS          read-only
    STATUS          mandatory
    DESCRIPTION     
            "
             Product Capability value of peer server.
             "
    ::= { sonusCpSystemServicesMIBNotificationsObjects 23 }

sonusCpSystemHardDiskName OBJECT-TYPE
    SYNTAX          DisplayString
    ACCESS          read-only
    STATUS          mandatory
    DESCRIPTION     
            "
             Name of a disk device on the system.
             "
    ::= { sonusCpSystemServicesMIBNotificationsObjects 24 }

sonusCpSystemHardDiskError OBJECT-TYPE
    SYNTAX          DisplayString
    ACCESS          read-only
    STATUS          mandatory
    DESCRIPTION     
            "
             Error string reported by Self-Monitoring, Analysis and Reporting Technology (SMART).
             "
    ::= { sonusCpSystemServicesMIBNotificationsObjects 25 }

sonusCpSystemLifeAvailAttrib OBJECT-TYPE
    SYNTAX          DisplayString
    ACCESS          read-only
    STATUS          mandatory
    DESCRIPTION     
            "
             Value representing the percentage of disk life remaining reported by Self-Monitoring, Analysis and Reporting Technology (SMART) or N/A if not supported.
             "
    ::= { sonusCpSystemServicesMIBNotificationsObjects 26 }

sonusCpSystemMemoryUsage OBJECT-TYPE
    SYNTAX          INTEGER
    ACCESS          read-only
    STATUS          mandatory
    DESCRIPTION     
            "
             Percentage of the system memory used.
             "
    ::= { sonusCpSystemServicesMIBNotificationsObjects 27 }

sonusCpSystemServiceRestartReason OBJECT-TYPE
    SYNTAX          DisplayString
    ACCESS          read-only
    STATUS          obsolete
    DESCRIPTION     
            "
             Detailed description of the event that cause the application to restart.
             "
    ::= { sonusCpSystemServicesMIBNotificationsObjects 28 }

sonusCpSystemUserString OBJECT-TYPE
    SYNTAX          OCTET STRING (SIZE(0..255))
    ACCESS          read-only
    STATUS          obsolete
    DESCRIPTION     
            "
             User provided information string.
             "
    ::= { sonusCpSystemServicesMIBNotificationsObjects 29 }

sonusCpSystemApplicationRestartReason OBJECT-TYPE
    SYNTAX          DisplayString
    ACCESS          read-only
    STATUS          mandatory
    DESCRIPTION     
            "
             Detailed description of the event that cause the application to restart.
             "
    ::= { sonusCpSystemServicesMIBNotificationsObjects 30 }

sonusCpSystemUserInfoString OBJECT-TYPE
    SYNTAX          OCTET STRING (SIZE(0..255))
    ACCESS          read-only
    STATUS          mandatory
    DESCRIPTION     
            "
             User provided information string.
             "
    ::= { sonusCpSystemServicesMIBNotificationsObjects 31 }

sonusServerIpAddress OBJECT-TYPE
    SYNTAX          DisplayString
    ACCESS          read-only
    STATUS          mandatory
    DESCRIPTION     
            "IP Address of the remote server"
    ::= { sonusCpSystemServicesMIBNotificationsObjects 32 }

sonusCpNifMIBNotifications OBJECT IDENTIFIER
    ::= { sonusCpBaseTraps 6 }

sonusCpNifMIBNotificationsPrefix OBJECT IDENTIFIER
    ::= { sonusCpNifMIBNotifications 0 }

sonusCpNifMIBNotificationsObjects OBJECT IDENTIFIER
    ::= { sonusCpNifMIBNotifications 1 }

sonusCpNifCeName OBJECT-TYPE
    SYNTAX          DisplayString
    ACCESS          read-only
    STATUS          mandatory
    DESCRIPTION     
            "
             The host name is this server.
             "
    ::= { sonusCpNifMIBNotificationsObjects 1 }

sonusCpNifType OBJECT-TYPE
    SYNTAX          INTEGER { externalSignaling(3), internalSignaling(2), 
                        management(1) }
    ACCESS          read-only
    STATUS          mandatory
    DESCRIPTION     
            "
             The type of nif to which the port belongs, which is one of:
             management
             internalSignaling
             externalSignaling
             "
    ::= { sonusCpNifMIBNotificationsObjects 2 }

sonusCpNifUsage OBJECT-TYPE
    SYNTAX          INTEGER { secondary(2), primary(1) }
    ACCESS          read-only
    STATUS          mandatory
    DESCRIPTION     
            "
             The way the port will be used, which is one of:
             primary
             secondary
             "
    ::= { sonusCpNifMIBNotificationsObjects 3 }

sonusCpRadiusAccountingMIBNotifications OBJECT IDENTIFIER
    ::= { sonusCpBaseTraps 7 }

sonusCpRadiusAccountingMIBNotificationsPrefix OBJECT IDENTIFIER
    ::= { sonusCpRadiusAccountingMIBNotifications 0 }

sonusCpRadiusAccountingMIBNotificationsObjects OBJECT IDENTIFIER
    ::= { sonusCpRadiusAccountingMIBNotifications 1 }

sonusCpRadiusServerName OBJECT-TYPE
    SYNTAX          DisplayString
    ACCESS          read-only
    STATUS          mandatory
    DESCRIPTION     
            "
             The host name of the radius server
             "
    ::= { sonusCpRadiusAccountingMIBNotificationsObjects 1 }

sonusCpRadiusFlushedPackets OBJECT-TYPE
    SYNTAX          INTEGER
    ACCESS          read-only
    STATUS          mandatory
    DESCRIPTION     
            "
             The number of Radius packets flushed to disk
             "
    ::= { sonusCpRadiusAccountingMIBNotificationsObjects 2 }

sonusCpRadiusFlushedPacketsFile OBJECT-TYPE
    SYNTAX          DisplayString
    ACCESS          read-only
    STATUS          mandatory
    DESCRIPTION     
            "
             The filename of the file containing the flushed Radius packets
             "
    ::= { sonusCpRadiusAccountingMIBNotificationsObjects 3 }

sonusCpLicenseMIBNotifications OBJECT IDENTIFIER
    ::= { sonusCpBaseTraps 8 }

sonusCpLicenseMIBNotificationsPrefix OBJECT IDENTIFIER
    ::= { sonusCpLicenseMIBNotifications 0 }

sonusCpLicenseMIBNotificationsObjects OBJECT IDENTIFIER
    ::= { sonusCpLicenseMIBNotifications 1 }

sonusCpLicenseViolationDescString OBJECT-TYPE
    SYNTAX          DisplayString
    ACCESS          read-only
    STATUS          mandatory
    DESCRIPTION     
            "This string describes details of any attempted violation of license integrity"
    ::= { sonusCpLicenseMIBNotificationsObjects 1 }

sonusCpLicenseId OBJECT-TYPE
    SYNTAX          DisplayString
    ACCESS          read-only
    STATUS          mandatory
    DESCRIPTION     
            "The license Id"
    ::= { sonusCpLicenseMIBNotificationsObjects 2 }

sonusCpLicenseFeatureName OBJECT-TYPE
    SYNTAX          DisplayString
    ACCESS          read-only
    STATUS          mandatory
    DESCRIPTION     
            "The license feature string"
    ::= { sonusCpLicenseMIBNotificationsObjects 3 }

sonusSessConfigLicenses OBJECT-TYPE
    SYNTAX          INTEGER
    ACCESS          read-only
    STATUS          mandatory
    DESCRIPTION     
            "
             The number of configured licenses
             "
    ::= { sonusCpLicenseMIBNotificationsObjects 4 }

sonusSessSystemLimit OBJECT-TYPE
    SYNTAX          INTEGER
    ACCESS          read-only
    STATUS          mandatory
    DESCRIPTION     
            "
             The system limit of maximum sessions
             "
    ::= { sonusCpLicenseMIBNotificationsObjects 5 }

sonusCpCountRequested OBJECT-TYPE
    SYNTAX          INTEGER
    ACCESS          read-only
    STATUS          mandatory
    DESCRIPTION     
            "
             The number of licenses requested
             "
    ::= { sonusCpLicenseMIBNotificationsObjects 6 }

sonusCpCountAcquired OBJECT-TYPE
    SYNTAX          INTEGER
    ACCESS          read-only
    STATUS          mandatory
    DESCRIPTION     
            "
             The number of licenses acquired
             "
    ::= { sonusCpLicenseMIBNotificationsObjects 7 }

sonusCpLicenseErrorReason OBJECT-TYPE
    SYNTAX          DisplayString
    ACCESS          read-only
    STATUS          mandatory
    DESCRIPTION     
            "
             The system limit of maximum sessions
             "
    ::= { sonusCpLicenseMIBNotificationsObjects 8 }

sonusCpCountReleased OBJECT-TYPE
    SYNTAX          INTEGER
    ACCESS          read-only
    STATUS          mandatory
    DESCRIPTION     
            "
             The number of licenses released
             "
    ::= { sonusCpLicenseMIBNotificationsObjects 9 }

sonusCpCountRemaining OBJECT-TYPE
    SYNTAX          INTEGER
    ACCESS          read-only
    STATUS          mandatory
    DESCRIPTION     
            "
             The number of licenses still held
             "
    ::= { sonusCpLicenseMIBNotificationsObjects 10 }

sonusCpLicenseServerName OBJECT-TYPE
    SYNTAX          DisplayString
    ACCESS          read-only
    STATUS          mandatory
    DESCRIPTION     
            "
             The license server name
             "
    ::= { sonusCpLicenseMIBNotificationsObjects 11 }

sonusCpLicenseServerAddress OBJECT-TYPE
    SYNTAX          DisplayString
    ACCESS          read-only
    STATUS          mandatory
    DESCRIPTION     
            "
             The license server address
             "
    ::= { sonusCpLicenseMIBNotificationsObjects 12 }

sonusCpLicenseBundleName OBJECT-TYPE
    SYNTAX          DisplayString
    ACCESS          read-only
    STATUS          mandatory
    DESCRIPTION     
            "
             The bundle name
             "
    ::= { sonusCpLicenseMIBNotificationsObjects 13 }

sonusCpCdrServerMIBNotifications OBJECT IDENTIFIER
    ::= { sonusCpBaseTraps 9 }

sonusCpCdrServerMIBNotificationsPrefix OBJECT IDENTIFIER
    ::= { sonusCpCdrServerMIBNotifications 0 }

sonusCpCdrServerMIBNotificationsObjects OBJECT IDENTIFIER
    ::= { sonusCpCdrServerMIBNotifications 1 }

sonusCpCdrServerType OBJECT-TYPE
    SYNTAX          DisplayString
    ACCESS          read-only
    STATUS          mandatory
    DESCRIPTION     
            "The CDR server that is currently active (primary or secondary)."
    ::= { sonusCpCdrServerMIBNotificationsObjects 1 }

sonusCpCdrServerIpAddress OBJECT-TYPE
    SYNTAX          DisplayString
    ACCESS          read-only
    STATUS          mandatory
    DESCRIPTION     
            "The IP address of this NTP Peer. "
    ::= { sonusCpCdrServerMIBNotificationsObjects 2 }

sonusCpVmMIBNotifications OBJECT IDENTIFIER
    ::= { sonusCpBaseTraps 10 }

sonusCpVmMIBNotificationsPrefix OBJECT IDENTIFIER
    ::= { sonusCpVmMIBNotifications 0 }

sonusCpVmMIBNotificationsObjects OBJECT IDENTIFIER
    ::= { sonusCpVmMIBNotifications 1 }

sonusCpVmAppName OBJECT-TYPE
    SYNTAX          DisplayString
    ACCESS          read-only
    STATUS          deprecated
    DESCRIPTION     
            "The name of the virtual machine application."
    ::= { sonusCpVmMIBNotificationsObjects 1 }

sonusCpVmInstalledConfiguration OBJECT-TYPE
    SYNTAX          INTEGER { none(1), epxMaster(2), epxSlave(3) }
    ACCESS          read-only
    STATUS          deprecated
    DESCRIPTION     
            "The installed configuration of the virtual machine application."
    ::= { sonusCpVmMIBNotificationsObjects 2 }

sonusCpVmConfigLicense OBJECT-TYPE
    SYNTAX          INTEGER { none(1), epxMaster(2), epxSlave(3) }
    ACCESS          read-only
    STATUS          deprecated
    DESCRIPTION     
            "The configured license for the virtual machine application."
    ::= { sonusCpVmMIBNotificationsObjects 3 }

sonusCpVmReason OBJECT-TYPE
    SYNTAX          DisplayString
    ACCESS          read-only
    STATUS          deprecated
    DESCRIPTION     
            "The reason the virtual machine application in not running."
    ::= { sonusCpVmMIBNotificationsObjects 4 }

sonusCpVmServerName OBJECT-TYPE
    SYNTAX          DisplayString
    ACCESS          read-only
    STATUS          deprecated
    DESCRIPTION     
            "
             The unique identifier assigned to this card or server.
             "
    ::= { sonusCpVmMIBNotificationsObjects 5 }

sonusCpVmId OBJECT-TYPE
    SYNTAX          INTEGER (1..3)
    ACCESS          read-only
    STATUS          deprecated
    DESCRIPTION     
            "Instance ID of virtual machine application."
    ::= { sonusCpVmMIBNotificationsObjects 6 }

sonusCpVmRedundancyMode OBJECT-TYPE
    SYNTAX          INTEGER { standbyInactive(0), standbyActive(1) }
    ACCESS          read-only
    STATUS          deprecated
    DESCRIPTION     
            "Redundancy mode of standby virtual machine application."
    ::= { sonusCpVmMIBNotificationsObjects 7 }

sonusFipsMIBNotifications OBJECT IDENTIFIER
    ::= { sonusCpBaseTraps 11 }

sonusFipsMIBNotificationsPrefix OBJECT IDENTIFIER
    ::= { sonusFipsMIBNotifications 0 }

sonusFipsMIBNotificationsObjects OBJECT IDENTIFIER
    ::= { sonusFipsMIBNotifications 1 }

sonusFipsNotificationDetails OBJECT-TYPE
    SYNTAX          DisplayString
    ACCESS          read-only
    STATUS          mandatory
    DESCRIPTION     
            "Detailed information about the FIPS related alarm. "
    ::= { sonusFipsMIBNotificationsObjects 1 }

sonusSystemSecurityMIBNotifications OBJECT IDENTIFIER
    ::= { sonusCpBaseTraps 12 }

sonusSystemSecurityMIBNotificationsPrefix OBJECT IDENTIFIER
    ::= { sonusSystemSecurityMIBNotifications 0 }

sonusSystemSecurityMIBNotificationsObjects OBJECT IDENTIFIER
    ::= { sonusSystemSecurityMIBNotifications 1 }

sonusSystemSecurityNotificationDetails OBJECT-TYPE
    SYNTAX          DisplayString
    ACCESS          read-only
    STATUS          mandatory
    DESCRIPTION     
            "Detailed information about the SystemSecurity related trap. "
    ::= { sonusSystemSecurityMIBNotificationsObjects 1 }

sonusEthErrorType OBJECT-TYPE
    SYNTAX          DisplayString
    ACCESS          read-only
    STATUS          mandatory
    DESCRIPTION     
            "Ethernet Error Type "
    ::= { sonusSystemSecurityMIBNotificationsObjects 2 }

sonusEthInterfaceType OBJECT-TYPE
    SYNTAX          DisplayString
    ACCESS          read-only
    STATUS          mandatory
    DESCRIPTION     
            "Name of Ethernet Interface "
    ::= { sonusSystemSecurityMIBNotificationsObjects 3 }

sonusMediaErrType OBJECT-TYPE
    SYNTAX          DisplayString
    ACCESS          read-only
    STATUS          mandatory
    DESCRIPTION     
            "Detailed information about the NP media error. "
    ::= { sonusSystemSecurityMIBNotificationsObjects 4 }

sonusUserName OBJECT-TYPE
    SYNTAX          DisplayString
    ACCESS          read-only
    STATUS          mandatory
    DESCRIPTION     
            "The user name of the affected account. "
    ::= { sonusSystemSecurityMIBNotificationsObjects 5 }

sonusGroupName OBJECT-TYPE
    SYNTAX          DisplayString
    ACCESS          read-only
    STATUS          mandatory
    DESCRIPTION     
            "The name of a group an account has been assigned to. "
    ::= { sonusSystemSecurityMIBNotificationsObjects 6 }

sonusConfigChange OBJECT-TYPE
    SYNTAX          DisplayString
    ACCESS          read-only
    STATUS          mandatory
    DESCRIPTION     
            "A string that contains the configuration type being changed and the new value it is given"
    ::= { sonusSystemSecurityMIBNotificationsObjects 7 }

sonusUnlockType OBJECT-TYPE
    SYNTAX          DisplayString
    ACCESS          read-only
    STATUS          mandatory
    DESCRIPTION     
            "A string that that indicates how the account is unlcocked (either automatic or manual)"
    ::= { sonusSystemSecurityMIBNotificationsObjects 8 }

sonusFileName OBJECT-TYPE
    SYNTAX          DisplayString
    ACCESS          read-only
    STATUS          mandatory
    DESCRIPTION     
            "A string that contains the file name of the log file"
    ::= { sonusSystemSecurityMIBNotificationsObjects 9 }

sonusProcessId OBJECT-TYPE
    SYNTAX          DisplayString
    ACCESS          read-only
    STATUS          mandatory
    DESCRIPTION     
            "A string that contains the PID of the user that is generating the large console session log"
    ::= { sonusSystemSecurityMIBNotificationsObjects 10 }

sonusFileList OBJECT-TYPE
    SYNTAX          DisplayString
    ACCESS          read-only
    STATUS          mandatory
    DESCRIPTION     
            ""
    ::= { sonusSystemSecurityMIBNotificationsObjects 11 }

sonusKeyName OBJECT-TYPE
    SYNTAX          DisplayString
    ACCESS          read-only
    STATUS          mandatory
    DESCRIPTION     
            "The name of a key"
    ::= { sonusSystemSecurityMIBNotificationsObjects 12 }

sonusSystemServerName OBJECT-TYPE
    SYNTAX          DisplayString
    ACCESS          read-only
    STATUS          mandatory
    DESCRIPTION     
            "The unique identifier assigned to this server"
    ::= { sonusSystemSecurityMIBNotificationsObjects 13 }

sonusSecurityCertName OBJECT-TYPE
    SYNTAX          DisplayString
    ACCESS          read-only
    STATUS          mandatory
    DESCRIPTION     
            "The unique identifier assigned to this certificate"
    ::= { sonusSystemSecurityMIBNotificationsObjects 14 }

sonusSecurityCertExpiryDaysLeft OBJECT-TYPE
    SYNTAX          INTEGER
    ACCESS          read-only
    STATUS          mandatory
    DESCRIPTION     
            "Days remaining before certificate expires"
    ::= { sonusSystemSecurityMIBNotificationsObjects 15 }

sonusCpSystemDataAgentMIBNotifications OBJECT IDENTIFIER
    ::= { sonusCpBaseTraps 13 }

sonusCpSystemDataAgentMIBNotificationsPrefix OBJECT IDENTIFIER
    ::= { sonusCpSystemDataAgentMIBNotifications 0 }

sonusCpSystemDataAgentMIBNotificationsObjects OBJECT IDENTIFIER
    ::= { sonusCpSystemDataAgentMIBNotifications 1 }

sonusCpDataNode OBJECT-TYPE
    SYNTAX          DisplayString
    ACCESS          read-only
    STATUS          mandatory
    DESCRIPTION     
            "FQDN or IP address of the data node. "
    ::= { sonusCpSystemDataAgentMIBNotificationsObjects 1 }

sonusCpDataAgentInstance OBJECT-TYPE
    SYNTAX          DisplayString
    ACCESS          read-only
    STATUS          mandatory
    DESCRIPTION     
            "Name of the data agent instance type. "
    ::= { sonusCpSystemDataAgentMIBNotificationsObjects 2 }

sonusCpDataAgentStream OBJECT-TYPE
    SYNTAX          DisplayString
    ACCESS          read-only
    STATUS          mandatory
    DESCRIPTION     
            "Data agent stream"
    ::= { sonusCpSystemDataAgentMIBNotificationsObjects 3 }

sonusSWeNewTrafficCommitNotifications OBJECT IDENTIFIER
    ::= { sonusCpBaseTraps 14 }

sonusSWeNewActiveProfiles OBJECT IDENTIFIER
    ::= { sonusSWeNewTrafficCommitNotifications 0 }

sonusSWeNewActiveProfileNotfierPrefix OBJECT IDENTIFIER
    ::= { sonusSWeNewTrafficCommitNotifications 1 }

sonusSWeNewTrafficProfileDetails OBJECT-TYPE
    SYNTAX          DisplayString
    ACCESS          read-only
    STATUS          deprecated
    DESCRIPTION     
            "Detailed information about the New SWe Profile Commit trap. "
    ::= { sonusSWeNewActiveProfileNotfierPrefix 1 }

sonusSWeBaseCapacityEstimationPrefix OBJECT IDENTIFIER
    ::= { sonusSWeNewTrafficCommitNotifications 2 }

sonusSWeCapacityEstimationDetails OBJECT-TYPE
    SYNTAX          DisplayString
    ACCESS          read-only
    STATUS          deprecated
    DESCRIPTION     
            "Capacity esimation details for the new base file. "
    ::= { sonusSWeBaseCapacityEstimationPrefix 2 }

sonusSWeBaseVcpuAllocationPrefix OBJECT IDENTIFIER
    ::= { sonusSWeNewTrafficCommitNotifications 3 }

sonusSWeVcpuAllocationDetails OBJECT-TYPE
    SYNTAX          DisplayString
    ACCESS          read-only
    STATUS          deprecated
    DESCRIPTION     
            "VCPU allocation details for the new base file. "
    ::= { sonusSWeBaseVcpuAllocationPrefix 3 }

sonusSWeActiveProfileMIBNotifications OBJECT IDENTIFIER
    ::= { sonusCpBaseTraps 15 }

sonusSWeActiveProfileMIBNotificationsPrefix OBJECT IDENTIFIER
    ::= { sonusSWeActiveProfileMIBNotifications 0 }

sonusSWeActiveProfileMIBNotificationsObjects OBJECT IDENTIFIER
    ::= { sonusSWeActiveProfileMIBNotifications 1 }

sonusFacPacketDroppedMIBNotifications OBJECT IDENTIFIER
    ::= { sonusCpBaseTraps 17 }

sonusFacPacketDroppedMIBNotificationsPrefix OBJECT IDENTIFIER
    ::= { sonusFacPacketDroppedMIBNotifications 0 }

sonusFacPacketDroppedMIBNotificationsObjects OBJECT IDENTIFIER
    ::= { sonusFacPacketDroppedMIBNotifications 1 }

sonusFacKeyElementName OBJECT-TYPE
    SYNTAX          DisplayString
    ACCESS          read-only
    STATUS          mandatory
    DESCRIPTION     
            "Key Element Name blocked"
    ::= { sonusFacPacketDroppedMIBNotificationsObjects 1 }

sonusFacKeyValueName OBJECT-TYPE
    SYNTAX          DisplayString
    ACCESS          read-only
    STATUS          mandatory
    DESCRIPTION     
            "Key Element value blocked"
    ::= { sonusFacPacketDroppedMIBNotificationsObjects 2 }

sonusCalledParty OBJECT-TYPE
    SYNTAX          DisplayString
    ACCESS          read-only
    STATUS          mandatory
    DESCRIPTION     
            "Provides called party information in case of blocking is due to callingNcalledParty key element."
    ::= { sonusFacPacketDroppedMIBNotificationsObjects 3 }

sonusDuplicateIpv6MIBNotifications OBJECT IDENTIFIER
    ::= { sonusCpBaseTraps 18 }

sonusDuplicateIpv6MIBNotificationsPrefix OBJECT IDENTIFIER
    ::= { sonusDuplicateIpv6MIBNotifications 0 }

sonusDuplicateIpv6MIBNotificationsObjects OBJECT IDENTIFIER
    ::= { sonusDuplicateIpv6MIBNotifications 1 }

sonusDuplicateIpv6Address OBJECT-TYPE
    SYNTAX          DisplayString
    ACCESS          read-only
    STATUS          mandatory
    DESCRIPTION     
            "Duplicate IPV6 address"
    ::= { sonusDuplicateIpv6MIBNotificationsObjects 1 }

sonusCpNtpServerInServiceNotification TRAP-TYPE
    ENTERPRISE      sonusCpNtpServicesMIBNotifications
    VARIABLES       { sonusAlarmNodeID, sonusAlarmLevel, 
                      sonusAlarmSequenceId, sonusAlarmTime, 
                      sonusAlarmDescription, sonusCpSystemServerName, 
                      sonusCpNtpIpAddress }
--     STATUS          mandatory
    DESCRIPTION     
            "This trap indicates that a Network Timing Protocol Server is in service."
    ::= 1

sonusCpNtpServerOutOfServiceNotification TRAP-TYPE
    ENTERPRISE      sonusCpNtpServicesMIBNotifications
    VARIABLES       { sonusAlarmNodeID, sonusAlarmLevel, 
                      sonusAlarmSequenceId, sonusAlarmTime, 
                      sonusAlarmDescription, sonusCpSystemServerName, 
                      sonusCpNtpIpAddress, 
                      sonusCpNtpServerOutOfServiceReason }
--     STATUS          mandatory
    DESCRIPTION     
            "This trap indicates that a Network Timing Protocol Server is out of service."
    ::= 2

sonusCpNtpUpNotification TRAP-TYPE
    ENTERPRISE      sonusCpNtpServicesMIBNotifications
    VARIABLES       { sonusAlarmNodeID, sonusAlarmLevel, 
                      sonusAlarmSequenceId, sonusAlarmTime, 
                      sonusAlarmDescription, sonusCpSystemServerName }
--     STATUS          mandatory
    DESCRIPTION     
            "This trap indicates that Network Timing Protocol Server is Up."
    ::= 3

sonusCpNtpDownNotification TRAP-TYPE
    ENTERPRISE      sonusCpNtpServicesMIBNotifications
    VARIABLES       { sonusAlarmNodeID, sonusAlarmLevel, 
                      sonusAlarmSequenceId, sonusAlarmTime, 
                      sonusAlarmDescription, sonusCpSystemServerName, 
                      sonusCpNtpDownReason }
--     STATUS          mandatory
    DESCRIPTION     
            "This trap indicates that Network Timing Protocol is down."
    ::= 4

sonusCpNtpAllServersOutOfSyncNotification TRAP-TYPE
    ENTERPRISE      sonusCpNtpServicesMIBNotifications
    VARIABLES       { sonusAlarmNodeID, sonusAlarmLevel, 
                      sonusAlarmSequenceId, sonusAlarmTime, 
                      sonusAlarmDescription, sonusCpSystemServerName }
--     STATUS          mandatory
    DESCRIPTION     
            "This trap indicates that all Network Timing Protocol Servers are Out of Sync."
    ::= 5

sonusCpNtpServerOutOfSyncNotification TRAP-TYPE
    ENTERPRISE      sonusCpNtpServicesMIBNotifications
    VARIABLES       { sonusAlarmNodeID, sonusAlarmLevel, 
                      sonusAlarmSequenceId, sonusAlarmTime, 
                      sonusAlarmDescription, sonusCpSystemServerName, 
                      sonusCpNtpIpAddress }
--     STATUS          mandatory
    DESCRIPTION     
            "This trap indicates that a Network Timing Protocol Server is out of Sync."
    ::= 6

sonusCpNtpServerInSyncNotification TRAP-TYPE
    ENTERPRISE      sonusCpNtpServicesMIBNotifications
    VARIABLES       { sonusAlarmNodeID, sonusAlarmLevel, 
                      sonusAlarmSequenceId, sonusAlarmTime, 
                      sonusAlarmDescription, sonusCpSystemServerName, 
                      sonusCpNtpIpAddress }
--     STATUS          mandatory
    DESCRIPTION     
            "This trap indicates that a Network Timing Protocol Server is in Sync."
    ::= 7

sonusCpNtpServerReachableNotification TRAP-TYPE
    ENTERPRISE      sonusCpNtpServicesMIBNotifications
    VARIABLES       { sonusAlarmNodeID, sonusAlarmLevel, 
                      sonusAlarmSequenceId, sonusAlarmTime, 
                      sonusAlarmDescription, sonusCpSystemServerName, 
                      sonusCpNtpIpAddress }
--     STATUS          mandatory
    DESCRIPTION     
            "This trap indicates that a Network Timing Protocol Server is Reachable."
    ::= 8

sonusCpRedundGroupSwitchOverNotification TRAP-TYPE
    ENTERPRISE      sonusCpRedundancyServicesMIBNotifications
    VARIABLES       { sonusAlarmNodeID, sonusAlarmLevel, 
                      sonusAlarmSequenceId, sonusAlarmTime, 
                      sonusAlarmDescription, sonusCpSystemServerName, 
                      sonusCpRedundPrevActiveServerName, 
                      sonusCpRedundancyServicesGroupName }
--     STATUS          mandatory
    DESCRIPTION     
            "This trap indicates a server module redundancy switchover has occurred.
             The standby server module has become active.  
             The previous active server module, and group
             information are included.  For 1+1 the redundancy model, there
             is no group name."
    ::= 1

sonusCpRedundGroupNoRedundancyNotification TRAP-TYPE
    ENTERPRISE      sonusCpRedundancyServicesMIBNotifications
    VARIABLES       { sonusAlarmNodeID, sonusAlarmLevel, 
                      sonusAlarmSequenceId, sonusAlarmTime, 
                      sonusAlarmDescription, 
                      sonusCpRedundancyServicesGroupName }
--     STATUS          mandatory
    DESCRIPTION     
            "This trap indicates that the specified redundancy group has
             no redundancy protection."
    ::= 2

sonusCpRedundGroupFullRedundancyNotification TRAP-TYPE
    ENTERPRISE      sonusCpRedundancyServicesMIBNotifications
    VARIABLES       { sonusAlarmNodeID, sonusAlarmLevel, 
                      sonusAlarmSequenceId, sonusAlarmTime, 
                      sonusAlarmDescription, 
                      sonusCpRedundancyServicesGroupName }
--     STATUS          mandatory
    DESCRIPTION     
            "This trap indicates that the specified redundancy group has
             full redundancy protection."
    ::= 3

sonusCpSoftwareUpgradeInitiatedNotification TRAP-TYPE
    ENTERPRISE      sonusCpSoftwareUpgradeServicesMIBNotifications
    VARIABLES       { sonusAlarmNodeID, sonusAlarmLevel, 
                      sonusAlarmSequenceId, sonusAlarmTime, 
                      sonusAlarmDescription, sonusCpSystemServerName }
--     STATUS          mandatory
    DESCRIPTION     
            "This trap indicates that a software upgrade 
             has been initiated."
    ::= 1

sonusCpSoftwareUpgradeTerminatedNotification TRAP-TYPE
    ENTERPRISE      sonusCpSoftwareUpgradeServicesMIBNotifications
    VARIABLES       { sonusAlarmNodeID, sonusAlarmLevel, 
                      sonusAlarmSequenceId, sonusAlarmTime, 
                      sonusAlarmDescription, 
                      sonusSystemSoftwareUpgradeStatusReason }
--     STATUS          mandatory
    DESCRIPTION     
            "This trap indicates that a software upgrade has terminated 
             for the specified reason."
    ::= 2

sonusCpSoftwareUpgradeSucceededNotification TRAP-TYPE
    ENTERPRISE      sonusCpSoftwareUpgradeServicesMIBNotifications
    VARIABLES       { sonusAlarmNodeID, sonusAlarmLevel, 
                      sonusAlarmSequenceId, sonusAlarmTime, 
                      sonusAlarmDescription, 
                      sonusSystemSoftwareUpgradeStatusReason }
--     STATUS          mandatory
    DESCRIPTION     
            "This trap indicates that a software upgrade has succeeded
             for the specified reason."
    ::= 3

sonusCpSoftwareUpgradeRevertNotification TRAP-TYPE
    ENTERPRISE      sonusCpSoftwareUpgradeServicesMIBNotifications
    VARIABLES       { sonusAlarmNodeID, sonusAlarmLevel, 
                      sonusAlarmSequenceId, sonusAlarmTime, 
                      sonusAlarmDescription }
--     STATUS          mandatory
    DESCRIPTION     
            "This trap indicates that a Live Software Upgrade
             revert to the previous release has occured."
    ::= 4

sonusCpSoftwareUpgradeCommitRequiredNotification TRAP-TYPE
    ENTERPRISE      sonusCpSoftwareUpgradeServicesMIBNotifications
    VARIABLES       { sonusAlarmNodeID, sonusAlarmLevel, 
                      sonusAlarmSequenceId, sonusAlarmTime, 
                      sonusAlarmDescription, 
                      sonusSystemSoftwareUpgradeOldRelease, 
                      sonusSystemSoftwareUpgradeNewRelease }
--     STATUS          deprecated
    DESCRIPTION     
            "This trap indicates that Live Software Upgrade
             commit is pending."
    ::= 5

sonusCpSoftwareUpgradeCommittedNotification TRAP-TYPE
    ENTERPRISE      sonusCpSoftwareUpgradeServicesMIBNotifications
    VARIABLES       { sonusAlarmNodeID, sonusAlarmLevel, 
                      sonusAlarmSequenceId, sonusAlarmTime, 
                      sonusAlarmDescription, 
                      sonusSystemSoftwareUpgradeOldRelease, 
                      sonusSystemSoftwareUpgradeNewRelease }
--     STATUS          mandatory
    DESCRIPTION     
            "This trap indicates that Live Software Upgrade is committed."
    ::= 6

sonusCpEventLogFileStateNotification TRAP-TYPE
    ENTERPRISE      sonusCpEventLogMIBNotifications
    VARIABLES       { sonusAlarmNodeID, sonusAlarmLevel, 
                      sonusAlarmSequenceId, sonusAlarmTime, 
                      sonusAlarmDescription, sonusCpEventLogType, 
                      sonusCpEvLogAdminState }
--     STATUS          mandatory
    DESCRIPTION     
            "This trap indicates the current state of event file logging."
    ::= 1

sonusCpEventLogFileCreatedNotification TRAP-TYPE
    ENTERPRISE      sonusCpEventLogMIBNotifications
    VARIABLES       { sonusAlarmNodeID, sonusAlarmLevel, 
                      sonusAlarmSequenceId, sonusAlarmTime, 
                      sonusAlarmDescription, sonusCpEventLogType, 
                      sonusEventLogTypeStatusCurrentFile }
--     STATUS          mandatory
    DESCRIPTION     
            "This trap indicates the name of the event file which has been created for logging."
    ::= 2

sonusCpEventLogFileRestartNotification TRAP-TYPE
    ENTERPRISE      sonusCpEventLogMIBNotifications
    VARIABLES       { sonusAlarmNodeID, sonusAlarmLevel, 
                      sonusAlarmSequenceId, sonusAlarmTime, 
                      sonusAlarmDescription, sonusCpEventLogType }
--     STATUS          mandatory
    DESCRIPTION     
            "This trap indicates that file event logging has been automatically restarted."
    ::= 3

sonusCpEventLogFileClosedNotification TRAP-TYPE
    ENTERPRISE      sonusCpEventLogMIBNotifications
    VARIABLES       { sonusAlarmNodeID, sonusAlarmLevel, 
                      sonusAlarmSequenceId, sonusAlarmTime, 
                      sonusAlarmDescription, sonusCpEventLogType, 
                      sonusEventLogTypeStatusCurrentFile }
--     STATUS          mandatory
    DESCRIPTION     
            "This trap indicates the name of the event file which has been closed."
    ::= 4

sonusCpEventLogFileShutdownNotification TRAP-TYPE
    ENTERPRISE      sonusCpEventLogMIBNotifications
    VARIABLES       { sonusAlarmNodeID, sonusAlarmLevel, 
                      sonusAlarmSequenceId, sonusAlarmTime, 
                      sonusAlarmDescription, sonusCpEventLogType, 
                      sonusCpEvLogShutdownReason, sonusCpEvLogAdminState }
--     STATUS          mandatory
    DESCRIPTION     
            "This trap indicates that a shutdown of file event logging has occurred."
    ::= 5

sonusCpEventLogFileCountNotification TRAP-TYPE
    ENTERPRISE      sonusCpEventLogMIBNotifications
    VARIABLES       { sonusAlarmNodeID, sonusAlarmLevel, 
                      sonusAlarmSequenceId, sonusAlarmTime, 
                      sonusAlarmDescription, sonusEvLogTypeName, 
                      sonusCpEvLogFilePercentage, 
                      sonusCpEvLogCurFileCount, 
                      sonusEventLogTypeAdminFileCount }
--     STATUS          mandatory
    DESCRIPTION     
            "This trap indicates that the number of event log files is approaching the configured maximum."
    ::= 6

sonusCpEventLogFileCountChngNotification TRAP-TYPE
    ENTERPRISE      sonusCpEventLogMIBNotifications
    VARIABLES       { sonusAlarmNodeID, sonusAlarmLevel, 
                      sonusAlarmSequenceId, sonusAlarmTime, 
                      sonusAlarmDescription, sonusCpEventLogType, 
                      sonusEventLogTypeAdminFileCount }
--     STATUS          mandatory
    DESCRIPTION     
            "This trap indicates the number of Event Log files that will be maintained for this event type is changed"
    ::= 7

sonusCpEventLogFileSizeChngNotification TRAP-TYPE
    ENTERPRISE      sonusCpEventLogMIBNotifications
    VARIABLES       { sonusAlarmNodeID, sonusAlarmLevel, 
                      sonusAlarmSequenceId, sonusAlarmTime, 
                      sonusAlarmDescription, sonusCpEventLogType, 
                      sonusEventLogTypeAdminFileSize }
--     STATUS          mandatory
    DESCRIPTION     
            "This trap indicates that the maximum size of a single event log file has changed."
    ::= 8

sonusCpEventLogFileMsgQueueChngNotification TRAP-TYPE
    ENTERPRISE      sonusCpEventLogMIBNotifications
    VARIABLES       { sonusAlarmNodeID, sonusAlarmLevel, 
                      sonusAlarmSequenceId, sonusAlarmTime, 
                      sonusAlarmDescription, sonusCpEventLogType, 
                      sonusEventLogTypeAdminMessageQueueSize }
--     STATUS          mandatory
    DESCRIPTION     
            "This trap indicates that the number event log message entries to the buffer changed"
    ::= 9

sonusCpEventLogSaveToChngNotification TRAP-TYPE
    ENTERPRISE      sonusCpEventLogMIBNotifications
    VARIABLES       { sonusAlarmNodeID, sonusAlarmLevel, 
                      sonusAlarmSequenceId, sonusAlarmTime, 
                      sonusAlarmDescription, sonusCpEventLogType, 
                      sonusEventLogTypeAdminSaveTo }
--     STATUS          mandatory
    DESCRIPTION     
            "This Trap indicates that the location where events are saved is being changed "
    ::= 10

sonusCpEventLogFileMaxEventMemSizeChngNotification TRAP-TYPE
    ENTERPRISE      sonusCpEventLogMIBNotifications
    VARIABLES       { sonusAlarmNodeID, sonusAlarmLevel, 
                      sonusAlarmSequenceId, sonusAlarmTime, 
                      sonusAlarmDescription, sonusCpEventLogType, 
                      sonusEventLogTypeAdminMaxEventMemorySize }
--     STATUS          mandatory
    DESCRIPTION     
            "This trap indicates that the maximum size of the memory event log buffer is changed"
    ::= 11

sonusCpEventLogFileFilterLevelChngNotification TRAP-TYPE
    ENTERPRISE      sonusCpEventLogMIBNotifications
    VARIABLES       { sonusAlarmNodeID, sonusAlarmLevel, 
                      sonusAlarmSequenceId, sonusAlarmTime, 
                      sonusAlarmDescription, sonusCpEventLogType, 
                      sonusEventLogTypeAdminFilterLevel }
--     STATUS          mandatory
    DESCRIPTION     
            "This trap indicates that the level of event logging for this event type is changed"
    ::= 12

sonusCpEventLogDirectoryCreateErrorNotification TRAP-TYPE
    ENTERPRISE      sonusCpEventLogMIBNotifications
    VARIABLES       { sonusAlarmNodeID, sonusAlarmLevel, 
                      sonusAlarmSequenceId, sonusAlarmTime, 
                      sonusAlarmDescription, sonusCpEventLogType, 
                      sonusCpEvLogDirName, sonusCpEvLogErrorCode }
--     STATUS          mandatory
    DESCRIPTION     
            "This trap indicates that the inability of the system to create a directory for event logging.
             This could also indicate an generic error with the NFS server."
    ::= 13

sonusCpEventLogRolloverScheduledNotification TRAP-TYPE
    ENTERPRISE      sonusCpEventLogMIBNotifications
    VARIABLES       { sonusAlarmNodeID, sonusAlarmLevel, 
                      sonusAlarmSequenceId, sonusAlarmTime, 
                      sonusAlarmDescription, sonusCpEventLogType }
--     STATUS          mandatory
    DESCRIPTION     
            "This trap indicates that event log for this log type is scheduled to rollover."
    ::= 14

sonusCpEventLogRolloverStoppedNotification TRAP-TYPE
    ENTERPRISE      sonusCpEventLogMIBNotifications
    VARIABLES       { sonusAlarmNodeID, sonusAlarmLevel, 
                      sonusAlarmSequenceId, sonusAlarmTime, 
                      sonusAlarmDescription, sonusCpEventLogType }
--     STATUS          mandatory
    DESCRIPTION     
            "This trap indicates that event log rollover for this log type is stopped."
    ::= 15

sonusCpEventLogRolloverFastNotification TRAP-TYPE
    ENTERPRISE      sonusCpEventLogMIBNotifications
    VARIABLES       { sonusAlarmNodeID, sonusAlarmLevel, 
                      sonusAlarmSequenceId, sonusAlarmTime, 
                      sonusAlarmDescription, sonusEvLogTypeName }
--     STATUS          mandatory
    DESCRIPTION     
            "This trap indicates that event log rollover is occuring frequently."
    ::= 16

sonusCpEventLogFileCountClearedNotification TRAP-TYPE
    ENTERPRISE      sonusCpEventLogMIBNotifications
    VARIABLES       { sonusAlarmNodeID, sonusAlarmLevel, 
                      sonusAlarmSequenceId, sonusAlarmTime, 
                      sonusAlarmDescription, sonusEvLogTypeName, 
                      sonusCpEvLogFilePercentage, 
                      sonusCpEvLogCurFileCount, 
                      sonusEventLogTypeAdminFileCount }
--     STATUS          mandatory
    DESCRIPTION     
            "This trap indicates that the number of event log files has dropped below the either the 100% or 75% threshold"
    ::= 17

sonusCpEventLogFileSkipped TRAP-TYPE
    ENTERPRISE      sonusCpEventLogMIBNotifications
    VARIABLES       { sonusAlarmNodeID, sonusAlarmLevel, 
                      sonusAlarmSequenceId, sonusAlarmTime, 
                      sonusAlarmDescription, sonusCpEventLogType, 
                      sonusEventLogTypeStatusCurrentFile }
--     STATUS          mandatory
    DESCRIPTION     
            "This trap indicates the name of the event file which has been skipped because of file errors."
    ::= 18

sonusCpEventLogFileDeletedNotification TRAP-TYPE
    ENTERPRISE      sonusCpEventLogMIBNotifications
    VARIABLES       { sonusAlarmNodeID, sonusAlarmLevel, 
                      sonusAlarmSequenceId, sonusAlarmTime, 
                      sonusAlarmDescription, sonusCpEventLogType, 
                      sonusEventLogTypeStatusCurrentFile }
--     STATUS          mandatory
    DESCRIPTION     
            "This trap indicates that an accountng file has been deleted because the maximum file count has been reached"
    ::= 19

sonusCpEventMgrAlarmManualClear TRAP-TYPE
    ENTERPRISE      sonusCpEventLogMIBNotifications
    VARIABLES       { sonusAlarmNodeID, sonusAlarmLevel, 
                      sonusAlarmSequenceId, sonusAlarmTime, 
                      sonusAlarmDescription, sonusAlarmMgrId }
--     STATUS          mandatory
    DESCRIPTION     
            "This trap indicates that an alarm has been manually cleared"
    ::= 20

sonusCpEventLogFileRenamedNotification TRAP-TYPE
    ENTERPRISE      sonusCpEventLogMIBNotifications
    VARIABLES       { sonusAlarmNodeID, sonusAlarmLevel, 
                      sonusAlarmSequenceId, sonusAlarmTime, 
                      sonusAlarmDescription, sonusCpEventLogType, 
                      sonusEventLogTypeStatusCurrentFile, 
                      sonusEventLogRenameToFile }
--     STATUS          mandatory
    DESCRIPTION     
            "This trap indicates that an accountng file has been renamed to remove the open file extension"
    ::= 21

sonusCpEventLogFileSecFilterLevelChngNotification TRAP-TYPE
    ENTERPRISE      sonusCpEventLogMIBNotifications
    VARIABLES       { sonusAlarmNodeID, sonusAlarmLevel, 
                      sonusAlarmSequenceId, sonusAlarmTime, 
                      sonusAlarmDescription, sonusCpEventLogType, 
                      sonusEventLogTypeAdminFilterLevel }
--     STATUS          mandatory
    DESCRIPTION     
            "This trap indicates that the level of event logging for this event type is changed"
    ::= 22

sonusCpEventLogAdminStateEnableNotification TRAP-TYPE
    ENTERPRISE      sonusCpEventLogMIBNotifications
    VARIABLES       { sonusAlarmNodeID, sonusAlarmLevel, 
                      sonusAlarmSequenceId, sonusAlarmTime, 
                      sonusAlarmDescription, sonusCpEventLogType }
--     STATUS          mandatory
    DESCRIPTION     
            "This trap indicates that the security or audit logging is enabled"
    ::= 23

sonusCpEventLogAdminStateDisableNotification TRAP-TYPE
    ENTERPRISE      sonusCpEventLogMIBNotifications
    VARIABLES       { sonusAlarmNodeID, sonusAlarmLevel, 
                      sonusAlarmSequenceId, sonusAlarmTime, 
                      sonusAlarmDescription, sonusCpEventLogType }
--     STATUS          mandatory
    DESCRIPTION     
            "This trap indicates that the security or audit logging is disabled"
    ::= 24

sonusCpEventLogFileWriteErrorNotification TRAP-TYPE
    ENTERPRISE      sonusCpEventLogMIBNotifications
    VARIABLES       { sonusAlarmNodeID, sonusAlarmLevel, 
                      sonusAlarmSequenceId, sonusAlarmTime, 
                      sonusAlarmDescription, 
                      sonusEventLogTypeStatusCurrentFile }
--     STATUS          mandatory
    DESCRIPTION     
            "This trap indicates the name of the event file which could not write an event."
    ::= 25

sonusCpEventLogInfoLevelLoggingDisabledNotfication TRAP-TYPE
    ENTERPRISE      sonusCpEventLogMIBNotifications
    VARIABLES       { sonusAlarmNodeID, sonusAlarmLevel, 
                      sonusAlarmSequenceId, sonusAlarmTime, 
                      sonusAlarmDescription }
--     STATUS          mandatory
    DESCRIPTION     
            "This trap indicates that info level logging has been disabled because of system congestion."
    ::= 26

sonusCpEventLogInfoLevelLoggingReenabledNotfication TRAP-TYPE
    ENTERPRISE      sonusCpEventLogMIBNotifications
    VARIABLES       { sonusAlarmNodeID, sonusAlarmLevel, 
                      sonusAlarmSequenceId, sonusAlarmTime, 
                      sonusAlarmDescription }
--     STATUS          mandatory
    DESCRIPTION     
            "This trap indicates that info level logging has been re-enabled."
    ::= 27

sonusCpEventMgrAlarmAckStateUpdate TRAP-TYPE
    ENTERPRISE      sonusCpEventLogMIBNotifications
    VARIABLES       { sonusAlarmNodeID, sonusAlarmLevel, 
                      sonusAlarmSequenceId, sonusAlarmTime, 
                      sonusAlarmDescription, sonusAlarmMgrId, 
                      sonusAlarmMgrAckState }
--     STATUS          mandatory
    DESCRIPTION     
            "This trap indicates that the alarm Ids acknowledge state has changed."
    ::= 28

sonusCpEventMgrAlarmCommentUpdate TRAP-TYPE
    ENTERPRISE      sonusCpEventLogMIBNotifications
    VARIABLES       { sonusAlarmNodeID, sonusAlarmLevel, 
                      sonusAlarmSequenceId, sonusAlarmTime, 
                      sonusAlarmDescription, sonusAlarmMgrId, 
                      sonusAlarmMgrComment }
--     STATUS          mandatory
    DESCRIPTION     
            "This trap indicates that the alarm Ids comment field has been updated."
    ::= 29

sonusCpEventLogFileDebugLevelInfoNotification TRAP-TYPE
    ENTERPRISE      sonusCpEventLogMIBNotifications
    VARIABLES       { sonusAlarmNodeID, sonusAlarmLevel, 
                      sonusAlarmSequenceId, sonusAlarmTime, 
                      sonusAlarmDescription }
--     STATUS          mandatory
    DESCRIPTION     
            "This trap indicates that the debug event log filter level has been set to INFO. "
    ::= 30

sonusCpEventLogFileDebugLevelInfoClearNotification TRAP-TYPE
    ENTERPRISE      sonusCpEventLogMIBNotifications
    VARIABLES       { sonusAlarmNodeID, sonusAlarmLevel, 
                      sonusAlarmSequenceId, sonusAlarmTime, 
                      sonusAlarmDescription }
--     STATUS          mandatory
    DESCRIPTION     
            "This trap indicates that the debug event log filter level is no longer set to INFO and clears sonusCpEventLogFileDebugLevelInfoNotification. "
    ::= 31

sonusCpSystemBootNotification TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName }
--     STATUS          mandatory
    DESCRIPTION     
            "This trap indicates that the node boot is requested."
    ::= 1

sonusCpSystemBootActiveNotification TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName }
--     STATUS          mandatory
    DESCRIPTION     
            "This trap indicates that the node is active after a reboot."
    ::= 2

sonusCpSystemSoftBootNotification TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName }
--     STATUS          mandatory
    DESCRIPTION     
            "This trap indicates that the node soft boot is requested."
    ::= 3

sonusCpSystemSoftBootActiveNotification TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName }
--     STATUS          mandatory
    DESCRIPTION     
            "This trap indicates that the node is active after a soft reboot."
    ::= 4

sonusCpSystemLocalDiskAvailableNotification TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName, 
                      sonusCpSystemServerName, 
                      sonusCpSystemHardDiskNumber }
--     STATUS          obsolete
    DESCRIPTION     
            "This trap indicates that a hard disk of a server is available."
    ::= 5

sonusCpSystemLocalDiskBadVolumeNotification TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName, 
                      sonusCpSystemServerName, 
                      sonusCpSystemHardDiskNumber }
--     STATUS          mandatory
    DESCRIPTION     
            "This trap indicates that bad volume is detected on hard disk of a server."
    ::= 6

sonusCpSystemLocalDiskMisMatchNotification TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName, 
                      sonusCpSystemServerName, 
                      sonusCpSystemHardDiskNumber }
--     STATUS          mandatory
    DESCRIPTION     
            "This trap indicates that an incorrect hard disk is inserted on a server."
    ::= 7

sonusCpSystemLocalDiskSpaceOkNotification TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName, 
                      sonusCpSystemServerName, 
                      sonusCpSystemHardDiskNumber, 
                      sonusCpSystemDiskPartition, 
                      sonusCpSystemDiskSpaceUsedPct }
--     STATUS          mandatory
    DESCRIPTION     
            "This trap indicates that space on the hard disk in with in the limits of normal operation."
    ::= 8

sonusCpSystemLocalDiskSpaceReadOnlyNotification TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName, 
                      sonusCpSystemServerName, 
                      sonusCpSystemHardDiskNumber }
--     STATUS          mandatory
    DESCRIPTION     
            "This trap indicates that space on the hard disk is low and no more data can be written and operating in read only mode."
    ::= 9

sonusCpSystemLocalDiskSpaceWarningNotification TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName, 
                      sonusCpSystemServerName, 
                      sonusCpSystemHardDiskNumber, 
                      sonusCpSystemDiskPartition, 
                      sonusCpSystemDiskSpaceUsedPct }
--     STATUS          mandatory
    DESCRIPTION     
            "This trap indicates that space on the hard disk is low."
    ::= 10

sonusCpSystemLocalDiskTooManyFilesNotification TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName, 
                      sonusCpSystemServerName, 
                      sonusCpSystemHardDiskNumber }
--     STATUS          mandatory
    DESCRIPTION     
            "This trap indicates that there are too many files on the hard disk."
    ::= 11

sonusCpSystemLocalDiskUnavailableNotification TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName, 
                      sonusCpSystemServerName, 
                      sonusCpSystemHardDiskNumber }
--     STATUS          obsolete
    DESCRIPTION     
            "This trap indicates that a hard disk is unavailable on the indicated server."
    ::= 12

sonusCpSystemLocalDiskWritableNotification TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName, 
                      sonusCpSystemServerName, 
                      sonusCpSystemHardDiskNumber }
--     STATUS          mandatory
    DESCRIPTION     
            "This trap indicates that space on a hard disk is above normal limit and disk is now writable."
    ::= 13

sonusCpSystemLocalDiskSyncStartNotification TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName, 
                      sonusCpSystemServerName, 
                      sonusCpSystemHardDiskNumber }
--     STATUS          obsolete
    DESCRIPTION     
            "This trap indicates that a hard disk synchronization is started on a server."
    ::= 14

sonusCpSystemLocalDiskSyncCompleteNotification TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName, 
                      sonusCpSystemServerName, 
                      sonusCpSystemHardDiskNumber }
--     STATUS          obsolete
    DESCRIPTION     
            "This trap indicates that a hard disk synchronization is completed on a server."
    ::= 15

sonusCpSystemCEDisabledNotification TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName, 
                      sonusCpSystemServerName }
--     STATUS          deprecated
    DESCRIPTION     
            "This trap indicates that a Server is disabled."
    ::= 16

sonusCpSystemCEEnabledNotification TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName, 
                      sonusCpSystemServerName }
--     STATUS          deprecated
    DESCRIPTION     
            "This trap indicates that a Server is enabled."
    ::= 17

sonusCpSystemCEOperationalNotification TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName, 
                      sonusCpSystemServerName }
--     STATUS          mandatory
    DESCRIPTION     
            "This trap indicates that a Server is operational."
    ::= 18

sonusCpSystemCEBootNotification TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName, 
                      sonusCpSystemServerName }
--     STATUS          mandatory
    DESCRIPTION     
            "This trap indicates that the CE/server boot is requested."
    ::= 19

sonusCpSystemCEBootActiveNotification TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName, 
                      sonusCpSystemServerName }
--     STATUS          mandatory
    DESCRIPTION     
            "This trap indicates that the CE/server is active after a reboot."
    ::= 20

sonusCpSystemCESoftBootNotification TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName, 
                      sonusCpSystemServerName }
--     STATUS          mandatory
    DESCRIPTION     
            "This trap indicates that the CE/server soft boot is requested."
    ::= 21

sonusCpSystemCESoftBootActiveNotification TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName, 
                      sonusCpSystemServerName }
--     STATUS          mandatory
    DESCRIPTION     
            "This trap indicates that the CE/server is active after a soft reboot."
    ::= 22

sonusCpSystemCETempFailureNotification TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName, 
                      sonusCpSystemServerName, 
                      sonusCpSystemServerTemperatureSensorId, 
                      sonusCpSystemServerTemperature }
--     STATUS          mandatory
    DESCRIPTION     
            "This trap indicates that the CE/server temperature is higher than normal."
    ::= 23

sonusCpSystemCETempNormalNotification TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName, 
                      sonusCpSystemServerName, 
                      sonusCpSystemServerTemperatureSensorId, 
                      sonusCpSystemServerTemperature }
--     STATUS          mandatory
    DESCRIPTION     
            "This trap indicates that the CE/server temperature is normal."
    ::= 24

sonusCpSystemCETempWarningNotification TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName, 
                      sonusCpSystemServerName, 
                      sonusCpSystemServerTemperatureSensorId, 
                      sonusCpSystemServerTemperature }
--     STATUS          mandatory
    DESCRIPTION     
            "This trap indicates that the CE/server temperature is reaching critical level."
    ::= 25

sonusCpConfigCommitSucceedNotification TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName, 
                      sonusCpSystemServerName }
--     STATUS          mandatory
    DESCRIPTION     
            "This trap indicates that a configuration commit has suceeded."
    ::= 26

sonusCpConfigCommitFailNotification TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName, 
                      sonusCpSystemServerName }
--     STATUS          mandatory
    DESCRIPTION     
            "This trap indicates that a configuration commit has failed."
    ::= 27

sonusCpSystemAllHardDisksFailedNotification TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName, 
                      sonusCpSystemServerName }
--     STATUS          obsolete
    DESCRIPTION     
            "This trap indicates that all the hard disks are unavailable on the indicated server."
    ::= 28

sonusCpSystemApacheFailedNotification TRAP-TYPE
    ENTERPRISE      sonusCpSystemServicesMIBNotifications
    VARIABLES       { sonusAlarmNodeID, sonusAlarmLevel, 
                      sonusAlarmSequenceId, sonusAlarmTime, 
                      sonusAlarmDescription, sonusCpSystemServerName }
--     STATUS          mandatory
    DESCRIPTION     
            "This trap indicates that the Apache service failed to start."
    ::= 29

sonusCpSystemServiceRestartedNotification TRAP-TYPE
    ENTERPRISE      sonusCpSystemServicesMIBNotifications
    VARIABLES       { sonusAlarmNodeID, sonusAlarmLevel, 
                      sonusAlarmSequenceId, sonusAlarmTime, 
                      sonusAlarmDescription, sonusCpSystemServerName, 
                      sonusCpSystemServiceRestartReason }
--     STATUS          obsolete
    DESCRIPTION     
            "This trap indicates the reason for the service restarting."
    ::= 30

sonusCpSystemNPTempFailureNotification TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName, 
                      sonusCpSystemServerName, 
                      sonusCpSystemServerTemperatureSensorId, 
                      sonusCpSystemServerTemperature }
--     STATUS          mandatory
    DESCRIPTION     
            "This trap indicates that the CE/server NP temperature is higher than normal."
    ::= 31

sonusCpSystemNPTempNormalNotification TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName, 
                      sonusCpSystemServerName, 
                      sonusCpSystemServerTemperatureSensorId, 
                      sonusCpSystemServerTemperature }
--     STATUS          mandatory
    DESCRIPTION     
            "This trap indicates that the CE/server NP temperature is normal."
    ::= 32

sonusCpSystemNPTempWarningNotification TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName, 
                      sonusCpSystemServerName, 
                      sonusCpSystemServerTemperatureSensorId, 
                      sonusCpSystemServerTemperature }
--     STATUS          mandatory
    DESCRIPTION     
            "This trap indicates that the CE/server NP temperature is reaching critical level."
    ::= 33

sonusCpSystemProcessCoredumpGeneratedNotification TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName, 
                      sonusCpSystemServerName, sonusCpSystemCoredumpFile }
--     STATUS          mandatory
    DESCRIPTION     
            "This trap indicates that a coredump is generated for a process running on the indicated server."
    ::= 36

sonusCpSystemCoredumpSpaceWarningNotification TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName, 
                      sonusCpSystemServerName, 
                      sonusCpSystemCoredumpSpacePct }
--     STATUS          mandatory
    DESCRIPTION     
            "This trap indicates that a system is running low on coredump space."
    ::= 37

sonusCpNodeStandbyDisabled TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName }
--     STATUS          mandatory
    DESCRIPTION     
            "This trap indicates that the node standby server is disabled."
    ::= 38

sonusCpNodeStandbyEnabled TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName }
--     STATUS          mandatory
    DESCRIPTION     
            "This trap indicates that the node standby server is enabled."
    ::= 39

sonusCpNodeHaPortDownNotification TRAP-TYPE
    ENTERPRISE      sonusCpSystemServicesMIBNotifications
    VARIABLES       { sonusAlarmNodeID, sonusAlarmLevel, 
                      sonusAlarmSequenceId, sonusAlarmTime, 
                      sonusAlarmDescription, sonusCpSystemServerName, 
                      sonusCpSystemPortName }
--     STATUS          mandatory
    DESCRIPTION     
            "This trap indicates that a high availability port is down."
    ::= 40

sonusCpNodeHaPortUpNotification TRAP-TYPE
    ENTERPRISE      sonusCpSystemServicesMIBNotifications
    VARIABLES       { sonusAlarmNodeID, sonusAlarmLevel, 
                      sonusAlarmSequenceId, sonusAlarmTime, 
                      sonusAlarmDescription, sonusCpSystemServerName, 
                      sonusCpSystemPortName }
--     STATUS          mandatory
    DESCRIPTION     
            "This trap indicates that a high availability port is up."
    ::= 41

sonusCpNodeBondingDeviceDownNotification TRAP-TYPE
    ENTERPRISE      sonusCpSystemServicesMIBNotifications
    VARIABLES       { sonusAlarmNodeID, sonusAlarmLevel, 
                      sonusAlarmSequenceId, sonusAlarmTime, 
                      sonusAlarmDescription, sonusCpSystemServerName }
--     STATUS          mandatory
    DESCRIPTION     
            "This trap indicates that the bonding device is down."
    ::= 42

sonusCpNodeBondingDeviceUpNotification TRAP-TYPE
    ENTERPRISE      sonusCpSystemServicesMIBNotifications
    VARIABLES       { sonusAlarmNodeID, sonusAlarmLevel, 
                      sonusAlarmSequenceId, sonusAlarmTime, 
                      sonusAlarmDescription, sonusCpSystemServerName }
--     STATUS          mandatory
    DESCRIPTION     
            "This trap indicates that the bonding device is up."
    ::= 43

sonusCpNodeHaPortDownNewNotification TRAP-TYPE
    ENTERPRISE      sonusCpSystemServicesMIBNotifications
    VARIABLES       { sonusAlarmNodeID, sonusAlarmLevel, 
                      sonusAlarmSequenceId, sonusAlarmTime, 
                      sonusAlarmDescription, sonusCpSystemServerName, 
                      sonusCpSystemPortName }
--     STATUS          mandatory
    DESCRIPTION     
            "This trap indicates that a high availability port is down."
    ::= 44

sonusCpSystemLocalRaidArrayDegradedNotification TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName, 
                      sonusCpSystemServerName, 
                      sonusCpSystemHardDiskNumber }
--     STATUS          obsolete
    DESCRIPTION     
            "This trap indicates that the RAID array has degraded due to a failure on the specified disk."
    ::= 45

sonusCpSystemRestoreConfigNotification TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName, 
                      sonusCpSystemConfigFileName }
--     STATUS          mandatory
    DESCRIPTION     
            "This trap indicates that the configuration restoration from specified config file is in progress."
    ::= 46

sonusCpSystemNotMacAddressOwnerNotification TRAP-TYPE
    ENTERPRISE      sonusCpSystemServicesMIBNotifications
    VARIABLES       { sonusAlarmNodeID, sonusAlarmLevel, 
                      sonusAlarmSequenceId, sonusAlarmTime, 
                      sonusAlarmDescription, sonusCpSelfBaseMacAddress, 
                      sonusCpPeerBaseMacAddress, 
                      sonusCpActiveBaseMacAddress }
--     STATUS          mandatory
    DESCRIPTION     
            "This trap indicates that the system is running with a set of MAC addresses that doesn't belog to this system. This is possible if a server is replaced."
    ::= 47

sonusSystemNodeResourceCongestionWarningNotification TRAP-TYPE
    ENTERPRISE      sonusCpSystemServicesMIBNotifications
    VARIABLES       { sonusAlarmNodeID, sonusAlarmLevel, 
                      sonusAlarmSequenceId, sonusAlarmTime, 
                      sonusAlarmDescription, sonusNodeOverloadType, 
                      sonusNodeOverloadLevel, 
                      sonusNodeOverloadThresholdCurrent, 
                      sonusNodeOverloadThresholdConfigured }
--     STATUS          mandatory
    DESCRIPTION     
            "This trap indicates that the system is running out of memory and will soon reboot."
    ::= 48

sonusCpSystemProductCapabalityMismatch TRAP-TYPE
    ENTERPRISE      sonusCpSystemServicesMIBNotifications
    VARIABLES       { sonusAlarmNodeID, sonusAlarmLevel, 
                      sonusAlarmSequenceId, sonusAlarmTime, 
                      sonusAlarmDescription, sonusCpSystemServerName, 
                      sonusCpProductCapabilityName, 
                      sonusCpProductCapabilityValue, 
                      sonusCpProductPeerCapabilityValue }
--     STATUS          mandatory
    DESCRIPTION     
            "This trap indicates that the specified server is running with a product capability that is not compatible with the peer capabilities."
    ::= 49

sonusSystemNodeResourceClearCongestionWarningNotification TRAP-TYPE
    ENTERPRISE      sonusCpSystemServicesMIBNotifications
    VARIABLES       { sonusAlarmNodeID, sonusAlarmLevel, 
                      sonusAlarmSequenceId, sonusAlarmTime, 
                      sonusAlarmDescription, sonusNodeOverloadType, 
                      sonusNodeOverloadLevel, 
                      sonusNodeOverloadThresholdCurrent, 
                      sonusNodeOverloadThresholdConfigured }
--     STATUS          mandatory
    DESCRIPTION     
            "This trap indicates that the system has fallen below the memory threshold"
    ::= 50

sonusCpSystemLocalDiskHealthErrorNotification TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName, 
                      sonusCpSystemServerName, sonusCpSystemHardDiskName, 
                      sonusCpSystemHardDiskError, 
                      sonusCpSystemLifeAvailAttrib }
--     STATUS          mandatory
    DESCRIPTION     
            "This trap indicates that the system received an error from  Self-Monitoring, Analysis and Reporting Technology (SMART) which is built into many hard drives"
    ::= 51

sonusCpSystemLocalDiskHealthErrorClearNotification TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName, 
                      sonusCpSystemServerName, sonusCpSystemHardDiskName, 
                      sonusCpSystemLifeAvailAttrib }
--     STATUS          mandatory
    DESCRIPTION     
            "This trap indicates that the system cleared an error cleared from Self-Monitoring, Analysis and Reporting Technology (SMART) which is built into many hard drives"
    ::= 52

sonusCpSystemLocalDiskLifeAttribErrorNotification TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName, 
                      sonusCpSystemServerName, sonusCpSystemHardDiskName, 
                      sonusCpSystemHardDiskError, 
                      sonusCpSystemLifeAvailAttrib }
--     STATUS          mandatory
    DESCRIPTION     
            "This trap indicates that the system received a life remaining threshold exceeded event from  Self-Monitoring, Analysis and Reporting Technology (SMART) which is built into many hard drives"
    ::= 53

sonusCpSystemLocalDiskLifeAttribErrorClearNotification TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName, 
                      sonusCpSystemServerName, sonusCpSystemHardDiskName, 
                      sonusCpSystemLifeAvailAttrib }
--     STATUS          mandatory
    DESCRIPTION     
            "This trap indicates that the system cleared life remaining threshold alarm from Self-Monitoring, Analysis and Reporting Technology (SMART) which is built into many hard drives"
    ::= 54

sonusSystemServerLinksDryupNotification TRAP-TYPE
    ENTERPRISE      sonusCpSystemServicesMIBNotifications
    VARIABLES       { sonusAlarmNodeID, sonusAlarmLevel, 
                      sonusAlarmSequenceId, sonusAlarmTime, 
                      sonusAlarmDescription, sonusCpSystemServerName }
--     STATUS          mandatory
    DESCRIPTION     
            "This trap indicates that the links for the specified server has dried up. Applicable to SGX4000 only."
    ::= 55

sonusCpSystemCEBootDeactiveNotification TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName, 
                      sonusCpSystemServerName }
--     STATUS          mandatory
    DESCRIPTION     
            "This trap indicates that the CE/server is deactivating."
    ::= 56

sonusCpSystemMemoryUsageWarningNotification TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName, 
                      sonusCpSystemServerName, sonusCpSystemMemoryUsage }
--     STATUS          mandatory
    DESCRIPTION     
            "This trap indicates that the system memory usage is high. This trap is only applicable for SGX4000"
    ::= 57

sonusCpSystemMemoryUsageOkNotification TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName, 
                      sonusCpSystemServerName }
--     STATUS          mandatory
    DESCRIPTION     
            "This trap indicates that the system memory usage is at a safe level. This trap is only applicable for SGX4000"
    ::= 58

sonusCpConfigHaSlaveDied TRAP-TYPE
    ENTERPRISE      sonusCpSystemServicesMIBNotifications
    VARIABLES       { sonusAlarmNodeID, sonusAlarmLevel, 
                      sonusAlarmSequenceId, sonusAlarmTime, 
                      sonusAlarmDescription }
--     STATUS          mandatory
    DESCRIPTION     
            "This trap indicates that the management active CE is no longer able to communicate configuration changes to the standby. This trap is only applicable for SGX4000"
    ::= 59

sonusCpSystemServerDrbdReformatCompletedNotification TRAP-TYPE
    ENTERPRISE      sonusCpSystemServicesMIBNotifications
    VARIABLES       { sonusAlarmNodeID, sonusAlarmLevel, 
                      sonusAlarmSequenceId, sonusAlarmTime, 
                      sonusAlarmDescription, sonusCpSystemServerName }
--     STATUS          obsolete
    DESCRIPTION     
            "This trap indicates drbd partition format has completed. A full disk sync will start"
    ::= 60

sonusCpSystemServerDrbdReformatStartNotification TRAP-TYPE
    ENTERPRISE      sonusCpSystemServicesMIBNotifications
    VARIABLES       { sonusAlarmNodeID, sonusAlarmLevel, 
                      sonusAlarmSequenceId, sonusAlarmTime, 
                      sonusAlarmDescription, sonusCpSystemServerName }
--     STATUS          obsolete
    DESCRIPTION     
            "This trap indicates that the drbd partition is being resized and reformatted to match the peer partition."
    ::= 61

sonusCpSystemServerDrbdReformatSwitchoverNotification TRAP-TYPE
    ENTERPRISE      sonusCpSystemServicesMIBNotifications
    VARIABLES       { sonusAlarmNodeID, sonusAlarmLevel, 
                      sonusAlarmSequenceId, sonusAlarmTime, 
                      sonusAlarmDescription, sonusCpSystemServerName }
--     STATUS          obsolete
    DESCRIPTION     
            "This trap indicates that the active server has requested the standby to become active, allowing the current active to reconfigure its drbd partition "
    ::= 62

sonusCpSystemServerDrbdReformatErrorNotification TRAP-TYPE
    ENTERPRISE      sonusCpSystemServicesMIBNotifications
    VARIABLES       { sonusAlarmNodeID, sonusAlarmLevel, 
                      sonusAlarmSequenceId, sonusAlarmTime, 
                      sonusAlarmDescription, sonusCpSystemServerName }
--     STATUS          obsolete
    DESCRIPTION     
            "This trap indicates that the drbd process encountered an error during reconfiguration"
    ::= 63

sonusCpSystemServerDrbdReformatBackupNotification TRAP-TYPE
    ENTERPRISE      sonusCpSystemServicesMIBNotifications
    VARIABLES       { sonusAlarmNodeID, sonusAlarmLevel, 
                      sonusAlarmSequenceId, sonusAlarmTime, 
                      sonusAlarmDescription, sonusCpSystemServerName }
--     STATUS          obsolete
    DESCRIPTION     
            "This trap indicates that the drbd process is backing up configuration and accounting files in preparation for a drbd partition reformat"
    ::= 64

sonusCpSystemMajorUserEvent TRAP-TYPE
    ENTERPRISE      sonusCpSystemServicesMIBNotifications
    VARIABLES       { sonusAlarmNodeID, sonusAlarmLevel, 
                      sonusAlarmSequenceId, sonusAlarmTime, 
                      sonusAlarmDescription, sonusCpSystemUserString }
--     STATUS          obsolete
    DESCRIPTION     
            "This trap is the user generated major severity trap. This trap is only applicable for SGX4000."
    ::= 65

sonusCpSystemMinorUserEvent TRAP-TYPE
    ENTERPRISE      sonusCpSystemServicesMIBNotifications
    VARIABLES       { sonusAlarmNodeID, sonusAlarmLevel, 
                      sonusAlarmSequenceId, sonusAlarmTime, 
                      sonusAlarmDescription, sonusCpSystemUserString }
--     STATUS          obsolete
    DESCRIPTION     
            "This trap is the user generated minor severity trap. This trap is only applicable for SGX4000."
    ::= 66

sonusCpSystemInfoUserEvent TRAP-TYPE
    ENTERPRISE      sonusCpSystemServicesMIBNotifications
    VARIABLES       { sonusAlarmNodeID, sonusAlarmLevel, 
                      sonusAlarmSequenceId, sonusAlarmTime, 
                      sonusAlarmDescription, sonusCpSystemUserString }
--     STATUS          obsolete
    DESCRIPTION     
            "This trap is the user generated info severity trap. This trap is only applicable for SGX4000."
    ::= 67

sonusCpSystemServerDrbdReformatStartNotify TRAP-TYPE
    ENTERPRISE      sonusCpSystemServicesMIBNotifications
    VARIABLES       { sonusAlarmNodeID, sonusAlarmLevel, 
                      sonusAlarmSequenceId, sonusAlarmTime, 
                      sonusAlarmDescription, sonusCpSystemServerName }
--     STATUS          mandatory
    DESCRIPTION     
            "This trap indicates that the drbd partition is being resized and reformatted to match the peer partition. This trap is only applicable for SBX."
    ::= 68

sonusCpSystemServerDrbdReformatSwitchoverNotify TRAP-TYPE
    ENTERPRISE      sonusCpSystemServicesMIBNotifications
    VARIABLES       { sonusAlarmNodeID, sonusAlarmLevel, 
                      sonusAlarmSequenceId, sonusAlarmTime, 
                      sonusAlarmDescription, sonusCpSystemServerName }
--     STATUS          mandatory
    DESCRIPTION     
            "This trap indicates that the active server has requested the standby to become active, allowing the current active to reconfigure its drbd partition. This trap is only applicable for SBX."
    ::= 69

sonusCpSystemServerDrbdReformatErrorNotify TRAP-TYPE
    ENTERPRISE      sonusCpSystemServicesMIBNotifications
    VARIABLES       { sonusAlarmNodeID, sonusAlarmLevel, 
                      sonusAlarmSequenceId, sonusAlarmTime, 
                      sonusAlarmDescription, sonusCpSystemServerName }
--     STATUS          mandatory
    DESCRIPTION     
            "This trap indicates that the drbd process encountered an error during reconfiguration. This trap is only applicable for SBX."
    ::= 70

sonusCpSystemServerDrbdReformatBackupNotify TRAP-TYPE
    ENTERPRISE      sonusCpSystemServicesMIBNotifications
    VARIABLES       { sonusAlarmNodeID, sonusAlarmLevel, 
                      sonusAlarmSequenceId, sonusAlarmTime, 
                      sonusAlarmDescription, sonusCpSystemServerName }
--     STATUS          mandatory
    DESCRIPTION     
            "This trap indicates that the drbd process is backing up configuration and accounting files in preparation for a drbd partition reformat. This trap is only applicable for SBX."
    ::= 71

sonusCpSystemServerDrbdReformatCompletedNotify TRAP-TYPE
    ENTERPRISE      sonusCpSystemServicesMIBNotifications
    VARIABLES       { sonusAlarmNodeID, sonusAlarmLevel, 
                      sonusAlarmSequenceId, sonusAlarmTime, 
                      sonusAlarmDescription, sonusCpSystemServerName }
--     STATUS          mandatory
    DESCRIPTION     
            "This trap indicates drbd partition format has completed. A full disk sync will start. This trap is only applicable for SBX."
    ::= 72

sonusCpSystemMemoryModuleFaultNotify TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName, 
                      sonusCpSystemServerName }
--     STATUS          mandatory
    DESCRIPTION     
            "This trap indicates that a server memory module maybe faulty. This trap is only applicable for SGX4000."
    ::= 73

sonusCpSystemReadonlyFileSystemNotify TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName, 
                      sonusCpSystemServerName }
--     STATUS          mandatory
    DESCRIPTION     
            "This trap indicates that the file system has gone into a read only state and nothing can be written to disk."
    ::= 74

sonusCpSystemFaultyHardDiskNotify TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName, 
                      sonusCpSystemServerName }
--     STATUS          mandatory
    DESCRIPTION     
            "This trap indicates that a hard disk maybe faulty."
    ::= 75

sonusCpConfigHaInSyncNotify TRAP-TYPE
    ENTERPRISE      sonusCpSystemServicesMIBNotifications
    VARIABLES       { sonusAlarmNodeID, sonusAlarmLevel, 
                      sonusAlarmSequenceId, sonusAlarmTime, 
                      sonusAlarmDescription }
--     STATUS          mandatory
    DESCRIPTION     
            "This trap indicates that the management active CE is in sync with the standby for configuration changes. This trap is only applicable for SGX4000."
    ::= 76

sonusCpSystemCriticalUserEventNotify TRAP-TYPE
    ENTERPRISE      sonusCpSystemServicesMIBNotifications
    VARIABLES       { sonusAlarmNodeID, sonusAlarmLevel, 
                      sonusAlarmSequenceId, sonusAlarmTime, 
                      sonusAlarmDescription, sonusCpSystemUserString }
--     STATUS          obsolete
    DESCRIPTION     
            "This trap is the user generated critical severity trap. This trap is only applicable for SGX4000."
    ::= 77

sonusCpSystemLocalDiskSpaceCriticalNotification TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName, 
                      sonusCpSystemServerName, 
                      sonusCpSystemHardDiskNumber, 
                      sonusCpSystemDiskPartition, 
                      sonusCpSystemDiskSpaceUsedPct }
--     STATUS          mandatory
    DESCRIPTION     
            "This trap indicates that space on the hard disk is low."
    ::= 78

sonusCpSystemLocalDiskSpaceFaultNotification TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName, 
                      sonusCpSystemServerName, 
                      sonusCpSystemHardDiskNumber, 
                      sonusCpSystemDiskPartition, 
                      sonusCpSystemDiskSpaceUsedPct }
--     STATUS          mandatory
    DESCRIPTION     
            "This trap indicates that space on the hard disk is low."
    ::= 79

sonusCpSystemLocalDiskSpaceClearAlarmsNotification TRAP-TYPE
    ENTERPRISE      sonusCpSystemServicesMIBNotifications
    VARIABLES       { sonusAlarmNodeID, sonusAlarmLevel, 
                      sonusAlarmSequenceId, sonusAlarmTime, 
                      sonusAlarmDescription, sonusCpSystemAdminName, 
                      sonusCpSystemServerName, 
                      sonusCpSystemHardDiskNumber, 
                      sonusCpSystemDiskPartition, 
                      sonusCpSystemDiskSpaceUsedPct }
--     STATUS          mandatory
    DESCRIPTION     
            "This trap clears all previous disk space usage alarms before issuing fresh ones."
    ::= 80

sonusCpSystemCriticalUserEventNfy TRAP-TYPE
    ENTERPRISE      sonusCpSystemServicesMIBNotifications
    VARIABLES       { sonusAlarmNodeID, sonusAlarmLevel, 
                      sonusAlarmSequenceId, sonusAlarmTime, 
                      sonusAlarmDescription, sonusCpSystemUserInfoString }
--     STATUS          mandatory
    DESCRIPTION     
            "This trap is the user generated critical severity trap. This trap is only applicable for SGX4000."
    ::= 81

sonusCpSystemMajorUserEventNfy TRAP-TYPE
    ENTERPRISE      sonusCpSystemServicesMIBNotifications
    VARIABLES       { sonusAlarmNodeID, sonusAlarmLevel, 
                      sonusAlarmSequenceId, sonusAlarmTime, 
                      sonusAlarmDescription, sonusCpSystemUserInfoString }
--     STATUS          mandatory
    DESCRIPTION     
            "This trap is the user generated major severity trap. This trap is only applicable for SGX4000."
    ::= 82

sonusCpSystemMinorUserEventNfy TRAP-TYPE
    ENTERPRISE      sonusCpSystemServicesMIBNotifications
    VARIABLES       { sonusAlarmNodeID, sonusAlarmLevel, 
                      sonusAlarmSequenceId, sonusAlarmTime, 
                      sonusAlarmDescription, sonusCpSystemUserInfoString }
--     STATUS          mandatory
    DESCRIPTION     
            "This trap is the user generated minor severity trap. This trap is only applicable for SGX4000."
    ::= 83

sonusCpSystemInfoUserEventNfy TRAP-TYPE
    ENTERPRISE      sonusCpSystemServicesMIBNotifications
    VARIABLES       { sonusAlarmNodeID, sonusAlarmLevel, 
                      sonusAlarmSequenceId, sonusAlarmTime, 
                      sonusAlarmDescription, sonusCpSystemUserInfoString }
--     STATUS          mandatory
    DESCRIPTION     
            "This trap is the user generated info severity trap. This trap is only applicable for SGX4000."
    ::= 84

sonusCpSystemServiceRestartNotification TRAP-TYPE
    ENTERPRISE      sonusCpSystemServicesMIBNotifications
    VARIABLES       { sonusAlarmNodeID, sonusAlarmLevel, 
                      sonusAlarmSequenceId, sonusAlarmTime, 
                      sonusAlarmDescription, sonusCpSystemServerName, 
                      sonusCpSystemApplicationRestartReason }
--     STATUS          mandatory
    DESCRIPTION     
            "This trap indicates the reason for the service restarting."
    ::= 85

sonusCpSystemSwitchoverIncompleteNotification TRAP-TYPE
    ENTERPRISE      sonusCpSystemServicesMIBNotifications
    VARIABLES       { sonusAlarmNodeID, sonusAlarmLevel, 
                      sonusAlarmSequenceId, sonusAlarmTime, 
                      sonusAlarmDescription }
--     STATUS          mandatory
    DESCRIPTION     
            "This trap indicates indicates that this CE started to switchover but the process did not complete, leaving the system in an undefined state. This trap is only applicable for SGX4000."
    ::= 86

sonusCpSystemRsyslogRemoteServerConnectionIssue TRAP-TYPE
    ENTERPRISE      sonusCpSystemServicesMIBNotifications
    VARIABLES       { sonusAlarmNodeID, sonusAlarmLevel, 
                      sonusAlarmSequenceId, sonusAlarmTime, 
                      sonusAlarmDescription, sonusServerIpAddress }
--     STATUS          mandatory
    DESCRIPTION     
            "This trap indicates there is a connection issue with the remote server being used for rsyslog."
    ::= 87

sonusCpSystemRsyslogRemoteServerConnectionRecovered TRAP-TYPE
    ENTERPRISE      sonusCpSystemServicesMIBNotifications
    VARIABLES       { sonusAlarmNodeID, sonusAlarmLevel, 
                      sonusAlarmSequenceId, sonusAlarmTime, 
                      sonusAlarmDescription, sonusServerIpAddress }
--     STATUS          mandatory
    DESCRIPTION     
            "This trap indicates that connection has been established for the remote server being used for rsyslog"
    ::= 88

sonusCpNifCrcErrorRateExceededNotification TRAP-TYPE
    ENTERPRISE      sonusCpNifMIBNotifications
    VARIABLES       { sonusAlarmNodeID, sonusAlarmLevel, 
                      sonusAlarmSequenceId, sonusAlarmTime, 
                      sonusAlarmDescription, sonusCpNifCeName, 
                      sonusCpNifType, sonusCpNifUsage }
--     STATUS          mandatory
    DESCRIPTION     
            "This trap indicates that CRC error rate has exceeded set threshold for the set duration."
    ::= 1

sonusCpNifCrcErrorRateClearedNotification TRAP-TYPE
    ENTERPRISE      sonusCpNifMIBNotifications
    VARIABLES       { sonusAlarmNodeID, sonusAlarmLevel, 
                      sonusAlarmSequenceId, sonusAlarmTime, 
                      sonusAlarmDescription, sonusCpNifCeName, 
                      sonusCpNifType, sonusCpNifUsage }
--     STATUS          mandatory
    DESCRIPTION     
            "This trap indicates that CRC error rate gone below the clear threshold for the clear duration."
    ::= 2

sonusCpNifCodeViolationErrorRateExceededNotification TRAP-TYPE
    ENTERPRISE      sonusCpNifMIBNotifications
    VARIABLES       { sonusAlarmNodeID, sonusAlarmLevel, 
                      sonusAlarmSequenceId, sonusAlarmTime, 
                      sonusAlarmDescription, sonusCpNifCeName, 
                      sonusCpNifType, sonusCpNifUsage }
--     STATUS          mandatory
    DESCRIPTION     
            "This trap indicates that code violation error rate has exceeded set threshold for the set duration."
    ::= 3

sonusCpNifCodeViolationErrorRateClearedNotification TRAP-TYPE
    ENTERPRISE      sonusCpNifMIBNotifications
    VARIABLES       { sonusAlarmNodeID, sonusAlarmLevel, 
                      sonusAlarmSequenceId, sonusAlarmTime, 
                      sonusAlarmDescription, sonusCpNifCeName, 
                      sonusCpNifType, sonusCpNifUsage }
--     STATUS          mandatory
    DESCRIPTION     
            "This trap indicates that code violation error rate gone below the clear threshold for the clear duration."
    ::= 4

sonusCpMaxPacketLengthErrorRateExceededNotification TRAP-TYPE
    ENTERPRISE      sonusCpNifMIBNotifications
    VARIABLES       { sonusAlarmNodeID, sonusAlarmLevel, 
                      sonusAlarmSequenceId, sonusAlarmTime, 
                      sonusAlarmDescription, sonusCpNifCeName, 
                      sonusCpNifType, sonusCpNifUsage }
--     STATUS          mandatory
    DESCRIPTION     
            "This trap indicates that the maximum packet length error rate has exceeded set threshold for the set duration."
    ::= 5

sonusCpMaxPacketLengthErrorRateClearedNotification TRAP-TYPE
    ENTERPRISE      sonusCpNifMIBNotifications
    VARIABLES       { sonusAlarmNodeID, sonusAlarmLevel, 
                      sonusAlarmSequenceId, sonusAlarmTime, 
                      sonusAlarmDescription, sonusCpNifCeName, 
                      sonusCpNifType, sonusCpNifUsage }
--     STATUS          mandatory
    DESCRIPTION     
            "This trap indicates that the maximum packet length error rate gone below the clear threshold for the clear duration."
    ::= 6

sonusCpNifRcrDcfErrorRateExceededNotification TRAP-TYPE
    ENTERPRISE      sonusCpNifMIBNotifications
    VARIABLES       { sonusAlarmNodeID, sonusAlarmLevel, 
                      sonusAlarmSequenceId, sonusAlarmTime, 
                      sonusAlarmDescription, sonusCpNifCeName, 
                      sonusCpNifType, sonusCpNifUsage }
--     STATUS          mandatory
    DESCRIPTION     
            "This trap indicates that the RCR DFC error rate has exceeded set threshold for the set duration."
    ::= 7

sonusCpfRcrDcfErrorRateClearedNotification TRAP-TYPE
    ENTERPRISE      sonusCpNifMIBNotifications
    VARIABLES       { sonusAlarmNodeID, sonusAlarmLevel, 
                      sonusAlarmSequenceId, sonusAlarmTime, 
                      sonusAlarmDescription, sonusCpNifCeName, 
                      sonusCpNifType, sonusCpNifUsage }
--     STATUS          mandatory
    DESCRIPTION     
            "This trap indicates that the RCR DFC error rate gone below the clear threshold for the clear duration."
    ::= 8

sonusCpNifRcrErrorRateExceededNotification TRAP-TYPE
    ENTERPRISE      sonusCpNifMIBNotifications
    VARIABLES       { sonusAlarmNodeID, sonusAlarmLevel, 
                      sonusAlarmSequenceId, sonusAlarmTime, 
                      sonusAlarmDescription, sonusCpNifCeName, 
                      sonusCpNifType, sonusCpNifUsage }
--     STATUS          mandatory
    DESCRIPTION     
            "This trap indicates that the RCR error rate has exceeded set threshold for the set duration."
    ::= 9

sonusCpNifRcrErrorRateClearedNotification TRAP-TYPE
    ENTERPRISE      sonusCpNifMIBNotifications
    VARIABLES       { sonusAlarmNodeID, sonusAlarmLevel, 
                      sonusAlarmSequenceId, sonusAlarmTime, 
                      sonusAlarmDescription, sonusCpNifCeName, 
                      sonusCpNifType, sonusCpNifUsage }
--     STATUS          mandatory
    DESCRIPTION     
            "This trap indicates that the RCR error rate gone below the clear threshold for the clear duration."
    ::= 10

sonusCpNifResourceErrorRateExceededNotification TRAP-TYPE
    ENTERPRISE      sonusCpNifMIBNotifications
    VARIABLES       { sonusAlarmNodeID, sonusAlarmLevel, 
                      sonusAlarmSequenceId, sonusAlarmTime, 
                      sonusAlarmDescription, sonusCpNifCeName, 
                      sonusCpNifType, sonusCpNifUsage }
--     STATUS          mandatory
    DESCRIPTION     
            "This trap indicates that the Resource Error rate has exceeded set threshold for the set duration."
    ::= 11

sonusCpNifResourceErrorRateClearedNotification TRAP-TYPE
    ENTERPRISE      sonusCpNifMIBNotifications
    VARIABLES       { sonusAlarmNodeID, sonusAlarmLevel, 
                      sonusAlarmSequenceId, sonusAlarmTime, 
                      sonusAlarmDescription, sonusCpNifCeName, 
                      sonusCpNifType, sonusCpNifUsage }
--     STATUS          mandatory
    DESCRIPTION     
            "This trap indicates that the Resource Error rate gone below the clear threshold for the clear duration."
    ::= 12

sonusCpNifRingOverflowErrorRateExceededNotification TRAP-TYPE
    ENTERPRISE      sonusCpNifMIBNotifications
    VARIABLES       { sonusAlarmNodeID, sonusAlarmLevel, 
                      sonusAlarmSequenceId, sonusAlarmTime, 
                      sonusAlarmDescription, sonusCpNifCeName, 
                      sonusCpNifType, sonusCpNifUsage }
--     STATUS          mandatory
    DESCRIPTION     
            "This trap indicates that the Overflow Error Rate rate has exceeded set threshold for the set duration."
    ::= 13

sonusCpNifRingOverflowErrorRateClearedNotification TRAP-TYPE
    ENTERPRISE      sonusCpNifMIBNotifications
    VARIABLES       { sonusAlarmNodeID, sonusAlarmLevel, 
                      sonusAlarmSequenceId, sonusAlarmTime, 
                      sonusAlarmDescription, sonusCpNifCeName, 
                      sonusCpNifType, sonusCpNifUsage }
--     STATUS          mandatory
    DESCRIPTION     
            "This trap indicates that the Overflow Error Rate rate gone below the clear threshold for the clear duration."
    ::= 14

sonusCpNifDroppedPacketsRateExceededNotification TRAP-TYPE
    ENTERPRISE      sonusCpNifMIBNotifications
    VARIABLES       { sonusAlarmNodeID, sonusAlarmLevel, 
                      sonusAlarmSequenceId, sonusAlarmTime, 
                      sonusAlarmDescription, sonusCpNifCeName, 
                      sonusCpNifType, sonusCpNifUsage }
--     STATUS          mandatory
    DESCRIPTION     
            "This trap indicates that the Dropped Packets rate has exceeded set threshold for the set duration."
    ::= 15

sonusCpNifRateDroppedPacketsClearedNotification TRAP-TYPE
    ENTERPRISE      sonusCpNifMIBNotifications
    VARIABLES       { sonusAlarmNodeID, sonusAlarmLevel, 
                      sonusAlarmSequenceId, sonusAlarmTime, 
                      sonusAlarmDescription, sonusCpNifCeName, 
                      sonusCpNifType, sonusCpNifUsage }
--     STATUS          mandatory
    DESCRIPTION     
            "This trap indicates that the Dropped Packets rate gone below the clear threshold for the clear duration."
    ::= 16

sonusCpNifRbrPrefetchEmptyErrorRateExceededNotification TRAP-TYPE
    ENTERPRISE      sonusCpNifMIBNotifications
    VARIABLES       { sonusAlarmNodeID, sonusAlarmLevel, 
                      sonusAlarmSequenceId, sonusAlarmTime, 
                      sonusAlarmDescription, sonusCpNifCeName, 
                      sonusCpNifType, sonusCpNifUsage }
--     STATUS          mandatory
    DESCRIPTION     
            "This trap indicates that the RBR Prefetch Empty rate has exceeded set threshold for the set duration."
    ::= 17

sonusCpNifRbrPrefetchEmptyErrorRateClearedNotification TRAP-TYPE
    ENTERPRISE      sonusCpNifMIBNotifications
    VARIABLES       { sonusAlarmNodeID, sonusAlarmLevel, 
                      sonusAlarmSequenceId, sonusAlarmTime, 
                      sonusAlarmDescription, sonusCpNifCeName, 
                      sonusCpNifType, sonusCpNifUsage }
--     STATUS          mandatory
    DESCRIPTION     
            "This trap indicates that the RBR Prefetch Empty rate gone below the clear threshold for the clear duration."
    ::= 18

sonusCpNifRbrEmptyErrorRateExceededNotification TRAP-TYPE
    ENTERPRISE      sonusCpNifMIBNotifications
    VARIABLES       { sonusAlarmNodeID, sonusAlarmLevel, 
                      sonusAlarmSequenceId, sonusAlarmTime, 
                      sonusAlarmDescription, sonusCpNifCeName, 
                      sonusCpNifType, sonusCpNifUsage }
--     STATUS          mandatory
    DESCRIPTION     
            "This trap indicates that the RBR Empty rate has exceeded set threshold for the set duration."
    ::= 19

sonusCpNifRbrEmptyErrorRateClearedNotification TRAP-TYPE
    ENTERPRISE      sonusCpNifMIBNotifications
    VARIABLES       { sonusAlarmNodeID, sonusAlarmLevel, 
                      sonusAlarmSequenceId, sonusAlarmTime, 
                      sonusAlarmDescription, sonusCpNifCeName, 
                      sonusCpNifType, sonusCpNifUsage }
--     STATUS          mandatory
    DESCRIPTION     
            "This trap indicates that the RBR Empty rate gone below the clear threshold for the clear duration."
    ::= 20

sonusCpNifWredDroppedPacketsRateExceededNotification TRAP-TYPE
    ENTERPRISE      sonusCpNifMIBNotifications
    VARIABLES       { sonusAlarmNodeID, sonusAlarmLevel, 
                      sonusAlarmSequenceId, sonusAlarmTime, 
                      sonusAlarmDescription, sonusCpNifCeName, 
                      sonusCpNifType, sonusCpNifUsage }
--     STATUS          mandatory
    DESCRIPTION     
            "This trap indicates that the WRED Dropped Packets rate has exceeded set threshold for the set duration."
    ::= 21

sonusCpNifWredDroppedPacketsRateClearedNotification TRAP-TYPE
    ENTERPRISE      sonusCpNifMIBNotifications
    VARIABLES       { sonusAlarmNodeID, sonusAlarmLevel, 
                      sonusAlarmSequenceId, sonusAlarmTime, 
                      sonusAlarmDescription, sonusCpNifCeName, 
                      sonusCpNifType, sonusCpNifUsage }
--     STATUS          mandatory
    DESCRIPTION     
            "This trap indicates that the WRED Dropped Packets rate gone below the clear threshold for the clear duration."
    ::= 22

sonusCpNifMailBoxNotification TRAP-TYPE
    ENTERPRISE      sonusCpNifMIBNotifications
    VARIABLES       { sonusAlarmNodeID, sonusAlarmLevel, 
                      sonusAlarmSequenceId, sonusAlarmTime, 
                      sonusAlarmDescription, sonusCpNifCeName, 
                      sonusCpNifType, sonusCpNifUsage }
--     STATUS          mandatory
    DESCRIPTION     
            "This trap indicates a fatal mailbox error."
    ::= 23

sonusCpNifNackPacketReadErrorNotification TRAP-TYPE
    ENTERPRISE      sonusCpNifMIBNotifications
    VARIABLES       { sonusAlarmNodeID, sonusAlarmLevel, 
                      sonusAlarmSequenceId, sonusAlarmTime, 
                      sonusAlarmDescription, sonusCpNifCeName, 
                      sonusCpNifType, sonusCpNifUsage }
--     STATUS          mandatory
    DESCRIPTION     
            "This trap indicates a fatal NACK Packet Read Error."
    ::= 24

sonusCpNifNackPrefetchErrorNotification TRAP-TYPE
    ENTERPRISE      sonusCpNifMIBNotifications
    VARIABLES       { sonusAlarmNodeID, sonusAlarmLevel, 
                      sonusAlarmSequenceId, sonusAlarmTime, 
                      sonusAlarmDescription, sonusCpNifCeName, 
                      sonusCpNifType, sonusCpNifUsage }
--     STATUS          mandatory
    DESCRIPTION     
            "This trap indicates a fatal NACK Prefetch Error."
    ::= 25

sonusCpNifPacketSizeErrorNotification TRAP-TYPE
    ENTERPRISE      sonusCpNifMIBNotifications
    VARIABLES       { sonusAlarmNodeID, sonusAlarmLevel, 
                      sonusAlarmSequenceId, sonusAlarmTime, 
                      sonusAlarmDescription, sonusCpNifCeName, 
                      sonusCpNifType, sonusCpNifUsage }
--     STATUS          mandatory
    DESCRIPTION     
            "This trap indicates a fatal Packet Size Error."
    ::= 26

sonusCpNifPacketPointerErrorNotification TRAP-TYPE
    ENTERPRISE      sonusCpNifMIBNotifications
    VARIABLES       { sonusAlarmNodeID, sonusAlarmLevel, 
                      sonusAlarmSequenceId, sonusAlarmTime, 
                      sonusAlarmDescription, sonusCpNifCeName, 
                      sonusCpNifType, sonusCpNifUsage }
--     STATUS          mandatory
    DESCRIPTION     
            "This trap indicates a fatal Packet Pointer Error."
    ::= 27

sonusCpNifParityErrorNotification TRAP-TYPE
    ENTERPRISE      sonusCpNifMIBNotifications
    VARIABLES       { sonusAlarmNodeID, sonusAlarmLevel, 
                      sonusAlarmSequenceId, sonusAlarmTime, 
                      sonusAlarmDescription, sonusCpNifCeName, 
                      sonusCpNifType, sonusCpNifUsage }
--     STATUS          mandatory
    DESCRIPTION     
            "This trap indicates a fatal Parity Error."
    ::= 28

sonusCpNifPartitionErrorNotification TRAP-TYPE
    ENTERPRISE      sonusCpNifMIBNotifications
    VARIABLES       { sonusAlarmNodeID, sonusAlarmLevel, 
                      sonusAlarmSequenceId, sonusAlarmTime, 
                      sonusAlarmDescription, sonusCpNifCeName, 
                      sonusCpNifType, sonusCpNifUsage }
--     STATUS          mandatory
    DESCRIPTION     
            "This trap indicates a fatal Partition Error."
    ::= 29

sonusCpNifByteEnableBusErrorNotification TRAP-TYPE
    ENTERPRISE      sonusCpNifMIBNotifications
    VARIABLES       { sonusAlarmNodeID, sonusAlarmLevel, 
                      sonusAlarmSequenceId, sonusAlarmTime, 
                      sonusAlarmDescription, sonusCpNifCeName, 
                      sonusCpNifType, sonusCpNifUsage }
--     STATUS          mandatory
    DESCRIPTION     
            "This trap indicates a fatal Byte Enable Bus Error."
    ::= 30

sonusCpNifPageViolationErrorNotification TRAP-TYPE
    ENTERPRISE      sonusCpNifMIBNotifications
    VARIABLES       { sonusAlarmNodeID, sonusAlarmLevel, 
                      sonusAlarmSequenceId, sonusAlarmTime, 
                      sonusAlarmDescription, sonusCpNifCeName, 
                      sonusCpNifType, sonusCpNifUsage }
--     STATUS          mandatory
    DESCRIPTION     
            "This trap indicates a fatal Page Violation Error."
    ::= 31

sonusCpNifDataControlFifoErrorNotification TRAP-TYPE
    ENTERPRISE      sonusCpNifMIBNotifications
    VARIABLES       { sonusAlarmNodeID, sonusAlarmLevel, 
                      sonusAlarmSequenceId, sonusAlarmTime, 
                      sonusAlarmDescription, sonusCpNifCeName, 
                      sonusCpNifType, sonusCpNifUsage }
--     STATUS          mandatory
    DESCRIPTION     
            "This trap indicates a fatal Data or Control FIFO Error."
    ::= 32

sonusCpNifRcrShadowParityErrorNotification TRAP-TYPE
    ENTERPRISE      sonusCpNifMIBNotifications
    VARIABLES       { sonusAlarmNodeID, sonusAlarmLevel, 
                      sonusAlarmSequenceId, sonusAlarmTime, 
                      sonusAlarmDescription, sonusCpNifCeName, 
                      sonusCpNifType, sonusCpNifUsage }
--     STATUS          mandatory
    DESCRIPTION     
            "This trap indicates a fatal RCR Shadow Parity Error."
    ::= 33

sonusCpNifPrefetchParityErrorNotification TRAP-TYPE
    ENTERPRISE      sonusCpNifMIBNotifications
    VARIABLES       { sonusAlarmNodeID, sonusAlarmLevel, 
                      sonusAlarmSequenceId, sonusAlarmTime, 
                      sonusAlarmDescription, sonusCpNifCeName, 
                      sonusCpNifType, sonusCpNifUsage }
--     STATUS          mandatory
    DESCRIPTION     
            "This trap indicates a fatal Prefetch Parity Error."
    ::= 34

sonusCpNifRbrFullErrorNotification TRAP-TYPE
    ENTERPRISE      sonusCpNifMIBNotifications
    VARIABLES       { sonusAlarmNodeID, sonusAlarmLevel, 
                      sonusAlarmSequenceId, sonusAlarmTime, 
                      sonusAlarmDescription, sonusCpNifCeName, 
                      sonusCpNifType, sonusCpNifUsage }
--     STATUS          mandatory
    DESCRIPTION     
            "This trap indicates a fatal RBR Full Error."
    ::= 35

sonusCpNifRbrLogicalPageErrorNotification TRAP-TYPE
    ENTERPRISE      sonusCpNifMIBNotifications
    VARIABLES       { sonusAlarmNodeID, sonusAlarmLevel, 
                      sonusAlarmSequenceId, sonusAlarmTime, 
                      sonusAlarmDescription, sonusCpNifCeName, 
                      sonusCpNifType, sonusCpNifUsage }
--     STATUS          mandatory
    DESCRIPTION     
            "This trap indicates a fatal RBR Logical Page Error."
    ::= 36

sonusCpNifRbrTimeoutNotification TRAP-TYPE
    ENTERPRISE      sonusCpNifMIBNotifications
    VARIABLES       { sonusAlarmNodeID, sonusAlarmLevel, 
                      sonusAlarmSequenceId, sonusAlarmTime, 
                      sonusAlarmDescription, sonusCpNifCeName, 
                      sonusCpNifType, sonusCpNifUsage }
--     STATUS          mandatory
    DESCRIPTION     
            "This trap indicates a fatal RBR Timeout."
    ::= 37

sonusCpNifRcrAckErrorNotification TRAP-TYPE
    ENTERPRISE      sonusCpNifMIBNotifications
    VARIABLES       { sonusAlarmNodeID, sonusAlarmLevel, 
                      sonusAlarmSequenceId, sonusAlarmTime, 
                      sonusAlarmDescription, sonusCpNifCeName, 
                      sonusCpNifType, sonusCpNifUsage }
--     STATUS          mandatory
    DESCRIPTION     
            "This trap indicates a fatal RCR Ack Error."
    ::= 38

sonusCpNifRcrInconsistencyErrorNotification TRAP-TYPE
    ENTERPRISE      sonusCpNifMIBNotifications
    VARIABLES       { sonusAlarmNodeID, sonusAlarmLevel, 
                      sonusAlarmSequenceId, sonusAlarmTime, 
                      sonusAlarmDescription, sonusCpNifCeName, 
                      sonusCpNifType, sonusCpNifUsage }
--     STATUS          mandatory
    DESCRIPTION     
            "This trap indicates a fatal RCR Inconsistancy Error."
    ::= 39

sonusCpNifRcrRingFullErrorNotification TRAP-TYPE
    ENTERPRISE      sonusCpNifMIBNotifications
    VARIABLES       { sonusAlarmNodeID, sonusAlarmLevel, 
                      sonusAlarmSequenceId, sonusAlarmTime, 
                      sonusAlarmDescription, sonusCpNifCeName, 
                      sonusCpNifType, sonusCpNifUsage }
--     STATUS          mandatory
    DESCRIPTION     
            "This trap indicates a fatal RCR Ring Full Error."
    ::= 40

sonusCpNifResponseCountErrorNotification TRAP-TYPE
    ENTERPRISE      sonusCpNifMIBNotifications
    VARIABLES       { sonusAlarmNodeID, sonusAlarmLevel, 
                      sonusAlarmSequenceId, sonusAlarmTime, 
                      sonusAlarmDescription, sonusCpNifCeName, 
                      sonusCpNifType, sonusCpNifUsage }
--     STATUS          mandatory
    DESCRIPTION     
            "This trap indicates a fatal Response Count Error."
    ::= 41

sonusCpRadiusServerFailedNotification TRAP-TYPE
    ENTERPRISE      sonusCpRadiusAccountingMIBNotifications
    VARIABLES       { sonusAlarmNodeID, sonusAlarmLevel, 
                      sonusAlarmSequenceId, sonusAlarmTime, 
                      sonusAlarmDescription, sonusCpRadiusServerName }
--     STATUS          mandatory
    DESCRIPTION     
            "This trap indicates a radius accounting server has been marked failed."
    ::= 1

sonusCpRadiusServerPacketsFlushedNotification TRAP-TYPE
    ENTERPRISE      sonusCpRadiusAccountingMIBNotifications
    VARIABLES       { sonusAlarmNodeID, sonusAlarmLevel, 
                      sonusAlarmSequenceId, sonusAlarmTime, 
                      sonusAlarmDescription, sonusCpRadiusFlushedPackets, 
                      sonusCpRadiusFlushedPacketsFile }
--     STATUS          mandatory
    DESCRIPTION     
            "This trap indicates that radius packets have been flushed because a radius server is not available."
    ::= 2

sonusCpLicenseIntegrityViolationNotification TRAP-TYPE
    ENTERPRISE      sonusCpLicenseMIBNotifications
    VARIABLES       { sonusAlarmNodeID, sonusAlarmLevel, 
                      sonusAlarmSequenceId, sonusAlarmTime, 
                      sonusAlarmDescription, sonusCpLicenseId, 
                      sonusCpLicenseViolationDescString }
--     STATUS          mandatory
    DESCRIPTION     
            "This trap indicates any attempted violation of license integrity"
    ::= 1

sonusCpLicenseBundleExpireWarningNotification TRAP-TYPE
    ENTERPRISE      sonusCpLicenseMIBNotifications
    VARIABLES       { sonusAlarmNodeID, sonusAlarmLevel, 
                      sonusAlarmSequenceId, sonusAlarmTime, 
                      sonusAlarmDescription, sonusCpLicenseId, 
                      sonusCpLicenseFeatureName }
--     STATUS          mandatory
    DESCRIPTION     
            "This trap indicates that license budle will expire in 14 days"
    ::= 2

sonusCpLicenseBundleExpiredNotification TRAP-TYPE
    ENTERPRISE      sonusCpLicenseMIBNotifications
    VARIABLES       { sonusAlarmNodeID, sonusAlarmLevel, 
                      sonusAlarmSequenceId, sonusAlarmTime, 
                      sonusAlarmDescription, sonusCpLicenseId, 
                      sonusCpLicenseFeatureName }
--     STATUS          mandatory
    DESCRIPTION     
            "This trap indicates that license budle is expired"
    ::= 3

sonusCpLicenseBundleRenewedNotification TRAP-TYPE
    ENTERPRISE      sonusCpLicenseMIBNotifications
    VARIABLES       { sonusAlarmNodeID, sonusAlarmLevel, 
                      sonusAlarmSequenceId, sonusAlarmTime, 
                      sonusAlarmDescription, sonusCpLicenseId, 
                      sonusCpLicenseFeatureName }
--     STATUS          mandatory
    DESCRIPTION     
            "This trap indicates that license budle will is renewed"
    ::= 4

sonusCpLicenseHostSerialUnavailable TRAP-TYPE
    ENTERPRISE      sonusCpLicenseMIBNotifications
    VARIABLES       { sonusAlarmNodeID, sonusAlarmLevel, 
                      sonusAlarmSequenceId, sonusAlarmTime, 
                      sonusAlarmDescription, sonusCpSystemServerName }
--     STATUS          mandatory
    DESCRIPTION     
            "This trap indicates that the host serial number could not be read from the hardware"
    ::= 5

sonusCpLicenseSerialMismatch TRAP-TYPE
    ENTERPRISE      sonusCpLicenseMIBNotifications
    VARIABLES       { sonusAlarmNodeID, sonusAlarmLevel, 
                      sonusAlarmSequenceId, sonusAlarmTime, 
                      sonusAlarmDescription, sonusCpSystemServerName, 
                      sonusCpLicenseId }
--     STATUS          mandatory
    DESCRIPTION     
            "This trap indicates that the host serial number does not match that the serial number in the license"
    ::= 6

sonusCpLicensePeerSerialMismatch TRAP-TYPE
    ENTERPRISE      sonusCpLicenseMIBNotifications
    VARIABLES       { sonusAlarmNodeID, sonusAlarmLevel, 
                      sonusAlarmSequenceId, sonusAlarmTime, 
                      sonusAlarmDescription, sonusCpSystemServerName, 
                      sonusCpLicenseId }
--     STATUS          mandatory
    DESCRIPTION     
            "This trap indicates that the peer host serial number does not match that the serial number in the license"
    ::= 7

sonusCpConfiguredExceedSystemLimit TRAP-TYPE
    ENTERPRISE      sonusCpLicenseMIBNotifications
    VARIABLES       { sonusAlarmNodeID, sonusAlarmLevel, 
                      sonusAlarmSequenceId, sonusAlarmTime, 
                      sonusAlarmDescription, sonusSessConfigLicenses, 
                      sonusSessSystemLimit }
--     STATUS          mandatory
    DESCRIPTION     
            "This trap indicates that configured licensed sessions are more than system limit"
    ::= 8

sonusCpLicenseAcquireFailed TRAP-TYPE
    ENTERPRISE      sonusCpLicenseMIBNotifications
    VARIABLES       { sonusAlarmNodeID, sonusAlarmLevel, 
                      sonusAlarmSequenceId, sonusAlarmTime, 
                      sonusAlarmDescription, sonusCpSystemServerName, 
                      sonusCpLicenseFeatureName, 
                      sonusCpLicenseServerName, sonusCpCountRequested, 
                      sonusCpCountAcquired, sonusCpLicenseErrorReason }
--     STATUS          mandatory
    DESCRIPTION     
            "This trap indicates that the requested number of licenses could be acquired"
    ::= 9

sonusCpLicenseAcquireSucceeded TRAP-TYPE
    ENTERPRISE      sonusCpLicenseMIBNotifications
    VARIABLES       { sonusAlarmNodeID, sonusAlarmLevel, 
                      sonusAlarmSequenceId, sonusAlarmTime, 
                      sonusAlarmDescription, sonusCpSystemServerName, 
                      sonusCpLicenseFeatureName, sonusCpCountAcquired }
--     STATUS          mandatory
    DESCRIPTION     
            "This trap indicates that the requested number of licenses were successfully acquired"
    ::= 10

sonusCpLicenseReleased TRAP-TYPE
    ENTERPRISE      sonusCpLicenseMIBNotifications
    VARIABLES       { sonusAlarmNodeID, sonusAlarmLevel, 
                      sonusAlarmSequenceId, sonusAlarmTime, 
                      sonusAlarmDescription, sonusCpSystemServerName, 
                      sonusCpLicenseFeatureName, sonusCpCountReleased, 
                      sonusCpCountRemaining }
--     STATUS          mandatory
    DESCRIPTION     
            "This trap indicates that the requested number of licenses were released"
    ::= 11

sonusCpLicenseRefreshFailure TRAP-TYPE
    ENTERPRISE      sonusCpLicenseMIBNotifications
    VARIABLES       { sonusAlarmNodeID, sonusAlarmLevel, 
                      sonusAlarmSequenceId, sonusAlarmTime, 
                      sonusAlarmDescription, sonusCpSystemServerName, 
                      sonusCpLicenseFeatureName, sonusCpCountReleased, 
                      sonusCpLicenseErrorReason }
--     STATUS          deprecated
    DESCRIPTION     
            "This trap indicates that the requested number of licenses were released because they could not be refreshed"
    ::= 12

sonusCpLicenseServerError TRAP-TYPE
    ENTERPRISE      sonusCpLicenseMIBNotifications
    VARIABLES       { sonusAlarmNodeID, sonusAlarmLevel, 
                      sonusAlarmSequenceId, sonusAlarmTime, 
                      sonusAlarmDescription, sonusCpSystemServerName, 
                      sonusCpLicenseServerName, 
                      sonusCpLicenseServerAddress, 
                      sonusCpLicenseErrorReason }
--     STATUS          deprecated
    DESCRIPTION     
            "This trap indicates that a request to the given license server failed"
    ::= 13

sonusCpLicenseServerErrorCleared TRAP-TYPE
    ENTERPRISE      sonusCpLicenseMIBNotifications
    VARIABLES       { sonusAlarmNodeID, sonusAlarmLevel, 
                      sonusAlarmSequenceId, sonusAlarmTime, 
                      sonusAlarmDescription, sonusCpSystemServerName, 
                      sonusCpLicenseServerName, 
                      sonusCpLicenseServerAddress }
--     STATUS          deprecated
    DESCRIPTION     
            "This trap indicates that a request to the given license server was successful"
    ::= 14

sonusCpLicenseExpireSoonWarningNotification TRAP-TYPE
    ENTERPRISE      sonusCpLicenseMIBNotifications
    VARIABLES       { sonusAlarmNodeID, sonusAlarmLevel, 
                      sonusAlarmSequenceId, sonusAlarmTime, 
                      sonusAlarmDescription, sonusCpLicenseFeatureName }
--     STATUS          mandatory
    DESCRIPTION     
            "This trap indicates that this feature will expire in 90, 60 or 30 days."
    ::= 15

sonusCpLicenseExpireWarningNotification TRAP-TYPE
    ENTERPRISE      sonusCpLicenseMIBNotifications
    VARIABLES       { sonusAlarmNodeID, sonusAlarmLevel, 
                      sonusAlarmSequenceId, sonusAlarmTime, 
                      sonusAlarmDescription, sonusCpLicenseFeatureName }
--     STATUS          mandatory
    DESCRIPTION     
            "This trap indicates that license budle will expire in 7 days, 1 day, 8 hours or 0 hours"
    ::= 16

sonusInvalidFingerPrintNotification TRAP-TYPE
    ENTERPRISE      sonusCpLicenseMIBNotifications
    VARIABLES       { sonusAlarmNodeID, sonusAlarmLevel, 
                      sonusAlarmSequenceId, sonusAlarmTime, 
                      sonusAlarmDescription, sonusCpLicenseId, 
                      sonusCpLicenseViolationDescString }
--     STATUS          mandatory
    DESCRIPTION     
            "This trap indicates attempted to install license with invalid finger print"
    ::= 17

sonusCpLicenseFingerprintMismatch TRAP-TYPE
    ENTERPRISE      sonusCpLicenseMIBNotifications
    VARIABLES       { sonusAlarmNodeID, sonusAlarmLevel, 
                      sonusAlarmSequenceId, sonusAlarmTime, 
                      sonusAlarmDescription, sonusCpSystemServerName, 
                      sonusCpLicenseBundleName }
--     STATUS          mandatory
    DESCRIPTION     
            "This trap indicates that the none of the fingerprints contained in the bundle match the fingerprint of the current host"
    ::= 18

sonusCpLicenseBundleInvalidUsageCount TRAP-TYPE
    ENTERPRISE      sonusCpLicenseMIBNotifications
    VARIABLES       { sonusAlarmNodeID, sonusAlarmLevel, 
                      sonusAlarmSequenceId, sonusAlarmTime, 
                      sonusAlarmDescription, sonusCpLicenseId, 
                      sonusCpLicenseFeatureName }
--     STATUS          mandatory
    DESCRIPTION     
            "This trap indicates that the usage limit for a counted license has an invalid count of 0"
    ::= 19

sonusCpLicenseGraceExpired TRAP-TYPE
    ENTERPRISE      sonusCpLicenseMIBNotifications
    VARIABLES       { sonusAlarmNodeID, sonusAlarmLevel, 
                      sonusAlarmSequenceId, sonusAlarmTime, 
                      sonusAlarmDescription }
--     STATUS          mandatory
    DESCRIPTION     
            ""
    ::= 20

sonusCpLicenseGraceMode TRAP-TYPE
    ENTERPRISE      sonusCpLicenseMIBNotifications
    VARIABLES       { sonusAlarmNodeID, sonusAlarmLevel, 
                      sonusAlarmSequenceId, sonusAlarmTime, 
                      sonusAlarmDescription }
--     STATUS          mandatory
    DESCRIPTION     
            "The provisioned servers are not reachable so licenses have trasitioned to grace mode."
    ::= 21

sonusCpLicenseGraceModeCleared TRAP-TYPE
    ENTERPRISE      sonusCpLicenseMIBNotifications
    VARIABLES       { sonusAlarmNodeID, sonusAlarmLevel, 
                      sonusAlarmSequenceId, sonusAlarmTime, 
                      sonusAlarmDescription, sonusCpLicenseServerName, 
                      sonusCpLicenseServerAddress }
--     STATUS          mandatory
    DESCRIPTION     
            "Provisioned License Server is rechanble,so grace mode is cleared"
    ::= 22

sonusCpLicenseServerUnreachable TRAP-TYPE
    ENTERPRISE      sonusCpLicenseMIBNotifications
    VARIABLES       { sonusAlarmNodeID, sonusAlarmLevel, 
                      sonusAlarmSequenceId, sonusAlarmTime, 
                      sonusAlarmDescription, sonusCpLicenseServerName, 
                      sonusCpLicenseServerAddress }
--     STATUS          mandatory
    DESCRIPTION     
            "The provisioned license server cannot be reached."
    ::= 23

sonusCpLicenseServerReachable TRAP-TYPE
    ENTERPRISE      sonusCpLicenseMIBNotifications
    VARIABLES       { sonusAlarmNodeID, sonusAlarmLevel, 
                      sonusAlarmSequenceId, sonusAlarmTime, 
                      sonusAlarmDescription, sonusCpLicenseServerName, 
                      sonusCpLicenseServerAddress }
--     STATUS          mandatory
    DESCRIPTION     
            "Provisioned License Server is reachanble."
    ::= 24

sonusCpLicenseGraceExpiring TRAP-TYPE
    ENTERPRISE      sonusCpLicenseMIBNotifications
    VARIABLES       { sonusAlarmNodeID, sonusAlarmLevel, 
                      sonusAlarmSequenceId, sonusAlarmTime, 
                      sonusAlarmDescription }
--     STATUS          mandatory
    DESCRIPTION     
            "This trap indicates that license budle will expire in 30/25/20/15/10 days.Then each day until 1 day.
             Then hourly until expiry."
    ::= 25

sonusCpLicenseServerNameResolutionError TRAP-TYPE
    ENTERPRISE      sonusCpLicenseMIBNotifications
    VARIABLES       { sonusAlarmNodeID, sonusAlarmLevel, 
                      sonusAlarmSequenceId, sonusAlarmTime, 
                      sonusAlarmDescription, sonusCpSystemServerName, 
                      sonusCpLicenseServerName, 
                      sonusCpLicenseServerAddress }
--     STATUS          mandatory
    DESCRIPTION     
            "This trap indicates that a the address specified in the serverName\
             field could not be resolved to an ip address"
    ::= 26

sonusCpLicenseFailsafeGraceMode TRAP-TYPE
    ENTERPRISE      sonusCpLicenseMIBNotifications
    VARIABLES       { sonusAlarmNodeID, sonusAlarmLevel, 
                      sonusAlarmSequenceId, sonusAlarmTime, 
                      sonusAlarmDescription }
--     STATUS          obsolete
    DESCRIPTION     
            "If the provisioned servers are sending error response, license trasitioned to fail safe grace mode."
    ::= 27

sonusCpLicenseFailsafeGraceModeCleared TRAP-TYPE
    ENTERPRISE      sonusCpLicenseMIBNotifications
    VARIABLES       { sonusAlarmNodeID, sonusAlarmLevel, 
                      sonusAlarmSequenceId, sonusAlarmTime, 
                      sonusAlarmDescription, sonusCpLicenseServerName, 
                      sonusCpLicenseServerAddress }
--     STATUS          obsolete
    DESCRIPTION     
            "Provisioned License Server is stopped sending error response,so fail safe grace mode is cleared"
    ::= 28

sonusCpLicenseFailsafeGraceExpiring TRAP-TYPE
    ENTERPRISE      sonusCpLicenseMIBNotifications
    VARIABLES       { sonusAlarmNodeID, sonusAlarmLevel, 
                      sonusAlarmSequenceId, sonusAlarmTime, 
                      sonusAlarmDescription }
--     STATUS          obsolete
    DESCRIPTION     
            "This trap indicates that license budle will expire in 30/25/20/15/10 days.Then each day until 1 day.
             Then hourly until expiry."
    ::= 29

sonusCpLicenseFailsafeGraceExpired TRAP-TYPE
    ENTERPRISE      sonusCpLicenseMIBNotifications
    VARIABLES       { sonusAlarmNodeID, sonusAlarmLevel, 
                      sonusAlarmSequenceId, sonusAlarmTime, 
                      sonusAlarmDescription }
--     STATUS          obsolete
    DESCRIPTION     
            ""
    ::= 30

sonusCpNiceRecLicenseExpireSoonWarningNotification TRAP-TYPE
    ENTERPRISE      sonusCpLicenseMIBNotifications
    VARIABLES       { sonusAlarmNodeID, sonusAlarmLevel, 
                      sonusAlarmSequenceId, sonusAlarmTime, 
                      sonusAlarmDescription }
--     STATUS          mandatory
    DESCRIPTION     
            "This trap indicates that this NiceRec feature will expire in 90, 60 or 30 days."
    ::= 31

sonusCpNiceRecLicenseExpireWarningNotification TRAP-TYPE
    ENTERPRISE      sonusCpLicenseMIBNotifications
    VARIABLES       { sonusAlarmNodeID, sonusAlarmLevel, 
                      sonusAlarmSequenceId, sonusAlarmTime, 
                      sonusAlarmDescription }
--     STATUS          mandatory
    DESCRIPTION     
            "This trap indicates that NiceRec license will expire in 7 days, 1 day, 8 hours or 0 hours"
    ::= 32

sonusCpCdrServerTransferFailNotification TRAP-TYPE
    ENTERPRISE      sonusCpCdrServerMIBNotifications
    VARIABLES       { sonusAlarmNodeID, sonusAlarmLevel, 
                      sonusAlarmSequenceId, sonusAlarmTime, 
                      sonusAlarmDescription, sonusCpCdrServerType, 
                      sonusCpCdrServerIpAddress }
--     STATUS          mandatory
    DESCRIPTION     
            "CDR transfer failure. This notification is flow controlled and
             will not occur more often than once every ten seconds."
    ::= 1

sonusCpCdrServerSwtichoverNotification TRAP-TYPE
    ENTERPRISE      sonusCpCdrServerMIBNotifications
    VARIABLES       { sonusAlarmNodeID, sonusAlarmLevel, 
                      sonusAlarmSequenceId, sonusAlarmTime, 
                      sonusAlarmDescription, sonusCpCdrServerType, 
                      sonusCpCdrServerIpAddress }
--     STATUS          obsolete
    DESCRIPTION     
            "CDR server is switching to alternate server. This notification is flow controlled
             and will not occur more often than once every ten seconds."
    ::= 2

sonusCpCdrServerNewXferPendingNotification TRAP-TYPE
    ENTERPRISE      sonusCpCdrServerMIBNotifications
    VARIABLES       { sonusAlarmNodeID, sonusAlarmLevel, 
                      sonusAlarmSequenceId, sonusAlarmTime, 
                      sonusAlarmDescription, sonusCpCdrServerType, 
                      sonusCpCdrServerIpAddress }
--     STATUS          mandatory
    DESCRIPTION     
            "CDR transfer added to pending queue"
    ::= 3

sonusCpCdrServerPendingQueueEmptiedNotification TRAP-TYPE
    ENTERPRISE      sonusCpCdrServerMIBNotifications
    VARIABLES       { sonusAlarmNodeID, sonusAlarmLevel, 
                      sonusAlarmSequenceId, sonusAlarmTime, 
                      sonusAlarmDescription, sonusCpCdrServerType, 
                      sonusCpCdrServerIpAddress }
--     STATUS          mandatory
    DESCRIPTION     
            "CDR server all pending transfers have completed"
    ::= 4

sonusCpCdrServerSwitchoverNotification TRAP-TYPE
    ENTERPRISE      sonusCpCdrServerMIBNotifications
    VARIABLES       { sonusAlarmNodeID, sonusAlarmLevel, 
                      sonusAlarmSequenceId, sonusAlarmTime, 
                      sonusAlarmDescription, sonusCpCdrServerType, 
                      sonusCpCdrServerIpAddress }
--     STATUS          mandatory
    DESCRIPTION     
            "CDR server is switching to alternate server. This notification is flow controlled
             and will not occur more often than once every ten seconds."
    ::= 5

sonusCpCdrServerTransferSucceededNotification TRAP-TYPE
    ENTERPRISE      sonusCpCdrServerMIBNotifications
    VARIABLES       { sonusAlarmNodeID, sonusAlarmLevel, 
                      sonusAlarmSequenceId, sonusAlarmTime, 
                      sonusAlarmDescription, sonusCpCdrServerType, 
                      sonusCpCdrServerIpAddress }
--     STATUS          mandatory
    DESCRIPTION     
            "CDR transfer succeeded."
    ::= 6

sonusCpVmInvalidLicenseNotification TRAP-TYPE
    ENTERPRISE      sonusCpVmMIBNotifications
    VARIABLES       { sonusAlarmNodeID, sonusAlarmLevel, 
                      sonusAlarmSequenceId, sonusAlarmTime, 
                      sonusAlarmDescription, sonusCpVmAppName, 
                      sonusCpVmInstalledConfiguration, 
                      sonusCpVmConfigLicense }
--     STATUS          deprecated
    DESCRIPTION     
            "The license for the virtual machine application is invalid."
    ::= 1

sonusCpVmMatchLicenseNotification TRAP-TYPE
    ENTERPRISE      sonusCpVmMIBNotifications
    VARIABLES       { sonusAlarmNodeID, sonusAlarmLevel, 
                      sonusAlarmSequenceId, sonusAlarmTime, 
                      sonusAlarmDescription, sonusCpVmAppName, 
                      sonusCpVmConfigLicense }
--     STATUS          deprecated
    DESCRIPTION     
            "The license for the virtual machine application is valid."
    ::= 2

sonusCpVmAppUpNotification TRAP-TYPE
    ENTERPRISE      sonusCpVmMIBNotifications
    VARIABLES       { sonusAlarmNodeID, sonusAlarmLevel, 
                      sonusAlarmSequenceId, sonusAlarmTime, 
                      sonusAlarmDescription, sonusCpVmAppName, 
                      sonusCpVmServerName }
--     STATUS          deprecated
    DESCRIPTION     
            "The virtual machine application is running."
    ::= 3

sonusCpVmAppDownNotification TRAP-TYPE
    ENTERPRISE      sonusCpVmMIBNotifications
    VARIABLES       { sonusAlarmNodeID, sonusAlarmLevel, 
                      sonusAlarmSequenceId, sonusAlarmTime, 
                      sonusAlarmDescription, sonusCpVmAppName, 
                      sonusCpVmServerName, sonusCpVmReason }
--     STATUS          deprecated
    DESCRIPTION     
            "The virtual machine application is not running."
    ::= 4

sonusCpVmUpgradeInitiatedNotification TRAP-TYPE
    ENTERPRISE      sonusCpVmMIBNotifications
    VARIABLES       { sonusAlarmNodeID, sonusAlarmLevel, 
                      sonusAlarmSequenceId, sonusAlarmTime, 
                      sonusAlarmDescription, sonusCpVmAppName, 
                      sonusCpVmServerName }
--     STATUS          deprecated
    DESCRIPTION     
            "This trap indicates that a VM software upgrade 
             has been initiated."
    ::= 5

sonusCpVmUpgradeTerminatedNotification TRAP-TYPE
    ENTERPRISE      sonusCpVmMIBNotifications
    VARIABLES       { sonusAlarmNodeID, sonusAlarmLevel, 
                      sonusAlarmSequenceId, sonusAlarmTime, 
                      sonusAlarmDescription, sonusCpVmAppName, 
                      sonusCpVmServerName, sonusCpVmReason }
--     STATUS          deprecated
    DESCRIPTION     
            "This trap indicates that a VM software upgrade has terminated 
             for the specified reason."
    ::= 6

sonusCpVmUpgradeSucceededNotification TRAP-TYPE
    ENTERPRISE      sonusCpVmMIBNotifications
    VARIABLES       { sonusAlarmNodeID, sonusAlarmLevel, 
                      sonusAlarmSequenceId, sonusAlarmTime, 
                      sonusAlarmDescription, sonusCpVmAppName, 
                      sonusCpVmServerName, sonusCpVmReason }
--     STATUS          deprecated
    DESCRIPTION     
            "This trap indicates that a VM software upgrade has succeeded
             for the specified reason."
    ::= 7

sonusCpVmUpgradeRevertNotification TRAP-TYPE
    ENTERPRISE      sonusCpVmMIBNotifications
    VARIABLES       { sonusAlarmNodeID, sonusAlarmLevel, 
                      sonusAlarmSequenceId, sonusAlarmTime, 
                      sonusAlarmDescription, sonusCpVmAppName }
--     STATUS          deprecated
    DESCRIPTION     
            "This trap indicates that a VM Software Upgrade
             is reverting to the previous release."
    ::= 8

sonusCpVmSyncCompletedNotification TRAP-TYPE
    ENTERPRISE      sonusCpVmMIBNotifications
    VARIABLES       { sonusAlarmNodeID, sonusAlarmLevel, 
                      sonusAlarmSequenceId, sonusAlarmTime, 
                      sonusAlarmDescription, sonusCpVmAppName, 
                      sonusCpVmId }
--     STATUS          deprecated
    DESCRIPTION     
            "The virtual machine application data sync is completed."
    ::= 9

sonusCpVmSyncInprogressNotification TRAP-TYPE
    ENTERPRISE      sonusCpVmMIBNotifications
    VARIABLES       { sonusAlarmNodeID, sonusAlarmLevel, 
                      sonusAlarmSequenceId, sonusAlarmTime, 
                      sonusAlarmDescription, sonusCpVmAppName, 
                      sonusCpVmId }
--     STATUS          deprecated
    DESCRIPTION     
            "The virtual machine application data sync is in progress."
    ::= 10

sonusCpVmRedundancyModeNotification TRAP-TYPE
    ENTERPRISE      sonusCpVmMIBNotifications
    VARIABLES       { sonusAlarmNodeID, sonusAlarmLevel, 
                      sonusAlarmSequenceId, sonusAlarmTime, 
                      sonusAlarmDescription, sonusCpVmAppName, 
                      sonusCpVmId, sonusCpVmRedundancyMode }
--     STATUS          mandatory
    DESCRIPTION     
            "This trap indicates a VM Redundancy Mode"
    ::= 11

sonusSshHostKeyZeroizedNotification TRAP-TYPE
    ENTERPRISE      sonusFipsMIBNotifications
    VARIABLES       { sonusAlarmNodeID, sonusAlarmLevel, 
                      sonusAlarmSequenceId, sonusAlarmTime, 
                      sonusAlarmDescription }
--     STATUS          mandatory
    DESCRIPTION     
            "This trap indicates SSH host keys are zeroized."
    ::= 1

sonusSshHostKeyRegeneratedNotification TRAP-TYPE
    ENTERPRISE      sonusFipsMIBNotifications
    VARIABLES       { sonusAlarmNodeID, sonusAlarmLevel, 
                      sonusAlarmSequenceId, sonusAlarmTime, 
                      sonusAlarmDescription }
--     STATUS          mandatory
    DESCRIPTION     
            "This trap indicates SSH host keys are regenerated."
    ::= 2

sonusCdbEncryptionKeyZeroizedNotification TRAP-TYPE
    ENTERPRISE      sonusFipsMIBNotifications
    VARIABLES       { sonusAlarmNodeID, sonusAlarmLevel, 
                      sonusAlarmSequenceId, sonusAlarmTime, 
                      sonusAlarmDescription }
--     STATUS          mandatory
    DESCRIPTION     
            "This trap indicates CDB encryption keys are zeroized."
    ::= 3

sonusCdbEncryptionKeyRegeneratedNotification TRAP-TYPE
    ENTERPRISE      sonusFipsMIBNotifications
    VARIABLES       { sonusAlarmNodeID, sonusAlarmLevel, 
                      sonusAlarmSequenceId, sonusAlarmTime, 
                      sonusAlarmDescription }
--     STATUS          mandatory
    DESCRIPTION     
            "This trap indicates CDB encryption keys are regenerated."
    ::= 4

sonusOpenSSLCRNGTestFailedNotification TRAP-TYPE
    ENTERPRISE      sonusFipsMIBNotifications
    VARIABLES       { sonusAlarmNodeID, sonusAlarmLevel, 
                      sonusAlarmSequenceId, sonusAlarmTime, 
                      sonusAlarmDescription, 
                      sonusFipsNotificationDetails }
--     STATUS          mandatory
    DESCRIPTION     
            "This trap indicates OpenSSL Continuous Random Number Generator Test has failed."
    ::= 5

sonusOpenSSLPairwiseConsistencyTestFailedNotification TRAP-TYPE
    ENTERPRISE      sonusFipsMIBNotifications
    VARIABLES       { sonusAlarmNodeID, sonusAlarmLevel, 
                      sonusAlarmSequenceId, sonusAlarmTime, 
                      sonusAlarmDescription, 
                      sonusFipsNotificationDetails }
--     STATUS          mandatory
    DESCRIPTION     
            "This trap indicates OpenSSL Pairwise Consistency Test has failed."
    ::= 6

sonusSoftwareLoadTestFailedNotification TRAP-TYPE
    ENTERPRISE      sonusFipsMIBNotifications
    VARIABLES       { sonusAlarmNodeID, sonusAlarmLevel, 
                      sonusAlarmSequenceId, sonusAlarmTime, 
                      sonusAlarmDescription, 
                      sonusFipsNotificationDetails }
--     STATUS          mandatory
    DESCRIPTION     
            "This trap indicates Package Integrity Test has failed."
    ::= 7

sonusSystemSecurityReportNotification TRAP-TYPE
    ENTERPRISE      sonusSystemSecurityMIBNotifications
    VARIABLES       { sonusAlarmNodeID, sonusAlarmLevel, 
                      sonusAlarmSequenceId, sonusAlarmTime, 
                      sonusAlarmDescription, 
                      sonusSystemSecurityNotificationDetails }
--     STATUS          mandatory
    DESCRIPTION     
            "This trap indicates major System Security events. "
    ::= 1

sonusSystemSecurityEthernetClearNotification TRAP-TYPE
    ENTERPRISE      sonusSystemSecurityMIBNotifications
    VARIABLES       { sonusAlarmNodeID, sonusAlarmLevel, 
                      sonusAlarmSequenceId, sonusAlarmTime, 
                      sonusAlarmDescription, sonusEthErrorType, 
                      sonusEthInterfaceType }
--     STATUS          mandatory
    DESCRIPTION     
            "This trap indicates that Ehternet Errors are below the threshold level"
    ::= 2

sonusSystemSecurityEthernetErrorNotification TRAP-TYPE
    ENTERPRISE      sonusSystemSecurityMIBNotifications
    VARIABLES       { sonusAlarmNodeID, sonusAlarmLevel, 
                      sonusAlarmSequenceId, sonusAlarmTime, 
                      sonusAlarmDescription, sonusEthErrorType, 
                      sonusEthInterfaceType }
--     STATUS          mandatory
    DESCRIPTION     
            "This trap indicates high error rate on ethernet ports. "
    ::= 3

sonusSystemSecurityMediaErrClearNotification TRAP-TYPE
    ENTERPRISE      sonusSystemSecurityMIBNotifications
    VARIABLES       { sonusAlarmNodeID, sonusAlarmLevel, 
                      sonusAlarmSequenceId, sonusAlarmTime, 
                      sonusAlarmDescription, sonusMediaErrType }
--     STATUS          mandatory
    DESCRIPTION     
            "This trap indicates that Media Errors are below the threshold level"
    ::= 4

sonusSystemSecurityMediaErrorNotification TRAP-TYPE
    ENTERPRISE      sonusSystemSecurityMIBNotifications
    VARIABLES       { sonusAlarmNodeID, sonusAlarmLevel, 
                      sonusAlarmSequenceId, sonusAlarmTime, 
                      sonusAlarmDescription, sonusMediaErrType }
--     STATUS          mandatory
    DESCRIPTION     
            "This trap indicates high error rate of NP Media Errors. "
    ::= 5

sonusSystemSecurityAccountDisabledNotification TRAP-TYPE
    ENTERPRISE      sonusSystemSecurityMIBNotifications
    VARIABLES       { sonusAlarmNodeID, sonusAlarmLevel, 
                      sonusAlarmSequenceId, sonusAlarmTime, 
                      sonusAlarmDescription, sonusUserName }
--     STATUS          mandatory
    DESCRIPTION     
            "This trap indicates that the account has been automatically disabled as it has not been used during the accountAgingPeriod. "
    ::= 6

sonusSystemSecurityAccountRemovedNotification TRAP-TYPE
    ENTERPRISE      sonusSystemSecurityMIBNotifications
    VARIABLES       { sonusAlarmNodeID, sonusAlarmLevel, 
                      sonusAlarmSequenceId, sonusAlarmTime, 
                      sonusAlarmDescription, sonusUserName }
--     STATUS          mandatory
    DESCRIPTION     
            "This trap indicates that the account has been automatically removed as it has not been used during the accountRemovalPeriod. "
    ::= 7

sonusSystemSecurityAccountCreatedNotification TRAP-TYPE
    ENTERPRISE      sonusSystemSecurityMIBNotifications
    VARIABLES       { sonusAlarmNodeID, sonusAlarmLevel, 
                      sonusAlarmSequenceId, sonusAlarmTime, 
                      sonusAlarmDescription, sonusUserName }
--     STATUS          mandatory
    DESCRIPTION     
            "This trap indicates that an account has been created. "
    ::= 8

sonusSystemSecurityAccountManuallyDeletedNotification TRAP-TYPE
    ENTERPRISE      sonusSystemSecurityMIBNotifications
    VARIABLES       { sonusAlarmNodeID, sonusAlarmLevel, 
                      sonusAlarmSequenceId, sonusAlarmTime, 
                      sonusAlarmDescription, sonusUserName }
--     STATUS          mandatory
    DESCRIPTION     
            "This trap indicates that an account has been manually deleted. "
    ::= 9

sonusSystemSecurityAccountNewGroupNotification TRAP-TYPE
    ENTERPRISE      sonusSystemSecurityMIBNotifications
    VARIABLES       { sonusAlarmNodeID, sonusAlarmLevel, 
                      sonusAlarmSequenceId, sonusAlarmTime, 
                      sonusAlarmDescription, sonusUserName, 
                      sonusGroupName }
--     STATUS          mandatory
    DESCRIPTION     
            "This trap indicates that an account has been assigned to a group. "
    ::= 10

sonusSystemSecurityAccountReEnabled TRAP-TYPE
    ENTERPRISE      sonusSystemSecurityMIBNotifications
    VARIABLES       { sonusAlarmNodeID, sonusAlarmLevel, 
                      sonusAlarmSequenceId, sonusAlarmTime, 
                      sonusAlarmDescription, sonusUserName }
--     STATUS          mandatory
    DESCRIPTION     
            "This trap indicates that an account has been enabled after being disabled. "
    ::= 11

sonusSystemSecurityOsAccountReEnabled TRAP-TYPE
    ENTERPRISE      sonusSystemSecurityMIBNotifications
    VARIABLES       { sonusAlarmNodeID, sonusAlarmLevel, 
                      sonusAlarmSequenceId, sonusAlarmTime, 
                      sonusAlarmDescription, sonusUserName }
--     STATUS          mandatory
    DESCRIPTION     
            "This trap indicates that an OS account has been enabled after being disabled. "
    ::= 12

sonusSystemSecurityAccountSshKeyChange TRAP-TYPE
    ENTERPRISE      sonusSystemSecurityMIBNotifications
    VARIABLES       { sonusAlarmNodeID, sonusAlarmLevel, 
                      sonusAlarmSequenceId, sonusAlarmTime, 
                      sonusAlarmDescription, sonusUserName }
--     STATUS          mandatory
    DESCRIPTION     
            "This trap indicates that there has been a change to the SSH keys for a user. "
    ::= 13

sonusSystemSecurityAccountConfigChange TRAP-TYPE
    ENTERPRISE      sonusSystemSecurityMIBNotifications
    VARIABLES       { sonusAlarmNodeID, sonusAlarmLevel, 
                      sonusAlarmSequenceId, sonusAlarmTime, 
                      sonusAlarmDescription, sonusUserName, 
                      sonusConfigChange }
--     STATUS          mandatory
    DESCRIPTION     
            "This trap indicates that an account has had its configuration changed. "
    ::= 14

sonusSystemSecurityAccountLocked TRAP-TYPE
    ENTERPRISE      sonusSystemSecurityMIBNotifications
    VARIABLES       { sonusAlarmNodeID, sonusAlarmLevel, 
                      sonusAlarmSequenceId, sonusAlarmTime, 
                      sonusAlarmDescription, sonusUserName, 
                      sonusUnlockType }
--     STATUS          mandatory
    DESCRIPTION     
            "This trap indicates that an account has been locked after a potential brute force attack. "
    ::= 15

sonusSystemSecurityOsAccountLocked TRAP-TYPE
    ENTERPRISE      sonusSystemSecurityMIBNotifications
    VARIABLES       { sonusAlarmNodeID, sonusAlarmLevel, 
                      sonusAlarmSequenceId, sonusAlarmTime, 
                      sonusAlarmDescription, sonusUserName, 
                      sonusUnlockType }
--     STATUS          mandatory
    DESCRIPTION     
            "This trap indicates that an OS account has been locked after a potential brute force attack. "
    ::= 16

sonusSystemSecurityLargeConsoleSessionLog TRAP-TYPE
    ENTERPRISE      sonusSystemSecurityMIBNotifications
    VARIABLES       { sonusAlarmNodeID, sonusAlarmLevel, 
                      sonusAlarmSequenceId, sonusAlarmTime, 
                      sonusAlarmDescription, sonusFileName, 
                      sonusUserName, sonusProcessId }
--     STATUS          mandatory
    DESCRIPTION     
            "This trap indicates that a Console Session Log file has reached at least 1GB in size."
    ::= 17

sonusSystemSecurityNewPrivateHashingKey TRAP-TYPE
    ENTERPRISE      sonusSystemSecurityMIBNotifications
    VARIABLES       { sonusAlarmNodeID, sonusAlarmLevel, 
                      sonusAlarmSequenceId, sonusAlarmTime, 
                      sonusAlarmDescription, sonusKeyName }
--     STATUS          mandatory
    DESCRIPTION     
            "This trap indicates that a new key will now be used to hash the event log files when they are rolled. "
    ::= 18

sonusSystemSecurityAccountAutoReEnabled TRAP-TYPE
    ENTERPRISE      sonusSystemSecurityMIBNotifications
    VARIABLES       { sonusAlarmNodeID, sonusAlarmLevel, 
                      sonusAlarmSequenceId, sonusAlarmTime, 
                      sonusAlarmDescription, sonusUserName }
--     STATUS          mandatory
    DESCRIPTION     
            "This trap indicates that an account has been auto re-enabled after being disabled due to bad passwords. "
    ::= 19

sonusSystemSecurityOsAccountAutoReEnabled TRAP-TYPE
    ENTERPRISE      sonusSystemSecurityMIBNotifications
    VARIABLES       { sonusAlarmNodeID, sonusAlarmLevel, 
                      sonusAlarmSequenceId, sonusAlarmTime, 
                      sonusAlarmDescription, sonusUserName, 
                      sonusSystemServerName }
--     STATUS          mandatory
    DESCRIPTION     
            "This trap indicates that an OS account has been auto re-enabled after being disabled due to bad passwords. "
    ::= 20

sonusSbxCertificateExpireSoonWarningNotification TRAP-TYPE
    ENTERPRISE      sonusSystemSecurityMIBNotifications
    VARIABLES       { sonusAlarmNodeID, sonusAlarmLevel, 
                      sonusAlarmSequenceId, sonusAlarmTime, 
                      sonusAlarmDescription, sonusSecurityCertName, 
                      sonusSecurityCertExpiryDaysLeft }
--     STATUS          mandatory
    DESCRIPTION     
            "This trap indicates that certificate mentioned will expire in the specified number of days"
    ::= 21

sonusCpDataAgentConnectedNotification TRAP-TYPE
    ENTERPRISE      sonusCpSystemDataAgentMIBNotifications
    VARIABLES       { sonusAlarmNodeID, sonusAlarmLevel, 
                      sonusAlarmSequenceId, sonusAlarmTime, 
                      sonusAlarmDescription, sonusCpSystemServerName, 
                      sonusCpDataAgentInstance, sonusCpDataNode }
--     STATUS          mandatory
    DESCRIPTION     
            "This trap indicates that the data agent made a new connection to the data node."
    ::= 1

sonusCpDataAgentDisconnectedNotification TRAP-TYPE
    ENTERPRISE      sonusCpSystemDataAgentMIBNotifications
    VARIABLES       { sonusAlarmNodeID, sonusAlarmLevel, 
                      sonusAlarmSequenceId, sonusAlarmTime, 
                      sonusAlarmDescription, sonusCpSystemServerName, 
                      sonusCpDataAgentInstance, sonusCpDataNode }
--     STATUS          mandatory
    DESCRIPTION     
            "This trap indicates that the data agent was unable to connect to the data node."
    ::= 2

sonusCpDataAgentAddStreamNotification TRAP-TYPE
    ENTERPRISE      sonusCpSystemDataAgentMIBNotifications
    VARIABLES       { sonusAlarmNodeID, sonusAlarmLevel, 
                      sonusAlarmSequenceId, sonusAlarmTime, 
                      sonusAlarmDescription, sonusCpSystemServerName, 
                      sonusCpDataAgentStream }
--     STATUS          mandatory
    DESCRIPTION     
            "This trap indicates that the data agent added a new stream"
    ::= 3

sonusCpDataAgentRemoveStreamNotification TRAP-TYPE
    ENTERPRISE      sonusCpSystemDataAgentMIBNotifications
    VARIABLES       { sonusAlarmNodeID, sonusAlarmLevel, 
                      sonusAlarmSequenceId, sonusAlarmTime, 
                      sonusAlarmDescription, sonusCpSystemServerName, 
                      sonusCpDataAgentStream }
--     STATUS          mandatory
    DESCRIPTION     
            "This trap indicates that the data agent removed a stream"
    ::= 4

sonusCpDataAgentStartNotification TRAP-TYPE
    ENTERPRISE      sonusCpSystemDataAgentMIBNotifications
    VARIABLES       { sonusAlarmNodeID, sonusAlarmLevel, 
                      sonusAlarmSequenceId, sonusAlarmTime, 
                      sonusAlarmDescription, sonusCpSystemServerName }
--     STATUS          mandatory
    DESCRIPTION     
            "This trap indicates that the data agent has started running"
    ::= 5

sonusCpDataAgentStopNotification TRAP-TYPE
    ENTERPRISE      sonusCpSystemDataAgentMIBNotifications
    VARIABLES       { sonusAlarmNodeID, sonusAlarmLevel, 
                      sonusAlarmSequenceId, sonusAlarmTime, 
                      sonusAlarmDescription, sonusCpSystemServerName }
--     STATUS          mandatory
    DESCRIPTION     
            "This trap indicates that the data agent was stopped gracefully."
    ::= 6

sonusSWeNewTrafficProfileCommitNotfication TRAP-TYPE
    ENTERPRISE      sonusSWeNewTrafficCommitNotifications
    VARIABLES       { sonusAlarmNodeID, sonusAlarmLevel, 
                      sonusAlarmSequenceId, sonusAlarmTime, 
                      sonusAlarmDescription, 
                      sonusSWeNewTrafficProfileDetails }
--     STATUS          deprecated
    DESCRIPTION     
            "This trap indicates about new SWe Traffic Profile Commit. "
    ::= 1

sonusSWeCreatNewProfileCapcityEstDiffers TRAP-TYPE
    ENTERPRISE      sonusSWeNewTrafficCommitNotifications
    VARIABLES       { sonusAlarmNodeID, sonusAlarmLevel, 
                      sonusAlarmSequenceId, sonusAlarmTime, 
                      sonusAlarmDescription, 
                      sonusSWeCapacityEstimationDetails }
--     STATUS          deprecated
    DESCRIPTION     
            "This trap indicates about Capacity Estimate Difference are more than 10% in sweCapacityEstimate, with the new base file. "
    ::= 2

sonusSWeVcpuAllocationDiffers TRAP-TYPE
    ENTERPRISE      sonusSWeNewTrafficCommitNotifications
    VARIABLES       { sonusAlarmNodeID, sonusAlarmLevel, 
                      sonusAlarmSequenceId, sonusAlarmTime, 
                      sonusAlarmDescription, 
                      sonusSWeVcpuAllocationDetails }
--     STATUS          deprecated
    DESCRIPTION     
            "This trap indicates about Capacity Estimate Difference are more than 10% in sweVcpuAllocation, with the new base file. "
    ::= 3

sonusSWeNewActiveProfileCommitNotification TRAP-TYPE
    ENTERPRISE      sonusSWeActiveProfileMIBNotifications
    VARIABLES       { sonusAlarmNodeID, sonusAlarmLevel, 
                      sonusAlarmSequenceId, sonusAlarmTime, 
                      sonusAlarmDescription, sonusCpSystemAdminName, 
                      sonusCpSystemServerName }
--     STATUS          mandatory
    DESCRIPTION     
            "This trap indicates that a new traffic profile is activated after reboot."
    ::= 1

sonusCpSystemFaultAvalancheControlPacketDroppedNotify TRAP-TYPE
    ENTERPRISE      sonusFacPacketDroppedMIBNotifications
    VARIABLES       { sonusAlarmNodeID, sonusAlarmLevel, 
                      sonusAlarmSequenceId, sonusAlarmTime, 
                      sonusAlarmDescription, sonusFacKeyElementName, 
                      sonusFacKeyValueName, sonusCalledParty }
--     STATUS          mandatory
    DESCRIPTION     
            "This trap indicates that a first packet is dropped due to matching entries in blocking entries of Fault Avalanche Detection and Control Feature."
    ::= 1

sonusIPv6DuplicateManualReviewNoRebootNotification TRAP-TYPE
    ENTERPRISE      sonusDuplicateIpv6MIBNotifications
    VARIABLES       { sonusAlarmNodeID, sonusAlarmLevel, 
                      sonusAlarmSequenceId, sonusAlarmTime, 
                      sonusAlarmDescription, sonusDuplicateIpv6Address }
--     STATUS          mandatory
    DESCRIPTION     
            "On bringing down the HA port on active, the standby role will set to active. On the new active node, some IPV6 pkt port contains the error 'tentative dadfailed' . On detection of 'tentative dadfailed' , check the configurations/logs and take the action accordingly"
    ::= 1

sonusIPv6DuplicateManualReviewRebootingNotification TRAP-TYPE
    ENTERPRISE      sonusDuplicateIpv6MIBNotifications
    VARIABLES       { sonusAlarmNodeID, sonusAlarmLevel, 
                      sonusAlarmSequenceId, sonusAlarmTime, 
                      sonusAlarmDescription }
--     STATUS          mandatory
    DESCRIPTION     
            "On bringing down the HA port on active, the standby role will set to active. On the new active node, all IPV6 pkt port contains the error 'tentative dadfailed' . On detection of 'tentative dadfailed' on all ports, node will be rebooted."
    ::= 2

END -- end of module HORNET-BASE-TRAPS-MIB.
