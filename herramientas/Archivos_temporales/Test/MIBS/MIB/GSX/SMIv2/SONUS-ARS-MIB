--
-- This SMIv2 module has been generated by smidump 0.2-cvs. Do not edit.
--

SONUS-ARS-MIB DEFINITIONS ::= BEGIN

IMPORTS
    Ipv6Address
        FROM IPV6-TC
    Counter32, Integer32, IpAddress, MODULE-IDENTITY, NOTIFICATION-TYPE, 
    OBJECT-TYPE, Unsigned32
        FROM SNMPv2-SMI
    DateAndTime, DisplayString, RowStatus
        FROM SNMPv2-TC
    sonusEventClass, sonusEventDescription, sonusEventLevel, 
    sonusEventTime, sonusSequenceId
        FROM SONUS-COMMON-MIB
    sonusSignallingMIBs
        FROM SONUS-SMI
    SonusAdminState, SonusName, SonusShelfIndex, SonusSlotIndex
        FROM SONUS-TC;

sonusArsSignallingMIB MODULE-IDENTITY
    LAST-UPDATED    "201607200000Z"
    ORGANIZATION    
            "Sonus Networks, Inc."
    CONTACT-INFO    
            "   Customer Support    
             Sonus Networks, Inc.
             7 Technology Park Drive
             Westford, MA 01886
             USA
             
             Tel: 978-614-8100
             Fax: 978-614-8609
             E-mail: cs.snmp@sonusnet.com"
    DESCRIPTION     
            "The MIB Module for Local Host Name Service."
    ::= { sonusSignallingMIBs 14 }


sonusArsSignallingMIBObjects OBJECT IDENTIFIER
    ::= { sonusArsSignallingMIB 1 }

sonusArsProfile OBJECT IDENTIFIER
    ::= { sonusArsSignallingMIBObjects 1 }

sonusArsProfileNextIndex OBJECT-TYPE
    SYNTAX          Unsigned32
    MAX-ACCESS      not-accessible
    STATUS          current
    DESCRIPTION     
            "The next valid index to use when creating a new sonusArsProfileEntry"
    ::= { sonusArsProfile 1 }

sonusArsProfileTable OBJECT-TYPE
    SYNTAX          SEQUENCE OF SonusArsProfileEntry
    MAX-ACCESS      not-accessible
    STATUS          current
    DESCRIPTION     
            "This table contains information about each Address
             Reachability Service Profile configured on the node."
    ::= { sonusArsProfile 2 }

sonusArsProfileEntry OBJECT-TYPE
    SYNTAX          SonusArsProfileEntry
    MAX-ACCESS      not-accessible
    STATUS          current
    DESCRIPTION     
            "This table describes the Address Reachability Service Profile."
    INDEX           { sonusArsProfIndex }
    ::= { sonusArsProfileTable 1 }

SonusArsProfileEntry ::=
    SEQUENCE {
        sonusArsProfIndex               Unsigned32,
        sonusArsProfName                SonusName,
        sonusArsProfRowStatus           RowStatus,
        sonusArsProfAdminState          SonusAdminState,
        sonusArsProfBlkListAlgTimeoutsType  INTEGER,
        sonusArsProfBlkListAlgTimeoutsNumTimeouts         Unsigned32,
        sonusArsProfBlkListAlgTimeoutsDuration      Unsigned32,
        sonusArsProfRecAlg              INTEGER,
        sonusArsProfRecAlgTimerDuration Unsigned32,
        sonusArsProfRecAlgProbeMethod   INTEGER,
        sonusArsProfRecAlgProbeInterval Unsigned32,
        sonusArsProfRecAlgProbeNumResponses   Unsigned32,
        sonusArsProfRecAlgProbeDuration Unsigned32,
        sonusArsProfBlkListAlgorithms   BITS,
        sonusArsProfBlkListAlgRetryAfterType    BITS
    }

sonusArsProfIndex OBJECT-TYPE
    SYNTAX          Unsigned32
    MAX-ACCESS      not-accessible
    STATUS          current
    DESCRIPTION     
            "The index of the SIP Address Reachability Service table entry."
    ::= { sonusArsProfileEntry 1 }

sonusArsProfName OBJECT-TYPE
    SYNTAX          SonusName
    MAX-ACCESS      read-write
    STATUS          current
    DESCRIPTION     
            "The name of this SIP Address Reachability Service Profile."
    ::= { sonusArsProfileEntry 2 }

sonusArsProfRowStatus OBJECT-TYPE
    SYNTAX          RowStatus
    MAX-ACCESS      read-write
    STATUS          current
    DESCRIPTION     
            ""
    ::= { sonusArsProfileEntry 3 }

sonusArsProfAdminState OBJECT-TYPE
    SYNTAX          SonusAdminState
    MAX-ACCESS      read-write
    STATUS          current
    DESCRIPTION     
            "The admin state of this SIP Address Reachability Profile.
             Some fields cannot be changed until the state is disabled
             while others can be changed. In the former case, the change
             will be effective once the state is set to enabled."
    DEFVAL          { disabled }
    ::= { sonusArsProfileEntry 4 }

sonusArsProfBlkListAlgTimeoutsType OBJECT-TYPE
    SYNTAX          INTEGER { sip-invite(1), setup(2) }
    MAX-ACCESS      read-write
    STATUS          current
    DESCRIPTION     
            "This specifies the timeout trigger."
    DEFVAL          { sip-invite }
    ::= { sonusArsProfileEntry 5 }

sonusArsProfBlkListAlgTimeoutsNumTimeouts OBJECT-TYPE
    SYNTAX          Unsigned32 (1..3600)
    MAX-ACCESS      read-write
    STATUS          current
    DESCRIPTION     
            "This field specifies the number of timeout events should
             occur before blacking listing the address."
    DEFVAL          { 1 }
    ::= { sonusArsProfileEntry 6 }

sonusArsProfBlkListAlgTimeoutsDuration OBJECT-TYPE
    SYNTAX          Unsigned32 (1..3600)
    MAX-ACCESS      read-write
    STATUS          current
    DESCRIPTION     
            "This field specifies the duration in seconds, in which the
             specified number of timeouts should occur."
    DEFVAL          { 1 }
    ::= { sonusArsProfileEntry 7 }

sonusArsProfRecAlg OBJECT-TYPE
    SYNTAX          INTEGER { probe(1), timer(2) }
    MAX-ACCESS      read-write
    STATUS          current
    DESCRIPTION     
            "This field specifies the recovery algorithm."
    DEFVAL          { probe }
    ::= { sonusArsProfileEntry 8 }

sonusArsProfRecAlgTimerDuration OBJECT-TYPE
    SYNTAX          Unsigned32 (1..3600)
    MAX-ACCESS      read-write
    STATUS          current
    DESCRIPTION     
            "This field specifies the duration in seconds, for which
             the IP address will remain black listed."
    DEFVAL          { 1 }
    ::= { sonusArsProfileEntry 9 }

sonusArsProfRecAlgProbeMethod OBJECT-TYPE
    SYNTAX          INTEGER { sip-options(1), tcp-connect(2) }
    MAX-ACCESS      read-write
    STATUS          current
    DESCRIPTION     
            "This field pecifies the probe method."
    DEFVAL          { sip-options }
    ::= { sonusArsProfileEntry 10 }

sonusArsProfRecAlgProbeInterval OBJECT-TYPE
    SYNTAX          Unsigned32 (1..600)
    MAX-ACCESS      read-write
    STATUS          current
    DESCRIPTION     
            "This field specifies the probe interval."
    DEFVAL          { 1 }
    ::= { sonusArsProfileEntry 11 }

sonusArsProfRecAlgProbeNumResponses OBJECT-TYPE
    SYNTAX          Unsigned32 (1..32)
    MAX-ACCESS      read-write
    STATUS          current
    DESCRIPTION     
            "This field specifies the number of responses should occur
             before removing the entry from the black list."
    DEFVAL          { 1 }
    ::= { sonusArsProfileEntry 12 }

sonusArsProfRecAlgProbeDuration OBJECT-TYPE
    SYNTAX          Unsigned32 (1..3600)
    MAX-ACCESS      read-write
    STATUS          current
    DESCRIPTION     
            "This field specifies the duration in seconds, in which the
             specified number of responses should occur."
    DEFVAL          { 1 }
    ::= { sonusArsProfileEntry 13 }

sonusArsProfBlkListAlgorithms OBJECT-TYPE
    SYNTAX          BITS { timeouts(0), retryafter(1) }
    MAX-ACCESS      read-write
    STATUS          current
    DESCRIPTION     
            "The blacklisting algorithms of this Address Reachability Service
             Profile. Currently, can support timeouts and retryafter algorithms
             or both of them.
             bit 0 -- indicate timeouts algorithm
             bit 1 -- indicate retryafter algorithm
             ...
             "
    DEFVAL          { 128 }
    ::= { sonusArsProfileEntry 14 }

sonusArsProfBlkListAlgRetryAfterType OBJECT-TYPE
    SYNTAX          BITS { sip-503(0) }
    MAX-ACCESS      read-write
    STATUS          current
    DESCRIPTION     
            "This specifies the sip status code which has a Retry After value.
             503 Retry After is the only event supported in this release.
             bit 0 -- indicate sip 503
             ...
             "
    DEFVAL          { 128 }
    ::= { sonusArsProfileEntry 15 }

sonusArsStatusTable OBJECT-TYPE
    SYNTAX          SEQUENCE OF SonusArsStatusEntry
    MAX-ACCESS      not-accessible
    STATUS          current
    DESCRIPTION     
            "Table of Address Reachability Service status."
    ::= { sonusArsSignallingMIBObjects 2 }

sonusArsStatusEntry OBJECT-TYPE
    SYNTAX          SonusArsStatusEntry
    MAX-ACCESS      not-accessible
    STATUS          current
    DESCRIPTION     
            "Address Reachability Service Status."
    INDEX           { sonusArsStatShelfIndex, sonusArsStatSlotIndex, 
                      sonusArsStatAgentId, sonusArsStatSigZoneId, 
                      sonusArsStatRecordIndex }
    ::= { sonusArsStatusTable 1 }

SonusArsStatusEntry ::=
    SEQUENCE {
        sonusArsStatShelfIndex          SonusShelfIndex,
        sonusArsStatSlotIndex           SonusSlotIndex,
        sonusArsStatSigZoneId           Unsigned32,
        sonusArsStatRecordIndex         Unsigned32,
        sonusArsStatSigPortNum          Unsigned32,
        sonusArsStatEndpointIpAddress   IpAddress,
        sonusArsStatEndpointIpPortNum   Unsigned32,
        sonusArsStatEndpointArsState    INTEGER,
        sonusArsStatEndpointStateTransitionTime       DateAndTime,
        sonusArsStatEndpointOwnerId     Unsigned32,
        sonusArsStatAgentId             INTEGER,
        sonusArsStatEndpointIpv6Address Ipv6Address
    }

sonusArsStatShelfIndex OBJECT-TYPE
    SYNTAX          SonusShelfIndex
    MAX-ACCESS      read-only
    STATUS          current
    DESCRIPTION     
            "The shelf of the card where address reachability service status is
             being shown."
    ::= { sonusArsStatusEntry 1 }

sonusArsStatSlotIndex OBJECT-TYPE
    SYNTAX          SonusSlotIndex
    MAX-ACCESS      read-only
    STATUS          current
    DESCRIPTION     
            "The card slot where address reachability service status is being shown."
    ::= { sonusArsStatusEntry 2 }

sonusArsStatSigZoneId OBJECT-TYPE
    SYNTAX          Unsigned32
    MAX-ACCESS      read-only
    STATUS          current
    DESCRIPTION     
            "The Id of the Signaling Zone where address reachability service status
             is being shown."
    ::= { sonusArsStatusEntry 3 }

sonusArsStatRecordIndex OBJECT-TYPE
    SYNTAX          Unsigned32
    MAX-ACCESS      read-only
    STATUS          current
    DESCRIPTION     
            "The internal table index of the address reachability service table."
    ::= { sonusArsStatusEntry 4 }

sonusArsStatSigPortNum OBJECT-TYPE
    SYNTAX          Unsigned32
    MAX-ACCESS      read-only
    STATUS          current
    DESCRIPTION     
            "A signaling port in the signaling zone showing status."
    ::= { sonusArsStatusEntry 5 }

sonusArsStatEndpointIpAddress OBJECT-TYPE
    SYNTAX          IpAddress
    MAX-ACCESS      read-only
    STATUS          current
    DESCRIPTION     
            "Blacklisted endpoint's IP Address."
    ::= { sonusArsStatusEntry 6 }

sonusArsStatEndpointIpPortNum OBJECT-TYPE
    SYNTAX          Unsigned32 (1..65535)
    MAX-ACCESS      read-only
    STATUS          current
    DESCRIPTION     
            "Blacklisted endpoint's UDP port number."
    ::= { sonusArsStatusEntry 7 }

sonusArsStatEndpointArsState OBJECT-TYPE
    SYNTAX          INTEGER { idle(0), monitoring(1), blacklisted(2), 
                        recovering(3), distrib-blklist(4), 
                        distrib-recovery(5) }
    MAX-ACCESS      read-only
    STATUS          current
    DESCRIPTION     
            "Endpoint's address reachability service state."
    ::= { sonusArsStatusEntry 8 }

sonusArsStatEndpointStateTransitionTime OBJECT-TYPE
    SYNTAX          DateAndTime
    MAX-ACCESS      read-only
    STATUS          current
    DESCRIPTION     
            "Octet string that identifies the date and GMT time at which the
             endpoint's ARS state transitioned."
    ::= { sonusArsStatusEntry 9 }

sonusArsStatEndpointOwnerId OBJECT-TYPE
    SYNTAX          Unsigned32 (1..65535)
    MAX-ACCESS      read-only
    STATUS          current
    DESCRIPTION     
            "Blacklisted endpoints owner id. This is identifies the slot that originally  blacklisted the endpoint."
    ::= { sonusArsStatusEntry 10 }

sonusArsStatAgentId OBJECT-TYPE
    SYNTAX          INTEGER { sip(0), h323(1) }
    MAX-ACCESS      read-only
    STATUS          current
    DESCRIPTION     
            "This identifies the agent task within a slot that use the ARS instance."
    ::= { sonusArsStatusEntry 11 }

sonusArsStatEndpointIpv6Address OBJECT-TYPE
    SYNTAX          Ipv6Address
    MAX-ACCESS      read-only
    STATUS          current
    DESCRIPTION     
            "Blacklisted endpoint's IPv6 Address."
    ::= { sonusArsStatusEntry 12 }

sonusArsEndpointRecoveryConfigObjects OBJECT IDENTIFIER
    ::= { sonusArsSignallingMIBObjects 3 }

sonusArsEndpointRecoverySigZoneId OBJECT-TYPE
    SYNTAX          Unsigned32 (0..2048)
    MAX-ACCESS      read-write
    STATUS          current
    DESCRIPTION     
            "The ID of the signaling zone of which endpoint(s) are being recovered."
    DEFVAL          { 0 }
    ::= { sonusArsEndpointRecoveryConfigObjects 1 }

sonusArsEndpointRecoverySigPortNum OBJECT-TYPE
    SYNTAX          Unsigned32 (1..2048)
    MAX-ACCESS      read-write
    STATUS          current
    DESCRIPTION     
            "The signaling port number of which endpoint(s) are being recovered."
    DEFVAL          { 0 }
    ::= { sonusArsEndpointRecoveryConfigObjects 2 }

sonusArsEndpointRecoveryIpAddress OBJECT-TYPE
    SYNTAX          IpAddress
    MAX-ACCESS      read-write
    STATUS          current
    DESCRIPTION     
            "The IP address of the endpoint being recovered."
    ::= { sonusArsEndpointRecoveryConfigObjects 3 }

sonusArsEndpointRecoveryIpPortNum OBJECT-TYPE
    SYNTAX          Integer32 (1..65535)
    MAX-ACCESS      read-write
    STATUS          current
    DESCRIPTION     
            "The IP port number of the endpoint being recovered."
    DEFVAL          { 5060 }
    ::= { sonusArsEndpointRecoveryConfigObjects 4 }

sonusArsEndpointRecoveryAll OBJECT-TYPE
    SYNTAX          INTEGER { none(0), oneSigZone(1), allSigZone(2), 
                        allinOneSlot(3) }
    MAX-ACCESS      read-write
    STATUS          current
    DESCRIPTION     
            "The flag for recovering a group of endpoints: all endpoints in one signaling
             zone or all endpoints in all signaling zones."
    DEFVAL          { 0 }
    ::= { sonusArsEndpointRecoveryConfigObjects 5 }

sonusArsEndpointRecoveryAgentId OBJECT-TYPE
    SYNTAX          INTEGER { sip(0), h323(1) }
    MAX-ACCESS      read-write
    STATUS          current
    DESCRIPTION     
            "This identifies the agent task from endpoints to be recovered."
    DEFVAL          { 0 }
    ::= { sonusArsEndpointRecoveryConfigObjects 6 }

sonusArsEndpointRecoveryIpv6Address OBJECT-TYPE
    SYNTAX          Ipv6Address
    MAX-ACCESS      read-write
    STATUS          current
    DESCRIPTION     
            "The IPv6 address of the endpoint being recovered."
    ::= { sonusArsEndpointRecoveryConfigObjects 7 }

sonusArsSignallingMIBNotifications OBJECT IDENTIFIER
    ::= { sonusArsSignallingMIB 2 }

sonusArsSignallingMIBNotificationsPrefix OBJECT IDENTIFIER
    ::= { sonusArsSignallingMIBNotifications 0 }

sonusArsSignallingMIBNotificationsObjects OBJECT IDENTIFIER
    ::= { sonusArsSignallingMIBNotifications 1 }

sonusArsBlacklistedEndPointNotification NOTIFICATION-TYPE
    OBJECTS         { sonusArsStatEndpointIpAddress, 
                      sonusArsStatEndpointIpPortNum, 
                      sonusArsStatSigZoneId, sonusArsStatSigPortNum, 
                      sonusArsStatEndpointOwnerId, sonusArsStatAgentId, 
                      sonusEventDescription, sonusEventClass, 
                      sonusEventLevel, sonusSequenceId, sonusEventTime, 
                      sonusArsStatEndpointIpv6Address }
    STATUS          deprecated
    DESCRIPTION     
            "This trap is deprecated. This trap indicates that  one  endpoint of the 
             specified ip address, port, sig zone, protocol has been blacklisted
             by the ARS service. This indicates the endpoint is unreachable"
    ::= { sonusArsSignallingMIBNotificationsPrefix 1 }

sonusArsRecoveredEndPointNotification NOTIFICATION-TYPE
    OBJECTS         { sonusArsStatEndpointIpAddress, 
                      sonusArsStatEndpointIpPortNum, 
                      sonusArsStatSigZoneId, sonusArsStatSigPortNum, 
                      sonusArsStatEndpointOwnerId, sonusArsStatAgentId, 
                      sonusEventDescription, sonusEventClass, 
                      sonusEventLevel, sonusSequenceId, sonusEventTime, 
                      sonusArsStatEndpointIpv6Address }
    STATUS          deprecated
    DESCRIPTION     
            "This trap is deprecated. This trap indicates that  one endpoint of the specified ip address,
             port, sig zone, protocol has been recovered from  blacklisting by the ARS service.
             This indicates the endpoint is now reachable"
    ::= { sonusArsSignallingMIBNotificationsPrefix 2 }

sonusArsRecoveredEndPointsNotification NOTIFICATION-TYPE
    OBJECTS         { sonusArsStatSigZoneId, sonusArsEndpointRecoveryAll, 
                      sonusArsStatAgentId, sonusEventDescription, 
                      sonusEventClass, sonusEventLevel, sonusSequenceId, 
                      sonusEventTime }
    STATUS          deprecated
    DESCRIPTION     
            "This trap is deprecated. This trap indicates that  all endpoints in the specified zone,
             OR all the zones, protocol has been recovered from  blacklisting by the ARS service.
             This indicates these endpoints are  now reachable"
    ::= { sonusArsSignallingMIBNotificationsPrefix 3 }

END -- end of module SONUS-ARS-MIB.
