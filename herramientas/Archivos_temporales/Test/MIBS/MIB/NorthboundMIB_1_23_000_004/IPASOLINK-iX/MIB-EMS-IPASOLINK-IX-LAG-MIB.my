MIB-EMS-IPASOLINK-IX-LAG-MIB DEFINITIONS ::= BEGIN
    
    IMPORTS
        InterfaceIndex
            FROM IF-MIB
        OBJECT-TYPE
            FROM RFC-1212
        Counter, IpAddress, Opaque
            FROM RFC1155-SMI
        enterprises
            FROM SNMPv2-SMI;
    
    IpeEnableDisableValue ::=
        INTEGER { invalid(0), disabled(1), enabled(2) }
    
    
    SeverityValue ::=
        INTEGER { cleared(1), indetermine(2), critical(3), major(4),
                        minor(5), warning(6) }
    
    
    -- 1.3.6.1.4.1.119
    nec OBJECT IDENTIFIER
        ::= { enterprises 119 }
    
    -- 1.3.6.1.4.1.119.2
    nec-mib OBJECT IDENTIFIER
        ::= { nec 2 }
    
    -- 1.3.6.1.4.1.119.2.3
    necProductDepend OBJECT IDENTIFIER
        ::= { nec-mib 3 }
    
    -- 1.3.6.1.4.1.119.2.3.69
    radioEquipment OBJECT IDENTIFIER
        ::= { necProductDepend 69 }
    
    -- 1.3.6.1.4.1.119.2.3.69.203
    commonPnms OBJECT IDENTIFIER
        ::= { radioEquipment 203 }
    
    -- 1.3.6.1.4.1.119.2.3.69.203.507
    ipasolinkIx OBJECT IDENTIFIER
        ::= { commonPnms 507 }
    
    -- 1.3.6.1.4.1.119.2.3.69.203.507.5
    system5 OBJECT IDENTIFIER
        ::= { ipasolinkIx 5 }
    
    -- 1.3.6.1.4.1.119.2.3.69.203.507.501
    pasoNeoIpe-common OBJECT IDENTIFIER
        ::= { ipasolinkIx 501 }
    
    -- 1.3.6.1.4.1.119.2.3.69.203.507.501.3
    alarmStatusGroup OBJECT IDENTIFIER
        ::= { pasoNeoIpe-common 3 }
    
    -- 1.3.6.1.4.1.119.2.3.69.203.507.501.3.38
    asLinkAggrGroup OBJECT IDENTIFIER
        ::= { alarmStatusGroup 38 }
    
    -- 1.3.6.1.4.1.119.2.3.69.203.507.501.3.38.1
    asLinkAggrGroupTable OBJECT-TYPE
        SYNTAX      SEQUENCE OF AsLinkAggrGroupEntry
        ACCESS      not-accessible
        STATUS      mandatory
        DESCRIPTION
            "Alarm/Status for Link Aggregation Group. This table is created
             automatically when the Link Aggregation Group is defined."
        ::= { asLinkAggrGroup 1 }
    
    -- 1.3.6.1.4.1.119.2.3.69.203.507.501.3.38.1.1
    asLinkAggrGroupEntry OBJECT-TYPE
        SYNTAX      AsLinkAggrGroupEntry
        ACCESS      not-accessible
        STATUS      mandatory
        DESCRIPTION
            ""
        INDEX       { asLinkAggrGroupNEAddress, asLinkAggrGroupIfIndex }
        ::= { asLinkAggrGroupTable 1 }
    
    AsLinkAggrGroupEntry ::= SEQUENCE {
        asLinkAggrGroupIfIndex      InterfaceIndex,
        asLinkAggrGroupNEAddress    IpAddress,
        asLinkAggrGroupLinkStatus   SeverityValue,
        asLinkAggrGroupLLFStatus    INTEGER,
        asLinkAggrGroupOperStatus   INTEGER
    }
    
    -- 1.3.6.1.4.1.119.2.3.69.203.507.501.3.38.1.1.1
    asLinkAggrGroupIfIndex OBJECT-TYPE
        SYNTAX      InterfaceIndex
        ACCESS      not-accessible
        STATUS      mandatory
        DESCRIPTION
            "Index of this table."
        ::= { asLinkAggrGroupEntry 1 }
    
    -- 1.3.6.1.4.1.119.2.3.69.203.507.501.3.38.1.1.2
    asLinkAggrGroupNEAddress OBJECT-TYPE
        SYNTAX      IpAddress
        ACCESS      not-accessible
        STATUS      mandatory
        DESCRIPTION
            "reserved"
        ::= { asLinkAggrGroupEntry 2 }
    
    -- 1.3.6.1.4.1.119.2.3.69.203.507.501.3.38.1.1.3
    asLinkAggrGroupLinkStatus OBJECT-TYPE
        SYNTAX      SeverityValue
        ACCESS      read-only
        STATUS      mandatory
        DESCRIPTION
            "Link Status for Link Aggregation Group. The all member ports
             become link down, this state becomes alarm state.
             But the lower layer is in alarm state, the link status becomes
             'normal' state because of alarm mask function."
        ::= { asLinkAggrGroupEntry 3 }
    
    -- 1.3.6.1.4.1.119.2.3.69.203.507.501.3.38.1.1.4
    asLinkAggrGroupLLFStatus OBJECT-TYPE
        SYNTAX      INTEGER { invalid(0), normal(1), force(2) }
        ACCESS      read-only
        STATUS      mandatory
        DESCRIPTION
            "The status for link loss forwarding. 'force' means the interface
             is shutting down by the link loss forwarding."
        ::= { asLinkAggrGroupEntry 4 }
    
    -- 1.3.6.1.4.1.119.2.3.69.203.507.501.3.38.1.1.5
    asLinkAggrGroupOperStatus OBJECT-TYPE
        SYNTAX      INTEGER { invalid(0), linkDown(1), linkUp(2) }
        ACCESS      read-only
        STATUS      mandatory
        DESCRIPTION
            "Link Status for Link Aggregation Group. This object keeps
             linkDown state, when the lower layer is in alarm state."
        ::= { asLinkAggrGroupEntry 5 }
    
    -- 1.3.6.1.4.1.119.2.3.69.203.507.501.3.38.2
    asLinkAggrPortTable OBJECT-TYPE
        SYNTAX      SEQUENCE OF AsLinkAggrPortEntry
        ACCESS      not-accessible
        STATUS      mandatory
        DESCRIPTION
            "The Link Aggregation Member Port Status. This table is created
             automatically when a link aggregation group is defined.
             This table is created per each member port per link aggregation
             group."
        ::= { asLinkAggrGroup 2 }
    
    -- 1.3.6.1.4.1.119.2.3.69.203.507.501.3.38.2.1
    asLinkAggrPortEntry OBJECT-TYPE
        SYNTAX      AsLinkAggrPortEntry
        ACCESS      not-accessible
        STATUS      mandatory
        DESCRIPTION
            ""
        INDEX       { asLinkAggrPortNEAddress, asLinkAggrPortGroupIfIndex, asLinkAggrPortIfIndex }
        ::= { asLinkAggrPortTable 1 }
    
    AsLinkAggrPortEntry ::= SEQUENCE {
        asLinkAggrPortGroupIfIndex          InterfaceIndex,
        asLinkAggrPortIfIndex               InterfaceIndex,
        asLinkAggrPortNEAddress             IpAddress,
        asLinkAggrPortStatus                INTEGER,
        asLinkAggrPortActorLacpStatus       OCTET STRING,
        asLinkAggrPortPartnerLacpStatus     OCTET STRING,
        asLinkAggrPortLoopDetect            INTEGER
    }
    
    -- 1.3.6.1.4.1.119.2.3.69.203.507.501.3.38.2.1.1
    asLinkAggrPortGroupIfIndex OBJECT-TYPE
        SYNTAX      InterfaceIndex
        ACCESS      not-accessible
        STATUS      mandatory
        DESCRIPTION
            "link aggregation group index of this table."
        ::= { asLinkAggrPortEntry 1 }
    
    -- 1.3.6.1.4.1.119.2.3.69.203.507.501.3.38.2.1.2
    asLinkAggrPortIfIndex OBJECT-TYPE
        SYNTAX      InterfaceIndex
        ACCESS      not-accessible
        STATUS      mandatory
        DESCRIPTION
            "member port index of this table."
        ::= { asLinkAggrPortEntry 2 }
    
    -- 1.3.6.1.4.1.119.2.3.69.203.507.501.3.38.2.1.3
    asLinkAggrPortNEAddress OBJECT-TYPE
        SYNTAX      IpAddress
        ACCESS      not-accessible
        STATUS      mandatory
        DESCRIPTION
            "reserved"
        ::= { asLinkAggrPortEntry 3 }
    
    -- 1.3.6.1.4.1.119.2.3.69.203.507.501.3.38.2.1.4
    asLinkAggrPortStatus OBJECT-TYPE
        SYNTAX      INTEGER { invalid(0), active(1), standby(2) }
        ACCESS      read-only
        STATUS      mandatory
        DESCRIPTION
            "The port role of the member port.
             'active' means the port forwards/receives the packets on the
             interface."
        ::= { asLinkAggrPortEntry 4 }
    
    -- 1.3.6.1.4.1.119.2.3.69.203.507.501.3.38.2.1.5
    asLinkAggrPortActorLacpStatus OBJECT-TYPE
        SYNTAX      OCTET STRING
        ACCESS      read-only
        STATUS      mandatory
        DESCRIPTION
            "A string of 8 bits, corresponding to the current operational
             values of Actor_State as transmitted by the Actor in LACPDUs."
        ::= { asLinkAggrPortEntry 5 }
    
    -- 1.3.6.1.4.1.119.2.3.69.203.507.501.3.38.2.1.6
    asLinkAggrPortPartnerLacpStatus OBJECT-TYPE
        SYNTAX      OCTET STRING
        ACCESS      read-only
        STATUS      mandatory
        DESCRIPTION
            "A string of 8 bits, corresponding to the current values of
             Actor_State in the most recently received LACPDU transmitted by
             the protocol Partner."
        ::= { asLinkAggrPortEntry 6 }
    
    -- 1.3.6.1.4.1.119.2.3.69.203.507.501.3.38.2.1.7
    asLinkAggrPortLoopDetect OBJECT-TYPE
        SYNTAX      INTEGER { invalid(0), none(1), detected(2) }
        ACCESS      read-only
        STATUS      mandatory
        DESCRIPTION
            "LACP Control frames loop detect status for that port. This
             status will be cleared when the condition is not detected for a
             fixed time."
        ::= { asLinkAggrPortEntry 7 }
    
    -- 1.3.6.1.4.1.119.2.3.69.203.507.501.3.38.3
    asLinkAggrPortStatsTable OBJECT-TYPE
        SYNTAX      SEQUENCE OF AsLinkAggrPortStatsEntry
        ACCESS      not-accessible
        STATUS      mandatory
        DESCRIPTION
            "Link Aggregation Statistics."
        ::= { asLinkAggrGroup 3 }
    
    -- 1.3.6.1.4.1.119.2.3.69.203.507.501.3.38.3.1
    asLinkAggrPortStatsEntry OBJECT-TYPE
        SYNTAX      AsLinkAggrPortStatsEntry
        ACCESS      not-accessible
        STATUS      mandatory
        DESCRIPTION
            ""
        INDEX       { asLinkAggrPortStatsNEAddress, asLinkAggrPortStatsIfIndex }
        ::= { asLinkAggrPortStatsTable 1 }
    
    AsLinkAggrPortStatsEntry ::= SEQUENCE {
        asLinkAggrPortStatsIfIndex              InterfaceIndex,
        asLinkAggrPortStatsNEAddress            IpAddress,
        asLinkAggrPortStatsLACPDUsRx            Counter,
        asLinkAggrPortStatsLACPDUsTx            Counter,
        asLinkAggrPortStatsMarkerPDUsRx         Counter,
        asLinkAggrPortStatsMarkerRespPDUsRx     Counter,
        asLinkAggrPortStatsMarkerPDUsTx         Counter,
        asLinkAggrPortStatsMarkerRespPDUsTx     Counter
    }
    
    -- 1.3.6.1.4.1.119.2.3.69.203.507.501.3.38.3.1.1
    asLinkAggrPortStatsIfIndex OBJECT-TYPE
        SYNTAX      InterfaceIndex
        ACCESS      not-accessible
        STATUS      mandatory
        DESCRIPTION
            "Index of this table. This table is created per each member
             port."
        ::= { asLinkAggrPortStatsEntry 1 }
    
    -- 1.3.6.1.4.1.119.2.3.69.203.507.501.3.38.3.1.2
    asLinkAggrPortStatsNEAddress OBJECT-TYPE
        SYNTAX      IpAddress
        ACCESS      not-accessible
        STATUS      mandatory
        DESCRIPTION
            "reserved"
        ::= { asLinkAggrPortStatsEntry 2 }
    
    -- 1.3.6.1.4.1.119.2.3.69.203.507.501.3.38.3.1.3
    asLinkAggrPortStatsLACPDUsRx OBJECT-TYPE
        SYNTAX      Counter
        ACCESS      read-only
        STATUS      mandatory
        DESCRIPTION
            "The number of valid LACPDUs received on this Aggregation Port."
        ::= { asLinkAggrPortStatsEntry 3 }
    
    -- 1.3.6.1.4.1.119.2.3.69.203.507.501.3.38.3.1.4
    asLinkAggrPortStatsLACPDUsTx OBJECT-TYPE
        SYNTAX      Counter
        ACCESS      read-only
        STATUS      mandatory
        DESCRIPTION
            "The number of LACPDUs transmitted on this
             Aggregation Port."
        ::= { asLinkAggrPortStatsEntry 4 }
    
    -- 1.3.6.1.4.1.119.2.3.69.203.507.501.3.38.3.1.5
    asLinkAggrPortStatsMarkerPDUsRx OBJECT-TYPE
        SYNTAX      Counter
        ACCESS      read-only
        STATUS      mandatory
        DESCRIPTION
            "The number of valid Marker PDUs received on this Aggregation
             Port."
        ::= { asLinkAggrPortStatsEntry 5 }
    
    -- 1.3.6.1.4.1.119.2.3.69.203.507.501.3.38.3.1.6
    asLinkAggrPortStatsMarkerRespPDUsRx OBJECT-TYPE
        SYNTAX      Counter
        ACCESS      read-only
        STATUS      mandatory
        DESCRIPTION
            "The number of valid Marker Response PDUs received on this
             Aggregation Port."
        ::= { asLinkAggrPortStatsEntry 6 }
    
    -- 1.3.6.1.4.1.119.2.3.69.203.507.501.3.38.3.1.7
    asLinkAggrPortStatsMarkerPDUsTx OBJECT-TYPE
        SYNTAX      Counter
        ACCESS      read-only
        STATUS      mandatory
        DESCRIPTION
            "The number of Marker PDUs transmitted on this Aggregation Port."
        ::= { asLinkAggrPortStatsEntry 7 }
    
    -- 1.3.6.1.4.1.119.2.3.69.203.507.501.3.38.3.1.8
    asLinkAggrPortStatsMarkerRespPDUsTx OBJECT-TYPE
        SYNTAX      Counter
        ACCESS      read-only
        STATUS      mandatory
        DESCRIPTION
            "The number of Marker Response PDUs transmitted on this
             Aggregation Port."
        ::= { asLinkAggrPortStatsEntry 8 }
    
    -- 1.3.6.1.4.1.119.2.3.69.203.507.507
    pasoNeoIpe-ix OBJECT IDENTIFIER
        ::= { ipasolinkIx 507 }
    
END -- end of module MIB-EMS-IPASOLINK-IX-LAG-MIB.
