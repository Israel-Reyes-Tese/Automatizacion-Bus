--
-- This SMIv2 module has been generated by smidump 0.2-cvs. Do not edit.
--

INTELCORPORATIONBASEBOARDMAPPERTRAP-MIB DEFINITIONS ::= BEGIN

IMPORTS
    dmiCompId, dmiEventAssociatedGroup, dmiEventDateTime, 
    dmiEventSeverity, dmiEventStateKey, dmiEventSubSystem, 
    dmiEventSystem
        FROM DMTF-DMI
    dmtfCoolingDeviceEvSub, dmtfCoolingDeviceEvSys, 
    dmtfCoolingUnitGlobalEvSub, dmtfCoolingUnitGlobalEvSys, 
    dmtfPhysicalContainerGlobalEvSub, dmtfPhysicalContainerGlobalEvSys, 
    dmtfPhysicalMemoryArrayEvSub, dmtfPhysicalMemoryArrayEvSys, 
    dmtfPowerSupplyEvSub, dmtfPowerSupplyEvSys, dmtfPowerUnitGlobalEvSub, 
    dmtfPowerUnitGlobalEvSys, dmtfProcessorEvSub, dmtfProcessorEvSys, 
    dmtfSystemSlotEvSub, dmtfSystemSlotEvSys, dmtfTemperatureProbeEvSub, 
    dmtfTemperatureProbeEvSys, dmtfVoltageProbeEvSub, 
    dmtfVoltageProbeEvSys
        FROM DMTF-SYSTEMS-TRAP
    a1005Selfid, a17PowerSupplyIndex, a19SlotIndex, a28CoolingUnitIndex, 
    a34MemoryArrayTableIndex, a54VoltageProbeIndex, 
    a55TemperatureProbeTableIndex, a64ContainerIndex, a67PowerUnitIndex, 
    a6ProcessorIndex, dmtf, dmtfStdMifs, mapperdmtfGroups
        FROM INTELCORPORATIONBASEBOARDMAPPER-MIB
    MODULE-IDENTITY, NOTIFICATION-TYPE, enterprises
        FROM SNMPv2-SMI;

mapbaseMIB MODULE-IDENTITY
    LAST-UPDATED    "190601091120Z"
    ORGANIZATION    
            "Intel Corporation"
    CONTACT-INFO    
            "Intel - Modular Telecom Server Divison
             
             Mailstop CBA1
             100 Center Point Circle, Suite 210
             Columbia, SC 29210"
    DESCRIPTION     
            "This MIB maps baseboard values translated from 
             DMTF MIFs."
    REVISION        "190601091120Z"
    DESCRIPTION     
            "Removed unnecessary DMIComponentIndex, DmiDisplayString, DmiOctetString, DmiCounter imports from INTELCORPORATIONBASEBOARDMAPPER-MIB. D. Berry"
    REVISION        "190511171530Z"
    DESCRIPTION     
            "Added changes for SMIv2 compliance. D. Berry"
    REVISION        "190511071200Z"
    DESCRIPTION     
            "Fixed identifier naming convention discrepancies. Fixed hanging
             references -> DMTF-SYSTEMS & DMTF-DMI. D. Throckmorton"
    REVISION        "190510101200Z"
    DESCRIPTION     
            "Fixed CoolingSensorsEv -> CoolingDeviceEv typo  A. Cress"
    REVISION        "190508081200Z"
    DESCRIPTION     
            "Fixed compiler problem 
             with tables having multiple objects instead 
             of just one row.  Moved trap objects that were under tables by 
             creating this separate mib, mapbase6t.mib.  D. Berry"
    ::= { intel 1 }


intel OBJECT IDENTIFIER
    ::= { enterprises 343 }

products OBJECT IDENTIFIER
    ::= { intel 2 }

servermanagement OBJECT IDENTIFIER
    ::= { intel 2 10 }

dmtfGroups OBJECT IDENTIFIER
    ::= { intel 2 10 7 }

tCoolingSensors OBJECT IDENTIFIER
    ::= { dmtfStdMifs 4 3 }

tCoolingSensorsTraps OBJECT IDENTIFIER
    ::= { dmtfStdMifs 4 3 0 }

tProcessor OBJECT IDENTIFIER
    ::= { dmtfStdMifs 4 5 }

tProcessorTraps OBJECT IDENTIFIER
    ::= { dmtfStdMifs 4 5 0 }

tPowerSupply OBJECT IDENTIFIER
    ::= { dmtfStdMifs 4 16 }

tPowerSupplyTraps OBJECT IDENTIFIER
    ::= { dmtfStdMifs 4 16 0 }

tSystemSlots OBJECT IDENTIFIER
    ::= { dmtfStdMifs 4 18 }

tSystemSlotsTraps OBJECT IDENTIFIER
    ::= { dmtfStdMifs 4 18 0 }

tPhysicalMemoryArray OBJECT IDENTIFIER
    ::= { dmtfStdMifs 4 33 }

tPhysicalMemoryArrayTraps OBJECT IDENTIFIER
    ::= { dmtfStdMifs 4 33 0 }

tVoltageProbe OBJECT IDENTIFIER
    ::= { dmtfStdMifs 4 53 }

tVoltageProbeTraps OBJECT IDENTIFIER
    ::= { dmtfStdMifs 4 53 0 }

tTemperatureProbe OBJECT IDENTIFIER
    ::= { dmtfStdMifs 4 54 }

tTemperatureProbeTraps OBJECT IDENTIFIER
    ::= { dmtfStdMifs 4 54 0 }

tPhysicalContainerGlobal OBJECT IDENTIFIER
    ::= { dmtfStdMifs 4 63 }

tPhysicalContainerGlobalTableTraps OBJECT IDENTIFIER
    ::= { dmtfStdMifs 4 63 0 }

tPowerUnitGlobalTable OBJECT IDENTIFIER
    ::= { dmtfStdMifs 4 66 }

tPowerUnitGlobalTableTraps OBJECT IDENTIFIER
    ::= { dmtfStdMifs 4 66 0 }

tCoolingUnitGlobalTable OBJECT IDENTIFIER
    ::= { dmtfStdMifs 4 67 }

tCoolingUnitGlobalTableTraps OBJECT IDENTIFIER
    ::= { dmtfStdMifs 4 67 0 }

coolingSensorsCoolingDeviceFailure NOTIFICATION-TYPE
    OBJECTS         { dmiEventDateTime, dmiCompId, dmiEventSeverity, 
                      dmiEventStateKey, dmiEventAssociatedGroup, 
                      dmtfCoolingDeviceEvSys, dmtfCoolingDeviceEvSub, 
                      a1005Selfid }
    STATUS          current
    DESCRIPTION     
            "Cooling Device Failure"
    REFERENCE       
            "'Intel|Cooling Sensors|002' 256"
    ::= { tCoolingSensorsTraps 256 }

coolingSensorsCoolingDeviceOK NOTIFICATION-TYPE
    OBJECTS         { dmiEventDateTime, dmiCompId, dmiEventSeverity, 
                      dmiEventStateKey, dmiEventAssociatedGroup, 
                      dmtfCoolingDeviceEvSys, dmtfCoolingDeviceEvSub, 
                      a1005Selfid }
    STATUS          current
    DESCRIPTION     
            "Cooling Device OK"
    REFERENCE       
            "'Intel|Cooling Sensors|002' 257"
    ::= { tCoolingSensorsTraps 257 }

coolingSensorsCoolingDeviceInserted NOTIFICATION-TYPE
    OBJECTS         { dmiEventDateTime, dmiCompId, dmiEventSeverity, 
                      dmiEventStateKey, dmiEventAssociatedGroup, 
                      dmtfCoolingDeviceEvSys, dmtfCoolingDeviceEvSub, 
                      a1005Selfid }
    STATUS          current
    DESCRIPTION     
            "Cooling Device Inserted"
    REFERENCE       
            "'Intel|Cooling Sensors|002' 258"
    ::= { tCoolingSensorsTraps 258 }

coolingSensorsCoolingDeviceRemoved NOTIFICATION-TYPE
    OBJECTS         { dmiEventDateTime, dmiCompId, dmiEventSeverity, 
                      dmiEventStateKey, dmiEventAssociatedGroup, 
                      dmtfCoolingDeviceEvSys, dmtfCoolingDeviceEvSub, 
                      a1005Selfid }
    STATUS          current
    DESCRIPTION     
            "Cooling Device Removed"
    REFERENCE       
            "'Intel|Cooling Sensors|002' 259"
    ::= { tCoolingSensorsTraps 259 }

processorInternalError NOTIFICATION-TYPE
    OBJECTS         { dmiEventDateTime, dmiCompId, dmiEventSeverity, 
                      dmiEventStateKey, dmiEventAssociatedGroup, 
                      dmtfProcessorEvSys, dmtfProcessorEvSub, 
                      a6ProcessorIndex }
    STATUS          current
    DESCRIPTION     
            "Processor Internal Error"
    REFERENCE       
            "'DMTF|Processor|009' 256"
    ::= { dmtfStdMifs 4 5 0 256 }

processorThermalTrip NOTIFICATION-TYPE
    OBJECTS         { dmiEventDateTime, dmiCompId, dmiEventSeverity, 
                      dmiEventStateKey, dmiEventAssociatedGroup, 
                      dmtfProcessorEvSys, dmtfProcessorEvSub, 
                      a6ProcessorIndex }
    STATUS          current
    DESCRIPTION     
            "Processor Thermal Trip"
    REFERENCE       
            "'DMTF|Processor|009' 257"
    ::= { dmtfStdMifs 4 5 0 257 }

processorFRB-3Failure NOTIFICATION-TYPE
    OBJECTS         { dmiEventDateTime, dmiCompId, dmiEventSeverity, 
                      dmiEventStateKey, dmiEventAssociatedGroup, 
                      dmtfProcessorEvSys, dmtfProcessorEvSub, 
                      a6ProcessorIndex }
    STATUS          current
    DESCRIPTION     
            "Processor FRB-3 Failure"
    REFERENCE       
            "'DMTF|Processor|009' 258"
    ::= { dmtfStdMifs 4 5 0 258 }

processorDisabled NOTIFICATION-TYPE
    OBJECTS         { dmiEventDateTime, dmiCompId, dmiEventSeverity, 
                      dmiEventStateKey, dmiEventAssociatedGroup, 
                      dmtfProcessorEvSys, dmtfProcessorEvSub, 
                      a6ProcessorIndex }
    STATUS          current
    DESCRIPTION     
            "Processor Disabled"
    REFERENCE       
            "'DMTF|Processor|009' 259"
    ::= { dmtfStdMifs 4 5 0 259 }

powerSupplyFailed NOTIFICATION-TYPE
    OBJECTS         { dmiEventDateTime, dmiCompId, dmiEventSeverity, 
                      dmiEventStateKey, dmiEventAssociatedGroup, 
                      dmtfPowerSupplyEvSys, dmtfPowerSupplyEvSub, 
                      a17PowerSupplyIndex }
    STATUS          current
    DESCRIPTION     
            "Power Supply Failed"
    REFERENCE       
            "'DMTF|Power Supply|002' 256"
    ::= { dmtfStdMifs 4 16 0 256 }

powerSupplyOK NOTIFICATION-TYPE
    OBJECTS         { dmiEventDateTime, dmiCompId, dmiEventSeverity, 
                      dmiEventStateKey, dmiEventAssociatedGroup, 
                      dmtfPowerSupplyEvSys, dmtfPowerSupplyEvSub, 
                      a17PowerSupplyIndex }
    STATUS          current
    DESCRIPTION     
            "Power Supply OK"
    REFERENCE       
            "'DMTF|Power Supply|002' 257"
    ::= { dmtfStdMifs 4 16 0 257 }

powerSupplyLikelyToFail NOTIFICATION-TYPE
    OBJECTS         { dmiEventDateTime, dmiCompId, dmiEventSeverity, 
                      dmiEventStateKey, dmiEventAssociatedGroup, 
                      dmtfPowerSupplyEvSys, dmtfPowerSupplyEvSub, 
                      a17PowerSupplyIndex }
    STATUS          current
    DESCRIPTION     
            "Power Supply Likely To Fail"
    REFERENCE       
            "'DMTF|Power Supply|002' 258"
    ::= { dmtfStdMifs 4 16 0 258 }

powerSupplyInserted NOTIFICATION-TYPE
    OBJECTS         { dmiEventDateTime, dmiCompId, dmiEventSeverity, 
                      dmiEventStateKey, dmiEventAssociatedGroup, 
                      dmtfPowerSupplyEvSys, dmtfPowerSupplyEvSub, 
                      a17PowerSupplyIndex }
    STATUS          current
    DESCRIPTION     
            "Power Supply Inserted"
    REFERENCE       
            "'DMTF|Power Supply|002' 259"
    ::= { dmtfStdMifs 4 16 0 259 }

powerSupplyRemoved NOTIFICATION-TYPE
    OBJECTS         { dmiEventDateTime, dmiCompId, dmiEventSeverity, 
                      dmiEventStateKey, dmiEventAssociatedGroup, 
                      dmtfPowerSupplyEvSys, dmtfPowerSupplyEvSub, 
                      a17PowerSupplyIndex }
    STATUS          current
    DESCRIPTION     
            "Power Supply Removed"
    REFERENCE       
            "'DMTF|Power Supply|002' 260"
    ::= { dmtfStdMifs 4 16 0 260 }

powerSupplyACLost NOTIFICATION-TYPE
    OBJECTS         { dmiEventDateTime, dmiCompId, dmiEventSeverity, 
                      dmiEventStateKey, dmiEventAssociatedGroup, 
                      dmtfPowerSupplyEvSys, dmtfPowerSupplyEvSub, 
                      a17PowerSupplyIndex }
    STATUS          current
    DESCRIPTION     
            "Power Supply AC lost"
    REFERENCE       
            "'DMTF|Power Supply|002' 261"
    ::= { dmtfStdMifs 4 16 0 261 }

powerSupplyACLostOrOutOfRange NOTIFICATION-TYPE
    OBJECTS         { dmiEventDateTime, dmiCompId, dmiEventSeverity, 
                      dmiEventStateKey, dmiEventAssociatedGroup, 
                      dmtfPowerSupplyEvSys, dmtfPowerSupplyEvSub, 
                      a17PowerSupplyIndex }
    STATUS          current
    DESCRIPTION     
            "Power Supply AC lost or out-of-range"
    REFERENCE       
            "'DMTF|Power Supply|002' 262"
    ::= { dmtfStdMifs 4 16 0 262 }

powerSupplyOutOfRangeButPresent NOTIFICATION-TYPE
    OBJECTS         { dmiEventDateTime, dmiCompId, dmiEventSeverity, 
                      dmiEventStateKey, dmiEventAssociatedGroup, 
                      dmtfPowerSupplyEvSys, dmtfPowerSupplyEvSub, 
                      a17PowerSupplyIndex }
    STATUS          current
    DESCRIPTION     
            "Power Supply AC out-of-range, but present"
    REFERENCE       
            "'DMTF|Power Supply|002' 263"
    ::= { dmtfStdMifs 4 16 0 263 }

systemSlotsSlotStatusChangeToOK NOTIFICATION-TYPE
    OBJECTS         { dmiEventDateTime, dmiCompId, dmiEventSeverity, 
                      dmiEventStateKey, dmiEventAssociatedGroup, 
                      dmtfSystemSlotEvSys, dmtfSystemSlotEvSub, 
                      a19SlotIndex }
    STATUS          current
    DESCRIPTION     
            "Slot status change to OK"
    REFERENCE       
            "'DMTF|System Slot|005' 1"
    ::= { tSystemSlotsTraps 1 }

systemSlotsSlotStatusChangeToNonCritical NOTIFICATION-TYPE
    OBJECTS         { dmiEventDateTime, dmiCompId, dmiEventSeverity, 
                      dmiEventStateKey, dmiEventAssociatedGroup, 
                      dmtfSystemSlotEvSys, dmtfSystemSlotEvSub, 
                      a19SlotIndex }
    STATUS          current
    DESCRIPTION     
            "Slot status change to Non-Critical"
    REFERENCE       
            "'DMTF|System Slot|005' 2"
    ::= { tSystemSlotsTraps 2 }

systemSlotsSlotStatusChangeToCritical NOTIFICATION-TYPE
    OBJECTS         { dmiEventDateTime, dmiCompId, dmiEventSeverity, 
                      dmiEventStateKey, dmiEventAssociatedGroup, 
                      dmtfSystemSlotEvSys, dmtfSystemSlotEvSub, 
                      a19SlotIndex }
    STATUS          current
    DESCRIPTION     
            "Slot status change to Critical"
    REFERENCE       
            "'DMTF|System Slot|005' 3"
    ::= { tSystemSlotsTraps 3 }

systemSlotsSlotPoweredOn NOTIFICATION-TYPE
    OBJECTS         { dmiEventDateTime, dmiCompId, dmiEventSeverity, 
                      dmiEventStateKey, dmiEventAssociatedGroup, 
                      dmtfSystemSlotEvSys, dmtfSystemSlotEvSub, 
                      a19SlotIndex }
    STATUS          current
    DESCRIPTION     
            "Slot Powered On"
    REFERENCE       
            "'DMTF|System Slot|005' 4"
    ::= { tSystemSlotsTraps 4 }

systemSlotsSlotPoweredOff NOTIFICATION-TYPE
    OBJECTS         { dmiEventDateTime, dmiCompId, dmiEventSeverity, 
                      dmiEventStateKey, dmiEventAssociatedGroup, 
                      dmtfSystemSlotEvSys, dmtfSystemSlotEvSub, 
                      a19SlotIndex }
    STATUS          current
    DESCRIPTION     
            "Slot Powered Off"
    REFERENCE       
            "'DMTF|System Slot|005' 5"
    ::= { tSystemSlotsTraps 5 }

systemSlotsSlotDisabled NOTIFICATION-TYPE
    OBJECTS         { dmiEventDateTime, dmiCompId, dmiEventSeverity, 
                      dmiEventStateKey, dmiEventAssociatedGroup, 
                      dmtfSystemSlotEvSys, dmtfSystemSlotEvSub, 
                      a19SlotIndex }
    STATUS          current
    DESCRIPTION     
            "Slot is Disabled"
    REFERENCE       
            "'DMTF|System Slot|005' 6"
    ::= { tSystemSlotsTraps 6 }

physicalMemorySingleBitECCError NOTIFICATION-TYPE
    OBJECTS         { dmiEventDateTime, dmiCompId, dmiEventSeverity, 
                      dmiEventStateKey, dmiEventAssociatedGroup, 
                      dmtfPhysicalMemoryArrayEvSys, 
                      dmtfPhysicalMemoryArrayEvSub, 
                      a34MemoryArrayTableIndex }
    STATUS          current
    DESCRIPTION     
            "Single BIT ECC Error"
    REFERENCE       
            "'DMTF|Physical Memory Array|001' 256"
    ::= { dmtfStdMifs 4 33 0 256 }

physicalMemoryMultiBitECCErrorFromPreviousBoot NOTIFICATION-TYPE
    OBJECTS         { dmiEventDateTime, dmiCompId, dmiEventSeverity, 
                      dmiEventStateKey, dmiEventAssociatedGroup, 
                      dmtfPhysicalMemoryArrayEvSys, 
                      dmtfPhysicalMemoryArrayEvSub, 
                      a34MemoryArrayTableIndex }
    STATUS          current
    DESCRIPTION     
            "Multi BIT ECC Error from previous boot"
    REFERENCE       
            "'DMTF|Physical Memory Array|001' 257"
    ::= { dmtfStdMifs 4 33 0 257 }

physicalMemoryScrubFailed NOTIFICATION-TYPE
    OBJECTS         { dmiEventDateTime, dmiCompId, dmiEventSeverity, 
                      dmiEventStateKey, dmiEventAssociatedGroup, 
                      dmtfPhysicalMemoryArrayEvSys, 
                      dmtfPhysicalMemoryArrayEvSub, 
                      a34MemoryArrayTableIndex }
    STATUS          current
    DESCRIPTION     
            "Memory Scrub Failed"
    REFERENCE       
            "'DMTF|Physical Memory Array|001' 258"
    ::= { dmtfStdMifs 4 33 0 258 }

physicalMemoryDeviceDisabled NOTIFICATION-TYPE
    OBJECTS         { dmiEventDateTime, dmiCompId, dmiEventSeverity, 
                      dmiEventStateKey, dmiEventAssociatedGroup, 
                      dmtfPhysicalMemoryArrayEvSys, 
                      dmtfPhysicalMemoryArrayEvSub, 
                      a34MemoryArrayTableIndex }
    STATUS          current
    DESCRIPTION     
            "Memory Device Disabled"
    REFERENCE       
            "'DMTF|Physical Memory Array|001' 259"
    ::= { dmtfStdMifs 4 33 0 259 }

physicalMemoryErrorLoggingLimitReached NOTIFICATION-TYPE
    OBJECTS         { dmiEventDateTime, dmiCompId, dmiEventSeverity, 
                      dmiEventStateKey, dmiEventAssociatedGroup, 
                      dmtfPhysicalMemoryArrayEvSys, 
                      dmtfPhysicalMemoryArrayEvSub, 
                      a34MemoryArrayTableIndex }
    STATUS          current
    DESCRIPTION     
            "Memory Error Logging Limit Reached"
    REFERENCE       
            "'DMTF|Physical Memory Array|001' 260"
    ::= { dmtfStdMifs 4 33 0 260 }

voltageProbeChangedToOK NOTIFICATION-TYPE
    OBJECTS         { dmiEventDateTime, dmiCompId, dmiEventSeverity, 
                      dmiEventStateKey, dmiEventAssociatedGroup, 
                      dmtfVoltageProbeEvSys, dmtfVoltageProbeEvSub, 
                      a54VoltageProbeIndex }
    STATUS          current
    DESCRIPTION     
            "Status Changed to OK"
    REFERENCE       
            "'DMTF|Voltage Probe|001' 256"
    ::= { dmtfStdMifs 4 53 0 256 }

voltageProbeChangedToUpperCritical NOTIFICATION-TYPE
    OBJECTS         { dmiEventDateTime, dmiCompId, dmiEventSeverity, 
                      dmiEventStateKey, dmiEventAssociatedGroup, 
                      dmtfVoltageProbeEvSys, dmtfVoltageProbeEvSub, 
                      a54VoltageProbeIndex }
    STATUS          current
    DESCRIPTION     
            "Status Changed to Upper Critical"
    REFERENCE       
            "'DMTF|Voltage Probe|001' 257"
    ::= { dmtfStdMifs 4 53 0 257 }

voltageProbeChangedToLowerCritical NOTIFICATION-TYPE
    OBJECTS         { dmiEventDateTime, dmiCompId, dmiEventSeverity, 
                      dmiEventStateKey, dmiEventAssociatedGroup, 
                      dmtfVoltageProbeEvSys, dmtfVoltageProbeEvSub, 
                      a54VoltageProbeIndex }
    STATUS          current
    DESCRIPTION     
            "Status Changed to Lower Critical"
    REFERENCE       
            "'DMTF|Voltage Probe|001' 258"
    ::= { dmtfStdMifs 4 53 0 258 }

voltageProbeChangedFromOKToUpperNonCritical NOTIFICATION-TYPE
    OBJECTS         { dmiEventDateTime, dmiCompId, dmiEventSeverity, 
                      dmiEventStateKey, dmiEventAssociatedGroup, 
                      dmtfVoltageProbeEvSys, dmtfVoltageProbeEvSub, 
                      a54VoltageProbeIndex }
    STATUS          current
    DESCRIPTION     
            "Status Changed to from OK to Upper Non Critical"
    REFERENCE       
            "'DMTF|Voltage Probe|001' 259"
    ::= { dmtfStdMifs 4 53 0 259 }

voltageProbeChangedFromOKToLowerNonCritical NOTIFICATION-TYPE
    OBJECTS         { dmiEventDateTime, dmiCompId, dmiEventSeverity, 
                      dmiEventStateKey, dmiEventAssociatedGroup, 
                      dmtfVoltageProbeEvSys, dmtfVoltageProbeEvSub, 
                      a54VoltageProbeIndex }
    STATUS          current
    DESCRIPTION     
            "Status Changed to from OK to Lower Non Critical"
    REFERENCE       
            "'DMTF|Voltage Probe|001' 260"
    ::= { dmtfStdMifs 4 53 0 260 }

voltageProbeChangedFromUpperCrtToUpperNonCrt NOTIFICATION-TYPE
    OBJECTS         { dmiEventDateTime, dmiCompId, dmiEventSeverity, 
                      dmiEventStateKey, dmiEventAssociatedGroup, 
                      dmtfVoltageProbeEvSys, dmtfVoltageProbeEvSub, 
                      a54VoltageProbeIndex }
    STATUS          current
    DESCRIPTION     
            "Status Changed to from Upper Critical to Upper Non Critical"
    REFERENCE       
            "'DMTF|Voltage Probe|001' 261"
    ::= { dmtfStdMifs 4 53 0 261 }

voltageProbeChangedFromLowerCrtToLowerNonCrt NOTIFICATION-TYPE
    OBJECTS         { dmiEventDateTime, dmiCompId, dmiEventSeverity, 
                      dmiEventStateKey, dmiEventAssociatedGroup, 
                      dmtfVoltageProbeEvSys, dmtfVoltageProbeEvSub, 
                      a54VoltageProbeIndex }
    STATUS          current
    DESCRIPTION     
            "Status Changed to from Lower Critical to Lower Non Critical"
    REFERENCE       
            "'DMTF|Voltage Probe|001' 262"
    ::= { dmtfStdMifs 4 53 0 262 }

temperatureProbeChangedToOK NOTIFICATION-TYPE
    OBJECTS         { dmiEventDateTime, dmiCompId, dmiEventSeverity, 
                      dmiEventStateKey, dmiEventAssociatedGroup, 
                      dmtfTemperatureProbeEvSys, 
                      dmtfTemperatureProbeEvSub, 
                      a55TemperatureProbeTableIndex }
    STATUS          current
    DESCRIPTION     
            "Status Changed to OK"
    REFERENCE       
            "'DMTF|Temperature Probe|002' 256"
    ::= { dmtfStdMifs 4 54 0 256 }

temperatureProbeChangedToUpperCritical NOTIFICATION-TYPE
    OBJECTS         { dmiEventDateTime, dmiCompId, dmiEventSeverity, 
                      dmiEventStateKey, dmiEventAssociatedGroup, 
                      dmtfTemperatureProbeEvSys, 
                      dmtfTemperatureProbeEvSub, 
                      a55TemperatureProbeTableIndex }
    STATUS          current
    DESCRIPTION     
            "Status Changed to Upper Critical"
    REFERENCE       
            "'DMTF|Temperature Probe|002' 257"
    ::= { dmtfStdMifs 4 54 0 257 }

temperatureProbeChangedToLowerCritical NOTIFICATION-TYPE
    OBJECTS         { dmiEventDateTime, dmiCompId, dmiEventSeverity, 
                      dmiEventStateKey, dmiEventAssociatedGroup, 
                      dmtfTemperatureProbeEvSys, 
                      dmtfTemperatureProbeEvSub, 
                      a55TemperatureProbeTableIndex }
    STATUS          current
    DESCRIPTION     
            "Status Changed to Lower Critical"
    REFERENCE       
            "'DMTF|Temperature Probe|002' 258"
    ::= { dmtfStdMifs 4 54 0 258 }

temperatureProbeChangedFromOKToUpperNonCritical NOTIFICATION-TYPE
    OBJECTS         { dmiEventDateTime, dmiCompId, dmiEventSeverity, 
                      dmiEventStateKey, dmiEventAssociatedGroup, 
                      dmtfTemperatureProbeEvSys, 
                      dmtfTemperatureProbeEvSub, 
                      a55TemperatureProbeTableIndex }
    STATUS          current
    DESCRIPTION     
            "Status Changed from OK to Upper Non Critical"
    REFERENCE       
            "'DMTF|Temperature Probe|002' 259"
    ::= { dmtfStdMifs 4 54 0 259 }

temperatureProbeChangedFromOKToLowerNonCritical NOTIFICATION-TYPE
    OBJECTS         { dmiEventDateTime, dmiCompId, dmiEventSeverity, 
                      dmiEventStateKey, dmiEventAssociatedGroup, 
                      dmtfTemperatureProbeEvSys, 
                      dmtfTemperatureProbeEvSub, 
                      a55TemperatureProbeTableIndex }
    STATUS          current
    DESCRIPTION     
            "Status Changed from OK to Lower Non Critical"
    REFERENCE       
            "'DMTF|Temperature Probe|002' 260"
    ::= { dmtfStdMifs 4 54 0 260 }

temperatureProbeChangedFromUpperCrtToUpperNonCrt NOTIFICATION-TYPE
    OBJECTS         { dmiEventDateTime, dmiCompId, dmiEventSeverity, 
                      dmiEventStateKey, dmiEventAssociatedGroup, 
                      dmtfTemperatureProbeEvSys, 
                      dmtfTemperatureProbeEvSub, 
                      a55TemperatureProbeTableIndex }
    STATUS          current
    DESCRIPTION     
            "Status Changed from Upper Critical to Upper Non Critical"
    REFERENCE       
            "'DMTF|Temperature Probe|002' 261"
    ::= { dmtfStdMifs 4 54 0 261 }

temperatureProbeChangedFromLowerCrtToLowerNonCrt NOTIFICATION-TYPE
    OBJECTS         { dmiEventDateTime, dmiCompId, dmiEventSeverity, 
                      dmiEventStateKey, dmiEventAssociatedGroup, 
                      dmtfTemperatureProbeEvSys, 
                      dmtfTemperatureProbeEvSub, 
                      a55TemperatureProbeTableIndex }
    STATUS          current
    DESCRIPTION     
            "Status Changed from Lower Critical to Lower Non Critical"
    REFERENCE       
            "'DMTF|Temperature Probe|002' 262"
    ::= { dmtfStdMifs 4 54 0 262 }

physicalContainerSecurityBreached NOTIFICATION-TYPE
    OBJECTS         { dmiEventDateTime, dmiCompId, dmiEventSeverity, 
                      dmiEventStateKey, dmiEventAssociatedGroup, 
                      dmtfPhysicalContainerGlobalEvSys, 
                      dmtfPhysicalContainerGlobalEvSub, 
                      a64ContainerIndex }
    STATUS          current
    DESCRIPTION     
            "Container Security Breached"
    REFERENCE       
            "'DMTF|Physical Container Global Table|001' 6"
    ::= { dmtfStdMifs 4 63 0 6 }

physicalContainerSecured NOTIFICATION-TYPE
    OBJECTS         { dmiEventDateTime, dmiCompId, dmiEventSeverity, 
                      dmiEventStateKey, dmiEventAssociatedGroup, 
                      dmtfPhysicalContainerGlobalEvSys, 
                      dmtfPhysicalContainerGlobalEvSub, 
                      a64ContainerIndex }
    STATUS          current
    DESCRIPTION     
            "Container Secured"
    REFERENCE       
            "'DMTF|Physical Container Global Table|001' 256"
    ::= { dmtfStdMifs 4 63 0 256 }

powerUnitRedundancyLost NOTIFICATION-TYPE
    OBJECTS         { dmiEventDateTime, dmiCompId, dmiEventSeverity, 
                      dmiEventStateKey, dmiEventAssociatedGroup, 
                      dmtfPowerUnitGlobalEvSys, dmtfPowerUnitGlobalEvSub, 
                      a67PowerUnitIndex }
    STATUS          current
    DESCRIPTION     
            "Power Unit Redundancy Lost"
    REFERENCE       
            "'DMTF|Power Unit Global Table|001' 1"
    ::= { tPowerUnitGlobalTableTraps 1 }

powerUnitRedundancyRegained NOTIFICATION-TYPE
    OBJECTS         { dmiEventDateTime, dmiCompId, dmiEventSeverity, 
                      dmiEventStateKey, dmiEventAssociatedGroup, 
                      dmtfPowerUnitGlobalEvSys, dmtfPowerUnitGlobalEvSub, 
                      a67PowerUnitIndex }
    STATUS          current
    DESCRIPTION     
            "Power Unit Redundancy Regained"
    REFERENCE       
            "'DMTF|Power Unit Global Table|001' 2"
    ::= { tPowerUnitGlobalTableTraps 2 }

powerUnitDegraded NOTIFICATION-TYPE
    OBJECTS         { dmiEventDateTime, dmiCompId, dmiEventSeverity, 
                      dmiEventStateKey, dmiEventAssociatedGroup, 
                      dmtfPowerUnitGlobalEvSys, dmtfPowerUnitGlobalEvSub, 
                      a67PowerUnitIndex }
    STATUS          current
    DESCRIPTION     
            "Power Unit Redundancy Degraded"
    REFERENCE       
            "'DMTF|Power Unit Global Table|001' 3"
    ::= { tPowerUnitGlobalTableTraps 3 }

powerUnitVAShutdownConditionCleared NOTIFICATION-TYPE
    OBJECTS         { dmiEventDateTime, dmiCompId, dmiEventSeverity, 
                      dmiEventStateKey, dmiEventAssociatedGroup, 
                      dmtfPowerUnitGlobalEvSys, dmtfPowerUnitGlobalEvSub, 
                      a67PowerUnitIndex }
    STATUS          current
    DESCRIPTION     
            "Power Unit VA Shutdown Condition Cleared"
    REFERENCE       
            "'DMTF|Power Unit Global Table|001' 4"
    ::= { tPowerUnitGlobalTableTraps 4 }

powerUnitVAShutdownLimitExceeded NOTIFICATION-TYPE
    OBJECTS         { dmiEventDateTime, dmiCompId, dmiEventSeverity, 
                      dmiEventStateKey, dmiEventAssociatedGroup, 
                      dmtfPowerUnitGlobalEvSys, dmtfPowerUnitGlobalEvSub, 
                      a67PowerUnitIndex }
    STATUS          current
    DESCRIPTION     
            "Power Unit VA Shutdown Limit Exceeded"
    REFERENCE       
            "'DMTF|Power Unit Global Table|001' 5"
    ::= { tPowerUnitGlobalTableTraps 5 }

coolingUnitFanFullyRedundant NOTIFICATION-TYPE
    OBJECTS         { dmiEventDateTime, dmiCompId, dmiEventSeverity, 
                      dmiEventStateKey, dmiEventAssociatedGroup, 
                      dmtfCoolingUnitGlobalEvSys, 
                      dmtfCoolingUnitGlobalEvSub, a28CoolingUnitIndex }
    STATUS          current
    DESCRIPTION     
            "Fan Fully Redundant"
    REFERENCE       
            "'DMTF|Cooling Unit Global Table|001' 1"
    ::= { tCoolingUnitGlobalTableTraps 1 }

coolingUnitFanRedundancyLost NOTIFICATION-TYPE
    OBJECTS         { dmiEventDateTime, dmiCompId, dmiEventSeverity, 
                      dmiEventStateKey, dmiEventAssociatedGroup, 
                      dmtfCoolingUnitGlobalEvSys, 
                      dmtfCoolingUnitGlobalEvSub, a28CoolingUnitIndex }
    STATUS          current
    DESCRIPTION     
            "Fan Redundancy Lost"
    REFERENCE       
            "'DMTF|Cooling Unit Global Table|001' 2"
    ::= { tCoolingUnitGlobalTableTraps 2 }

coolingUnitFanRedundancyDegraded NOTIFICATION-TYPE
    OBJECTS         { dmiEventDateTime, dmiCompId, dmiEventSeverity, 
                      dmiEventStateKey, dmiEventAssociatedGroup, 
                      dmtfCoolingUnitGlobalEvSys, 
                      dmtfCoolingUnitGlobalEvSub, a28CoolingUnitIndex }
    STATUS          current
    DESCRIPTION     
            "Fan Redundancy Degraded"
    REFERENCE       
            "'DMTF|Cooling Unit Global Table|001' 3"
    ::= { tCoolingUnitGlobalTableTraps 3 }

coolingUnitFanSufficientResourcesFromRedundant NOTIFICATION-TYPE
    OBJECTS         { dmiEventDateTime, dmiCompId, dmiEventSeverity, 
                      dmiEventStateKey, dmiEventAssociatedGroup, 
                      dmtfCoolingUnitGlobalEvSys, 
                      dmtfCoolingUnitGlobalEvSub, a28CoolingUnitIndex }
    STATUS          current
    DESCRIPTION     
            "Fan Sufficient Resources From Redundant"
    REFERENCE       
            "'DMTF|Cooling Unit Global Table|001' 4"
    ::= { tCoolingUnitGlobalTableTraps 4 }

coolingUnitFanSufficientResourcesFromInsufficient NOTIFICATION-TYPE
    OBJECTS         { dmiEventDateTime, dmiCompId, dmiEventSeverity, 
                      dmiEventStateKey, dmiEventAssociatedGroup, 
                      dmtfCoolingUnitGlobalEvSys, 
                      dmtfCoolingUnitGlobalEvSub, a28CoolingUnitIndex }
    STATUS          current
    DESCRIPTION     
            "Fan Sufficient Resources From Insufficient"
    REFERENCE       
            "'DMTF|Cooling Unit Global Table|001' 5"
    ::= { tCoolingUnitGlobalTableTraps 5 }

coolingUnitFanNonRedundantInsufficientResources NOTIFICATION-TYPE
    OBJECTS         { dmiEventDateTime, dmiCompId, dmiEventSeverity, 
                      dmiEventStateKey, dmiEventAssociatedGroup, 
                      dmtfCoolingUnitGlobalEvSys, 
                      dmtfCoolingUnitGlobalEvSub, a28CoolingUnitIndex }
    STATUS          current
    DESCRIPTION     
            "Fan Non Redundant Insufficient Resources "
    REFERENCE       
            "'DMTF|Cooling Unit Global Table|001' 6"
    ::= { tCoolingUnitGlobalTableTraps 6 }

coolingUnitFanRedundancyDegradedFromFullyRedundant NOTIFICATION-TYPE
    OBJECTS         { dmiEventDateTime, dmiCompId, dmiEventSeverity, 
                      dmiEventStateKey, dmiEventAssociatedGroup, 
                      dmtfCoolingUnitGlobalEvSys, 
                      dmtfCoolingUnitGlobalEvSub, a28CoolingUnitIndex }
    STATUS          current
    DESCRIPTION     
            "Fan Redundancy Degraded From Fully Redundant"
    REFERENCE       
            "'DMTF|Cooling Unit Global Table|001' 7"
    ::= { tCoolingUnitGlobalTableTraps 7 }

coolingUnitFanRedundancyDegradedFromNonRedundant NOTIFICATION-TYPE
    OBJECTS         { dmiEventDateTime, dmiCompId, dmiEventSeverity, 
                      dmiEventStateKey, dmiEventAssociatedGroup, 
                      dmtfCoolingUnitGlobalEvSys, 
                      dmtfCoolingUnitGlobalEvSub, a28CoolingUnitIndex }
    STATUS          current
    DESCRIPTION     
            "Fan Redundancy Degraded From Non Redundant"
    REFERENCE       
            "'DMTF|Cooling Unit Global Table|001' 8"
    ::= { tCoolingUnitGlobalTableTraps 8 }

END -- end of module INTELCORPORATIONBASEBOARDMAPPERTRAP-MIB.
