--
-- This SMIv2 module has been generated by smidump 0.2-cvs. Do not edit.
--

SONUS-AAA-MIB DEFINITIONS ::= BEGIN

IMPORTS
    Counter32, Counter64, Gauge32, Integer32, IpAddress, MODULE-IDENTITY, 
    OBJECT-TYPE, Unsigned32
        FROM SNMPv2-SMI
    DateAndTime, RowStatus, TEXTUAL-CONVENTION, TruthValue
        FROM SNMPv2-TC
    sonusCommonSoftwarePlatformServicesMIBs
        FROM SONUS-SMI;

sonusAaaMIB MODULE-IDENTITY
    LAST-UPDATED    "201212310000Z"
    ORGANIZATION    
            "Ribbon Communications, Inc."
    CONTACT-INFO    
            "Customer Support        
             Ribbon Communications, Inc. 
             4 Technology Park Drive 
             Westford, MA 01886      
             USA                     
                                     
             Tel: 978-614-8100       
             Fax: 978-614-8609"
    DESCRIPTION     
            "The MIB Module for AAA Services."
    REVISION        "201212310000Z"
    DESCRIPTION     
            "Auto generated MIB."
    ::= { sonusCommonSoftwarePlatformServicesMIBs 18 }


ConfdString ::= TEXTUAL-CONVENTION
    DISPLAY-HINT    "1t"
    STATUS          current
    DESCRIPTION     
            "xs: and confd: types mapped to strings"
    SYNTAX          OCTET STRING

InetAddressIP ::= TEXTUAL-CONVENTION
    STATUS          current
    DESCRIPTION     
            "confd:inetAddressIP"
    SYNTAX          OCTET STRING (SIZE(4 | 16))

String ::= TEXTUAL-CONVENTION
    DISPLAY-HINT    "1t"
    STATUS          current
    DESCRIPTION     
            "xs:string"
    SYNTAX          OCTET STRING

SonusRsaKeyType ::= TEXTUAL-CONVENTION
    DISPLAY-HINT    "1t"
    STATUS          current
    DESCRIPTION     
            "
             Used to store the RSA key.
             "
    SYNTAX          OCTET STRING (SIZE(0..10240))

PasswordType ::= TEXTUAL-CONVENTION
    DISPLAY-HINT    "1t"
    STATUS          current
    DESCRIPTION     
            ""
    SYNTAX          OCTET STRING (SIZE(0..32))

sonusAAA OBJECT IDENTIFIER
    ::= { sonusAaaMIB 1 }

sonusAAAUserTable OBJECT-TYPE
    SYNTAX          SEQUENCE OF SonusAAAUserEntry
    MAX-ACCESS      not-accessible
    STATUS          obsolete
    DESCRIPTION     
            ""
    ::= { sonusAAA 1 }

sonusAAAUserEntry OBJECT-TYPE
    SYNTAX          SonusAAAUserEntry
    MAX-ACCESS      not-accessible
    STATUS          obsolete
    DESCRIPTION     
            ""
    INDEX           { sonusAAAUserName }
    ::= { sonusAAAUserTable 1 }

SonusAAAUserEntry ::=
    SEQUENCE {
        sonusAAAUserName                String,
        sonusAAAUserGroup               String,
        sonusAAAUserRowstatus           RowStatus
    }

sonusAAAUserName OBJECT-TYPE
    SYNTAX          String (SIZE(1..23))
    MAX-ACCESS      not-accessible
    STATUS          obsolete
    DESCRIPTION     
            "
             The name of the user.
             "
    ::= { sonusAAAUserEntry 1 }

sonusAAAUserGroup OBJECT-TYPE
    SYNTAX          String (SIZE(1..65535))
    MAX-ACCESS      read-create
    STATUS          obsolete
    DESCRIPTION     
            "
             The group that the user is a member of.
             "
    ::= { sonusAAAUserEntry 2 }

sonusAAAUserRowstatus OBJECT-TYPE
    SYNTAX          RowStatus
    MAX-ACCESS      read-create
    STATUS          obsolete
    DESCRIPTION     
            ""
    ::= { sonusAAAUserEntry 3 }

sonusAAAUserStatusTable OBJECT-TYPE
    SYNTAX          SEQUENCE OF SonusAAAUserStatusEntry
    MAX-ACCESS      not-accessible
    STATUS          current
    DESCRIPTION     
            ""
    ::= { sonusAAA 3 }

sonusAAAUserStatusEntry OBJECT-TYPE
    SYNTAX          SonusAAAUserStatusEntry
    MAX-ACCESS      not-accessible
    STATUS          current
    DESCRIPTION     
            ""
    INDEX           { sonusAAAUserStatusName }
    ::= { sonusAAAUserStatusTable 1 }

SonusAAAUserStatusEntry ::=
    SEQUENCE {
        sonusAAAUserStatusName          String,
        sonusAAAUserStatusCurrentStatus String,
        sonusAAAUserStatusUserId        Integer32
    }

sonusAAAUserStatusName OBJECT-TYPE
    SYNTAX          String (SIZE(0..23))
    MAX-ACCESS      not-accessible
    STATUS          current
    DESCRIPTION     
            "
             The name of the user.
             "
    ::= { sonusAAAUserStatusEntry 1 }

sonusAAAUserStatusCurrentStatus OBJECT-TYPE
    SYNTAX          String (SIZE(0..23))
    MAX-ACCESS      read-only
    STATUS          current
    DESCRIPTION     
            "
             The current status of the user.
             "
    ::= { sonusAAAUserStatusEntry 2 }

sonusAAAUserStatusUserId OBJECT-TYPE
    SYNTAX          Integer32
    MAX-ACCESS      read-only
    STATUS          current
    DESCRIPTION     
            "
             User ID
             "
    ::= { sonusAAAUserStatusEntry 3 }

END -- end of module SONUS-AAA-MIB.
