--
-- This SMIv1 module has been generated by smidump 0.2-cvs. Do not edit.
--

CRITAPP-MIB DEFINITIONS ::= BEGIN

IMPORTS
    OBJECT-TYPE
        FROM RFC-1212
    TRAP-TYPE
        FROM RFC-1215
    Counter
        FROM RFC1155-SMI
    snmpResearchMIBs
        FROM SNMP-RESEARCH-MIB
    DisplayString, RowStatus, TimeInterval, TimeStamp, TruthValue
        FROM SNMPv2-TC;

critApp OBJECT IDENTIFIER
    ::= { iso 3 6 1 4 1 99 12 29 }

-- critApp MODULE-IDENTITY
--     LAST-UPDATED    "199804061200Z"
--     ORGANIZATION    
--             "SNMP Research"
--     CONTACT-INFO    
--             "Postal: SNMP Research
--              3001 Kimberlin Heights Road
--              Knoxville, TN  37920
--              US
--              
--              Tel:    +1 865 579 3311
--              E-mail: info@int.snmp.com
--              WWW:    http://www.int.snmp.com"
--     DESCRIPTION     
--             "A set of object for managing critical application processes."
--     ::= { iso 3 6 1 4 1 99 12 29 }


CritAppCommandLine ::=
    OCTET STRING (SIZE(0..255))

-- CritAppCommandLine ::= TEXTUAL-CONVENTION
--     DISPLAY-HINT    "255a"
--     STATUS          mandatory
--     DESCRIPTION     
--             "Represents a command line used to invoke an external 
--              command.  It is a string containing the full path to
--              the binary as well as command line parameters.  It
--              will be passed to the standard command line shell of
--              the OS (e.g. using system(3) on Unix.)"
--     SYNTAX          OCTET STRING (SIZE(0..255))

critAppTable OBJECT IDENTIFIER
    ::= { critApp 1 }

critAppProcTable OBJECT-TYPE
    SYNTAX          SEQUENCE OF CritAppProcEntry
    ACCESS          not-accessible
    STATUS          mandatory
    DESCRIPTION     
            "A table describing critical processes."
    ::= { critAppTable 1 }

critAppProcEntry OBJECT-TYPE
    SYNTAX          CritAppProcEntry
    ACCESS          not-accessible
    STATUS          mandatory
    DESCRIPTION     
            "An entry in the critical process table."
    INDEX           { critAppIndex }
    ::= { critAppProcTable 1 }

CritAppProcEntry ::=
    SEQUENCE {
        critAppIndex                    INTEGER,
        critAppName                     DisplayString,
        critAppProcID                   INTEGER,
        critAppStartCommand             CritAppCommandLine,
        critAppTerminateCommand         CritAppCommandLine,
        critAppAdminStatus              INTEGER,
        critAppOperStatus               INTEGER,
        critAppRestartOnExit            TruthValue,
        critAppRestartInterval          TimeInterval,
        critAppLastRestart              TimeStamp,
        critAppRestarts                 Counter,
        critAppLastExitStatus           INTEGER,
        critAppTrapOnDown               TruthValue,
        critAppTrapOnUp                 TruthValue,
        critAppFindProc                 TruthValue,
        critAppRowStatus                RowStatus
    }

critAppIndex OBJECT-TYPE
    SYNTAX          INTEGER (1..2147483647)
    ACCESS          not-accessible
    STATUS          mandatory
    DESCRIPTION     
            "A numeric index for the critical application table."
    ::= { critAppProcEntry 1 }

critAppName OBJECT-TYPE
    SYNTAX          DisplayString
    ACCESS          read-write
    STATUS          mandatory
    DESCRIPTION     
            "The name of the application.  If critAppFindProc is true then
             this must be the last component of the execed pathname.
             Otherwise, it is arbitrary."
    ::= { critAppProcEntry 2 }

critAppProcID OBJECT-TYPE
    SYNTAX          INTEGER
    ACCESS          read-only
    STATUS          mandatory
    DESCRIPTION     
            "The process ID of the critical application, if running.
             0 indicates that the process is not currently running."
    DEFVAL          { 0 }
    ::= { critAppProcEntry 3 }

critAppStartCommand OBJECT-TYPE
    SYNTAX          CritAppCommandLine
    ACCESS          read-write
    STATUS          mandatory
    DESCRIPTION     
            "The command used in order to start the application."
    ::= { critAppProcEntry 4 }

critAppTerminateCommand OBJECT-TYPE
    SYNTAX          CritAppCommandLine
    ACCESS          read-write
    STATUS          mandatory
    DESCRIPTION     
            "The command used in order to terminate the application.
             At invocation time, the environment variable
             CRITAPP_PID will contain the process ID of the
             application to be terminated.  If the empty string is
             given, a reasonable default method is used for
             terminating the application."
    DEFVAL          { "" }
    ::= { critAppProcEntry 5 }

critAppAdminStatus OBJECT-TYPE
    SYNTAX          INTEGER { up(1), down(2) }
    ACCESS          read-write
    STATUS          mandatory
    DESCRIPTION     
            "This variable reflects whether the application is 
             supposed to be running (up) or not (down). By setting
             this variable, an attempt to start and/or terminate 
             the application according to this table:
             
               critApp       critApp   
             OperStatus    AdminStatus   attempted action
             ----------    -----------   ----------------
             down          up            start
             up            down          termination
             
             Otherwise, the set will have no effect.  Note that the
             critAppAdminStatus only reflects intended status and
             not actual status."
    ::= { critAppProcEntry 8 }

critAppOperStatus OBJECT-TYPE
    SYNTAX          INTEGER { up(1), down(2) }
    ACCESS          read-only
    STATUS          mandatory
    DESCRIPTION     
            "This variable indicates whether or not the application is
             actually running (up)or not running (down).  This variable 
             is read-only and is controlled by the implementing agent 
             based on the actual status of the application."
    ::= { critAppProcEntry 9 }

critAppRestartOnExit OBJECT-TYPE
    SYNTAX          TruthValue
    ACCESS          read-write
    STATUS          mandatory
    DESCRIPTION     
            "This variable determines whether or not the application
             should be restarted when it exits."
    ::= { critAppProcEntry 10 }

critAppRestartInterval OBJECT-TYPE
    SYNTAX          TimeInterval
    ACCESS          read-write
    STATUS          mandatory
    DESCRIPTION     
            "Automatic restarts of the application will be limited
             to one attempt within the time interval specified 
             by this variable."
    DEFVAL          { 500 }
    ::= { critAppProcEntry 12 }

critAppLastRestart OBJECT-TYPE
    SYNTAX          TimeStamp
    ACCESS          read-only
    STATUS          mandatory
    DESCRIPTION     
            "The value of sysUpTime.0 at the last time the application
             was started."
    DEFVAL          { 0 }
    ::= { critAppProcEntry 13 }

critAppRestarts OBJECT-TYPE
    SYNTAX          Counter
    ACCESS          read-only
    STATUS          mandatory
    DESCRIPTION     
            "The total number of times the application has been started."
    ::= { critAppProcEntry 14 }

critAppLastExitStatus OBJECT-TYPE
    SYNTAX          INTEGER
    ACCESS          read-only
    STATUS          mandatory
    DESCRIPTION     
            "The exit status of the application the last time it exited."
    DEFVAL          { 0 }
    ::= { critAppProcEntry 15 }

critAppTrapOnDown OBJECT-TYPE
    SYNTAX          TruthValue
    ACCESS          read-write
    STATUS          mandatory
    DESCRIPTION     
            "This value determines if a critAppDown trap should be sent
             whenever an application has gone down (exited.)"
    DEFVAL          { true }
    ::= { critAppProcEntry 16 }

critAppTrapOnUp OBJECT-TYPE
    SYNTAX          TruthValue
    ACCESS          read-write
    STATUS          mandatory
    DESCRIPTION     
            "This value determines if a critAppUp trap should be sent
             when an application has come up."
    DEFVAL          { false }
    ::= { critAppProcEntry 17 }

critAppFindProc OBJECT-TYPE
    SYNTAX          TruthValue
    ACCESS          read-write
    STATUS          mandatory
    DESCRIPTION     
            "This value determines if the critApp subagent attempts to
             locate a running copy of the program on startup rather than
             starting a new one."
    DEFVAL          { false }
    ::= { critAppProcEntry 19 }

critAppRowStatus OBJECT-TYPE
    SYNTAX          RowStatus
    ACCESS          read-write
    STATUS          mandatory
    DESCRIPTION     
            "A row status object for the critical application table."
    ::= { critAppProcEntry 25 }

critAppGlobals OBJECT IDENTIFIER
    ::= { critApp 2 }

critAppTrapWhenAllRunning OBJECT-TYPE
    SYNTAX          TruthValue
    ACCESS          read-write
    STATUS          mandatory
    DESCRIPTION     
            "This variable determines if a critAppAllRunningTrap
             should be send when all critical applications are
             up."
    ::= { critAppGlobals 1 }

critAppTrapWhenNotAllRunning OBJECT-TYPE
    SYNTAX          TruthValue
    ACCESS          read-write
    STATUS          mandatory
    DESCRIPTION     
            "This variable determines if a critAppNotAllRunningTrap
             should be send when at least one application is down."
    ::= { critAppGlobals 2 }

critAppTraps OBJECT IDENTIFIER
    ::= { critApp 3 }

critAppMIBGroups OBJECT IDENTIFIER
    ::= { critApp 4 }

critAppDown TRAP-TYPE
    ENTERPRISE      critAppTraps
    VARIABLES       { critAppName, critAppProcID, critAppLastExitStatus }
--     STATUS          mandatory
    DESCRIPTION     
            "This trap means that the application corresponding to
             critAppIndex changed status to down (exited.)"
    ::= 1

critAppUp TRAP-TYPE
    ENTERPRISE      critAppTraps
    VARIABLES       { critAppName, critAppProcID }
--     STATUS          mandatory
    DESCRIPTION     
            "This trap means that the application corresponding to
             critAppIndex changed status to up."
    ::= 2

critAppAllRunning TRAP-TYPE
    ENTERPRISE      critAppTraps
--     STATUS          mandatory
    DESCRIPTION     
            "This trap means that all applications are up."
    ::= 4

critAppNotAllRunning TRAP-TYPE
    ENTERPRISE      critAppTraps
--     STATUS          mandatory
    DESCRIPTION     
            "This trap means that at least one applications is
             down."
    ::= 5

critAppLeafObjects OBJECT IDENTIFIER
    ::= { critAppMIBGroups 1 }

-- critAppLeafObjects OBJECT-GROUP
--     OBJECTS         { critAppName, critAppProcID, critAppStartCommand, 
--                       critAppTerminateCommand, critAppAdminStatus, 
--                       critAppOperStatus, critAppRestartOnExit, 
--                       critAppRestartInterval, critAppLastRestart, 
--                       critAppRestarts, critAppLastExitStatus, 
--                       critAppTrapOnDown, critAppTrapOnUp, 
--                       critAppFindProc, critAppRowStatus, 
--                       critAppTrapWhenAllRunning, 
--                       critAppTrapWhenNotAllRunning }
--     STATUS          mandatory
--     DESCRIPTION     
--             "Leaf objects of the critApp MIB"
--     ::= { critAppMIBGroups 1 }

END -- end of module CRITAPP-MIB.
