--
-- This SMIv2 module has been generated by smidump 0.2-cvs. Do not edit.
--

SONUS-SOFTSWITCH-DIMA-MIB DEFINITIONS ::= BEGIN

IMPORTS
    Counter32, MODULE-IDENTITY, NOTIFICATION-TYPE, OBJECT-TYPE
        FROM SNMPv2-SMI
    sonusEventClass, sonusEventDescription, sonusEventLevel, 
    sonusEventTime
        FROM SONUS-COMMON-MIB
    sonusServicesMIBs
        FROM SONUS-SMI;

sonusSoftSwitchDIMAMIB MODULE-IDENTITY
    LAST-UPDATED    "200707100000Z"
    ORGANIZATION    
            "Sonus Networks, Inc."
    CONTACT-INFO    
            "   Customer Support    
             Sonus Networks, Inc.
             7 Technology Park Drive
             Westford, MA 01886
             USA
             
             Tel: 978-614-8100
             Fax: 978-614-8609"
    DESCRIPTION     
            "The MIB Module for the Diameter Agent."
    ::= { sonusServicesMIBs 31 }


sonusSoftSwitchDIMAMIBObjects OBJECT IDENTIFIER
    ::= { sonusSoftSwitchDIMAMIB 1 }

sonusSoftSwitchDIMAMIBNotifications OBJECT IDENTIFIER
    ::= { sonusSoftSwitchDIMAMIB 2 }

sonusSoftSwitchDIMAMIBNotificationsPrefix OBJECT IDENTIFIER
    ::= { sonusSoftSwitchDIMAMIBNotifications 0 }

sonusSoftSwitchDIMAMIBNotificationsObjects OBJECT IDENTIFIER
    ::= { sonusSoftSwitchDIMAMIBNotifications 1 }

sonusSoftSwitchDIMADiameterPeerName OBJECT-TYPE
    SYNTAX          OCTET STRING
    MAX-ACCESS      read-only
    STATUS          current
    DESCRIPTION     
            "Diameter Peer Name."
    ::= { sonusSoftSwitchDIMAMIBNotificationsObjects 1 }

sonusSoftSwitchDIMAMIBCounters OBJECT IDENTIFIER
    ::= { sonusSoftSwitchDIMAMIB 3 }

sonusSoftSwitchDIMAStdDiameterMesgSent OBJECT-TYPE
    SYNTAX          Counter32
    MAX-ACCESS      read-only
    STATUS          current
    DESCRIPTION     
            "Number of messages sent to Standard Diameter Peers."
    ::= { sonusSoftSwitchDIMAMIBCounters 1 }

sonusSoftSwitchDIMAStdDiameterMesgRcvd OBJECT-TYPE
    SYNTAX          Counter32
    MAX-ACCESS      read-only
    STATUS          current
    DESCRIPTION     
            "Number of messages received from Standard Diameter Peers."
    ::= { sonusSoftSwitchDIMAMIBCounters 2 }

sonusSoftSwitchDIMAMesgSentToPES OBJECT-TYPE
    SYNTAX          Counter32
    MAX-ACCESS      read-only
    STATUS          current
    DESCRIPTION     
            "Number of messages sent to PES."
    ::= { sonusSoftSwitchDIMAMIBCounters 3 }

sonusSoftSwitchDIMAMesgRcvdFromPES OBJECT-TYPE
    SYNTAX          Counter32
    MAX-ACCESS      read-only
    STATUS          current
    DESCRIPTION     
            "Number of messages received from PES."
    ::= { sonusSoftSwitchDIMAMIBCounters 4 }

sonusSoftSwitchDIMAMesgSentToSCPA OBJECT-TYPE
    SYNTAX          Counter32
    MAX-ACCESS      read-only
    STATUS          current
    DESCRIPTION     
            "Number of messages sent to SCPA."
    ::= { sonusSoftSwitchDIMAMIBCounters 5 }

sonusSoftSwitchDIMAMesgRcvdFromSCPA OBJECT-TYPE
    SYNTAX          Counter32
    MAX-ACCESS      read-only
    STATUS          current
    DESCRIPTION     
            "Number of messages received from SCPA."
    ::= { sonusSoftSwitchDIMAMIBCounters 6 }

sonusSoftSwitchDIMADownNotification NOTIFICATION-TYPE
    OBJECTS         { sonusEventDescription, sonusEventClass, 
                      sonusEventLevel, sonusEventTime }
    STATUS          current
    DESCRIPTION     
            "DIMA shutdown event."
    ::= { sonusSoftSwitchDIMAMIBNotificationsPrefix 1 }

sonusSoftSwitchDIMAUpNotification NOTIFICATION-TYPE
    OBJECTS         { sonusEventDescription, sonusEventClass, 
                      sonusEventLevel, sonusEventTime }
    STATUS          current
    DESCRIPTION     
            "DIMA startup event"
    ::= { sonusSoftSwitchDIMAMIBNotificationsPrefix 2 }

sonusSoftSwitchDIMADiameterPeerOpenNotification NOTIFICATION-TYPE
    OBJECTS         { sonusSoftSwitchDIMADiameterPeerName, 
                      sonusEventDescription, sonusEventClass, 
                      sonusEventLevel, sonusEventTime }
    STATUS          current
    DESCRIPTION     
            "Connection to a Standard Diameter peer is opened."
    ::= { sonusSoftSwitchDIMAMIBNotificationsPrefix 3 }

sonusSoftSwitchDIMADiameterPeerCloseNotification NOTIFICATION-TYPE
    OBJECTS         { sonusSoftSwitchDIMADiameterPeerName, 
                      sonusEventDescription, sonusEventClass, 
                      sonusEventLevel, sonusEventTime }
    STATUS          current
    DESCRIPTION     
            "Connection to a Standard Diameter peer is closed."
    ::= { sonusSoftSwitchDIMAMIBNotificationsPrefix 4 }

END -- end of module SONUS-SOFTSWITCH-DIMA-MIB.
