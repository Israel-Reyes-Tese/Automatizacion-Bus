--
-- This SMIv2 module has been generated by smidump 0.2-cvs. Do not edit.
--

SONUS-LDAP-MIB DEFINITIONS ::= BEGIN

IMPORTS
    Counter32, Counter64, Gauge32, Integer32, IpAddress, MODULE-IDENTITY, 
    OBJECT-TYPE, Unsigned32
        FROM SNMPv2-SMI
    DateAndTime, RowStatus, TEXTUAL-CONVENTION, TruthValue
        FROM SNMPv2-TC
    sonusCommonSoftwarePlatformServicesMIBs
        FROM SONUS-SMI;

sonusLdapMIB MODULE-IDENTITY
    LAST-UPDATED    "201212310000Z"
    ORGANIZATION    
            "Ribbon Communications, Inc."
    CONTACT-INFO    
            "Customer Support        
             Ribbon Communications, Inc. 
             4 Technology Park Drive 
             Westford, MA 01886      
             USA                     
                                     
             Tel: 978-614-8100       
             Fax: 978-614-8609"
    DESCRIPTION     
            "The MIB Module for LDAP Authentication Server Management."
    REVISION        "201212310000Z"
    DESCRIPTION     
            "Auto generated MIB."
    ::= { sonusCommonSoftwarePlatformServicesMIBs 27 }


Byte ::= TEXTUAL-CONVENTION
    DISPLAY-HINT    "d"
    STATUS          current
    DESCRIPTION     
            "xs:byte"
    SYNTAX          Integer32 (-128..127)

UnsignedByte ::= TEXTUAL-CONVENTION
    DISPLAY-HINT    "d"
    STATUS          current
    DESCRIPTION     
            "xs:unsignedByte"
    SYNTAX          Unsigned32 (0..255)

UnsignedShort ::= TEXTUAL-CONVENTION
    DISPLAY-HINT    "d"
    STATUS          current
    DESCRIPTION     
            "xs:unsignedShort"
    SYNTAX          Unsigned32 (0..65535)

InetAddressIP ::= TEXTUAL-CONVENTION
    STATUS          current
    DESCRIPTION     
            "confd:inetAddressIP"
    SYNTAX          OCTET STRING (SIZE(4 | 16))

String ::= TEXTUAL-CONVENTION
    DISPLAY-HINT    "1t"
    STATUS          current
    DESCRIPTION     
            "xs:string"
    SYNTAX          OCTET STRING

SonusOosDurationType ::= TEXTUAL-CONVENTION
    STATUS          current
    DESCRIPTION     
            ""
    SYNTAX          Unsigned32 (0..300)

LdapTransportType ::= TEXTUAL-CONVENTION
    STATUS          current
    DESCRIPTION     
            ""
    SYNTAX          INTEGER { tcp(1), ssltls(2) }

SonusRetryTimeType ::= TEXTUAL-CONVENTION
    STATUS          current
    DESCRIPTION     
            ""
    SYNTAX          Integer32 (500..3000)

LdapSaslMechanismType ::= TEXTUAL-CONVENTION
    STATUS          current
    DESCRIPTION     
            ""
    SYNTAX          INTEGER { plain(1) }

SonusLdapStatusType ::= TEXTUAL-CONVENTION
    STATUS          current
    DESCRIPTION     
            ""
    SYNTAX          INTEGER { unavailable(1), available(2) }

SonusLdapAvailableTimeType ::= TEXTUAL-CONVENTION
    DISPLAY-HINT    "1t"
    STATUS          current
    DESCRIPTION     
            ""
    SYNTAX          OCTET STRING (SIZE(0..255))

SonusLdapServerPriorityType ::= TEXTUAL-CONVENTION
    STATUS          current
    DESCRIPTION     
            ""
    SYNTAX          Integer32 (1..3)

LdapBindType ::= TEXTUAL-CONVENTION
    STATUS          current
    DESCRIPTION     
            ""
    SYNTAX          INTEGER { simple(1), sasl(2) }

SonusRetryCountType ::= TEXTUAL-CONVENTION
    DISPLAY-HINT    "d"
    STATUS          current
    DESCRIPTION     
            ""
    SYNTAX          Integer32 (1..3)

sonusLdapAuthentication OBJECT IDENTIFIER
    ::= { sonusLdapMIB 1 }

sonusLdapAuthenticationLdapServerTable OBJECT-TYPE
    SYNTAX          SEQUENCE OF SonusLdapAuthenticationLdapServerEntry
    MAX-ACCESS      not-accessible
    STATUS          current
    DESCRIPTION     
            " Per-server configuration."
    ::= { sonusLdapAuthentication 1 }

sonusLdapAuthenticationLdapServerEntry OBJECT-TYPE
    SYNTAX          SonusLdapAuthenticationLdapServerEntry
    MAX-ACCESS      not-accessible
    STATUS          current
    DESCRIPTION     
            ""
    INDEX           { sonusLdapAuthenticationLdapServerServerName }
    ::= { sonusLdapAuthenticationLdapServerTable 1 }

SonusLdapAuthenticationLdapServerEntry ::=
    SEQUENCE {
        sonusLdapAuthenticationLdapServerServerName           String,
        sonusLdapAuthenticationLdapServerPriority         SonusLdapServerPriorityType,
        sonusLdapAuthenticationLdapServerState      INTEGER,
        sonusLdapAuthenticationLdapServerBindMethod           LdapBindType,
        sonusLdapAuthenticationLdapServerSaslMechanism              LdapSaslMechanismType,
        sonusLdapAuthenticationLdapServerTransport          LdapTransportType,
        sonusLdapAuthenticationLdapServerBinddn       String,
        sonusLdapAuthenticationLdapServerSearchbase           String,
        sonusLdapAuthenticationLdapServerLdapServerAddress                  InetAddressIP,
        sonusLdapAuthenticationLdapServerLdapServerPort               UnsignedShort,
        sonusLdapAuthenticationLdapServerGroupNameAttribute                   String,
        sonusLdapAuthenticationLdapServerStatus       UnsignedByte,
        sonusLdapAuthenticationLdapServerUnAvailableFrom                DateAndTime
    }

sonusLdapAuthenticationLdapServerServerName OBJECT-TYPE
    SYNTAX          String (SIZE(0..23))
    MAX-ACCESS      not-accessible
    STATUS          current
    DESCRIPTION     
            "The name used to reference this server"
    ::= { sonusLdapAuthenticationLdapServerEntry 1 }

sonusLdapAuthenticationLdapServerPriority OBJECT-TYPE
    SYNTAX          SonusLdapServerPriorityType
    MAX-ACCESS      read-write
    STATUS          current
    DESCRIPTION     
            "A lower numerical value implies a higher priority will be given for selecting the server."
    ::= { sonusLdapAuthenticationLdapServerEntry 2 }

sonusLdapAuthenticationLdapServerState OBJECT-TYPE
    SYNTAX          INTEGER { disabled(1), enabled(2) }
    MAX-ACCESS      read-write
    STATUS          current
    DESCRIPTION     
            "The administrative state of the Ldap server."
    ::= { sonusLdapAuthenticationLdapServerEntry 3 }

sonusLdapAuthenticationLdapServerBindMethod OBJECT-TYPE
    SYNTAX          LdapBindType
    MAX-ACCESS      read-write
    STATUS          current
    DESCRIPTION     
            "The administrative state of the Ldap server."
    DEFVAL          { simple }
    ::= { sonusLdapAuthenticationLdapServerEntry 4 }

sonusLdapAuthenticationLdapServerSaslMechanism OBJECT-TYPE
    SYNTAX          LdapSaslMechanismType
    MAX-ACCESS      read-write
    STATUS          current
    DESCRIPTION     
            "The administrative state of the Ldap server."
    DEFVAL          { plain }
    ::= { sonusLdapAuthenticationLdapServerEntry 5 }

sonusLdapAuthenticationLdapServerTransport OBJECT-TYPE
    SYNTAX          LdapTransportType
    MAX-ACCESS      read-write
    STATUS          current
    DESCRIPTION     
            "The transport type to use"
    DEFVAL          { tcp }
    ::= { sonusLdapAuthenticationLdapServerEntry 6 }

sonusLdapAuthenticationLdapServerBinddn OBJECT-TYPE
    SYNTAX          String (SIZE(0..255))
    MAX-ACCESS      read-write
    STATUS          current
    DESCRIPTION     
            "The distinguished name to use for the bind operation( only used for simple binds)"
    ::= { sonusLdapAuthenticationLdapServerEntry 7 }

sonusLdapAuthenticationLdapServerSearchbase OBJECT-TYPE
    SYNTAX          String (SIZE(0..255))
    MAX-ACCESS      read-write
    STATUS          current
    DESCRIPTION     
            "The base for the LDAP query"
    ::= { sonusLdapAuthenticationLdapServerEntry 8 }

sonusLdapAuthenticationLdapServerLdapServerAddress OBJECT-TYPE
    SYNTAX          InetAddressIP
    MAX-ACCESS      read-write
    STATUS          current
    DESCRIPTION     
            "The IPv4 or IPv6 ipaddress of the server as either a hostname, an IPv4 address in dot notation, or an IPv6 address in hex-colon notation."
    ::= { sonusLdapAuthenticationLdapServerEntry 9 }

sonusLdapAuthenticationLdapServerLdapServerPort OBJECT-TYPE
    SYNTAX          UnsignedShort (1..65535)
    MAX-ACCESS      read-write
    STATUS          current
    DESCRIPTION     
            "The ldap server IP port used for authentication."
    ::= { sonusLdapAuthenticationLdapServerEntry 10 }

sonusLdapAuthenticationLdapServerGroupNameAttribute OBJECT-TYPE
    SYNTAX          String (SIZE(0..255))
    MAX-ACCESS      read-write
    STATUS          current
    DESCRIPTION     
            "The attribute in the user record that contains the cli group name. If empty, the ldapFilters table is used."
    ::= { sonusLdapAuthenticationLdapServerEntry 11 }

sonusLdapAuthenticationLdapServerStatus OBJECT-TYPE
    SYNTAX          UnsignedByte
    MAX-ACCESS      read-only
    STATUS          current
    DESCRIPTION     
            "The status field updated by ldapAuthentication module."
    DEFVAL          { 2 }
    ::= { sonusLdapAuthenticationLdapServerEntry 12 }

sonusLdapAuthenticationLdapServerUnAvailableFrom OBJECT-TYPE
    SYNTAX          DateAndTime
    MAX-ACCESS      read-only
    STATUS          current
    DESCRIPTION     
            "The time at which server was marked unavailable."
    ::= { sonusLdapAuthenticationLdapServerEntry 13 }

sonusLdapAuthenticationRetryCriteria OBJECT IDENTIFIER
    ::= { sonusLdapAuthentication 4 }

sonusLdapAuthenticationRetryCriteriaRetryTimer OBJECT-TYPE
    SYNTAX          SonusRetryTimeType
    MAX-ACCESS      read-write
    STATUS          current
    DESCRIPTION     
            "Time in milliseconds before retry. "
    ::= { sonusLdapAuthenticationRetryCriteria 1 }

sonusLdapAuthenticationRetryCriteriaRetryCount OBJECT-TYPE
    SYNTAX          SonusRetryCountType
    MAX-ACCESS      read-write
    STATUS          current
    DESCRIPTION     
            " Number of retries. "
    ::= { sonusLdapAuthenticationRetryCriteria 2 }

sonusLdapAuthenticationRetryCriteriaOosDuration OBJECT-TYPE
    SYNTAX          SonusOosDurationType
    MAX-ACCESS      read-write
    STATUS          current
    DESCRIPTION     
            " Time in minutes the Ldap server will stay OOS. "
    ::= { sonusLdapAuthenticationRetryCriteria 3 }

sonusLdapAuthenticationLdapStatusTable OBJECT-TYPE
    SYNTAX          SEQUENCE OF SonusLdapAuthenticationLdapStatusEntry
    MAX-ACCESS      not-accessible
    STATUS          current
    DESCRIPTION     
            "
             The status of the Ldap server.
             "
    ::= { sonusLdapAuthentication 5 }

sonusLdapAuthenticationLdapStatusEntry OBJECT-TYPE
    SYNTAX          SonusLdapAuthenticationLdapStatusEntry
    MAX-ACCESS      not-accessible
    STATUS          current
    DESCRIPTION     
            ""
    INDEX           { IMPLIED 
                      sonusLdapAuthenticationLdapStatusServerNameId }
    ::= { sonusLdapAuthenticationLdapStatusTable 1 }

SonusLdapAuthenticationLdapStatusEntry ::=
    SEQUENCE {
        sonusLdapAuthenticationLdapStatusServerNameId             String,
        sonusLdapAuthenticationLdapStatusStatus       SonusLdapStatusType,
        sonusLdapAuthenticationLdapStatusAvailableAt            SonusLdapAvailableTimeType
    }

sonusLdapAuthenticationLdapStatusServerNameId OBJECT-TYPE
    SYNTAX          String (SIZE(0..255))
    MAX-ACCESS      not-accessible
    STATUS          current
    DESCRIPTION     
            "The current status of a specific Ldap server."
    ::= { sonusLdapAuthenticationLdapStatusEntry 1 }

sonusLdapAuthenticationLdapStatusStatus OBJECT-TYPE
    SYNTAX          SonusLdapStatusType
    MAX-ACCESS      read-only
    STATUS          current
    DESCRIPTION     
            "The actual status of the Ldap server."
    ::= { sonusLdapAuthenticationLdapStatusEntry 2 }

sonusLdapAuthenticationLdapStatusAvailableAt OBJECT-TYPE
    SYNTAX          SonusLdapAvailableTimeType
    MAX-ACCESS      read-only
    STATUS          current
    DESCRIPTION     
            "The time when the server will automatically be put back into available state."
    ::= { sonusLdapAuthenticationLdapStatusEntry 3 }

END -- end of module SONUS-LDAP-MIB.
