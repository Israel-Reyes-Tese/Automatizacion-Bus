--
-- This SMIv1 module has been generated by smidump 0.2-cvs. Do not edit.
--

SONUS-LDAP-MIB DEFINITIONS ::= BEGIN

IMPORTS
    OBJECT-TYPE
        FROM RFC-1212
    Counter, Gauge, IpAddress
        FROM RFC1155-SMI
    DateAndTime
        FROM SNMPv2-TC
    sonusCommonSoftwarePlatformServicesMIBs
        FROM SONUS-SMI;

sonusLdapMIB OBJECT IDENTIFIER
    ::= { sonusCommonSoftwarePlatformServicesMIBs 27 }

-- sonusLdapMIB MODULE-IDENTITY
--     LAST-UPDATED    "201212310000Z"
--     ORGANIZATION    
--             "Ribbon Communications, Inc."
--     CONTACT-INFO    
--             "Customer Support        
--              Ribbon Communications, Inc. 
--              4 Technology Park Drive 
--              Westford, MA 01886      
--              USA                     
--                                      
--              Tel: 978-614-8100       
--              Fax: 978-614-8609"
--     DESCRIPTION     
--             "The MIB Module for LDAP Authentication Server Management."
--     REVISION        "201212310000Z"
--     DESCRIPTION     
--             "Auto generated MIB."
--     ::= { sonusCommonSoftwarePlatformServicesMIBs 27 }


Byte ::=
    INTEGER (-128..127)

-- Byte ::= TEXTUAL-CONVENTION
--     DISPLAY-HINT    "d"
--     STATUS          mandatory
--     DESCRIPTION     
--             "xs:byte"
--     SYNTAX          INTEGER (-128..127)

UnsignedByte ::=
    Gauge (0..255)

-- UnsignedByte ::= TEXTUAL-CONVENTION
--     DISPLAY-HINT    "d"
--     STATUS          mandatory
--     DESCRIPTION     
--             "xs:unsignedByte"
--     SYNTAX          Gauge (0..255)

UnsignedShort ::=
    Gauge (0..65535)

-- UnsignedShort ::= TEXTUAL-CONVENTION
--     DISPLAY-HINT    "d"
--     STATUS          mandatory
--     DESCRIPTION     
--             "xs:unsignedShort"
--     SYNTAX          Gauge (0..65535)

InetAddressIP ::=
    OCTET STRING (SIZE(4 | 16))

-- InetAddressIP ::= TEXTUAL-CONVENTION
--     STATUS          mandatory
--     DESCRIPTION     
--             "confd:inetAddressIP"
--     SYNTAX          OCTET STRING (SIZE(4 | 16))

String ::=
    OCTET STRING

-- String ::= TEXTUAL-CONVENTION
--     DISPLAY-HINT    "1t"
--     STATUS          mandatory
--     DESCRIPTION     
--             "xs:string"
--     SYNTAX          OCTET STRING

SonusOosDurationType ::=
    Gauge (0..300)

-- SonusOosDurationType ::= TEXTUAL-CONVENTION
--     STATUS          mandatory
--     DESCRIPTION     
--             ""
--     SYNTAX          Gauge (0..300)

LdapTransportType ::=
    INTEGER { tcp(1), ssltls(2) }

-- LdapTransportType ::= TEXTUAL-CONVENTION
--     STATUS          mandatory
--     DESCRIPTION     
--             ""
--     SYNTAX          INTEGER
--                       { tcp(1), ssltls(2) }

SonusRetryTimeType ::=
    INTEGER (500..3000)

-- SonusRetryTimeType ::= TEXTUAL-CONVENTION
--     STATUS          mandatory
--     DESCRIPTION     
--             ""
--     SYNTAX          INTEGER (500..3000)

LdapSaslMechanismType ::=
    INTEGER { plain(1) }

-- LdapSaslMechanismType ::= TEXTUAL-CONVENTION
--     STATUS          mandatory
--     DESCRIPTION     
--             ""
--     SYNTAX          INTEGER
--                       { plain(1) }

SonusLdapStatusType ::=
    INTEGER { unavailable(1), available(2) }

-- SonusLdapStatusType ::= TEXTUAL-CONVENTION
--     STATUS          mandatory
--     DESCRIPTION     
--             ""
--     SYNTAX          INTEGER
--                       { unavailable(1), available(2) }

SonusLdapAvailableTimeType ::=
    OCTET STRING (SIZE(0..255))

-- SonusLdapAvailableTimeType ::= TEXTUAL-CONVENTION
--     DISPLAY-HINT    "1t"
--     STATUS          mandatory
--     DESCRIPTION     
--             ""
--     SYNTAX          OCTET STRING (SIZE(0..255))

SonusLdapServerPriorityType ::=
    INTEGER (1..3)

-- SonusLdapServerPriorityType ::= TEXTUAL-CONVENTION
--     STATUS          mandatory
--     DESCRIPTION     
--             ""
--     SYNTAX          INTEGER (1..3)

LdapBindType ::=
    INTEGER { simple(1), sasl(2) }

-- LdapBindType ::= TEXTUAL-CONVENTION
--     STATUS          mandatory
--     DESCRIPTION     
--             ""
--     SYNTAX          INTEGER
--                       { simple(1), sasl(2) }

SonusRetryCountType ::=
    INTEGER (1..3)

-- SonusRetryCountType ::= TEXTUAL-CONVENTION
--     DISPLAY-HINT    "d"
--     STATUS          mandatory
--     DESCRIPTION     
--             ""
--     SYNTAX          INTEGER (1..3)

sonusLdapAuthentication OBJECT IDENTIFIER
    ::= { sonusLdapMIB 1 }

sonusLdapAuthenticationLdapServerTable OBJECT-TYPE
    SYNTAX          SEQUENCE OF SonusLdapAuthenticationLdapServerEntry
    ACCESS          not-accessible
    STATUS          mandatory
    DESCRIPTION     
            " Per-server configuration."
    ::= { sonusLdapAuthentication 1 }

sonusLdapAuthenticationLdapServerEntry OBJECT-TYPE
    SYNTAX          SonusLdapAuthenticationLdapServerEntry
    ACCESS          not-accessible
    STATUS          mandatory
    DESCRIPTION     
            ""
    INDEX           { sonusLdapAuthenticationLdapServerServerName }
    ::= { sonusLdapAuthenticationLdapServerTable 1 }

SonusLdapAuthenticationLdapServerEntry ::=
    SEQUENCE {
        sonusLdapAuthenticationLdapServerServerName           String,
        sonusLdapAuthenticationLdapServerPriority         SonusLdapServerPriorityType,
        sonusLdapAuthenticationLdapServerState      INTEGER,
        sonusLdapAuthenticationLdapServerBindMethod           LdapBindType,
        sonusLdapAuthenticationLdapServerSaslMechanism              LdapSaslMechanismType,
        sonusLdapAuthenticationLdapServerTransport          LdapTransportType,
        sonusLdapAuthenticationLdapServerBinddn       String,
        sonusLdapAuthenticationLdapServerSearchbase           String,
        sonusLdapAuthenticationLdapServerLdapServerAddress                  InetAddressIP,
        sonusLdapAuthenticationLdapServerLdapServerPort               UnsignedShort,
        sonusLdapAuthenticationLdapServerGroupNameAttribute                   String,
        sonusLdapAuthenticationLdapServerStatus       UnsignedByte,
        sonusLdapAuthenticationLdapServerUnAvailableFrom                DateAndTime
    }

sonusLdapAuthenticationLdapServerServerName OBJECT-TYPE
    SYNTAX          String (SIZE(0..23))
    ACCESS          not-accessible
    STATUS          mandatory
    DESCRIPTION     
            "The name used to reference this server"
    ::= { sonusLdapAuthenticationLdapServerEntry 1 }

sonusLdapAuthenticationLdapServerPriority OBJECT-TYPE
    SYNTAX          SonusLdapServerPriorityType
    ACCESS          read-write
    STATUS          mandatory
    DESCRIPTION     
            "A lower numerical value implies a higher priority will be given for selecting the server."
    ::= { sonusLdapAuthenticationLdapServerEntry 2 }

sonusLdapAuthenticationLdapServerState OBJECT-TYPE
    SYNTAX          INTEGER { disabled(1), enabled(2) }
    ACCESS          read-write
    STATUS          mandatory
    DESCRIPTION     
            "The administrative state of the Ldap server."
    ::= { sonusLdapAuthenticationLdapServerEntry 3 }

sonusLdapAuthenticationLdapServerBindMethod OBJECT-TYPE
    SYNTAX          LdapBindType
    ACCESS          read-write
    STATUS          mandatory
    DESCRIPTION     
            "The administrative state of the Ldap server."
    DEFVAL          { simple }
    ::= { sonusLdapAuthenticationLdapServerEntry 4 }

sonusLdapAuthenticationLdapServerSaslMechanism OBJECT-TYPE
    SYNTAX          LdapSaslMechanismType
    ACCESS          read-write
    STATUS          mandatory
    DESCRIPTION     
            "The administrative state of the Ldap server."
    DEFVAL          { plain }
    ::= { sonusLdapAuthenticationLdapServerEntry 5 }

sonusLdapAuthenticationLdapServerTransport OBJECT-TYPE
    SYNTAX          LdapTransportType
    ACCESS          read-write
    STATUS          mandatory
    DESCRIPTION     
            "The transport type to use"
    DEFVAL          { tcp }
    ::= { sonusLdapAuthenticationLdapServerEntry 6 }

sonusLdapAuthenticationLdapServerBinddn OBJECT-TYPE
    SYNTAX          String (SIZE(0..255))
    ACCESS          read-write
    STATUS          mandatory
    DESCRIPTION     
            "The distinguished name to use for the bind operation( only used for simple binds)"
    ::= { sonusLdapAuthenticationLdapServerEntry 7 }

sonusLdapAuthenticationLdapServerSearchbase OBJECT-TYPE
    SYNTAX          String (SIZE(0..255))
    ACCESS          read-write
    STATUS          mandatory
    DESCRIPTION     
            "The base for the LDAP query"
    ::= { sonusLdapAuthenticationLdapServerEntry 8 }

sonusLdapAuthenticationLdapServerLdapServerAddress OBJECT-TYPE
    SYNTAX          InetAddressIP
    ACCESS          read-write
    STATUS          mandatory
    DESCRIPTION     
            "The IPv4 or IPv6 ipaddress of the server as either a hostname, an IPv4 address in dot notation, or an IPv6 address in hex-colon notation."
    ::= { sonusLdapAuthenticationLdapServerEntry 9 }

sonusLdapAuthenticationLdapServerLdapServerPort OBJECT-TYPE
    SYNTAX          UnsignedShort (1..65535)
    ACCESS          read-write
    STATUS          mandatory
    DESCRIPTION     
            "The ldap server IP port used for authentication."
    ::= { sonusLdapAuthenticationLdapServerEntry 10 }

sonusLdapAuthenticationLdapServerGroupNameAttribute OBJECT-TYPE
    SYNTAX          String (SIZE(0..255))
    ACCESS          read-write
    STATUS          mandatory
    DESCRIPTION     
            "The attribute in the user record that contains the cli group name. If empty, the ldapFilters table is used."
    ::= { sonusLdapAuthenticationLdapServerEntry 11 }

sonusLdapAuthenticationLdapServerStatus OBJECT-TYPE
    SYNTAX          UnsignedByte
    ACCESS          read-only
    STATUS          mandatory
    DESCRIPTION     
            "The status field updated by ldapAuthentication module."
    DEFVAL          { 2 }
    ::= { sonusLdapAuthenticationLdapServerEntry 12 }

sonusLdapAuthenticationLdapServerUnAvailableFrom OBJECT-TYPE
    SYNTAX          DateAndTime
    ACCESS          read-only
    STATUS          mandatory
    DESCRIPTION     
            "The time at which server was marked unavailable."
    ::= { sonusLdapAuthenticationLdapServerEntry 13 }

sonusLdapAuthenticationRetryCriteria OBJECT IDENTIFIER
    ::= { sonusLdapAuthentication 4 }

sonusLdapAuthenticationRetryCriteriaRetryTimer OBJECT-TYPE
    SYNTAX          SonusRetryTimeType
    ACCESS          read-write
    STATUS          mandatory
    DESCRIPTION     
            "Time in milliseconds before retry. "
    ::= { sonusLdapAuthenticationRetryCriteria 1 }

sonusLdapAuthenticationRetryCriteriaRetryCount OBJECT-TYPE
    SYNTAX          SonusRetryCountType
    ACCESS          read-write
    STATUS          mandatory
    DESCRIPTION     
            " Number of retries. "
    ::= { sonusLdapAuthenticationRetryCriteria 2 }

sonusLdapAuthenticationRetryCriteriaOosDuration OBJECT-TYPE
    SYNTAX          SonusOosDurationType
    ACCESS          read-write
    STATUS          mandatory
    DESCRIPTION     
            " Time in minutes the Ldap server will stay OOS. "
    ::= { sonusLdapAuthenticationRetryCriteria 3 }

sonusLdapAuthenticationLdapStatusTable OBJECT-TYPE
    SYNTAX          SEQUENCE OF SonusLdapAuthenticationLdapStatusEntry
    ACCESS          not-accessible
    STATUS          mandatory
    DESCRIPTION     
            "
             The status of the Ldap server.
             "
    ::= { sonusLdapAuthentication 5 }

sonusLdapAuthenticationLdapStatusEntry OBJECT-TYPE
    SYNTAX          SonusLdapAuthenticationLdapStatusEntry
    ACCESS          not-accessible
    STATUS          mandatory
    DESCRIPTION     
            ""
    INDEX           { IMPLIED 
                      sonusLdapAuthenticationLdapStatusServerNameId }
    ::= { sonusLdapAuthenticationLdapStatusTable 1 }

SonusLdapAuthenticationLdapStatusEntry ::=
    SEQUENCE {
        sonusLdapAuthenticationLdapStatusServerNameId             String,
        sonusLdapAuthenticationLdapStatusStatus       SonusLdapStatusType,
        sonusLdapAuthenticationLdapStatusAvailableAt            SonusLdapAvailableTimeType
    }

sonusLdapAuthenticationLdapStatusServerNameId OBJECT-TYPE
    SYNTAX          String (SIZE(0..255))
    ACCESS          not-accessible
    STATUS          mandatory
    DESCRIPTION     
            "The current status of a specific Ldap server."
    ::= { sonusLdapAuthenticationLdapStatusEntry 1 }

sonusLdapAuthenticationLdapStatusStatus OBJECT-TYPE
    SYNTAX          SonusLdapStatusType
    ACCESS          read-only
    STATUS          mandatory
    DESCRIPTION     
            "The actual status of the Ldap server."
    ::= { sonusLdapAuthenticationLdapStatusEntry 2 }

sonusLdapAuthenticationLdapStatusAvailableAt OBJECT-TYPE
    SYNTAX          SonusLdapAvailableTimeType
    ACCESS          read-only
    STATUS          mandatory
    DESCRIPTION     
            "The time when the server will automatically be put back into available state."
    ::= { sonusLdapAuthenticationLdapStatusEntry 3 }

END -- end of module SONUS-LDAP-MIB.
