--
-- This SMIv1 module has been generated by smidump 0.2-cvs. Do not edit.
--

SONUS-COMMON-CALL-PROCESS-MIB DEFINITIONS ::= BEGIN

IMPORTS
    OBJECT-TYPE
        FROM RFC-1212
    TRAP-TYPE
        FROM RFC-1215
    sonusEventClass, sonusEventDescription, sonusEventLevel, 
    sonusEventTime, sonusSequenceId
        FROM SONUS-COMMON-MIB
    sonusStaticCallGcid
        FROM SONUS-NODE-RESOURCES-MIB
    sonusSignallingMIBs
        FROM SONUS-SMI
    sonusTgName
        FROM SONUS-TRUNK-GROUP-RESOURCES-MIB;

sonusCommonCallProcessMIB OBJECT IDENTIFIER
    ::= { sonusSignallingMIBs 9 }

-- sonusCommonCallProcessMIB MODULE-IDENTITY
--     LAST-UPDATED    "200703280000Z"
--     ORGANIZATION    
--             "Sonus Networks, Inc."
--     CONTACT-INFO    
--             "   Customer Support
--              Sonus Networks, Inc.
--              7 Technology Park Drive
--              Westford, MA 01886
--              USA
--              
--              Tel: 978-614-8100
--              Fax: 978-614-8609"
--     DESCRIPTION     
--             "The MIB Module for Common Call Processing Configuration."
--     ::= { sonusSignallingMIBs 9 }


sonusCommonCallProcessMIBNotifications OBJECT IDENTIFIER
    ::= { sonusCommonCallProcessMIB 1 }

sonusCommonCallProcessMIBNotificationsPrefix OBJECT IDENTIFIER
    ::= { sonusCommonCallProcessMIBNotifications 0 }

sonusCommonCallProcessMIBNotificationsObjects OBJECT IDENTIFIER
    ::= { sonusCommonCallProcessMIBNotifications 1 }

sonusIngressTgName OBJECT-TYPE
    SYNTAX          DisplayString (SIZE(0..23))
    ACCESS          read-only
    STATUS          mandatory
    DESCRIPTION     
            "Name of the ingress trunk group."
    ::= { sonusCommonCallProcessMIBNotificationsObjects 1 }

sonusIngressCep OBJECT-TYPE
    SYNTAX          DisplayString (SIZE(0..48))
    ACCESS          read-only
    STATUS          mandatory
    DESCRIPTION     
            "Ingress circuit end point information, this could be PSTN or IP formatted."
    ::= { sonusCommonCallProcessMIBNotificationsObjects 2 }

sonusEgressTgName OBJECT-TYPE
    SYNTAX          DisplayString (SIZE(0..23))
    ACCESS          read-only
    STATUS          mandatory
    DESCRIPTION     
            "Name of the egress trunk group."
    ::= { sonusCommonCallProcessMIBNotificationsObjects 3 }

sonusEgressCep OBJECT-TYPE
    SYNTAX          DisplayString (SIZE(0..48))
    ACCESS          read-only
    STATUS          mandatory
    DESCRIPTION     
            "Egress circuit end point information, this could be PSTN or IP formatted."
    ::= { sonusCommonCallProcessMIBNotificationsObjects 4 }

sonusCalledNumber OBJECT-TYPE
    SYNTAX          DisplayString (SIZE(0..30))
    ACCESS          read-only
    STATUS          mandatory
    DESCRIPTION     
            "Called Party Number."
    ::= { sonusCommonCallProcessMIBNotificationsObjects 5 }

sonusCallingNumber OBJECT-TYPE
    SYNTAX          DisplayString (SIZE(0..30))
    ACCESS          read-only
    STATUS          mandatory
    DESCRIPTION     
            "Calling Party Number."
    ::= { sonusCommonCallProcessMIBNotificationsObjects 6 }

sonusLdcStatus OBJECT-TYPE
    SYNTAX          DisplayString (SIZE(0..13))
    ACCESS          read-only
    STATUS          mandatory
    DESCRIPTION     
            "Is the LDC call to be disconnected or remain active."
    ::= { sonusCommonCallProcessMIBNotificationsObjects 7 }

sonusCep OBJECT-TYPE
    SYNTAX          DisplayString (SIZE(0..48))
    ACCESS          read-only
    STATUS          mandatory
    DESCRIPTION     
            "Circuit end point information, this could be PSTN or IP formatted."
    ::= { sonusCommonCallProcessMIBNotificationsObjects 8 }

sonusCallProcAnswerSupervisionTimeout TRAP-TYPE
    ENTERPRISE      sonusCommonCallProcessMIBNotifications
    VARIABLES       { sonusIngressTgName, sonusIngressCep, 
                      sonusEgressTgName, sonusEgressCep, 
                      sonusCalledNumber, sonusCallingNumber, 
                      sonusEventDescription, sonusEventClass, 
                      sonusEventLevel, sonusSequenceId, sonusEventTime }
--     STATUS          mandatory
    DESCRIPTION     
            "The answer supervision timer has expired, indicating that 
             answer message has not been received from the called party.
             This trap is used to inform maintenance personnel of the
             situation so they can decide whether executive action is 
             required to tear the call down."
    ::= 1

sonusCallProcLongDurationCallTimeout TRAP-TYPE
    ENTERPRISE      sonusCommonCallProcessMIBNotifications
    VARIABLES       { sonusTgName, sonusCep, sonusStaticCallGcid, 
                      sonusCalledNumber, sonusCallingNumber, 
                      sonusLdcStatus, sonusEventDescription, 
                      sonusEventClass, sonusEventLevel, sonusSequenceId, 
                      sonusEventTime }
--     STATUS          mandatory
    DESCRIPTION     
            "This trap is used to inform that the long duration call 
             timer has expired. The call has been active for the 
             configured timeout period and the appropriate
             action has been taken."
    ::= 2

END -- end of module SONUS-COMMON-CALL-PROCESS-MIB.
