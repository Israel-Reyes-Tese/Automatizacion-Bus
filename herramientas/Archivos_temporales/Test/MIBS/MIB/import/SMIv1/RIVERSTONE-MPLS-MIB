--
-- This SMIv1 module has been generated by smidump 0.2-cvs. Do not edit.
--

RIVERSTONE-MPLS-MIB DEFINITIONS ::= BEGIN

IMPORTS
    mplsXCEntry, mplsXCOperStatus
        FROM MPLS-LSR-MIB
    OBJECT-TYPE
        FROM RFC-1212
    TRAP-TYPE
        FROM RFC-1215
    riverstoneMibs
        FROM RIVERSTONE-SMI-MIB
    RowPointer, TruthValue
        FROM SNMPv2-TC;

rsMPLSMIB OBJECT IDENTIFIER
    ::= { riverstoneMibs 39 }

-- rsMPLSMIB MODULE-IDENTITY
--     LAST-UPDATED    "200205240000Z"
--     ORGANIZATION    
--             "Riverstone Networks, Inc."
--     CONTACT-INFO    
--             "Riverstone Networks, Inc
--              5200 Great America Parkway
--              Santa Clara, CA 95054
--              (408) 878-6500
--              nms-eng@riverstonenet.com
--              http://www.riverstonenet.com"
--     DESCRIPTION     
--             "This mib module defines an SNMP API to manage Riverstone's
--              MPLS module"
--     ::= { riverstoneMibs 39 }


rsMPLSObjects OBJECT IDENTIFIER
    ::= { rsMPLSMIB 1 }

rsMPLSXCExtTable OBJECT-TYPE
    SYNTAX          SEQUENCE OF RsMPLSXCExtEntry
    ACCESS          not-accessible
    STATUS          mandatory
    DESCRIPTION     
            "This table specifies extra parameters which might be of interest
             to a SNMP manager, which are not present in the mplsXCTable."
    ::= { rsMPLSObjects 1 }

rsMPLSXCExtEntry OBJECT-TYPE
    SYNTAX          RsMPLSXCExtEntry
    ACCESS          not-accessible
    STATUS          mandatory
    DESCRIPTION     
            "An entry in this table supplies additional necessary parameters 
             like whether rerouted or not, detour LSP, secondary LSP."
    INDEX           { mplsXCIndex, mplsInSegmentIfIndex, 
                      mplsInSegmentLabel, mplsOutSegmentIndex }
--     AUGMENTS        { mplsXCEntry }
    ::= { rsMPLSXCExtTable 1 }

RsMPLSXCExtEntry ::=
    SEQUENCE {
        rsMPLSXCType                    INTEGER,
        rsMPLSXCExtendedOperStatus      INTEGER,
        rsMPLSXCDetourXC                RowPointer,
        rsMPLSXCSecondaryXC             RowPointer
    }

rsMPLSXCType OBJECT-TYPE
    SYNTAX          INTEGER { unknown(1), other(2), nonIngress(3), 
                        primaryNoSecondary(4), primary(5), secondary(6), 
                        detour(7) }
    ACCESS          read-only
    STATUS          mandatory
    DESCRIPTION     
            "This object reflects the type of the LSP.  In case of ingress,
             this reports whether it is a primary or secondary or detour for
             some other LSPs."
    ::= { rsMPLSXCExtEntry 1 }

rsMPLSXCExtendedOperStatus OBJECT-TYPE
    SYNTAX          INTEGER { up(1), down(2), testing(3), unknown(4), 
                        dormant(5), notPresent(6), lowerLayerDown(7), 
                        rerouted(8) }
    ACCESS          read-only
    STATUS          mandatory
    DESCRIPTION     
            "This object is the same as the mplsXCOperStatus during the normal
             operation.  If the LSP has a Detour (Fast Reroute LSP), this value
             is set to rerouted (8), when the detour is used for transmitting
             the data path.  At this time, the rsMPLSXCDetourXC will point to
             the cross-connect of the detour LSP.  The mplsOutSegmentTopLabel
             value of the outsegment of this LSP will be set to 0 (invalid
             label).
             
             When this LSP comes back up, again the value will change as 
             mplsXCOperStatus and the rsMPLSXCDetourXC will be set to 
             the ZeroDotZero OID.  Also the mplsOutSegmentTopLabel will
             be set to the proper value."
    ::= { rsMPLSXCExtEntry 2 }

rsMPLSXCDetourXC OBJECT-TYPE
    SYNTAX          RowPointer
    ACCESS          read-only
    STATUS          mandatory
    DESCRIPTION     
            "A pointer to a conceptual row in the mplsXCTable.
             
             This object is set to the ZeroDotZero OID by default.  Whenever
             the LSP identified by this cross-connect uses a detour, this
             object is set to point to the cross-connect which acts as a
             detour for this LSP.  At this time, the rsMPLSExtOperStatus
             will set to the value of rerouted (8)."
    ::= { rsMPLSXCExtEntry 3 }

rsMPLSXCSecondaryXC OBJECT-TYPE
    SYNTAX          RowPointer
    ACCESS          read-only
    STATUS          mandatory
    DESCRIPTION     
            "A pointer to a conceptual row in the mplsXCTable.
             
             This object is set to the ZeroDotZero OID by default.  This
             object is valid only in case of Ingress LSRs.
             
             If the LSP identified by this cross-connect is a primary, and 
             when this LSP goes down, and if there is a secondary LSP, this
             cross-connect is not torn down.  In stead, the mplsXCOperStatus
             will be set to down, the mplsOutSegmentTopLabel identified by
             the out segment of the cross-connect is set to 0 (invalid label).
             At this time, this object is set to point to the cross-connect
             which acts as the secondary LSP.
             
             Note that, this is the last resort.  First the mpls engine will
             try to use a detour.  If no detours are configured or up, then
             only will it use the secondary LSP."
    ::= { rsMPLSXCExtEntry 4 }

rsMPLSNotification OBJECT IDENTIFIER
    ::= { rsMPLSMIB 2 }

rsMPLSNotificationControl OBJECT IDENTIFIER
    ::= { rsMPLSNotification 1 }

rsMPLSEnableNotifications OBJECT-TYPE
    SYNTAX          TruthValue
    ACCESS          read-write
    STATUS          mandatory
    DESCRIPTION     
            "When this object is set to True(1), the notifications will be sent
             out depending upon the events.  If set to False(2), the 
             notifications will not go out.  By default, the notifications are
             disabled. "
    DEFVAL          { false }
    ::= { rsMPLSNotificationControl 1 }

rsMPLSNotifications OBJECT IDENTIFIER
    ::= { rsMPLSNotification 2 }

rsMPLSNotifyPrefix OBJECT IDENTIFIER
    ::= { rsMPLSNotifications 0 }

rsMPLSConformance OBJECT IDENTIFIER
    ::= { rsMPLSMIB 3 }

rsMPLSCompliances OBJECT IDENTIFIER
    ::= { rsMPLSConformance 1 }

rsMPLSGroups OBJECT IDENTIFIER
    ::= { rsMPLSConformance 2 }

rsMPLSPrimaryPathFailOver TRAP-TYPE
    ENTERPRISE      rsMPLSNotifications
    VARIABLES       { rsMPLSXCExtendedOperStatus, 
                      rsMPLSXCExtendedOperStatus }
--     STATUS          mandatory
    DESCRIPTION     
            "This notification is generated when the primary LSP goes down and
             the secondary path (if any) takes over.  First the Fast Reroute
             mecahnism will try to use the primary path.  For this event, fast
             reroute notification will be generated.  If this does not exist
             or if this also fails, then only will this notification will be
             generated and the seconday path will take over.
             
             The variables included are the operational status of the primary
             path that failed and the secondary path that took over.
             
             This notificiation is generated by the ingress-router of the LSP."
    ::= 1

rsMPLSPrimaryPathTakeOver TRAP-TYPE
    ENTERPRISE      rsMPLSNotifications
    VARIABLES       { rsMPLSXCExtendedOperStatus }
--     STATUS          mandatory
    DESCRIPTION     
            "This notification is generated when the primary LSP comes back
             up and takes over from the secondary path.
             
             This notificiation is generated by the ingress-router of the LSP."
    ::= 2

rsMPLSStartedDetourUse TRAP-TYPE
    ENTERPRISE      rsMPLSNotifications
    VARIABLES       { rsMPLSXCExtendedOperStatus, 
                      rsMPLSXCExtendedOperStatus }
--     STATUS          mandatory
    DESCRIPTION     
            "This notification is generated when the Detour LSP is used to
             circumvent the next hop in the LSP.  
             
             The objects included are the OperationalStatus of the 
             cross-connect of the original LSP and the operational status of
             the detour LSP being used.
             
             This notificiation is generated by the ingress-router of the 
             detour LSP."
    ::= 3

rsMPLSEndedDetourUse TRAP-TYPE
    ENTERPRISE      rsMPLSNotifications
    VARIABLES       { rsMPLSXCExtendedOperStatus }
--     STATUS          mandatory
    DESCRIPTION     
            "This notification is generated when the original next hop is
             reachable, and the regular path is used.  At this point the
             the data will go through the regular next hop.
             
             The object included is the OperationalStatus of the 
             cross-connect of the original LSP.
             
             This notificiation is generated by the ingress-router of the 
             detour LSP."
    ::= 4

rsMPLSLSPPreempted TRAP-TYPE
    ENTERPRISE      rsMPLSNotifications
    VARIABLES       { rsMPLSXCExtendedOperStatus, 
                      rsMPLSXCExtendedOperStatus }
--     STATUS          mandatory
    DESCRIPTION     
            "This notification is generated when a higher priority LSP
             pre-empts and tears down a lower priority LSP.  The lower 
             priority LSP then can use a detour or go down.
             
             The objects included are the OperationalStatus of the 
             cross-connect of the higher priority LSP and that of the lower
             priority LSP.
             
             This notificiation is generated by the hop of the LSP where the
             pre-emption takes place."
    ::= 5

rsMPLSLSRExtensionGroup OBJECT IDENTIFIER
    ::= { rsMPLSGroups 1 }

-- rsMPLSLSRExtensionGroup OBJECT-GROUP
--     OBJECTS         { rsMPLSXCExtendedOperStatus, rsMPLSXCDetourXC, 
--                       rsMPLSXCSecondaryXC }
--     STATUS          mandatory
--     DESCRIPTION     
--             "The collection of objects which are extended from MPLS-LSR-MIB."
--     ::= { rsMPLSGroups 1 }

rsMPLSNotificationGroup OBJECT IDENTIFIER
    ::= { rsMPLSGroups 2 }

-- rsMPLSNotificationGroup NOTIFICATION-GROUP
--     NOTIFICATIONS   { rsMPLSPrimaryPathFailOver, 
--                       rsMPLSPrimaryPathTakeOver, 
--                       rsMPLSStartedDetourUse, rsMPLSEndedDetourUse, 
--                       rsMPLSLSPPreempted }
--     STATUS          mandatory
--     DESCRIPTION     
--             "Set of notifications implemented in this module."
--     ::= { rsMPLSGroups 2 }

rsMPLSNotificationControlGroup OBJECT IDENTIFIER
    ::= { rsMPLSGroups 3 }

-- rsMPLSNotificationControlGroup OBJECT-GROUP
--     OBJECTS         { rsMPLSEnableNotifications }
--     STATUS          mandatory
--     DESCRIPTION     
--             "This object is mandatory to control emission of notifications,
--              when the SNMP-NOTIFICATION-MIB is not available in a given agent."
--     ::= { rsMPLSGroups 3 }

rsMPLSCompliance OBJECT IDENTIFIER
    ::= { rsMPLSCompliances 1 }

-- rsMPLSCompliance MODULE-COMPLIANCE
--     STATUS          mandatory
--     DESCRIPTION     
--             "The compliance statement for SNMP entities which implement
--              the Riverstone Router Config Management MIB."

--     MODULE          -- -- this module

--         MANDATORY-GROUPS    { rsMPLSLSRExtensionGroup }

--     ::= { rsMPLSCompliances 1 }

END -- end of module RIVERSTONE-MPLS-MIB.
