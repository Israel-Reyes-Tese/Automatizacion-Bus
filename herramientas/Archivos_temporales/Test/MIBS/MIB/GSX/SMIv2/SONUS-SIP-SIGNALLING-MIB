--
-- This SMIv2 module has been generated by smidump 0.2-cvs. Do not edit.
--

SONUS-SIP-SIGNALLING-MIB DEFINITIONS ::= BEGIN

IMPORTS
    Ipv6Address
        FROM IPV6-TC
    Counter32, Counter64, Gauge32, Integer32, IpAddress, MODULE-IDENTITY, 
    NOTIFICATION-TYPE, OBJECT-TYPE, Unsigned32
        FROM SNMPv2-SMI
    DateAndTime, DisplayString, RowStatus, TEXTUAL-CONVENTION
        FROM SNMPv2-TC
    sonusEventClass, sonusEventDescription, sonusEventLevel, 
    sonusEventTime, sonusSequenceId
        FROM SONUS-COMMON-MIB
    sonusSignallingMIBs
        FROM SONUS-SMI
    SonusAdminState, SonusBoolean, SonusExtendedName, SonusName, 
    SonusNameReference, SonusServiceState, SonusShelfIndex, 
    SonusSlotIndex, SonusTransportProtocolType
        FROM SONUS-TC;

sonusSipSignallingMIB MODULE-IDENTITY
    LAST-UPDATED    "201706080000Z"
    ORGANIZATION    
            "Sonus Networks, Inc."
    CONTACT-INFO    
            "   Customer Support    
             Sonus Networks, Inc.
             7 Technology Park Drive
             Westford, MA 01886
             USA
             
             Tel: 978-614-8100
             Fax: 978-614-8609"
    DESCRIPTION     
            "The MIB Module for SIP IP Call Signal Port Management."
    ::= { sonusSignallingMIBs 7 }


SonusFilterProfileState ::= TEXTUAL-CONVENTION
    STATUS          current
    DESCRIPTION     
            "State of Filter Profile for all the optional headers"
    SYNTAX          INTEGER { parse(1), filter(2) }

SonusFilterProfileStateWithUnknown ::= TEXTUAL-CONVENTION
    STATUS          current
    DESCRIPTION     
            "State of Filter Profile for all the optional headers"
    SYNTAX          INTEGER { parse(1), filter(2), treatasunknown(3) }

SonusE164ProfileState ::= TEXTUAL-CONVENTION
    STATUS          current
    DESCRIPTION     
            "State of E164 Profile for all the hex-digits"
    SYNTAX          INTEGER { allow(1), truncate(2), remove(3) }

sonusSipSignallingMIBObjects OBJECT IDENTIFIER
    ::= { sonusSipSignallingMIB 1 }

sonusSipSigTimerObjects OBJECT IDENTIFIER
    ::= { sonusSipSignallingMIBObjects 1 }

sonusSipSigTimerT1 OBJECT-TYPE
    SYNTAX          Integer32 (1..10000)
    MAX-ACCESS      read-write
    STATUS          obsolete
    DESCRIPTION     
            "This is the SIP protocol retransmission timer T1 (in milliseconds). 
             This value applies to all future SIP calls.
             This is obsoleted in release 6.3.X, and a similar configuration 
             object is created under SIP Service group."
    DEFVAL          { 500 }
    ::= { sonusSipSigTimerObjects 1 }

sonusSipSigTimerT2 OBJECT-TYPE
    SYNTAX          Integer32 (1..65535)
    MAX-ACCESS      read-write
    STATUS          obsolete
    DESCRIPTION     
            "This is the SIP protocol retransmission timer T2 (in milliseconds). 
             This value applies to all future SIP calls. This is obsoleted 
             in release 6.3.X, and a similar configuration object is created 
             under SIP Service group."
    DEFVAL          { 4000 }
    ::= { sonusSipSigTimerObjects 2 }

sonusSipSigTimerSessionKeepalive OBJECT-TYPE
    SYNTAX          Integer32 (0..65535)
    MAX-ACCESS      read-write
    STATUS          obsolete
    DESCRIPTION     
            "This is the SIP protocol session keep-alive timer (in seconds). 
             This value applies to all future SIP calls. when it
             is set to 0 keepalive is turned off. This is obsoleted in release 6.3.X, 
             and a similar configuration object is created under SIP Service group. "
    DEFVAL          { 1800 }
    ::= { sonusSipSigTimerObjects 3 }

sonusSipSigTimerSessionMinSE OBJECT-TYPE
    SYNTAX          Integer32 (0..65535)
    MAX-ACCESS      read-write
    STATUS          obsolete
    DESCRIPTION     
            "The Min-SE header field indicates the minimum value for the session interval, in units of 
             delta-seconds.  When used in an INVITE or UPDATE request, it indicates the smallest value 
             of the session interval that can be used for that session.  When present in a request or 
             response, its value MUST NOT be less than 90 seconds. This is obsoleted in release 6.3.X, 
              and a similar configuration object is created under SIP Service group."
    DEFVAL          { 90 }
    ::= { sonusSipSigTimerObjects 5 }

sonusSipSigTimerSessionTerminationDeltaTime OBJECT-TYPE
    SYNTAX          Integer32 (0..65535)
    MAX-ACCESS      read-write
    STATUS          obsolete
    DESCRIPTION     
            "The time before the session expiration at which a SIP user agent not performing 
             refreshes SHOULD send BYE to the peer to take the session down if that SIP user agent
             hasn't received any refresh request from its peer. This is obsoleted in release 6.3.X, 
              and a similar configuration object is created under SIP Service group."
    DEFVAL          { 0 }
    ::= { sonusSipSigTimerObjects 6 }

sonusSipSigRetryObjects OBJECT IDENTIFIER
    ::= { sonusSipSignallingMIBObjects 2 }

sonusSipSigNumOfRetry OBJECT-TYPE
    SYNTAX          Integer32 (4..12)
    MAX-ACCESS      read-write
    STATUS          obsolete
    DESCRIPTION     
            "This is the number of retransmission for SIP message. 
             This value applies to all future SIP calls.This is obsoleted 
             in release 6.3.X, and a similar configuration object 
             is created under SIP Service group."
    DEFVAL          { 7 }
    ::= { sonusSipSigRetryObjects 1 }

sonusSipSigInviteRetry OBJECT-TYPE
    SYNTAX          Integer32 (0..12)
    MAX-ACCESS      read-write
    STATUS          obsolete
    DESCRIPTION     
            "This is the number of retransmission for SIP INVITE request. 
             This value applies to all future SIP calls.This object is obsoleted 
             in release 6.3.X, and a similar configuration object 
             is created under SIP Service group."
    DEFVAL          { 6 }
    ::= { sonusSipSigRetryObjects 2 }

sonusSipSigByeRetry OBJECT-TYPE
    SYNTAX          Integer32 (0..12)
    MAX-ACCESS      read-write
    STATUS          obsolete
    DESCRIPTION     
            "This is the number of retransmission for SIP BYE request. 
             This value applies to all future SIP calls.This object is obsoleted 
             in release 6.3.X, and a similar configuration object 
             is created under SIP Service group."
    DEFVAL          { 3 }
    ::= { sonusSipSigRetryObjects 3 }

sonusSipSigCancelRetry OBJECT-TYPE
    SYNTAX          Integer32 (0..12)
    MAX-ACCESS      read-write
    STATUS          obsolete
    DESCRIPTION     
            "This is the number of retransmission for SIP CANCEL request. 
             This value applies to all future SIP calls.This object is obsoleted 
             in release 6.3.X, and a similar configuration object 
             is created under SIP Service group."
    DEFVAL          { 3 }
    ::= { sonusSipSigRetryObjects 4 }

sonusSipSigPortTable OBJECT-TYPE
    SYNTAX          SEQUENCE OF SonusSipSigPortEntry
    MAX-ACCESS      not-accessible
    STATUS          current
    DESCRIPTION     
            "Table of SIP Signalling Port configurations."
    ::= { sonusSipSignallingMIBObjects 3 }

sonusSipSigPortEntry OBJECT-TYPE
    SYNTAX          SonusSipSigPortEntry
    MAX-ACCESS      not-accessible
    STATUS          current
    DESCRIPTION     
            "SIP Signalling Port configuration."
    INDEX           { sonusSipSigPortIndex }
    ::= { sonusSipSigPortTable 1 }

SonusSipSigPortEntry ::=
    SEQUENCE {
        sonusSipSigPortIndex            Integer32,
        sonusSipSigPortIpAddress        IpAddress,
        sonusSipSigPortNum              Integer32,
        sonusSipSigPortInterface        INTEGER,
        sonusSipSigPortRole             INTEGER,
        sonusSipSigPortMode             SonusServiceState,
        sonusSipSigPortState            SonusAdminState,
        sonusSipSigPortRowStatus        RowStatus,
        sonusSipSigPortAclState         SonusAdminState,
        sonusSipSigPortSigZoneId        Integer32,
        sonusSipSigPortNifGroupName     SonusNameReference,
        sonusSipSigPortSigZoneName      SonusNameReference,
        sonusSipSigPortSlot             SonusSlotIndex,
        sonusSipSigPortSecondaryIpAddress IpAddress,
        sonusSipSigPortSctpProfileName  SonusNameReference,
        sonusSipSigPortRecorder         SonusAdminState,
        sonusSipSigPortIp6Address       Ipv6Address,
        sonusSipSigPortSecondaryIp6Address  Ipv6Address,
        sonusSipSigPortIpVersion        INTEGER,
        sonusSipSigPortUdpChecksumState SonusAdminState,
        sonusSipSigPortIpsecPolicyName  DisplayString,
        sonusSipSigPortTraceRoute       SonusAdminState
    }

sonusSipSigPortIndex OBJECT-TYPE
    SYNTAX          Integer32
    MAX-ACCESS      read-only
    STATUS          current
    DESCRIPTION     
            "Identifies the Signal Listen Port entry."
    ::= { sonusSipSigPortEntry 1 }

sonusSipSigPortIpAddress OBJECT-TYPE
    SYNTAX          IpAddress
    MAX-ACCESS      read-write
    STATUS          current
    DESCRIPTION     
            "IP Address of the Sip Signalling Port - mandatory parameter"
    ::= { sonusSipSigPortEntry 2 }

sonusSipSigPortNum OBJECT-TYPE
    SYNTAX          Integer32 (1..65535)
    MAX-ACCESS      read-write
    STATUS          current
    DESCRIPTION     
            "UDP/TCP port number of SIP Signalling Port (default is 5060)."
    DEFVAL          { 5060 }
    ::= { sonusSipSigPortEntry 3 }

sonusSipSigPortInterface OBJECT-TYPE
    SYNTAX          INTEGER { mgtNif(1), nif(2) }
    MAX-ACCESS      read-write
    STATUS          current
    DESCRIPTION     
            "The interface type of SIP Call Signal Port. 'mgtnif' routes traffic over the gateway Managment ports.  'nif' routes traffic over one of the gateway PNS ports."
    DEFVAL          { mgtNif }
    ::= { sonusSipSigPortEntry 4 }

sonusSipSigPortRole OBJECT-TYPE
    SYNTAX          INTEGER { primary(1), secondary(2) }
    MAX-ACCESS      read-only
    STATUS          current
    DESCRIPTION     
            "Role of the Sip Call Signalling Port. As of GSX release V06.03, this field is retained only for backward compatibility."
    DEFVAL          { primary }
    ::= { sonusSipSigPortEntry 5 }

sonusSipSigPortMode OBJECT-TYPE
    SYNTAX          SonusServiceState
    MAX-ACCESS      read-write
    STATUS          current
    DESCRIPTION     
            "Mode of the SIP Signalling Port."
    DEFVAL          { inService }
    ::= { sonusSipSigPortEntry 6 }

sonusSipSigPortState OBJECT-TYPE
    SYNTAX          SonusAdminState
    MAX-ACCESS      read-write
    STATUS          current
    DESCRIPTION     
            "State of the SIP Signalling Port."
    DEFVAL          { disabled }
    ::= { sonusSipSigPortEntry 7 }

sonusSipSigPortRowStatus OBJECT-TYPE
    SYNTAX          RowStatus
    MAX-ACCESS      read-write
    STATUS          current
    DESCRIPTION     
            "This is for SNMP use."
    ::= { sonusSipSigPortEntry 8 }

sonusSipSigPortAclState OBJECT-TYPE
    SYNTAX          SonusAdminState
    MAX-ACCESS      read-write
    STATUS          obsolete
    DESCRIPTION     
            "ACL checking state of the SIP Signalling port"
    DEFVAL          { disabled }
    ::= { sonusSipSigPortEntry 9 }

sonusSipSigPortSigZoneId OBJECT-TYPE
    SYNTAX          Integer32 (0..32)
    MAX-ACCESS      read-only
    STATUS          obsolete
    DESCRIPTION     
            "Identifies the Signaling Zone this signaling port belongs to.
             Obsolete in release 6.5 by a new object: sonusZoneEntry."
    DEFVAL          { 0 }
    ::= { sonusSipSigPortEntry 10 }

sonusSipSigPortNifGroupName OBJECT-TYPE
    SYNTAX          SonusNameReference
    MAX-ACCESS      read-write
    STATUS          current
    DESCRIPTION     
            "The NIF Group which this SIP signaling port belongs to."
    ::= { sonusSipSigPortEntry 11 }

sonusSipSigPortSigZoneName OBJECT-TYPE
    SYNTAX          SonusNameReference
    MAX-ACCESS      read-write
    STATUS          current
    DESCRIPTION     
            "The Signaling Zone that this SIP signaling port belongs to."
    ::= { sonusSipSigPortEntry 12 }

sonusSipSigPortSlot OBJECT-TYPE
    SYNTAX          SonusSlotIndex
    MAX-ACCESS      read-write
    STATUS          current
    DESCRIPTION     
            "The slot number with which this SIP signaling port is associated."
    DEFVAL          { 1 }
    ::= { sonusSipSigPortEntry 13 }

sonusSipSigPortSecondaryIpAddress OBJECT-TYPE
    SYNTAX          IpAddress
    MAX-ACCESS      read-write
    STATUS          current
    DESCRIPTION     
            "Secondary IP Address of the  Sip Signalling Port. "
    DEFVAL          { 0 }
    ::= { sonusSipSigPortEntry 14 }

sonusSipSigPortSctpProfileName OBJECT-TYPE
    SYNTAX          SonusNameReference
    MAX-ACCESS      read-write
    STATUS          current
    DESCRIPTION     
            "Identifies the SCTP Profile for a Sip Signaling Port."
    DEFVAL          { "defaultSctpProfile" }
    ::= { sonusSipSigPortEntry 15 }

sonusSipSigPortRecorder OBJECT-TYPE
    SYNTAX          SonusAdminState
    MAX-ACCESS      read-write
    STATUS          current
    DESCRIPTION     
            "Recorder function for the sig port"
    DEFVAL          { disabled }
    ::= { sonusSipSigPortEntry 16 }

sonusSipSigPortIp6Address OBJECT-TYPE
    SYNTAX          Ipv6Address
    MAX-ACCESS      read-write
    STATUS          current
    DESCRIPTION     
            "IPv6 Address of the Sip Signalling Port - mandatory parameter"
    ::= { sonusSipSigPortEntry 17 }

sonusSipSigPortSecondaryIp6Address OBJECT-TYPE
    SYNTAX          Ipv6Address
    MAX-ACCESS      read-write
    STATUS          current
    DESCRIPTION     
            "Secondary IPv6 Address of the  Sip Signalling Port. "
    ::= { sonusSipSigPortEntry 18 }

sonusSipSigPortIpVersion OBJECT-TYPE
    SYNTAX          INTEGER { afInet(2), afInet6(24) }
    MAX-ACCESS      read-only
    STATUS          current
    DESCRIPTION     
            "IP Address Type of the Sip Signalling Port "
    ::= { sonusSipSigPortEntry 19 }

sonusSipSigPortUdpChecksumState OBJECT-TYPE
    SYNTAX          SonusAdminState
    MAX-ACCESS      read-write
    STATUS          current
    DESCRIPTION     
            "UDP checksum state"
    DEFVAL          { disabled }
    ::= { sonusSipSigPortEntry 20 }

sonusSipSigPortIpsecPolicyName OBJECT-TYPE
    SYNTAX          DisplayString (SIZE(0..23))
    MAX-ACCESS      read-write
    STATUS          current
    DESCRIPTION     
            "The name of the IPsec Policy assigned to this SSP. Null if IPsec is disabled."
    ::= { sonusSipSigPortEntry 21 }

sonusSipSigPortTraceRoute OBJECT-TYPE
    SYNTAX          SonusAdminState
    MAX-ACCESS      read-write
    STATUS          current
    DESCRIPTION     
            "This flag is used to control whether traceroute should be done for the peer blacklisted via ARS"
    DEFVAL          { disabled }
    ::= { sonusSipSigPortEntry 22 }

sonusSipSigPortStatusTable OBJECT-TYPE
    SYNTAX          SEQUENCE OF SonusSipSigPortStatusEntry
    MAX-ACCESS      not-accessible
    STATUS          current
    DESCRIPTION     
            "Table of SIP Signalling Port status."
    ::= { sonusSipSignallingMIBObjects 4 }

sonusSipSigPortStatusEntry OBJECT-TYPE
    SYNTAX          SonusSipSigPortStatusEntry
    MAX-ACCESS      not-accessible
    STATUS          current
    DESCRIPTION     
            "SIP Signalling Port Status."
    INDEX           { sonusSipSigPortStatusIndex }
    ::= { sonusSipSigPortStatusTable 1 }

SonusSipSigPortStatusEntry ::=
    SEQUENCE {
        sonusSipSigPortStatusIndex      Integer32,
        sonusSipSigPortStatusIpAddress  IpAddress,
        sonusSipSigPortStatusNum        Integer32,
        sonusSipSigPortStatusInterface  INTEGER,
        sonusSipSigPortStatusRole       INTEGER,
        sonusSipSigPortStatusNif        Integer32,
        sonusSipSigPortStatusState      SonusServiceState,
        sonusSipSigPortStatusSigZoneId  Integer32,
        sonusSipSigPortStatusNifGroupName SonusNameReference,
        sonusSipSigPortStatusSigZoneName SonusNameReference,
        sonusSipSigPortStatusSecondaryIpAddress       IpAddress,
        sonusSipSigPortStatusIp6Address Ipv6Address,
        sonusSipSigPortStatusSecondaryIp6Address        Ipv6Address,
        sonusSipSigPortStatusIpVersion  INTEGER,
        sonusSipSigPortStatusUdpChecksumState     SonusAdminState
    }

sonusSipSigPortStatusIndex OBJECT-TYPE
    SYNTAX          Integer32
    MAX-ACCESS      read-only
    STATUS          current
    DESCRIPTION     
            "Identifies the Signal Listen Port entry."
    ::= { sonusSipSigPortStatusEntry 1 }

sonusSipSigPortStatusIpAddress OBJECT-TYPE
    SYNTAX          IpAddress
    MAX-ACCESS      read-only
    STATUS          current
    DESCRIPTION     
            "IP Address of the Sip Signalling Port"
    ::= { sonusSipSigPortStatusEntry 2 }

sonusSipSigPortStatusNum OBJECT-TYPE
    SYNTAX          Integer32 (1..65535)
    MAX-ACCESS      read-only
    STATUS          current
    DESCRIPTION     
            "UDP port number of SIP Signalling Port."
    ::= { sonusSipSigPortStatusEntry 3 }

sonusSipSigPortStatusInterface OBJECT-TYPE
    SYNTAX          INTEGER { mgtNif(1), nif(2) }
    MAX-ACCESS      read-only
    STATUS          current
    DESCRIPTION     
            "The interface type of SIP Call Signal Port. 'mgtnif' routes traffic over the gateway Managment ports.  'nif' routes traffic over one of the gateway PNS ports."
    ::= { sonusSipSigPortStatusEntry 4 }

sonusSipSigPortStatusRole OBJECT-TYPE
    SYNTAX          INTEGER { primary(1), secondary(2) }
    MAX-ACCESS      read-only
    STATUS          current
    DESCRIPTION     
            "Role of the Sip Call Signalling Port. As of GSX release V06.03, this field is retained only for backward compatibility."
    ::= { sonusSipSigPortStatusEntry 5 }

sonusSipSigPortStatusNif OBJECT-TYPE
    SYNTAX          Integer32
    MAX-ACCESS      read-only
    STATUS          current
    DESCRIPTION     
            "The network interface index of the port."
    ::= { sonusSipSigPortStatusEntry 6 }

sonusSipSigPortStatusState OBJECT-TYPE
    SYNTAX          SonusServiceState
    MAX-ACCESS      read-only
    STATUS          current
    DESCRIPTION     
            "State of the SIP Signalling Port."
    ::= { sonusSipSigPortStatusEntry 7 }

sonusSipSigPortStatusSigZoneId OBJECT-TYPE
    SYNTAX          Integer32 (0..32)
    MAX-ACCESS      read-only
    STATUS          current
    DESCRIPTION     
            "Identifies the Signaling Port Group this signaling port belongs to."
    ::= { sonusSipSigPortStatusEntry 8 }

sonusSipSigPortStatusNifGroupName OBJECT-TYPE
    SYNTAX          SonusNameReference
    MAX-ACCESS      read-only
    STATUS          current
    DESCRIPTION     
            "The NIF Group which this SIP signaling port belongs to."
    ::= { sonusSipSigPortStatusEntry 9 }

sonusSipSigPortStatusSigZoneName OBJECT-TYPE
    SYNTAX          SonusNameReference
    MAX-ACCESS      read-only
    STATUS          current
    DESCRIPTION     
            "The Signaling Zone that this SIP signaling port belongs to."
    ::= { sonusSipSigPortStatusEntry 10 }

sonusSipSigPortStatusSecondaryIpAddress OBJECT-TYPE
    SYNTAX          IpAddress
    MAX-ACCESS      read-only
    STATUS          current
    DESCRIPTION     
            "Secondary IP Address of the Sip Signalling Port"
    ::= { sonusSipSigPortStatusEntry 11 }

sonusSipSigPortStatusIp6Address OBJECT-TYPE
    SYNTAX          Ipv6Address
    MAX-ACCESS      read-only
    STATUS          current
    DESCRIPTION     
            "IPv6 Address of the Sip Signalling Port"
    ::= { sonusSipSigPortStatusEntry 12 }

sonusSipSigPortStatusSecondaryIp6Address OBJECT-TYPE
    SYNTAX          Ipv6Address
    MAX-ACCESS      read-only
    STATUS          current
    DESCRIPTION     
            "Secondary IPv6 Address of the Sip Signalling Port"
    ::= { sonusSipSigPortStatusEntry 13 }

sonusSipSigPortStatusIpVersion OBJECT-TYPE
    SYNTAX          INTEGER { afInet(2), afInet6(24) }
    MAX-ACCESS      read-only
    STATUS          current
    DESCRIPTION     
            "IP Address Type of the Sip Signalling Port"
    ::= { sonusSipSigPortStatusEntry 14 }

sonusSipSigPortStatusUdpChecksumState OBJECT-TYPE
    SYNTAX          SonusAdminState
    MAX-ACCESS      read-write
    STATUS          current
    DESCRIPTION     
            "UDP checksum state"
    ::= { sonusSipSigPortStatusEntry 15 }

sonusSipSigPortStatTable OBJECT-TYPE
    SYNTAX          SEQUENCE OF SonusSipSigPortStatEntry
    MAX-ACCESS      not-accessible
    STATUS          current
    DESCRIPTION     
            "Table of SIP Signalling Port statistics data."
    ::= { sonusSipSignallingMIBObjects 5 }

sonusSipSigPortStatEntry OBJECT-TYPE
    SYNTAX          SonusSipSigPortStatEntry
    MAX-ACCESS      not-accessible
    STATUS          current
    DESCRIPTION     
            "SIP Signalling Port Statistics."
    INDEX           { sonusSipSigPortStatIndex }
    ::= { sonusSipSigPortStatTable 1 }

SonusSipSigPortStatEntry ::=
    SEQUENCE {
        sonusSipSigPortStatIndex        Integer32,
        sonusSipSigPortStatIpAddress    IpAddress,
        sonusSipSigPortStatPortNum      Integer32,
        sonusSipSigPortStatCountReset   INTEGER,
        sonusSipSigPortStatCallRate     Integer32,
        sonusSipSigPortStatNumOrigCalls Integer32,
        sonusSipSigPortStatNumTermCalls Integer32,
        sonusSipSigPortStatNumTxPdus    Counter64,
        sonusSipSigPortStatNumRxPdus    Counter64,
        sonusSipSigPortStatNumTxBytes   Counter64,
        sonusSipSigPortStatNumRxBytes   Counter64,
        sonusSipSigPortStatNumInRegs    Integer32,
        sonusSipSigPortStatNumOutRegs   Integer32,
        sonusSipSigPortStatIp6Address   Ipv6Address
    }

sonusSipSigPortStatIndex OBJECT-TYPE
    SYNTAX          Integer32
    MAX-ACCESS      read-only
    STATUS          current
    DESCRIPTION     
            "Identifies the Signal Listen Port entry."
    ::= { sonusSipSigPortStatEntry 1 }

sonusSipSigPortStatIpAddress OBJECT-TYPE
    SYNTAX          IpAddress
    MAX-ACCESS      read-only
    STATUS          current
    DESCRIPTION     
            "IP Address of the Sip Signalling Port"
    ::= { sonusSipSigPortStatEntry 2 }

sonusSipSigPortStatPortNum OBJECT-TYPE
    SYNTAX          Integer32 (1..65535)
    MAX-ACCESS      read-only
    STATUS          current
    DESCRIPTION     
            "UDP port number of SIP Signalling Port."
    ::= { sonusSipSigPortStatEntry 3 }

sonusSipSigPortStatCountReset OBJECT-TYPE
    SYNTAX          INTEGER { unknown(1), reset(2) }
    MAX-ACCESS      read-write
    STATUS          current
    DESCRIPTION     
            "set opertion on this object resets all the statistics counts to zero"
    ::= { sonusSipSigPortStatEntry 4 }

sonusSipSigPortStatCallRate OBJECT-TYPE
    SYNTAX          Integer32
    MAX-ACCESS      read-only
    STATUS          current
    DESCRIPTION     
            "number of SIP calls per second during the last minute"
    ::= { sonusSipSigPortStatEntry 5 }

sonusSipSigPortStatNumOrigCalls OBJECT-TYPE
    SYNTAX          Integer32
    MAX-ACCESS      read-only
    STATUS          current
    DESCRIPTION     
            "Total number of outgoing calls sent out from this signaling port"
    ::= { sonusSipSigPortStatEntry 6 }

sonusSipSigPortStatNumTermCalls OBJECT-TYPE
    SYNTAX          Integer32
    MAX-ACCESS      read-only
    STATUS          current
    DESCRIPTION     
            "Total number of incoming calls received on this signaling port"
    ::= { sonusSipSigPortStatEntry 7 }

sonusSipSigPortStatNumTxPdus OBJECT-TYPE
    SYNTAX          Counter64
    MAX-ACCESS      read-only
    STATUS          current
    DESCRIPTION     
            "The total number of signalling PDUS sent out on this port"
    ::= { sonusSipSigPortStatEntry 8 }

sonusSipSigPortStatNumRxPdus OBJECT-TYPE
    SYNTAX          Counter64
    MAX-ACCESS      read-only
    STATUS          current
    DESCRIPTION     
            "The total number of signalling PDUS received on this port"
    ::= { sonusSipSigPortStatEntry 9 }

sonusSipSigPortStatNumTxBytes OBJECT-TYPE
    SYNTAX          Counter64
    MAX-ACCESS      read-only
    STATUS          current
    DESCRIPTION     
            "The total number of signalling BYTES sent out from this port"
    ::= { sonusSipSigPortStatEntry 10 }

sonusSipSigPortStatNumRxBytes OBJECT-TYPE
    SYNTAX          Counter64
    MAX-ACCESS      read-only
    STATUS          current
    DESCRIPTION     
            "The total number of signalling BYTES received by this port"
    ::= { sonusSipSigPortStatEntry 11 }

sonusSipSigPortStatNumInRegs OBJECT-TYPE
    SYNTAX          Integer32
    MAX-ACCESS      read-only
    STATUS          current
    DESCRIPTION     
            "Total number of inbound registration(s) received on this
             signaling port"
    ::= { sonusSipSigPortStatEntry 12 }

sonusSipSigPortStatNumOutRegs OBJECT-TYPE
    SYNTAX          Integer32
    MAX-ACCESS      read-only
    STATUS          current
    DESCRIPTION     
            "Total number of outbound registration(s) sent on this
             signaling port"
    ::= { sonusSipSigPortStatEntry 13 }

sonusSipSigPortStatIp6Address OBJECT-TYPE
    SYNTAX          Ipv6Address
    MAX-ACCESS      read-only
    STATUS          current
    DESCRIPTION     
            "IPv6 Address of the Sip Signalling Port"
    ::= { sonusSipSigPortStatEntry 14 }

sonusSipAcl OBJECT IDENTIFIER
    ::= { sonusSipSignallingMIBObjects 6 }

sonusSipAclNextIndex OBJECT-TYPE
    SYNTAX          Integer32
    MAX-ACCESS      read-only
    STATUS          obsolete
    DESCRIPTION     
            "the next valid index to use when creating a new sonusSipAclEntry"
    ::= { sonusSipAcl 1 }

sonusSipAclTable OBJECT-TYPE
    SYNTAX          SEQUENCE OF SonusSipAclEntry
    MAX-ACCESS      not-accessible
    STATUS          obsolete
    DESCRIPTION     
            "This is the Application Server List"
    ::= { sonusSipAcl 2 }

sonusSipAclEntry OBJECT-TYPE
    SYNTAX          SonusSipAclEntry
    MAX-ACCESS      not-accessible
    STATUS          obsolete
    DESCRIPTION     
            "An Application Server"
    INDEX           { sonusSipRemoteAppSvrIndex }
    ::= { sonusSipAclTable 1 }

SonusSipAclEntry ::=
    SEQUENCE {
        sonusSipRemoteAppSvrIndex       Integer32,
        sonusSipRemoteAppSvrName        SonusName,
        sonusSipRemoteAppSvrIpAddress   IpAddress,
        sonusSipRemoteAppSvrRowStatus   RowStatus,
        sonusSipRemoteAppSvrIp6Address  Ipv6Address
    }

sonusSipRemoteAppSvrIndex OBJECT-TYPE
    SYNTAX          Integer32
    MAX-ACCESS      read-only
    STATUS          obsolete
    DESCRIPTION     
            "Identifies a remote application server entry."
    ::= { sonusSipAclEntry 1 }

sonusSipRemoteAppSvrName OBJECT-TYPE
    SYNTAX          SonusName
    MAX-ACCESS      read-write
    STATUS          obsolete
    DESCRIPTION     
            "Name of the application server."
    ::= { sonusSipAclEntry 2 }

sonusSipRemoteAppSvrIpAddress OBJECT-TYPE
    SYNTAX          IpAddress
    MAX-ACCESS      read-write
    STATUS          obsolete
    DESCRIPTION     
            "IP Address of the application server."
    ::= { sonusSipAclEntry 3 }

sonusSipRemoteAppSvrRowStatus OBJECT-TYPE
    SYNTAX          RowStatus
    MAX-ACCESS      read-write
    STATUS          obsolete
    DESCRIPTION     
            "row status of the application server."
    ::= { sonusSipAclEntry 4 }

sonusSipRemoteAppSvrIp6Address OBJECT-TYPE
    SYNTAX          Ipv6Address
    MAX-ACCESS      read-write
    STATUS          obsolete
    DESCRIPTION     
            "IPv6 Address of the application server."
    ::= { sonusSipAclEntry 5 }

sonusSipSigServiceGroup OBJECT IDENTIFIER
    ::= { sonusSipSignallingMIBObjects 7 }

sonusSipSigServiceGroupNextIndex OBJECT-TYPE
    SYNTAX          Integer32
    MAX-ACCESS      read-only
    STATUS          current
    DESCRIPTION     
            "The next valid index to use when creating a new sonusSipSigServiceGroupEntry"
    ::= { sonusSipSigServiceGroup 1 }

sonusSipSigServiceGroupTable OBJECT-TYPE
    SYNTAX          SEQUENCE OF SonusSipSigServiceGroupEntry
    MAX-ACCESS      not-accessible
    STATUS          current
    DESCRIPTION     
            "This table contains information about each SIP Service Group
             configured to be a member of the node. 
             A management entity may create rows for Service Group that are
             anticipated to be supported in the future."
    ::= { sonusSipSigServiceGroup 2 }

sonusSipSigServiceGroupEntry OBJECT-TYPE
    SYNTAX          SonusSipSigServiceGroupEntry
    MAX-ACCESS      not-accessible
    STATUS          current
    DESCRIPTION     
            "This table describes the SIP Service Groups that interconnect
             GSX9000s"
    INDEX           { sonusSipSigServiceGroupListIndex }
    ::= { sonusSipSigServiceGroupTable 1 }

SonusSipSigServiceGroupEntry ::=
    SEQUENCE {
        sonusSipSigServiceGroupListIndex Integer32,
        sonusSipSigServiceGroupName     SonusName,
        sonusSipSigServiceGroupRowStatus RowStatus,
        sonusSipSigServiceGroupAdminState SonusAdminState,
        sonusSipSigServiceGroupMode     SonusServiceState,
        sonusSipSigServiceGroupAction   INTEGER,
        sonusSipSigServiceGroupDryupTimeout   Integer32,
        sonusSipSigServiceGroupTG       SonusNameReference,
        sonusSipSigServiceGroupDiscTreatmentProfileName               SonusNameReference,
        sonusSipSigServiceGroupTonePackageName      SonusNameReference,
        sonusSipSigServiceGroupSourceAddressFiltering             SonusAdminState,
        sonusSipSigServiceGroupAnsSupervisionTimeout            Integer32,
        sonusSipSigServiceGroupSigZoneId Integer32,
        sonusSipSigServiceGroupMediaNifGroupName        SonusNameReference,
        sonusSipSigServiceGroupNaptForSignaling       SonusAdminState,
        sonusSipSigServiceGroupNaptForMedia   SonusAdminState,
        sonusSipSigServiceGroupRegistrationExpires          Integer32,
        sonusSipSigServiceGroupParseEmbeddedBgid        SonusAdminState,
        sonusSipSigServiceGroupSigZoneName  SonusNameReference,
        sonusSipSigServiceGroupAnsSupervisionTimeoutAction                  INTEGER,
        sonusSipSigServiceGroupCongRetryAfterMin        Integer32,
        sonusSipSigServiceGroupCongRetryAfterMax        Integer32,
        sonusSipSigServiceGroupCongRelTimeout     Integer32,
        sonusSipSigServiceGroupCongRejMethod    INTEGER,
        sonusSipSigServiceGroupTimerT1  Integer32,
        sonusSipSigServiceGroupTimerT2  Integer32,
        sonusSipSigServiceGroupTimerSessionKeepalive            Integer32,
        sonusSipSigServiceGroupTimerSessionMinSE        Integer32,
        sonusSipSigServiceGroupTimerSessionTerminationDeltaTime                       Integer32,
        sonusSipSigServiceGroupGeneralRetryCount        Integer32,
        sonusSipSigServiceGroupInviteRetryCount       Integer32,
        sonusSipSigServiceGroupByeRetryCount    Integer32,
        sonusSipSigServiceGroupCancelRetryCount       Integer32,
        sonusSipSigServiceGroupUseRouteSet  INTEGER,
        sonusSipSigServiceGroupRegRedirMethod     INTEGER,
        sonusSipSigServiceGroupMethodOptions    INTEGER,
        sonusSipSigServiceGroupMethodRefer  INTEGER,
        sonusSipSigServiceGroupMethodSubscribe      INTEGER,
        sonusSipSigServiceGroupMethodNotify   INTEGER,
        sonusSipSigServiceGroupMethodInfo INTEGER,
        sonusSipSigServiceGroupMethodRegister     INTEGER,
        sonusSipSigServiceGroupArsProfileName     SonusNameReference,
        sonusSipSigServiceGroupCpcParamFromHeader         INTEGER,
        sonusSipSigServiceGroupRequireRegistration          SonusAdminState,
        sonusSipSigServiceGroupIsupMimeBodyRelay        SonusAdminState,
        sonusSipSigServiceGroupPrivacyParamRestricted             INTEGER,
        sonusSipSigServiceGroupPAIForCallingParty         SonusAdminState,
        sonusSipSigServiceGroupPPIForCallingParty         SonusAdminState,
        sonusSipSigServiceGroupRPIForCallingParty         SonusAdminState,
        sonusSipSigServiceGroupFromHdrForCallingParty             SonusAdminState,
        sonusSipSigServiceGroupRegistrarMinExpires          Integer32,
        sonusSipSigServiceGroupSessionKeepaliveRetryCountOn422                      Unsigned32,
        sonusSipSigServiceGroupSessionKeepaliveRetryCountOn491                      Unsigned32,
        sonusSipSigServiceGroupLdcTimeout Integer32,
        sonusSipSigServiceGroupLdcAction INTEGER,
        sonusSipSigServiceGroupLdcRelCause  Integer32,
        sonusSipSigServiceGroupLdcEmergencyCalls        INTEGER,
        sonusSipSigServiceGroupCrankBackProfile       Integer32,
        sonusSipSigServiceGroupTcpRetransmitTimer         Unsigned32,
        sonusSipSigServiceGroupNatKeepaliveTcpTimer           Unsigned32,
        sonusSipSigServiceGroupNatKeepaliveUdpTimer           Unsigned32,
        sonusSipSigServiceGroupForceFastRefresh       SonusBoolean,
        sonusSipSigServiceGroupCallRedirection      SonusAdminState,
        sonusSipSigServiceGroupTransportPreference1           SonusTransportProtocolType,
        sonusSipSigServiceGroupTransportPreference2           SonusTransportProtocolType,
        sonusSipSigServiceGroupTransportPreference3           SonusTransportProtocolType,
        sonusSipSigServiceGroupEtsProfileName     SonusNameReference,
        sonusSipSigServiceGroupVariantType  INTEGER,
        sonusSipSigServiceGroupTrustedSource    SonusAdminState,
        sonusSipSigServiceGroupComediaConnectionRole            INTEGER,
        sonusSipSigServiceGroupDnsSupportType     INTEGER,
        sonusSipSigServiceGroupMethodMessage    INTEGER,
        sonusSipSigServiceGroupMethodPublish    INTEGER,
        sonusSipSigServiceGroupMediaZoneName    SonusNameReference,
        sonusSipSigServiceGroupDirectMediaAllowed         SonusAdminState,
        sonusSipSigServiceGroupFilterProfileName        SonusNameReference,
        sonusSipSigServiceGroupMediaZoneId  Unsigned32,
        sonusSipSigServiceGroupFactorValue  Integer32,
        sonusSipSigServiceGroupMaxFwdsDefault     Integer32,
        sonusSipSigServiceGroupRouteMsgValidation         INTEGER,
        sonusSipSigServiceGroupOverlapAddr  INTEGER,
        sonusSipSigServiceGroupMinDigitsForQuery        Integer32,
        sonusSipSigServiceGroupOverlapTimer2    Integer32,
        sonusSipSigServiceGroupOverlapTimer3    Integer32,
        sonusSipSigServiceGroupTMR64K   SonusAdminState,
        sonusSipSigServiceGroupTransmitPreconditions            INTEGER,
        sonusSipSigServiceGroupReceivePreconditions           INTEGER,
        sonusSipSigServiceGroupInterOperatorID      SonusName,
        sonusSipSigServiceGroupURIPreference    INTEGER,
        sonusSipSigServiceGroupTransmitProfileName          SonusNameReference,
        sonusSipSigServiceGroupStrictParse  SonusAdminState,
        sonusSipSigServiceGroupIncludeAppHdrs     SonusAdminState,
        sonusSipSigServiceGroupCpcSipProfileIndex         Integer32,
        sonusSipSigServiceGroupSipCpcProfileIndex         Integer32,
        sonusSipSigServiceGroupDataPathModePassthru           SonusAdminState,
        sonusSipSigServiceGroupNaptQualificationTblName               SonusNameReference,
        sonusSipSigServiceGroupInternationalNoaPlus           SonusAdminState,
        sonusSipSigServiceGroupRelayNonInviteRequest            SonusAdminState,
        sonusSipSigServiceGroupMaxPtimeDefault      Integer32,
        sonusSipSigServiceGroupTransportPreference4           SonusTransportProtocolType,
        sonusSipSigServiceGroupSctpRetransmitTimer          Unsigned32,
        sonusSipSigServiceGroupLateMediaSupport       INTEGER,
        sonusSipSigServiceGroupRegistration   INTEGER,
        sonusSipSigServiceGroupReInviteRetryCount         Unsigned32,
        sonusSipSigServiceGroupInputAdaptorProfile          SonusNameReference,
        sonusSipSigServiceGroupOutputAdaptorProfile           SonusNameReference,
        sonusSipSigServiceGroup100RelSupport    INTEGER,
        sonusSipSigServiceGroupEmergencyProfileIndex            Unsigned32,
        sonusSipSigServiceGroupDBLProfileName     SonusNameReference,
        sonusSipSigServiceGroupEstimatedChildRegistrations                  Integer32,
        sonusSipSigServiceGroupRegistrantCacProfile           SonusNameReference,
        sonusSipSigServiceGroupPeerOvldThrottling         SonusAdminState,
        sonusSipSigServiceGroupSkipCrankBackProfile           Unsigned32,
        sonusSipSigServiceGroupBckwdInfoMsgConDialog            SonusAdminState,
        sonusSipSigServiceGroupIsubParamPreference          INTEGER,
        sonusSipSigServiceGroupUseIngressOrigCa       SonusAdminState,
        sonusSipSigServiceGroupAddEgressOrigCa      SonusAdminState,
        sonusSipSigServiceGroupPcrfRealm DisplayString,
        sonusSipSigServiceGroupPcrfCommitment     INTEGER,
        sonusSipSigServiceGroupPcrfCushionPacketSize            SonusAdminState,
        sonusSipSigServiceGroupPcrfCushionNullSdp         SonusAdminState,
        sonusSipSigServiceGroupUsePsxRouteForSubscribe              SonusAdminState,
        sonusSipSigServiceGroupPrecedenceParamForwarding                INTEGER,
        sonusSipSigServiceGroupValidateAor  SonusAdminState,
        sonusSipSigServiceGroupMethodUpdate   INTEGER,
        sonusSipSigServiceGroupDnsZoneName  SonusNameReference,
        sonusSipSigServiceGroupDnsZoneId Unsigned32,
        sonusSipSigServiceGroupRelayReplacesHeader          SonusAdminState,
        sonusSipSigServiceGroupSipProfileIndex      Integer32,
        sonusSipSigServiceGroupCondIncMethInAllow         SonusAdminState,
        sonusSipSigServiceGroupMediaRecordingSupport            SonusAdminState,
        sonusSipSigServiceGroupSendOriginatingCIC         SonusAdminState,
        sonusSipSigServiceGroupUseIngressChargeInfo           SonusAdminState,
        sonusSipSigServiceGroupSendChargeInfo     SonusAdminState,
        sonusSipSigServiceGroupMediaAddrType    INTEGER,
        sonusSipSigServiceGroupOverlapTimer1    Integer32,
        sonusSipSigServiceGroupReferRejectRspCode         Unsigned32,
        sonusSipSigServiceGroupRedirectDisconnectCode             Unsigned32,
        sonusSipSigServiceGroupRtcpInactivityOnCallConnect                  INTEGER,
        sonusSipSigServiceGroupOtagProfileName      SonusNameReference,
        sonusSipSigServiceGroupMsrpSupport  SonusAdminState,
        sonusSipSigServiceGroupPddTimeout Integer32,
        sonusSipSigServiceGroupPddRspCode Unsigned32,
        sonusSipSigServiceGroupDefaultNoa INTEGER,
        sonusSipSigServiceGroupsrstate  SonusAdminState,
        sonusSipSigServiceGroupsrvalue  Integer32,
        sonusSipSigServiceGroupNoAttemptCdrUriUser          DisplayString,
        sonusSipSigServiceGroup3xxRlyContactsInCdr          INTEGER,
        sonusSipSigServiceGroupAllowVsc SonusAdminState,
        sonusSipSigServiceGroupJurisdictionSupport          SonusAdminState,
        sonusSipSigServiceGroupJipProfileName     SonusNameReference,
        sonusSipSigServiceGroupReuseIpAddrOnFqdnResolution                  SonusAdminState,
        sonusSipSigServiceGroupFeidForPDCS  DisplayString,
        sonusSipSigServiceGroupE164LocalProfileName           SonusNameReference,
        sonusSipSigServiceGroupE164GlobalProfileName            SonusNameReference,
        sonusSipSigServiceGroupEnableSuspendResumeTimerFor                  INTEGER,
        sonusSipSigServiceGroupOliSupport SonusAdminState,
        sonusSipSigServiceGroupBlockProgressOn3xxResp             SonusAdminState,
        sonusSipSigServiceGroupMediaEarlyMediaCutThrough                INTEGER,
        sonusSipSigServiceGroupMediaEgressSupport         SonusAdminState,
        sonusSipSigServiceGroupMediaDefaultGatingMethod               INTEGER,
        sonusSipSigServiceGroupMediaRtpSerProf      SonusNameReference,
        sonusSipSigServiceGroupNaptPublicIPBehindNATSupport                   SonusAdminState,
        sonusSipSigServiceGroupLockDwnPreferredCodec            INTEGER,
        sonusSipSigServiceGroupUseNonDefaultCauseCodeForARSBlacklist                            SonusAdminState,
        sonusSipSigServiceGroupNoRdiUpdateOn3xx       SonusAdminState,
        sonusSipSigServiceGroupSourceAddressValidation              INTEGER,
        sonusSipSigServiceGroupRewriteIdentities        SonusAdminState,
        sonusSipSigServiceGroupAcceptHistoryInfo        SonusAdminState,
        sonusSipSigServiceGroupJapanMnpLnpMapping         SonusAdminState,
        sonusSipSigServiceGroupSendSdpToPsx   SonusAdminState,
        sonusSipSigServiceGroupPopulateRN SonusAdminState,
        sonusSipSigServiceGroupEmgrCallIntwkTreatment             SonusAdminState,
        sonusSipSigServiceGroupSilenceSuppTreatment           INTEGER,
        sonusSipSigServiceGroupGtdFeature SonusAdminState,
        sonusSipSigServiceGroupGtdMode  INTEGER,
        sonusSipSigServiceGroupGtdIsupSigGrp    SonusNameReference,
        sonusSipSigServiceGroupTransparencyProfileName              SonusNameReference,
        sonusSipSigServiceGroupUseGAPWhenRnDisabled           SonusAdminState,
        sonusSipSigServiceGroupEnhancedARS  SonusAdminState,
        sonusSipSigServiceGroupMapIsupCgpnToPAI       SonusAdminState,
        sonusSipSigServiceGroupMapFromHeaderToIsupGAP             SonusAdminState
    }

sonusSipSigServiceGroupListIndex OBJECT-TYPE
    SYNTAX          Integer32
    MAX-ACCESS      read-only
    STATUS          current
    DESCRIPTION     
            "The index of the SIP Service Group entry."
    ::= { sonusSipSigServiceGroupEntry 1 }

sonusSipSigServiceGroupName OBJECT-TYPE
    SYNTAX          SonusName
    MAX-ACCESS      read-write
    STATUS          current
    DESCRIPTION     
            "The name of this SIP Service Group."
    ::= { sonusSipSigServiceGroupEntry 2 }

sonusSipSigServiceGroupRowStatus OBJECT-TYPE
    SYNTAX          RowStatus
    MAX-ACCESS      read-write
    STATUS          current
    DESCRIPTION     
            ""
    ::= { sonusSipSigServiceGroupEntry 3 }

sonusSipSigServiceGroupAdminState OBJECT-TYPE
    SYNTAX          SonusAdminState
    MAX-ACCESS      read-write
    STATUS          current
    DESCRIPTION     
            "The admin state of the this SIP Service Group."
    ::= { sonusSipSigServiceGroupEntry 4 }

sonusSipSigServiceGroupMode OBJECT-TYPE
    SYNTAX          SonusServiceState
    MAX-ACCESS      read-write
    STATUS          current
    DESCRIPTION     
            "The mode of operation of this SIP Service Group."
    ::= { sonusSipSigServiceGroupEntry 5 }

sonusSipSigServiceGroupAction OBJECT-TYPE
    SYNTAX          INTEGER { dryup(1), force(2), undefined(3) }
    MAX-ACCESS      read-write
    STATUS          current
    DESCRIPTION     
            "The action taken on calls for this SIP Service Group."
    DEFVAL          { dryup }
    ::= { sonusSipSigServiceGroupEntry 6 }

sonusSipSigServiceGroupDryupTimeout OBJECT-TYPE
    SYNTAX          Integer32 (0..1440)
    MAX-ACCESS      read-write
    STATUS          current
    DESCRIPTION     
            "The timeout value in minutes for dryup action for this
             SIP Service Group."
    DEFVAL          { 5 }
    ::= { sonusSipSigServiceGroupEntry 7 }

sonusSipSigServiceGroupTG OBJECT-TYPE
    SYNTAX          SonusNameReference
    MAX-ACCESS      read-write
    STATUS          current
    DESCRIPTION     
            "The Trunk Group which this SIP Service Group belongs to."
    ::= { sonusSipSigServiceGroupEntry 8 }

sonusSipSigServiceGroupDiscTreatmentProfileName OBJECT-TYPE
    SYNTAX          SonusNameReference
    MAX-ACCESS      read-write
    STATUS          current
    DESCRIPTION     
            "The disconnect treatment profile to be used for this service."
    ::= { sonusSipSigServiceGroupEntry 9 }

sonusSipSigServiceGroupTonePackageName OBJECT-TYPE
    SYNTAX          SonusNameReference
    MAX-ACCESS      read-write
    STATUS          current
    DESCRIPTION     
            "The tone package to be used for this service."
    ::= { sonusSipSigServiceGroupEntry 10 }

sonusSipSigServiceGroupSourceAddressFiltering OBJECT-TYPE
    SYNTAX          SonusAdminState
    MAX-ACCESS      read-write
    STATUS          current
    DESCRIPTION     
            "This object indicates whether or not the GSX will perform IP source
             address filtering on incoming media packets for this trunk group.
             When ENABLED, the SG will only accept incoming media packets whose
             source address matches the destination address of outbound packets.
             When DISABLED, the GSX does not filter the incoming media stream.
             The source address to filter on is supplied during call signaling."
    DEFVAL          { disabled }
    ::= { sonusSipSigServiceGroupEntry 11 }

sonusSipSigServiceGroupAnsSupervisionTimeout OBJECT-TYPE
    SYNTAX          Integer32 (0..1000)
    MAX-ACCESS      read-write
    STATUS          current
    DESCRIPTION     
            "This is the time from egress call setup to egress receiving an answer."
    DEFVAL          { 300 }
    ::= { sonusSipSigServiceGroupEntry 12 }

sonusSipSigServiceGroupSigZoneId OBJECT-TYPE
    SYNTAX          Integer32 (0..32)
    MAX-ACCESS      read-only
    STATUS          current
    DESCRIPTION     
            "Identifies the Signaling Zone this SIP service group is bound to.
             This ID is automatically generated when a new signaling zone is
             created."
    DEFVAL          { 0 }
    ::= { sonusSipSigServiceGroupEntry 13 }

sonusSipSigServiceGroupMediaNifGroupName OBJECT-TYPE
    SYNTAX          SonusNameReference
    MAX-ACCESS      read-write
    STATUS          current
    DESCRIPTION     
            "The media NIF Group which this SIP service group is bound to."
    ::= { sonusSipSigServiceGroupEntry 14 }

sonusSipSigServiceGroupNaptForSignaling OBJECT-TYPE
    SYNTAX          SonusAdminState
    MAX-ACCESS      read-write
    STATUS          current
    DESCRIPTION     
            "This indicates whether or not the devices matching this trunk group
             require NAPT support for signaling. When ENABLED, the GSX will send
             signaling packets to the learned source address and port of 
             the peer. When DISABLED, the GSX will send signaling packets as
             		 dictated by the SIP signaling from the peer."
    DEFVAL          { disabled }
    ::= { sonusSipSigServiceGroupEntry 15 }

sonusSipSigServiceGroupNaptForMedia OBJECT-TYPE
    SYNTAX          SonusAdminState
    MAX-ACCESS      read-write
    STATUS          current
    DESCRIPTION     
            "This indicates whether or not the devices matching this trunk group
             require NAPT support for media. When ENABLED, the GSX will send
             RTP packets to the learned source address and port of the
             inbound RTP stream. When DISABLED, the GSX will send RTP
             packets as negotiated by the SIP signaling from the peer."
    DEFVAL          { disabled }
    ::= { sonusSipSigServiceGroupEntry 16 }

sonusSipSigServiceGroupRegistrationExpires OBJECT-TYPE
    SYNTAX          Integer32 (15..65535)
    MAX-ACCESS      read-write
    STATUS          current
    DESCRIPTION     
            "This is maximum refresh registration interval(in seconds) for SIP endpoint
             that is not behind NAT. This is also the default refresh interval if the
             SIP endpoint has not proposed an expires value during registration.
               	 The minimum value is 15 seconds."
    DEFVAL          { 3600 }
    ::= { sonusSipSigServiceGroupEntry 17 }

sonusSipSigServiceGroupParseEmbeddedBgid OBJECT-TYPE
    SYNTAX          SonusAdminState
    MAX-ACCESS      read-write
    STATUS          current
    DESCRIPTION     
            "This indicates whether the digits after the '*' should be processed
             separately as BGID. When ENABLED, the PSX will process the BGID 
             separately. When DISABLED, the PSX will process the entire digit
             string as a whole."
    DEFVAL          { disabled }
    ::= { sonusSipSigServiceGroupEntry 18 }

sonusSipSigServiceGroupSigZoneName OBJECT-TYPE
    SYNTAX          SonusNameReference
    MAX-ACCESS      read-write
    STATUS          current
    DESCRIPTION     
            "The signaling zone which this SIP service group is bound to."
    ::= { sonusSipSigServiceGroupEntry 19 }

sonusSipSigServiceGroupAnsSupervisionTimeoutAction OBJECT-TYPE
    SYNTAX          INTEGER { release(1), trapAndRestart(2) }
    MAX-ACCESS      read-write
    STATUS          current
    DESCRIPTION     
            "This is the action to take if the answer supervision timer
             expires.  The call may be released or the timer can be restarted
             and a trap fired."
    DEFVAL          { release }
    ::= { sonusSipSigServiceGroupEntry 20 }

sonusSipSigServiceGroupCongRetryAfterMin OBJECT-TYPE
    SYNTAX          Integer32 (0..120)
    MAX-ACCESS      read-write
    STATUS          current
    DESCRIPTION     
            "Retry-After minimum duration for calls rejected due to congestion."
    DEFVAL          { 10 }
    ::= { sonusSipSigServiceGroupEntry 21 }

sonusSipSigServiceGroupCongRetryAfterMax OBJECT-TYPE
    SYNTAX          Integer32 (0..120)
    MAX-ACCESS      read-write
    STATUS          current
    DESCRIPTION     
            "Retry-After maximum duration for calls rejected due to congestion."
    DEFVAL          { 30 }
    ::= { sonusSipSigServiceGroupEntry 22 }

sonusSipSigServiceGroupCongRelTimeout OBJECT-TYPE
    SYNTAX          Integer32 (0..5)
    MAX-ACCESS      read-write
    STATUS          current
    DESCRIPTION     
            "Time to delay sending of release during congestion."
    DEFVAL          { 0 }
    ::= { sonusSipSigServiceGroupEntry 23 }

sonusSipSigServiceGroupCongRejMethod OBJECT-TYPE
    SYNTAX          INTEGER { release(1), ignore(2), discard(3) }
    MAX-ACCESS      read-write
    STATUS          current
    DESCRIPTION     
            "Determines how a SIP call is rejected during congestion.
             Release - send 100 Trying followed by 503 Service Unavailable.
                       The 503 can optionally be delayed by the 
                       ConRelTimeout value. It can also have an optional
                       retry after parameter.
             Ignore -  send 100 Trying and then drop the call.
             Discard - drop the call with no response."
    DEFVAL          { release }
    ::= { sonusSipSigServiceGroupEntry 24 }

sonusSipSigServiceGroupTimerT1 OBJECT-TYPE
    SYNTAX          Integer32 (1..10000)
    MAX-ACCESS      read-write
    STATUS          current
    DESCRIPTION     
            "This is the SIP protocol retransmission timer T1 (in milliseconds).
             T1 is an estimate of the round-trip time (RTT), and it defaults to 500 ms. "
    DEFVAL          { 500 }
    ::= { sonusSipSigServiceGroupEntry 25 }

sonusSipSigServiceGroupTimerT2 OBJECT-TYPE
    SYNTAX          Integer32 (1..65535)
    MAX-ACCESS      read-write
    STATUS          current
    DESCRIPTION     
            "This is the SIP protocol timer T2 (in milliseconds). This represents
             the maximum retransmit interval for non-INVITE requests and INVITE responses."
    DEFVAL          { 4000 }
    ::= { sonusSipSigServiceGroupEntry 26 }

sonusSipSigServiceGroupTimerSessionKeepalive OBJECT-TYPE
    SYNTAX          Integer32 (0..65535)
    MAX-ACCESS      read-write
    STATUS          current
    DESCRIPTION     
            "This is the SIP protocol session keep-alive timer (in seconds). 
             When the timer is set to 0 keepalive is turned off"
    DEFVAL          { 1800 }
    ::= { sonusSipSigServiceGroupEntry 27 }

sonusSipSigServiceGroupTimerSessionMinSE OBJECT-TYPE
    SYNTAX          Integer32 (0..65535)
    MAX-ACCESS      read-write
    STATUS          current
    DESCRIPTION     
            "The Min-SE header field indicates the minimum value for the session interval, in units of 
             delta-seconds.  When used in an INVITE or UPDATE request, it indicates the smallest value 
             of the session interval that can be used for that session.  When present in a request or 
             response, its value MUST NOT be less than 90 seconds"
    DEFVAL          { 90 }
    ::= { sonusSipSigServiceGroupEntry 28 }

sonusSipSigServiceGroupTimerSessionTerminationDeltaTime OBJECT-TYPE
    SYNTAX          Integer32 (0..65535)
    MAX-ACCESS      read-write
    STATUS          current
    DESCRIPTION     
            "The time before the session expiration at which a SIP user agent not performing 
             refreshes SHOULD send BYE to the peer to take the session down if that SIP user agent
             hasn't received any refresh request from its peer."
    DEFVAL          { 0 }
    ::= { sonusSipSigServiceGroupEntry 29 }

sonusSipSigServiceGroupGeneralRetryCount OBJECT-TYPE
    SYNTAX          Integer32 (4..12)
    MAX-ACCESS      read-write
    STATUS          current
    DESCRIPTION     
            "This object represents the maximum number of retransmissions 
             that the SIP stack will perform for SIP message."
    DEFVAL          { 7 }
    ::= { sonusSipSigServiceGroupEntry 30 }

sonusSipSigServiceGroupInviteRetryCount OBJECT-TYPE
    SYNTAX          Integer32 (0..6)
    MAX-ACCESS      read-write
    STATUS          current
    DESCRIPTION     
            "This object represents the maximum number of retransmissions 
             that the SIP stack will perform for SIP INVITE message."
    DEFVAL          { 6 }
    ::= { sonusSipSigServiceGroupEntry 31 }

sonusSipSigServiceGroupByeRetryCount OBJECT-TYPE
    SYNTAX          Integer32 (0..12)
    MAX-ACCESS      read-write
    STATUS          current
    DESCRIPTION     
            "This object represents the maximum number of retransmissions 
             that the SIP stack will perform for SIP BYE message."
    DEFVAL          { 3 }
    ::= { sonusSipSigServiceGroupEntry 32 }

sonusSipSigServiceGroupCancelRetryCount OBJECT-TYPE
    SYNTAX          Integer32 (0..12)
    MAX-ACCESS      read-write
    STATUS          current
    DESCRIPTION     
            "This object represents the maximum number of retransmissions 
             that the SIP stack will perform for SIP CANCEL message."
    DEFVAL          { 3 }
    ::= { sonusSipSigServiceGroupEntry 33 }

sonusSipSigServiceGroupUseRouteSet OBJECT-TYPE
    SYNTAX          INTEGER { disabled(1), stored(2), received(3), 
                        stored-all(4) }
    MAX-ACCESS      read-write
    STATUS          current
    DESCRIPTION     
            "This indicates whether the Path or Service-Route information stored
             in the RCB or the received Route headers are to be used for routing.
             Disabled       - Use default method (PSX query) for routing.
             StoredRouteSet - Use the Path or Service-Route stored in RCB for routing.
             received       - Use the received Route set for routing.
             stored-all     - Use stored route set for all requests including refresh registers"
    DEFVAL          { disabled }
    ::= { sonusSipSigServiceGroupEntry 34 }

sonusSipSigServiceGroupRegRedirMethod OBJECT-TYPE
    SYNTAX          INTEGER { none(1), redir3xx(2) }
    MAX-ACCESS      read-write
    STATUS          current
    DESCRIPTION     
            "The way, within the SIP protocol, of redirecting peer
             REGISTER methods to a desired SIP signaling port."
    DEFVAL          { none }
    ::= { sonusSipSigServiceGroupEntry 35 }

sonusSipSigServiceGroupMethodOptions OBJECT-TYPE
    SYNTAX          INTEGER { allow(1), reject(2) }
    MAX-ACCESS      read-write
    STATUS          current
    DESCRIPTION     
            "Determines whether OPTIONS request is accepted and processed or rejected with 405."
    DEFVAL          { 1 }
    ::= { sonusSipSigServiceGroupEntry 36 }

sonusSipSigServiceGroupMethodRefer OBJECT-TYPE
    SYNTAX          INTEGER { allow(1), reject(2) }
    MAX-ACCESS      read-write
    STATUS          current
    DESCRIPTION     
            "Determines whether REFER request is accepted and processed or rejected with 405."
    DEFVAL          { 1 }
    ::= { sonusSipSigServiceGroupEntry 37 }

sonusSipSigServiceGroupMethodSubscribe OBJECT-TYPE
    SYNTAX          INTEGER { allow(1), reject(2) }
    MAX-ACCESS      read-write
    STATUS          current
    DESCRIPTION     
            "Determines whether SUBSCRIBE request is accepted and processed or rejected with 405."
    DEFVAL          { 1 }
    ::= { sonusSipSigServiceGroupEntry 38 }

sonusSipSigServiceGroupMethodNotify OBJECT-TYPE
    SYNTAX          INTEGER { allow(1), reject(2) }
    MAX-ACCESS      read-write
    STATUS          current
    DESCRIPTION     
            "Determines whether NOTIFY request is accepted and processed or rejected with 405."
    DEFVAL          { 1 }
    ::= { sonusSipSigServiceGroupEntry 39 }

sonusSipSigServiceGroupMethodInfo OBJECT-TYPE
    SYNTAX          INTEGER { allow(1), reject(2) }
    MAX-ACCESS      read-write
    STATUS          current
    DESCRIPTION     
            "Determines whether INFO method is allowed to be included in the Allow header."
    DEFVAL          { 1 }
    ::= { sonusSipSigServiceGroupEntry 40 }

sonusSipSigServiceGroupMethodRegister OBJECT-TYPE
    SYNTAX          INTEGER { allow(1), reject(2) }
    MAX-ACCESS      read-write
    STATUS          current
    DESCRIPTION     
            "Determines whether REGISTER method is allowed to be included in the Allow header."
    DEFVAL          { 1 }
    ::= { sonusSipSigServiceGroupEntry 41 }

sonusSipSigServiceGroupArsProfileName OBJECT-TYPE
    SYNTAX          SonusNameReference
    MAX-ACCESS      read-write
    STATUS          current
    DESCRIPTION     
            "The Address Reachability Service profile for this
             service group. None assigned means no reachability service
             enforced."
    ::= { sonusSipSigServiceGroupEntry 42 }

sonusSipSigServiceGroupCpcParamFromHeader OBJECT-TYPE
    SYNTAX          INTEGER { default(1), paitel(2), fromheader(3), 
                        paisip(4) }
    MAX-ACCESS      read-write
    STATUS          current
    DESCRIPTION     
            "SIP Mapping CPC parameter from incoming call to outgoing call.
             Default - map CPC parameter from PAI TEL header.
             or map CPC parameter from From header, if PAI TEL has no CPC.
             or map CPC parameter from From header, if there is no PAI header.
             or map CPC parameter as default ordinary.
             PAITEL -  only map CPC parameter from PAI TEL header if exists. 
             FROMHEADER - only map CPC parameter from From header if exists.
             PAISIP -    only map CPC parameter from PAI SIP header if exists. "
    DEFVAL          { default }
    ::= { sonusSipSigServiceGroupEntry 43 }

sonusSipSigServiceGroupRequireRegistration OBJECT-TYPE
    SYNTAX          SonusAdminState
    MAX-ACCESS      read-write
    STATUS          obsolete
    DESCRIPTION     
            "This flag should be ENABLED when the associated IP trunk group is used for
             endpoints requiring registration. It should be DISABLED in other cases.
             This field is obsoleted in GSX 7.2.x and replaced by expanded Registration."
    DEFVAL          { disabled }
    ::= { sonusSipSigServiceGroupEntry 44 }

sonusSipSigServiceGroupIsupMimeBodyRelay OBJECT-TYPE
    SYNTAX          SonusAdminState
    MAX-ACCESS      read-write
    STATUS          current
    DESCRIPTION     
            "This indicates whether or not MIME body needs to be relayed. When ENABLED, 
             the GSX if receives an ISUP mime body in the SIP signaling message will include
             the body transparently without any modification in the outgoing SIP signaling message.
             When DISABLED, the GSX will fallback to present interworking mode behavior and 
             process MIME bodies received in SIP signaling messages."
    DEFVAL          { disabled }
    ::= { sonusSipSigServiceGroupEntry 45 }

sonusSipSigServiceGroupPrivacyParamRestricted OBJECT-TYPE
    SYNTAX          INTEGER { default(1), idonly(2) }
    MAX-ACCESS      read-write
    STATUS          current
    DESCRIPTION     
            "SIP Mapping Privacy Header parameters from incoming call to outgoing call.
             Default - map Privacy parameters header, id, or user to restrict.
             IdOnly - only map Privacy parameter id to restrict"
    DEFVAL          { default }
    ::= { sonusSipSigServiceGroupEntry 46 }

sonusSipSigServiceGroupPAIForCallingParty OBJECT-TYPE
    SYNTAX          SonusAdminState
    MAX-ACCESS      read-write
    STATUS          current
    DESCRIPTION     
            "When this flag is ENABLED, the PAI header if presented will be accepted to form the Calling-Party-ID.
             If this flag is DISABLED, the PAI header will be ignored when forming the Calling-Party-ID as if it
             does not present"
    DEFVAL          { enabled }
    ::= { sonusSipSigServiceGroupEntry 47 }

sonusSipSigServiceGroupPPIForCallingParty OBJECT-TYPE
    SYNTAX          SonusAdminState
    MAX-ACCESS      read-write
    STATUS          current
    DESCRIPTION     
            "When this flag is ENABLED, the PPI header if presented will be accepted to form the Calling-Party-ID.
             If this flag is DISABLED, the PPI header will be ignored when forming the Calling-Party-ID as if it
             does not present"
    DEFVAL          { enabled }
    ::= { sonusSipSigServiceGroupEntry 48 }

sonusSipSigServiceGroupRPIForCallingParty OBJECT-TYPE
    SYNTAX          SonusAdminState
    MAX-ACCESS      read-write
    STATUS          current
    DESCRIPTION     
            "When this flag is ENABLED, the RPI header if presented will be accepted to form the Calling-Party-ID.
             If this flag is DISABLED, the RPI header will be ignored when forming the Calling-Party-ID as if it
             does not present"
    DEFVAL          { enabled }
    ::= { sonusSipSigServiceGroupEntry 49 }

sonusSipSigServiceGroupFromHdrForCallingParty OBJECT-TYPE
    SYNTAX          SonusAdminState
    MAX-ACCESS      read-write
    STATUS          current
    DESCRIPTION     
            "When this flag is ENABLED, the FROM header will be used to form the Calling-Party-ID provided no
             PAI/PPI/RPI header presents. If this flag is DISABLED, the FROM header will not take part in
             forming the Calling-Party-ID."
    DEFVAL          { enabled }
    ::= { sonusSipSigServiceGroupEntry 50 }

sonusSipSigServiceGroupRegistrarMinExpires OBJECT-TYPE
    SYNTAX          Integer32 (0..65535)
    MAX-ACCESS      read-write
    STATUS          current
    DESCRIPTION     
            "This controls the initial expires value in a REGISTER 
             forwarded by the NBS.The max of this value and the 
             value received from the IAD will be used."
    DEFVAL          { 3600 }
    ::= { sonusSipSigServiceGroupEntry 51 }

sonusSipSigServiceGroupSessionKeepaliveRetryCountOn422 OBJECT-TYPE
    SYNTAX          Unsigned32 (0..12)
    MAX-ACCESS      read-write
    STATUS          current
    DESCRIPTION     
            "This object represents the maximum number of retries that the SIP stack
             will perform for Session Keepalive message on receipt  of 422."
    DEFVAL          { 5 }
    ::= { sonusSipSigServiceGroupEntry 52 }

sonusSipSigServiceGroupSessionKeepaliveRetryCountOn491 OBJECT-TYPE
    SYNTAX          Unsigned32 (0..12)
    MAX-ACCESS      read-write
    STATUS          current
    DESCRIPTION     
            "This object represents the maximum number of retries  that the SIP stack
             will perform for Session Keepalive message on receipt of 491."
    DEFVAL          { 5 }
    ::= { sonusSipSigServiceGroupEntry 53 }

sonusSipSigServiceGroupLdcTimeout OBJECT-TYPE
    SYNTAX          Integer32 (0..2880)
    MAX-ACCESS      read-write
    STATUS          current
    DESCRIPTION     
            "The timeout value of the long duration call timer in minutes.
             Allowed values are 0 to disable the timer, 60-2880 minutes to set the timer."
    DEFVAL          { 0 }
    ::= { sonusSipSigServiceGroupEntry 54 }

sonusSipSigServiceGroupLdcAction OBJECT-TYPE
    SYNTAX          INTEGER { noAction(0), trap(1), release(2), 
                        trapAndRelease(3) }
    MAX-ACCESS      read-write
    STATUS          current
    DESCRIPTION     
            "This is the action to take if the long duration call timer
             expires.  The call may be released or a trap fired, or both."
    DEFVAL          { noAction }
    ::= { sonusSipSigServiceGroupEntry 55 }

sonusSipSigServiceGroupLdcRelCause OBJECT-TYPE
    SYNTAX          Integer32 (1..127)
    MAX-ACCESS      read-write
    STATUS          current
    DESCRIPTION     
            "The Q.850 release value to use should the call be released 
             due to long duration call timer expiry"
    DEFVAL          { 41 }
    ::= { sonusSipSigServiceGroupEntry 56 }

sonusSipSigServiceGroupLdcEmergencyCalls OBJECT-TYPE
    SYNTAX          INTEGER { include(0), exclude(1) }
    MAX-ACCESS      read-write
    STATUS          current
    DESCRIPTION     
            "Whether Emergency Calls should be excluded from or included 
             in Long Duration Call Disconnect procedures"
    DEFVAL          { exclude }
    ::= { sonusSipSigServiceGroupEntry 57 }

sonusSipSigServiceGroupCrankBackProfile OBJECT-TYPE
    SYNTAX          Integer32 (1..20)
    MAX-ACCESS      read-write
    STATUS          current
    DESCRIPTION     
            "The Crank Back Profile to be used for this Service."
    DEFVAL          { 1 }
    ::= { sonusSipSigServiceGroupEntry 58 }

sonusSipSigServiceGroupTcpRetransmitTimer OBJECT-TYPE
    SYNTAX          Unsigned32 (0..15)
    MAX-ACCESS      read-write
    STATUS          current
    DESCRIPTION     
            "The retransmit timer in seconds for SIP over TCP."
    DEFVAL          { 6 }
    ::= { sonusSipSigServiceGroupEntry 67 }

sonusSipSigServiceGroupNatKeepaliveTcpTimer OBJECT-TYPE
    SYNTAX          Unsigned32 (15..65535)
    MAX-ACCESS      read-write
    STATUS          current
    DESCRIPTION     
            "This is maximum refresh registration interval(in seconds) for 
             SIP endpoint that is behind NAT using TCP. This is also the
             default refresh interval if the SIP endpoint has not proposed
             an expires value during registration."
    DEFVAL          { 240 }
    ::= { sonusSipSigServiceGroupEntry 68 }

sonusSipSigServiceGroupNatKeepaliveUdpTimer OBJECT-TYPE
    SYNTAX          Unsigned32 (15..65535)
    MAX-ACCESS      read-write
    STATUS          current
    DESCRIPTION     
            "This is maximum refresh registration interval(in seconds) for 
             SIP endpoint that is behind NAT using UDP. This is also the
             default refresh interval if the SIP endpoint has not proposed
             an expires value during registration."
    DEFVAL          { 60 }
    ::= { sonusSipSigServiceGroupEntry 69 }

sonusSipSigServiceGroupForceFastRefresh OBJECT-TYPE
    SYNTAX          SonusBoolean
    MAX-ACCESS      read-write
    STATUS          obsolete
    DESCRIPTION     
            "This Force Fast Refresh flag indicates whether 
             NAT keepalive timer value shall be used to set 
             registration refresh expiration."
    DEFVAL          { false }
    ::= { sonusSipSigServiceGroupEntry 70 }

sonusSipSigServiceGroupCallRedirection OBJECT-TYPE
    SYNTAX          SonusAdminState
    MAX-ACCESS      read-write
    STATUS          current
    DESCRIPTION     
            "This object enables or disables inbound SIP call redirection
             landing on MNS."
    DEFVAL          { enabled }
    ::= { sonusSipSigServiceGroupEntry 71 }

sonusSipSigServiceGroupTransportPreference1 OBJECT-TYPE
    SYNTAX          SonusTransportProtocolType
    MAX-ACCESS      read-write
    STATUS          current
    DESCRIPTION     
            "This first choice of transport protocol for SIP calls."
    DEFVAL          { none }
    ::= { sonusSipSigServiceGroupEntry 72 }

sonusSipSigServiceGroupTransportPreference2 OBJECT-TYPE
    SYNTAX          SonusTransportProtocolType
    MAX-ACCESS      read-write
    STATUS          current
    DESCRIPTION     
            "This second choice of transport protocol for SIP calls."
    DEFVAL          { none }
    ::= { sonusSipSigServiceGroupEntry 73 }

sonusSipSigServiceGroupTransportPreference3 OBJECT-TYPE
    SYNTAX          SonusTransportProtocolType
    MAX-ACCESS      read-write
    STATUS          current
    DESCRIPTION     
            "This third choice of transport protocol for SIP calls."
    DEFVAL          { none }
    ::= { sonusSipSigServiceGroupEntry 74 }

sonusSipSigServiceGroupEtsProfileName OBJECT-TYPE
    SYNTAX          SonusNameReference
    MAX-ACCESS      read-write
    STATUS          current
    DESCRIPTION     
            "The Resource Priority Header profile to be used for this service."
    ::= { sonusSipSigServiceGroupEntry 75 }

sonusSipSigServiceGroupVariantType OBJECT-TYPE
    SYNTAX          INTEGER { sonus(1), ttc(2), q1912(3), uk(4), mgcf(5) }
    MAX-ACCESS      read-write
    STATUS          current
    DESCRIPTION     
            "As we support specifications with conflicting requirements, a control
             is needed to determine what type of functionality to invoke when
             a message is processed."
    DEFVAL          { sonus }
    ::= { sonusSipSigServiceGroupEntry 76 }

sonusSipSigServiceGroupTrustedSource OBJECT-TYPE
    SYNTAX          SonusAdminState
    MAX-ACCESS      read-write
    STATUS          current
    DESCRIPTION     
            "Used to indicate if the message came from a trusted source and the FROM header
             can be used to map into ISUP parameters."
    DEFVAL          { enabled }
    ::= { sonusSipSigServiceGroupEntry 77 }

sonusSipSigServiceGroupComediaConnectionRole OBJECT-TYPE
    SYNTAX          INTEGER { none(1), active(2), passive(3) }
    MAX-ACCESS      read-write
    STATUS          current
    DESCRIPTION     
            "This indicates whether the SDP offer sent by GSX will include any direction
             attribute line defined by COMEDIA draft.
             None       - SDP offer does not include direction attribute line
             Active     - SDP offer sends a=direction:active
             Passive    - SDP offer sends a=direction:passive "
    DEFVAL          { none }
    ::= { sonusSipSigServiceGroupEntry 78 }

sonusSipSigServiceGroupDnsSupportType OBJECT-TYPE
    SYNTAX          INTEGER { a-only(1), a-srv-naptr(7) }
    MAX-ACCESS      read-write
    STATUS          current
    DESCRIPTION     
            "This controls the DNS support type.This is a bit-mask for each record type, using SIPSG_DNS_SUPPORT_ENUM"
    DEFVAL          { a-only }
    ::= { sonusSipSigServiceGroupEntry 79 }

sonusSipSigServiceGroupMethodMessage OBJECT-TYPE
    SYNTAX          INTEGER { allow(1), reject(2) }
    MAX-ACCESS      read-write
    STATUS          current
    DESCRIPTION     
            "Determines whether MESSAGE request is accepted and processed or rejected with 405."
    DEFVAL          { 2 }
    ::= { sonusSipSigServiceGroupEntry 80 }

sonusSipSigServiceGroupMethodPublish OBJECT-TYPE
    SYNTAX          INTEGER { allow(1), reject(2) }
    MAX-ACCESS      read-write
    STATUS          current
    DESCRIPTION     
            "Determines whether PUBLISH request is accepted and processed or rejected with 405."
    DEFVAL          { 2 }
    ::= { sonusSipSigServiceGroupEntry 81 }

sonusSipSigServiceGroupMediaZoneName OBJECT-TYPE
    SYNTAX          SonusNameReference
    MAX-ACCESS      read-write
    STATUS          current
    DESCRIPTION     
            "The Media Zone to which this SIP service group is bound."
    ::= { sonusSipSigServiceGroupEntry 82 }

sonusSipSigServiceGroupDirectMediaAllowed OBJECT-TYPE
    SYNTAX          SonusAdminState
    MAX-ACCESS      read-write
    STATUS          current
    DESCRIPTION     
            "This indicates whether or not Direct Media should be attempted
             for calls to or from endpoints in this service group. If
             enabled, the GSX will attempt to set up the media path such
             that media flows directly between two Direct-Media-enabled 
             endpoints in the same media zone."
    DEFVAL          { disabled }
    ::= { sonusSipSigServiceGroupEntry 83 }

sonusSipSigServiceGroupFilterProfileName OBJECT-TYPE
    SYNTAX          SonusNameReference
    MAX-ACCESS      read-write
    STATUS          current
    DESCRIPTION     
            "The Filter profile to be used for this service.
             None assigned means no Receive Side Filter."
    ::= { sonusSipSigServiceGroupEntry 84 }

sonusSipSigServiceGroupMediaZoneId OBJECT-TYPE
    SYNTAX          Unsigned32 (0..32)
    MAX-ACCESS      read-only
    STATUS          current
    DESCRIPTION     
            "Identifies the Media Zone this SIP service group is bound to."
    ::= { sonusSipSigServiceGroupEntry 85 }

sonusSipSigServiceGroupFactorValue OBJECT-TYPE
    SYNTAX          Integer32 (0..50)
    MAX-ACCESS      read-write
    STATUS          current
    DESCRIPTION     
            "Specifies the factor value used to interwork the SIP Max Forwards
             Header and the ISUP Hop counter parameter. If the value is zero
             		 the default Max Fwds Header value provisioned will be used"
    DEFVAL          { 1 }
    ::= { sonusSipSigServiceGroupEntry 86 }

sonusSipSigServiceGroupMaxFwdsDefault OBJECT-TYPE
    SYNTAX          Integer32 (1..100)
    MAX-ACCESS      read-write
    STATUS          current
    DESCRIPTION     
            "Specifies the default value for the Max Forwards Header"
    DEFVAL          { 70 }
    ::= { sonusSipSigServiceGroupEntry 87 }

sonusSipSigServiceGroupRouteMsgValidation OBJECT-TYPE
    SYNTAX          INTEGER { noValidation(1), sipOnly(2), sipI(3) }
    MAX-ACCESS      read-write
    STATUS          current
    DESCRIPTION     
            "Specifies if route validation should be done for the 
             received message and if the message should be validated
             to ensure it is SIP-only or SIP-I. The call will be 
             		 released if validation is done and an invalid message 
             		 type is received"
    DEFVAL          { 1 }
    ::= { sonusSipSigServiceGroupEntry 88 }

sonusSipSigServiceGroupOverlapAddr OBJECT-TYPE
    SYNTAX          INTEGER { disabled(1), 
                        recvMultiInviteSendMultiInvite(2), 
                        recvInfoSendInfo(3), recvMultiInviteSendInfo(4), 
                        recvMultiInviteSendEnbloc(5), 
                        recvInfoSendMultiInvite(6), 
                        recvInfoSendEnbloc(7), 
                        recvEnblocSendMultiInvite(8), 
                        recvEnblocSendInfo(9) }
    MAX-ACCESS      read-write
    STATUS          current
    DESCRIPTION     
            "Control to determine if Overlap Address signaling is supported and what type"
    DEFVAL          { disabled }
    ::= { sonusSipSigServiceGroupEntry 89 }

sonusSipSigServiceGroupMinDigitsForQuery OBJECT-TYPE
    SYNTAX          Integer32 (0..30)
    MAX-ACCESS      read-write
    STATUS          current
    DESCRIPTION     
            "The minimum number of digits that need to be received before sending
             a routing request to the PSX - this is used if overlap is supported."
    DEFVAL          { 0 }
    ::= { sonusSipSigServiceGroupEntry 90 }

sonusSipSigServiceGroupOverlapTimer2 OBJECT-TYPE
    SYNTAX          Integer32 (0..14)
    MAX-ACCESS      read-write
    STATUS          current
    DESCRIPTION     
            "Time in seconds between sending an INVITE and receiving a backward
             message. If this timer is set to 0 then it is not in use"
    DEFVAL          { 0 }
    ::= { sonusSipSigServiceGroupEntry 91 }

sonusSipSigServiceGroupOverlapTimer3 OBJECT-TYPE
    SYNTAX          Integer32 (4..64)
    MAX-ACCESS      read-write
    STATUS          current
    DESCRIPTION     
            "Time in seconds between receiving a 484 Address Incomplete message
             if there are no outstanding INVITE transactions and the receipt of fresh
             address information."
    DEFVAL          { 4 }
    ::= { sonusSipSigServiceGroupEntry 92 }

sonusSipSigServiceGroupTMR64K OBJECT-TYPE
    SYNTAX          SonusAdminState
    MAX-ACCESS      read-write
    STATUS          current
    DESCRIPTION     
            "The Transmission Medium Requirement Unrestricted 64kbit/s control
             is needed for SIP-ISUP interworking."
    DEFVAL          { disabled }
    ::= { sonusSipSigServiceGroupEntry 93 }

sonusSipSigServiceGroupTransmitPreconditions OBJECT-TYPE
    SYNTAX          INTEGER { none(1), optional(2), required(3) }
    MAX-ACCESS      read-write
    STATUS          current
    DESCRIPTION     
            " Configuration required for setting up preconditions on outgoing request"
    DEFVAL          { none }
    ::= { sonusSipSigServiceGroupEntry 94 }

sonusSipSigServiceGroupReceivePreconditions OBJECT-TYPE
    SYNTAX          INTEGER { none(1), supported(2), required(3) }
    MAX-ACCESS      read-write
    STATUS          current
    DESCRIPTION     
            " Configuration required for validating and performing preconditions on incoming request"
    DEFVAL          { none }
    ::= { sonusSipSigServiceGroupEntry 95 }

sonusSipSigServiceGroupInterOperatorID OBJECT-TYPE
    SYNTAX          SonusName
    MAX-ACCESS      read-write
    STATUS          current
    DESCRIPTION     
            "The Inter Operator ID for MGCF"
    ::= { sonusSipSigServiceGroupEntry 96 }

sonusSipSigServiceGroupURIPreference OBJECT-TYPE
    SYNTAX          INTEGER { none(1), sip(2), tel(3) }
    MAX-ACCESS      read-write
    STATUS          current
    DESCRIPTION     
            "This indicates URI presentation preference for outgoing messages.
             None       - No preference
             SIP        - Present TEL URI as SIP URI
             TEL        - Present SIP URI as TEL URI"
    DEFVAL          { none }
    ::= { sonusSipSigServiceGroupEntry 97 }

sonusSipSigServiceGroupTransmitProfileName OBJECT-TYPE
    SYNTAX          SonusNameReference
    MAX-ACCESS      read-write
    STATUS          current
    DESCRIPTION     
            "The Transmit profile to be used for this service.
             None assigned means no Additional Headers will be transmitted."
    ::= { sonusSipSigServiceGroupEntry 98 }

sonusSipSigServiceGroupStrictParse OBJECT-TYPE
    SYNTAX          SonusAdminState
    MAX-ACCESS      read-write
    STATUS          current
    DESCRIPTION     
            "Enables Strict SIP Parsing"
    DEFVAL          { disabled }
    ::= { sonusSipSigServiceGroupEntry 99 }

sonusSipSigServiceGroupIncludeAppHdrs OBJECT-TYPE
    SYNTAX          SonusAdminState
    MAX-ACCESS      read-write
    STATUS          current
    DESCRIPTION     
            "Enables Application to add Headers in outgoing messages"
    DEFVAL          { disabled }
    ::= { sonusSipSigServiceGroupEntry 100 }

sonusSipSigServiceGroupCpcSipProfileIndex OBJECT-TYPE
    SYNTAX          Integer32 (0..64)
    MAX-ACCESS      read-write
    STATUS          current
    DESCRIPTION     
            "This field indicates the index of the CPC_TO_SIP profile that shall be 
             applied to calls that have not yet received a CPC_TO_SIP profile index from the PSX.
             0 is default behavior(not default cause map)"
    DEFVAL          { 0 }
    ::= { sonusSipSigServiceGroupEntry 101 }

sonusSipSigServiceGroupSipCpcProfileIndex OBJECT-TYPE
    SYNTAX          Integer32 (0..64)
    MAX-ACCESS      read-write
    STATUS          current
    DESCRIPTION     
            "This field indicates the index of the SIP_TO_CPC profile that shall be 
             applied to calls that have not yet received a SIP_TO_CPC profile index from the PSX.
             0 is default behavior(not default cause map)"
    DEFVAL          { 0 }
    ::= { sonusSipSigServiceGroupEntry 102 }

sonusSipSigServiceGroupDataPathModePassthru OBJECT-TYPE
    SYNTAX          SonusAdminState
    MAX-ACCESS      read-write
    STATUS          current
    DESCRIPTION     
            "Passthru Data path Mode received from peer in Offer SDP with 0 RTP IP."
    DEFVAL          { disabled }
    ::= { sonusSipSigServiceGroupEntry 103 }

sonusSipSigServiceGroupNaptQualificationTblName OBJECT-TYPE
    SYNTAX          SonusNameReference
    MAX-ACCESS      read-write
    STATUS          current
    DESCRIPTION     
            "The name of the IP network selector table used as NAPT 
             qualification table by this service group.  The table 
             contains a list of IP addresses that qualifies as  
             private addresses that would have been converted by NAPT."
    ::= { sonusSipSigServiceGroupEntry 104 }

sonusSipSigServiceGroupInternationalNoaPlus OBJECT-TYPE
    SYNTAX          SonusAdminState
    MAX-ACCESS      read-write
    STATUS          current
    DESCRIPTION     
            "Set the CPN and CIN NOA to International if number begins with '+'."
    DEFVAL          { disabled }
    ::= { sonusSipSigServiceGroupEntry 105 }

sonusSipSigServiceGroupRelayNonInviteRequest OBJECT-TYPE
    SYNTAX          SonusAdminState
    MAX-ACCESS      read-write
    STATUS          current
    DESCRIPTION     
            "Relay Non Invite Requests. "
    DEFVAL          { disabled }
    ::= { sonusSipSigServiceGroupEntry 106 }

sonusSipSigServiceGroupMaxPtimeDefault OBJECT-TYPE
    SYNTAX          Integer32 (10..150)
    MAX-ACCESS      read-write
    STATUS          current
    DESCRIPTION     
            "This field indicates the default packet size to be used for this SIP Service Group."
    DEFVAL          { 150 }
    ::= { sonusSipSigServiceGroupEntry 107 }

sonusSipSigServiceGroupTransportPreference4 OBJECT-TYPE
    SYNTAX          SonusTransportProtocolType
    MAX-ACCESS      read-write
    STATUS          current
    DESCRIPTION     
            "This fourth choice of transport protocol for SIP calls."
    DEFVAL          { none }
    ::= { sonusSipSigServiceGroupEntry 108 }

sonusSipSigServiceGroupSctpRetransmitTimer OBJECT-TYPE
    SYNTAX          Unsigned32 (0..15)
    MAX-ACCESS      read-write
    STATUS          current
    DESCRIPTION     
            "The retransmit timer in seconds for SIP over SCTP."
    DEFVAL          { 6 }
    ::= { sonusSipSigServiceGroupEntry 109 }

sonusSipSigServiceGroupLateMediaSupport OBJECT-TYPE
    SYNTAX          INTEGER { convert(1), passthru(2) }
    MAX-ACCESS      read-write
    STATUS          current
    DESCRIPTION     
            "Determines whether a SIP late media (reverse offer) INVITE should be converted to
             a forward offer on egress."
    DEFVAL          { convert }
    ::= { sonusSipSigServiceGroupEntry 110 }

sonusSipSigServiceGroupRegistration OBJECT-TYPE
    SYNTAX          INTEGER { none(1), supported(2), required(3), 
                        required-nonpriority(4), supported-group(5) }
    MAX-ACCESS      read-write
    STATUS          current
    DESCRIPTION     
            "This flag should be SUPPORTED when the associated IP trunk group is used for endpoints
             optionally requiring registration.  It should be REQUIRED in cases where absolutely no
             unregistered IAD may make any calls.  It should be SUPPORTED-GROUP to allow calls from 
             unregistred users and to allow calls from users whose username does not match with the 
             stored URI in RCB. It should be REQUIRED-NONPRIORITY when unregistered
             IAD cannot make any non-priority calls.  NONE (default) is selected when no registration
             validation is to be performed."
    DEFVAL          { none }
    ::= { sonusSipSigServiceGroupEntry 111 }

sonusSipSigServiceGroupReInviteRetryCount OBJECT-TYPE
    SYNTAX          Unsigned32 (0..6)
    MAX-ACCESS      read-write
    STATUS          current
    DESCRIPTION     
            "This object represents the maximum number of retransmissions 
             for SIP Re-INVITE message."
    DEFVAL          { 0 }
    ::= { sonusSipSigServiceGroupEntry 112 }

sonusSipSigServiceGroupInputAdaptorProfile OBJECT-TYPE
    SYNTAX          SonusNameReference
    MAX-ACCESS      read-write
    STATUS          current
    DESCRIPTION     
            "The input SIP Message Manipulation profile used by this SIP Service Group."
    ::= { sonusSipSigServiceGroupEntry 113 }

sonusSipSigServiceGroupOutputAdaptorProfile OBJECT-TYPE
    SYNTAX          SonusNameReference
    MAX-ACCESS      read-write
    STATUS          current
    DESCRIPTION     
            "The output SIP Message Manipulation profile used by this SIP Service Group."
    ::= { sonusSipSigServiceGroupEntry 114 }

sonusSipSigServiceGroup100RelSupport OBJECT-TYPE
    SYNTAX          INTEGER { disabled(1), enabled(2) }
    MAX-ACCESS      read-write
    STATUS          current
    DESCRIPTION     
            "This object controls the 100rel support for the reliability of provisional 
             messages as specified in RFC3262. This object can be set to either disabled(1)
             or enabled(2) on the specified service group for either ingess or egress leg.
             When this object is disabled, the specified service group is not supporting 
             the 100rel that appeared in the INVITE or PRACK message header. The default 
             setting of this object is enabled."
    DEFVAL          { enabled }
    ::= { sonusSipSigServiceGroupEntry 115 }

sonusSipSigServiceGroupEmergencyProfileIndex OBJECT-TYPE
    SYNTAX          Unsigned32 (0..16)
    MAX-ACCESS      read-write
    STATUS          current
    DESCRIPTION     
            "The index of the SIP emergency profile associated with this
             SIP service group."
    DEFVAL          { 0 }
    ::= { sonusSipSigServiceGroupEntry 118 }

sonusSipSigServiceGroupDBLProfileName OBJECT-TYPE
    SYNTAX          SonusNameReference
    MAX-ACCESS      read-write
    STATUS          current
    DESCRIPTION     
            "The dynamic black listing profile used for this service."
    ::= { sonusSipSigServiceGroupEntry 119 }

sonusSipSigServiceGroupEstimatedChildRegistrations OBJECT-TYPE
    SYNTAX          Integer32 (1..256)
    MAX-ACCESS      read-only
    STATUS          current
    DESCRIPTION     
            "This read-only object represents the estimated number of implicit registrations
             configured at the TG this Service Group belongs to."
    DEFVAL          { 1 }
    ::= { sonusSipSigServiceGroupEntry 120 }

sonusSipSigServiceGroupRegistrantCacProfile OBJECT-TYPE
    SYNTAX          SonusNameReference
    MAX-ACCESS      read-write
    STATUS          current
    DESCRIPTION     
            "The CAC profile to used for registered users. No profile means no endpoint CAC for registrants."
    ::= { sonusSipSigServiceGroupEntry 121 }

sonusSipSigServiceGroupPeerOvldThrottling OBJECT-TYPE
    SYNTAX          SonusAdminState
    MAX-ACCESS      read-write
    STATUS          current
    DESCRIPTION     
            "Determines whether peer overload indications (SIP 503 w/ Retry After) cause us to throttle calls to that peer."
    DEFVAL          { disabled }
    ::= { sonusSipSigServiceGroupEntry 122 }

sonusSipSigServiceGroupSkipCrankBackProfile OBJECT-TYPE
    SYNTAX          Unsigned32 (0..20)
    MAX-ACCESS      read-write
    STATUS          current
    DESCRIPTION     
            "Skip Blacklisted Route on Crank Back Profile to be used for this Service."
    DEFVAL          { 0 }
    ::= { sonusSipSigServiceGroupEntry 123 }

sonusSipSigServiceGroupBckwdInfoMsgConDialog OBJECT-TYPE
    SYNTAX          SonusAdminState
    MAX-ACCESS      read-write
    STATUS          current
    DESCRIPTION     
            "If Enabled an INFO message will only be sent after confirmed Dialog.
             If Disabled an INFO message will be only sent after a 18x message.
                  This functionality only applies to SIP-T"
    DEFVAL          { disabled }
    ::= { sonusSipSigServiceGroupEntry 124 }

sonusSipSigServiceGroupIsubParamPreference OBJECT-TYPE
    SYNTAX          INTEGER { rfc2806(1), nonstandard(2), rfc3966(3) }
    MAX-ACCESS      read-write
    STATUS          current
    DESCRIPTION     
            "This service group attribute specifies how the ISDN
             Sub-Address parameter shall be handled in SIP. 
             Default: GSX SIP shall follow rfc2806 when handling ISUB
             parameter.
             Non-Standard: GSX SIP shall treat the percentage character as an
             escape character when receiving this parameter. On the sending side
             GSX shall not include characters that are not allowed by the proxy in
             the Willcom network.
             rfc3966: GSX SIP shall encode and decode the ISUB
             parameter based on the ABNF for ISUB specified in RFC3966."
    DEFVAL          { rfc2806 }
    ::= { sonusSipSigServiceGroupEntry 125 }

sonusSipSigServiceGroupUseIngressOrigCa OBJECT-TYPE
    SYNTAX          SonusAdminState
    MAX-ACCESS      read-write
    STATUS          current
    DESCRIPTION     
            "Honor P-Orig-CA header received on the ingress
             CMD         USEINGRESSORIGCA
             SCREEN      SIP Service Group - Use Ingress Orig CA
             REQS        PCR 1743"
    DEFVAL          { disabled }
    ::= { sonusSipSigServiceGroupEntry 126 }

sonusSipSigServiceGroupAddEgressOrigCa OBJECT-TYPE
    SYNTAX          SonusAdminState
    MAX-ACCESS      read-write
    STATUS          current
    DESCRIPTION     
            "Allow P-Orig-CA header to be sent on the egress
             CMD         ADDEGRESSORIGCA
             SCREEN      SIP Service Group - Add Egress Orig CA
             REQS        PCR 1743"
    DEFVAL          { disabled }
    ::= { sonusSipSigServiceGroupEntry 127 }

sonusSipSigServiceGroupPcrfRealm OBJECT-TYPE
    SYNTAX          DisplayString (SIZE(0..127))
    MAX-ACCESS      read-write
    STATUS          current
    DESCRIPTION     
            "The DIAMETER domain of a Policy and Charging Rule Function
             configured for the SG.  AAR commands are sent to the PCRF
             requesting authorization and bandwidth reservation for
             the IP flows of an ingress or egress call."
    ::= { sonusSipSigServiceGroupEntry 128 }

sonusSipSigServiceGroupPcrfCommitment OBJECT-TYPE
    SYNTAX          INTEGER { none(1), optional(2), required(3) }
    MAX-ACCESS      read-write
    STATUS          current
    DESCRIPTION     
            "The degree of commitment expected from the PCRF:
             none - do not send AAR;
             		  optional - send AAR, proceed even if it fails;
             		  required - send AAR, proceed only if it succeeds."
    DEFVAL          { none }
    ::= { sonusSipSigServiceGroupEntry 129 }

sonusSipSigServiceGroupPcrfCushionPacketSize OBJECT-TYPE
    SYNTAX          SonusAdminState
    MAX-ACCESS      read-write
    STATUS          current
    DESCRIPTION     
            "Whether the bandwidth estimate from a call setup or call update
             offer shall be padded to account for increases that may result
             from a legitimate answer to the offer:
              disabled - use packet sizes present in the offer;
              enabled - use smaller packet sizes that may be present
                in an answer from the range supported for each codec.
             This option applies to offer processing and a preliminary AAR.
             The final AAR sent during answer processing reflects the exact outcome.
             Enabling this option may avoid the need to reject an answer because
             its AAR fails, even though the offer AAR succeeded, and to abort a call
             after ringing the destination."
    DEFVAL          { disabled }
    ::= { sonusSipSigServiceGroupEntry 130 }

sonusSipSigServiceGroupPcrfCushionNullSdp OBJECT-TYPE
    SYNTAX          SonusAdminState
    MAX-ACCESS      read-write
    STATUS          current
    DESCRIPTION     
            "Whether a preliminary AAR shall be sent when the initial call setup
             is an INVITE that lacks SDP.
              disabled - no, wait for a reverse offer;
              enabled - yes, estimate G.711 10 msec as a worst case.
             Enabling this option may avoid the need to reject an offer because
             its AAR fails and to abort a call after ringing the destination."
    DEFVAL          { disabled }
    ::= { sonusSipSigServiceGroupEntry 131 }

sonusSipSigServiceGroupUsePsxRouteForSubscribe OBJECT-TYPE
    SYNTAX          SonusAdminState
    MAX-ACCESS      read-write
    STATUS          current
    DESCRIPTION     
            "This flag specifies whether to use PSX routes for routing the SUBSCRIBE to
             registered users.  When ENABLED PSX routing is performed and when DISABLED no
             PSX routing is performed."
    DEFVAL          { disabled }
    ::= { sonusSipSigServiceGroupEntry 132 }

sonusSipSigServiceGroupPrecedenceParamForwarding OBJECT-TYPE
    SYNTAX          INTEGER { disabled(1), enabled(2) }
    MAX-ACCESS      read-write
    STATUS          current
    DESCRIPTION     
            "This enables and disables precedence parameter forwarding
             on each service profile that is associated with each trunk group."
    DEFVAL          { disabled }
    ::= { sonusSipSigServiceGroupEntry 133 }

sonusSipSigServiceGroupValidateAor OBJECT-TYPE
    SYNTAX          SonusAdminState
    MAX-ACCESS      read-write
    STATUS          current
    DESCRIPTION     
            "This indicates whether AOR validation is required or not.
             When ENABLED, the GSX will perform AOR validation while searching for RCB, 
             if DISABLED GSX shall just search based on srcIP, srcPort and zoneId."
    DEFVAL          { enabled }
    ::= { sonusSipSigServiceGroupEntry 135 }

sonusSipSigServiceGroupMethodUpdate OBJECT-TYPE
    SYNTAX          INTEGER { allow(1), reject(2) }
    MAX-ACCESS      read-write
    STATUS          current
    DESCRIPTION     
            "Determines whether UPDATE request is accepted and processed or rejected with 405."
    DEFVAL          { 1 }
    ::= { sonusSipSigServiceGroupEntry 136 }

sonusSipSigServiceGroupDnsZoneName OBJECT-TYPE
    SYNTAX          SonusNameReference
    MAX-ACCESS      read-write
    STATUS          current
    DESCRIPTION     
            "The DNS Zone Name used for this service."
    DEFVAL          { "INTERNAL" }
    ::= { sonusSipSigServiceGroupEntry 137 }

sonusSipSigServiceGroupDnsZoneId OBJECT-TYPE
    SYNTAX          Unsigned32
    MAX-ACCESS      read-only
    STATUS          current
    DESCRIPTION     
            "Identifies the DNS Zone this SIP service group is bound to.
             This ID is automatically generated when a new dns zone is
             created."
    DEFVAL          { 0 }
    ::= { sonusSipSigServiceGroupEntry 138 }

sonusSipSigServiceGroupRelayReplacesHeader OBJECT-TYPE
    SYNTAX          SonusAdminState
    MAX-ACCESS      read-write
    STATUS          current
    DESCRIPTION     
            "This indicates whether or not the Replaces header in INVITE needs to
             be relayed. When ENABLED, GSX relays the Replaces header in INVITE
             after mapping the dialog-identifier in the Replaces header appropriately
             for the case of matching dialog. The INVITE with Replaces header is
             sent on the egress side even if there is no matching dialog.
             When DISABLED, GSX processes the Replaces header in INVITE locally
             always. The INVITE with Replaces header is never sent on the
             egress side for the case of matching dialog and is rejected for
             the case of non-matching dialog."
    DEFVAL          { disabled }
    ::= { sonusSipSigServiceGroupEntry 139 }

sonusSipSigServiceGroupSipProfileIndex OBJECT-TYPE
    SYNTAX          Integer32 (0..64)
    MAX-ACCESS      read-write
    STATUS          current
    DESCRIPTION     
            "This field indicates the index of the SIP Cause Map profile"
    DEFVAL          { 0 }
    ::= { sonusSipSigServiceGroupEntry 140 }

sonusSipSigServiceGroupCondIncMethInAllow OBJECT-TYPE
    SYNTAX          SonusAdminState
    MAX-ACCESS      read-write
    STATUS          current
    DESCRIPTION     
            "This field if enabled allows outgoing ALLOW header to contain only
             subset of methods received in ALLOW header of the incoming request.
             If disabled Allow header is populated considering all the methods 
             allowed on the egress SIP SERVICE group."
    DEFVAL          { disabled }
    ::= { sonusSipSigServiceGroupEntry 141 }

sonusSipSigServiceGroupMediaRecordingSupport OBJECT-TYPE
    SYNTAX          SonusAdminState
    MAX-ACCESS      read-write
    STATUS          current
    DESCRIPTION     
            "This object controls the Service Group media recoding for the NICE feature
             This object can be set to either ENABLED or DISABLED.
             on the specified service group for the ingess leg only.
             When this object is enabled, the specified service group supports
             media recording. The default setting of this object is disabled."
    DEFVAL          { disabled }
    ::= { sonusSipSigServiceGroupEntry 142 }

sonusSipSigServiceGroupSendOriginatingCIC OBJECT-TYPE
    SYNTAX          SonusAdminState
    MAX-ACCESS      read-write
    STATUS          current
    DESCRIPTION     
            "Send Originating CIC received from ingress ISUP leg inside P-Carrier-Info header
             CMD         SENDORIGCIC
             SCREEN      SIP Service Group - Send Originating CIC
             REQS        PCR 3162"
    DEFVAL          { disabled }
    ::= { sonusSipSigServiceGroupEntry 143 }

sonusSipSigServiceGroupUseIngressChargeInfo OBJECT-TYPE
    SYNTAX          SonusAdminState
    MAX-ACCESS      read-write
    STATUS          current
    DESCRIPTION     
            "Use Charge Information received on ingress
             CMD         USEINGRESSCHGINFO
             SCREEN      SIP Service Group - Use Ingress Charge Info 
             REQS        PCR 2479"
    DEFVAL          { disabled }
    ::= { sonusSipSigServiceGroupEntry 144 }

sonusSipSigServiceGroupSendChargeInfo OBJECT-TYPE
    SYNTAX          SonusAdminState
    MAX-ACCESS      read-write
    STATUS          current
    DESCRIPTION     
            "Send Charge Information received from ingress leg inside P-ChgMsg-Info header
             CMD         SENDCHGINFO
             SCREEN      SIP Service Group - Send Charge Information 
             REQS        PCR 2479"
    DEFVAL          { disabled }
    ::= { sonusSipSigServiceGroupEntry 145 }

sonusSipSigServiceGroupMediaAddrType OBJECT-TYPE
    SYNTAX          INTEGER { sipSigAddrIpType(1), ipv4(2), ipv6(24) }
    MAX-ACCESS      read-write
    STATUS          deprecated
    DESCRIPTION     
            "Type of IP address used in offer for media address"
    DEFVAL          { 1 }
    ::= { sonusSipSigServiceGroupEntry 146 }

sonusSipSigServiceGroupOverlapTimer1 OBJECT-TYPE
    SYNTAX          Integer32 (5..15)
    MAX-ACCESS      read-write
    STATUS          current
    DESCRIPTION     
            "Time in seconds between sending subsequent INFOs before PSX returns a route. Applicable
             only for INFO based ingress overlap service groups"
    DEFVAL          { 10 }
    ::= { sonusSipSigServiceGroupEntry 149 }

sonusSipSigServiceGroupReferRejectRspCode OBJECT-TYPE
    SYNTAX          Unsigned32 (400..699)
    MAX-ACCESS      read-write
    STATUS          current
    DESCRIPTION     
            "SIP response code to be sent if a REFER request is reject because the target type
             (IP/TN) is not allowed on the trunk group."
    DEFVAL          { 403 }
    ::= { sonusSipSigServiceGroupEntry 150 }

sonusSipSigServiceGroupRedirectDisconnectCode OBJECT-TYPE
    SYNTAX          Unsigned32 (400..699)
    MAX-ACCESS      read-write
    STATUS          current
    DESCRIPTION     
            "SIP response code to be sent if a 3xx could not be relayed because the target type
             (IP/TN) is not allowed on the trunk group."
    DEFVAL          { 503 }
    ::= { sonusSipSigServiceGroupEntry 151 }

sonusSipSigServiceGroupRtcpInactivityOnCallConnect OBJECT-TYPE
    SYNTAX          INTEGER { disabled(1), enabled(2) }
    MAX-ACCESS      read-write
    STATUS          current
    DESCRIPTION     
            "This enables and disables rtcp inactivity detection
             on call connect."
    DEFVAL          { disabled }
    ::= { sonusSipSigServiceGroupEntry 152 }

sonusSipSigServiceGroupOtagProfileName OBJECT-TYPE
    SYNTAX          SonusNameReference
    MAX-ACCESS      read-write
    STATUS          current
    DESCRIPTION     
            "The Option Tag profile to be used for this service."
    ::= { sonusSipSigServiceGroupEntry 153 }

sonusSipSigServiceGroupMsrpSupport OBJECT-TYPE
    SYNTAX          SonusAdminState
    MAX-ACCESS      read-write
    STATUS          current
    DESCRIPTION     
            "MSRP support is either enabled or disabled for this sip service group. "
    DEFVAL          { disabled }
    ::= { sonusSipSigServiceGroupEntry 154 }

sonusSipSigServiceGroupPddTimeout OBJECT-TYPE
    SYNTAX          Integer32 (0..20)
    MAX-ACCESS      read-write
    STATUS          current
    DESCRIPTION     
            "Post Dial Delay timer in seconds."
    DEFVAL          { 0 }
    ::= { sonusSipSigServiceGroupEntry 155 }

sonusSipSigServiceGroupPddRspCode OBJECT-TYPE
    SYNTAX          Unsigned32 (400..699)
    MAX-ACCESS      read-write
    STATUS          current
    DESCRIPTION     
            "The SIP response code to use should the call be released 
             due to PDD timer expiry"
    DEFVAL          { 503 }
    ::= { sonusSipSigServiceGroupEntry 156 }

sonusSipSigServiceGroupDefaultNoa OBJECT-TYPE
    SYNTAX          INTEGER { subscriber(1), national(2), 
                        international(3) }
    MAX-ACCESS      read-write
    STATUS          current
    DESCRIPTION     
            "This object controls the default NOA for sip endpoints"
    DEFVAL          { national }
    ::= { sonusSipSigServiceGroupEntry 157 }

sonusSipSigServiceGroupsrstate OBJECT-TYPE
    SYNTAX          SonusAdminState
    MAX-ACCESS      read-write
    STATUS          current
    DESCRIPTION     
            "This enables and disables SUS and RES timer functionality of SR timer."
    DEFVAL          { disabled }
    ::= { sonusSipSigServiceGroupEntry 158 }

sonusSipSigServiceGroupsrvalue OBJECT-TYPE
    SYNTAX          Integer32 (1..720)
    MAX-ACCESS      read-write
    STATUS          current
    DESCRIPTION     
            "This object will set SUS and RES timer."
    DEFVAL          { 30 }
    ::= { sonusSipSigServiceGroupEntry 159 }

sonusSipSigServiceGroupNoAttemptCdrUriUser OBJECT-TYPE
    SYNTAX          DisplayString (SIZE(0..127))
    MAX-ACCESS      read-write
    STATUS          current
    DESCRIPTION     
            "Called Number or Username configured for which an attempt cdr 
             should not be generated and attempt count should not be incremented ."
    ::= { sonusSipSigServiceGroupEntry 160 }

sonusSipSigServiceGroup3xxRlyContactsInCdr OBJECT-TYPE
    SYNTAX          INTEGER { disabled(1), enabled(2) }
    MAX-ACCESS      read-write
    STATUS          current
    DESCRIPTION     
            "This object controls the logging of M/C to Attempt CDR for 3xx Relay responses"
    DEFVAL          { disabled }
    ::= { sonusSipSigServiceGroupEntry 161 }

sonusSipSigServiceGroupAllowVsc OBJECT-TYPE
    SYNTAX          SonusAdminState
    MAX-ACCESS      read-write
    STATUS          current
    DESCRIPTION     
            "This object controls GSX to allow VSC codes start with * and # in the E164 format numbers"
    DEFVAL          { disabled }
    ::= { sonusSipSigServiceGroupEntry 162 }

sonusSipSigServiceGroupJurisdictionSupport OBJECT-TYPE
    SYNTAX          SonusAdminState
    MAX-ACCESS      read-write
    STATUS          current
    DESCRIPTION     
            "JURISDICTION support is either enabled or disabled for this sip service group. "
    DEFVAL          { disabled }
    ::= { sonusSipSigServiceGroupEntry 163 }

sonusSipSigServiceGroupJipProfileName OBJECT-TYPE
    SYNTAX          SonusNameReference
    MAX-ACCESS      read-write
    STATUS          current
    DESCRIPTION     
            "The JIP profile to be used for this service."
    ::= { sonusSipSigServiceGroupEntry 164 }

sonusSipSigServiceGroupReuseIpAddrOnFqdnResolution OBJECT-TYPE
    SYNTAX          SonusAdminState
    MAX-ACCESS      read-write
    STATUS          current
    DESCRIPTION     
            "This enables and disables Reuse IP Address on Fqdn Resolution functionality."
    DEFVAL          { disabled }
    ::= { sonusSipSigServiceGroupEntry 165 }

sonusSipSigServiceGroupFeidForPDCS OBJECT-TYPE
    SYNTAX          DisplayString (SIZE(0..127))
    MAX-ACCESS      read-write
    STATUS          current
    DESCRIPTION     
            "The Feid used in P-DCS-Billing-Info header."
    ::= { sonusSipSigServiceGroupEntry 166 }

sonusSipSigServiceGroupE164LocalProfileName OBJECT-TYPE
    SYNTAX          SonusNameReference
    MAX-ACCESS      read-write
    STATUS          current
    DESCRIPTION     
            "The E164 profile to be used for this service."
    ::= { sonusSipSigServiceGroupEntry 167 }

sonusSipSigServiceGroupE164GlobalProfileName OBJECT-TYPE
    SYNTAX          SonusNameReference
    MAX-ACCESS      read-write
    STATUS          current
    DESCRIPTION     
            "The E164 profile to be used for this service."
    ::= { sonusSipSigServiceGroupEntry 168 }

sonusSipSigServiceGroupEnableSuspendResumeTimerFor OBJECT-TYPE
    SYNTAX          INTEGER { usertypeonly(0), networktypeonly(1), 
                        both(2) }
    MAX-ACCESS      read-write
    STATUS          current
    DESCRIPTION     
            " This gives the facility to start the the SR timer for user, network or both."
    DEFVAL          { both }
    ::= { sonusSipSigServiceGroupEntry 169 }

sonusSipSigServiceGroupOliSupport OBJECT-TYPE
    SYNTAX          SonusAdminState
    MAX-ACCESS      read-write
    STATUS          current
    DESCRIPTION     
            "OLI support in PAI header is either enabled or disabled for this sip service group.
             When enabled, OLI parameter will be picked from PAI of Ingress and sent in PAI of Egerss.
             Otherwise earlier behaviour is followed which is from From header."
    DEFVAL          { disabled }
    ::= { sonusSipSigServiceGroupEntry 170 }

sonusSipSigServiceGroupBlockProgressOn3xxResp OBJECT-TYPE
    SYNTAX          SonusAdminState
    MAX-ACCESS      read-write
    STATUS          current
    DESCRIPTION     
            "This control blocks the progress message towards originating side when 3XX response is received."
    DEFVAL          { disabled }
    ::= { sonusSipSigServiceGroupEntry 171 }

sonusSipSigServiceGroupMediaEarlyMediaCutThrough OBJECT-TYPE
    SYNTAX          INTEGER { sessionAnswer(1), rtpServerTable(2), 
                        pEarlyMedia(3) }
    MAX-ACCESS      read-write
    STATUS          current
    DESCRIPTION     
            "This object controls the early media cut-through mode for sip endpoints"
    DEFVAL          { rtpServerTable }
    ::= { sonusSipSigServiceGroupEntry 172 }

sonusSipSigServiceGroupMediaEgressSupport OBJECT-TYPE
    SYNTAX          SonusAdminState
    MAX-ACCESS      read-write
    STATUS          current
    DESCRIPTION     
            "This enables and disables"
    DEFVAL          { enabled }
    ::= { sonusSipSigServiceGroupEntry 173 }

sonusSipSigServiceGroupMediaDefaultGatingMethod OBJECT-TYPE
    SYNTAX          INTEGER { sendrecv(0), sendonly(1), recvonly(2), 
                        inactive(3) }
    MAX-ACCESS      read-write
    STATUS          current
    DESCRIPTION     
            "This object controls the method used for early media cut-through for sip endpoints"
    DEFVAL          { sendrecv }
    ::= { sonusSipSigServiceGroupEntry 174 }

sonusSipSigServiceGroupMediaRtpSerProf OBJECT-TYPE
    SYNTAX          SonusNameReference
    MAX-ACCESS      read-only
    STATUS          current
    DESCRIPTION     
            "The RTP Server profile name."
    DEFVAL          { "default" }
    ::= { sonusSipSigServiceGroupEntry 175 }

sonusSipSigServiceGroupNaptPublicIPBehindNATSupport OBJECT-TYPE
    SYNTAX          SonusAdminState
    MAX-ACCESS      read-write
    STATUS          current
    DESCRIPTION     
            "This indicates whether or not the devices matching this trunk group
             require NAPT support for media in special scenarios where the EPs
             are behind a NAT device and SDP C-Line does not match with the NAPT 
             Qualification Table Entry"
    DEFVAL          { disabled }
    ::= { sonusSipSigServiceGroupEntry 176 }

sonusSipSigServiceGroupLockDwnPreferredCodec OBJECT-TYPE
    SYNTAX          INTEGER { disabled(1), enabled(2) }
    MAX-ACCESS      read-write
    STATUS          current
    DESCRIPTION     
            "Lock Down Preferred Codec is either enabled or disabled for this sip service group. "
    DEFVAL          { disabled }
    ::= { sonusSipSigServiceGroupEntry 178 }

sonusSipSigServiceGroupUseNonDefaultCauseCodeForARSBlacklist OBJECT-TYPE
    SYNTAX          SonusAdminState
    MAX-ACCESS      read-write
    STATUS          current
    DESCRIPTION     
            "This indicates whether we use new cpc disc code 169 for ARS or old 151"
    DEFVAL          { disabled }
    ::= { sonusSipSigServiceGroupEntry 179 }

sonusSipSigServiceGroupNoRdiUpdateOn3xx OBJECT-TYPE
    SYNTAX          SonusAdminState
    MAX-ACCESS      read-write
    STATUS          current
    DESCRIPTION     
            "This control is used to update the RDI information in the outgoing 
             ISUP IAM/SIP INVITE/SIPI INVITE(IAM) after 3XX redirection"
    DEFVAL          { disabled }
    ::= { sonusSipSigServiceGroupEntry 180 }

sonusSipSigServiceGroupSourceAddressValidation OBJECT-TYPE
    SYNTAX          INTEGER { disabled(0), enabled(1) }
    MAX-ACCESS      read-write
    STATUS          current
    DESCRIPTION     
            "Source address validation performs security checks to ensure 
             that calls from unauthorized IP are not allowed"
    DEFVAL          { disabled }
    ::= { sonusSipSigServiceGroupEntry 181 }

sonusSipSigServiceGroupRewriteIdentities OBJECT-TYPE
    SYNTAX          SonusAdminState
    MAX-ACCESS      read-write
    STATUS          current
    DESCRIPTION     
            "This flag enables enhanced SIP URI transparency feature where IP Address received in certain headers
             will be mapped to domain names and domain name will be preserved if received in these headers."
    DEFVAL          { disabled }
    ::= { sonusSipSigServiceGroupEntry 182 }

sonusSipSigServiceGroupAcceptHistoryInfo OBJECT-TYPE
    SYNTAX          SonusAdminState
    MAX-ACCESS      read-write
    STATUS          current
    DESCRIPTION     
            "This object controls processing of history info header"
    DEFVAL          { disabled }
    ::= { sonusSipSigServiceGroupEntry 183 }

sonusSipSigServiceGroupJapanMnpLnpMapping OBJECT-TYPE
    SYNTAX          SonusAdminState
    MAX-ACCESS      read-write
    STATUS          current
    DESCRIPTION     
            "This flag enables enhanced SIP URI transparency feature where IP Address received in certain headers
             will be mapped to domain names and domain name will be preserved if received in these headers."
    DEFVAL          { disabled }
    ::= { sonusSipSigServiceGroupEntry 184 }

sonusSipSigServiceGroupSendSdpToPsx OBJECT-TYPE
    SYNTAX          SonusAdminState
    MAX-ACCESS      read-write
    STATUS          current
    DESCRIPTION     
            "When this flag enabled, SDP information with m-lines and related a-lines will be sent to PSX
             in policy request for the SIP SCP enhancement."
    DEFVAL          { disabled }
    ::= { sonusSipSigServiceGroupEntry 185 }

sonusSipSigServiceGroupPopulateRN OBJECT-TYPE
    SYNTAX          SonusAdminState
    MAX-ACCESS      read-write
    STATUS          current
    DESCRIPTION     
            "If this flag is enabled and a Single Diversion Header is encountered, the diversion information 
             will be copied only to the Redirecting Number(RN) structure but not to the Original Called Number (OCN) structure."
    DEFVAL          { disabled }
    ::= { sonusSipSigServiceGroupEntry 186 }

sonusSipSigServiceGroupEmgrCallIntwkTreatment OBJECT-TYPE
    SYNTAX          SonusAdminState
    MAX-ACCESS      read-write
    STATUS          current
    DESCRIPTION     
            "This flag when enabled, will provide Emergency call treatment for Specific Headers, namely
             Resource-Priority:emgr.0 and Priority:emergency."
    DEFVAL          { disabled }
    ::= { sonusSipSigServiceGroupEntry 187 }

sonusSipSigServiceGroupSilenceSuppTreatment OBJECT-TYPE
    SYNTAX          INTEGER { treatAsFaxTransmissionIndication(0), 
                        treatAsG711SilenceSuppOff(1) }
    MAX-ACCESS      read-write
    STATUS          current
    DESCRIPTION     
            "This object controls the silence suppression treatment. 
             When enabled(treatAsG711SilenceSuppOff), a ReInvite received with G711 SS:Off will be considered as a voice call rather than fax."
    DEFVAL          { treatAsFaxTransmissionIndication }
    ::= { sonusSipSigServiceGroupEntry 188 }

sonusSipSigServiceGroupGtdFeature OBJECT-TYPE
    SYNTAX          SonusAdminState
    MAX-ACCESS      read-write
    STATUS          current
    DESCRIPTION     
            "This flag is used for SIP GTD Feature."
    DEFVAL          { disabled }
    ::= { sonusSipSigServiceGroupEntry 189 }

sonusSipSigServiceGroupGtdMode OBJECT-TYPE
    SYNTAX          INTEGER { compact(1), verbose(2) }
    MAX-ACCESS      read-write
    STATUS          current
    DESCRIPTION     
            "SIP GTD encoding format Mode."
    DEFVAL          { compact }
    ::= { sonusSipSigServiceGroupEntry 190 }

sonusSipSigServiceGroupGtdIsupSigGrp OBJECT-TYPE
    SYNTAX          SonusNameReference
    MAX-ACCESS      read-write
    STATUS          current
    DESCRIPTION     
            "The ISUP SIGNALING GROUP to be used for ingress SIP-GTD leg."
    ::= { sonusSipSigServiceGroupEntry 191 }

sonusSipSigServiceGroupTransparencyProfileName OBJECT-TYPE
    SYNTAX          SonusNameReference
    MAX-ACCESS      read-write
    STATUS          current
    DESCRIPTION     
            "The Transparency profile to be used for this service.
             None assigned means no Receive Side Filter."
    ::= { sonusSipSigServiceGroupEntry 192 }

sonusSipSigServiceGroupUseGAPWhenRnDisabled OBJECT-TYPE
    SYNTAX          SonusAdminState
    MAX-ACCESS      read-write
    STATUS          current
    DESCRIPTION     
            "Enable disableRn flag on egress profile and enable useGAPWhenRnDisabled flag on the egress trunk group
             then the outgoing INVITE from GSX should not have RN parameter and user info part of the R-URI and TO header 
             should contain the GAP/OCN number."
    DEFVAL          { disabled }
    ::= { sonusSipSigServiceGroupEntry 193 }

sonusSipSigServiceGroupEnhancedARS OBJECT-TYPE
    SYNTAX          SonusAdminState
    MAX-ACCESS      read-write
    STATUS          current
    DESCRIPTION     
            "This flag ENABLES or DISABLE 
             ARS Enhanced Blacklisting.
             By default this flag is in disable state"
    DEFVAL          { disabled }
    ::= { sonusSipSigServiceGroupEntry 194 }

sonusSipSigServiceGroupMapIsupCgpnToPAI OBJECT-TYPE
    SYNTAX          SonusAdminState
    MAX-ACCESS      read-write
    STATUS          current
    DESCRIPTION     
            "This flag ENABLES or DISABLE 
             mapping ISUP calling party number to PAI header.
             By default this flag is in disable state"
    DEFVAL          { disabled }
    ::= { sonusSipSigServiceGroupEntry 195 }

sonusSipSigServiceGroupMapFromHeaderToIsupGAP OBJECT-TYPE
    SYNTAX          SonusAdminState
    MAX-ACCESS      read-write
    STATUS          current
    DESCRIPTION     
            "This flag ENABLES or DISABLE 
             mapping FROM header to ISUP GAP parameter.
             By default this flag is in disable state"
    DEFVAL          { disabled }
    ::= { sonusSipSigServiceGroupEntry 196 }

sonusSipSigServiceGroupStatTable OBJECT-TYPE
    SYNTAX          SEQUENCE OF SonusSipSigServiceGroupStatEntry
    MAX-ACCESS      not-accessible
    STATUS          current
    DESCRIPTION     
            "This table contains status information about each SIP Service
             Group in the GSX9000 Switch node."
    ::= { sonusSipSigServiceGroup 3 }

sonusSipSigServiceGroupStatEntry OBJECT-TYPE
    SYNTAX          SonusSipSigServiceGroupStatEntry
    MAX-ACCESS      not-accessible
    STATUS          current
    DESCRIPTION     
            "This table describes the status of the SIP Service Groups."
    INDEX           { sonusSipSigServiceGroupStatListIndex }
    ::= { sonusSipSigServiceGroupStatTable 1 }

SonusSipSigServiceGroupStatEntry ::=
    SEQUENCE {
        sonusSipSigServiceGroupStatListIndex    Integer32,
        sonusSipSigServiceGroupStatStatus INTEGER
    }

sonusSipSigServiceGroupStatListIndex OBJECT-TYPE
    SYNTAX          Integer32 (1..256)
    MAX-ACCESS      read-only
    STATUS          current
    DESCRIPTION     
            "The index of the SIP Service Group."
    ::= { sonusSipSigServiceGroupStatEntry 1 }

sonusSipSigServiceGroupStatStatus OBJECT-TYPE
    SYNTAX          INTEGER { available(1), unavailable(2), dryup(3) }
    MAX-ACCESS      read-only
    STATUS          current
    DESCRIPTION     
            "The state of the SIP Service Group."
    ::= { sonusSipSigServiceGroupStatEntry 2 }

sonusSipSig180NoSdpConfigObjects OBJECT IDENTIFIER
    ::= { sonusSipSignallingMIBObjects 8 }

sonusSipSig180NoSdpAdminState OBJECT-TYPE
    SYNTAX          SonusAdminState
    MAX-ACCESS      read-write
    STATUS          obsolete
    DESCRIPTION     
            "This configuration can control whether or not to include SDP in 180. When disabled, GSX may send 180 with SDP included. When enabled, SIPSG never includes SDP in 180 and uses 183 to send SDP.
             This object is made obsolete in GSX release 6.3.X."
    DEFVAL          { disabled }
    ::= { sonusSipSig180NoSdpConfigObjects 1 }

sonusSipSigMethodObjects OBJECT IDENTIFIER
    ::= { sonusSipSignallingMIBObjects 9 }

sonusSipSigMethodOptions OBJECT-TYPE
    SYNTAX          INTEGER { allow(1), reject(2) }
    MAX-ACCESS      read-write
    STATUS          obsolete
    DESCRIPTION     
            "Determines whether OPTIONS request is accepted and processed or rejected with 405.
             This object is made obsolete in GSX release 6.3.X."
    DEFVAL          { 1 }
    ::= { sonusSipSigMethodObjects 1 }

sonusSipSigMethodRefer OBJECT-TYPE
    SYNTAX          INTEGER { allow(1), reject(2) }
    MAX-ACCESS      read-write
    STATUS          obsolete
    DESCRIPTION     
            "Determines whether REFER request is accepted and processed or rejected with 405.
             This object is made obsolete in release GSX 6.3.X."
    DEFVAL          { 1 }
    ::= { sonusSipSigMethodObjects 2 }

sonusSipSigMethodSubscribe OBJECT-TYPE
    SYNTAX          INTEGER { allow(1), reject(2) }
    MAX-ACCESS      read-write
    STATUS          obsolete
    DESCRIPTION     
            "Determines whether SUBSCRIBE request is accepted and processed or rejected with 405.
             This object is made obsolete in GSX release 6.3.X."
    DEFVAL          { 1 }
    ::= { sonusSipSigMethodObjects 3 }

sonusSipSigMethodNotify OBJECT-TYPE
    SYNTAX          INTEGER { allow(1), reject(2) }
    MAX-ACCESS      read-write
    STATUS          obsolete
    DESCRIPTION     
            "Determines whether NOTIFY request is accepted and processed or rejected with 405.
             This object is made obsolete in GSX release 6.3.X."
    DEFVAL          { 1 }
    ::= { sonusSipSigMethodObjects 4 }

sonusSipSigMethodInfo OBJECT-TYPE
    SYNTAX          INTEGER { allow(1), reject(2) }
    MAX-ACCESS      read-write
    STATUS          obsolete
    DESCRIPTION     
            "Determines whether INFO method is allowed to be included in the Allow header.
             This object is made obsolete in GSX release 6.3.X"
    DEFVAL          { 1 }
    ::= { sonusSipSigMethodObjects 5 }

sonusRtpServerObjects OBJECT IDENTIFIER
    ::= { sonusSipSignallingMIBObjects 10 }

sonusRtpServerProfileNextIndex OBJECT-TYPE
    SYNTAX          Integer32 (1)
    MAX-ACCESS      read-only
    STATUS          current
    DESCRIPTION     
            "The next valid index to use when creating a new sonusRtpServerObject"
    ::= { sonusRtpServerObjects 1 }

sonusRtpServerProfileTable OBJECT-TYPE
    SYNTAX          SEQUENCE OF SonusRtpServerProfileEntry
    MAX-ACCESS      not-accessible
    STATUS          current
    DESCRIPTION     
            "This mib table is used to create a name for a  RTP Server Profile table."
    ::= { sonusRtpServerObjects 2 }

sonusRtpServerProfileEntry OBJECT-TYPE
    SYNTAX          SonusRtpServerProfileEntry
    MAX-ACCESS      not-accessible
    STATUS          current
    DESCRIPTION     
            "This mib table is used to create a name for  RTP Server Profile table."
    INDEX           { sonusRtpServerProfileIndex }
    ::= { sonusRtpServerProfileTable 1 }

SonusRtpServerProfileEntry ::=
    SEQUENCE {
        sonusRtpServerProfileIndex      Integer32,
        sonusRtpServerProfileName       SonusName,
        sonusRtpServerProfileRowStatus  RowStatus
    }

sonusRtpServerProfileIndex OBJECT-TYPE
    SYNTAX          Integer32
    MAX-ACCESS      read-only
    STATUS          current
    DESCRIPTION     
            "A unique index for this  RTP Server Profile table name."
    ::= { sonusRtpServerProfileEntry 1 }

sonusRtpServerProfileName OBJECT-TYPE
    SYNTAX          SonusName
    MAX-ACCESS      read-only
    STATUS          current
    DESCRIPTION     
            "The name of the RTP Server Profile table."
    ::= { sonusRtpServerProfileEntry 2 }

sonusRtpServerProfileRowStatus OBJECT-TYPE
    SYNTAX          RowStatus
    MAX-ACCESS      read-write
    STATUS          current
    DESCRIPTION     
            "This is for SNMP use."
    ::= { sonusRtpServerProfileEntry 3 }

sonusRtpServerNumberTable OBJECT-TYPE
    SYNTAX          SEQUENCE OF SonusRtpServerNumberEntry
    MAX-ACCESS      not-accessible
    STATUS          current
    DESCRIPTION     
            "This mib table is for  RTP Server Number Table Entries."
    ::= { sonusRtpServerObjects 3 }

sonusRtpServerNumberEntry OBJECT-TYPE
    SYNTAX          SonusRtpServerNumberEntry
    MAX-ACCESS      not-accessible
    STATUS          current
    DESCRIPTION     
            "This mib table is for  RTP Server Number Table Entries."
    INDEX           { sonusRtpServerNumberProfileIndex, 
                      sonusRtpServerNumberIpAddress, 
                      sonusRtpServerNumberNetMask, 
                      sonusRtpServerNumberIp6Address, 
                      sonusRtpServerNumberIp6Prefix, 
                      sonusRtpServerNumberIpVersion }
    ::= { sonusRtpServerNumberTable 1 }

SonusRtpServerNumberEntry ::=
    SEQUENCE {
        sonusRtpServerNumberProfileIndex Integer32,
        sonusRtpServerNumberIpAddress   IpAddress,
        sonusRtpServerNumberNetMask     IpAddress,
        sonusRtpServerNumberRowStatus   RowStatus,
        sonusRtpServerNumberIp6Address  Ipv6Address,
        sonusRtpServerNumberIp6Prefix   Integer32,
        sonusRtpServerNumberIpVersion   INTEGER
    }

sonusRtpServerNumberProfileIndex OBJECT-TYPE
    SYNTAX          Integer32
    MAX-ACCESS      read-only
    STATUS          current
    DESCRIPTION     
            "Unique  RTP Server Number Table index."
    ::= { sonusRtpServerNumberEntry 1 }

sonusRtpServerNumberIpAddress OBJECT-TYPE
    SYNTAX          IpAddress
    MAX-ACCESS      read-only
    STATUS          current
    DESCRIPTION     
            "Ip Address."
    ::= { sonusRtpServerNumberEntry 2 }

sonusRtpServerNumberNetMask OBJECT-TYPE
    SYNTAX          IpAddress
    MAX-ACCESS      read-only
    STATUS          current
    DESCRIPTION     
            "Net Mask."
    ::= { sonusRtpServerNumberEntry 3 }

sonusRtpServerNumberRowStatus OBJECT-TYPE
    SYNTAX          RowStatus
    MAX-ACCESS      read-write
    STATUS          current
    DESCRIPTION     
            "This is for SNMP use."
    ::= { sonusRtpServerNumberEntry 4 }

sonusRtpServerNumberIp6Address OBJECT-TYPE
    SYNTAX          Ipv6Address
    MAX-ACCESS      read-write
    STATUS          current
    DESCRIPTION     
            "Ipv6 Address."
    ::= { sonusRtpServerNumberEntry 5 }

sonusRtpServerNumberIp6Prefix OBJECT-TYPE
    SYNTAX          Integer32
    MAX-ACCESS      read-write
    STATUS          current
    DESCRIPTION     
            "IpV6 Address Prefix."
    ::= { sonusRtpServerNumberEntry 6 }

sonusRtpServerNumberIpVersion OBJECT-TYPE
    SYNTAX          INTEGER { afInet(2), afInet6(24) }
    MAX-ACCESS      read-only
    STATUS          current
    DESCRIPTION     
            "Ip Address type ."
    ::= { sonusRtpServerNumberEntry 7 }

sonusSipSigControlsObjects OBJECT IDENTIFIER
    ::= { sonusSipSignallingMIBObjects 11 }

sonusSipSigControlsLoopDetectionFeature OBJECT-TYPE
    SYNTAX          INTEGER { disabled(1), enabled(2) }
    MAX-ACCESS      read-write
    STATUS          current
    DESCRIPTION     
            "This object indicates whether or, not the SIP Stack will
             perform loop detection on incoming INVITE messages. When
             DISABLED, the SIP stack on the GSX will not perform loop
             detection on an incoming INVITE message, and will allow
             SIPSG to process the INVITE message."
    DEFVAL          { enabled }
    ::= { sonusSipSigControlsObjects 1 }

sonusSipSigControlsStatsticsFeature OBJECT-TYPE
    SYNTAX          INTEGER { disabled(1), enabled(2) }
    MAX-ACCESS      read-write
    STATUS          current
    DESCRIPTION     
            "This object indicates whether or, not the SIP Stack will
             perform loop detection on incoming INVITE messages. When
             DISABLED, the SIP stack on the GSX will not perform loop
             detection on an incoming INVITE message, and will allow
             SIPSG to process the INVITE message."
    DEFVAL          { disabled }
    ::= { sonusSipSigControlsObjects 2 }

sonusSipSigControlsRegistrarSupportContactParam OBJECT-TYPE
    SYNTAX          INTEGER { disabled(1), enabled(2) }
    MAX-ACCESS      read-write
    STATUS          current
    DESCRIPTION     
            "TBD..."
    DEFVAL          { disabled }
    ::= { sonusSipSigControlsObjects 3 }

sonusSipSigControlsSuppressErrorInfoHdr OBJECT-TYPE
    SYNTAX          INTEGER { disabled(1), enabled(2) }
    MAX-ACCESS      read-write
    STATUS          current
    DESCRIPTION     
            "This object indicates whether or, not the GSX will
             supress the Error-Info header in response to a request message with syntax error. 
             When ENABLE, the GSX will not include the Error-Info header in response message."
    DEFVAL          { disabled }
    ::= { sonusSipSigControlsObjects 4 }

sonusSipSigControlsMaxPduSizeState OBJECT-TYPE
    SYNTAX          SonusAdminState
    MAX-ACCESS      read-write
    STATUS          current
    DESCRIPTION     
            "This object indicates whether, or not the SIP Stack
             has ENABLED or DISABLED the SIP Maximum PDU Size feature.
             If DISABLED, the SIP Maximum PDU Size = 2KB.
             If ENABLED, the SIP Maximum PDU Size is defined by
             the SIP Maximum PDU Size Value."
    DEFVAL          { disabled }
    ::= { sonusSipSigControlsObjects 5 }

sonusSipSigControlsMaxPduSizeValue OBJECT-TYPE
    SYNTAX          INTEGER { pdusize2kb(2), pdusize3kb(3), 
                        pdusize6kb(4) }
    MAX-ACCESS      read-write
    STATUS          current
    DESCRIPTION     
            "This object indicates the SIP Maximum PDU Size Value."
    DEFVAL          { pdusize2kb }
    ::= { sonusSipSigControlsObjects 6 }

sonusSipSigControlsMaxPduSize OBJECT-TYPE
    SYNTAX          INTEGER { pdusize2kb(2), pdusize3kb(3), 
                        pdusize6kb(4) }
    MAX-ACCESS      read-only
    STATUS          current
    DESCRIPTION     
            "This object indicates the SIP Maximum PDU Size
             that is currently in use by the system."
    DEFVAL          { pdusize2kb }
    ::= { sonusSipSigControlsObjects 7 }

sonusSipSigControlsEgressRNParam OBJECT-TYPE
    SYNTAX          INTEGER { enabled(1), disabled(2) }
    MAX-ACCESS      read-write
    STATUS          current
    DESCRIPTION     
            "Not include RN param for ATT in Egress"
    DEFVAL          { disabled }
    ::= { sonusSipSigControlsObjects 8 }

sonusSipSigControlsProcessInvalidCancelReq OBJECT-TYPE
    SYNTAX          INTEGER { disabled(1), enabled(2) }
    MAX-ACCESS      read-write
    STATUS          obsolete
    DESCRIPTION     
            "This object indicates whether or, not the SIP Stack will
             process invalid CANCEL request from UAS. CANCEL request is 
             valid when sent from UAC before INVITE is responded with 
             200 OK request. This object is made obsolete in release 7.2.1"
    DEFVAL          { disabled }
    ::= { sonusSipSigControlsObjects 9 }

sonusSipSigControlsMultipleContactsPerAOR OBJECT-TYPE
    SYNTAX          SonusAdminState
    MAX-ACCESS      read-write
    STATUS          current
    DESCRIPTION     
            "If enabled per AOR multiple bindings shall be supported"
    DEFVAL          { disabled }
    ::= { sonusSipSigControlsObjects 10 }

sonusSipSigControlsSiploopbackPrimerValue OBJECT-TYPE
    SYNTAX          Integer32 (96..127)
    MAX-ACCESS      read-write
    STATUS          current
    DESCRIPTION     
            "SIP Loopback Primer value"
    DEFVAL          { 114 }
    ::= { sonusSipSigControlsObjects 11 }

sonusSipSigControlsNpdiMbitState OBJECT-TYPE
    SYNTAX          SonusAdminState
    MAX-ACCESS      read-write
    STATUS          current
    DESCRIPTION     
            "This object indicates whether or not the SIP NPDI M-bit Feature is ENABLED.
             When this feature is enabled, the SIP code will check the state of the M-bit
             in the PSX policy response egress parameters to decide whether or not to
             send NPDI in the egress INVITE."
    DEFVAL          { disabled }
    ::= { sonusSipSigControlsObjects 13 }

sonusSipToCpcCauseMappingObject OBJECT IDENTIFIER
    ::= { sonusSipSignallingMIBObjects 12 }

sonusSipToCpcCauseMappingProfile OBJECT IDENTIFIER
    ::= { sonusSipToCpcCauseMappingObject 1 }

sonusSipToCpcCauseMappingProfileNextIndex OBJECT-TYPE
    SYNTAX          Integer32
    MAX-ACCESS      read-only
    STATUS          current
    DESCRIPTION     
            "The next valid index to use when creating a new sonusSipToCpcCauseMappingProfileTable"
    ::= { sonusSipToCpcCauseMappingProfile 1 }

sonusSipToCpcCauseMappingProfileTable OBJECT-TYPE
    SYNTAX          SEQUENCE OF SonusSipToCpcCauseMappingProfileEntry
    MAX-ACCESS      not-accessible
    STATUS          current
    DESCRIPTION     
            "This table contains information about each SIP cause Profile
             configured to be a member of the node. 
             A management entity may create rows for Service Group that are
             anticipated to be supported in the future."
    ::= { sonusSipToCpcCauseMappingProfile 2 }

sonusSipToCpcCauseMappingProfileEntry OBJECT-TYPE
    SYNTAX          SonusSipToCpcCauseMappingProfileEntry
    MAX-ACCESS      not-accessible
    STATUS          current
    DESCRIPTION     
            "This table describes the SIP-to-CPC cause mapping that are configured."
    INDEX           { sonusSipToCpcCauseMappingProfileIndex }
    ::= { sonusSipToCpcCauseMappingProfileTable 1 }

SonusSipToCpcCauseMappingProfileEntry ::=
    SEQUENCE {
        sonusSipToCpcCauseMappingProfileIndex     Integer32,
        sonusSipToCpcCauseMappingProfileName    SonusName,
        sonusSipToCpcCauseMappingBaseProfile    INTEGER,
        sonusSipToCpcCauseMappingProfileRowStatus         RowStatus,
        sonusSipToCpcCauseMappingIndexProfileVersion            Integer32,
        sonusSipToCpcCauseMappingProfileCancelCause           Integer32,
        sonusSipToCpcCauseMappingProfileByeLoc      INTEGER,
        sonusSipToCpcCauseMappingProfileCancelLoc         INTEGER,
        sonusSipToCpcCauseMappingProfile3xxLoc      INTEGER,
        sonusSipToCpcCauseMappingProfile4xxLoc      INTEGER,
        sonusSipToCpcCauseMappingProfile5xxLoc      INTEGER,
        sonusSipToCpcCauseMappingProfile6xxLoc      INTEGER
    }

sonusSipToCpcCauseMappingProfileIndex OBJECT-TYPE
    SYNTAX          Integer32 (1..128)
    MAX-ACCESS      read-only
    STATUS          current
    DESCRIPTION     
            "Identifies the SIP-To-CPC cause mapping Profile."
    ::= { sonusSipToCpcCauseMappingProfileEntry 1 }

sonusSipToCpcCauseMappingProfileName OBJECT-TYPE
    SYNTAX          SonusName
    MAX-ACCESS      read-write
    STATUS          current
    DESCRIPTION     
            "The user name of the SipToCpcCauseMapping Profile."
    ::= { sonusSipToCpcCauseMappingProfileEntry 2 }

sonusSipToCpcCauseMappingBaseProfile OBJECT-TYPE
    SYNTAX          INTEGER { defaultSipCpc(1), defaultQ1912SipCpc(2), 
                        defaultRfc3398SipCpc(3), defaultTs29163SipCpc(4) }
    MAX-ACCESS      read-write
    STATUS          current
    DESCRIPTION     
            "The name of the SIPtoCPC Profile on which to base the new profile."
    ::= { sonusSipToCpcCauseMappingProfileEntry 3 }

sonusSipToCpcCauseMappingProfileRowStatus OBJECT-TYPE
    SYNTAX          RowStatus
    MAX-ACCESS      read-write
    STATUS          current
    DESCRIPTION     
            ""
    ::= { sonusSipToCpcCauseMappingProfileEntry 4 }

sonusSipToCpcCauseMappingIndexProfileVersion OBJECT-TYPE
    SYNTAX          Integer32 (1..64)
    MAX-ACCESS      read-write
    STATUS          current
    DESCRIPTION     
            "Identifies the SIP-To-CPC cause mapping Profile Index Version."
    ::= { sonusSipToCpcCauseMappingProfileEntry 5 }

sonusSipToCpcCauseMappingProfileCancelCause OBJECT-TYPE
    SYNTAX          Integer32 (1..127)
    MAX-ACCESS      read-write
    STATUS          current
    DESCRIPTION     
            "The CPC cause value set when a CANCEL is received."
    ::= { sonusSipToCpcCauseMappingProfileEntry 6 }

sonusSipToCpcCauseMappingProfileByeLoc OBJECT-TYPE
    SYNTAX          INTEGER { user(1), localPrivateNetwork(2), 
                        localLocalNetwork(3), transitNetwork(4), 
                        remoteLocalNetwork(5), remotePrivateNetwork(6), 
                        localInterfaceControlledByThisSigLink(7), 
                        internationalNetwork(8), networkBeyondPoint(9), 
                        privateBranchExchange(10) }
    MAX-ACCESS      read-write
    STATUS          current
    DESCRIPTION     
            "The Location to be set when a BYE is received."
    ::= { sonusSipToCpcCauseMappingProfileEntry 7 }

sonusSipToCpcCauseMappingProfileCancelLoc OBJECT-TYPE
    SYNTAX          INTEGER { user(1), localPrivateNetwork(2), 
                        localLocalNetwork(3), transitNetwork(4), 
                        remoteLocalNetwork(5), remotePrivateNetwork(6), 
                        localInterfaceControlledByThisSigLink(7), 
                        internationalNetwork(8), networkBeyondPoint(9), 
                        privateBranchExchange(10) }
    MAX-ACCESS      read-write
    STATUS          current
    DESCRIPTION     
            "The Location to be set when a CANCEL is received."
    ::= { sonusSipToCpcCauseMappingProfileEntry 8 }

sonusSipToCpcCauseMappingProfile3xxLoc OBJECT-TYPE
    SYNTAX          INTEGER { user(1), localPrivateNetwork(2), 
                        localLocalNetwork(3), transitNetwork(4), 
                        remoteLocalNetwork(5), remotePrivateNetwork(6), 
                        localInterfaceControlledByThisSigLink(7), 
                        internationalNetwork(8), networkBeyondPoint(9), 
                        privateBranchExchange(10) }
    MAX-ACCESS      read-write
    STATUS          current
    DESCRIPTION     
            "The Location to be set when a 3xx is received."
    ::= { sonusSipToCpcCauseMappingProfileEntry 9 }

sonusSipToCpcCauseMappingProfile4xxLoc OBJECT-TYPE
    SYNTAX          INTEGER { user(1), localPrivateNetwork(2), 
                        localLocalNetwork(3), transitNetwork(4), 
                        remoteLocalNetwork(5), remotePrivateNetwork(6), 
                        localInterfaceControlledByThisSigLink(7), 
                        internationalNetwork(8), networkBeyondPoint(9), 
                        privateBranchExchange(10) }
    MAX-ACCESS      read-write
    STATUS          current
    DESCRIPTION     
            "The Location to be set when a 4xx is received."
    ::= { sonusSipToCpcCauseMappingProfileEntry 10 }

sonusSipToCpcCauseMappingProfile5xxLoc OBJECT-TYPE
    SYNTAX          INTEGER { user(1), localPrivateNetwork(2), 
                        localLocalNetwork(3), transitNetwork(4), 
                        remoteLocalNetwork(5), remotePrivateNetwork(6), 
                        localInterfaceControlledByThisSigLink(7), 
                        internationalNetwork(8), networkBeyondPoint(9), 
                        privateBranchExchange(10) }
    MAX-ACCESS      read-write
    STATUS          current
    DESCRIPTION     
            "The Location to be set when a 5xx is received."
    ::= { sonusSipToCpcCauseMappingProfileEntry 11 }

sonusSipToCpcCauseMappingProfile6xxLoc OBJECT-TYPE
    SYNTAX          INTEGER { user(1), localPrivateNetwork(2), 
                        localLocalNetwork(3), transitNetwork(4), 
                        remoteLocalNetwork(5), remotePrivateNetwork(6), 
                        localInterfaceControlledByThisSigLink(7), 
                        internationalNetwork(8), networkBeyondPoint(9), 
                        privateBranchExchange(10) }
    MAX-ACCESS      read-write
    STATUS          current
    DESCRIPTION     
            "The Location to be set when a 6xx is received."
    ::= { sonusSipToCpcCauseMappingProfileEntry 12 }

sonusSipSgFromCauseMappingAdmnTable OBJECT-TYPE
    SYNTAX          SEQUENCE OF SonusSipSgFromCauseMappingAdmnEntry
    MAX-ACCESS      not-accessible
    STATUS          current
    DESCRIPTION     
            "SIP-to-CPC cause mapping Table"
    ::= { sonusSipToCpcCauseMappingObject 2 }

sonusSipSgFromCauseMappingAdmnEntry OBJECT-TYPE
    SYNTAX          SonusSipSgFromCauseMappingAdmnEntry
    MAX-ACCESS      not-accessible
    STATUS          current
    DESCRIPTION     
            "This table describes the SIP-to-CPC cause mapping that are configured."
    INDEX           { sonusSipToCpcCauseBackwardMappingProfileIndex, 
                      sonusSipToCpcCauseMappingSipCause }
    ::= { sonusSipSgFromCauseMappingAdmnTable 1 }

SonusSipSgFromCauseMappingAdmnEntry ::=
    SEQUENCE {
        sonusSipToCpcCauseBackwardMappingProfileIndex             Integer32,
        sonusSipToCpcCauseMappingSipCause Integer32,
        sonusSipToCpcCauseMappingCpcCause Integer32,
        sonusSipToCpcCauseMappingRowStatus  RowStatus
    }

sonusSipToCpcCauseBackwardMappingProfileIndex OBJECT-TYPE
    SYNTAX          Integer32
    MAX-ACCESS      not-accessible
    STATUS          current
    DESCRIPTION     
            "Identifies the SipSGFromCauseMapping Profile to which this entry belongs."
    ::= { sonusSipSgFromCauseMappingAdmnEntry 1 }

sonusSipToCpcCauseMappingSipCause OBJECT-TYPE
    SYNTAX          Integer32 (300..606)
    MAX-ACCESS      read-write
    STATUS          current
    DESCRIPTION     
            "SIP Cause value "
    ::= { sonusSipSgFromCauseMappingAdmnEntry 2 }

sonusSipToCpcCauseMappingCpcCause OBJECT-TYPE
    SYNTAX          Integer32 (1..127)
    MAX-ACCESS      read-write
    STATUS          current
    DESCRIPTION     
            "CPC Cause value "
    ::= { sonusSipSgFromCauseMappingAdmnEntry 3 }

sonusSipToCpcCauseMappingRowStatus OBJECT-TYPE
    SYNTAX          RowStatus
    MAX-ACCESS      read-write
    STATUS          current
    DESCRIPTION     
            ""
    ::= { sonusSipSgFromCauseMappingAdmnEntry 4 }

sonusCpcToSipCauseMappingObject OBJECT IDENTIFIER
    ::= { sonusSipSignallingMIBObjects 13 }

sonusCpcToSipCauseMappingProfile OBJECT IDENTIFIER
    ::= { sonusCpcToSipCauseMappingObject 1 }

sonusCpcToSipCauseMappingProfileNextIndex OBJECT-TYPE
    SYNTAX          Integer32
    MAX-ACCESS      read-write
    STATUS          current
    DESCRIPTION     
            "The next valid index to use when creating a new sonusCpcToSipCauseMappingProfileTable"
    ::= { sonusCpcToSipCauseMappingProfile 1 }

sonusCpcToSipCauseMappingProfileTable OBJECT-TYPE
    SYNTAX          SEQUENCE OF SonusCpcToSipCauseMappingProfileEntry
    MAX-ACCESS      not-accessible
    STATUS          current
    DESCRIPTION     
            "This table contains information about each CPC to SIP cause Profile
             configured to be a member of the node."
    ::= { sonusCpcToSipCauseMappingProfile 2 }

sonusCpcToSipCauseMappingProfileEntry OBJECT-TYPE
    SYNTAX          SonusCpcToSipCauseMappingProfileEntry
    MAX-ACCESS      not-accessible
    STATUS          current
    DESCRIPTION     
            "This table describes the SIP-to-CPC cause mapping that are configured."
    INDEX           { sonusCpcToSipCauseMappingProfileIndex }
    ::= { sonusCpcToSipCauseMappingProfileTable 1 }

SonusCpcToSipCauseMappingProfileEntry ::=
    SEQUENCE {
        sonusCpcToSipCauseMappingProfileIndex     Integer32,
        sonusCpcToSipCauseMappingProfileName    SonusName,
        sonusCpcToSipCauseMappingBaseProfile    INTEGER,
        sonusCpcToSipCauseMappingProfileRowStatus         RowStatus,
        sonusCpcToSipCauseMappingIndexProfileVersion            Integer32,
        sonusCpcToSipCauseMappingProfileUnrecAction           INTEGER,
        sonusCpcToSipCauseMappingProfileIncludeQ850Reason                 SonusAdminState
    }

sonusCpcToSipCauseMappingProfileIndex OBJECT-TYPE
    SYNTAX          Integer32 (1..128)
    MAX-ACCESS      read-only
    STATUS          current
    DESCRIPTION     
            "Identifies the SIP-To-CPC cause mapping Profile."
    ::= { sonusCpcToSipCauseMappingProfileEntry 1 }

sonusCpcToSipCauseMappingProfileName OBJECT-TYPE
    SYNTAX          SonusName
    MAX-ACCESS      read-write
    STATUS          current
    DESCRIPTION     
            "The user name of the CpcToSipCauseMapping Profile."
    ::= { sonusCpcToSipCauseMappingProfileEntry 2 }

sonusCpcToSipCauseMappingBaseProfile OBJECT-TYPE
    SYNTAX          INTEGER { defaultCpcSip(1), defaultQ1912CpcSip(2), 
                        defaultRfc3398CpcSip(3), defaultTs29163CpcSip(4) }
    MAX-ACCESS      read-write
    STATUS          current
    DESCRIPTION     
            "The name of the CPCtoSIP mapping profile on which the new profile is based."
    ::= { sonusCpcToSipCauseMappingProfileEntry 3 }

sonusCpcToSipCauseMappingProfileRowStatus OBJECT-TYPE
    SYNTAX          RowStatus
    MAX-ACCESS      read-write
    STATUS          current
    DESCRIPTION     
            ""
    ::= { sonusCpcToSipCauseMappingProfileEntry 4 }

sonusCpcToSipCauseMappingIndexProfileVersion OBJECT-TYPE
    SYNTAX          Integer32 (1..64)
    MAX-ACCESS      read-write
    STATUS          current
    DESCRIPTION     
            "Identifies the CPC-to-SIP cause mapping Profile Index Version."
    ::= { sonusCpcToSipCauseMappingProfileEntry 5 }

sonusCpcToSipCauseMappingProfileUnrecAction OBJECT-TYPE
    SYNTAX          INTEGER { q1912Procedure(1), rfc3398Procedure(2), 
                        ts29163Procedure(3) }
    MAX-ACCESS      read-write
    STATUS          current
    DESCRIPTION     
            "The cause procedure to be used when an unrecognised cause is received"
    ::= { sonusCpcToSipCauseMappingProfileEntry 6 }

sonusCpcToSipCauseMappingProfileIncludeQ850Reason OBJECT-TYPE
    SYNTAX          SonusAdminState
    MAX-ACCESS      read-write
    STATUS          current
    DESCRIPTION     
            "This field indicates if to include Q.850 value in Reason header of SIP messages."
    DEFVAL          { disabled }
    ::= { sonusCpcToSipCauseMappingProfileEntry 7 }

sonusSipSgFromCpcCauseMappingAdmnTable OBJECT-TYPE
    SYNTAX          SEQUENCE OF SonusSipSgFromCpcToSipCauseMappingAdmnEntry
    MAX-ACCESS      not-accessible
    STATUS          current
    DESCRIPTION     
            "CPC-to-SIP cause mapping Table"
    ::= { sonusCpcToSipCauseMappingObject 2 }

sonusSipSgFromCpcToSipCauseMappingAdmnEntry OBJECT-TYPE
    SYNTAX          SonusSipSgFromCpcToSipCauseMappingAdmnEntry
    MAX-ACCESS      not-accessible
    STATUS          current
    DESCRIPTION     
            "This table describes the CPC-to-SIP-to cause mapping that are configured."
    INDEX           { sonusCpcToSipCauseBackwardMappingProfileIndex, 
                      sonusCpcToSipCauseMappingCpcCause }
    ::= { sonusSipSgFromCpcCauseMappingAdmnTable 1 }

SonusSipSgFromCpcToSipCauseMappingAdmnEntry ::=
    SEQUENCE {
        sonusCpcToSipCauseBackwardMappingProfileIndex             Integer32,
        sonusCpcToSipCauseMappingSipCause Integer32,
        sonusCpcToSipCauseMappingCpcCause Integer32,
        sonusCpcToSipCauseMappingRowStatus  RowStatus,
        sonusCpcToSipCauseMappingQ850Reason   Integer32
    }

sonusCpcToSipCauseBackwardMappingProfileIndex OBJECT-TYPE
    SYNTAX          Integer32
    MAX-ACCESS      not-accessible
    STATUS          current
    DESCRIPTION     
            "Identifies the SipSGFromCauseMapping Profile to which this entry belongs."
    ::= { sonusSipSgFromCpcToSipCauseMappingAdmnEntry 1 }

sonusCpcToSipCauseMappingSipCause OBJECT-TYPE
    SYNTAX          Integer32 (300..606)
    MAX-ACCESS      read-write
    STATUS          current
    DESCRIPTION     
            "CPC Cause value "
    ::= { sonusSipSgFromCpcToSipCauseMappingAdmnEntry 2 }

sonusCpcToSipCauseMappingCpcCause OBJECT-TYPE
    SYNTAX          Integer32 (1..255)
    MAX-ACCESS      read-write
    STATUS          current
    DESCRIPTION     
            "CPC Cause value "
    ::= { sonusSipSgFromCpcToSipCauseMappingAdmnEntry 3 }

sonusCpcToSipCauseMappingRowStatus OBJECT-TYPE
    SYNTAX          RowStatus
    MAX-ACCESS      read-write
    STATUS          current
    DESCRIPTION     
            ""
    ::= { sonusSipSgFromCpcToSipCauseMappingAdmnEntry 4 }

sonusCpcToSipCauseMappingQ850Reason OBJECT-TYPE
    SYNTAX          Integer32 (0..127)
    MAX-ACCESS      read-write
    STATUS          current
    DESCRIPTION     
            "Q.850 reason for a given CPC cause value"
    ::= { sonusSipSgFromCpcToSipCauseMappingAdmnEntry 5 }

sonusSipSigPortPerNifStatusTable OBJECT-TYPE
    SYNTAX          SEQUENCE OF SonusSipSigPortPerNifStatusEntry
    MAX-ACCESS      not-accessible
    STATUS          current
    DESCRIPTION     
            "Table of SIP Signalling Port Per-NIF status."
    ::= { sonusSipSignallingMIBObjects 14 }

sonusSipSigPortPerNifStatusEntry OBJECT-TYPE
    SYNTAX          SonusSipSigPortPerNifStatusEntry
    MAX-ACCESS      not-accessible
    STATUS          current
    DESCRIPTION     
            "SIP Signalling Port Per-NIF Status."
    INDEX           { sonusSipSigPortPerNifStatusIndex, 
                      sonusSipSigPortPerNifStatusIfNum }
    ::= { sonusSipSigPortPerNifStatusTable 1 }

SonusSipSigPortPerNifStatusEntry ::=
    SEQUENCE {
        sonusSipSigPortPerNifStatusIndex Integer32,
        sonusSipSigPortPerNifStatusIfNum Integer32,
        sonusSipSigPortPerNifStatusNifName  SonusNameReference,
        sonusSipSigPortPerNifStatusStatus INTEGER
    }

sonusSipSigPortPerNifStatusIndex OBJECT-TYPE
    SYNTAX          Integer32
    MAX-ACCESS      read-only
    STATUS          current
    DESCRIPTION     
            "SIP signaling port index number."
    ::= { sonusSipSigPortPerNifStatusEntry 1 }

sonusSipSigPortPerNifStatusIfNum OBJECT-TYPE
    SYNTAX          Integer32
    MAX-ACCESS      read-only
    STATUS          current
    DESCRIPTION     
            "The NIF's Interface number."
    ::= { sonusSipSigPortPerNifStatusEntry 2 }

sonusSipSigPortPerNifStatusNifName OBJECT-TYPE
    SYNTAX          SonusNameReference
    MAX-ACCESS      read-only
    STATUS          current
    DESCRIPTION     
            "The NIF's name."
    ::= { sonusSipSigPortPerNifStatusEntry 3 }

sonusSipSigPortPerNifStatusStatus OBJECT-TYPE
    SYNTAX          INTEGER { unavailable(0), available(1), 
                        notApplicable(2) }
    MAX-ACCESS      read-only
    STATUS          current
    DESCRIPTION     
            "The availability status of the local address allocated
             to the NIF of the NIF group bound to this signaling port."
    ::= { sonusSipSigPortPerNifStatusEntry 4 }

sonusSipRegCountTable OBJECT-TYPE
    SYNTAX          SEQUENCE OF SonusSipRegCountEntry
    MAX-ACCESS      not-accessible
    STATUS          current
    DESCRIPTION     
            "This table presents SIP registration count statistics for the node."
    ::= { sonusSipSignallingMIBObjects 16 }

sonusSipRegCountEntry OBJECT-TYPE
    SYNTAX          SonusSipRegCountEntry
    MAX-ACCESS      not-accessible
    STATUS          current
    DESCRIPTION     
            ""
    INDEX           { sonusSipRegCountShelfIndex, 
                      sonusSipRegCountSlotIndex }
    ::= { sonusSipRegCountTable 1 }

SonusSipRegCountEntry ::=
    SEQUENCE {
        sonusSipRegCountShelfIndex      SonusShelfIndex,
        sonusSipRegCountSlotIndex       SonusSlotIndex,
        sonusSipRegCountReset           INTEGER,
        sonusSipRegCountAttempts        Counter32,
        sonusSipRegCountCumCompletions  Counter32,
        sonusSipRegCountPending         Counter32,
        sonusSipRegCountStable          Counter32,
        sonusSipRegCountTotal           Counter32
    }

sonusSipRegCountShelfIndex OBJECT-TYPE
    SYNTAX          SonusShelfIndex
    MAX-ACCESS      read-only
    STATUS          current
    DESCRIPTION     
            "Identifies the target shelf to obtain the SIP registration counters."
    ::= { sonusSipRegCountEntry 1 }

sonusSipRegCountSlotIndex OBJECT-TYPE
    SYNTAX          SonusSlotIndex
    MAX-ACCESS      read-only
    STATUS          current
    DESCRIPTION     
            "Identifies the target slot."
    ::= { sonusSipRegCountEntry 2 }

sonusSipRegCountReset OBJECT-TYPE
    SYNTAX          INTEGER { unknown(1), reset(2) }
    MAX-ACCESS      read-create
    STATUS          current
    DESCRIPTION     
            "Provides a means to reset a subset of the SIP registration
             counters. Any set operation on this object will result in the
             		 attempt and cummulative completion counters being cleared."
    ::= { sonusSipRegCountEntry 3 }

sonusSipRegCountAttempts OBJECT-TYPE
    SYNTAX          Counter32
    MAX-ACCESS      read-only
    STATUS          current
    DESCRIPTION     
            "Indicates the number of SIP registration attempts on this card."
    ::= { sonusSipRegCountEntry 4 }

sonusSipRegCountCumCompletions OBJECT-TYPE
    SYNTAX          Counter32
    MAX-ACCESS      read-only
    STATUS          current
    DESCRIPTION     
            "Indicates the accumulative number of completed SIP registration attempts on this card."
    ::= { sonusSipRegCountEntry 5 }

sonusSipRegCountPending OBJECT-TYPE
    SYNTAX          Counter32
    MAX-ACCESS      read-only
    STATUS          current
    DESCRIPTION     
            "Indicates the current number of pending SIP registrations on this card."
    ::= { sonusSipRegCountEntry 6 }

sonusSipRegCountStable OBJECT-TYPE
    SYNTAX          Counter32
    MAX-ACCESS      read-only
    STATUS          current
    DESCRIPTION     
            "Indicates the current number of stable SIP registrations on this card."
    ::= { sonusSipRegCountEntry 7 }

sonusSipRegCountTotal OBJECT-TYPE
    SYNTAX          Counter32
    MAX-ACCESS      read-only
    STATUS          current
    DESCRIPTION     
            "Indicates the total number of current SIP registrations on this card."
    ::= { sonusSipRegCountEntry 8 }

sonusSipRegActRegStatusTable OBJECT-TYPE
    SYNTAX          SEQUENCE OF SonusSipRegActRegStatusEntry
    MAX-ACCESS      not-accessible
    STATUS          deprecated
    DESCRIPTION     
            "This table presents the active SIP registration status for 
             a list of SIP endpoints.  This table is deprecated and replaced with
             sonusSipRegActGroupRegStatusTable in 7.1x for BT phase 2"
    ::= { sonusSipSignallingMIBObjects 17 }

sonusSipRegActRegStatusEntry OBJECT-TYPE
    SYNTAX          SonusSipRegActRegStatusEntry
    MAX-ACCESS      not-accessible
    STATUS          deprecated
    DESCRIPTION     
            "This entry presents the active SIP registration status for
             a SIP endpoint."
    INDEX           { sonusSipRegActRegStatusShelfIndex, 
                      sonusSipRegActRegStatusSlotIndex, 
                      sonusSipRegActRegStatusRegId }
    ::= { sonusSipRegActRegStatusTable 1 }

SonusSipRegActRegStatusEntry ::=
    SEQUENCE {
        sonusSipRegActRegStatusShelfIndex SonusShelfIndex,
        sonusSipRegActRegStatusSlotIndex SonusSlotIndex,
        sonusSipRegActRegStatusRegId    Integer32,
        sonusSipRegActRegStatusAorName  DisplayString,
        sonusSipRegActRegStatusState    INTEGER,
        sonusSipRegActRegStatusContactURI DisplayString,
        sonusSipRegActRegStatusNextHopIpAddress       IpAddress,
        sonusSipRegActRegStatusNextHopPortNum     Integer32,
        sonusSipRegActRegStatusRegistrarIpAddress         IpAddress,
        sonusSipRegActRegStatusRegistrarPortNum       Integer32,
        sonusSipRegActRegStatusExtExpirationTime        Integer32,
        sonusSipRegActRegStatusIntExpirationTime        Integer32,
        sonusSipRegActRegStatusCreationTime   DateAndTime,
        sonusSipRegActRegStatusRegistrarDomainName          DisplayString,
        sonusSipRegActRegStatusNextHopIp6Address        Ipv6Address,
        sonusSipRegActRegStatusRegistrarIp6Address          Ipv6Address
    }

sonusSipRegActRegStatusShelfIndex OBJECT-TYPE
    SYNTAX          SonusShelfIndex
    MAX-ACCESS      read-only
    STATUS          deprecated
    DESCRIPTION     
            "Identifies the target shelf."
    ::= { sonusSipRegActRegStatusEntry 1 }

sonusSipRegActRegStatusSlotIndex OBJECT-TYPE
    SYNTAX          SonusSlotIndex
    MAX-ACCESS      read-only
    STATUS          deprecated
    DESCRIPTION     
            "Identifies the target slot."
    ::= { sonusSipRegActRegStatusEntry 2 }

sonusSipRegActRegStatusRegId OBJECT-TYPE
    SYNTAX          Integer32 (1..1000000)
    MAX-ACCESS      read-only
    STATUS          deprecated
    DESCRIPTION     
            "The registration ID created for the registration session."
    ::= { sonusSipRegActRegStatusEntry 3 }

sonusSipRegActRegStatusAorName OBJECT-TYPE
    SYNTAX          DisplayString (SIZE(0..63))
    MAX-ACCESS      read-only
    STATUS          deprecated
    DESCRIPTION     
            "The E.164 number plus optional BGID representing the 
             Address Of Record of the registering endpoint."
    ::= { sonusSipRegActRegStatusEntry 4 }

sonusSipRegActRegStatusState OBJECT-TYPE
    SYNTAX          INTEGER { null(0), initiating(1), completed(2), 
                        refreshing(3), updating(4), challenged(5), 
                        deleting(6), terminated(7), expired(8) }
    MAX-ACCESS      read-only
    STATUS          deprecated
    DESCRIPTION     
            "The registration state of the endpoint."
    ::= { sonusSipRegActRegStatusEntry 5 }

sonusSipRegActRegStatusContactURI OBJECT-TYPE
    SYNTAX          DisplayString (SIZE(0..127))
    MAX-ACCESS      read-only
    STATUS          deprecated
    DESCRIPTION     
            "The SIP CONTACT URI header."
    ::= { sonusSipRegActRegStatusEntry 6 }

sonusSipRegActRegStatusNextHopIpAddress OBJECT-TYPE
    SYNTAX          IpAddress
    MAX-ACCESS      read-only
    STATUS          deprecated
    DESCRIPTION     
            "Next hop TSAP IP address."
    ::= { sonusSipRegActRegStatusEntry 7 }

sonusSipRegActRegStatusNextHopPortNum OBJECT-TYPE
    SYNTAX          Integer32 (1..65535)
    MAX-ACCESS      read-only
    STATUS          deprecated
    DESCRIPTION     
            "Next hop TSAP UDP port number."
    ::= { sonusSipRegActRegStatusEntry 8 }

sonusSipRegActRegStatusRegistrarIpAddress OBJECT-TYPE
    SYNTAX          IpAddress
    MAX-ACCESS      read-only
    STATUS          deprecated
    DESCRIPTION     
            "SIP Registrar's IP Address."
    ::= { sonusSipRegActRegStatusEntry 9 }

sonusSipRegActRegStatusRegistrarPortNum OBJECT-TYPE
    SYNTAX          Integer32 (1..65535)
    MAX-ACCESS      read-only
    STATUS          deprecated
    DESCRIPTION     
            "SIP Registrar's UDP port number."
    ::= { sonusSipRegActRegStatusEntry 10 }

sonusSipRegActRegStatusExtExpirationTime OBJECT-TYPE
    SYNTAX          Integer32
    MAX-ACCESS      read-only
    STATUS          deprecated
    DESCRIPTION     
            "The external expiration timer value in seconds."
    ::= { sonusSipRegActRegStatusEntry 11 }

sonusSipRegActRegStatusIntExpirationTime OBJECT-TYPE
    SYNTAX          Integer32
    MAX-ACCESS      read-only
    STATUS          deprecated
    DESCRIPTION     
            "The internal expiration timer value in seconds."
    ::= { sonusSipRegActRegStatusEntry 12 }

sonusSipRegActRegStatusCreationTime OBJECT-TYPE
    SYNTAX          DateAndTime
    MAX-ACCESS      read-only
    STATUS          deprecated
    DESCRIPTION     
            "Octet string that identifies the date and GMT time at which the
             SIP registration is initiated."
    ::= { sonusSipRegActRegStatusEntry 13 }

sonusSipRegActRegStatusRegistrarDomainName OBJECT-TYPE
    SYNTAX          DisplayString (SIZE(0..127))
    MAX-ACCESS      read-only
    STATUS          deprecated
    DESCRIPTION     
            "The SIP registrar's domain name."
    ::= { sonusSipRegActRegStatusEntry 14 }

sonusSipRegActRegStatusNextHopIp6Address OBJECT-TYPE
    SYNTAX          Ipv6Address
    MAX-ACCESS      read-only
    STATUS          deprecated
    DESCRIPTION     
            "Next hop TSAP IPv6 address."
    ::= { sonusSipRegActRegStatusEntry 15 }

sonusSipRegActRegStatusRegistrarIp6Address OBJECT-TYPE
    SYNTAX          Ipv6Address
    MAX-ACCESS      read-only
    STATUS          deprecated
    DESCRIPTION     
            "SIP Registrar's IPv6 Address."
    ::= { sonusSipRegActRegStatusEntry 16 }

sonusSipRegDelRegStatusTable OBJECT-TYPE
    SYNTAX          SEQUENCE OF SonusSipRegDelRegStatusEntry
    MAX-ACCESS      not-accessible
    STATUS          current
    DESCRIPTION     
            "This table presents the deleted SIP registration status for
             a list of SIP endpoints."
    ::= { sonusSipSignallingMIBObjects 18 }

sonusSipRegDelRegStatusEntry OBJECT-TYPE
    SYNTAX          SonusSipRegDelRegStatusEntry
    MAX-ACCESS      not-accessible
    STATUS          current
    DESCRIPTION     
            "This entry presents the deleted SIP registration status for
             a SIP endpoint."
    INDEX           { sonusSipRegDelRegStatusShelfIndex, 
                      sonusSipRegDelRegStatusSlotIndex, 
                      sonusSipRegDelRegStatusRegId }
    ::= { sonusSipRegDelRegStatusTable 1 }

SonusSipRegDelRegStatusEntry ::=
    SEQUENCE {
        sonusSipRegDelRegStatusShelfIndex SonusShelfIndex,
        sonusSipRegDelRegStatusSlotIndex SonusSlotIndex,
        sonusSipRegDelRegStatusRegId    Integer32,
        sonusSipRegDelRegStatusAorName  DisplayString,
        sonusSipRegDelRegStatusReasonCode INTEGER,
        sonusSipRegDelRegStatusContactURI DisplayString,
        sonusSipRegDelRegStatusNextHopIpAddress       IpAddress,
        sonusSipRegDelRegStatusNextHopPortNum     Integer32,
        sonusSipRegDelRegStatusRegistrarIpAddress         IpAddress,
        sonusSipRegDelRegStatusRegistrarPortNum       Integer32,
        sonusSipRegDelRegStatusCreationTime   DateAndTime,
        sonusSipRegDelRegStatusTerminationTime      DateAndTime,
        sonusSipRegDelRegStatusRegistrarDomainName          DisplayString,
        sonusSipRegDelRegStatusNextHopIp6Address        Ipv6Address,
        sonusSipRegDelRegStatusRegistrarIp6Address          Ipv6Address,
        sonusSipRegDelRegStatusNextHopIpVersion       INTEGER,
        sonusSipRegDelRegStatusRegistrarIpVersion         INTEGER
    }

sonusSipRegDelRegStatusShelfIndex OBJECT-TYPE
    SYNTAX          SonusShelfIndex
    MAX-ACCESS      read-only
    STATUS          current
    DESCRIPTION     
            "Identifies the target shelf."
    ::= { sonusSipRegDelRegStatusEntry 1 }

sonusSipRegDelRegStatusSlotIndex OBJECT-TYPE
    SYNTAX          SonusSlotIndex
    MAX-ACCESS      read-only
    STATUS          current
    DESCRIPTION     
            "Identifies the target slot."
    ::= { sonusSipRegDelRegStatusEntry 2 }

sonusSipRegDelRegStatusRegId OBJECT-TYPE
    SYNTAX          Integer32 (1..1000000)
    MAX-ACCESS      read-only
    STATUS          current
    DESCRIPTION     
            "The registration ID created for the registration session."
    ::= { sonusSipRegDelRegStatusEntry 3 }

sonusSipRegDelRegStatusAorName OBJECT-TYPE
    SYNTAX          DisplayString (SIZE(0..127))
    MAX-ACCESS      read-only
    STATUS          current
    DESCRIPTION     
            "The E.164 number and host portion plus optional BGID representing the 
             Address Of Record of the registered endpoint."
    ::= { sonusSipRegDelRegStatusEntry 4 }

sonusSipRegDelRegStatusReasonCode OBJECT-TYPE
    SYNTAX          INTEGER { none(0), internalError(1), 
                        serviceUnavailable(2), configProblem(3), 
                        endpointInitiated(4), registrationRejected(5), 
                        registrationMoved(6), regTimerExpired(7) }
    MAX-ACCESS      read-only
    STATUS          current
    DESCRIPTION     
            "The registration termination reason."
    ::= { sonusSipRegDelRegStatusEntry 5 }

sonusSipRegDelRegStatusContactURI OBJECT-TYPE
    SYNTAX          DisplayString (SIZE(0..127))
    MAX-ACCESS      read-only
    STATUS          current
    DESCRIPTION     
            "The SIP CONTACT URI header."
    ::= { sonusSipRegDelRegStatusEntry 6 }

sonusSipRegDelRegStatusNextHopIpAddress OBJECT-TYPE
    SYNTAX          IpAddress
    MAX-ACCESS      read-only
    STATUS          current
    DESCRIPTION     
            "Next hop IP Address."
    ::= { sonusSipRegDelRegStatusEntry 7 }

sonusSipRegDelRegStatusNextHopPortNum OBJECT-TYPE
    SYNTAX          Integer32 (1..65535)
    MAX-ACCESS      read-only
    STATUS          current
    DESCRIPTION     
            "Next hop TSAP UDP port number."
    ::= { sonusSipRegDelRegStatusEntry 8 }

sonusSipRegDelRegStatusRegistrarIpAddress OBJECT-TYPE
    SYNTAX          IpAddress
    MAX-ACCESS      read-only
    STATUS          current
    DESCRIPTION     
            "Registrar's IP Address."
    ::= { sonusSipRegDelRegStatusEntry 9 }

sonusSipRegDelRegStatusRegistrarPortNum OBJECT-TYPE
    SYNTAX          Integer32 (1..65535)
    MAX-ACCESS      read-only
    STATUS          current
    DESCRIPTION     
            "SIP Registrar's UDP port number."
    ::= { sonusSipRegDelRegStatusEntry 10 }

sonusSipRegDelRegStatusCreationTime OBJECT-TYPE
    SYNTAX          DateAndTime
    MAX-ACCESS      read-only
    STATUS          current
    DESCRIPTION     
            "Octet string that identifies the date and GMT time at which the
             SIP registration is initiated."
    ::= { sonusSipRegDelRegStatusEntry 11 }

sonusSipRegDelRegStatusTerminationTime OBJECT-TYPE
    SYNTAX          DateAndTime
    MAX-ACCESS      read-only
    STATUS          current
    DESCRIPTION     
            "Octet string that identifies the date and GMT time at which the
             SIP registration is terminated."
    ::= { sonusSipRegDelRegStatusEntry 12 }

sonusSipRegDelRegStatusRegistrarDomainName OBJECT-TYPE
    SYNTAX          DisplayString (SIZE(0..127))
    MAX-ACCESS      read-only
    STATUS          current
    DESCRIPTION     
            "The SIP registrar's domain name."
    ::= { sonusSipRegDelRegStatusEntry 13 }

sonusSipRegDelRegStatusNextHopIp6Address OBJECT-TYPE
    SYNTAX          Ipv6Address
    MAX-ACCESS      read-only
    STATUS          current
    DESCRIPTION     
            "Next hop IPv6 Address."
    ::= { sonusSipRegDelRegStatusEntry 14 }

sonusSipRegDelRegStatusRegistrarIp6Address OBJECT-TYPE
    SYNTAX          Ipv6Address
    MAX-ACCESS      read-only
    STATUS          current
    DESCRIPTION     
            "Registrar's IPv6 Address."
    ::= { sonusSipRegDelRegStatusEntry 15 }

sonusSipRegDelRegStatusNextHopIpVersion OBJECT-TYPE
    SYNTAX          INTEGER { afInet(2), afInet6(24) }
    MAX-ACCESS      read-only
    STATUS          current
    DESCRIPTION     
            "Next hop IP Address Type"
    ::= { sonusSipRegDelRegStatusEntry 16 }

sonusSipRegDelRegStatusRegistrarIpVersion OBJECT-TYPE
    SYNTAX          INTEGER { afInet(2), afInet6(24) }
    MAX-ACCESS      read-only
    STATUS          current
    DESCRIPTION     
            "Registrar's IP Address Type"
    ::= { sonusSipRegDelRegStatusEntry 17 }

sonusSipRegActRegNameStatusTable OBJECT-TYPE
    SYNTAX          SEQUENCE OF SonusSipRegActRegNameStatusEntry
    MAX-ACCESS      not-accessible
    STATUS          current
    DESCRIPTION     
            "This table presents the active SIP registration status for 
             a list of SIP endpoints."
    ::= { sonusSipSignallingMIBObjects 19 }

sonusSipRegActRegNameStatusEntry OBJECT-TYPE
    SYNTAX          SonusSipRegActRegNameStatusEntry
    MAX-ACCESS      not-accessible
    STATUS          current
    DESCRIPTION     
            "This entry presents the active SIP registration status for
             a SIP endpoint."
    INDEX           { IMPLIED sonusSipRegActRegNameStatusAorName }
    ::= { sonusSipRegActRegNameStatusTable 1 }

SonusSipRegActRegNameStatusEntry ::=
    SEQUENCE {
        sonusSipRegActRegNameStatusShelfIndex     SonusShelfIndex,
        sonusSipRegActRegNameStatusSlotIndex    SonusSlotIndex,
        sonusSipRegActRegNameStatusRegId Integer32,
        sonusSipRegActRegNameStatusAorName  DisplayString,
        sonusSipRegActRegNameStatusState INTEGER,
        sonusSipRegActRegNameStatusContactURI     DisplayString,
        sonusSipRegActRegNameStatusNextHopIpAddress           IpAddress,
        sonusSipRegActRegNameStatusNextHopPortNum         Integer32,
        sonusSipRegActRegNameStatusRegistrarIpAddress             IpAddress,
        sonusSipRegActRegNameStatusRegistrarPortNum           Integer32,
        sonusSipRegActRegNameStatusExtExpirationTime            Integer32,
        sonusSipRegActRegNameStatusIntExpirationTime            Integer32,
        sonusSipRegActRegNameStatusCreationTime       DateAndTime,
        sonusSipRegActRegNameStatusRegistrarDomainName              DisplayString,
        sonusSipRegActRegNameStatusNextHopIp6Address            Ipv6Address,
        sonusSipRegActRegNameStatusRegistrarIp6Address              Ipv6Address,
        sonusSipRegActRegNameStatusNextHopIpVersion           INTEGER,
        sonusSipRegActRegNameStatusRegistrarIpVersion             INTEGER
    }

sonusSipRegActRegNameStatusShelfIndex OBJECT-TYPE
    SYNTAX          SonusShelfIndex
    MAX-ACCESS      read-only
    STATUS          current
    DESCRIPTION     
            "Identifies the target shelf."
    ::= { sonusSipRegActRegNameStatusEntry 1 }

sonusSipRegActRegNameStatusSlotIndex OBJECT-TYPE
    SYNTAX          SonusSlotIndex
    MAX-ACCESS      read-only
    STATUS          current
    DESCRIPTION     
            "Identifies the target slot."
    ::= { sonusSipRegActRegNameStatusEntry 2 }

sonusSipRegActRegNameStatusRegId OBJECT-TYPE
    SYNTAX          Integer32
    MAX-ACCESS      read-only
    STATUS          current
    DESCRIPTION     
            "The registration ID created for the registration session."
    ::= { sonusSipRegActRegNameStatusEntry 3 }

sonusSipRegActRegNameStatusAorName OBJECT-TYPE
    SYNTAX          DisplayString (SIZE(1..128))
    MAX-ACCESS      read-only
    STATUS          current
    DESCRIPTION     
            "The E.164 number and host portion plus optional BGID representing the 
             Address Of Record of the registering endpoint."
    ::= { sonusSipRegActRegNameStatusEntry 4 }

sonusSipRegActRegNameStatusState OBJECT-TYPE
    SYNTAX          INTEGER { null(0), initiating(1), completed(2), 
                        refreshing(3), updating(4), challenged(5), 
                        deleting(6), terminated(7) }
    MAX-ACCESS      read-only
    STATUS          current
    DESCRIPTION     
            "The registration state of the endpoint."
    ::= { sonusSipRegActRegNameStatusEntry 5 }

sonusSipRegActRegNameStatusContactURI OBJECT-TYPE
    SYNTAX          DisplayString (SIZE(0..127))
    MAX-ACCESS      read-only
    STATUS          current
    DESCRIPTION     
            "The SIP CONTACT URI header."
    ::= { sonusSipRegActRegNameStatusEntry 6 }

sonusSipRegActRegNameStatusNextHopIpAddress OBJECT-TYPE
    SYNTAX          IpAddress
    MAX-ACCESS      read-only
    STATUS          current
    DESCRIPTION     
            "Next hop TSAP IP address."
    ::= { sonusSipRegActRegNameStatusEntry 7 }

sonusSipRegActRegNameStatusNextHopPortNum OBJECT-TYPE
    SYNTAX          Integer32 (1..65535)
    MAX-ACCESS      read-only
    STATUS          current
    DESCRIPTION     
            "Next hop TSAP UDP port number."
    ::= { sonusSipRegActRegNameStatusEntry 8 }

sonusSipRegActRegNameStatusRegistrarIpAddress OBJECT-TYPE
    SYNTAX          IpAddress
    MAX-ACCESS      read-only
    STATUS          current
    DESCRIPTION     
            "SIP Registrar's IP Address."
    ::= { sonusSipRegActRegNameStatusEntry 9 }

sonusSipRegActRegNameStatusRegistrarPortNum OBJECT-TYPE
    SYNTAX          Integer32 (1..65535)
    MAX-ACCESS      read-only
    STATUS          current
    DESCRIPTION     
            "SIP Registrar's UDP port number."
    ::= { sonusSipRegActRegNameStatusEntry 10 }

sonusSipRegActRegNameStatusExtExpirationTime OBJECT-TYPE
    SYNTAX          Integer32
    MAX-ACCESS      read-only
    STATUS          current
    DESCRIPTION     
            "The external expiration timer value in seconds."
    ::= { sonusSipRegActRegNameStatusEntry 11 }

sonusSipRegActRegNameStatusIntExpirationTime OBJECT-TYPE
    SYNTAX          Integer32
    MAX-ACCESS      read-only
    STATUS          current
    DESCRIPTION     
            "The internal expiration timer value in seconds."
    ::= { sonusSipRegActRegNameStatusEntry 12 }

sonusSipRegActRegNameStatusCreationTime OBJECT-TYPE
    SYNTAX          DateAndTime
    MAX-ACCESS      read-only
    STATUS          current
    DESCRIPTION     
            "Octet string that identifies the date and GMT time at which the
             SIP registration is initiated."
    ::= { sonusSipRegActRegNameStatusEntry 13 }

sonusSipRegActRegNameStatusRegistrarDomainName OBJECT-TYPE
    SYNTAX          DisplayString (SIZE(0..127))
    MAX-ACCESS      read-only
    STATUS          current
    DESCRIPTION     
            "The SIP registrar's domain name."
    ::= { sonusSipRegActRegNameStatusEntry 14 }

sonusSipRegActRegNameStatusNextHopIp6Address OBJECT-TYPE
    SYNTAX          Ipv6Address
    MAX-ACCESS      read-only
    STATUS          current
    DESCRIPTION     
            "Next hop TSAP IPv6 address."
    ::= { sonusSipRegActRegNameStatusEntry 15 }

sonusSipRegActRegNameStatusRegistrarIp6Address OBJECT-TYPE
    SYNTAX          Ipv6Address
    MAX-ACCESS      read-only
    STATUS          current
    DESCRIPTION     
            "SIP Registrar's IPv6 Address."
    ::= { sonusSipRegActRegNameStatusEntry 16 }

sonusSipRegActRegNameStatusNextHopIpVersion OBJECT-TYPE
    SYNTAX          INTEGER { afInet(2), afInet6(24) }
    MAX-ACCESS      read-only
    STATUS          current
    DESCRIPTION     
            "Next hop TSAP IP address Type."
    ::= { sonusSipRegActRegNameStatusEntry 17 }

sonusSipRegActRegNameStatusRegistrarIpVersion OBJECT-TYPE
    SYNTAX          INTEGER { afInet(2), afInet6(24) }
    MAX-ACCESS      read-only
    STATUS          current
    DESCRIPTION     
            "SIP Registrar's IPv6 Address."
    ::= { sonusSipRegActRegNameStatusEntry 18 }

sonusSipRegDelRegNameStatusTable OBJECT-TYPE
    SYNTAX          SEQUENCE OF SonusSipRegDelRegNameStatusEntry
    MAX-ACCESS      not-accessible
    STATUS          current
    DESCRIPTION     
            "This table presents the deleted SIP registration status for
             a list of SIP endpoints."
    ::= { sonusSipSignallingMIBObjects 20 }

sonusSipRegDelRegNameStatusEntry OBJECT-TYPE
    SYNTAX          SonusSipRegDelRegNameStatusEntry
    MAX-ACCESS      not-accessible
    STATUS          current
    DESCRIPTION     
            "This entry presents the deleted SIP registration status for
             a SIP endpoint."
    INDEX           { IMPLIED sonusSipRegDelRegNameStatusAorName }
    ::= { sonusSipRegDelRegNameStatusTable 1 }

SonusSipRegDelRegNameStatusEntry ::=
    SEQUENCE {
        sonusSipRegDelRegNameStatusShelfIndex     SonusShelfIndex,
        sonusSipRegDelRegNameStatusSlotIndex    SonusSlotIndex,
        sonusSipRegDelRegNameStatusRegId Integer32,
        sonusSipRegDelRegNameStatusAorName  DisplayString,
        sonusSipRegDelRegNameStatusReasonCode     INTEGER,
        sonusSipRegDelRegNameStatusContactURI     DisplayString,
        sonusSipRegDelRegNameStatusNextHopIpAddress           IpAddress,
        sonusSipRegDelRegNameStatusNextHopPortNum         Integer32,
        sonusSipRegDelRegNameStatusRegistrarIpAddress             IpAddress,
        sonusSipRegDelRegNameStatusRegistrarPortNum           Integer32,
        sonusSipRegDelRegNameStatusCreationTime       DateAndTime,
        sonusSipRegDelRegNameStatusTerminationTime          DateAndTime,
        sonusSipRegDelRegNameStatusRegistrarDomainName              DisplayString,
        sonusSipRegDelRegNameStatusNextHopIp6Address            Ipv6Address,
        sonusSipRegDelRegNameStatusRegistrarIp6Address              Ipv6Address,
        sonusSipRegDelRegNameStatusNextHopIpVersion           INTEGER,
        sonusSipRegDelRegNameStatusRegistrarIpVersion             INTEGER
    }

sonusSipRegDelRegNameStatusShelfIndex OBJECT-TYPE
    SYNTAX          SonusShelfIndex
    MAX-ACCESS      read-only
    STATUS          current
    DESCRIPTION     
            "Identifies the target shelf."
    ::= { sonusSipRegDelRegNameStatusEntry 1 }

sonusSipRegDelRegNameStatusSlotIndex OBJECT-TYPE
    SYNTAX          SonusSlotIndex
    MAX-ACCESS      read-only
    STATUS          current
    DESCRIPTION     
            "Identifies the target slot."
    ::= { sonusSipRegDelRegNameStatusEntry 2 }

sonusSipRegDelRegNameStatusRegId OBJECT-TYPE
    SYNTAX          Integer32
    MAX-ACCESS      read-only
    STATUS          current
    DESCRIPTION     
            "The registration ID created for the registration session."
    ::= { sonusSipRegDelRegNameStatusEntry 3 }

sonusSipRegDelRegNameStatusAorName OBJECT-TYPE
    SYNTAX          DisplayString (SIZE(1..128))
    MAX-ACCESS      read-only
    STATUS          current
    DESCRIPTION     
            "The E.164 number and host portion plus optional BGID representing the 
             Address Of Record of the registered endpoint."
    ::= { sonusSipRegDelRegNameStatusEntry 4 }

sonusSipRegDelRegNameStatusReasonCode OBJECT-TYPE
    SYNTAX          INTEGER { none(0), internalError(1), 
                        serviceUnavailable(2), configProblem(3), 
                        endpointInitiated(4), registrationRejected(5), 
                        registrationMoved(6), regTimerExpired(7) }
    MAX-ACCESS      read-only
    STATUS          current
    DESCRIPTION     
            "The registration termination reason."
    ::= { sonusSipRegDelRegNameStatusEntry 5 }

sonusSipRegDelRegNameStatusContactURI OBJECT-TYPE
    SYNTAX          DisplayString (SIZE(0..127))
    MAX-ACCESS      read-only
    STATUS          current
    DESCRIPTION     
            "The SIP CONTACT URI header."
    ::= { sonusSipRegDelRegNameStatusEntry 6 }

sonusSipRegDelRegNameStatusNextHopIpAddress OBJECT-TYPE
    SYNTAX          IpAddress
    MAX-ACCESS      read-only
    STATUS          current
    DESCRIPTION     
            "Next hop IP Address."
    ::= { sonusSipRegDelRegNameStatusEntry 7 }

sonusSipRegDelRegNameStatusNextHopPortNum OBJECT-TYPE
    SYNTAX          Integer32 (1..65535)
    MAX-ACCESS      read-only
    STATUS          current
    DESCRIPTION     
            "Next hop TSAP UDP port number."
    ::= { sonusSipRegDelRegNameStatusEntry 8 }

sonusSipRegDelRegNameStatusRegistrarIpAddress OBJECT-TYPE
    SYNTAX          IpAddress
    MAX-ACCESS      read-only
    STATUS          current
    DESCRIPTION     
            "Registrar's IP Address."
    ::= { sonusSipRegDelRegNameStatusEntry 9 }

sonusSipRegDelRegNameStatusRegistrarPortNum OBJECT-TYPE
    SYNTAX          Integer32 (1..65535)
    MAX-ACCESS      read-only
    STATUS          current
    DESCRIPTION     
            "SIP Registrar's UDP port number."
    ::= { sonusSipRegDelRegNameStatusEntry 10 }

sonusSipRegDelRegNameStatusCreationTime OBJECT-TYPE
    SYNTAX          DateAndTime
    MAX-ACCESS      read-only
    STATUS          current
    DESCRIPTION     
            "Octet string that identifies the date and GMT time at which the
             SIP registration is initiated."
    ::= { sonusSipRegDelRegNameStatusEntry 11 }

sonusSipRegDelRegNameStatusTerminationTime OBJECT-TYPE
    SYNTAX          DateAndTime
    MAX-ACCESS      read-only
    STATUS          current
    DESCRIPTION     
            "Octet string that identifies the date and GMT time at which the
             SIP registration is terminated."
    ::= { sonusSipRegDelRegNameStatusEntry 12 }

sonusSipRegDelRegNameStatusRegistrarDomainName OBJECT-TYPE
    SYNTAX          DisplayString (SIZE(0..127))
    MAX-ACCESS      read-only
    STATUS          current
    DESCRIPTION     
            "The SIP registrar's domain name."
    ::= { sonusSipRegDelRegNameStatusEntry 13 }

sonusSipRegDelRegNameStatusNextHopIp6Address OBJECT-TYPE
    SYNTAX          Ipv6Address
    MAX-ACCESS      read-only
    STATUS          current
    DESCRIPTION     
            "Next hop IPv6 Address."
    ::= { sonusSipRegDelRegNameStatusEntry 14 }

sonusSipRegDelRegNameStatusRegistrarIp6Address OBJECT-TYPE
    SYNTAX          Ipv6Address
    MAX-ACCESS      read-only
    STATUS          current
    DESCRIPTION     
            "Registrar's IPv6 Address."
    ::= { sonusSipRegDelRegNameStatusEntry 15 }

sonusSipRegDelRegNameStatusNextHopIpVersion OBJECT-TYPE
    SYNTAX          INTEGER { afInet(2), afInet6(24) }
    MAX-ACCESS      read-only
    STATUS          current
    DESCRIPTION     
            "Next hop IP Address Type."
    ::= { sonusSipRegDelRegNameStatusEntry 16 }

sonusSipRegDelRegNameStatusRegistrarIpVersion OBJECT-TYPE
    SYNTAX          INTEGER { afInet(2), afInet6(24) }
    MAX-ACCESS      read-only
    STATUS          current
    DESCRIPTION     
            "Registrar's IP Address Type."
    ::= { sonusSipRegDelRegNameStatusEntry 17 }

sonusSipArsProfile OBJECT IDENTIFIER
    ::= { sonusSipSignallingMIBObjects 21 }

sonusSipArsProfileNextIndex OBJECT-TYPE
    SYNTAX          Unsigned32
    MAX-ACCESS      not-accessible
    STATUS          current
    DESCRIPTION     
            "The next valid index to use when creating a new sonusSipArsProfileEntry"
    ::= { sonusSipArsProfile 1 }

sonusSipArsProfileTable OBJECT-TYPE
    SYNTAX          SEQUENCE OF SonusSipArsProfileEntry
    MAX-ACCESS      not-accessible
    STATUS          current
    DESCRIPTION     
            "This table contains information about each Address
             Reachability Service Profile configured on the node."
    ::= { sonusSipArsProfile 2 }

sonusSipArsProfileEntry OBJECT-TYPE
    SYNTAX          SonusSipArsProfileEntry
    MAX-ACCESS      not-accessible
    STATUS          current
    DESCRIPTION     
            "This table describes the Address Reachability Service Profile."
    INDEX           { sonusSipArsProfIndex }
    ::= { sonusSipArsProfileTable 1 }

SonusSipArsProfileEntry ::=
    SEQUENCE {
        sonusSipArsProfIndex            Unsigned32,
        sonusSipArsProfName             SonusName,
        sonusSipArsProfRowStatus        RowStatus,
        sonusSipArsProfAdminState       SonusAdminState,
        sonusSipArsProfBlkListAlg       INTEGER,
        sonusSipArsProfBlkListAlgTimeoutsType     INTEGER,
        sonusSipArsProfBlkListAlgTimeoutsNumTimeouts            Unsigned32,
        sonusSipArsProfBlkListAlgTimeoutsDuration         Unsigned32,
        sonusSipArsProfRecAlg           INTEGER,
        sonusSipArsProfRecAlgTimerDuration  Unsigned32,
        sonusSipArsProfRecAlgProbeMethod INTEGER,
        sonusSipArsProfRecAlgProbeInterval  Unsigned32,
        sonusSipArsProfRecAlgProbeNumResponses      Unsigned32,
        sonusSipArsProfRecAlgProbeDuration  Unsigned32,
        sonusSipArsProfBlkListAlgorithms BITS,
        sonusSipArsProfBlkListAlgRetryAfterType       BITS
    }

sonusSipArsProfIndex OBJECT-TYPE
    SYNTAX          Unsigned32
    MAX-ACCESS      not-accessible
    STATUS          current
    DESCRIPTION     
            "The index of the SIP Address Reachability Service table entry."
    ::= { sonusSipArsProfileEntry 1 }

sonusSipArsProfName OBJECT-TYPE
    SYNTAX          SonusName
    MAX-ACCESS      read-write
    STATUS          current
    DESCRIPTION     
            "The name of this SIP Address Reachability Service Profile."
    ::= { sonusSipArsProfileEntry 2 }

sonusSipArsProfRowStatus OBJECT-TYPE
    SYNTAX          RowStatus
    MAX-ACCESS      read-write
    STATUS          current
    DESCRIPTION     
            ""
    ::= { sonusSipArsProfileEntry 3 }

sonusSipArsProfAdminState OBJECT-TYPE
    SYNTAX          SonusAdminState
    MAX-ACCESS      read-write
    STATUS          current
    DESCRIPTION     
            "The admin state of this SIP Address Reachability Profile.
             Some fields cannot be changed until the state is disabled
             while others can be changed. In the former case, the change
             will be effective once the state is set to enabled."
    DEFVAL          { disabled }
    ::= { sonusSipArsProfileEntry 4 }

sonusSipArsProfBlkListAlg OBJECT-TYPE
    SYNTAX          INTEGER { timeouts(1) }
    MAX-ACCESS      read-write
    STATUS          obsolete
    DESCRIPTION     
            "This MIB is obsoleted by sonusSipArsProfBlkListAlgorithms.
             The blacklisting algorithm of this Address Reachability Service
             Profile. Currently, can only support timeouts."
    DEFVAL          { timeouts }
    ::= { sonusSipArsProfileEntry 5 }

sonusSipArsProfBlkListAlgTimeoutsType OBJECT-TYPE
    SYNTAX          INTEGER { sip-invite(1) }
    MAX-ACCESS      read-write
    STATUS          current
    DESCRIPTION     
            "This specifies the timeout trigger. SIP-INIVTE timeout is the
             only event that is supported in this release."
    DEFVAL          { sip-invite }
    ::= { sonusSipArsProfileEntry 6 }

sonusSipArsProfBlkListAlgTimeoutsNumTimeouts OBJECT-TYPE
    SYNTAX          Unsigned32 (1..3600)
    MAX-ACCESS      read-write
    STATUS          current
    DESCRIPTION     
            "This field specifies the number of timeout events should
             occur before blacking listing the address."
    DEFVAL          { 1 }
    ::= { sonusSipArsProfileEntry 7 }

sonusSipArsProfBlkListAlgTimeoutsDuration OBJECT-TYPE
    SYNTAX          Unsigned32 (1..3600)
    MAX-ACCESS      read-write
    STATUS          current
    DESCRIPTION     
            "This field specifies the duration in seconds, in which the
             specified number of timeouts should occur."
    DEFVAL          { 1 }
    ::= { sonusSipArsProfileEntry 8 }

sonusSipArsProfRecAlg OBJECT-TYPE
    SYNTAX          INTEGER { probe(1), timer(2) }
    MAX-ACCESS      read-write
    STATUS          current
    DESCRIPTION     
            "This field specifies the recovery algorithm."
    DEFVAL          { probe }
    ::= { sonusSipArsProfileEntry 9 }

sonusSipArsProfRecAlgTimerDuration OBJECT-TYPE
    SYNTAX          Unsigned32 (1..3600)
    MAX-ACCESS      read-write
    STATUS          current
    DESCRIPTION     
            "This field specifies the duration in seconds, for which
             the IP address will remain black listed."
    DEFVAL          { 1 }
    ::= { sonusSipArsProfileEntry 10 }

sonusSipArsProfRecAlgProbeMethod OBJECT-TYPE
    SYNTAX          INTEGER { sip-options(1) }
    MAX-ACCESS      read-write
    STATUS          current
    DESCRIPTION     
            "This field pecifies the probe method. Only SIP-OPTIONS will
             be supported for this release."
    DEFVAL          { sip-options }
    ::= { sonusSipArsProfileEntry 11 }

sonusSipArsProfRecAlgProbeInterval OBJECT-TYPE
    SYNTAX          Unsigned32 (1..600)
    MAX-ACCESS      read-write
    STATUS          current
    DESCRIPTION     
            "This field specifies the probe interval."
    DEFVAL          { 1 }
    ::= { sonusSipArsProfileEntry 12 }

sonusSipArsProfRecAlgProbeNumResponses OBJECT-TYPE
    SYNTAX          Unsigned32 (1..32)
    MAX-ACCESS      read-write
    STATUS          current
    DESCRIPTION     
            "This field specifies the number of responses should occur
             before removing the entry from the black list."
    DEFVAL          { 1 }
    ::= { sonusSipArsProfileEntry 13 }

sonusSipArsProfRecAlgProbeDuration OBJECT-TYPE
    SYNTAX          Unsigned32 (1..3600)
    MAX-ACCESS      read-write
    STATUS          current
    DESCRIPTION     
            "This field specifies the duration in seconds, in which the
             specified number of responses should occur."
    DEFVAL          { 1 }
    ::= { sonusSipArsProfileEntry 14 }

sonusSipArsProfBlkListAlgorithms OBJECT-TYPE
    SYNTAX          BITS { timeouts(0), retryafter(1) }
    MAX-ACCESS      read-write
    STATUS          current
    DESCRIPTION     
            "This one obsoletes sonusSiipArsProfBlkListAlg.
             The blacklisting algorithms of this Address Reachability Service
             Profile. Currently, can support timeouts and retryafter algorithms
             or both of them.
             bit 0 -- indicate timeouts algorithm
             bit 1 -- indicate retryafter algorithm
             ...
             "
    DEFVAL          { 128 }
    ::= { sonusSipArsProfileEntry 15 }

sonusSipArsProfBlkListAlgRetryAfterType OBJECT-TYPE
    SYNTAX          BITS { sip-503(0) }
    MAX-ACCESS      read-write
    STATUS          current
    DESCRIPTION     
            "This specifies the sip status code which has a Retry After value.
             503 Retry After is the only event supported in this release.
             bit 0 -- indicate sip 503
             ...
             "
    DEFVAL          { 128 }
    ::= { sonusSipArsProfileEntry 16 }

sonusSipArsStatusTable OBJECT-TYPE
    SYNTAX          SEQUENCE OF SonusSipArsStatusEntry
    MAX-ACCESS      not-accessible
    STATUS          current
    DESCRIPTION     
            "Table of Address Reachability Service status."
    ::= { sonusSipSignallingMIBObjects 22 }

sonusSipArsStatusEntry OBJECT-TYPE
    SYNTAX          SonusSipArsStatusEntry
    MAX-ACCESS      not-accessible
    STATUS          current
    DESCRIPTION     
            "Address Reachability Service Status."
    INDEX           { sonusSipArsStatShelfIndex, 
                      sonusSipArsStatSlotIndex, sonusSipArsStatSigZoneId, 
                      sonusSipArsStatRecordIndex }
    ::= { sonusSipArsStatusTable 1 }

SonusSipArsStatusEntry ::=
    SEQUENCE {
        sonusSipArsStatShelfIndex       SonusShelfIndex,
        sonusSipArsStatSlotIndex        SonusSlotIndex,
        sonusSipArsStatSigZoneId        Unsigned32,
        sonusSipArsStatRecordIndex      Unsigned32,
        sonusSipArsStatSigPortNum       Unsigned32,
        sonusSipArsStatEndpointIpAddress IpAddress,
        sonusSipArsStatEndpointIpPortNum Unsigned32,
        sonusSipArsStatEndpointArsState INTEGER,
        sonusSipArsStatEndpointStateTransitionTime          DateAndTime,
        sonusSipArsStatEndpointOwnerId  Unsigned32,
        sonusSipArsStatEndpointIpv6Address  Ipv6Address
    }

sonusSipArsStatShelfIndex OBJECT-TYPE
    SYNTAX          SonusShelfIndex
    MAX-ACCESS      read-only
    STATUS          current
    DESCRIPTION     
            "The shelf of the card where address reachability service status is
             being shown."
    ::= { sonusSipArsStatusEntry 1 }

sonusSipArsStatSlotIndex OBJECT-TYPE
    SYNTAX          SonusSlotIndex
    MAX-ACCESS      read-only
    STATUS          current
    DESCRIPTION     
            "The card slot where address reachability service status is being shown."
    ::= { sonusSipArsStatusEntry 2 }

sonusSipArsStatSigZoneId OBJECT-TYPE
    SYNTAX          Unsigned32
    MAX-ACCESS      read-only
    STATUS          current
    DESCRIPTION     
            "The Id of the Signaling Zone where address reachability service status
             is being shown."
    ::= { sonusSipArsStatusEntry 3 }

sonusSipArsStatRecordIndex OBJECT-TYPE
    SYNTAX          Unsigned32
    MAX-ACCESS      read-only
    STATUS          current
    DESCRIPTION     
            "The internal table index of the address reachability service table."
    ::= { sonusSipArsStatusEntry 4 }

sonusSipArsStatSigPortNum OBJECT-TYPE
    SYNTAX          Unsigned32
    MAX-ACCESS      read-only
    STATUS          current
    DESCRIPTION     
            "A signaling port in the signaling zone showing status."
    ::= { sonusSipArsStatusEntry 5 }

sonusSipArsStatEndpointIpAddress OBJECT-TYPE
    SYNTAX          IpAddress
    MAX-ACCESS      read-only
    STATUS          current
    DESCRIPTION     
            "Blacklisted endpoint's IP Address."
    ::= { sonusSipArsStatusEntry 6 }

sonusSipArsStatEndpointIpPortNum OBJECT-TYPE
    SYNTAX          Unsigned32 (1..65535)
    MAX-ACCESS      read-only
    STATUS          current
    DESCRIPTION     
            "Blacklisted endpoint's UDP port number."
    ::= { sonusSipArsStatusEntry 7 }

sonusSipArsStatEndpointArsState OBJECT-TYPE
    SYNTAX          INTEGER { idle(0), monitoring(1), blacklisted(2), 
                        recovering(3), distrib-blklist(4), 
                        distrib-recovery(5) }
    MAX-ACCESS      read-only
    STATUS          current
    DESCRIPTION     
            "Endpoint's address reachability service state."
    ::= { sonusSipArsStatusEntry 8 }

sonusSipArsStatEndpointStateTransitionTime OBJECT-TYPE
    SYNTAX          DateAndTime
    MAX-ACCESS      read-only
    STATUS          current
    DESCRIPTION     
            "Octet string that identifies the date and GMT time at which the
             endpoint's ARS state transitioned."
    ::= { sonusSipArsStatusEntry 9 }

sonusSipArsStatEndpointOwnerId OBJECT-TYPE
    SYNTAX          Unsigned32 (1..65535)
    MAX-ACCESS      read-only
    STATUS          current
    DESCRIPTION     
            "Blacklisted endpoints owner id. This is identifies the slot that originally  blacklisted the endpoint."
    ::= { sonusSipArsStatusEntry 10 }

sonusSipArsStatEndpointIpv6Address OBJECT-TYPE
    SYNTAX          Ipv6Address
    MAX-ACCESS      read-only
    STATUS          current
    DESCRIPTION     
            "Blacklisted endpoint's IPv6 Address."
    ::= { sonusSipArsStatusEntry 11 }

sonusSipArsEndpointRecoveryConfigObjects OBJECT IDENTIFIER
    ::= { sonusSipSignallingMIBObjects 23 }

sonusSipArsEndpointRecoverySigZoneId OBJECT-TYPE
    SYNTAX          Unsigned32 (0..2048)
    MAX-ACCESS      read-write
    STATUS          current
    DESCRIPTION     
            "The ID of the signaling zone of which endpoint(s) are being recovered."
    DEFVAL          { 0 }
    ::= { sonusSipArsEndpointRecoveryConfigObjects 1 }

sonusSipArsEndpointRecoverySigPortNum OBJECT-TYPE
    SYNTAX          Unsigned32 (1..2048)
    MAX-ACCESS      read-write
    STATUS          current
    DESCRIPTION     
            "The signaling port number of which endpoint(s) are being recovered."
    DEFVAL          { 0 }
    ::= { sonusSipArsEndpointRecoveryConfigObjects 2 }

sonusSipArsEndpointRecoveryIpAddress OBJECT-TYPE
    SYNTAX          IpAddress
    MAX-ACCESS      read-write
    STATUS          current
    DESCRIPTION     
            "The IP address of the endpoint being recovered."
    ::= { sonusSipArsEndpointRecoveryConfigObjects 3 }

sonusSipArsEndpointRecoveryIpPortNum OBJECT-TYPE
    SYNTAX          Integer32 (1..65535)
    MAX-ACCESS      read-write
    STATUS          current
    DESCRIPTION     
            "The IP port number of the endpoint being recovered."
    DEFVAL          { 5060 }
    ::= { sonusSipArsEndpointRecoveryConfigObjects 4 }

sonusSipArsEndpointRecoveryAll OBJECT-TYPE
    SYNTAX          INTEGER { none(0), oneSigZone(1), allSigZone(2), 
                        allinOneSlot(3) }
    MAX-ACCESS      read-write
    STATUS          current
    DESCRIPTION     
            "The flag for recovering a group of endpoints: all endpoints in one signaling
             zone or all endpoints in all signaling zones."
    DEFVAL          { 0 }
    ::= { sonusSipArsEndpointRecoveryConfigObjects 5 }

sonusSipArsEndpointRecoveryIpv6Address OBJECT-TYPE
    SYNTAX          Ipv6Address
    MAX-ACCESS      read-write
    STATUS          current
    DESCRIPTION     
            "The IPv6 address of the endpoint being recovered."
    ::= { sonusSipArsEndpointRecoveryConfigObjects 6 }

sonusSipEtsProfile OBJECT IDENTIFIER
    ::= { sonusSipSignallingMIBObjects 24 }

sonusSipEtsProfileNextIndex OBJECT-TYPE
    SYNTAX          Unsigned32
    MAX-ACCESS      not-accessible
    STATUS          current
    DESCRIPTION     
            "The next valid index to use when creating a new sonusSipEtsProfileEntry"
    ::= { sonusSipEtsProfile 1 }

sonusSipEtsProfileTable OBJECT-TYPE
    SYNTAX          SEQUENCE OF SonusSipEtsProfileEntry
    MAX-ACCESS      not-accessible
    STATUS          current
    DESCRIPTION     
            "This table contains information about each Ets
             Profile configured on the node."
    ::= { sonusSipEtsProfile 2 }

sonusSipEtsProfileEntry OBJECT-TYPE
    SYNTAX          SonusSipEtsProfileEntry
    MAX-ACCESS      not-accessible
    STATUS          current
    DESCRIPTION     
            "This table describes the Ets Profile."
    INDEX           { sonusSipEtsProfIndex }
    ::= { sonusSipEtsProfileTable 1 }

SonusSipEtsProfileEntry ::=
    SEQUENCE {
        sonusSipEtsProfIndex            Unsigned32,
        sonusSipEtsProfName             SonusName,
        sonusSipEtsProfRowStatus        RowStatus,
        sonusSipEtsProfRphEnabled       SonusAdminState,
        sonusSipEtsProfRphEtsDefault    Unsigned32,
        sonusSipEtsProfRphWpsPrecedence SonusAdminState,
        sonusSipEtsProfRphIncludeRequire SonusAdminState,
        sonusSipEtsProfRph417ResponseAction   INTEGER,
        sonusSipEtsProfRphInclude417Accept  SonusAdminState,
        sonusSipEtsProfRphUseIncomingEts SonusAdminState,
        sonusSipEtsProfRphRejectNonEtsDn SonusAdminState,
        sonusSipEtsProfRph400With417Stats SonusAdminState,
        sonusSipEtsProfRph417Stats      SonusAdminState,
        sonusSipEtsProfRph420Stats      SonusAdminState,
        sonusSipEtsProfEtsCpcPrecedence INTEGER,
        sonusSipEtsProfWpsMlppPrecedence INTEGER,
        sonusSipEtsProfSipCpcPriority   INTEGER,
        sonusSipEtsProfRphSendEtsInResponse   SonusAdminState
    }

sonusSipEtsProfIndex OBJECT-TYPE
    SYNTAX          Unsigned32
    MAX-ACCESS      not-accessible
    STATUS          current
    DESCRIPTION     
            "The index of the SIP Ets table entry."
    ::= { sonusSipEtsProfileEntry 1 }

sonusSipEtsProfName OBJECT-TYPE
    SYNTAX          SonusName
    MAX-ACCESS      read-write
    STATUS          current
    DESCRIPTION     
            "The name of this SIP Ets Profile."
    ::= { sonusSipEtsProfileEntry 2 }

sonusSipEtsProfRowStatus OBJECT-TYPE
    SYNTAX          RowStatus
    MAX-ACCESS      read-write
    STATUS          current
    DESCRIPTION     
            ""
    ::= { sonusSipEtsProfileEntry 3 }

sonusSipEtsProfRphEnabled OBJECT-TYPE
    SYNTAX          SonusAdminState
    MAX-ACCESS      read-write
    STATUS          current
    DESCRIPTION     
            "This parameter controls whether Ets is used or generated."
    DEFVAL          { disabled }
    ::= { sonusSipEtsProfileEntry 4 }

sonusSipEtsProfRphEtsDefault OBJECT-TYPE
    SYNTAX          Unsigned32 (0..4)
    MAX-ACCESS      read-write
    STATUS          current
    DESCRIPTION     
            "Default value used for the ETS namespace."
    DEFVAL          { 0 }
    ::= { sonusSipEtsProfileEntry 5 }

sonusSipEtsProfRphWpsPrecedence OBJECT-TYPE
    SYNTAX          SonusAdminState
    MAX-ACCESS      read-write
    STATUS          current
    DESCRIPTION     
            "This governs whether the ETS value will be taken from WPS precedence
             or from the configured default."
    DEFVAL          { disabled }
    ::= { sonusSipEtsProfileEntry 6 }

sonusSipEtsProfRphIncludeRequire OBJECT-TYPE
    SYNTAX          SonusAdminState
    MAX-ACCESS      read-write
    STATUS          current
    DESCRIPTION     
            "This controls whether a Require: Resource-Priority will be be
             included in an egress INVITE."
    DEFVAL          { disabled }
    ::= { sonusSipEtsProfileEntry 7 }

sonusSipEtsProfRph417ResponseAction OBJECT-TYPE
    SYNTAX          INTEGER { reject(1), resendnoets(2), 
                        resendetsdefault(3) }
    MAX-ACCESS      read-write
    STATUS          current
    DESCRIPTION     
            "This parameter controls the GSX behavior when it receives a 417 response."
    DEFVAL          { resendnoets }
    ::= { sonusSipEtsProfileEntry 8 }

sonusSipEtsProfRphInclude417Accept OBJECT-TYPE
    SYNTAX          SonusAdminState
    MAX-ACCESS      read-write
    STATUS          current
    DESCRIPTION     
            "This determines whether GSX includes the Accept-Resource-Priority header
             when sending a 417 response."
    DEFVAL          { disabled }
    ::= { sonusSipEtsProfileEntry 9 }

sonusSipEtsProfRphUseIncomingEts OBJECT-TYPE
    SYNTAX          SonusAdminState
    MAX-ACCESS      read-write
    STATUS          current
    DESCRIPTION     
            "This parameter controls whether the GSX accept the receievd ETS value or
             always override with the default."
    DEFVAL          { disabled }
    ::= { sonusSipEtsProfileEntry 10 }

sonusSipEtsProfRphRejectNonEtsDn OBJECT-TYPE
    SYNTAX          SonusAdminState
    MAX-ACCESS      read-write
    STATUS          current
    DESCRIPTION     
            "This governs whether a call with Ets but non-ETS-DN is accepted."
    DEFVAL          { disabled }
    ::= { sonusSipEtsProfileEntry 11 }

sonusSipEtsProfRph400With417Stats OBJECT-TYPE
    SYNTAX          SonusAdminState
    MAX-ACCESS      read-write
    STATUS          current
    DESCRIPTION     
            "This controls if to count incoming and outgoing 400 with 417 towards SIP statistics."
    DEFVAL          { enabled }
    ::= { sonusSipEtsProfileEntry 12 }

sonusSipEtsProfRph417Stats OBJECT-TYPE
    SYNTAX          SonusAdminState
    MAX-ACCESS      read-write
    STATUS          current
    DESCRIPTION     
            "This controls if to count incoming and outgoing 417 towards SIP statistics."
    DEFVAL          { enabled }
    ::= { sonusSipEtsProfileEntry 13 }

sonusSipEtsProfRph420Stats OBJECT-TYPE
    SYNTAX          SonusAdminState
    MAX-ACCESS      read-write
    STATUS          current
    DESCRIPTION     
            "This controls if to count incoming and outgoing 420 towards SIP statistics."
    DEFVAL          { enabled }
    ::= { sonusSipEtsProfileEntry 14 }

sonusSipEtsProfEtsCpcPrecedence OBJECT-TYPE
    SYNTAX          INTEGER { ets(1), cpc(2), hpc(3), sip-cpc(4) }
    MAX-ACCESS      read-write
    STATUS          current
    DESCRIPTION     
            "This parameter controls the GSX behavior when it receives conflicting ETS(RPH), and CPC(ISUP-MIME) values.
             Starting in Release 7.3, SIP-CPC is no longer supported."
    DEFVAL          { hpc }
    ::= { sonusSipEtsProfileEntry 15 }

sonusSipEtsProfWpsMlppPrecedence OBJECT-TYPE
    SYNTAX          INTEGER { wps(1), mlpp(2) }
    MAX-ACCESS      read-write
    STATUS          current
    DESCRIPTION     
            "This parameter controls the GSX behavior when it receives conflicting WPS(RPH)) and MLPP(ISUP-MIME) values."
    DEFVAL          { mlpp }
    ::= { sonusSipEtsProfileEntry 16 }

sonusSipEtsProfSipCpcPriority OBJECT-TYPE
    SYNTAX          INTEGER { none(1), priority(2) }
    MAX-ACCESS      read-write
    STATUS          obsolete
    DESCRIPTION     
            "This field has been obsolete since release 7.3."
    DEFVAL          { none }
    ::= { sonusSipEtsProfileEntry 17 }

sonusSipEtsProfRphSendEtsInResponse OBJECT-TYPE
    SYNTAX          SonusAdminState
    MAX-ACCESS      read-write
    STATUS          current
    DESCRIPTION     
            "This parameter controls whether to send received ets value in response."
    DEFVAL          { disabled }
    ::= { sonusSipEtsProfileEntry 18 }

sonusSipSigPortTlsStatTable OBJECT-TYPE
    SYNTAX          SEQUENCE OF SonusSipSigPortTlsStatEntry
    MAX-ACCESS      not-accessible
    STATUS          current
    DESCRIPTION     
            "Table of SIP Signalling Port TLS statistics data."
    ::= { sonusSipSignallingMIBObjects 25 }

sonusSipSigPortTlsStatEntry OBJECT-TYPE
    SYNTAX          SonusSipSigPortTlsStatEntry
    MAX-ACCESS      not-accessible
    STATUS          current
    DESCRIPTION     
            "SIP Signalling Port TLS Statistics."
    INDEX           { sonusSipSigPortTlsStatIndex }
    ::= { sonusSipSigPortTlsStatTable 1 }

SonusSipSigPortTlsStatEntry ::=
    SEQUENCE {
        sonusSipSigPortTlsStatIndex     Unsigned32,
        sonusSipSigPortTlsStatActiveClientSessions          Gauge32,
        sonusSipSigPortTlsStatActiveServerSessions          Gauge32,
        sonusSipSigPortTlsStatSuspendedClientSessions             Gauge32,
        sonusSipSigPortTlsStatSuspendedServerSessions             Gauge32,
        sonusSipSigPortTlsStatIncClientHandshakes         Gauge32,
        sonusSipSigPortTlsStatIncServerHandshakes         Gauge32,
        sonusSipSigPortTlsStatTotalClientSessions         Counter32,
        sonusSipSigPortTlsStatTotalServerSessions         Counter32,
        sonusSipSigPortTlsStatTotalServerResumed        Counter32,
        sonusSipSigPortTlsStatNoCipherSuite   Counter32,
        sonusSipSigPortTlsStatHandshakeTimeout      Counter32,
        sonusSipSigPortTlsStatHigherAuthTimeout       Counter32,
        sonusSipSigPortTlsStatClientAuthFail    Counter32,
        sonusSipSigPortTlsStatServerAuthFail    Counter32,
        sonusSipSigPortTlsStatFatalAlerts Counter32,
        sonusSipSigPortTlsStatWarningAlerts   Counter32,
        sonusSipSigPortTlsStatHandshakeFails    Counter32,
        sonusSipSigPortTlsStatRcvFails  Counter32,
        sonusSipSigPortTlsStatSendFails Counter32,
        sonusSipSigPortTlsStatNoAuthDrops Counter32,
        sonusSipSigPortTlsStatNoAuth488 Counter32,
        sonusSipSigPortTlsStatMidConnHello  Counter32,
        sonusSipSigPortTlsStatNoClientCert  Counter32,
        sonusSipSigPortTlsStatCountReset INTEGER
    }

sonusSipSigPortTlsStatIndex OBJECT-TYPE
    SYNTAX          Unsigned32
    MAX-ACCESS      read-only
    STATUS          current
    DESCRIPTION     
            "Identifies the SIP Signaling Port entry."
    ::= { sonusSipSigPortTlsStatEntry 1 }

sonusSipSigPortTlsStatActiveClientSessions OBJECT-TYPE
    SYNTAX          Gauge32
    MAX-ACCESS      read-only
    STATUS          current
    DESCRIPTION     
            "Number of current up sessions in which the GSX is the client"
    ::= { sonusSipSigPortTlsStatEntry 2 }

sonusSipSigPortTlsStatActiveServerSessions OBJECT-TYPE
    SYNTAX          Gauge32
    MAX-ACCESS      read-only
    STATUS          current
    DESCRIPTION     
            "Number of current up sessions in which the GSX is the server"
    ::= { sonusSipSigPortTlsStatEntry 3 }

sonusSipSigPortTlsStatSuspendedClientSessions OBJECT-TYPE
    SYNTAX          Gauge32
    MAX-ACCESS      read-only
    STATUS          current
    DESCRIPTION     
            "Number of current suspended sessions in which the GSX is the client"
    ::= { sonusSipSigPortTlsStatEntry 4 }

sonusSipSigPortTlsStatSuspendedServerSessions OBJECT-TYPE
    SYNTAX          Gauge32
    MAX-ACCESS      read-only
    STATUS          current
    DESCRIPTION     
            "Number of current suspended sessions in which the GSX is the server"
    ::= { sonusSipSigPortTlsStatEntry 5 }

sonusSipSigPortTlsStatIncClientHandshakes OBJECT-TYPE
    SYNTAX          Gauge32
    MAX-ACCESS      read-only
    STATUS          current
    DESCRIPTION     
            "Number of current incomplete handshakes in which the GSX is the client"
    ::= { sonusSipSigPortTlsStatEntry 6 }

sonusSipSigPortTlsStatIncServerHandshakes OBJECT-TYPE
    SYNTAX          Gauge32
    MAX-ACCESS      read-only
    STATUS          current
    DESCRIPTION     
            "Number of current incomplete handshakes in which the GSX is the server"
    ::= { sonusSipSigPortTlsStatEntry 7 }

sonusSipSigPortTlsStatTotalClientSessions OBJECT-TYPE
    SYNTAX          Counter32
    MAX-ACCESS      read-only
    STATUS          current
    DESCRIPTION     
            "Cumulative total number of sessions in which the GSX is the client"
    ::= { sonusSipSigPortTlsStatEntry 8 }

sonusSipSigPortTlsStatTotalServerSessions OBJECT-TYPE
    SYNTAX          Counter32
    MAX-ACCESS      read-only
    STATUS          current
    DESCRIPTION     
            "Cumulative total number of sessions in which the GSX is the server"
    ::= { sonusSipSigPortTlsStatEntry 9 }

sonusSipSigPortTlsStatTotalServerResumed OBJECT-TYPE
    SYNTAX          Counter32
    MAX-ACCESS      read-only
    STATUS          current
    DESCRIPTION     
            "Number of sessions that have been resumed in which the GSX is the server"
    ::= { sonusSipSigPortTlsStatEntry 10 }

sonusSipSigPortTlsStatNoCipherSuite OBJECT-TYPE
    SYNTAX          Counter32
    MAX-ACCESS      read-only
    STATUS          current
    DESCRIPTION     
            "Number of handshake failures due to inability to converge on a cipher suite"
    ::= { sonusSipSigPortTlsStatEntry 11 }

sonusSipSigPortTlsStatHandshakeTimeout OBJECT-TYPE
    SYNTAX          Counter32
    MAX-ACCESS      read-only
    STATUS          current
    DESCRIPTION     
            "Number of handshakes that timed out before completing"
    ::= { sonusSipSigPortTlsStatEntry 12 }

sonusSipSigPortTlsStatHigherAuthTimeout OBJECT-TYPE
    SYNTAX          Counter32
    MAX-ACCESS      read-only
    STATUS          current
    DESCRIPTION     
            "Number of handshakes in which the GSX was the server
             and the client did not authenticate itself through TLS
             and failed to authenticate itself through any higher level
             protocol (e.g. SIP) before timing out"
    ::= { sonusSipSigPortTlsStatEntry 13 }

sonusSipSigPortTlsStatClientAuthFail OBJECT-TYPE
    SYNTAX          Counter32
    MAX-ACCESS      read-only
    STATUS          current
    DESCRIPTION     
            "Number of times peer failed TLS authentication when
             the GSX was the client"
    ::= { sonusSipSigPortTlsStatEntry 14 }

sonusSipSigPortTlsStatServerAuthFail OBJECT-TYPE
    SYNTAX          Counter32
    MAX-ACCESS      read-only
    STATUS          current
    DESCRIPTION     
            "Number of times peer failed TLS authentication when
             the GSX was the server"
    ::= { sonusSipSigPortTlsStatEntry 15 }

sonusSipSigPortTlsStatFatalAlerts OBJECT-TYPE
    SYNTAX          Counter32
    MAX-ACCESS      read-only
    STATUS          current
    DESCRIPTION     
            "Number of FATAL Alerts received"
    ::= { sonusSipSigPortTlsStatEntry 16 }

sonusSipSigPortTlsStatWarningAlerts OBJECT-TYPE
    SYNTAX          Counter32
    MAX-ACCESS      read-only
    STATUS          current
    DESCRIPTION     
            "Number of WARNING Alerts received"
    ::= { sonusSipSigPortTlsStatEntry 17 }

sonusSipSigPortTlsStatHandshakeFails OBJECT-TYPE
    SYNTAX          Counter32
    MAX-ACCESS      read-only
    STATUS          current
    DESCRIPTION     
            "Cumulative total of all handshake failures"
    ::= { sonusSipSigPortTlsStatEntry 18 }

sonusSipSigPortTlsStatRcvFails OBJECT-TYPE
    SYNTAX          Counter32
    MAX-ACCESS      read-only
    STATUS          current
    DESCRIPTION     
            "Number of receive failures (failure to decrypt)"
    ::= { sonusSipSigPortTlsStatEntry 19 }

sonusSipSigPortTlsStatSendFails OBJECT-TYPE
    SYNTAX          Counter32
    MAX-ACCESS      read-only
    STATUS          current
    DESCRIPTION     
            "Number of send failures (failure to encrypt)"
    ::= { sonusSipSigPortTlsStatEntry 20 }

sonusSipSigPortTlsStatNoAuthDrops OBJECT-TYPE
    SYNTAX          Counter32
    MAX-ACCESS      read-only
    STATUS          current
    DESCRIPTION     
            "Number of SIP messages dropped due to lack
             of peer authentication at the SIP level"
    ::= { sonusSipSigPortTlsStatEntry 21 }

sonusSipSigPortTlsStatNoAuth488 OBJECT-TYPE
    SYNTAX          Counter32
    MAX-ACCESS      read-only
    STATUS          current
    DESCRIPTION     
            "Number of SIP messages rejected with 488 due to lack
             of peer authentication at the SIP level"
    ::= { sonusSipSigPortTlsStatEntry 22 }

sonusSipSigPortTlsStatMidConnHello OBJECT-TYPE
    SYNTAX          Counter32
    MAX-ACCESS      read-only
    STATUS          current
    DESCRIPTION     
            "Number times a peer sent a TLS Hello on a connection
             that was already up (i.e. the peer tried to renegotiate.)"
    ::= { sonusSipSigPortTlsStatEntry 23 }

sonusSipSigPortTlsStatNoClientCert OBJECT-TYPE
    SYNTAX          Counter32
    MAX-ACCESS      read-only
    STATUS          current
    DESCRIPTION     
            "Number times we were the client and we failed to
             derive a certificate to send the server (in the mutual
             authentication case). This is probably because there was
             no overlap between our configured trust anchors and the list
             of trust anchors the server sent in its Certificate Request"
    ::= { sonusSipSigPortTlsStatEntry 24 }

sonusSipSigPortTlsStatCountReset OBJECT-TYPE
    SYNTAX          INTEGER { unknown(1), reset(2) }
    MAX-ACCESS      read-write
    STATUS          current
    DESCRIPTION     
            "set opertion on this object resets all the TLS statistics counts to zero"
    ::= { sonusSipSigPortTlsStatEntry 25 }

sonusSipSigPortTlsStatusTable OBJECT-TYPE
    SYNTAX          SEQUENCE OF SonusSipSigPortTlsStatusEntry
    MAX-ACCESS      not-accessible
    STATUS          current
    DESCRIPTION     
            "Table of SIP Signalling Port TLS status data."
    ::= { sonusSipSignallingMIBObjects 26 }

sonusSipSigPortTlsStatusEntry OBJECT-TYPE
    SYNTAX          SonusSipSigPortTlsStatusEntry
    MAX-ACCESS      not-accessible
    STATUS          current
    DESCRIPTION     
            "SIP Signalling Port TLS Status information."
    INDEX           { sonusSipSigPortTlsStatusSSPIndex, 
                      sonusSipSigPortTlsStatusPeerIpAddress, 
                      sonusSipSigPortTlsStatusPeerIp6Address, 
                      sonusSipSigPortTlsStatusVersion, 
                      sonusSipSigPortTlsStatusSession }
    ::= { sonusSipSigPortTlsStatusTable 1 }

SonusSipSigPortTlsStatusEntry ::=
    SEQUENCE {
        sonusSipSigPortTlsStatusSSPIndex Unsigned32,
        sonusSipSigPortTlsStatusSession Unsigned32,
        sonusSipSigPortTlsStatusPeerIpAddress     IpAddress,
        sonusSipSigPortTlsStatusPeerPortNum   Integer32,
        sonusSipSigPortTlsStatusSocket  Integer32,
        sonusSipSigPortTlsStatusSessionID OCTET STRING,
        sonusSipSigPortTlsStatusConnId  Integer32,
        sonusSipSigPortTlsStatusSessState INTEGER,
        sonusSipSigPortTlsStatusRole    INTEGER,
        sonusSipSigPortTlsStatusResumptions   Counter32,
        sonusSipSigPortTlsStatusBytesSent Counter32,
        sonusSipSigPortTlsStatusRecordsSent   Counter32,
        sonusSipSigPortTlsStatusBytesRecOK  Counter32,
        sonusSipSigPortTlsStatusRecordsRecOK    Counter32,
        sonusSipSigPortTlsStatusRowStatus RowStatus,
        sonusSipSigPortTlsStatusPeerIp6Address      Ipv6Address,
        sonusSipSigPortTlsStatusVersion INTEGER
    }

sonusSipSigPortTlsStatusSSPIndex OBJECT-TYPE
    SYNTAX          Unsigned32
    MAX-ACCESS      read-only
    STATUS          current
    DESCRIPTION     
            "Identifies the SIP Signaling Port entry."
    ::= { sonusSipSigPortTlsStatusEntry 1 }

sonusSipSigPortTlsStatusSession OBJECT-TYPE
    SYNTAX          Unsigned32
    MAX-ACCESS      read-only
    STATUS          current
    DESCRIPTION     
            "Identifies the TLS session. This is an internal session tracking
             number and should not be confused with the session ID that
             is actually used on the wire between the TLS peers."
    ::= { sonusSipSigPortTlsStatusEntry 2 }

sonusSipSigPortTlsStatusPeerIpAddress OBJECT-TYPE
    SYNTAX          IpAddress
    MAX-ACCESS      read-only
    STATUS          current
    DESCRIPTION     
            "IP address of the peer of this session"
    ::= { sonusSipSigPortTlsStatusEntry 3 }

sonusSipSigPortTlsStatusPeerPortNum OBJECT-TYPE
    SYNTAX          Integer32
    MAX-ACCESS      read-only
    STATUS          current
    DESCRIPTION     
            "TCP port number used by the peer of this session"
    ::= { sonusSipSigPortTlsStatusEntry 4 }

sonusSipSigPortTlsStatusSocket OBJECT-TYPE
    SYNTAX          Integer32
    MAX-ACCESS      read-only
    STATUS          current
    DESCRIPTION     
            "socket number used internally for the TCP component of this session"
    ::= { sonusSipSigPortTlsStatusEntry 5 }

sonusSipSigPortTlsStatusSessionID OBJECT-TYPE
    SYNTAX          OCTET STRING (SIZE(0..32))
    MAX-ACCESS      read-only
    STATUS          current
    DESCRIPTION     
            "The TLS Session ID of this session"
    ::= { sonusSipSigPortTlsStatusEntry 6 }

sonusSipSigPortTlsStatusConnId OBJECT-TYPE
    SYNTAX          Integer32
    MAX-ACCESS      read-only
    STATUS          current
    DESCRIPTION     
            "Current internal connection ID of this session
             (0 means none, i.e. suspended session)"
    ::= { sonusSipSigPortTlsStatusEntry 7 }

sonusSipSigPortTlsStatusSessState OBJECT-TYPE
    SYNTAX          INTEGER { none(1), suspended(2), tcpConnecting(3), 
                        negotiating(4), highLevelAuth(5), up(6) }
    MAX-ACCESS      read-only
    STATUS          current
    DESCRIPTION     
            "Connection state of this session"
    ::= { sonusSipSigPortTlsStatusEntry 8 }

sonusSipSigPortTlsStatusRole OBJECT-TYPE
    SYNTAX          INTEGER { client(1), server(2) }
    MAX-ACCESS      read-only
    STATUS          current
    DESCRIPTION     
            "The role taken by the GSX in this session"
    ::= { sonusSipSigPortTlsStatusEntry 9 }

sonusSipSigPortTlsStatusResumptions OBJECT-TYPE
    SYNTAX          Counter32
    MAX-ACCESS      read-only
    STATUS          current
    DESCRIPTION     
            "Number of times this session has been resumed"
    ::= { sonusSipSigPortTlsStatusEntry 10 }

sonusSipSigPortTlsStatusBytesSent OBJECT-TYPE
    SYNTAX          Counter32
    MAX-ACCESS      read-only
    STATUS          current
    DESCRIPTION     
            "Number of payload bytes sent on the current connection associated
             with this session"
    ::= { sonusSipSigPortTlsStatusEntry 11 }

sonusSipSigPortTlsStatusRecordsSent OBJECT-TYPE
    SYNTAX          Counter32
    MAX-ACCESS      read-only
    STATUS          current
    DESCRIPTION     
            "Number of TLS records sent on the current connection associated
             with this session"
    ::= { sonusSipSigPortTlsStatusEntry 12 }

sonusSipSigPortTlsStatusBytesRecOK OBJECT-TYPE
    SYNTAX          Counter32
    MAX-ACCESS      read-only
    STATUS          current
    DESCRIPTION     
            "Number of payload bytes received on the current connection
             without integrity check failure"
    ::= { sonusSipSigPortTlsStatusEntry 13 }

sonusSipSigPortTlsStatusRecordsRecOK OBJECT-TYPE
    SYNTAX          Counter32
    MAX-ACCESS      read-only
    STATUS          current
    DESCRIPTION     
            "Number of TLS records received on the current connection
             without integrity check failure"
    ::= { sonusSipSigPortTlsStatusEntry 14 }

sonusSipSigPortTlsStatusRowStatus OBJECT-TYPE
    SYNTAX          RowStatus
    MAX-ACCESS      read-write
    STATUS          current
    DESCRIPTION     
            "This is for SNMP use."
    ::= { sonusSipSigPortTlsStatusEntry 15 }

sonusSipSigPortTlsStatusPeerIp6Address OBJECT-TYPE
    SYNTAX          Ipv6Address
    MAX-ACCESS      read-only
    STATUS          current
    DESCRIPTION     
            "IP address of the peer of this session"
    ::= { sonusSipSigPortTlsStatusEntry 16 }

sonusSipSigPortTlsStatusVersion OBJECT-TYPE
    SYNTAX          INTEGER { afInet(2), afInet6(24) }
    MAX-ACCESS      read-only
    STATUS          current
    DESCRIPTION     
            "The role taken by the GSX in this session"
    ::= { sonusSipSigPortTlsStatusEntry 17 }

sonusFilterProfile OBJECT IDENTIFIER
    ::= { sonusSipSignallingMIBObjects 27 }

sonusFilterProfileNextIndex OBJECT-TYPE
    SYNTAX          Unsigned32
    MAX-ACCESS      not-accessible
    STATUS          current
    DESCRIPTION     
            "The next valid index to use when creating a new sonusFilterProfileEntry"
    ::= { sonusFilterProfile 1 }

sonusFilterProfileTable OBJECT-TYPE
    SYNTAX          SEQUENCE OF SonusFilterProfileEntry
    MAX-ACCESS      not-accessible
    STATUS          current
    DESCRIPTION     
            "This table contains information about each Filter
             Profile configured on the node."
    ::= { sonusFilterProfile 2 }

sonusFilterProfileEntry OBJECT-TYPE
    SYNTAX          SonusFilterProfileEntry
    MAX-ACCESS      not-accessible
    STATUS          current
    DESCRIPTION     
            "This table describes the Filter Profile."
    INDEX           { sonusFilterProfIndex }
    ::= { sonusFilterProfileTable 1 }

SonusFilterProfileEntry ::=
    SEQUENCE {
        sonusFilterProfIndex            Unsigned32,
        sonusFilterProfName             SonusName,
        sonusFilterProfRowStatus        RowStatus,
        sonusFilterProfAccepted         SonusFilterProfileState,
        sonusFilterProfAcceptResourcePriority     SonusFilterProfileState,
        sonusFilterProfAlertInfo        SonusFilterProfileState,
        sonusFilterProfAllowed          SonusFilterProfileState,
        sonusFilterProfAlso             SonusFilterProfileState,
        sonusFilterProfAnonymity        SonusFilterProfileState,
        sonusFilterProfAuthorization    SonusFilterProfileState,
        sonusFilterProfCallConnectId    SonusFilterProfileState,
        sonusFilterProfContentDisp      SonusFilterProfileState,
        sonusFilterProfDiversion        SonusFilterProfileState,
        sonusFilterProfError            SonusFilterProfileState,
        sonusFilterProfErrorInfo        SonusFilterProfileState,
        sonusFilterProfEvent            SonusFilterProfileState,
        sonusFilterProfExpire           SonusFilterProfileState,
        sonusFilterProfMaxForwards      SonusFilterProfileState,
        sonusFilterProfMinExpires       SonusFilterProfileState,
        sonusFilterProfMinSe            SonusFilterProfileState,
        sonusFilterProfPAssertedId      SonusFilterProfileState,
        sonusFilterProfPCarrierInfo     SonusFilterProfileStateWithUnknown,
        sonusFilterProfPChargingVector  SonusFilterProfileState,
        sonusFilterProfPKAdn            SonusFilterProfileStateWithUnknown,
        sonusFilterProfPPreferredId     SonusFilterProfileState,
        sonusFilterProfPSigInfo         SonusFilterProfileState,
        sonusFilterProfPSvcInfo         SonusFilterProfileState,
        sonusFilterProfPTermCa          SonusFilterProfileStateWithUnknown,
        sonusFilterProfPath             SonusFilterProfileState,
        sonusFilterProfPCdrInfo         SonusFilterProfileState,
        sonusFilterProfPChargeInfo      SonusFilterProfileState,
        sonusFilterProfPKCfl            SonusFilterProfileState,
        sonusFilterProfPKCfo            SonusFilterProfileState,
        sonusFilterProfPrivacy          SonusFilterProfileState,
        sonusFilterProfProxyAuthorization SonusFilterProfileState,
        sonusFilterProfProxyReq         SonusFilterProfileState,
        sonusFilterProfReason           SonusFilterProfileState,
        sonusFilterProfRemoteParty      SonusFilterProfileState,
        sonusFilterProfReplaces         SonusFilterProfileState,
        sonusFilterProfReplyTo          SonusFilterProfileState,
        sonusFilterProfRequestBy        SonusFilterProfileState,
        sonusFilterProfRequired         SonusFilterProfileState,
        sonusFilterProfResourcePriority SonusFilterProfileState,
        sonusFilterProfRetryAfter       SonusFilterProfileState,
        sonusFilterProfRoute            SonusFilterProfileState,
        sonusFilterProfServiceRoute     SonusFilterProfileState,
        sonusFilterProfSessExpires      SonusFilterProfileState,
        sonusFilterProfSubscriptionState SonusFilterProfileState,
        sonusFilterProfSupported        SonusFilterProfileState,
        sonusFilterProfTimeStamp        SonusFilterProfileStateWithUnknown,
        sonusFilterProfUnknown          SonusFilterProfileState,
        sonusFilterProfUnsupported      SonusFilterProfileState,
        sonusFilterProfWWWAuthenticate  SonusFilterProfileState,
        sonusFilterProfAcceptContact    SonusFilterProfileStateWithUnknown,
        sonusFilterProfHistoryInfo      SonusFilterProfileStateWithUnknown,
        sonusFilterProfPChgMsgInfo      SonusFilterProfileStateWithUnknown,
        sonusFilterProfPOrigCa          SonusFilterProfileStateWithUnknown,
        sonusFilterProfTargetDialog     SonusFilterProfileStateWithUnknown,
        sonusFilterProfUserAgent        SonusFilterProfileStateWithUnknown,
        sonusFilterProfServer           SonusFilterProfileStateWithUnknown,
        sonusFilterProfWarning          SonusFilterProfileStateWithUnknown,
        sonusFilterProfAcceptLanguage   SonusFilterProfileStateWithUnknown,
        sonusFilterProfCallInfo         SonusFilterProfileStateWithUnknown,
        sonusFilterProfSipEtag          SonusFilterProfileStateWithUnknown,
        sonusFilterProfSipIfMatch       SonusFilterProfileStateWithUnknown,
        sonusFilterProfSuppressIfMatch  SonusFilterProfileStateWithUnknown,
        sonusFilterProfReferSub         SonusFilterProfileStateWithUnknown,
        sonusFilterProfProxyAuthenticate SonusFilterProfileStateWithUnknown,
        sonusFilterProfPEarlyMedia      SonusFilterProfileStateWithUnknown,
        sonusFilterProfPAssociatedUri   SonusFilterProfileStateWithUnknown,
        sonusFilterProfXSrvcIndicator   SonusFilterProfileStateWithUnknown,
        sonusFilterProfPDcsBillingInfo  SonusFilterProfileStateWithUnknown,
        sonusFilterProfRecordRoute      SonusFilterProfileState,
        sonusFilterProfReferTo          SonusFilterProfileState,
        sonusFilterProfReferredBy       SonusFilterProfileState
    }

sonusFilterProfIndex OBJECT-TYPE
    SYNTAX          Unsigned32
    MAX-ACCESS      not-accessible
    STATUS          current
    DESCRIPTION     
            "The index of the Filter table entry."
    ::= { sonusFilterProfileEntry 1 }

sonusFilterProfName OBJECT-TYPE
    SYNTAX          SonusName
    MAX-ACCESS      read-write
    STATUS          current
    DESCRIPTION     
            "The name of this Filter Profile."
    ::= { sonusFilterProfileEntry 2 }

sonusFilterProfRowStatus OBJECT-TYPE
    SYNTAX          RowStatus
    MAX-ACCESS      read-write
    STATUS          current
    DESCRIPTION     
            ""
    ::= { sonusFilterProfileEntry 3 }

sonusFilterProfAccepted OBJECT-TYPE
    SYNTAX          SonusFilterProfileState
    MAX-ACCESS      read-write
    STATUS          current
    DESCRIPTION     
            "Accept Header will be filtered when enabled."
    DEFVAL          { parse }
    ::= { sonusFilterProfileEntry 4 }

sonusFilterProfAcceptResourcePriority OBJECT-TYPE
    SYNTAX          SonusFilterProfileState
    MAX-ACCESS      read-write
    STATUS          current
    DESCRIPTION     
            "Accept Resource Priority Header will be filtered when enabled."
    DEFVAL          { parse }
    ::= { sonusFilterProfileEntry 5 }

sonusFilterProfAlertInfo OBJECT-TYPE
    SYNTAX          SonusFilterProfileState
    MAX-ACCESS      read-write
    STATUS          current
    DESCRIPTION     
            "Alert Info Header will be filtered when enabled."
    DEFVAL          { parse }
    ::= { sonusFilterProfileEntry 6 }

sonusFilterProfAllowed OBJECT-TYPE
    SYNTAX          SonusFilterProfileState
    MAX-ACCESS      read-write
    STATUS          current
    DESCRIPTION     
            "Allowed Header will be filtered when enabled."
    DEFVAL          { parse }
    ::= { sonusFilterProfileEntry 7 }

sonusFilterProfAlso OBJECT-TYPE
    SYNTAX          SonusFilterProfileState
    MAX-ACCESS      read-write
    STATUS          current
    DESCRIPTION     
            "Also Header will be filtered when enabled."
    DEFVAL          { parse }
    ::= { sonusFilterProfileEntry 8 }

sonusFilterProfAnonymity OBJECT-TYPE
    SYNTAX          SonusFilterProfileState
    MAX-ACCESS      read-write
    STATUS          current
    DESCRIPTION     
            "Anonymity Header will be filtered when enabled."
    DEFVAL          { parse }
    ::= { sonusFilterProfileEntry 9 }

sonusFilterProfAuthorization OBJECT-TYPE
    SYNTAX          SonusFilterProfileState
    MAX-ACCESS      read-write
    STATUS          current
    DESCRIPTION     
            "Authorization Header will be filtered when enabled."
    DEFVAL          { parse }
    ::= { sonusFilterProfileEntry 10 }

sonusFilterProfCallConnectId OBJECT-TYPE
    SYNTAX          SonusFilterProfileState
    MAX-ACCESS      read-write
    STATUS          current
    DESCRIPTION     
            "Call Connect ID Header will be filtered when enabled."
    DEFVAL          { parse }
    ::= { sonusFilterProfileEntry 11 }

sonusFilterProfContentDisp OBJECT-TYPE
    SYNTAX          SonusFilterProfileState
    MAX-ACCESS      read-write
    STATUS          current
    DESCRIPTION     
            "Content Disposition Header will be filtered when enabled."
    DEFVAL          { parse }
    ::= { sonusFilterProfileEntry 12 }

sonusFilterProfDiversion OBJECT-TYPE
    SYNTAX          SonusFilterProfileState
    MAX-ACCESS      read-write
    STATUS          current
    DESCRIPTION     
            "Diversion Header will be filtered when enabled."
    DEFVAL          { parse }
    ::= { sonusFilterProfileEntry 13 }

sonusFilterProfError OBJECT-TYPE
    SYNTAX          SonusFilterProfileState
    MAX-ACCESS      read-write
    STATUS          current
    DESCRIPTION     
            "Error Header will be filtered when enabled."
    DEFVAL          { parse }
    ::= { sonusFilterProfileEntry 14 }

sonusFilterProfErrorInfo OBJECT-TYPE
    SYNTAX          SonusFilterProfileState
    MAX-ACCESS      read-write
    STATUS          current
    DESCRIPTION     
            "Error Info Header will be filtered when enabled."
    DEFVAL          { parse }
    ::= { sonusFilterProfileEntry 15 }

sonusFilterProfEvent OBJECT-TYPE
    SYNTAX          SonusFilterProfileState
    MAX-ACCESS      read-write
    STATUS          current
    DESCRIPTION     
            "Event Header will be filtered when enabled."
    DEFVAL          { parse }
    ::= { sonusFilterProfileEntry 16 }

sonusFilterProfExpire OBJECT-TYPE
    SYNTAX          SonusFilterProfileState
    MAX-ACCESS      read-write
    STATUS          current
    DESCRIPTION     
            "Expires Header will be filtered when enabled."
    DEFVAL          { parse }
    ::= { sonusFilterProfileEntry 17 }

sonusFilterProfMaxForwards OBJECT-TYPE
    SYNTAX          SonusFilterProfileState
    MAX-ACCESS      read-write
    STATUS          current
    DESCRIPTION     
            "Max Forwards Header will be filtered when enabled."
    DEFVAL          { parse }
    ::= { sonusFilterProfileEntry 18 }

sonusFilterProfMinExpires OBJECT-TYPE
    SYNTAX          SonusFilterProfileState
    MAX-ACCESS      read-write
    STATUS          current
    DESCRIPTION     
            "Min Expires Header will be filtered when enabled."
    DEFVAL          { parse }
    ::= { sonusFilterProfileEntry 19 }

sonusFilterProfMinSe OBJECT-TYPE
    SYNTAX          SonusFilterProfileState
    MAX-ACCESS      read-write
    STATUS          current
    DESCRIPTION     
            "Min SE Header will be filtered when enabled."
    DEFVAL          { parse }
    ::= { sonusFilterProfileEntry 20 }

sonusFilterProfPAssertedId OBJECT-TYPE
    SYNTAX          SonusFilterProfileState
    MAX-ACCESS      read-write
    STATUS          current
    DESCRIPTION     
            "P_Asserted_ID Header will be filtered when enabled."
    DEFVAL          { parse }
    ::= { sonusFilterProfileEntry 21 }

sonusFilterProfPCarrierInfo OBJECT-TYPE
    SYNTAX          SonusFilterProfileStateWithUnknown
    MAX-ACCESS      read-write
    STATUS          current
    DESCRIPTION     
            "P_Carrier_Info Header will be filtered when enabled."
    DEFVAL          { parse }
    ::= { sonusFilterProfileEntry 22 }

sonusFilterProfPChargingVector OBJECT-TYPE
    SYNTAX          SonusFilterProfileState
    MAX-ACCESS      read-write
    STATUS          current
    DESCRIPTION     
            "P_Charging_Vector Header will be filtered when enabled."
    DEFVAL          { parse }
    ::= { sonusFilterProfileEntry 23 }

sonusFilterProfPKAdn OBJECT-TYPE
    SYNTAX          SonusFilterProfileStateWithUnknown
    MAX-ACCESS      read-write
    STATUS          current
    DESCRIPTION     
            "P_K_ADN Header will be set to TREATASUNKNOWN by default. This should be modified to parse once parsing support is implemented."
    DEFVAL          { treatasunknown }
    ::= { sonusFilterProfileEntry 24 }

sonusFilterProfPPreferredId OBJECT-TYPE
    SYNTAX          SonusFilterProfileState
    MAX-ACCESS      read-write
    STATUS          current
    DESCRIPTION     
            "P_Preferred_ID Header will be filtered when enabled."
    DEFVAL          { parse }
    ::= { sonusFilterProfileEntry 25 }

sonusFilterProfPSigInfo OBJECT-TYPE
    SYNTAX          SonusFilterProfileState
    MAX-ACCESS      read-write
    STATUS          current
    DESCRIPTION     
            "P_Sig_Info Header will be filtered when enabled."
    DEFVAL          { parse }
    ::= { sonusFilterProfileEntry 26 }

sonusFilterProfPSvcInfo OBJECT-TYPE
    SYNTAX          SonusFilterProfileState
    MAX-ACCESS      read-write
    STATUS          current
    DESCRIPTION     
            "P_Svc_Info Header will be filtered when enabled."
    DEFVAL          { parse }
    ::= { sonusFilterProfileEntry 27 }

sonusFilterProfPTermCa OBJECT-TYPE
    SYNTAX          SonusFilterProfileStateWithUnknown
    MAX-ACCESS      read-write
    STATUS          current
    DESCRIPTION     
            "P_Term_CA Header will be filtered when enabled."
    DEFVAL          { parse }
    ::= { sonusFilterProfileEntry 28 }

sonusFilterProfPath OBJECT-TYPE
    SYNTAX          SonusFilterProfileState
    MAX-ACCESS      read-write
    STATUS          current
    DESCRIPTION     
            "Path Header will be filtered when enabled."
    DEFVAL          { parse }
    ::= { sonusFilterProfileEntry 29 }

sonusFilterProfPCdrInfo OBJECT-TYPE
    SYNTAX          SonusFilterProfileState
    MAX-ACCESS      read-write
    STATUS          current
    DESCRIPTION     
            "PCdrInfo Header will be filtered when enabled."
    DEFVAL          { parse }
    ::= { sonusFilterProfileEntry 30 }

sonusFilterProfPChargeInfo OBJECT-TYPE
    SYNTAX          SonusFilterProfileState
    MAX-ACCESS      read-write
    STATUS          current
    DESCRIPTION     
            "PChargeInfo Header will be filtered when enabled."
    DEFVAL          { parse }
    ::= { sonusFilterProfileEntry 31 }

sonusFilterProfPKCfl OBJECT-TYPE
    SYNTAX          SonusFilterProfileState
    MAX-ACCESS      read-write
    STATUS          current
    DESCRIPTION     
            "PKCfl Header will be filtered when enabled."
    DEFVAL          { parse }
    ::= { sonusFilterProfileEntry 32 }

sonusFilterProfPKCfo OBJECT-TYPE
    SYNTAX          SonusFilterProfileState
    MAX-ACCESS      read-write
    STATUS          current
    DESCRIPTION     
            "PKCfo Header will be filtered when enabled."
    DEFVAL          { parse }
    ::= { sonusFilterProfileEntry 33 }

sonusFilterProfPrivacy OBJECT-TYPE
    SYNTAX          SonusFilterProfileState
    MAX-ACCESS      read-write
    STATUS          current
    DESCRIPTION     
            "Privacy Header will be filtered when enabled."
    DEFVAL          { parse }
    ::= { sonusFilterProfileEntry 34 }

sonusFilterProfProxyAuthorization OBJECT-TYPE
    SYNTAX          SonusFilterProfileState
    MAX-ACCESS      read-write
    STATUS          current
    DESCRIPTION     
            "Proxy Authorization Header will be filtered when enabled."
    DEFVAL          { parse }
    ::= { sonusFilterProfileEntry 35 }

sonusFilterProfProxyReq OBJECT-TYPE
    SYNTAX          SonusFilterProfileState
    MAX-ACCESS      read-write
    STATUS          current
    DESCRIPTION     
            "Proxy Req Header will be filtered when enabled."
    DEFVAL          { parse }
    ::= { sonusFilterProfileEntry 36 }

sonusFilterProfReason OBJECT-TYPE
    SYNTAX          SonusFilterProfileState
    MAX-ACCESS      read-write
    STATUS          current
    DESCRIPTION     
            "Reason Header will be filtered when enabled."
    DEFVAL          { parse }
    ::= { sonusFilterProfileEntry 37 }

sonusFilterProfRemoteParty OBJECT-TYPE
    SYNTAX          SonusFilterProfileState
    MAX-ACCESS      read-write
    STATUS          current
    DESCRIPTION     
            "Remote Party Header will be filtered when enabled."
    DEFVAL          { parse }
    ::= { sonusFilterProfileEntry 38 }

sonusFilterProfReplaces OBJECT-TYPE
    SYNTAX          SonusFilterProfileState
    MAX-ACCESS      read-write
    STATUS          current
    DESCRIPTION     
            "Replaces Header will be filtered when enabled."
    DEFVAL          { parse }
    ::= { sonusFilterProfileEntry 39 }

sonusFilterProfReplyTo OBJECT-TYPE
    SYNTAX          SonusFilterProfileState
    MAX-ACCESS      read-write
    STATUS          current
    DESCRIPTION     
            "Reply To Header will be filtered when enabled."
    DEFVAL          { parse }
    ::= { sonusFilterProfileEntry 40 }

sonusFilterProfRequestBy OBJECT-TYPE
    SYNTAX          SonusFilterProfileState
    MAX-ACCESS      read-write
    STATUS          current
    DESCRIPTION     
            "Request By Header will be filtered when enabled."
    DEFVAL          { parse }
    ::= { sonusFilterProfileEntry 41 }

sonusFilterProfRequired OBJECT-TYPE
    SYNTAX          SonusFilterProfileState
    MAX-ACCESS      read-write
    STATUS          current
    DESCRIPTION     
            "Required Header will be filtered when enabled."
    DEFVAL          { parse }
    ::= { sonusFilterProfileEntry 42 }

sonusFilterProfResourcePriority OBJECT-TYPE
    SYNTAX          SonusFilterProfileState
    MAX-ACCESS      read-write
    STATUS          current
    DESCRIPTION     
            "Resource Priority Header will be filtered when enabled."
    DEFVAL          { parse }
    ::= { sonusFilterProfileEntry 43 }

sonusFilterProfRetryAfter OBJECT-TYPE
    SYNTAX          SonusFilterProfileState
    MAX-ACCESS      read-write
    STATUS          current
    DESCRIPTION     
            "Retry After Header will be filtered when enabled."
    DEFVAL          { parse }
    ::= { sonusFilterProfileEntry 44 }

sonusFilterProfRoute OBJECT-TYPE
    SYNTAX          SonusFilterProfileState
    MAX-ACCESS      read-write
    STATUS          current
    DESCRIPTION     
            "Route Header will be filtered when enabled."
    DEFVAL          { parse }
    ::= { sonusFilterProfileEntry 45 }

sonusFilterProfServiceRoute OBJECT-TYPE
    SYNTAX          SonusFilterProfileState
    MAX-ACCESS      read-write
    STATUS          current
    DESCRIPTION     
            "Service Route Header will be filtered when enabled."
    DEFVAL          { parse }
    ::= { sonusFilterProfileEntry 46 }

sonusFilterProfSessExpires OBJECT-TYPE
    SYNTAX          SonusFilterProfileState
    MAX-ACCESS      read-write
    STATUS          current
    DESCRIPTION     
            "Sess Expires Header will be filtered when enabled."
    DEFVAL          { parse }
    ::= { sonusFilterProfileEntry 47 }

sonusFilterProfSubscriptionState OBJECT-TYPE
    SYNTAX          SonusFilterProfileState
    MAX-ACCESS      read-write
    STATUS          current
    DESCRIPTION     
            "Subscription State Header will be filtered when enabled."
    DEFVAL          { parse }
    ::= { sonusFilterProfileEntry 48 }

sonusFilterProfSupported OBJECT-TYPE
    SYNTAX          SonusFilterProfileState
    MAX-ACCESS      read-write
    STATUS          current
    DESCRIPTION     
            "Supported Header will be filtered when enabled."
    DEFVAL          { parse }
    ::= { sonusFilterProfileEntry 49 }

sonusFilterProfTimeStamp OBJECT-TYPE
    SYNTAX          SonusFilterProfileStateWithUnknown
    MAX-ACCESS      read-write
    STATUS          current
    DESCRIPTION     
            "Time Stamp Header will be filtered when enabled."
    DEFVAL          { parse }
    ::= { sonusFilterProfileEntry 50 }

sonusFilterProfUnknown OBJECT-TYPE
    SYNTAX          SonusFilterProfileState
    MAX-ACCESS      read-write
    STATUS          current
    DESCRIPTION     
            "Unknown Headers will be filtered when enabled."
    DEFVAL          { parse }
    ::= { sonusFilterProfileEntry 51 }

sonusFilterProfUnsupported OBJECT-TYPE
    SYNTAX          SonusFilterProfileState
    MAX-ACCESS      read-write
    STATUS          current
    DESCRIPTION     
            "Unsupported Header will be filtered when enabled."
    DEFVAL          { parse }
    ::= { sonusFilterProfileEntry 52 }

sonusFilterProfWWWAuthenticate OBJECT-TYPE
    SYNTAX          SonusFilterProfileState
    MAX-ACCESS      read-write
    STATUS          current
    DESCRIPTION     
            "WWWAuthenticate Header will be filtered when enabled."
    DEFVAL          { parse }
    ::= { sonusFilterProfileEntry 53 }

sonusFilterProfAcceptContact OBJECT-TYPE
    SYNTAX          SonusFilterProfileStateWithUnknown
    MAX-ACCESS      read-write
    STATUS          current
    DESCRIPTION     
            "Accept-Contact Header will be filtered when enabled."
    DEFVAL          { parse }
    ::= { sonusFilterProfileEntry 54 }

sonusFilterProfHistoryInfo OBJECT-TYPE
    SYNTAX          SonusFilterProfileStateWithUnknown
    MAX-ACCESS      read-write
    STATUS          current
    DESCRIPTION     
            "History-Info Header will be filtered when enabled."
    DEFVAL          { parse }
    ::= { sonusFilterProfileEntry 55 }

sonusFilterProfPChgMsgInfo OBJECT-TYPE
    SYNTAX          SonusFilterProfileStateWithUnknown
    MAX-ACCESS      read-write
    STATUS          current
    DESCRIPTION     
            "P_ChgMsg_Info Header will be filtered when enabled."
    DEFVAL          { parse }
    ::= { sonusFilterProfileEntry 56 }

sonusFilterProfPOrigCa OBJECT-TYPE
    SYNTAX          SonusFilterProfileStateWithUnknown
    MAX-ACCESS      read-write
    STATUS          current
    DESCRIPTION     
            "P_Orig_Ca Header will be filtered when enabled."
    DEFVAL          { parse }
    ::= { sonusFilterProfileEntry 57 }

sonusFilterProfTargetDialog OBJECT-TYPE
    SYNTAX          SonusFilterProfileStateWithUnknown
    MAX-ACCESS      read-write
    STATUS          current
    DESCRIPTION     
            "Target-Dialog Header will be filtered when enabled."
    DEFVAL          { parse }
    ::= { sonusFilterProfileEntry 58 }

sonusFilterProfUserAgent OBJECT-TYPE
    SYNTAX          SonusFilterProfileStateWithUnknown
    MAX-ACCESS      read-write
    STATUS          current
    DESCRIPTION     
            "UserKey Header will be filtered when enabled."
    DEFVAL          { parse }
    ::= { sonusFilterProfileEntry 59 }

sonusFilterProfServer OBJECT-TYPE
    SYNTAX          SonusFilterProfileStateWithUnknown
    MAX-ACCESS      read-write
    STATUS          current
    DESCRIPTION     
            "Server Header will be filtered when enabled."
    DEFVAL          { parse }
    ::= { sonusFilterProfileEntry 60 }

sonusFilterProfWarning OBJECT-TYPE
    SYNTAX          SonusFilterProfileStateWithUnknown
    MAX-ACCESS      read-write
    STATUS          current
    DESCRIPTION     
            "Warning Header will be filtered when enabled."
    DEFVAL          { parse }
    ::= { sonusFilterProfileEntry 61 }

sonusFilterProfAcceptLanguage OBJECT-TYPE
    SYNTAX          SonusFilterProfileStateWithUnknown
    MAX-ACCESS      read-write
    STATUS          current
    DESCRIPTION     
            "AcceptLanguage Header will be filtered when enabled."
    DEFVAL          { parse }
    ::= { sonusFilterProfileEntry 62 }

sonusFilterProfCallInfo OBJECT-TYPE
    SYNTAX          SonusFilterProfileStateWithUnknown
    MAX-ACCESS      read-write
    STATUS          current
    DESCRIPTION     
            "CallInfo Header will be filtered when enabled."
    DEFVAL          { parse }
    ::= { sonusFilterProfileEntry 63 }

sonusFilterProfSipEtag OBJECT-TYPE
    SYNTAX          SonusFilterProfileStateWithUnknown
    MAX-ACCESS      read-write
    STATUS          current
    DESCRIPTION     
            "SipEtag Header will be filtered when enabled."
    DEFVAL          { parse }
    ::= { sonusFilterProfileEntry 64 }

sonusFilterProfSipIfMatch OBJECT-TYPE
    SYNTAX          SonusFilterProfileStateWithUnknown
    MAX-ACCESS      read-write
    STATUS          current
    DESCRIPTION     
            "Sip-If-Match Header will be filtered when enabled."
    DEFVAL          { parse }
    ::= { sonusFilterProfileEntry 65 }

sonusFilterProfSuppressIfMatch OBJECT-TYPE
    SYNTAX          SonusFilterProfileStateWithUnknown
    MAX-ACCESS      read-write
    STATUS          current
    DESCRIPTION     
            "SuppressIfMatch Header will be filtered when enabled."
    DEFVAL          { parse }
    ::= { sonusFilterProfileEntry 66 }

sonusFilterProfReferSub OBJECT-TYPE
    SYNTAX          SonusFilterProfileStateWithUnknown
    MAX-ACCESS      read-write
    STATUS          current
    DESCRIPTION     
            "ReferSub Header will be filtered when enabled."
    DEFVAL          { parse }
    ::= { sonusFilterProfileEntry 67 }

sonusFilterProfProxyAuthenticate OBJECT-TYPE
    SYNTAX          SonusFilterProfileStateWithUnknown
    MAX-ACCESS      read-write
    STATUS          current
    DESCRIPTION     
            "ReferSub Header will be filtered when enabled."
    DEFVAL          { parse }
    ::= { sonusFilterProfileEntry 68 }

sonusFilterProfPEarlyMedia OBJECT-TYPE
    SYNTAX          SonusFilterProfileStateWithUnknown
    MAX-ACCESS      read-write
    STATUS          current
    DESCRIPTION     
            "ReferSub Header will be filtered when enabled."
    DEFVAL          { parse }
    ::= { sonusFilterProfileEntry 69 }

sonusFilterProfPAssociatedUri OBJECT-TYPE
    SYNTAX          SonusFilterProfileStateWithUnknown
    MAX-ACCESS      read-write
    STATUS          current
    DESCRIPTION     
            "ReferSub Header will be filtered when enabled."
    DEFVAL          { parse }
    ::= { sonusFilterProfileEntry 70 }

sonusFilterProfXSrvcIndicator OBJECT-TYPE
    SYNTAX          SonusFilterProfileStateWithUnknown
    MAX-ACCESS      read-write
    STATUS          current
    DESCRIPTION     
            "ReferSub Header will be filtered when enabled."
    DEFVAL          { parse }
    ::= { sonusFilterProfileEntry 71 }

sonusFilterProfPDcsBillingInfo OBJECT-TYPE
    SYNTAX          SonusFilterProfileStateWithUnknown
    MAX-ACCESS      read-write
    STATUS          current
    DESCRIPTION     
            "PDcsBillingInfo Header will be filtered when enabled."
    DEFVAL          { parse }
    ::= { sonusFilterProfileEntry 72 }

sonusFilterProfRecordRoute OBJECT-TYPE
    SYNTAX          SonusFilterProfileState
    MAX-ACCESS      read-write
    STATUS          current
    DESCRIPTION     
            "Record Route Header will be filtered when enabled."
    DEFVAL          { parse }
    ::= { sonusFilterProfileEntry 73 }

sonusFilterProfReferTo OBJECT-TYPE
    SYNTAX          SonusFilterProfileState
    MAX-ACCESS      read-write
    STATUS          current
    DESCRIPTION     
            "Refer-To Header will be filtered when enabled."
    DEFVAL          { parse }
    ::= { sonusFilterProfileEntry 74 }

sonusFilterProfReferredBy OBJECT-TYPE
    SYNTAX          SonusFilterProfileState
    MAX-ACCESS      read-write
    STATUS          current
    DESCRIPTION     
            "Referred-By Header will be filtered when enabled."
    DEFVAL          { parse }
    ::= { sonusFilterProfileEntry 75 }

sonusSipSigPortConnectionStatusTable OBJECT-TYPE
    SYNTAX          SEQUENCE OF SonusSipSigPortConnectionStatusEntry
    MAX-ACCESS      not-accessible
    STATUS          current
    DESCRIPTION     
            "Table of SIP Signalling Port connection status data."
    ::= { sonusSipSignallingMIBObjects 28 }

sonusSipSigPortConnectionStatusEntry OBJECT-TYPE
    SYNTAX          SonusSipSigPortConnectionStatusEntry
    MAX-ACCESS      not-accessible
    STATUS          current
    DESCRIPTION     
            "SIP Signalling Port Connection Status information."
    INDEX           { sonusSipSigPortConnectionStatusSSPIndex, 
                      sonusSipSigPortConnectionStatusPeerIpAddress, 
                      sonusSipSigPortConnectionStatusPeerIp6Address, 
                      sonusSipSigPortConnectionStatusPeerIpVersion, 
                      sonusSipSigPortConnectionStatusConnId }
    ::= { sonusSipSigPortConnectionStatusTable 1 }

SonusSipSigPortConnectionStatusEntry ::=
    SEQUENCE {
        sonusSipSigPortConnectionStatusSSPIndex       Unsigned32,
        sonusSipSigPortConnectionStatusPeerIpAddress            IpAddress,
        sonusSipSigPortConnectionStatusConnId     Unsigned32,
        sonusSipSigPortConnectionStatusPeerPortNum          Integer32,
        sonusSipSigPortConnectionStatusSocket     Integer32,
        sonusSipSigPortConnectionStatusTransport        INTEGER,
        sonusSipSigPortConnectionStatusState    INTEGER,
        sonusSipSigPortConnectionStatusRole   INTEGER,
        sonusSipSigPortConnectionStatusAging    INTEGER,
        sonusSipSigPortConnectionStatusIdleTime       Unsigned32,
        sonusSipSigPortConnectionStatusBytesSent        Counter32,
        sonusSipSigPortConnectionStatusBytesRcvd        Counter32,
        sonusSipSigPortConnectionStatusPduSendQueued            Counter32,
        sonusSipSigPortConnectionStatusPduRecvQueued            Counter32,
        sonusSipSigPortConnectionStatusRowStatus        RowStatus,
        sonusSipSigPortConnectionStatusPeerIp6Address             Ipv6Address,
        sonusSipSigPortConnectionStatusPeerIpVersion            INTEGER
    }

sonusSipSigPortConnectionStatusSSPIndex OBJECT-TYPE
    SYNTAX          Unsigned32
    MAX-ACCESS      read-only
    STATUS          current
    DESCRIPTION     
            "Identifies the SIP Signaling Port entry."
    ::= { sonusSipSigPortConnectionStatusEntry 1 }

sonusSipSigPortConnectionStatusPeerIpAddress OBJECT-TYPE
    SYNTAX          IpAddress
    MAX-ACCESS      read-only
    STATUS          current
    DESCRIPTION     
            "IP address of the peer of this connection"
    ::= { sonusSipSigPortConnectionStatusEntry 2 }

sonusSipSigPortConnectionStatusConnId OBJECT-TYPE
    SYNTAX          Unsigned32
    MAX-ACCESS      read-only
    STATUS          current
    DESCRIPTION     
            "Identifier used internally for the connection"
    ::= { sonusSipSigPortConnectionStatusEntry 3 }

sonusSipSigPortConnectionStatusPeerPortNum OBJECT-TYPE
    SYNTAX          Integer32
    MAX-ACCESS      read-only
    STATUS          current
    DESCRIPTION     
            "port number used by the peer of this connection"
    ::= { sonusSipSigPortConnectionStatusEntry 4 }

sonusSipSigPortConnectionStatusSocket OBJECT-TYPE
    SYNTAX          Integer32
    MAX-ACCESS      read-only
    STATUS          current
    DESCRIPTION     
            "socket number used internally for the connection"
    ::= { sonusSipSigPortConnectionStatusEntry 5 }

sonusSipSigPortConnectionStatusTransport OBJECT-TYPE
    SYNTAX          INTEGER { udp(1), tcp(2), tls-tcp(3), sctp(4) }
    MAX-ACCESS      read-only
    STATUS          current
    DESCRIPTION     
            "The transport type used for the connection"
    ::= { sonusSipSigPortConnectionStatusEntry 6 }

sonusSipSigPortConnectionStatusState OBJECT-TYPE
    SYNTAX          INTEGER { none(0), connecting(1), connected(2), 
                        blocked(3), deleted(4) }
    MAX-ACCESS      read-only
    STATUS          current
    DESCRIPTION     
            "state of this connection"
    ::= { sonusSipSigPortConnectionStatusEntry 7 }

sonusSipSigPortConnectionStatusRole OBJECT-TYPE
    SYNTAX          INTEGER { client(0), server(1) }
    MAX-ACCESS      read-only
    STATUS          current
    DESCRIPTION     
            "The role taken by the GSX in this connection"
    ::= { sonusSipSigPortConnectionStatusEntry 8 }

sonusSipSigPortConnectionStatusAging OBJECT-TYPE
    SYNTAX          INTEGER { no(0), yes(1) }
    MAX-ACCESS      read-only
    STATUS          current
    DESCRIPTION     
            "Whether or not an idle connection can be taken down"
    ::= { sonusSipSigPortConnectionStatusEntry 9 }

sonusSipSigPortConnectionStatusIdleTime OBJECT-TYPE
    SYNTAX          Unsigned32
    MAX-ACCESS      read-only
    STATUS          current
    DESCRIPTION     
            "Time internal since the last activity"
    ::= { sonusSipSigPortConnectionStatusEntry 10 }

sonusSipSigPortConnectionStatusBytesSent OBJECT-TYPE
    SYNTAX          Counter32
    MAX-ACCESS      read-only
    STATUS          current
    DESCRIPTION     
            "Number of payload bytes sent on the connection"
    ::= { sonusSipSigPortConnectionStatusEntry 11 }

sonusSipSigPortConnectionStatusBytesRcvd OBJECT-TYPE
    SYNTAX          Counter32
    MAX-ACCESS      read-only
    STATUS          current
    DESCRIPTION     
            "Number of payload bytes received on the connection"
    ::= { sonusSipSigPortConnectionStatusEntry 12 }

sonusSipSigPortConnectionStatusPduSendQueued OBJECT-TYPE
    SYNTAX          Counter32
    MAX-ACCESS      read-only
    STATUS          current
    DESCRIPTION     
            "Number of PDUs waiting to be sent on the connection"
    ::= { sonusSipSigPortConnectionStatusEntry 13 }

sonusSipSigPortConnectionStatusPduRecvQueued OBJECT-TYPE
    SYNTAX          Counter32
    MAX-ACCESS      read-only
    STATUS          current
    DESCRIPTION     
            "Number of fragmented PDUs received on the connection"
    ::= { sonusSipSigPortConnectionStatusEntry 14 }

sonusSipSigPortConnectionStatusRowStatus OBJECT-TYPE
    SYNTAX          RowStatus
    MAX-ACCESS      read-write
    STATUS          current
    DESCRIPTION     
            "This is for SNMP use."
    ::= { sonusSipSigPortConnectionStatusEntry 15 }

sonusSipSigPortConnectionStatusPeerIp6Address OBJECT-TYPE
    SYNTAX          Ipv6Address
    MAX-ACCESS      read-only
    STATUS          current
    DESCRIPTION     
            "IPv6 address of the peer of this connection"
    ::= { sonusSipSigPortConnectionStatusEntry 16 }

sonusSipSigPortConnectionStatusPeerIpVersion OBJECT-TYPE
    SYNTAX          INTEGER { afInet(2), afInet6(24) }
    MAX-ACCESS      read-only
    STATUS          current
    DESCRIPTION     
            "IP address version of the peer of this connection"
    ::= { sonusSipSigPortConnectionStatusEntry 17 }

sonusSipSigPortConnectionStatTable OBJECT-TYPE
    SYNTAX          SEQUENCE OF SonusSipSigPortConnectionStatEntry
    MAX-ACCESS      not-accessible
    STATUS          current
    DESCRIPTION     
            "Table of SIP Signalling Port Connection statistics data."
    ::= { sonusSipSignallingMIBObjects 29 }

sonusSipSigPortConnectionStatEntry OBJECT-TYPE
    SYNTAX          SonusSipSigPortConnectionStatEntry
    MAX-ACCESS      not-accessible
    STATUS          current
    DESCRIPTION     
            "SIP Signalling Port Connection Statistics."
    INDEX           { sonusSipSigPortConnectionStatIndex }
    ::= { sonusSipSigPortConnectionStatTable 1 }

SonusSipSigPortConnectionStatEntry ::=
    SEQUENCE {
        sonusSipSigPortConnectionStatIndex  Unsigned32,
        sonusSipSigPortConnectionStatActiveTcpConnection                Counter32,
        sonusSipSigPortConnectionStatTotalTcpConnection               Counter32,
        sonusSipSigPortConnectionStatActiveTlsTcpConnection                   Counter32,
        sonusSipSigPortConnectionStatTotalTlsTcpConnection                  Counter32,
        sonusSipSigPortConnectionStatCountReset       INTEGER
    }

sonusSipSigPortConnectionStatIndex OBJECT-TYPE
    SYNTAX          Unsigned32
    MAX-ACCESS      read-only
    STATUS          current
    DESCRIPTION     
            "Identifies the SIP Signaling Port entry."
    ::= { sonusSipSigPortConnectionStatEntry 1 }

sonusSipSigPortConnectionStatActiveTcpConnection OBJECT-TYPE
    SYNTAX          Counter32
    MAX-ACCESS      read-only
    STATUS          current
    DESCRIPTION     
            "Number of current TCP connections"
    ::= { sonusSipSigPortConnectionStatEntry 2 }

sonusSipSigPortConnectionStatTotalTcpConnection OBJECT-TYPE
    SYNTAX          Counter32
    MAX-ACCESS      read-only
    STATUS          current
    DESCRIPTION     
            "Number of total TCP connections made"
    ::= { sonusSipSigPortConnectionStatEntry 3 }

sonusSipSigPortConnectionStatActiveTlsTcpConnection OBJECT-TYPE
    SYNTAX          Counter32
    MAX-ACCESS      read-only
    STATUS          current
    DESCRIPTION     
            "Number of current TLS-TCP connections made"
    ::= { sonusSipSigPortConnectionStatEntry 4 }

sonusSipSigPortConnectionStatTotalTlsTcpConnection OBJECT-TYPE
    SYNTAX          Counter32
    MAX-ACCESS      read-only
    STATUS          current
    DESCRIPTION     
            "Number of total TLS-TCP connections"
    ::= { sonusSipSigPortConnectionStatEntry 5 }

sonusSipSigPortConnectionStatCountReset OBJECT-TYPE
    SYNTAX          INTEGER { unknown(1), reset(2) }
    MAX-ACCESS      read-write
    STATUS          current
    DESCRIPTION     
            "set opertion on this object resets all the Connection statistics counts to zero"
    ::= { sonusSipSigPortConnectionStatEntry 6 }

sonusTransmitProfile OBJECT IDENTIFIER
    ::= { sonusSipSignallingMIBObjects 30 }

sonusTransmitProfileNextIndex OBJECT-TYPE
    SYNTAX          Unsigned32
    MAX-ACCESS      not-accessible
    STATUS          current
    DESCRIPTION     
            "The next valid index to use when creating a new sonusTransmitProfileEntry"
    ::= { sonusTransmitProfile 1 }

sonusTransmitProfileTable OBJECT-TYPE
    SYNTAX          SEQUENCE OF SonusTransmitProfileEntry
    MAX-ACCESS      not-accessible
    STATUS          current
    DESCRIPTION     
            "This table contains information about each Transmit
             Profile configured on the node."
    ::= { sonusTransmitProfile 2 }

sonusTransmitProfileEntry OBJECT-TYPE
    SYNTAX          SonusTransmitProfileEntry
    MAX-ACCESS      not-accessible
    STATUS          current
    DESCRIPTION     
            "This table describes the Transmit Profile."
    INDEX           { sonusTransmitProfIndex }
    ::= { sonusTransmitProfileTable 1 }

SonusTransmitProfileEntry ::=
    SEQUENCE {
        sonusTransmitProfIndex          Unsigned32,
        sonusTransmitProfName           SonusName,
        sonusTransmitProfRowStatus      RowStatus,
        sonusTransmitProfAccepted       SonusAdminState,
        sonusTransmitProfAcceptResourcePriority       SonusAdminState,
        sonusTransmitProfAlertInfo      SonusAdminState,
        sonusTransmitProfAllowed        SonusAdminState,
        sonusTransmitProfAlso           SonusAdminState,
        sonusTransmitProfAnonymity      SonusAdminState,
        sonusTransmitProfAuthorization  SonusAdminState,
        sonusTransmitProfCallConnectId  SonusAdminState,
        sonusTransmitProfContentDisp    SonusAdminState,
        sonusTransmitProfDiversion      SonusAdminState,
        sonusTransmitProfError          SonusAdminState,
        sonusTransmitProfErrorInfo      SonusAdminState,
        sonusTransmitProfEvent          SonusAdminState,
        sonusTransmitProfExpire         SonusAdminState,
        sonusTransmitProfMaxForwards    SonusAdminState,
        sonusTransmitProfMinExpires     SonusAdminState,
        sonusTransmitProfMinSe          SonusAdminState,
        sonusTransmitProfPAssertedId    SonusAdminState,
        sonusTransmitProfPCarrierInfo   SonusAdminState,
        sonusTransmitProfPChargingVector SonusAdminState,
        sonusTransmitProfPKAdn          SonusAdminState,
        sonusTransmitProfPPreferredId   SonusAdminState,
        sonusTransmitProfPSigInfo       SonusAdminState,
        sonusTransmitProfPSvcInfo       SonusAdminState,
        sonusTransmitProfPTermCa        SonusAdminState,
        sonusTransmitProfPath           SonusAdminState,
        sonusTransmitProfPCdrInfo       SonusAdminState,
        sonusTransmitProfPChargeInfo    SonusAdminState,
        sonusTransmitProfPKCfl          SonusAdminState,
        sonusTransmitProfPKCfo          SonusAdminState,
        sonusTransmitProfPrivacy        SonusAdminState,
        sonusTransmitProfProxyAuthorization   SonusAdminState,
        sonusTransmitProfProxyReq       SonusAdminState,
        sonusTransmitProfReason         SonusAdminState,
        sonusTransmitProfRemoteParty    SonusAdminState,
        sonusTransmitProfReplaces       SonusAdminState,
        sonusTransmitProfReplyTo        SonusAdminState,
        sonusTransmitProfRequestBy      SonusAdminState,
        sonusTransmitProfRequired       SonusAdminState,
        sonusTransmitProfResourcePriority SonusAdminState,
        sonusTransmitProfRetryAfter     SonusAdminState,
        sonusTransmitProfRoute          SonusAdminState,
        sonusTransmitProfServiceRoute   SonusAdminState,
        sonusTransmitProfSessExpires    SonusAdminState,
        sonusTransmitProfSubscriptionState  SonusAdminState,
        sonusTransmitProfSupported      SonusAdminState,
        sonusTransmitProfTimeStamp      SonusAdminState,
        sonusTransmitProfUnknown        SonusAdminState,
        sonusTransmitProfUnsupported    SonusAdminState,
        sonusTransmitProfWWWAuthenticate SonusAdminState,
        sonusTransmitProfAcceptContact  SonusAdminState
    }

sonusTransmitProfIndex OBJECT-TYPE
    SYNTAX          Unsigned32
    MAX-ACCESS      not-accessible
    STATUS          current
    DESCRIPTION     
            "The index of the Transmit table entry."
    ::= { sonusTransmitProfileEntry 1 }

sonusTransmitProfName OBJECT-TYPE
    SYNTAX          SonusName
    MAX-ACCESS      read-write
    STATUS          current
    DESCRIPTION     
            "The name of this Transmit Profile."
    ::= { sonusTransmitProfileEntry 2 }

sonusTransmitProfRowStatus OBJECT-TYPE
    SYNTAX          RowStatus
    MAX-ACCESS      read-write
    STATUS          current
    DESCRIPTION     
            ""
    ::= { sonusTransmitProfileEntry 3 }

sonusTransmitProfAccepted OBJECT-TYPE
    SYNTAX          SonusAdminState
    MAX-ACCESS      read-write
    STATUS          current
    DESCRIPTION     
            "Accept Header will be transmited when enabled."
    DEFVAL          { disabled }
    ::= { sonusTransmitProfileEntry 4 }

sonusTransmitProfAcceptResourcePriority OBJECT-TYPE
    SYNTAX          SonusAdminState
    MAX-ACCESS      read-write
    STATUS          current
    DESCRIPTION     
            "Accept Resource Priority Header will be transmited when enabled."
    DEFVAL          { disabled }
    ::= { sonusTransmitProfileEntry 5 }

sonusTransmitProfAlertInfo OBJECT-TYPE
    SYNTAX          SonusAdminState
    MAX-ACCESS      read-write
    STATUS          current
    DESCRIPTION     
            "Alert Info Header will be transmited when enabled."
    DEFVAL          { disabled }
    ::= { sonusTransmitProfileEntry 6 }

sonusTransmitProfAllowed OBJECT-TYPE
    SYNTAX          SonusAdminState
    MAX-ACCESS      read-write
    STATUS          current
    DESCRIPTION     
            "Allowed Header will be transmited when enabled."
    DEFVAL          { disabled }
    ::= { sonusTransmitProfileEntry 7 }

sonusTransmitProfAlso OBJECT-TYPE
    SYNTAX          SonusAdminState
    MAX-ACCESS      read-write
    STATUS          current
    DESCRIPTION     
            "Also Header will be transmited when enabled."
    DEFVAL          { disabled }
    ::= { sonusTransmitProfileEntry 8 }

sonusTransmitProfAnonymity OBJECT-TYPE
    SYNTAX          SonusAdminState
    MAX-ACCESS      read-write
    STATUS          current
    DESCRIPTION     
            "Anonymity Header will be transmited when enabled."
    DEFVAL          { disabled }
    ::= { sonusTransmitProfileEntry 9 }

sonusTransmitProfAuthorization OBJECT-TYPE
    SYNTAX          SonusAdminState
    MAX-ACCESS      read-write
    STATUS          current
    DESCRIPTION     
            "Authorization Header will be transmited when enabled."
    DEFVAL          { disabled }
    ::= { sonusTransmitProfileEntry 10 }

sonusTransmitProfCallConnectId OBJECT-TYPE
    SYNTAX          SonusAdminState
    MAX-ACCESS      read-write
    STATUS          current
    DESCRIPTION     
            "Call Connect ID Header will be transmited when enabled."
    DEFVAL          { disabled }
    ::= { sonusTransmitProfileEntry 11 }

sonusTransmitProfContentDisp OBJECT-TYPE
    SYNTAX          SonusAdminState
    MAX-ACCESS      read-write
    STATUS          current
    DESCRIPTION     
            "Content Disposition Header will be transmited when enabled."
    DEFVAL          { disabled }
    ::= { sonusTransmitProfileEntry 12 }

sonusTransmitProfDiversion OBJECT-TYPE
    SYNTAX          SonusAdminState
    MAX-ACCESS      read-write
    STATUS          current
    DESCRIPTION     
            "Diversion Header will be transmited when enabled."
    DEFVAL          { disabled }
    ::= { sonusTransmitProfileEntry 13 }

sonusTransmitProfError OBJECT-TYPE
    SYNTAX          SonusAdminState
    MAX-ACCESS      read-write
    STATUS          current
    DESCRIPTION     
            "Error Header will be transmited when enabled."
    DEFVAL          { disabled }
    ::= { sonusTransmitProfileEntry 14 }

sonusTransmitProfErrorInfo OBJECT-TYPE
    SYNTAX          SonusAdminState
    MAX-ACCESS      read-write
    STATUS          current
    DESCRIPTION     
            "Error Info Header will be transmited when enabled."
    DEFVAL          { disabled }
    ::= { sonusTransmitProfileEntry 15 }

sonusTransmitProfEvent OBJECT-TYPE
    SYNTAX          SonusAdminState
    MAX-ACCESS      read-write
    STATUS          current
    DESCRIPTION     
            "Event Header will be transmited when enabled."
    DEFVAL          { disabled }
    ::= { sonusTransmitProfileEntry 16 }

sonusTransmitProfExpire OBJECT-TYPE
    SYNTAX          SonusAdminState
    MAX-ACCESS      read-write
    STATUS          current
    DESCRIPTION     
            "Expires Header will be transmited when enabled."
    DEFVAL          { disabled }
    ::= { sonusTransmitProfileEntry 17 }

sonusTransmitProfMaxForwards OBJECT-TYPE
    SYNTAX          SonusAdminState
    MAX-ACCESS      read-write
    STATUS          current
    DESCRIPTION     
            "Max Forwards Header will be transmited when enabled."
    DEFVAL          { disabled }
    ::= { sonusTransmitProfileEntry 18 }

sonusTransmitProfMinExpires OBJECT-TYPE
    SYNTAX          SonusAdminState
    MAX-ACCESS      read-write
    STATUS          current
    DESCRIPTION     
            "Min Expires Header will be transmited when enabled."
    DEFVAL          { disabled }
    ::= { sonusTransmitProfileEntry 19 }

sonusTransmitProfMinSe OBJECT-TYPE
    SYNTAX          SonusAdminState
    MAX-ACCESS      read-write
    STATUS          current
    DESCRIPTION     
            "Min SE Header will be transmited when enabled."
    DEFVAL          { disabled }
    ::= { sonusTransmitProfileEntry 20 }

sonusTransmitProfPAssertedId OBJECT-TYPE
    SYNTAX          SonusAdminState
    MAX-ACCESS      read-write
    STATUS          current
    DESCRIPTION     
            "P_Asserted_ID Header will be transmited when enabled."
    DEFVAL          { disabled }
    ::= { sonusTransmitProfileEntry 21 }

sonusTransmitProfPCarrierInfo OBJECT-TYPE
    SYNTAX          SonusAdminState
    MAX-ACCESS      read-write
    STATUS          current
    DESCRIPTION     
            "P_Carrier_Info Header will be transmited when enabled."
    DEFVAL          { disabled }
    ::= { sonusTransmitProfileEntry 22 }

sonusTransmitProfPChargingVector OBJECT-TYPE
    SYNTAX          SonusAdminState
    MAX-ACCESS      read-write
    STATUS          current
    DESCRIPTION     
            "P_Charging_Vector Header will be transmited when enabled."
    DEFVAL          { disabled }
    ::= { sonusTransmitProfileEntry 23 }

sonusTransmitProfPKAdn OBJECT-TYPE
    SYNTAX          SonusAdminState
    MAX-ACCESS      read-write
    STATUS          current
    DESCRIPTION     
            "P_K_ADN Header will be transmited when enabled."
    DEFVAL          { disabled }
    ::= { sonusTransmitProfileEntry 24 }

sonusTransmitProfPPreferredId OBJECT-TYPE
    SYNTAX          SonusAdminState
    MAX-ACCESS      read-write
    STATUS          current
    DESCRIPTION     
            "P_Preferred_ID Header will be transmited when enabled."
    DEFVAL          { disabled }
    ::= { sonusTransmitProfileEntry 25 }

sonusTransmitProfPSigInfo OBJECT-TYPE
    SYNTAX          SonusAdminState
    MAX-ACCESS      read-write
    STATUS          current
    DESCRIPTION     
            "P_Sig_Info Header will be transmited when enabled."
    DEFVAL          { disabled }
    ::= { sonusTransmitProfileEntry 26 }

sonusTransmitProfPSvcInfo OBJECT-TYPE
    SYNTAX          SonusAdminState
    MAX-ACCESS      read-write
    STATUS          current
    DESCRIPTION     
            "P_Svc_Info Header will be transmited when enabled."
    DEFVAL          { disabled }
    ::= { sonusTransmitProfileEntry 27 }

sonusTransmitProfPTermCa OBJECT-TYPE
    SYNTAX          SonusAdminState
    MAX-ACCESS      read-write
    STATUS          current
    DESCRIPTION     
            "P_Term_CA Header will be transmited when enabled."
    DEFVAL          { disabled }
    ::= { sonusTransmitProfileEntry 28 }

sonusTransmitProfPath OBJECT-TYPE
    SYNTAX          SonusAdminState
    MAX-ACCESS      read-write
    STATUS          current
    DESCRIPTION     
            "Path Header will be transmited when enabled."
    DEFVAL          { disabled }
    ::= { sonusTransmitProfileEntry 29 }

sonusTransmitProfPCdrInfo OBJECT-TYPE
    SYNTAX          SonusAdminState
    MAX-ACCESS      read-write
    STATUS          current
    DESCRIPTION     
            "PCdrInfo Header will be transmited when enabled."
    DEFVAL          { disabled }
    ::= { sonusTransmitProfileEntry 30 }

sonusTransmitProfPChargeInfo OBJECT-TYPE
    SYNTAX          SonusAdminState
    MAX-ACCESS      read-write
    STATUS          current
    DESCRIPTION     
            "PChargeInfo Header will be transmited when enabled."
    DEFVAL          { disabled }
    ::= { sonusTransmitProfileEntry 31 }

sonusTransmitProfPKCfl OBJECT-TYPE
    SYNTAX          SonusAdminState
    MAX-ACCESS      read-write
    STATUS          current
    DESCRIPTION     
            "PKCfl Header will be transmited when enabled."
    DEFVAL          { disabled }
    ::= { sonusTransmitProfileEntry 32 }

sonusTransmitProfPKCfo OBJECT-TYPE
    SYNTAX          SonusAdminState
    MAX-ACCESS      read-write
    STATUS          current
    DESCRIPTION     
            "PKCfo Header will be transmited when enabled."
    DEFVAL          { disabled }
    ::= { sonusTransmitProfileEntry 33 }

sonusTransmitProfPrivacy OBJECT-TYPE
    SYNTAX          SonusAdminState
    MAX-ACCESS      read-write
    STATUS          current
    DESCRIPTION     
            "Privacy Header will be transmited when enabled."
    DEFVAL          { disabled }
    ::= { sonusTransmitProfileEntry 34 }

sonusTransmitProfProxyAuthorization OBJECT-TYPE
    SYNTAX          SonusAdminState
    MAX-ACCESS      read-write
    STATUS          current
    DESCRIPTION     
            "Proxy Authorization Header will be transmited when enabled."
    DEFVAL          { disabled }
    ::= { sonusTransmitProfileEntry 35 }

sonusTransmitProfProxyReq OBJECT-TYPE
    SYNTAX          SonusAdminState
    MAX-ACCESS      read-write
    STATUS          current
    DESCRIPTION     
            "Proxy Req Header will be transmited when enabled."
    DEFVAL          { disabled }
    ::= { sonusTransmitProfileEntry 36 }

sonusTransmitProfReason OBJECT-TYPE
    SYNTAX          SonusAdminState
    MAX-ACCESS      read-write
    STATUS          current
    DESCRIPTION     
            "Reason Header will be transmited when enabled."
    DEFVAL          { disabled }
    ::= { sonusTransmitProfileEntry 37 }

sonusTransmitProfRemoteParty OBJECT-TYPE
    SYNTAX          SonusAdminState
    MAX-ACCESS      read-write
    STATUS          current
    DESCRIPTION     
            "Remote Party Header will be transmited when enabled."
    DEFVAL          { disabled }
    ::= { sonusTransmitProfileEntry 38 }

sonusTransmitProfReplaces OBJECT-TYPE
    SYNTAX          SonusAdminState
    MAX-ACCESS      read-write
    STATUS          current
    DESCRIPTION     
            "Replaces Header will be transmited when enabled."
    DEFVAL          { disabled }
    ::= { sonusTransmitProfileEntry 39 }

sonusTransmitProfReplyTo OBJECT-TYPE
    SYNTAX          SonusAdminState
    MAX-ACCESS      read-write
    STATUS          current
    DESCRIPTION     
            "Reply To Header will be transmited when enabled."
    DEFVAL          { disabled }
    ::= { sonusTransmitProfileEntry 40 }

sonusTransmitProfRequestBy OBJECT-TYPE
    SYNTAX          SonusAdminState
    MAX-ACCESS      read-write
    STATUS          current
    DESCRIPTION     
            "Request By Header will be transmited when enabled."
    DEFVAL          { disabled }
    ::= { sonusTransmitProfileEntry 41 }

sonusTransmitProfRequired OBJECT-TYPE
    SYNTAX          SonusAdminState
    MAX-ACCESS      read-write
    STATUS          current
    DESCRIPTION     
            "Required Header will be transmited when enabled."
    DEFVAL          { disabled }
    ::= { sonusTransmitProfileEntry 42 }

sonusTransmitProfResourcePriority OBJECT-TYPE
    SYNTAX          SonusAdminState
    MAX-ACCESS      read-write
    STATUS          current
    DESCRIPTION     
            "Resource Priority Header will be transmited when enabled."
    DEFVAL          { disabled }
    ::= { sonusTransmitProfileEntry 43 }

sonusTransmitProfRetryAfter OBJECT-TYPE
    SYNTAX          SonusAdminState
    MAX-ACCESS      read-write
    STATUS          current
    DESCRIPTION     
            "Retry After Header will be transmited when enabled."
    DEFVAL          { disabled }
    ::= { sonusTransmitProfileEntry 44 }

sonusTransmitProfRoute OBJECT-TYPE
    SYNTAX          SonusAdminState
    MAX-ACCESS      read-write
    STATUS          current
    DESCRIPTION     
            "Route Header will be transmited when enabled."
    DEFVAL          { disabled }
    ::= { sonusTransmitProfileEntry 45 }

sonusTransmitProfServiceRoute OBJECT-TYPE
    SYNTAX          SonusAdminState
    MAX-ACCESS      read-write
    STATUS          current
    DESCRIPTION     
            "Service Route Header will be transmited when enabled."
    DEFVAL          { disabled }
    ::= { sonusTransmitProfileEntry 46 }

sonusTransmitProfSessExpires OBJECT-TYPE
    SYNTAX          SonusAdminState
    MAX-ACCESS      read-write
    STATUS          current
    DESCRIPTION     
            "Sess Expires Header will be transmited when enabled."
    DEFVAL          { disabled }
    ::= { sonusTransmitProfileEntry 47 }

sonusTransmitProfSubscriptionState OBJECT-TYPE
    SYNTAX          SonusAdminState
    MAX-ACCESS      read-write
    STATUS          current
    DESCRIPTION     
            "Subscription State Header will be transmited when enabled."
    DEFVAL          { disabled }
    ::= { sonusTransmitProfileEntry 48 }

sonusTransmitProfSupported OBJECT-TYPE
    SYNTAX          SonusAdminState
    MAX-ACCESS      read-write
    STATUS          current
    DESCRIPTION     
            "Supported Header will be transmited when enabled."
    DEFVAL          { disabled }
    ::= { sonusTransmitProfileEntry 49 }

sonusTransmitProfTimeStamp OBJECT-TYPE
    SYNTAX          SonusAdminState
    MAX-ACCESS      read-write
    STATUS          current
    DESCRIPTION     
            "Time Stamp Header will be transmited when enabled."
    DEFVAL          { disabled }
    ::= { sonusTransmitProfileEntry 50 }

sonusTransmitProfUnknown OBJECT-TYPE
    SYNTAX          SonusAdminState
    MAX-ACCESS      read-write
    STATUS          current
    DESCRIPTION     
            "Unknown Headers will be transmited when enabled."
    DEFVAL          { disabled }
    ::= { sonusTransmitProfileEntry 51 }

sonusTransmitProfUnsupported OBJECT-TYPE
    SYNTAX          SonusAdminState
    MAX-ACCESS      read-write
    STATUS          current
    DESCRIPTION     
            "Unsupported Header will be transmited when enabled."
    DEFVAL          { disabled }
    ::= { sonusTransmitProfileEntry 52 }

sonusTransmitProfWWWAuthenticate OBJECT-TYPE
    SYNTAX          SonusAdminState
    MAX-ACCESS      read-write
    STATUS          current
    DESCRIPTION     
            "WWWAuthenticate Header will be transmited when enabled."
    DEFVAL          { disabled }
    ::= { sonusTransmitProfileEntry 53 }

sonusTransmitProfAcceptContact OBJECT-TYPE
    SYNTAX          SonusAdminState
    MAX-ACCESS      read-write
    STATUS          current
    DESCRIPTION     
            "Accept-Contact Header will be transmited when enabled."
    DEFVAL          { disabled }
    ::= { sonusTransmitProfileEntry 54 }

sonusSipRegistrationDeleteConfigObjects OBJECT IDENTIFIER
    ::= { sonusSipSignallingMIBObjects 31 }

sonusSipRegistrationDeleteShelfIndex OBJECT-TYPE
    SYNTAX          SonusShelfIndex
    MAX-ACCESS      read-write
    STATUS          current
    DESCRIPTION     
            "Identifies the target shelf for deletion of SIP registration."
    ::= { sonusSipRegistrationDeleteConfigObjects 1 }

sonusSipRegistrationDeleteSlotIndex OBJECT-TYPE
    SYNTAX          SonusSlotIndex
    MAX-ACCESS      read-write
    STATUS          current
    DESCRIPTION     
            "Identifies the target slot."
    ::= { sonusSipRegistrationDeleteConfigObjects 2 }

sonusSipRegistrationDeleteRegId OBJECT-TYPE
    SYNTAX          Integer32 (1..16777214)
    MAX-ACCESS      read-write
    STATUS          current
    DESCRIPTION     
            "The registration ID to be deleted."
    ::= { sonusSipRegistrationDeleteConfigObjects 3 }

sonusSipSubCountTable OBJECT-TYPE
    SYNTAX          SEQUENCE OF SonusSipSubCountEntry
    MAX-ACCESS      not-accessible
    STATUS          current
    DESCRIPTION     
            "This table presents SIP relayed subscription count statistics for the node."
    ::= { sonusSipSignallingMIBObjects 32 }

sonusSipSubCountEntry OBJECT-TYPE
    SYNTAX          SonusSipSubCountEntry
    MAX-ACCESS      not-accessible
    STATUS          current
    DESCRIPTION     
            ""
    INDEX           { sonusSipSubCountShelfIndex, 
                      sonusSipSubCountSlotIndex }
    ::= { sonusSipSubCountTable 1 }

SonusSipSubCountEntry ::=
    SEQUENCE {
        sonusSipSubCountShelfIndex      SonusShelfIndex,
        sonusSipSubCountSlotIndex       SonusSlotIndex,
        sonusSipSubCountReset           INTEGER,
        sonusSipSubCountAttempts        Counter32,
        sonusSipSubCountCumCompletions  Counter32,
        sonusSipSubCountStable          Counter32,
        sonusSipSubCountTotal           Counter32
    }

sonusSipSubCountShelfIndex OBJECT-TYPE
    SYNTAX          SonusShelfIndex
    MAX-ACCESS      read-only
    STATUS          current
    DESCRIPTION     
            "Identifies the target shelf to obtain the SIP subscription counters."
    ::= { sonusSipSubCountEntry 1 }

sonusSipSubCountSlotIndex OBJECT-TYPE
    SYNTAX          SonusSlotIndex
    MAX-ACCESS      read-only
    STATUS          current
    DESCRIPTION     
            "Identifies the target slot."
    ::= { sonusSipSubCountEntry 2 }

sonusSipSubCountReset OBJECT-TYPE
    SYNTAX          INTEGER { unknown(1), reset(2) }
    MAX-ACCESS      read-create
    STATUS          current
    DESCRIPTION     
            "Provides a means to reset a subset of the SIP subscription
             counters. Any set operation on this object will result in the
             		 attempt and cummulative completion counters being cleared."
    ::= { sonusSipSubCountEntry 3 }

sonusSipSubCountAttempts OBJECT-TYPE
    SYNTAX          Counter32
    MAX-ACCESS      read-only
    STATUS          current
    DESCRIPTION     
            "Indicates the number of SIP relayed subscription attempts on this card."
    ::= { sonusSipSubCountEntry 4 }

sonusSipSubCountCumCompletions OBJECT-TYPE
    SYNTAX          Counter32
    MAX-ACCESS      read-only
    STATUS          current
    DESCRIPTION     
            "Indicates the accumulative number of completed SIP subscription attempts on this card."
    ::= { sonusSipSubCountEntry 5 }

sonusSipSubCountStable OBJECT-TYPE
    SYNTAX          Counter32
    MAX-ACCESS      read-only
    STATUS          current
    DESCRIPTION     
            "Indicates the current number of stable SIP subscription on this card."
    ::= { sonusSipSubCountEntry 6 }

sonusSipSubCountTotal OBJECT-TYPE
    SYNTAX          Counter32
    MAX-ACCESS      read-only
    STATUS          current
    DESCRIPTION     
            "Indicates the total number of current SIP subscription on this card."
    ::= { sonusSipSubCountEntry 7 }

sonusSctpProfile OBJECT IDENTIFIER
    ::= { sonusSipSignallingMIBObjects 33 }

sonusSctpProfileNextIndex OBJECT-TYPE
    SYNTAX          Integer32
    MAX-ACCESS      read-only
    STATUS          current
    DESCRIPTION     
            "The next valid index to use when creating an entry in
             the sonusSctpProfileTable."
    ::= { sonusSctpProfile 1 }

sonusSctpProfileTable OBJECT-TYPE
    SYNTAX          SEQUENCE OF SonusSctpProfileEntry
    MAX-ACCESS      not-accessible
    STATUS          current
    DESCRIPTION     
            "Table of SIP Signalling Port Sctp Profile data."
    ::= { sonusSctpProfile 2 }

sonusSctpProfileEntry OBJECT-TYPE
    SYNTAX          SonusSctpProfileEntry
    MAX-ACCESS      not-accessible
    STATUS          current
    DESCRIPTION     
            "SIP Signalling Port SCTP configuration."
    INDEX           { sonusSctpProfileIndex }
    ::= { sonusSctpProfileTable 1 }

SonusSctpProfileEntry ::=
    SEQUENCE {
        sonusSctpProfileIndex           Unsigned32,
        sonusSctpProfileName            SonusName,
        sonusSctpProfileOutboundStreams Unsigned32,
        sonusSctpProfileInboundStreams  Unsigned32,
        sonusSctpProfilePeerTransportAddresses      Unsigned32,
        sonusSctpProfileRetransmissionsPerPath      Unsigned32,
        sonusSctpProfileHeartbeatInterval Unsigned32,
        sonusSctpProfileRowStatus       RowStatus,
        sonusSctpProfileOrderedDelivery SonusAdminState,
        sonusSctpProfileSackDelay       SonusAdminState,
        sonusSctpProfileRetransmissionsPerAssociation             Unsigned32,
        sonusSctpProfileRtoInitial      Unsigned32,
        sonusSctpProfileRtoMin          Unsigned32,
        sonusSctpProfileRtoMax          Unsigned32,
        sonusSctpProfileInitRetry       Unsigned32,
        sonusSctpProfilePathMtu         Unsigned32,
        sonusSctpProfileIdleTimeout     Unsigned32
    }

sonusSctpProfileIndex OBJECT-TYPE
    SYNTAX          Unsigned32
    MAX-ACCESS      read-only
    STATUS          current
    DESCRIPTION     
            "Identifies the SCTP profile entry."
    ::= { sonusSctpProfileEntry 1 }

sonusSctpProfileName OBJECT-TYPE
    SYNTAX          SonusName
    MAX-ACCESS      read-write
    STATUS          current
    DESCRIPTION     
            "The user name of the SCTP profile."
    ::= { sonusSctpProfileEntry 2 }

sonusSctpProfileOutboundStreams OBJECT-TYPE
    SYNTAX          Unsigned32 (1..32)
    MAX-ACCESS      read-write
    STATUS          current
    DESCRIPTION     
            "The number of Outbound Streams for this SCTP profile."
    DEFVAL          { 1 }
    ::= { sonusSctpProfileEntry 3 }

sonusSctpProfileInboundStreams OBJECT-TYPE
    SYNTAX          Unsigned32 (1..32)
    MAX-ACCESS      read-write
    STATUS          current
    DESCRIPTION     
            "The number of Inbound Streams for this SCTP profile"
    DEFVAL          { 1 }
    ::= { sonusSctpProfileEntry 4 }

sonusSctpProfilePeerTransportAddresses OBJECT-TYPE
    SYNTAX          Unsigned32 (1..2)
    MAX-ACCESS      read-write
    STATUS          current
    DESCRIPTION     
            "The number of Peer Trabsport Addresses for this SCTP profile ."
    DEFVAL          { 2 }
    ::= { sonusSctpProfileEntry 5 }

sonusSctpProfileRetransmissionsPerPath OBJECT-TYPE
    SYNTAX          Unsigned32 (1..10)
    MAX-ACCESS      read-write
    STATUS          current
    DESCRIPTION     
            "The number of Retransmissions per path for this SCTP profile ."
    DEFVAL          { 8 }
    ::= { sonusSctpProfileEntry 6 }

sonusSctpProfileHeartbeatInterval OBJECT-TYPE
    SYNTAX          Unsigned32 (1..6)
    MAX-ACCESS      read-write
    STATUS          current
    DESCRIPTION     
            "The SCTP Heartbeat Interval in seconds. In future this can be made editable"
    DEFVAL          { 4 }
    ::= { sonusSctpProfileEntry 7 }

sonusSctpProfileRowStatus OBJECT-TYPE
    SYNTAX          RowStatus
    MAX-ACCESS      read-write
    STATUS          current
    DESCRIPTION     
            "The row status of this SCTP profile."
    ::= { sonusSctpProfileEntry 8 }

sonusSctpProfileOrderedDelivery OBJECT-TYPE
    SYNTAX          SonusAdminState
    MAX-ACCESS      read-write
    STATUS          current
    DESCRIPTION     
            "This indicates whether ordered delivery should be used in SCTP."
    DEFVAL          { disabled }
    ::= { sonusSctpProfileEntry 9 }

sonusSctpProfileSackDelay OBJECT-TYPE
    SYNTAX          SonusAdminState
    MAX-ACCESS      read-write
    STATUS          current
    DESCRIPTION     
            "This indicates whether SACK Delay should be enabled in SCTP."
    DEFVAL          { disabled }
    ::= { sonusSctpProfileEntry 10 }

sonusSctpProfileRetransmissionsPerAssociation OBJECT-TYPE
    SYNTAX          Unsigned32 (0..20)
    MAX-ACCESS      read-write
    STATUS          current
    DESCRIPTION     
            "The Maximum retransmissions per SCTP association"
    DEFVAL          { 0 }
    ::= { sonusSctpProfileEntry 11 }

sonusSctpProfileRtoInitial OBJECT-TYPE
    SYNTAX          Unsigned32 (50..1000)
    MAX-ACCESS      read-write
    STATUS          current
    DESCRIPTION     
            "The SCTP RTO Initial in milli seconds."
    DEFVAL          { 0 }
    ::= { sonusSctpProfileEntry 12 }

sonusSctpProfileRtoMin OBJECT-TYPE
    SYNTAX          Unsigned32 (10..5000)
    MAX-ACCESS      read-write
    STATUS          current
    DESCRIPTION     
            "The SCTP RTO Min in milli seconds."
    DEFVAL          { 0 }
    ::= { sonusSctpProfileEntry 13 }

sonusSctpProfileRtoMax OBJECT-TYPE
    SYNTAX          Unsigned32 (200..5000)
    MAX-ACCESS      read-write
    STATUS          current
    DESCRIPTION     
            "The SCTP RTO Max in milli seconds."
    DEFVAL          { 0 }
    ::= { sonusSctpProfileEntry 14 }

sonusSctpProfileInitRetry OBJECT-TYPE
    SYNTAX          Unsigned32 (1..10)
    MAX-ACCESS      read-write
    STATUS          current
    DESCRIPTION     
            "The SCTP Max INIT retry."
    DEFVAL          { 8 }
    ::= { sonusSctpProfileEntry 15 }

sonusSctpProfilePathMtu OBJECT-TYPE
    SYNTAX          Unsigned32 (1000..1500)
    MAX-ACCESS      read-write
    STATUS          current
    DESCRIPTION     
            "The SCTP Path MTU in bytes."
    DEFVAL          { 1500 }
    ::= { sonusSctpProfileEntry 16 }

sonusSctpProfileIdleTimeout OBJECT-TYPE
    SYNTAX          Unsigned32 (0..86400)
    MAX-ACCESS      read-write
    STATUS          current
    DESCRIPTION     
            "The SCTP Idle Timeout Interval in seconds."
    DEFVAL          { 3600 }
    ::= { sonusSctpProfileEntry 17 }

sonusSipActSubStatusTable OBJECT-TYPE
    SYNTAX          SEQUENCE OF SonusSipActSubStatusEntry
    MAX-ACCESS      not-accessible
    STATUS          current
    DESCRIPTION     
            "This table presents the active SIP subscription status for 
             a list of SIP endpoints."
    ::= { sonusSipSignallingMIBObjects 34 }

sonusSipActSubStatusEntry OBJECT-TYPE
    SYNTAX          SonusSipActSubStatusEntry
    MAX-ACCESS      not-accessible
    STATUS          current
    DESCRIPTION     
            "This entry presents the active SIP subscription status for
             a SIP endpoint."
    INDEX           { sonusSipActSubStatusShelfIndex, 
                      sonusSipActSubStatusSlotIndex, 
                      sonusSipActSubStatusSubId }
    ::= { sonusSipActSubStatusTable 1 }

SonusSipActSubStatusEntry ::=
    SEQUENCE {
        sonusSipActSubStatusShelfIndex  SonusShelfIndex,
        sonusSipActSubStatusSlotIndex   SonusSlotIndex,
        sonusSipActSubStatusSubId       Integer32,
        sonusSipActSubStatusCallId      DisplayString,
        sonusSipActSubStatusState       INTEGER,
        sonusSipActSubStatusNextHopIpAddress    IpAddress,
        sonusSipActSubStatusNextHopPortNum  Integer32,
        sonusSipActSubStatusPreviousHopIpAddress        IpAddress,
        sonusSipActSubStatusPreviousHopPortNum      Integer32,
        sonusSipActSubStatusSubExpirationTime     Integer32,
        sonusSipActSubStatusSubServerDomainName       DisplayString,
        sonusSipActSubStatusOrigEPDomain DisplayString,
        sonusSipActSubStatusNextHopIp6Address     Ipv6Address,
        sonusSipActSubStatusPreviousHopIp6Address         Ipv6Address,
        sonusSipActSubStatusIpVersion   INTEGER,
        sonusSipActSubStatusPreviousHopIpVersion        INTEGER
    }

sonusSipActSubStatusShelfIndex OBJECT-TYPE
    SYNTAX          SonusShelfIndex
    MAX-ACCESS      read-only
    STATUS          current
    DESCRIPTION     
            "Identifies the target shelf."
    ::= { sonusSipActSubStatusEntry 1 }

sonusSipActSubStatusSlotIndex OBJECT-TYPE
    SYNTAX          SonusSlotIndex
    MAX-ACCESS      read-only
    STATUS          current
    DESCRIPTION     
            "Identifies the target slot."
    ::= { sonusSipActSubStatusEntry 2 }

sonusSipActSubStatusSubId OBJECT-TYPE
    SYNTAX          Integer32 (1..16777214)
    MAX-ACCESS      read-only
    STATUS          current
    DESCRIPTION     
            "The Subscription ID created for the relayed Subscription session."
    ::= { sonusSipActSubStatusEntry 3 }

sonusSipActSubStatusCallId OBJECT-TYPE
    SYNTAX          DisplayString (SIZE(0..63))
    MAX-ACCESS      read-only
    STATUS          current
    DESCRIPTION     
            "CallID that uniquely identified the relayed subscription "
    ::= { sonusSipActSubStatusEntry 4 }

sonusSipActSubStatusState OBJECT-TYPE
    SYNTAX          INTEGER { null(0), initiating(1), active(2), 
                        expired(3), terminated(4) }
    MAX-ACCESS      read-only
    STATUS          current
    DESCRIPTION     
            "The subscription state of the endpoint."
    ::= { sonusSipActSubStatusEntry 5 }

sonusSipActSubStatusNextHopIpAddress OBJECT-TYPE
    SYNTAX          IpAddress
    MAX-ACCESS      read-only
    STATUS          current
    DESCRIPTION     
            "Next hop TSAP IP address."
    ::= { sonusSipActSubStatusEntry 6 }

sonusSipActSubStatusNextHopPortNum OBJECT-TYPE
    SYNTAX          Integer32 (1..65535)
    MAX-ACCESS      read-only
    STATUS          current
    DESCRIPTION     
            "Next hop TSAP UDP port number."
    ::= { sonusSipActSubStatusEntry 7 }

sonusSipActSubStatusPreviousHopIpAddress OBJECT-TYPE
    SYNTAX          IpAddress
    MAX-ACCESS      read-only
    STATUS          current
    DESCRIPTION     
            "Originating Endpoint's IP Address."
    ::= { sonusSipActSubStatusEntry 8 }

sonusSipActSubStatusPreviousHopPortNum OBJECT-TYPE
    SYNTAX          Integer32 (1..65535)
    MAX-ACCESS      read-only
    STATUS          current
    DESCRIPTION     
            "Originating Endpoint's UDP port number."
    ::= { sonusSipActSubStatusEntry 9 }

sonusSipActSubStatusSubExpirationTime OBJECT-TYPE
    SYNTAX          Integer32
    MAX-ACCESS      read-only
    STATUS          current
    DESCRIPTION     
            "The  expiration timer value in seconds."
    ::= { sonusSipActSubStatusEntry 10 }

sonusSipActSubStatusSubServerDomainName OBJECT-TYPE
    SYNTAX          DisplayString (SIZE(0..127))
    MAX-ACCESS      read-only
    STATUS          current
    DESCRIPTION     
            "The SIP subscription server's domain name."
    ::= { sonusSipActSubStatusEntry 11 }

sonusSipActSubStatusOrigEPDomain OBJECT-TYPE
    SYNTAX          DisplayString (SIZE(0..127))
    MAX-ACCESS      read-only
    STATUS          current
    DESCRIPTION     
            "Originating EPs Contact host"
    ::= { sonusSipActSubStatusEntry 12 }

sonusSipActSubStatusNextHopIp6Address OBJECT-TYPE
    SYNTAX          Ipv6Address
    MAX-ACCESS      read-only
    STATUS          current
    DESCRIPTION     
            "Next hop TSAP IPv6 address."
    ::= { sonusSipActSubStatusEntry 13 }

sonusSipActSubStatusPreviousHopIp6Address OBJECT-TYPE
    SYNTAX          Ipv6Address
    MAX-ACCESS      read-only
    STATUS          current
    DESCRIPTION     
            "Originating Endpoint's IPv6 Address."
    ::= { sonusSipActSubStatusEntry 14 }

sonusSipActSubStatusIpVersion OBJECT-TYPE
    SYNTAX          INTEGER { afInet(2), afInet6(24) }
    MAX-ACCESS      read-only
    STATUS          current
    DESCRIPTION     
            "The IP address type  of the Sip Subscription."
    ::= { sonusSipActSubStatusEntry 15 }

sonusSipActSubStatusPreviousHopIpVersion OBJECT-TYPE
    SYNTAX          INTEGER { afInet(2), afInet6(24) }
    MAX-ACCESS      read-only
    STATUS          current
    DESCRIPTION     
            "The IP address type  of the Sip Subscription."
    ::= { sonusSipActSubStatusEntry 16 }

sonusSipSubscriptionDeleteConfigObjects OBJECT IDENTIFIER
    ::= { sonusSipSignallingMIBObjects 35 }

sonusSipSubscriptionDeleteShelfIndex OBJECT-TYPE
    SYNTAX          SonusShelfIndex
    MAX-ACCESS      read-write
    STATUS          current
    DESCRIPTION     
            "Identifies the target shelf for deletion of SIP subscription."
    ::= { sonusSipSubscriptionDeleteConfigObjects 1 }

sonusSipSubscriptionDeleteSlotIndex OBJECT-TYPE
    SYNTAX          SonusSlotIndex
    MAX-ACCESS      read-write
    STATUS          current
    DESCRIPTION     
            "Identifies the target slot."
    ::= { sonusSipSubscriptionDeleteConfigObjects 2 }

sonusSipSubscriptionDeleteSubId OBJECT-TYPE
    SYNTAX          Integer32 (1..16777214)
    MAX-ACCESS      read-write
    STATUS          current
    DESCRIPTION     
            "The subscription ID to be deleted."
    ::= { sonusSipSubscriptionDeleteConfigObjects 3 }

sonusSipRegActGroupRegStatusTable OBJECT-TYPE
    SYNTAX          SEQUENCE OF SonusSipRegActGroupRegStatusEntry
    MAX-ACCESS      not-accessible
    STATUS          current
    DESCRIPTION     
            "This table presents the active SIP registration status for 
             a list of SIP endpoints."
    ::= { sonusSipSignallingMIBObjects 36 }

sonusSipRegActGroupRegStatusEntry OBJECT-TYPE
    SYNTAX          SonusSipRegActGroupRegStatusEntry
    MAX-ACCESS      not-accessible
    STATUS          current
    DESCRIPTION     
            "This entry presents the active SIP registration status for
             a SIP endpoint."
    INDEX           { sonusSipRegActGroupRegStatusSlotIndex, 
                      sonusSipRegActGroupRegStatusRegId, 
                      sonusSipRegActGroupRegStatusNextRegId }
    ::= { sonusSipRegActGroupRegStatusTable 1 }

SonusSipRegActGroupRegStatusEntry ::=
    SEQUENCE {
        sonusSipRegActGroupRegStatusSlotIndex     SonusSlotIndex,
        sonusSipRegActGroupRegStatusRegId Integer32,
        sonusSipRegActGroupRegStatusNextRegId     Integer32,
        sonusSipRegActGroupRegStatusAorName   DisplayString,
        sonusSipRegActGroupRegStatusState INTEGER,
        sonusSipRegActGroupRegStatusContactURI      DisplayString,
        sonusSipRegActGroupRegStatusNextHopIpAddress            IpAddress,
        sonusSipRegActGroupRegStatusNextHopPortNum          Integer32,
        sonusSipRegActGroupRegStatusRegistrarIpAddress              IpAddress,
        sonusSipRegActGroupRegStatusRegistrarPortNum            Integer32,
        sonusSipRegActGroupRegStatusExtExpirationTime             Integer32,
        sonusSipRegActGroupRegStatusIntExpirationTime             Integer32,
        sonusSipRegActGroupRegStatusCreationTime        DateAndTime,
        sonusSipRegActGroupRegStatusRegistrarDomainName               DisplayString,
        sonusSipRegActGroupRegStatusNextRegIdIsChild            Integer32,
        sonusSipRegActGroupRegStatusNextHopIp6Address             Ipv6Address,
        sonusSipRegActGroupRegStatusRegistrarIp6Address               Ipv6Address,
        sonusSipRegActGroupRegStatusNextHopIpVersion            INTEGER,
        sonusSipRegActGroupRegStatusRegistrarIpVersion              INTEGER,
        sonusSipRegActGroupRegStatusParentAorName         DisplayString
    }

sonusSipRegActGroupRegStatusSlotIndex OBJECT-TYPE
    SYNTAX          SonusSlotIndex
    MAX-ACCESS      read-only
    STATUS          current
    DESCRIPTION     
            "Identifies the target slot."
    ::= { sonusSipRegActGroupRegStatusEntry 1 }

sonusSipRegActGroupRegStatusRegId OBJECT-TYPE
    SYNTAX          Integer32 (1..1000000)
    MAX-ACCESS      read-only
    STATUS          current
    DESCRIPTION     
            "The registration ID created for the registration session."
    ::= { sonusSipRegActGroupRegStatusEntry 2 }

sonusSipRegActGroupRegStatusNextRegId OBJECT-TYPE
    SYNTAX          Integer32 (1..1000000)
    MAX-ACCESS      read-only
    STATUS          current
    DESCRIPTION     
            "The Child registration ID created for the registration session."
    ::= { sonusSipRegActGroupRegStatusEntry 3 }

sonusSipRegActGroupRegStatusAorName OBJECT-TYPE
    SYNTAX          DisplayString (SIZE(0..127))
    MAX-ACCESS      read-only
    STATUS          current
    DESCRIPTION     
            "The E.164 number and host portion plus optional BGID representing the 
             Address Of Record of the registering endpoint."
    ::= { sonusSipRegActGroupRegStatusEntry 4 }

sonusSipRegActGroupRegStatusState OBJECT-TYPE
    SYNTAX          INTEGER { null(0), initiating(1), completed(2), 
                        refreshing(3), updating(4), challenged(5), 
                        deleting(6), terminated(7), expired(8) }
    MAX-ACCESS      read-only
    STATUS          current
    DESCRIPTION     
            "The registration state of the endpoint."
    ::= { sonusSipRegActGroupRegStatusEntry 5 }

sonusSipRegActGroupRegStatusContactURI OBJECT-TYPE
    SYNTAX          DisplayString (SIZE(0..127))
    MAX-ACCESS      read-only
    STATUS          current
    DESCRIPTION     
            "The SIP CONTACT URI header."
    ::= { sonusSipRegActGroupRegStatusEntry 6 }

sonusSipRegActGroupRegStatusNextHopIpAddress OBJECT-TYPE
    SYNTAX          IpAddress
    MAX-ACCESS      read-only
    STATUS          current
    DESCRIPTION     
            "Next hop TSAP IP address."
    ::= { sonusSipRegActGroupRegStatusEntry 7 }

sonusSipRegActGroupRegStatusNextHopPortNum OBJECT-TYPE
    SYNTAX          Integer32 (1..65535)
    MAX-ACCESS      read-only
    STATUS          current
    DESCRIPTION     
            "Next hop TSAP UDP port number."
    ::= { sonusSipRegActGroupRegStatusEntry 8 }

sonusSipRegActGroupRegStatusRegistrarIpAddress OBJECT-TYPE
    SYNTAX          IpAddress
    MAX-ACCESS      read-only
    STATUS          current
    DESCRIPTION     
            "SIP Registrar's IP Address."
    ::= { sonusSipRegActGroupRegStatusEntry 9 }

sonusSipRegActGroupRegStatusRegistrarPortNum OBJECT-TYPE
    SYNTAX          Integer32 (1..65535)
    MAX-ACCESS      read-only
    STATUS          current
    DESCRIPTION     
            "SIP Registrar's UDP port number."
    ::= { sonusSipRegActGroupRegStatusEntry 10 }

sonusSipRegActGroupRegStatusExtExpirationTime OBJECT-TYPE
    SYNTAX          Integer32
    MAX-ACCESS      read-only
    STATUS          current
    DESCRIPTION     
            "The external expiration timer value in seconds."
    ::= { sonusSipRegActGroupRegStatusEntry 11 }

sonusSipRegActGroupRegStatusIntExpirationTime OBJECT-TYPE
    SYNTAX          Integer32
    MAX-ACCESS      read-only
    STATUS          current
    DESCRIPTION     
            "The internal expiration timer value in seconds."
    ::= { sonusSipRegActGroupRegStatusEntry 12 }

sonusSipRegActGroupRegStatusCreationTime OBJECT-TYPE
    SYNTAX          DateAndTime
    MAX-ACCESS      read-only
    STATUS          current
    DESCRIPTION     
            "Octet string that identifies the date and GMT time at which the
             SIP registration is initiated."
    ::= { sonusSipRegActGroupRegStatusEntry 13 }

sonusSipRegActGroupRegStatusRegistrarDomainName OBJECT-TYPE
    SYNTAX          DisplayString (SIZE(0..127))
    MAX-ACCESS      read-only
    STATUS          current
    DESCRIPTION     
            "The SIP registrar's domain name."
    ::= { sonusSipRegActGroupRegStatusEntry 14 }

sonusSipRegActGroupRegStatusNextRegIdIsChild OBJECT-TYPE
    SYNTAX          Integer32 (0..1)
    MAX-ACCESS      read-only
    STATUS          current
    DESCRIPTION     
            "The next reg Id is a child ."
    ::= { sonusSipRegActGroupRegStatusEntry 15 }

sonusSipRegActGroupRegStatusNextHopIp6Address OBJECT-TYPE
    SYNTAX          Ipv6Address
    MAX-ACCESS      read-only
    STATUS          current
    DESCRIPTION     
            "Next hop TSAP IPv6 address."
    ::= { sonusSipRegActGroupRegStatusEntry 16 }

sonusSipRegActGroupRegStatusRegistrarIp6Address OBJECT-TYPE
    SYNTAX          Ipv6Address
    MAX-ACCESS      read-only
    STATUS          current
    DESCRIPTION     
            "SIP Registrar's IPv6 Address."
    ::= { sonusSipRegActGroupRegStatusEntry 17 }

sonusSipRegActGroupRegStatusNextHopIpVersion OBJECT-TYPE
    SYNTAX          INTEGER { afInet(2), afInet6(24) }
    MAX-ACCESS      read-only
    STATUS          current
    DESCRIPTION     
            "Next hop TSAP IP address version."
    ::= { sonusSipRegActGroupRegStatusEntry 18 }

sonusSipRegActGroupRegStatusRegistrarIpVersion OBJECT-TYPE
    SYNTAX          INTEGER { afInet(2), afInet6(24) }
    MAX-ACCESS      read-only
    STATUS          current
    DESCRIPTION     
            "SIP Registrar's IP Address Type."
    ::= { sonusSipRegActGroupRegStatusEntry 19 }

sonusSipRegActGroupRegStatusParentAorName OBJECT-TYPE
    SYNTAX          DisplayString (SIZE(0..127))
    MAX-ACCESS      read-only
    STATUS          current
    DESCRIPTION     
            "Holds parent's AOR for a child registration"
    ::= { sonusSipRegActGroupRegStatusEntry 20 }

sonusSipRegActGroupRegStatusSummaryTable OBJECT-TYPE
    SYNTAX          SEQUENCE OF SonusSipRegActGroupRegStatusSummaryEntry
    MAX-ACCESS      not-accessible
    STATUS          current
    DESCRIPTION     
            "This table presents the active SIP registration status  
             summary for a list of SIP endpoints."
    ::= { sonusSipSignallingMIBObjects 37 }

sonusSipRegActGroupRegStatusSummaryEntry OBJECT-TYPE
    SYNTAX          SonusSipRegActGroupRegStatusSummaryEntry
    MAX-ACCESS      not-accessible
    STATUS          current
    DESCRIPTION     
            "This entry presents the active SIP registration status for
             a SIP endpoint."
    INDEX           { 
                      sonusSipRegActGroupRegStatusSummaryRegistrarIpAddress, 
                      sonusSipRegActGroupRegStatusSummaryRegistrarIp6Address, 
                      sonusSipRegActGroupRegStatusSummaryRegistrarIpVersion, 
                      sonusSipRegActGroupRegStatusSummarySlotIndex, 
                      sonusSipRegActGroupRegStatusSummaryNextRegId }
    ::= { sonusSipRegActGroupRegStatusSummaryTable 1 }

SonusSipRegActGroupRegStatusSummaryEntry ::=
    SEQUENCE {
        sonusSipRegActGroupRegStatusSummarySlotIndex            SonusSlotIndex,
        sonusSipRegActGroupRegStatusSummaryNextRegId            Integer32,
        sonusSipRegActGroupRegStatusSummaryRegistrarIpAddress                     IpAddress,
        sonusSipRegActGroupRegStatusSummaryAorName          DisplayString,
        sonusSipRegActGroupRegStatusSummaryState        INTEGER,
        sonusSipRegActGroupRegStatusSummaryNextRegIdIsChild                   Integer32,
        sonusSipRegActGroupRegStatusSummaryRegistrarPort                Integer32,
        sonusSipRegActGroupRegStatusSummaryRegistrarDomainName                      DisplayString,
        sonusSipRegActGroupRegStatusSummaryPeerIpAddress                IpAddress,
        sonusSipRegActGroupRegStatusSummaryPeerPort           Integer32,
        sonusSipRegActGroupRegStatusSummaryPeerIp6Address                 Ipv6Address,
        sonusSipRegActGroupRegStatusSummaryRegistrarIp6Address                      Ipv6Address,
        sonusSipRegActGroupRegStatusSummaryRegistrarIpVersion                     INTEGER,
        sonusSipRegActGroupRegStatusSummaryPeerIpVersion                INTEGER
    }

sonusSipRegActGroupRegStatusSummarySlotIndex OBJECT-TYPE
    SYNTAX          SonusSlotIndex
    MAX-ACCESS      read-only
    STATUS          current
    DESCRIPTION     
            "Identifies the target slot."
    ::= { sonusSipRegActGroupRegStatusSummaryEntry 1 }

sonusSipRegActGroupRegStatusSummaryNextRegId OBJECT-TYPE
    SYNTAX          Integer32 (1..1000000)
    MAX-ACCESS      read-only
    STATUS          current
    DESCRIPTION     
            "The next registration ID created for the registration session."
    ::= { sonusSipRegActGroupRegStatusSummaryEntry 2 }

sonusSipRegActGroupRegStatusSummaryRegistrarIpAddress OBJECT-TYPE
    SYNTAX          IpAddress
    MAX-ACCESS      read-only
    STATUS          current
    DESCRIPTION     
            "SIP Registrar's IP Address."
    ::= { sonusSipRegActGroupRegStatusSummaryEntry 3 }

sonusSipRegActGroupRegStatusSummaryAorName OBJECT-TYPE
    SYNTAX          DisplayString (SIZE(0..127))
    MAX-ACCESS      read-only
    STATUS          current
    DESCRIPTION     
            "The E.164 number and host portion plus optional BGID representing the 
             Address Of Record of the registering endpoint."
    ::= { sonusSipRegActGroupRegStatusSummaryEntry 4 }

sonusSipRegActGroupRegStatusSummaryState OBJECT-TYPE
    SYNTAX          INTEGER { null(0), initiating(1), completed(2), 
                        refreshing(3), updating(4), challenged(5), 
                        deleting(6), terminated(7), expired(8) }
    MAX-ACCESS      read-only
    STATUS          current
    DESCRIPTION     
            "The registration state of the endpoint."
    ::= { sonusSipRegActGroupRegStatusSummaryEntry 5 }

sonusSipRegActGroupRegStatusSummaryNextRegIdIsChild OBJECT-TYPE
    SYNTAX          Integer32 (0..1)
    MAX-ACCESS      read-only
    STATUS          current
    DESCRIPTION     
            "The next reg Id is a child ."
    ::= { sonusSipRegActGroupRegStatusSummaryEntry 6 }

sonusSipRegActGroupRegStatusSummaryRegistrarPort OBJECT-TYPE
    SYNTAX          Integer32 (0..65535)
    MAX-ACCESS      read-only
    STATUS          current
    DESCRIPTION     
            "The Registrar port number."
    ::= { sonusSipRegActGroupRegStatusSummaryEntry 7 }

sonusSipRegActGroupRegStatusSummaryRegistrarDomainName OBJECT-TYPE
    SYNTAX          DisplayString (SIZE(0..127))
    MAX-ACCESS      read-only
    STATUS          current
    DESCRIPTION     
            "The domain name of registrar"
    ::= { sonusSipRegActGroupRegStatusSummaryEntry 8 }

sonusSipRegActGroupRegStatusSummaryPeerIpAddress OBJECT-TYPE
    SYNTAX          IpAddress
    MAX-ACCESS      read-only
    STATUS          current
    DESCRIPTION     
            "Next hop TSAP IP Address."
    ::= { sonusSipRegActGroupRegStatusSummaryEntry 9 }

sonusSipRegActGroupRegStatusSummaryPeerPort OBJECT-TYPE
    SYNTAX          Integer32 (1..65535)
    MAX-ACCESS      read-only
    STATUS          current
    DESCRIPTION     
            "Next hop TSAP port number."
    ::= { sonusSipRegActGroupRegStatusSummaryEntry 10 }

sonusSipRegActGroupRegStatusSummaryPeerIp6Address OBJECT-TYPE
    SYNTAX          Ipv6Address
    MAX-ACCESS      read-only
    STATUS          current
    DESCRIPTION     
            "Next hop TSAP IP Address."
    ::= { sonusSipRegActGroupRegStatusSummaryEntry 11 }

sonusSipRegActGroupRegStatusSummaryRegistrarIp6Address OBJECT-TYPE
    SYNTAX          Ipv6Address
    MAX-ACCESS      read-only
    STATUS          current
    DESCRIPTION     
            "SIP Registrar's IPv6 Address."
    ::= { sonusSipRegActGroupRegStatusSummaryEntry 12 }

sonusSipRegActGroupRegStatusSummaryRegistrarIpVersion OBJECT-TYPE
    SYNTAX          INTEGER { afInet(2), afInet6(24) }
    MAX-ACCESS      read-only
    STATUS          current
    DESCRIPTION     
            "SIP Registrar's IP Address Version."
    ::= { sonusSipRegActGroupRegStatusSummaryEntry 13 }

sonusSipRegActGroupRegStatusSummaryPeerIpVersion OBJECT-TYPE
    SYNTAX          INTEGER { afInet(2), afInet6(24) }
    MAX-ACCESS      read-only
    STATUS          current
    DESCRIPTION     
            "Next hop TSAP IP Address Version."
    ::= { sonusSipRegActGroupRegStatusSummaryEntry 14 }

sonusSipRegistrationDeleteIpConfigObjects OBJECT IDENTIFIER
    ::= { sonusSipSignallingMIBObjects 38 }

sonusSipRegistrationDeleteIpRegstrarIp OBJECT-TYPE
    SYNTAX          IpAddress
    MAX-ACCESS      read-write
    STATUS          current
    DESCRIPTION     
            "SIP Registrar's IP Address."
    ::= { sonusSipRegistrationDeleteIpConfigObjects 1 }

sonusSipRegistrationDeleteIpRegistrarPort OBJECT-TYPE
    SYNTAX          Integer32 (1..65535)
    MAX-ACCESS      read-write
    STATUS          current
    DESCRIPTION     
            "SIP Registrar's Port number."
    ::= { sonusSipRegistrationDeleteIpConfigObjects 2 }

sonusSipRegistrationDeleteIpRegistrarDomainName OBJECT-TYPE
    SYNTAX          DisplayString (SIZE(0..127))
    MAX-ACCESS      read-write
    STATUS          current
    DESCRIPTION     
            "SIP Registrar's Domain Name."
    ::= { sonusSipRegistrationDeleteIpConfigObjects 3 }

sonusSipRegistrationDeleteIp6RegstrarIp OBJECT-TYPE
    SYNTAX          Ipv6Address
    MAX-ACCESS      read-write
    STATUS          current
    DESCRIPTION     
            "SIP Registrar's IP Address."
    ::= { sonusSipRegistrationDeleteIpConfigObjects 4 }

sonusSipEmergencyProfile OBJECT IDENTIFIER
    ::= { sonusSipSignallingMIBObjects 39 }

sonusSipEmergencyProfileNextIndex OBJECT-TYPE
    SYNTAX          Unsigned32
    MAX-ACCESS      read-only
    STATUS          current
    DESCRIPTION     
            "The next valid index to use when creating a new sonusSipEmergencyProfileEntry"
    ::= { sonusSipEmergencyProfile 1 }

sonusSipEmergencyProfileTable OBJECT-TYPE
    SYNTAX          SEQUENCE OF SonusSipEmergencyProfileEntry
    MAX-ACCESS      read-only
    STATUS          current
    DESCRIPTION     
            "This table contains information about each Emergency
             Profile configured on the node."
    ::= { sonusSipEmergencyProfile 2 }

sonusSipEmergencyProfileEntry OBJECT-TYPE
    SYNTAX          SonusSipEmergencyProfileEntry
    MAX-ACCESS      not-accessible
    STATUS          current
    DESCRIPTION     
            "This table describes the SIP Emergency Profile."
    INDEX           { sonusSipEmergencyProfIndex }
    ::= { sonusSipEmergencyProfileTable 1 }

SonusSipEmergencyProfileEntry ::=
    SEQUENCE {
        sonusSipEmergencyProfIndex      Unsigned32,
        sonusSipEmergencyProfName       SonusName,
        sonusSipEmergencyProfRowStatus  RowStatus,
        sonusSipEmergencyProfPrefix1    DisplayString,
        sonusSipEmergencyProfPrefix2    DisplayString,
        sonusSipEmergencyProfPrefix3    DisplayString,
        sonusSipEmergencyProfCpc        INTEGER
    }

sonusSipEmergencyProfIndex OBJECT-TYPE
    SYNTAX          Unsigned32
    MAX-ACCESS      not-accessible
    STATUS          current
    DESCRIPTION     
            "The index of the SIP emergency profile table entry."
    ::= { sonusSipEmergencyProfileEntry 1 }

sonusSipEmergencyProfName OBJECT-TYPE
    SYNTAX          SonusName
    MAX-ACCESS      read-write
    STATUS          current
    DESCRIPTION     
            "The name of this SIP Emergency Profile."
    ::= { sonusSipEmergencyProfileEntry 2 }

sonusSipEmergencyProfRowStatus OBJECT-TYPE
    SYNTAX          RowStatus
    MAX-ACCESS      read-write
    STATUS          current
    DESCRIPTION     
            ""
    ::= { sonusSipEmergencyProfileEntry 3 }

sonusSipEmergencyProfPrefix1 OBJECT-TYPE
    SYNTAX          DisplayString (SIZE(0..15))
    MAX-ACCESS      read-write
    STATUS          current
    DESCRIPTION     
            "SIP alphanumeric string emergency prefix #1.
             An incoming SIP call will be classified as an emergency call
             if the prefix of the user name portion of the relevant headers of
             the INVITE message matches with this prefix."
    ::= { sonusSipEmergencyProfileEntry 4 }

sonusSipEmergencyProfPrefix2 OBJECT-TYPE
    SYNTAX          DisplayString (SIZE(0..15))
    MAX-ACCESS      read-write
    STATUS          current
    DESCRIPTION     
            "SIP alphanumeric string emergency prefix #2."
    ::= { sonusSipEmergencyProfileEntry 5 }

sonusSipEmergencyProfPrefix3 OBJECT-TYPE
    SYNTAX          DisplayString (SIZE(0..15))
    MAX-ACCESS      read-write
    STATUS          current
    DESCRIPTION     
            "SIP alphanumeric string emergency prefix #3."
    ::= { sonusSipEmergencyProfileEntry 6 }

sonusSipEmergencyProfCpc OBJECT-TYPE
    SYNTAX          INTEGER { none(1), priority(2) }
    MAX-ACCESS      read-write
    STATUS          current
    DESCRIPTION     
            "This parameter controls the GSX behavior of whether SIP cpc=priority
             can be used for emergency call indication or not"
    DEFVAL          { none }
    ::= { sonusSipEmergencyProfileEntry 7 }

sonusSipSigPeer OBJECT IDENTIFIER
    ::= { sonusSipSignallingMIBObjects 40 }

sonusSipSigPeerNextIndex OBJECT-TYPE
    SYNTAX          Integer32
    MAX-ACCESS      read-only
    STATUS          current
    DESCRIPTION     
            "The next valid index to use when creating a new sonusSipSigPeerEntry"
    ::= { sonusSipSigPeer 1 }

sonusSipSigPeerTable OBJECT-TYPE
    SYNTAX          SEQUENCE OF SonusSipSigPeerEntry
    MAX-ACCESS      not-accessible
    STATUS          current
    DESCRIPTION     
            "This table contains information about each static SIP signaling peer."
    ::= { sonusSipSigPeer 2 }

sonusSipSigPeerEntry OBJECT-TYPE
    SYNTAX          SonusSipSigPeerEntry
    MAX-ACCESS      not-accessible
    STATUS          current
    DESCRIPTION     
            "This table describes the static SIP signaling peers."
    INDEX           { sonusSipSigPeerListIndex }
    ::= { sonusSipSigPeerTable 1 }

SonusSipSigPeerEntry ::=
    SEQUENCE {
        sonusSipSigPeerListIndex        Unsigned32,
        sonusSipSigPeerName             SonusName,
        sonusSipSigPeerIpAddress        IpAddress,
        sonusSipSigPeerZoneName         SonusNameReference,
        sonusSipSigPeerCacProfile       SonusNameReference,
        sonusSipSigPeerRowStatus        RowStatus,
        sonusSipSigPeerAdminState       SonusAdminState,
        sonusSipSigPeerIp6Address       Ipv6Address,
        sonusSipSigPeerIpVersion        INTEGER
    }

sonusSipSigPeerListIndex OBJECT-TYPE
    SYNTAX          Unsigned32
    MAX-ACCESS      read-only
    STATUS          current
    DESCRIPTION     
            "The index of the static SIP signaling peer entry."
    ::= { sonusSipSigPeerEntry 1 }

sonusSipSigPeerName OBJECT-TYPE
    SYNTAX          SonusName
    MAX-ACCESS      read-write
    STATUS          current
    DESCRIPTION     
            "The name of this SIP signaling peer."
    ::= { sonusSipSigPeerEntry 2 }

sonusSipSigPeerIpAddress OBJECT-TYPE
    SYNTAX          IpAddress
    MAX-ACCESS      read-write
    STATUS          current
    DESCRIPTION     
            "Signaling IP Address of the SIP Peer"
    ::= { sonusSipSigPeerEntry 3 }

sonusSipSigPeerZoneName OBJECT-TYPE
    SYNTAX          SonusNameReference
    MAX-ACCESS      read-write
    STATUS          current
    DESCRIPTION     
            "The ZONE name for the SIP Peer."
    ::= { sonusSipSigPeerEntry 4 }

sonusSipSigPeerCacProfile OBJECT-TYPE
    SYNTAX          SonusNameReference
    MAX-ACCESS      read-write
    STATUS          current
    DESCRIPTION     
            "The name of the endpoint CAC profile for this SIP peer."
    ::= { sonusSipSigPeerEntry 5 }

sonusSipSigPeerRowStatus OBJECT-TYPE
    SYNTAX          RowStatus
    MAX-ACCESS      read-write
    STATUS          current
    DESCRIPTION     
            ""
    ::= { sonusSipSigPeerEntry 6 }

sonusSipSigPeerAdminState OBJECT-TYPE
    SYNTAX          SonusAdminState
    MAX-ACCESS      read-write
    STATUS          current
    DESCRIPTION     
            "The admin state of the this SIP signaling peer."
    DEFVAL          { disabled }
    ::= { sonusSipSigPeerEntry 7 }

sonusSipSigPeerIp6Address OBJECT-TYPE
    SYNTAX          Ipv6Address
    MAX-ACCESS      read-write
    STATUS          current
    DESCRIPTION     
            "Signaling IP Address of the SIP Peer"
    ::= { sonusSipSigPeerEntry 8 }

sonusSipSigPeerIpVersion OBJECT-TYPE
    SYNTAX          INTEGER { afInet(2), afInet6(24) }
    MAX-ACCESS      read-only
    STATUS          current
    DESCRIPTION     
            "Signaling IP Address Version of the SIP Peer"
    ::= { sonusSipSigPeerEntry 9 }

sonusSipCac OBJECT IDENTIFIER
    ::= { sonusSipSignallingMIBObjects 41 }

sonusSipCacNextIndex OBJECT-TYPE
    SYNTAX          Integer32
    MAX-ACCESS      read-only
    STATUS          current
    DESCRIPTION     
            "The next valid index to use when creating a new sonusSipCacEntry"
    ::= { sonusSipCac 1 }

sonusSipCacTable OBJECT-TYPE
    SYNTAX          SEQUENCE OF SonusSipCacEntry
    MAX-ACCESS      not-accessible
    STATUS          current
    DESCRIPTION     
            "This table contains information about each endpoint CAC profile."
    ::= { sonusSipCac 2 }

sonusSipCacEntry OBJECT-TYPE
    SYNTAX          SonusSipCacEntry
    MAX-ACCESS      not-accessible
    STATUS          current
    DESCRIPTION     
            "This table describes the endpoint CAC profiles."
    INDEX           { sonusSipCacIndex }
    ::= { sonusSipCacTable 1 }

SonusSipCacEntry ::=
    SEQUENCE {
        sonusSipCacIndex                Unsigned32,
        sonusSipCacProfName             SonusName,
        sonusSipCacRowStatus            RowStatus,
        sonusSipCacAdminState           SonusAdminState,
        sonusSipCacCallIngressRate      Integer32,
        sonusSipCacCallIngressRatePeriod Unsigned32,
        sonusSipCacCallIngressBurstSize Unsigned32,
        sonusSipCacCallIngressPriorityThreshold       Unsigned32,
        sonusSipCacCallEgressRate       Integer32,
        sonusSipCacCallEgressRatePeriod Unsigned32,
        sonusSipCacCallEgressBurstSize  Unsigned32,
        sonusSipCacCallEgressPriorityThreshold      Unsigned32,
        sonusSipCacCallLimit            Integer32,
        sonusSipCacCallLimitPriorityOverage   Unsigned32,
        sonusSipCacCallIngressEmergencyPref   SonusAdminState,
        sonusSipCacCallEgressEmergencyPref  SonusAdminState,
        sonusSipCacCallIngressAggrPref  Unsigned32,
        sonusSipCacCallEgressAggrPref   Unsigned32,
        sonusSipCacCallIngressAggrEmergPref   Unsigned32,
        sonusSipCacCallEgressAggrEmergPref  Unsigned32,
        sonusSipCacSubscribeIngressRate Integer32,
        sonusSipCacSubscribeIngressRatePeriod     Unsigned32,
        sonusSipCacSubscribeIngressBurstSize    Unsigned32,
        sonusSipCacSubscribeIngressAggrPref   Unsigned32,
        sonusSipCacSubscribeEgressRate  Integer32,
        sonusSipCacSubscribeEgressRatePeriod    Unsigned32,
        sonusSipCacSubscribeEgressBurstSize   Unsigned32,
        sonusSipCacSubscribeEgressAggrPref  Unsigned32,
        sonusSipCacReferIngressRate     Integer32,
        sonusSipCacReferIngressRatePeriod Unsigned32,
        sonusSipCacReferIngressBurstSize Unsigned32,
        sonusSipCacReferIngressAggrPref Unsigned32,
        sonusSipCacReferEgressRate      Integer32,
        sonusSipCacReferEgressRatePeriod Unsigned32,
        sonusSipCacReferEgressBurstSize Unsigned32,
        sonusSipCacReferEgressAggrPref  Unsigned32,
        sonusSipCacNotifyIngressRate    Integer32,
        sonusSipCacNotifyIngressRatePeriod  Unsigned32,
        sonusSipCacNotifyIngressAggrPref Unsigned32,
        sonusSipCacNotifyIngressBurstSize Unsigned32,
        sonusSipCacNotifyEgressRate     Integer32,
        sonusSipCacNotifyEgressRatePeriod Unsigned32,
        sonusSipCacNotifyEgressBurstSize Unsigned32,
        sonusSipCacNotifyEgressAggrPref Unsigned32,
        sonusSipCacOptionsIngressRate   Integer32,
        sonusSipCacOptionsIngressRatePeriod   Unsigned32,
        sonusSipCacOptionsIngressBurstSize  Unsigned32,
        sonusSipCacOptionsIngressAggrPref Unsigned32,
        sonusSipCacOptionsEgressRate    Integer32,
        sonusSipCacOptionsEgressRatePeriod  Unsigned32,
        sonusSipCacOptionsEgressBurstSize Unsigned32,
        sonusSipCacOptionsEgressAggrPref Unsigned32,
        sonusSipCacMessageIngressRate   Integer32,
        sonusSipCacMessageIngressRatePeriod   Unsigned32,
        sonusSipCacMessageIngressBurstSize  Unsigned32,
        sonusSipCacMessageIngressAggrPref Unsigned32,
        sonusSipCacMessageEgressRate    Integer32,
        sonusSipCacMessageEgressRatePeriod  Unsigned32,
        sonusSipCacMessageEgressBurstSize Unsigned32,
        sonusSipCacMessageEgressAggrPref Unsigned32,
        sonusSipCacOtherReqIngressRate  Integer32,
        sonusSipCacOtherReqIngressRatePeriod    Unsigned32,
        sonusSipCacOtherReqIngressBurstSize   Unsigned32,
        sonusSipCacOtherReqIngressAggrPref  Unsigned32,
        sonusSipCacOtherReqEgressRate   Integer32,
        sonusSipCacOtherReqEgressRatePeriod   Unsigned32,
        sonusSipCacOtherReqEgressBurstSize  Unsigned32,
        sonusSipCacOtherReqEgressAggrPref Unsigned32,
        sonusSipCacResponseIngressRate  Integer32,
        sonusSipCacResponseIngressRatePeriod    Unsigned32,
        sonusSipCacResponseIngressBurstSize   Unsigned32,
        sonusSipCacResponseIngressAggrPref  Unsigned32,
        sonusSipCacResponseEgressRate   Integer32,
        sonusSipCacResponseEgressRatePeriod   Unsigned32,
        sonusSipCacResponseEgressBurstSize  Unsigned32,
        sonusSipCacResponseEgressAggrPref Unsigned32,
        sonusSipCacAggrRejIngressRate   Integer32,
        sonusSipCacAggrRejIngressRatePeriod   Unsigned32,
        sonusSipCacAggrRejIngressBurstSize  Unsigned32,
        sonusSipCacAggrMsgIngressRate   Integer32,
        sonusSipCacAggrMsgIngressRatePeriod   Unsigned32,
        sonusSipCacAggrMsgIngressBurstSize  Unsigned32,
        sonusSipCacAggrMsgEgressRate    Integer32,
        sonusSipCacAggrMsgEgressRatePeriod  Unsigned32,
        sonusSipCacAggrMsgEgressBurstSize Unsigned32,
        sonusSipCacCallLimitOverage     Unsigned32
    }

sonusSipCacIndex OBJECT-TYPE
    SYNTAX          Unsigned32
    MAX-ACCESS      read-only
    STATUS          current
    DESCRIPTION     
            "The index of the endpoint CAC profile."
    ::= { sonusSipCacEntry 1 }

sonusSipCacProfName OBJECT-TYPE
    SYNTAX          SonusName
    MAX-ACCESS      read-write
    STATUS          current
    DESCRIPTION     
            "The name of this endpoint CAC profile."
    ::= { sonusSipCacEntry 2 }

sonusSipCacRowStatus OBJECT-TYPE
    SYNTAX          RowStatus
    MAX-ACCESS      read-write
    STATUS          current
    DESCRIPTION     
            ""
    ::= { sonusSipCacEntry 3 }

sonusSipCacAdminState OBJECT-TYPE
    SYNTAX          SonusAdminState
    MAX-ACCESS      read-write
    STATUS          current
    DESCRIPTION     
            "The admin state of the endpoint CAC profile."
    DEFVAL          { disabled }
    ::= { sonusSipCacEntry 4 }

sonusSipCacCallIngressRate OBJECT-TYPE
    SYNTAX          Integer32 (0..500)
    MAX-ACCESS      read-write
    STATUS          current
    DESCRIPTION     
            "Maximum ingress call rate in calls per period"
    DEFVAL          { 0 }
    ::= { sonusSipCacEntry 5 }

sonusSipCacCallIngressRatePeriod OBJECT-TYPE
    SYNTAX          Unsigned32 (1..10)
    MAX-ACCESS      read-write
    STATUS          current
    DESCRIPTION     
            "Period in seconds over which ingress call rate applies."
    DEFVAL          { 1 }
    ::= { sonusSipCacEntry 6 }

sonusSipCacCallIngressBurstSize OBJECT-TYPE
    SYNTAX          Unsigned32 (1..500)
    MAX-ACCESS      read-write
    STATUS          current
    DESCRIPTION     
            "Maximum burst size for ingress calls."
    DEFVAL          { 1 }
    ::= { sonusSipCacEntry 7 }

sonusSipCacCallIngressPriorityThreshold OBJECT-TYPE
    SYNTAX          Unsigned32 (0..500)
    MAX-ACCESS      read-write
    STATUS          current
    DESCRIPTION     
            "Portion ingress burst size reserved for emergency calls."
    DEFVAL          { 0 }
    ::= { sonusSipCacEntry 8 }

sonusSipCacCallEgressRate OBJECT-TYPE
    SYNTAX          Integer32 (0..500)
    MAX-ACCESS      read-write
    STATUS          current
    DESCRIPTION     
            "Maximum egress call rate in calls per period"
    DEFVAL          { 0 }
    ::= { sonusSipCacEntry 9 }

sonusSipCacCallEgressRatePeriod OBJECT-TYPE
    SYNTAX          Unsigned32 (1..10)
    MAX-ACCESS      read-write
    STATUS          current
    DESCRIPTION     
            "Period in seconds over which egress call rate applies."
    DEFVAL          { 1 }
    ::= { sonusSipCacEntry 10 }

sonusSipCacCallEgressBurstSize OBJECT-TYPE
    SYNTAX          Unsigned32 (1..500)
    MAX-ACCESS      read-write
    STATUS          current
    DESCRIPTION     
            "Maximum burst size for egress calls."
    DEFVAL          { 1 }
    ::= { sonusSipCacEntry 11 }

sonusSipCacCallEgressPriorityThreshold OBJECT-TYPE
    SYNTAX          Unsigned32 (0..500)
    MAX-ACCESS      read-write
    STATUS          current
    DESCRIPTION     
            "Portion of egress burst size reserved for emergency calls."
    DEFVAL          { 0 }
    ::= { sonusSipCacEntry 12 }

sonusSipCacCallLimit OBJECT-TYPE
    SYNTAX          Integer32 (-1..30000)
    MAX-ACCESS      read-write
    STATUS          current
    DESCRIPTION     
            "Maximum number of active calls."
    DEFVAL          { -1 }
    ::= { sonusSipCacEntry 13 }

sonusSipCacCallLimitPriorityOverage OBJECT-TYPE
    SYNTAX          Unsigned32 (0..30000)
    MAX-ACCESS      read-write
    STATUS          current
    DESCRIPTION     
            "Overage for call limit allowed for emergency calls."
    DEFVAL          { 0 }
    ::= { sonusSipCacEntry 14 }

sonusSipCacCallIngressEmergencyPref OBJECT-TYPE
    SYNTAX          SonusAdminState
    MAX-ACCESS      read-write
    STATUS          current
    DESCRIPTION     
            "The emergency call preference at ingress"
    DEFVAL          { disabled }
    ::= { sonusSipCacEntry 15 }

sonusSipCacCallEgressEmergencyPref OBJECT-TYPE
    SYNTAX          SonusAdminState
    MAX-ACCESS      read-write
    STATUS          current
    DESCRIPTION     
            "The emergency call preference at egress"
    DEFVAL          { disabled }
    ::= { sonusSipCacEntry 16 }

sonusSipCacCallIngressAggrPref OBJECT-TYPE
    SYNTAX          Unsigned32 (1..10)
    MAX-ACCESS      read-write
    STATUS          current
    DESCRIPTION     
            "The preference of calls within  the aggregate policer at ingress"
    DEFVAL          { 5 }
    ::= { sonusSipCacEntry 17 }

sonusSipCacCallEgressAggrPref OBJECT-TYPE
    SYNTAX          Unsigned32 (1..10)
    MAX-ACCESS      read-write
    STATUS          current
    DESCRIPTION     
            "The preference of calls within  the aggregate policer at egress"
    DEFVAL          { 5 }
    ::= { sonusSipCacEntry 18 }

sonusSipCacCallIngressAggrEmergPref OBJECT-TYPE
    SYNTAX          Unsigned32 (1..10)
    MAX-ACCESS      read-write
    STATUS          current
    DESCRIPTION     
            "The preference of calls within  the aggregate policer at ingress"
    DEFVAL          { 5 }
    ::= { sonusSipCacEntry 19 }

sonusSipCacCallEgressAggrEmergPref OBJECT-TYPE
    SYNTAX          Unsigned32 (1..10)
    MAX-ACCESS      read-write
    STATUS          current
    DESCRIPTION     
            "The preference of calls within  the aggregate policer at egress"
    DEFVAL          { 5 }
    ::= { sonusSipCacEntry 20 }

sonusSipCacSubscribeIngressRate OBJECT-TYPE
    SYNTAX          Integer32 (0..500)
    MAX-ACCESS      read-write
    STATUS          current
    DESCRIPTION     
            "Maximum ingress dialog initiating SUBSCRIBE rate in SUBSCRIBEs per period"
    DEFVAL          { 0 }
    ::= { sonusSipCacEntry 21 }

sonusSipCacSubscribeIngressRatePeriod OBJECT-TYPE
    SYNTAX          Unsigned32 (1..10)
    MAX-ACCESS      read-write
    STATUS          current
    DESCRIPTION     
            "Period in seconds over which ingress SUBSCRIBE rate applies."
    DEFVAL          { 1 }
    ::= { sonusSipCacEntry 22 }

sonusSipCacSubscribeIngressBurstSize OBJECT-TYPE
    SYNTAX          Unsigned32 (1..500)
    MAX-ACCESS      read-write
    STATUS          current
    DESCRIPTION     
            "Maximum burst size for ingress SUBSCRIBEs."
    DEFVAL          { 1 }
    ::= { sonusSipCacEntry 23 }

sonusSipCacSubscribeIngressAggrPref OBJECT-TYPE
    SYNTAX          Unsigned32 (1..10)
    MAX-ACCESS      read-write
    STATUS          current
    DESCRIPTION     
            "The preference of SUBSCRIBEes within  the aggregate policer at ingress"
    DEFVAL          { 5 }
    ::= { sonusSipCacEntry 24 }

sonusSipCacSubscribeEgressRate OBJECT-TYPE
    SYNTAX          Integer32 (0..500)
    MAX-ACCESS      read-write
    STATUS          current
    DESCRIPTION     
            "Maximum egress SUBSCRIBE rate in SUBSCRIBEs per period"
    DEFVAL          { 0 }
    ::= { sonusSipCacEntry 25 }

sonusSipCacSubscribeEgressRatePeriod OBJECT-TYPE
    SYNTAX          Unsigned32 (1..10)
    MAX-ACCESS      read-write
    STATUS          current
    DESCRIPTION     
            "Period in seconds over which egress SUBSCRIBE rate applies."
    DEFVAL          { 1 }
    ::= { sonusSipCacEntry 26 }

sonusSipCacSubscribeEgressBurstSize OBJECT-TYPE
    SYNTAX          Unsigned32 (1..500)
    MAX-ACCESS      read-write
    STATUS          current
    DESCRIPTION     
            "Maximum burst size for egress SUBSCRIBEs."
    DEFVAL          { 1 }
    ::= { sonusSipCacEntry 27 }

sonusSipCacSubscribeEgressAggrPref OBJECT-TYPE
    SYNTAX          Unsigned32 (1..10)
    MAX-ACCESS      read-write
    STATUS          current
    DESCRIPTION     
            "The preference of SUBSCRIBEs within  the aggregate policer at egress"
    DEFVAL          { 5 }
    ::= { sonusSipCacEntry 28 }

sonusSipCacReferIngressRate OBJECT-TYPE
    SYNTAX          Integer32 (0..500)
    MAX-ACCESS      read-write
    STATUS          current
    DESCRIPTION     
            "Maximum ingress dialog initiating REFER rate in REFERs per period"
    DEFVAL          { 0 }
    ::= { sonusSipCacEntry 29 }

sonusSipCacReferIngressRatePeriod OBJECT-TYPE
    SYNTAX          Unsigned32 (1..10)
    MAX-ACCESS      read-write
    STATUS          current
    DESCRIPTION     
            "Period in seconds over which ingress REFER rate applies."
    DEFVAL          { 1 }
    ::= { sonusSipCacEntry 30 }

sonusSipCacReferIngressBurstSize OBJECT-TYPE
    SYNTAX          Unsigned32 (1..500)
    MAX-ACCESS      read-write
    STATUS          current
    DESCRIPTION     
            "Maximum burst size for ingress REFERs."
    DEFVAL          { 1 }
    ::= { sonusSipCacEntry 31 }

sonusSipCacReferIngressAggrPref OBJECT-TYPE
    SYNTAX          Unsigned32 (1..10)
    MAX-ACCESS      read-write
    STATUS          current
    DESCRIPTION     
            "The preference of REFERs within  the aggregate policer at ingress"
    DEFVAL          { 5 }
    ::= { sonusSipCacEntry 32 }

sonusSipCacReferEgressRate OBJECT-TYPE
    SYNTAX          Integer32 (0..500)
    MAX-ACCESS      read-write
    STATUS          current
    DESCRIPTION     
            "Maximum egress REFER rate in REFERs per period"
    DEFVAL          { 0 }
    ::= { sonusSipCacEntry 33 }

sonusSipCacReferEgressRatePeriod OBJECT-TYPE
    SYNTAX          Unsigned32 (1..10)
    MAX-ACCESS      read-write
    STATUS          current
    DESCRIPTION     
            "Period in seconds over which egress REFER rate applies."
    DEFVAL          { 1 }
    ::= { sonusSipCacEntry 34 }

sonusSipCacReferEgressBurstSize OBJECT-TYPE
    SYNTAX          Unsigned32 (1..500)
    MAX-ACCESS      read-write
    STATUS          current
    DESCRIPTION     
            "Maximum burst size for egress REFERs."
    DEFVAL          { 1 }
    ::= { sonusSipCacEntry 35 }

sonusSipCacReferEgressAggrPref OBJECT-TYPE
    SYNTAX          Unsigned32 (1..10)
    MAX-ACCESS      read-write
    STATUS          current
    DESCRIPTION     
            "The preference of REFERs within  the aggregate policer at egress"
    DEFVAL          { 5 }
    ::= { sonusSipCacEntry 36 }

sonusSipCacNotifyIngressRate OBJECT-TYPE
    SYNTAX          Integer32 (0..500)
    MAX-ACCESS      read-write
    STATUS          current
    DESCRIPTION     
            "Maximum ingress outofdialog  NOTIFY rate in NOTIFYs per period"
    DEFVAL          { 0 }
    ::= { sonusSipCacEntry 37 }

sonusSipCacNotifyIngressRatePeriod OBJECT-TYPE
    SYNTAX          Unsigned32 (1..10)
    MAX-ACCESS      read-write
    STATUS          current
    DESCRIPTION     
            "Period in seconds over which ingress NOTIFY rate applies."
    DEFVAL          { 1 }
    ::= { sonusSipCacEntry 38 }

sonusSipCacNotifyIngressAggrPref OBJECT-TYPE
    SYNTAX          Unsigned32 (1..10)
    MAX-ACCESS      read-write
    STATUS          current
    DESCRIPTION     
            "The preference of NOTIFYs within  the aggregate policer at ingress"
    DEFVAL          { 5 }
    ::= { sonusSipCacEntry 39 }

sonusSipCacNotifyIngressBurstSize OBJECT-TYPE
    SYNTAX          Unsigned32 (1..500)
    MAX-ACCESS      read-write
    STATUS          current
    DESCRIPTION     
            "Maximum burst size for ingress NOTIFYs."
    DEFVAL          { 1 }
    ::= { sonusSipCacEntry 40 }

sonusSipCacNotifyEgressRate OBJECT-TYPE
    SYNTAX          Integer32 (0..500)
    MAX-ACCESS      read-write
    STATUS          current
    DESCRIPTION     
            "Maximum egress NOTIFY rate in NOTIFYs per period"
    DEFVAL          { 0 }
    ::= { sonusSipCacEntry 41 }

sonusSipCacNotifyEgressRatePeriod OBJECT-TYPE
    SYNTAX          Unsigned32 (1..10)
    MAX-ACCESS      read-write
    STATUS          current
    DESCRIPTION     
            "Period in seconds over which egress NOTIFY rate applies."
    DEFVAL          { 1 }
    ::= { sonusSipCacEntry 42 }

sonusSipCacNotifyEgressBurstSize OBJECT-TYPE
    SYNTAX          Unsigned32 (1..500)
    MAX-ACCESS      read-write
    STATUS          current
    DESCRIPTION     
            "Maximum burst size for egress NOTIFYs."
    DEFVAL          { 1 }
    ::= { sonusSipCacEntry 43 }

sonusSipCacNotifyEgressAggrPref OBJECT-TYPE
    SYNTAX          Unsigned32 (1..10)
    MAX-ACCESS      read-write
    STATUS          current
    DESCRIPTION     
            "The preference of NOTIFYs within  the aggregate policer at Egress"
    DEFVAL          { 5 }
    ::= { sonusSipCacEntry 44 }

sonusSipCacOptionsIngressRate OBJECT-TYPE
    SYNTAX          Integer32 (0..500)
    MAX-ACCESS      read-write
    STATUS          current
    DESCRIPTION     
            "Maximum ingress outofdialog  OPTIONS rate in OPTIONS per period"
    DEFVAL          { 0 }
    ::= { sonusSipCacEntry 45 }

sonusSipCacOptionsIngressRatePeriod OBJECT-TYPE
    SYNTAX          Unsigned32 (1..10)
    MAX-ACCESS      read-write
    STATUS          current
    DESCRIPTION     
            "Period in seconds over which ingress OPTIONS rate applies."
    DEFVAL          { 1 }
    ::= { sonusSipCacEntry 46 }

sonusSipCacOptionsIngressBurstSize OBJECT-TYPE
    SYNTAX          Unsigned32 (1..500)
    MAX-ACCESS      read-write
    STATUS          current
    DESCRIPTION     
            "Maximum burst size for ingress OPTIONS."
    DEFVAL          { 1 }
    ::= { sonusSipCacEntry 47 }

sonusSipCacOptionsIngressAggrPref OBJECT-TYPE
    SYNTAX          Unsigned32 (1..10)
    MAX-ACCESS      read-write
    STATUS          current
    DESCRIPTION     
            "The preference of OPTIONS within  the aggregate policer at ingress"
    DEFVAL          { 5 }
    ::= { sonusSipCacEntry 48 }

sonusSipCacOptionsEgressRate OBJECT-TYPE
    SYNTAX          Integer32 (0..500)
    MAX-ACCESS      read-write
    STATUS          current
    DESCRIPTION     
            "Maximum egress OPTIONS rate in OPTIONS per period"
    DEFVAL          { 0 }
    ::= { sonusSipCacEntry 49 }

sonusSipCacOptionsEgressRatePeriod OBJECT-TYPE
    SYNTAX          Unsigned32 (1..10)
    MAX-ACCESS      read-write
    STATUS          current
    DESCRIPTION     
            "Period in seconds over which egress OPTIONS rate applies."
    DEFVAL          { 1 }
    ::= { sonusSipCacEntry 50 }

sonusSipCacOptionsEgressBurstSize OBJECT-TYPE
    SYNTAX          Unsigned32 (1..500)
    MAX-ACCESS      read-write
    STATUS          current
    DESCRIPTION     
            "Maximum burst size for egress OPTIONS."
    DEFVAL          { 1 }
    ::= { sonusSipCacEntry 51 }

sonusSipCacOptionsEgressAggrPref OBJECT-TYPE
    SYNTAX          Unsigned32 (1..10)
    MAX-ACCESS      read-write
    STATUS          current
    DESCRIPTION     
            "The preference of OPTIONS within  the aggregate policer at egress"
    DEFVAL          { 5 }
    ::= { sonusSipCacEntry 52 }

sonusSipCacMessageIngressRate OBJECT-TYPE
    SYNTAX          Integer32 (0..500)
    MAX-ACCESS      read-write
    STATUS          current
    DESCRIPTION     
            "Maximum ingress outofdialog  MESSAGE rate in MESSAGEs per period"
    DEFVAL          { 0 }
    ::= { sonusSipCacEntry 53 }

sonusSipCacMessageIngressRatePeriod OBJECT-TYPE
    SYNTAX          Unsigned32 (1..10)
    MAX-ACCESS      read-write
    STATUS          current
    DESCRIPTION     
            "Period in seconds over which ingress MESSAGE rate applies."
    DEFVAL          { 1 }
    ::= { sonusSipCacEntry 54 }

sonusSipCacMessageIngressBurstSize OBJECT-TYPE
    SYNTAX          Unsigned32 (1..500)
    MAX-ACCESS      read-write
    STATUS          current
    DESCRIPTION     
            "Maximum burst size for ingress MESSAGEs."
    DEFVAL          { 1 }
    ::= { sonusSipCacEntry 55 }

sonusSipCacMessageIngressAggrPref OBJECT-TYPE
    SYNTAX          Unsigned32 (1..10)
    MAX-ACCESS      read-write
    STATUS          current
    DESCRIPTION     
            "The preference of MESSAGEs within  the aggregate policer at ingress"
    DEFVAL          { 5 }
    ::= { sonusSipCacEntry 56 }

sonusSipCacMessageEgressRate OBJECT-TYPE
    SYNTAX          Integer32 (0..500)
    MAX-ACCESS      read-write
    STATUS          current
    DESCRIPTION     
            "Maximum egress MESSAGE rate in MESSAGEs per period"
    DEFVAL          { 0 }
    ::= { sonusSipCacEntry 57 }

sonusSipCacMessageEgressRatePeriod OBJECT-TYPE
    SYNTAX          Unsigned32 (1..10)
    MAX-ACCESS      read-write
    STATUS          current
    DESCRIPTION     
            "Period in seconds over which egress MESSAGE rate applies."
    DEFVAL          { 1 }
    ::= { sonusSipCacEntry 58 }

sonusSipCacMessageEgressBurstSize OBJECT-TYPE
    SYNTAX          Unsigned32 (1..500)
    MAX-ACCESS      read-write
    STATUS          current
    DESCRIPTION     
            "Maximum burst size for egress MESSAGEs."
    DEFVAL          { 1 }
    ::= { sonusSipCacEntry 59 }

sonusSipCacMessageEgressAggrPref OBJECT-TYPE
    SYNTAX          Unsigned32 (1..10)
    MAX-ACCESS      read-write
    STATUS          current
    DESCRIPTION     
            "The preference of MESSAGEs within  the aggregate policer at egress"
    DEFVAL          { 5 }
    ::= { sonusSipCacEntry 60 }

sonusSipCacOtherReqIngressRate OBJECT-TYPE
    SYNTAX          Integer32 (0..500)
    MAX-ACCESS      read-write
    STATUS          current
    DESCRIPTION     
            "Maximum ingress  Other Requests rate in Other Requests per period"
    DEFVAL          { 0 }
    ::= { sonusSipCacEntry 61 }

sonusSipCacOtherReqIngressRatePeriod OBJECT-TYPE
    SYNTAX          Unsigned32 (1..10)
    MAX-ACCESS      read-write
    STATUS          current
    DESCRIPTION     
            "Period in seconds over which ingress Other Requests rate applies."
    DEFVAL          { 1 }
    ::= { sonusSipCacEntry 62 }

sonusSipCacOtherReqIngressBurstSize OBJECT-TYPE
    SYNTAX          Unsigned32 (1..500)
    MAX-ACCESS      read-write
    STATUS          current
    DESCRIPTION     
            "Maximum burst size for ingress Other Requests."
    DEFVAL          { 5 }
    ::= { sonusSipCacEntry 63 }

sonusSipCacOtherReqIngressAggrPref OBJECT-TYPE
    SYNTAX          Unsigned32 (1..10)
    MAX-ACCESS      read-write
    STATUS          current
    DESCRIPTION     
            "The preference of Other Requests within  the aggregate policer at ingress"
    DEFVAL          { 5 }
    ::= { sonusSipCacEntry 64 }

sonusSipCacOtherReqEgressRate OBJECT-TYPE
    SYNTAX          Integer32 (0..500)
    MAX-ACCESS      read-write
    STATUS          current
    DESCRIPTION     
            "Maximum ingress  Other Requests rate in Other Requests per period"
    DEFVAL          { 0 }
    ::= { sonusSipCacEntry 65 }

sonusSipCacOtherReqEgressRatePeriod OBJECT-TYPE
    SYNTAX          Unsigned32 (1..10)
    MAX-ACCESS      read-write
    STATUS          current
    DESCRIPTION     
            "Period in seconds over which egress Other Requests rate applies."
    DEFVAL          { 1 }
    ::= { sonusSipCacEntry 66 }

sonusSipCacOtherReqEgressBurstSize OBJECT-TYPE
    SYNTAX          Unsigned32 (1..500)
    MAX-ACCESS      read-write
    STATUS          current
    DESCRIPTION     
            "Maximum burst size for egress Other Requests."
    DEFVAL          { 5 }
    ::= { sonusSipCacEntry 67 }

sonusSipCacOtherReqEgressAggrPref OBJECT-TYPE
    SYNTAX          Unsigned32 (1..10)
    MAX-ACCESS      read-write
    STATUS          current
    DESCRIPTION     
            "The preference of Other Requests within  the aggregate policer at Egress"
    DEFVAL          { 5 }
    ::= { sonusSipCacEntry 68 }

sonusSipCacResponseIngressRate OBJECT-TYPE
    SYNTAX          Integer32 (0..500)
    MAX-ACCESS      read-write
    STATUS          current
    DESCRIPTION     
            "Maximum ingress  Responses rate in Responses per period"
    DEFVAL          { 0 }
    ::= { sonusSipCacEntry 69 }

sonusSipCacResponseIngressRatePeriod OBJECT-TYPE
    SYNTAX          Unsigned32 (1..10)
    MAX-ACCESS      read-write
    STATUS          current
    DESCRIPTION     
            "Period in seconds over which ingress Responses rate applies."
    DEFVAL          { 1 }
    ::= { sonusSipCacEntry 70 }

sonusSipCacResponseIngressBurstSize OBJECT-TYPE
    SYNTAX          Unsigned32 (1..500)
    MAX-ACCESS      read-write
    STATUS          current
    DESCRIPTION     
            "Maximum burst size for ingress Responses."
    DEFVAL          { 5 }
    ::= { sonusSipCacEntry 71 }

sonusSipCacResponseIngressAggrPref OBJECT-TYPE
    SYNTAX          Unsigned32 (1..10)
    MAX-ACCESS      read-write
    STATUS          current
    DESCRIPTION     
            "The preference of Responses within  the aggregate policer at ingress"
    DEFVAL          { 5 }
    ::= { sonusSipCacEntry 72 }

sonusSipCacResponseEgressRate OBJECT-TYPE
    SYNTAX          Integer32 (0..500)
    MAX-ACCESS      read-write
    STATUS          current
    DESCRIPTION     
            "Maximum egress  Responses rate in Responses per period"
    DEFVAL          { 0 }
    ::= { sonusSipCacEntry 73 }

sonusSipCacResponseEgressRatePeriod OBJECT-TYPE
    SYNTAX          Unsigned32 (1..10)
    MAX-ACCESS      read-write
    STATUS          current
    DESCRIPTION     
            "Period in seconds over which egress Responses rate applies."
    DEFVAL          { 1 }
    ::= { sonusSipCacEntry 74 }

sonusSipCacResponseEgressBurstSize OBJECT-TYPE
    SYNTAX          Unsigned32 (1..500)
    MAX-ACCESS      read-write
    STATUS          current
    DESCRIPTION     
            "Maximum burst size for egress Responses."
    DEFVAL          { 5 }
    ::= { sonusSipCacEntry 75 }

sonusSipCacResponseEgressAggrPref OBJECT-TYPE
    SYNTAX          Unsigned32 (1..10)
    MAX-ACCESS      read-write
    STATUS          current
    DESCRIPTION     
            "The preference of Responses within  the aggregate policer at egress"
    DEFVAL          { 5 }
    ::= { sonusSipCacEntry 76 }

sonusSipCacAggrRejIngressRate OBJECT-TYPE
    SYNTAX          Integer32 (0..500)
    MAX-ACCESS      read-write
    STATUS          current
    DESCRIPTION     
            "Maximum ingress  aggregate reject rate in aggregate rejects per period"
    DEFVAL          { 0 }
    ::= { sonusSipCacEntry 77 }

sonusSipCacAggrRejIngressRatePeriod OBJECT-TYPE
    SYNTAX          Unsigned32 (1..10)
    MAX-ACCESS      read-write
    STATUS          current
    DESCRIPTION     
            "Period in seconds over which ingress aggregate rejects rate applies."
    DEFVAL          { 1 }
    ::= { sonusSipCacEntry 78 }

sonusSipCacAggrRejIngressBurstSize OBJECT-TYPE
    SYNTAX          Unsigned32 (1..500)
    MAX-ACCESS      read-write
    STATUS          current
    DESCRIPTION     
            "Maximum burst size for ingress aggregate rejects."
    DEFVAL          { 1 }
    ::= { sonusSipCacEntry 79 }

sonusSipCacAggrMsgIngressRate OBJECT-TYPE
    SYNTAX          Integer32 (0..500)
    MAX-ACCESS      read-write
    STATUS          current
    DESCRIPTION     
            "Maximum ingress Aggregate messages rate in aggregate messages per period"
    DEFVAL          { 0 }
    ::= { sonusSipCacEntry 81 }

sonusSipCacAggrMsgIngressRatePeriod OBJECT-TYPE
    SYNTAX          Unsigned32 (1..10)
    MAX-ACCESS      read-write
    STATUS          current
    DESCRIPTION     
            "Period in seconds over which ingress aggregate messages rate applies."
    DEFVAL          { 1 }
    ::= { sonusSipCacEntry 82 }

sonusSipCacAggrMsgIngressBurstSize OBJECT-TYPE
    SYNTAX          Unsigned32 (1..500)
    MAX-ACCESS      read-write
    STATUS          current
    DESCRIPTION     
            "Maximum burst size for ingress aggregate messages."
    DEFVAL          { 5 }
    ::= { sonusSipCacEntry 83 }

sonusSipCacAggrMsgEgressRate OBJECT-TYPE
    SYNTAX          Integer32 (0..500)
    MAX-ACCESS      read-write
    STATUS          current
    DESCRIPTION     
            "Maximum egress Aggregate messages rate in aggregate messages per period"
    DEFVAL          { 0 }
    ::= { sonusSipCacEntry 84 }

sonusSipCacAggrMsgEgressRatePeriod OBJECT-TYPE
    SYNTAX          Unsigned32 (1..10)
    MAX-ACCESS      read-write
    STATUS          current
    DESCRIPTION     
            "Period in seconds over which Egress aggregate messages rate applies."
    DEFVAL          { 1 }
    ::= { sonusSipCacEntry 85 }

sonusSipCacAggrMsgEgressBurstSize OBJECT-TYPE
    SYNTAX          Unsigned32 (1..500)
    MAX-ACCESS      read-write
    STATUS          current
    DESCRIPTION     
            "Maximum burst size for Egress aggregate messages."
    DEFVAL          { 5 }
    ::= { sonusSipCacEntry 86 }

sonusSipCacCallLimitOverage OBJECT-TYPE
    SYNTAX          Unsigned32 (0..30000)
    MAX-ACCESS      read-write
    STATUS          current
    DESCRIPTION     
            "Overage for call limit allowed for normal calls."
    DEFVAL          { 0 }
    ::= { sonusSipCacEntry 87 }

sonusSipSigPeerStatusTable OBJECT-TYPE
    SYNTAX          SEQUENCE OF SonusSipSigPeerStatusEntry
    MAX-ACCESS      not-accessible
    STATUS          current
    DESCRIPTION     
            "Table of SIP Signalling Peer status."
    ::= { sonusSipSignallingMIBObjects 42 }

sonusSipSigPeerStatusEntry OBJECT-TYPE
    SYNTAX          SonusSipSigPeerStatusEntry
    MAX-ACCESS      not-accessible
    STATUS          current
    DESCRIPTION     
            "SIP Signalling Peer Status."
    INDEX           { sonusSipSigPeerStatusSlotIndex, 
                      sonusSipSigPeerStatusIpAddress, 
                      sonusSipSigPeerStatusZoneId, 
                      sonusSipSigPeerStatusPortNum, 
                      sonusSipSigPeerStatusIp6Address, 
                      sonusSipSigPeerStatusIpVersion }
    ::= { sonusSipSigPeerStatusTable 1 }

SonusSipSigPeerStatusEntry ::=
    SEQUENCE {
        sonusSipSigPeerStatusSlotIndex  SonusSlotIndex,
        sonusSipSigPeerStatusIpAddress  IpAddress,
        sonusSipSigPeerStatusZoneId     Unsigned32,
        sonusSipSigPeerStatusPortNum    Unsigned32,
        sonusSipSigPeerStatusType       INTEGER,
        sonusSipSigPeerStatusCreatedAt  DateAndTime,
        sonusSipSigPeerStatusIngressCallsAllowed        Unsigned32,
        sonusSipSigPeerStatusIngressCallsActive       Unsigned32,
        sonusSipSigPeerStatusIngressCallRejectsLimit            Unsigned32,
        sonusSipSigPeerStatusIngressCallRejectsRate           Unsigned32,
        sonusSipSigPeerStatusEgressCallsAllowed       Unsigned32,
        sonusSipSigPeerStatusEgressCallsActive      Unsigned32,
        sonusSipSigPeerStatusEgressCallRejectsLimit           Unsigned32,
        sonusSipSigPeerStatusEgressCallRejectsRate          Unsigned32,
        sonusSipSigPeerStatusState      INTEGER,
        sonusSipSigPeerStatusIngressSubscribeAllowed            Unsigned32,
        sonusSipSigPeerStatusIngressSubscribeRejectsRate                Unsigned32,
        sonusSipSigPeerStatusEgressSubscribeAllowed           Unsigned32,
        sonusSipSigPeerStatusEgressSubscribeRejectsRate               Unsigned32,
        sonusSipSigPeerStatusIngressReferAllowed        Unsigned32,
        sonusSipSigPeerStatusIngressReferRejectsRate            Unsigned32,
        sonusSipSigPeerStatusEgressReferAllowed       Unsigned32,
        sonusSipSigPeerStatusEgressReferRejectsRate           Unsigned32,
        sonusSipSigPeerStatusIngressNotifyAllowed         Unsigned32,
        sonusSipSigPeerStatusIngressNotifyRejectsRate             Unsigned32,
        sonusSipSigPeerStatusEgressNotifyAllowed        Unsigned32,
        sonusSipSigPeerStatusEgressNotifyRejectsRate            Unsigned32,
        sonusSipSigPeerStatusIngressOptionsAllowed          Unsigned32,
        sonusSipSigPeerStatusIngressOptionsRejectsRate              Unsigned32,
        sonusSipSigPeerStatusEgressOptionsAllowed         Unsigned32,
        sonusSipSigPeerStatusEgressOptionsRejectsRate             Unsigned32,
        sonusSipSigPeerStatusIngressMessageAllowed          Unsigned32,
        sonusSipSigPeerStatusIngressMessageRejectsRate              Unsigned32,
        sonusSipSigPeerStatusEgressMessageAllowed         Unsigned32,
        sonusSipSigPeerStatusEgressMessageRejectsRate             Unsigned32,
        sonusSipSigPeerStatusIngressOtherReqAllowed           Unsigned32,
        sonusSipSigPeerStatusIngressOtherReqRejectsRate               Unsigned32,
        sonusSipSigPeerStatusEgressOtherReqAllowed          Unsigned32,
        sonusSipSigPeerStatusEgressOtherReqRejectsRate              Unsigned32,
        sonusSipSigPeerStatusIngressResponseAllowed           Unsigned32,
        sonusSipSigPeerStatusIngressResponseRejectsRate               Unsigned32,
        sonusSipSigPeerStatusEgressResponseAllowed          Unsigned32,
        sonusSipSigPeerStatusEgressResponseRejectsRate              Unsigned32,
        sonusSipSigPeerStatusIngressAggrMsgAllowed          Unsigned32,
        sonusSipSigPeerStatusIngressAggrMsgRejectsRate              Unsigned32,
        sonusSipSigPeerStatusEgressAggrMsgAllowed         Unsigned32,
        sonusSipSigPeerStatusEgressAggrMsgRejectsRate             Unsigned32,
        sonusSipSigPeerStatusIngressAggrRejAllowed          Unsigned32,
        sonusSipSigPeerStatusIngressAggrRejRejectsRate              Unsigned32,
        sonusSipSigPeerStatusIp6Address Ipv6Address,
        sonusSipSigPeerStatusIpVersion  INTEGER
    }

sonusSipSigPeerStatusSlotIndex OBJECT-TYPE
    SYNTAX          SonusSlotIndex
    MAX-ACCESS      read-only
    STATUS          current
    DESCRIPTION     
            "The card slot for the Sip Signaling Peering"
    ::= { sonusSipSigPeerStatusEntry 1 }

sonusSipSigPeerStatusIpAddress OBJECT-TYPE
    SYNTAX          IpAddress
    MAX-ACCESS      read-only
    STATUS          current
    DESCRIPTION     
            "IP Address of the Sip Signaling Peer"
    ::= { sonusSipSigPeerStatusEntry 2 }

sonusSipSigPeerStatusZoneId OBJECT-TYPE
    SYNTAX          Unsigned32 (0..65535)
    MAX-ACCESS      read-only
    STATUS          current
    DESCRIPTION     
            "Identifies the Zone ID for this signaling peer."
    ::= { sonusSipSigPeerStatusEntry 3 }

sonusSipSigPeerStatusPortNum OBJECT-TYPE
    SYNTAX          Unsigned32 (0..65535)
    MAX-ACCESS      read-only
    STATUS          current
    DESCRIPTION     
            "The port number for this signaling peer. Always zero for static and non-NATed registrant peer."
    ::= { sonusSipSigPeerStatusEntry 4 }

sonusSipSigPeerStatusType OBJECT-TYPE
    SYNTAX          INTEGER { static(0), registrant(1) }
    MAX-ACCESS      read-only
    STATUS          current
    DESCRIPTION     
            "Identifies the TYPE of signaling peer."
    ::= { sonusSipSigPeerStatusEntry 5 }

sonusSipSigPeerStatusCreatedAt OBJECT-TYPE
    SYNTAX          DateAndTime
    MAX-ACCESS      read-only
    STATUS          current
    DESCRIPTION     
            "The date and GMT time at which this peer control was created."
    ::= { sonusSipSigPeerStatusEntry 6 }

sonusSipSigPeerStatusIngressCallsAllowed OBJECT-TYPE
    SYNTAX          Unsigned32
    MAX-ACCESS      read-only
    STATUS          current
    DESCRIPTION     
            "Number of ingress calls allowed for this peer."
    ::= { sonusSipSigPeerStatusEntry 7 }

sonusSipSigPeerStatusIngressCallsActive OBJECT-TYPE
    SYNTAX          Unsigned32
    MAX-ACCESS      read-only
    STATUS          current
    DESCRIPTION     
            "Number of ingress calls currently active for peer."
    ::= { sonusSipSigPeerStatusEntry 8 }

sonusSipSigPeerStatusIngressCallRejectsLimit OBJECT-TYPE
    SYNTAX          Unsigned32
    MAX-ACCESS      read-only
    STATUS          current
    DESCRIPTION     
            "Number of ingress calls rejected by the endpoint CAC policer due to call count limits."
    ::= { sonusSipSigPeerStatusEntry 9 }

sonusSipSigPeerStatusIngressCallRejectsRate OBJECT-TYPE
    SYNTAX          Unsigned32
    MAX-ACCESS      read-only
    STATUS          current
    DESCRIPTION     
            "Number of ingress calls rejected by the endpoint CAC policer due to call rate."
    ::= { sonusSipSigPeerStatusEntry 10 }

sonusSipSigPeerStatusEgressCallsAllowed OBJECT-TYPE
    SYNTAX          Unsigned32
    MAX-ACCESS      read-only
    STATUS          current
    DESCRIPTION     
            "Number of egress calls allowed for this peer."
    ::= { sonusSipSigPeerStatusEntry 11 }

sonusSipSigPeerStatusEgressCallsActive OBJECT-TYPE
    SYNTAX          Unsigned32
    MAX-ACCESS      read-only
    STATUS          current
    DESCRIPTION     
            "Number of egress calls currently active for peer."
    ::= { sonusSipSigPeerStatusEntry 12 }

sonusSipSigPeerStatusEgressCallRejectsLimit OBJECT-TYPE
    SYNTAX          Unsigned32
    MAX-ACCESS      read-only
    STATUS          current
    DESCRIPTION     
            "Number of egress calls rejected by the endpoint CAC policer due to call count limits."
    ::= { sonusSipSigPeerStatusEntry 13 }

sonusSipSigPeerStatusEgressCallRejectsRate OBJECT-TYPE
    SYNTAX          Unsigned32
    MAX-ACCESS      read-only
    STATUS          current
    DESCRIPTION     
            "Number of egress calls rejected by the endpoint CAC policer due to call rate."
    ::= { sonusSipSigPeerStatusEntry 14 }

sonusSipSigPeerStatusState OBJECT-TYPE
    SYNTAX          INTEGER { none(0), enabled(1), disabled(2), 
                        deleted(3) }
    MAX-ACCESS      read-only
    STATUS          current
    DESCRIPTION     
            "The current state of the signaling peer control."
    ::= { sonusSipSigPeerStatusEntry 15 }

sonusSipSigPeerStatusIngressSubscribeAllowed OBJECT-TYPE
    SYNTAX          Unsigned32
    MAX-ACCESS      read-only
    STATUS          current
    DESCRIPTION     
            "Number of ingress SUBSCRIBEs allowed for this peer."
    ::= { sonusSipSigPeerStatusEntry 16 }

sonusSipSigPeerStatusIngressSubscribeRejectsRate OBJECT-TYPE
    SYNTAX          Unsigned32
    MAX-ACCESS      read-only
    STATUS          current
    DESCRIPTION     
            "Number of ingress SUBSCRIBEs rejected by the endpoint CAC policer due to SUBSCRIBEs rate."
    ::= { sonusSipSigPeerStatusEntry 17 }

sonusSipSigPeerStatusEgressSubscribeAllowed OBJECT-TYPE
    SYNTAX          Unsigned32
    MAX-ACCESS      read-only
    STATUS          current
    DESCRIPTION     
            "Number of egress SUBSCRIBEs allowed for this peer."
    ::= { sonusSipSigPeerStatusEntry 18 }

sonusSipSigPeerStatusEgressSubscribeRejectsRate OBJECT-TYPE
    SYNTAX          Unsigned32
    MAX-ACCESS      read-only
    STATUS          current
    DESCRIPTION     
            "Number of egress SUBSCRIBEs rejected by the endpoint CAC policer due to SUBSCRIBEs rate."
    ::= { sonusSipSigPeerStatusEntry 19 }

sonusSipSigPeerStatusIngressReferAllowed OBJECT-TYPE
    SYNTAX          Unsigned32
    MAX-ACCESS      read-only
    STATUS          current
    DESCRIPTION     
            "Number of ingress REFERs allowed for this peer."
    ::= { sonusSipSigPeerStatusEntry 20 }

sonusSipSigPeerStatusIngressReferRejectsRate OBJECT-TYPE
    SYNTAX          Unsigned32
    MAX-ACCESS      read-only
    STATUS          current
    DESCRIPTION     
            "Number of ingress REFERs rejected by the endpoint CAC policer due to REFERs rate."
    ::= { sonusSipSigPeerStatusEntry 21 }

sonusSipSigPeerStatusEgressReferAllowed OBJECT-TYPE
    SYNTAX          Unsigned32
    MAX-ACCESS      read-only
    STATUS          current
    DESCRIPTION     
            "Number of egress REFERs allowed for this peer."
    ::= { sonusSipSigPeerStatusEntry 22 }

sonusSipSigPeerStatusEgressReferRejectsRate OBJECT-TYPE
    SYNTAX          Unsigned32
    MAX-ACCESS      read-only
    STATUS          current
    DESCRIPTION     
            "Number of egress REFERs rejected by the endpoint CAC policer due to REFERs rate."
    ::= { sonusSipSigPeerStatusEntry 23 }

sonusSipSigPeerStatusIngressNotifyAllowed OBJECT-TYPE
    SYNTAX          Unsigned32
    MAX-ACCESS      read-only
    STATUS          current
    DESCRIPTION     
            "Number of ingress NOTIFYs allowed for this peer."
    ::= { sonusSipSigPeerStatusEntry 24 }

sonusSipSigPeerStatusIngressNotifyRejectsRate OBJECT-TYPE
    SYNTAX          Unsigned32
    MAX-ACCESS      read-only
    STATUS          current
    DESCRIPTION     
            "Number of ingress NOTIFYs rejected by the endpoint CAC policer due to NOTIFYs rate."
    ::= { sonusSipSigPeerStatusEntry 25 }

sonusSipSigPeerStatusEgressNotifyAllowed OBJECT-TYPE
    SYNTAX          Unsigned32
    MAX-ACCESS      read-only
    STATUS          current
    DESCRIPTION     
            "Number of egress NOTIFYs allowed for this peer."
    ::= { sonusSipSigPeerStatusEntry 26 }

sonusSipSigPeerStatusEgressNotifyRejectsRate OBJECT-TYPE
    SYNTAX          Unsigned32
    MAX-ACCESS      read-only
    STATUS          current
    DESCRIPTION     
            "Number of egress NOTIFYs rejected by the endpoint CAC policer due to NOTIFYs rate."
    ::= { sonusSipSigPeerStatusEntry 27 }

sonusSipSigPeerStatusIngressOptionsAllowed OBJECT-TYPE
    SYNTAX          Unsigned32
    MAX-ACCESS      read-only
    STATUS          current
    DESCRIPTION     
            "Number of ingress OPTIONS allowed for this peer."
    ::= { sonusSipSigPeerStatusEntry 28 }

sonusSipSigPeerStatusIngressOptionsRejectsRate OBJECT-TYPE
    SYNTAX          Unsigned32
    MAX-ACCESS      read-only
    STATUS          current
    DESCRIPTION     
            "Number of ingress OPTIONS rejected by the endpoint CAC policer due to OPTIONS rate."
    ::= { sonusSipSigPeerStatusEntry 29 }

sonusSipSigPeerStatusEgressOptionsAllowed OBJECT-TYPE
    SYNTAX          Unsigned32
    MAX-ACCESS      read-only
    STATUS          current
    DESCRIPTION     
            "Number of egress OPTIONS allowed for this peer."
    ::= { sonusSipSigPeerStatusEntry 30 }

sonusSipSigPeerStatusEgressOptionsRejectsRate OBJECT-TYPE
    SYNTAX          Unsigned32
    MAX-ACCESS      read-only
    STATUS          current
    DESCRIPTION     
            "Number of egress OPTIONS rejected by the endpoint CAC policer due to OPTIONS rate."
    ::= { sonusSipSigPeerStatusEntry 31 }

sonusSipSigPeerStatusIngressMessageAllowed OBJECT-TYPE
    SYNTAX          Unsigned32
    MAX-ACCESS      read-only
    STATUS          current
    DESCRIPTION     
            "Number of ingress MESSAGEs allowed for this peer."
    ::= { sonusSipSigPeerStatusEntry 32 }

sonusSipSigPeerStatusIngressMessageRejectsRate OBJECT-TYPE
    SYNTAX          Unsigned32
    MAX-ACCESS      read-only
    STATUS          current
    DESCRIPTION     
            "Number of ingress MESSAGEs ejected by the endpoint CAC policer due to MESSAGEs rate."
    ::= { sonusSipSigPeerStatusEntry 33 }

sonusSipSigPeerStatusEgressMessageAllowed OBJECT-TYPE
    SYNTAX          Unsigned32
    MAX-ACCESS      read-only
    STATUS          current
    DESCRIPTION     
            "Number of egress MESSAGEs allowed for this peer."
    ::= { sonusSipSigPeerStatusEntry 34 }

sonusSipSigPeerStatusEgressMessageRejectsRate OBJECT-TYPE
    SYNTAX          Unsigned32
    MAX-ACCESS      read-only
    STATUS          current
    DESCRIPTION     
            "Number of egress MESSAGEs rejected by the endpoint CAC policer due to MESSAGEs rate."
    ::= { sonusSipSigPeerStatusEntry 35 }

sonusSipSigPeerStatusIngressOtherReqAllowed OBJECT-TYPE
    SYNTAX          Unsigned32
    MAX-ACCESS      read-only
    STATUS          current
    DESCRIPTION     
            "Number of ingress Other Requests allowed for this peer."
    ::= { sonusSipSigPeerStatusEntry 36 }

sonusSipSigPeerStatusIngressOtherReqRejectsRate OBJECT-TYPE
    SYNTAX          Unsigned32
    MAX-ACCESS      read-only
    STATUS          current
    DESCRIPTION     
            "Number of ingress Other Requests rejected by the endpoint CAC policer due to Other Requests rate."
    ::= { sonusSipSigPeerStatusEntry 37 }

sonusSipSigPeerStatusEgressOtherReqAllowed OBJECT-TYPE
    SYNTAX          Unsigned32
    MAX-ACCESS      read-only
    STATUS          current
    DESCRIPTION     
            "Number of egress Other Requests allowed for this peer."
    ::= { sonusSipSigPeerStatusEntry 38 }

sonusSipSigPeerStatusEgressOtherReqRejectsRate OBJECT-TYPE
    SYNTAX          Unsigned32
    MAX-ACCESS      read-only
    STATUS          current
    DESCRIPTION     
            "Number of egress Other Requests rejected by the endpoint CAC policer due to Other Requests rate."
    ::= { sonusSipSigPeerStatusEntry 39 }

sonusSipSigPeerStatusIngressResponseAllowed OBJECT-TYPE
    SYNTAX          Unsigned32
    MAX-ACCESS      read-only
    STATUS          current
    DESCRIPTION     
            "Number of ingress Responses allowed for this peer."
    ::= { sonusSipSigPeerStatusEntry 40 }

sonusSipSigPeerStatusIngressResponseRejectsRate OBJECT-TYPE
    SYNTAX          Unsigned32
    MAX-ACCESS      read-only
    STATUS          current
    DESCRIPTION     
            "Number of ingress Responses rejected by the endpoint CAC policer due to Responses rate."
    ::= { sonusSipSigPeerStatusEntry 41 }

sonusSipSigPeerStatusEgressResponseAllowed OBJECT-TYPE
    SYNTAX          Unsigned32
    MAX-ACCESS      read-only
    STATUS          current
    DESCRIPTION     
            "Number of egress Responses allowed for this peer."
    ::= { sonusSipSigPeerStatusEntry 42 }

sonusSipSigPeerStatusEgressResponseRejectsRate OBJECT-TYPE
    SYNTAX          Unsigned32
    MAX-ACCESS      read-only
    STATUS          current
    DESCRIPTION     
            "Number of egress Responses rejected by the endpoint CAC policer due to Responses rate."
    ::= { sonusSipSigPeerStatusEntry 43 }

sonusSipSigPeerStatusIngressAggrMsgAllowed OBJECT-TYPE
    SYNTAX          Unsigned32
    MAX-ACCESS      read-only
    STATUS          current
    DESCRIPTION     
            "Number of ingress Aggregate Messages allowed for this peer."
    ::= { sonusSipSigPeerStatusEntry 44 }

sonusSipSigPeerStatusIngressAggrMsgRejectsRate OBJECT-TYPE
    SYNTAX          Unsigned32
    MAX-ACCESS      read-only
    STATUS          current
    DESCRIPTION     
            "Number of ingress Aggregate Messages rejected by the endpoint CAC policer due to Aggregate Messages rate."
    ::= { sonusSipSigPeerStatusEntry 45 }

sonusSipSigPeerStatusEgressAggrMsgAllowed OBJECT-TYPE
    SYNTAX          Unsigned32
    MAX-ACCESS      read-only
    STATUS          current
    DESCRIPTION     
            "Number of egress Aggregate Messages allowed for this peer."
    ::= { sonusSipSigPeerStatusEntry 46 }

sonusSipSigPeerStatusEgressAggrMsgRejectsRate OBJECT-TYPE
    SYNTAX          Unsigned32
    MAX-ACCESS      read-only
    STATUS          current
    DESCRIPTION     
            "Number of egress Aggregate Messages rejected by the endpoint CAC policer due to Aggregate Messages rate."
    ::= { sonusSipSigPeerStatusEntry 47 }

sonusSipSigPeerStatusIngressAggrRejAllowed OBJECT-TYPE
    SYNTAX          Unsigned32
    MAX-ACCESS      read-only
    STATUS          current
    DESCRIPTION     
            "Number of ingress Aggregate Rejects allowed for this peer."
    ::= { sonusSipSigPeerStatusEntry 48 }

sonusSipSigPeerStatusIngressAggrRejRejectsRate OBJECT-TYPE
    SYNTAX          Unsigned32
    MAX-ACCESS      read-only
    STATUS          current
    DESCRIPTION     
            "Number of ingress Aggregate Rejects rejected by the endpoint CAC policer due to Aggregate Rejects rate."
    ::= { sonusSipSigPeerStatusEntry 49 }

sonusSipSigPeerStatusIp6Address OBJECT-TYPE
    SYNTAX          Ipv6Address
    MAX-ACCESS      read-only
    STATUS          current
    DESCRIPTION     
            "IPv6 Address of the Sip Signaling Peer"
    ::= { sonusSipSigPeerStatusEntry 50 }

sonusSipSigPeerStatusIpVersion OBJECT-TYPE
    SYNTAX          INTEGER { afInet(2), afInet6(24) }
    MAX-ACCESS      read-only
    STATUS          current
    DESCRIPTION     
            "IP Address version of the Sip Signaling Peer"
    ::= { sonusSipSigPeerStatusEntry 51 }

sonusSipCacOffenderTable OBJECT-TYPE
    SYNTAX          SEQUENCE OF SonusSipCacOffenderEntry
    MAX-ACCESS      not-accessible
    STATUS          current
    DESCRIPTION     
            "Table of SIP Signalling Peer statistics."
    ::= { sonusSipSignallingMIBObjects 43 }

sonusSipCacOffenderEntry OBJECT-TYPE
    SYNTAX          SonusSipCacOffenderEntry
    MAX-ACCESS      not-accessible
    STATUS          current
    DESCRIPTION     
            "SIP Peer CAC Offenders."
    INDEX           { sonusSipCacOffenderSlotIndex, 
                      sonusSipCacOffenderListIndex }
    ::= { sonusSipCacOffenderTable 1 }

SonusSipCacOffenderEntry ::=
    SEQUENCE {
        sonusSipCacOffenderSlotIndex    SonusSlotIndex,
        sonusSipCacOffenderListIndex    Unsigned32,
        sonusSipCacOffenderIpAddress    IpAddress,
        sonusSipCacOffenderZoneName     SonusNameReference,
        sonusSipCacOffenderIngressCallRejects     Unsigned32,
        sonusSipCacOffenderEgressCallRejects    Unsigned32,
        sonusSipCacOffenderLastRejectAt DateAndTime,
        sonusSipCacOffenderFirstRejectAt DateAndTime,
        sonusSipCacOffenderPortNum      Unsigned32,
        sonusSipCacOffenderIngressSubscribeRejects          Unsigned32,
        sonusSipCacOffenderEgressSubscribeRejects         Unsigned32,
        sonusSipCacOffenderSubscribeLastRejectAt        DateAndTime,
        sonusSipCacOffenderSubscribeFirstRejectAt         DateAndTime,
        sonusSipCacOffenderIngressReferRejects      Unsigned32,
        sonusSipCacOffenderEgressReferRejects     Unsigned32,
        sonusSipCacOffenderReferLastRejectAt    DateAndTime,
        sonusSipCacOffenderReferFirstRejectAt     DateAndTime,
        sonusSipCacOffenderIngressNotifyRejects       Unsigned32,
        sonusSipCacOffenderEgressNotifyRejects      Unsigned32,
        sonusSipCacOffenderNotifyLastRejectAt     DateAndTime,
        sonusSipCacOffenderNotifyFirstRejectAt      DateAndTime,
        sonusSipCacOffenderIngressOptionsRejects        Unsigned32,
        sonusSipCacOffenderEgressOptionsRejects       Unsigned32,
        sonusSipCacOffenderOptionsLastRejectAt      DateAndTime,
        sonusSipCacOffenderOptionsFirstRejectAt       DateAndTime,
        sonusSipCacOffenderIngressMessageRejects        Unsigned32,
        sonusSipCacOffenderEgressMessageRejects       Unsigned32,
        sonusSipCacOffenderMessageLastRejectAt      DateAndTime,
        sonusSipCacOffenderMessageFirstRejectAt       DateAndTime,
        sonusSipCacOffenderIngressOtherReqRejects         Unsigned32,
        sonusSipCacOffenderEgressOtherReqRejects        Unsigned32,
        sonusSipCacOffenderOtherReqLastRejectAt       DateAndTime,
        sonusSipCacOffenderOtherReqFirstRejectAt        DateAndTime,
        sonusSipCacOffenderIngressAggrMsgRejects        Unsigned32,
        sonusSipCacOffenderEgressAggrMsgRejects       Unsigned32,
        sonusSipCacOffenderAggrMsgLastRejectAt      DateAndTime,
        sonusSipCacOffenderAggrMsgFirstRejectAt       DateAndTime,
        sonusSipCacOffenderIp6Address   Ipv6Address
    }

sonusSipCacOffenderSlotIndex OBJECT-TYPE
    SYNTAX          SonusSlotIndex
    MAX-ACCESS      read-only
    STATUS          current
    DESCRIPTION     
            "The card slot for the CAC offenders."
    ::= { sonusSipCacOffenderEntry 1 }

sonusSipCacOffenderListIndex OBJECT-TYPE
    SYNTAX          Unsigned32
    MAX-ACCESS      read-only
    STATUS          current
    DESCRIPTION     
            "The index of the CAC offender entry."
    ::= { sonusSipCacOffenderEntry 2 }

sonusSipCacOffenderIpAddress OBJECT-TYPE
    SYNTAX          IpAddress
    MAX-ACCESS      read-only
    STATUS          current
    DESCRIPTION     
            "IP Address of the CAC offender."
    ::= { sonusSipCacOffenderEntry 3 }

sonusSipCacOffenderZoneName OBJECT-TYPE
    SYNTAX          SonusNameReference
    MAX-ACCESS      read-only
    STATUS          current
    DESCRIPTION     
            "Identifies the Zone for this CAC offender."
    ::= { sonusSipCacOffenderEntry 4 }

sonusSipCacOffenderIngressCallRejects OBJECT-TYPE
    SYNTAX          Unsigned32
    MAX-ACCESS      read-only
    STATUS          current
    DESCRIPTION     
            "Number of ingress calls recently rejected for this peer by the endpoint CAC policer."
    ::= { sonusSipCacOffenderEntry 5 }

sonusSipCacOffenderEgressCallRejects OBJECT-TYPE
    SYNTAX          Unsigned32
    MAX-ACCESS      read-only
    STATUS          current
    DESCRIPTION     
            "Number of egress calls recently rejected for this peer by the endpoint CAC policer."
    ::= { sonusSipCacOffenderEntry 6 }

sonusSipCacOffenderLastRejectAt OBJECT-TYPE
    SYNTAX          DateAndTime
    MAX-ACCESS      read-only
    STATUS          current
    DESCRIPTION     
            "The date and GMT time for the last CALL reject reported here for this peer."
    ::= { sonusSipCacOffenderEntry 7 }

sonusSipCacOffenderFirstRejectAt OBJECT-TYPE
    SYNTAX          DateAndTime
    MAX-ACCESS      read-only
    STATUS          current
    DESCRIPTION     
            "The date and GMT time for the first CALL reject reported here for this peer."
    ::= { sonusSipCacOffenderEntry 8 }

sonusSipCacOffenderPortNum OBJECT-TYPE
    SYNTAX          Unsigned32 (0..65535)
    MAX-ACCESS      read-only
    STATUS          current
    DESCRIPTION     
            "The port number for this offending peer.This is zero for static peer and non NAT'ed registrant peer"
    ::= { sonusSipCacOffenderEntry 9 }

sonusSipCacOffenderIngressSubscribeRejects OBJECT-TYPE
    SYNTAX          Unsigned32
    MAX-ACCESS      read-only
    STATUS          current
    DESCRIPTION     
            "Number of ingress Subscribes recently rejected for this peer by the endpoint CAC policer."
    ::= { sonusSipCacOffenderEntry 10 }

sonusSipCacOffenderEgressSubscribeRejects OBJECT-TYPE
    SYNTAX          Unsigned32
    MAX-ACCESS      read-only
    STATUS          current
    DESCRIPTION     
            "Number of egress Subscribes recently rejected for this peer by the endpoint CAC policer."
    ::= { sonusSipCacOffenderEntry 11 }

sonusSipCacOffenderSubscribeLastRejectAt OBJECT-TYPE
    SYNTAX          DateAndTime
    MAX-ACCESS      read-only
    STATUS          current
    DESCRIPTION     
            "The date and GMT time for the last SUBSCRIBE reject reported here for this peer."
    ::= { sonusSipCacOffenderEntry 12 }

sonusSipCacOffenderSubscribeFirstRejectAt OBJECT-TYPE
    SYNTAX          DateAndTime
    MAX-ACCESS      read-only
    STATUS          current
    DESCRIPTION     
            "The date and GMT time for the first SUBSCRIBE reject reported here for this peer."
    ::= { sonusSipCacOffenderEntry 13 }

sonusSipCacOffenderIngressReferRejects OBJECT-TYPE
    SYNTAX          Unsigned32
    MAX-ACCESS      read-only
    STATUS          current
    DESCRIPTION     
            "Number of ingress Refers recently rejected for this peer by the endpoint CAC policer."
    ::= { sonusSipCacOffenderEntry 14 }

sonusSipCacOffenderEgressReferRejects OBJECT-TYPE
    SYNTAX          Unsigned32
    MAX-ACCESS      read-only
    STATUS          current
    DESCRIPTION     
            "Number of egress Refers recently rejected for this peer by the endpoint CAC policer."
    ::= { sonusSipCacOffenderEntry 15 }

sonusSipCacOffenderReferLastRejectAt OBJECT-TYPE
    SYNTAX          DateAndTime
    MAX-ACCESS      read-only
    STATUS          current
    DESCRIPTION     
            "The date and GMT time for the last REFER reject reported here for this peer."
    ::= { sonusSipCacOffenderEntry 16 }

sonusSipCacOffenderReferFirstRejectAt OBJECT-TYPE
    SYNTAX          DateAndTime
    MAX-ACCESS      read-only
    STATUS          current
    DESCRIPTION     
            "The date and GMT time for the first REFER reject reported here for this peer."
    ::= { sonusSipCacOffenderEntry 17 }

sonusSipCacOffenderIngressNotifyRejects OBJECT-TYPE
    SYNTAX          Unsigned32
    MAX-ACCESS      read-only
    STATUS          current
    DESCRIPTION     
            "Number of ingress Notifys recently rejected for this peer by the endpoint CAC policer."
    ::= { sonusSipCacOffenderEntry 18 }

sonusSipCacOffenderEgressNotifyRejects OBJECT-TYPE
    SYNTAX          Unsigned32
    MAX-ACCESS      read-only
    STATUS          current
    DESCRIPTION     
            "Number of egress Notifys recently rejected for this peer by the endpoint CAC policer."
    ::= { sonusSipCacOffenderEntry 19 }

sonusSipCacOffenderNotifyLastRejectAt OBJECT-TYPE
    SYNTAX          DateAndTime
    MAX-ACCESS      read-only
    STATUS          current
    DESCRIPTION     
            "The date and GMT time for the last NOTIFY reject reported here for this peer."
    ::= { sonusSipCacOffenderEntry 20 }

sonusSipCacOffenderNotifyFirstRejectAt OBJECT-TYPE
    SYNTAX          DateAndTime
    MAX-ACCESS      read-only
    STATUS          current
    DESCRIPTION     
            "The date and GMT time for the first NOTIFY reject reported here for this peer."
    ::= { sonusSipCacOffenderEntry 21 }

sonusSipCacOffenderIngressOptionsRejects OBJECT-TYPE
    SYNTAX          Unsigned32
    MAX-ACCESS      read-only
    STATUS          current
    DESCRIPTION     
            "Number of ingress Options recently rejected for this peer by the endpoint CAC policer."
    ::= { sonusSipCacOffenderEntry 22 }

sonusSipCacOffenderEgressOptionsRejects OBJECT-TYPE
    SYNTAX          Unsigned32
    MAX-ACCESS      read-only
    STATUS          current
    DESCRIPTION     
            "Number of egress Options recently rejected for this peer by the endpoint CAC policer."
    ::= { sonusSipCacOffenderEntry 23 }

sonusSipCacOffenderOptionsLastRejectAt OBJECT-TYPE
    SYNTAX          DateAndTime
    MAX-ACCESS      read-only
    STATUS          current
    DESCRIPTION     
            "The date and GMT time for the last OPTIONS reject reported here for this peer."
    ::= { sonusSipCacOffenderEntry 24 }

sonusSipCacOffenderOptionsFirstRejectAt OBJECT-TYPE
    SYNTAX          DateAndTime
    MAX-ACCESS      read-only
    STATUS          current
    DESCRIPTION     
            "The date and GMT time for the first OPTIONS reject reported here for this peer."
    ::= { sonusSipCacOffenderEntry 25 }

sonusSipCacOffenderIngressMessageRejects OBJECT-TYPE
    SYNTAX          Unsigned32
    MAX-ACCESS      read-only
    STATUS          current
    DESCRIPTION     
            "Number of ingress Messages recently rejected for this peer by the endpoint CAC policer."
    ::= { sonusSipCacOffenderEntry 26 }

sonusSipCacOffenderEgressMessageRejects OBJECT-TYPE
    SYNTAX          Unsigned32
    MAX-ACCESS      read-only
    STATUS          current
    DESCRIPTION     
            "Number of egress Messages recently rejected for this peer by the endpoint CAC policer."
    ::= { sonusSipCacOffenderEntry 27 }

sonusSipCacOffenderMessageLastRejectAt OBJECT-TYPE
    SYNTAX          DateAndTime
    MAX-ACCESS      read-only
    STATUS          current
    DESCRIPTION     
            "The date and GMT time for the last Message reject reported here for this peer."
    ::= { sonusSipCacOffenderEntry 28 }

sonusSipCacOffenderMessageFirstRejectAt OBJECT-TYPE
    SYNTAX          DateAndTime
    MAX-ACCESS      read-only
    STATUS          current
    DESCRIPTION     
            "The date and GMT time for the first Message reject reported here for this peer."
    ::= { sonusSipCacOffenderEntry 29 }

sonusSipCacOffenderIngressOtherReqRejects OBJECT-TYPE
    SYNTAX          Unsigned32
    MAX-ACCESS      read-only
    STATUS          current
    DESCRIPTION     
            "Number of ingress Other requests recently rejected for this peer by the endpoint CAC policer."
    ::= { sonusSipCacOffenderEntry 30 }

sonusSipCacOffenderEgressOtherReqRejects OBJECT-TYPE
    SYNTAX          Unsigned32
    MAX-ACCESS      read-only
    STATUS          current
    DESCRIPTION     
            "Number of egress Other requests recently rejected for this peer by the endpoint CAC policer."
    ::= { sonusSipCacOffenderEntry 31 }

sonusSipCacOffenderOtherReqLastRejectAt OBJECT-TYPE
    SYNTAX          DateAndTime
    MAX-ACCESS      read-only
    STATUS          current
    DESCRIPTION     
            "The date and GMT time for the last Other request reject reported here for this peer."
    ::= { sonusSipCacOffenderEntry 32 }

sonusSipCacOffenderOtherReqFirstRejectAt OBJECT-TYPE
    SYNTAX          DateAndTime
    MAX-ACCESS      read-only
    STATUS          current
    DESCRIPTION     
            "The date and GMT time for the first Other request reject reported here for this peer."
    ::= { sonusSipCacOffenderEntry 33 }

sonusSipCacOffenderIngressAggrMsgRejects OBJECT-TYPE
    SYNTAX          Unsigned32
    MAX-ACCESS      read-only
    STATUS          current
    DESCRIPTION     
            "Number of ingress Aggregate Messages recently rejected for this peer by the endpoint CAC policer."
    ::= { sonusSipCacOffenderEntry 34 }

sonusSipCacOffenderEgressAggrMsgRejects OBJECT-TYPE
    SYNTAX          Unsigned32
    MAX-ACCESS      read-only
    STATUS          current
    DESCRIPTION     
            "Number of egress Aggregate Messages recently rejected for this peer by the endpoint CAC policer."
    ::= { sonusSipCacOffenderEntry 35 }

sonusSipCacOffenderAggrMsgLastRejectAt OBJECT-TYPE
    SYNTAX          DateAndTime
    MAX-ACCESS      read-only
    STATUS          current
    DESCRIPTION     
            "The date and GMT time for the last Aggregate Messsage reject reported here for this peer."
    ::= { sonusSipCacOffenderEntry 36 }

sonusSipCacOffenderAggrMsgFirstRejectAt OBJECT-TYPE
    SYNTAX          DateAndTime
    MAX-ACCESS      read-only
    STATUS          current
    DESCRIPTION     
            "The date and GMT time for the first Aggregate Messsage reject reported here for this peer."
    ::= { sonusSipCacOffenderEntry 37 }

sonusSipCacOffenderIp6Address OBJECT-TYPE
    SYNTAX          Ipv6Address
    MAX-ACCESS      read-only
    STATUS          current
    DESCRIPTION     
            "IPv6 Address of the CAC offender."
    ::= { sonusSipCacOffenderEntry 38 }

sonusSipPeerOvldObject OBJECT IDENTIFIER
    ::= { sonusSipSignallingMIBObjects 44 }

sonusSipPeerOvldSamplingPeriod OBJECT-TYPE
    SYNTAX          Unsigned32 (1..10)
    MAX-ACCESS      read-write
    STATUS          current
    DESCRIPTION     
            "The sampling period (in seconds) for the peer-overload backoff algorithm."
    DEFVAL          { 2 }
    ::= { sonusSipPeerOvldObject 1 }

sonusSipPeerOvldDiscardPeriod OBJECT-TYPE
    SYNTAX          Unsigned32 (1..10)
    MAX-ACCESS      read-write
    STATUS          current
    DESCRIPTION     
            "The discard period (in seconds) for the peer-overload backoff algorithm."
    DEFVAL          { 2 }
    ::= { sonusSipPeerOvldObject 2 }

sonusSipPeerOvldStepDownGain OBJECT-TYPE
    SYNTAX          Unsigned32 (1..200)
    MAX-ACCESS      read-write
    STATUS          current
    DESCRIPTION     
            "The step down gain for the peer overload backoff algorithm."
    DEFVAL          { 100 }
    ::= { sonusSipPeerOvldObject 3 }

sonusSipPeerOvldRejectThreshold OBJECT-TYPE
    SYNTAX          Unsigned32 (0..50)
    MAX-ACCESS      read-write
    STATUS          current
    DESCRIPTION     
            "The reject threshold (in rejects/sec) for the peer overload backoff algorithm."
    DEFVAL          { 1 }
    ::= { sonusSipPeerOvldObject 4 }

sonusSipSigPeerOvldStatusTable OBJECT-TYPE
    SYNTAX          SEQUENCE OF SonusSipSigPeerOvldStatusEntry
    MAX-ACCESS      not-accessible
    STATUS          current
    DESCRIPTION     
            "Table of SIP Signaling Peer Overload Status."
    ::= { sonusSipSignallingMIBObjects 45 }

sonusSipSigPeerOvldStatusEntry OBJECT-TYPE
    SYNTAX          SonusSipSigPeerOvldStatusEntry
    MAX-ACCESS      not-accessible
    STATUS          current
    DESCRIPTION     
            "SIP Signaling Peer Overload Status."
    INDEX           { sonusSipSigPeerOvldStatusSlotIndex, 
                      sonusSipSigPeerOvldStatusIpAddress, 
                      sonusSipSigPeerOvldStatusSigPortId, 
                      sonusSipSigPeerOvldStatusIp6Address, 
                      sonusSipSigPeerOvldStatusIpVersion }
    ::= { sonusSipSigPeerOvldStatusTable 1 }

SonusSipSigPeerOvldStatusEntry ::=
    SEQUENCE {
        sonusSipSigPeerOvldStatusSlotIndex  SonusSlotIndex,
        sonusSipSigPeerOvldStatusIpAddress  IpAddress,
        sonusSipSigPeerOvldStatusSigPortId  Unsigned32,
        sonusSipSigPeerOvldStatusZoneId Unsigned32,
        sonusSipSigPeerOvldStatusZoneName SonusNameReference,
        sonusSipSigPeerOvldStatusCallsSent  Unsigned32,
        sonusSipSigPeerOvldStatusCallsRejected      Unsigned32,
        sonusSipSigPeerOvldStatus503sReceived     Unsigned32,
        sonusSipSigPeerOvldStatusAllowedRate    Unsigned32,
        sonusSipSigPeerOvldStatusIp6Address   Ipv6Address,
        sonusSipSigPeerOvldStatusIpVersion  INTEGER
    }

sonusSipSigPeerOvldStatusSlotIndex OBJECT-TYPE
    SYNTAX          SonusSlotIndex
    MAX-ACCESS      read-only
    STATUS          current
    DESCRIPTION     
            "The card slot for the Sip Signaling Overload Peering"
    ::= { sonusSipSigPeerOvldStatusEntry 1 }

sonusSipSigPeerOvldStatusIpAddress OBJECT-TYPE
    SYNTAX          IpAddress
    MAX-ACCESS      read-only
    STATUS          current
    DESCRIPTION     
            "IP Address of the Sip Signaling Overload Peer"
    ::= { sonusSipSigPeerOvldStatusEntry 2 }

sonusSipSigPeerOvldStatusSigPortId OBJECT-TYPE
    SYNTAX          Unsigned32 (0..65535)
    MAX-ACCESS      read-only
    STATUS          current
    DESCRIPTION     
            "The signaling port Id for this signaling peer."
    ::= { sonusSipSigPeerOvldStatusEntry 3 }

sonusSipSigPeerOvldStatusZoneId OBJECT-TYPE
    SYNTAX          Unsigned32 (0..65535)
    MAX-ACCESS      read-only
    STATUS          current
    DESCRIPTION     
            "Identifies the Zone Id for this signaling peer."
    ::= { sonusSipSigPeerOvldStatusEntry 4 }

sonusSipSigPeerOvldStatusZoneName OBJECT-TYPE
    SYNTAX          SonusNameReference
    MAX-ACCESS      read-only
    STATUS          current
    DESCRIPTION     
            "Identifies the Zone for this signaling peer."
    ::= { sonusSipSigPeerOvldStatusEntry 5 }

sonusSipSigPeerOvldStatusCallsSent OBJECT-TYPE
    SYNTAX          Unsigned32
    MAX-ACCESS      read-only
    STATUS          current
    DESCRIPTION     
            "Number of calls sent in the last sampling period for peer."
    ::= { sonusSipSigPeerOvldStatusEntry 6 }

sonusSipSigPeerOvldStatusCallsRejected OBJECT-TYPE
    SYNTAX          Unsigned32
    MAX-ACCESS      read-only
    STATUS          current
    DESCRIPTION     
            "Number of calls rejected in the last sampling period for peer."
    ::= { sonusSipSigPeerOvldStatusEntry 7 }

sonusSipSigPeerOvldStatus503sReceived OBJECT-TYPE
    SYNTAX          Unsigned32
    MAX-ACCESS      read-only
    STATUS          current
    DESCRIPTION     
            "Number of 503s received in the last sampling period."
    ::= { sonusSipSigPeerOvldStatusEntry 8 }

sonusSipSigPeerOvldStatusAllowedRate OBJECT-TYPE
    SYNTAX          Unsigned32
    MAX-ACCESS      read-only
    STATUS          current
    DESCRIPTION     
            "Rate of calls allowed per second for this peer."
    ::= { sonusSipSigPeerOvldStatusEntry 9 }

sonusSipSigPeerOvldStatusIp6Address OBJECT-TYPE
    SYNTAX          Ipv6Address
    MAX-ACCESS      read-only
    STATUS          current
    DESCRIPTION     
            "IP Address of the Sip Signaling Overload Peer"
    ::= { sonusSipSigPeerOvldStatusEntry 10 }

sonusSipSigPeerOvldStatusIpVersion OBJECT-TYPE
    SYNTAX          INTEGER { afInet(2), afInet6(24) }
    MAX-ACCESS      read-only
    STATUS          current
    DESCRIPTION     
            "IP Version of the Sip Signaling Overload Peer"
    ::= { sonusSipSigPeerOvldStatusEntry 11 }

sonusSipMultipleActRegNameStatusTable OBJECT-TYPE
    SYNTAX          SEQUENCE OF SonusSipMultipleActRegNameStatusEntry
    MAX-ACCESS      not-accessible
    STATUS          current
    DESCRIPTION     
            "This table presents the active SIP registration status for 
             a list of SIP endpoints."
    ::= { sonusSipSignallingMIBObjects 46 }

sonusSipMultipleActRegNameStatusEntry OBJECT-TYPE
    SYNTAX          SonusSipMultipleActRegNameStatusEntry
    MAX-ACCESS      not-accessible
    STATUS          current
    DESCRIPTION     
            "This entry presents the active SIP registration status for
             a SIP endpoint."
    INDEX           { sonusSipMultipleActRegNameStatusKey1, 
                      sonusSipMultipleActRegNameStatusKey2, 
                      sonusSipMultipleActRegNameStatusKey3, 
                      sonusSipMultipleActRegNameStatusKey4, 
                      sonusSipMultipleActRegNameStatusSlotIndex, 
                      sonusSipMultipleActRegNameStatusInstance }
    ::= { sonusSipMultipleActRegNameStatusTable 1 }

SonusSipMultipleActRegNameStatusEntry ::=
    SEQUENCE {
        sonusSipMultipleActRegNameStatusSlotIndex         SonusSlotIndex,
        sonusSipMultipleActRegNameStatusRegId     Integer32,
        sonusSipMultipleActRegNameStatusAorName       DisplayString,
        sonusSipMultipleActRegNameStatusState     INTEGER,
        sonusSipMultipleActRegNameStatusContactURI          DisplayString,
        sonusSipMultipleActRegNameStatusNextHopIpAddress                IpAddress,
        sonusSipMultipleActRegNameStatusNextHopPortNum              Integer32,
        sonusSipMultipleActRegNameStatusRegistrarIpAddress                  IpAddress,
        sonusSipMultipleActRegNameStatusRegistrarPortNum                Integer32,
        sonusSipMultipleActRegNameStatusExtExpirationTime                 Integer32,
        sonusSipMultipleActRegNameStatusIntExpirationTime                 Integer32,
        sonusSipMultipleActRegNameStatusCreationTime            DateAndTime,
        sonusSipMultipleActRegNameStatusRegistrarDomainName                   DisplayString,
        sonusSipMultipleActRegNameStatusKey1    Integer32,
        sonusSipMultipleActRegNameStatusKey2    Integer32,
        sonusSipMultipleActRegNameStatusKey3    Integer32,
        sonusSipMultipleActRegNameStatusKey4    Integer32,
        sonusSipMultipleActRegNameStatusInstance        Integer32,
        sonusSipMultipleActRegNameStatusNextHopIp6Address                 Ipv6Address,
        sonusSipMultipleActRegNameStatusRegistrarIp6Address                   Ipv6Address,
        sonusSipMultipleActRegNameStatusNextHopIpVersion                INTEGER,
        sonusSipMultipleActRegNameStatusRegistrarIpVersion                  INTEGER
    }

sonusSipMultipleActRegNameStatusSlotIndex OBJECT-TYPE
    SYNTAX          SonusSlotIndex
    MAX-ACCESS      read-only
    STATUS          current
    DESCRIPTION     
            "Identifies the target slot."
    ::= { sonusSipMultipleActRegNameStatusEntry 1 }

sonusSipMultipleActRegNameStatusRegId OBJECT-TYPE
    SYNTAX          Integer32
    MAX-ACCESS      read-only
    STATUS          current
    DESCRIPTION     
            "The registration ID created for the registration session."
    ::= { sonusSipMultipleActRegNameStatusEntry 2 }

sonusSipMultipleActRegNameStatusAorName OBJECT-TYPE
    SYNTAX          DisplayString (SIZE(1..128))
    MAX-ACCESS      read-only
    STATUS          current
    DESCRIPTION     
            "The E.164 number and host portion plus optional BGID representing the 
             Address Of Record of the registering endpoint."
    ::= { sonusSipMultipleActRegNameStatusEntry 3 }

sonusSipMultipleActRegNameStatusState OBJECT-TYPE
    SYNTAX          INTEGER { null(0), initiating(1), completed(2), 
                        refreshing(3), updating(4), challenged(5), 
                        deleting(6), terminated(7) }
    MAX-ACCESS      read-only
    STATUS          current
    DESCRIPTION     
            "The registration state of the endpoint."
    ::= { sonusSipMultipleActRegNameStatusEntry 4 }

sonusSipMultipleActRegNameStatusContactURI OBJECT-TYPE
    SYNTAX          DisplayString (SIZE(0..127))
    MAX-ACCESS      read-only
    STATUS          current
    DESCRIPTION     
            "The SIP CONTACT URI header."
    ::= { sonusSipMultipleActRegNameStatusEntry 5 }

sonusSipMultipleActRegNameStatusNextHopIpAddress OBJECT-TYPE
    SYNTAX          IpAddress
    MAX-ACCESS      read-only
    STATUS          current
    DESCRIPTION     
            "Next hop TSAP IP address."
    ::= { sonusSipMultipleActRegNameStatusEntry 6 }

sonusSipMultipleActRegNameStatusNextHopPortNum OBJECT-TYPE
    SYNTAX          Integer32 (1..65535)
    MAX-ACCESS      read-only
    STATUS          current
    DESCRIPTION     
            "Next hop TSAP UDP port number."
    ::= { sonusSipMultipleActRegNameStatusEntry 7 }

sonusSipMultipleActRegNameStatusRegistrarIpAddress OBJECT-TYPE
    SYNTAX          IpAddress
    MAX-ACCESS      read-only
    STATUS          current
    DESCRIPTION     
            "SIP Registrar's IP Address."
    ::= { sonusSipMultipleActRegNameStatusEntry 8 }

sonusSipMultipleActRegNameStatusRegistrarPortNum OBJECT-TYPE
    SYNTAX          Integer32 (1..65535)
    MAX-ACCESS      read-only
    STATUS          current
    DESCRIPTION     
            "SIP Registrar's UDP port number."
    ::= { sonusSipMultipleActRegNameStatusEntry 9 }

sonusSipMultipleActRegNameStatusExtExpirationTime OBJECT-TYPE
    SYNTAX          Integer32
    MAX-ACCESS      read-only
    STATUS          current
    DESCRIPTION     
            "The external expiration timer value in seconds."
    ::= { sonusSipMultipleActRegNameStatusEntry 10 }

sonusSipMultipleActRegNameStatusIntExpirationTime OBJECT-TYPE
    SYNTAX          Integer32
    MAX-ACCESS      read-only
    STATUS          current
    DESCRIPTION     
            "The internal expiration timer value in seconds."
    ::= { sonusSipMultipleActRegNameStatusEntry 11 }

sonusSipMultipleActRegNameStatusCreationTime OBJECT-TYPE
    SYNTAX          DateAndTime
    MAX-ACCESS      read-only
    STATUS          current
    DESCRIPTION     
            "Octet string that identifies the date and GMT time at which the
             SIP registration is initiated."
    ::= { sonusSipMultipleActRegNameStatusEntry 12 }

sonusSipMultipleActRegNameStatusRegistrarDomainName OBJECT-TYPE
    SYNTAX          DisplayString (SIZE(0..127))
    MAX-ACCESS      read-only
    STATUS          current
    DESCRIPTION     
            "The SIP registrar's domain name."
    ::= { sonusSipMultipleActRegNameStatusEntry 13 }

sonusSipMultipleActRegNameStatusKey1 OBJECT-TYPE
    SYNTAX          Integer32
    MAX-ACCESS      read-only
    STATUS          current
    DESCRIPTION     
            "UserKey of RCB to be fetched"
    ::= { sonusSipMultipleActRegNameStatusEntry 14 }

sonusSipMultipleActRegNameStatusKey2 OBJECT-TYPE
    SYNTAX          Integer32
    MAX-ACCESS      read-only
    STATUS          current
    DESCRIPTION     
            "HostKey of RCB to be fetched"
    ::= { sonusSipMultipleActRegNameStatusEntry 15 }

sonusSipMultipleActRegNameStatusKey3 OBJECT-TYPE
    SYNTAX          Integer32
    MAX-ACCESS      read-only
    STATUS          current
    DESCRIPTION     
            "UserKey of RCB to be fetched"
    ::= { sonusSipMultipleActRegNameStatusEntry 16 }

sonusSipMultipleActRegNameStatusKey4 OBJECT-TYPE
    SYNTAX          Integer32
    MAX-ACCESS      read-only
    STATUS          current
    DESCRIPTION     
            "HostKey of RCB to be fetched"
    ::= { sonusSipMultipleActRegNameStatusEntry 17 }

sonusSipMultipleActRegNameStatusInstance OBJECT-TYPE
    SYNTAX          Integer32
    MAX-ACCESS      read-only
    STATUS          current
    DESCRIPTION     
            "Instance of RCB to be fetched"
    ::= { sonusSipMultipleActRegNameStatusEntry 18 }

sonusSipMultipleActRegNameStatusNextHopIp6Address OBJECT-TYPE
    SYNTAX          Ipv6Address
    MAX-ACCESS      read-only
    STATUS          current
    DESCRIPTION     
            "Next hop TSAP IP address."
    ::= { sonusSipMultipleActRegNameStatusEntry 19 }

sonusSipMultipleActRegNameStatusRegistrarIp6Address OBJECT-TYPE
    SYNTAX          Ipv6Address
    MAX-ACCESS      read-only
    STATUS          current
    DESCRIPTION     
            "SIP Registrar's IP Address."
    ::= { sonusSipMultipleActRegNameStatusEntry 20 }

sonusSipMultipleActRegNameStatusNextHopIpVersion OBJECT-TYPE
    SYNTAX          INTEGER { afInet(2), afInet6(24) }
    MAX-ACCESS      read-only
    STATUS          current
    DESCRIPTION     
            "Next hop TSAP IP address Type."
    ::= { sonusSipMultipleActRegNameStatusEntry 21 }

sonusSipMultipleActRegNameStatusRegistrarIpVersion OBJECT-TYPE
    SYNTAX          INTEGER { afInet(2), afInet6(24) }
    MAX-ACCESS      read-only
    STATUS          current
    DESCRIPTION     
            "SIP Registrar's IP Address Type."
    ::= { sonusSipMultipleActRegNameStatusEntry 22 }

sonusSipCauseMappingProfileTable OBJECT-TYPE
    SYNTAX          SEQUENCE OF SonusSipCauseMappingProfileEntry
    MAX-ACCESS      not-accessible
    STATUS          current
    DESCRIPTION     
            "This table presents the SIP Cause mapping"
    ::= { sonusSipSignallingMIBObjects 47 }

sonusSipCauseMappingProfileEntry OBJECT-TYPE
    SYNTAX          SonusSipCauseMappingProfileEntry
    MAX-ACCESS      not-accessible
    STATUS          current
    DESCRIPTION     
            "This table describes the SIP cause mapping that are configured."
    INDEX           { sonusSipCauseMappingProfileIndex }
    ::= { sonusSipCauseMappingProfileTable 1 }

SonusSipCauseMappingProfileEntry ::=
    SEQUENCE {
        sonusSipCauseMappingProfileIndex Integer32,
        sonusSipCauseMappingProfileName SonusName,
        sonusSipCauseMappingProfileRowStatus    RowStatus,
        sonusSipCauseMappingProfileRegTimeout     Integer32,
        sonusSipCauseMappingProfileRegOverloadCongLimit               Integer32,
        sonusSipCauseMappingProfileRegOverloadTgLimit             Integer32
    }

sonusSipCauseMappingProfileIndex OBJECT-TYPE
    SYNTAX          Integer32 (1..128)
    MAX-ACCESS      read-only
    STATUS          current
    DESCRIPTION     
            "Identifies the SIP cause mapping Profile."
    ::= { sonusSipCauseMappingProfileEntry 1 }

sonusSipCauseMappingProfileName OBJECT-TYPE
    SYNTAX          SonusName
    MAX-ACCESS      read-write
    STATUS          current
    DESCRIPTION     
            "The user name of the SipCauseMapping Profile."
    ::= { sonusSipCauseMappingProfileEntry 2 }

sonusSipCauseMappingProfileRowStatus OBJECT-TYPE
    SYNTAX          RowStatus
    MAX-ACCESS      read-write
    STATUS          current
    DESCRIPTION     
            ""
    ::= { sonusSipCauseMappingProfileEntry 3 }

sonusSipCauseMappingProfileRegTimeout OBJECT-TYPE
    SYNTAX          Integer32 (300..606)
    MAX-ACCESS      read-write
    STATUS          current
    DESCRIPTION     
            "CPC Cause value "
    DEFVAL          { 408 }
    ::= { sonusSipCauseMappingProfileEntry 4 }

sonusSipCauseMappingProfileRegOverloadCongLimit OBJECT-TYPE
    SYNTAX          Integer32 (300..606)
    MAX-ACCESS      read-write
    STATUS          current
    DESCRIPTION     
            "SIP Cause value"
    DEFVAL          { 503 }
    ::= { sonusSipCauseMappingProfileEntry 5 }

sonusSipCauseMappingProfileRegOverloadTgLimit OBJECT-TYPE
    SYNTAX          Integer32 (300..606)
    MAX-ACCESS      read-write
    STATUS          current
    DESCRIPTION     
            "SIP Cause value"
    DEFVAL          { 403 }
    ::= { sonusSipCauseMappingProfileEntry 6 }

sonusSipRegActGroupRegFromAnIpStatusSummaryTable OBJECT-TYPE
    SYNTAX          SEQUENCE OF SonusSipRegActGroupRegFromAnIpStatusSummaryEntry
    MAX-ACCESS      not-accessible
    STATUS          current
    DESCRIPTION     
            "This table presents the active SIP registration status  
             summary for a list of SIP endpoints."
    ::= { sonusSipSignallingMIBObjects 48 }

sonusSipRegActGroupRegFromAnIpStatusSummaryEntry OBJECT-TYPE
    SYNTAX          SonusSipRegActGroupRegFromAnIpStatusSummaryEntry
    MAX-ACCESS      not-accessible
    STATUS          current
    DESCRIPTION     
            "This entry presents the active SIP registration status for
             a SIP endpoint."
    INDEX           { 
                      sonusSipRegActGroupRegFromAnIpStatusSummaryPeerIpAddress, 
                      sonusSipRegActGroupRegFromAnIpStatusSummaryPeerIp6Address, 
                      sonusSipRegActGroupRegFromAnIpStatusSummaryPeerIpVersion, 
                      sonusSipRegActGroupRegFromAnIpStatusSummarySlotIndex, 
                      sonusSipRegActGroupRegFromAnIpStatusSummaryNextRegId }
    ::= { sonusSipRegActGroupRegFromAnIpStatusSummaryTable 1 }

SonusSipRegActGroupRegFromAnIpStatusSummaryEntry ::=
    SEQUENCE {
        sonusSipRegActGroupRegFromAnIpStatusSummarySlotIndex                    SonusSlotIndex,
        sonusSipRegActGroupRegFromAnIpStatusSummaryNextRegId                    Integer32,
        sonusSipRegActGroupRegFromAnIpStatusSummaryAorName                  DisplayString,
        sonusSipRegActGroupRegFromAnIpStatusSummaryState                INTEGER,
        sonusSipRegActGroupRegFromAnIpStatusSummaryNextRegIdIsChild                           Integer32,
        sonusSipRegActGroupRegFromAnIpStatusSummaryPeerIpAddress                        IpAddress,
        sonusSipRegActGroupRegFromAnIpStatusSummaryPeerPort                   Integer32,
        sonusSipRegActGroupRegFromAnIpStatusSummaryNextZoneId                     Integer32,
        sonusSipRegActGroupRegFromAnIpStatusSummaryPeerIp6Address                         Ipv6Address,
        sonusSipRegActGroupRegFromAnIpStatusSummaryPeerIpVersion                        INTEGER
    }

sonusSipRegActGroupRegFromAnIpStatusSummarySlotIndex OBJECT-TYPE
    SYNTAX          SonusSlotIndex
    MAX-ACCESS      read-only
    STATUS          current
    DESCRIPTION     
            "Identifies the target slot."
    ::= { sonusSipRegActGroupRegFromAnIpStatusSummaryEntry 1 }

sonusSipRegActGroupRegFromAnIpStatusSummaryNextRegId OBJECT-TYPE
    SYNTAX          Integer32 (1..1000000)
    MAX-ACCESS      read-only
    STATUS          current
    DESCRIPTION     
            "The next registration ID created for the registration session."
    ::= { sonusSipRegActGroupRegFromAnIpStatusSummaryEntry 2 }

sonusSipRegActGroupRegFromAnIpStatusSummaryAorName OBJECT-TYPE
    SYNTAX          DisplayString (SIZE(0..127))
    MAX-ACCESS      read-only
    STATUS          current
    DESCRIPTION     
            "The E.164 number and host portion plus optional BGID representing the 
             Address Of Record of the registering endpoint."
    ::= { sonusSipRegActGroupRegFromAnIpStatusSummaryEntry 3 }

sonusSipRegActGroupRegFromAnIpStatusSummaryState OBJECT-TYPE
    SYNTAX          INTEGER { null(0), initiating(1), completed(2), 
                        refreshing(3), updating(4), challenged(5), 
                        deleting(6), terminated(7), expired(8) }
    MAX-ACCESS      read-only
    STATUS          current
    DESCRIPTION     
            "The registration state of the endpoint."
    ::= { sonusSipRegActGroupRegFromAnIpStatusSummaryEntry 4 }

sonusSipRegActGroupRegFromAnIpStatusSummaryNextRegIdIsChild OBJECT-TYPE
    SYNTAX          Integer32 (0..1)
    MAX-ACCESS      read-only
    STATUS          current
    DESCRIPTION     
            "The next reg Id is a child ."
    ::= { sonusSipRegActGroupRegFromAnIpStatusSummaryEntry 5 }

sonusSipRegActGroupRegFromAnIpStatusSummaryPeerIpAddress OBJECT-TYPE
    SYNTAX          IpAddress
    MAX-ACCESS      read-only
    STATUS          current
    DESCRIPTION     
            "Next hop TSAP IP Address."
    ::= { sonusSipRegActGroupRegFromAnIpStatusSummaryEntry 6 }

sonusSipRegActGroupRegFromAnIpStatusSummaryPeerPort OBJECT-TYPE
    SYNTAX          Integer32 (1..65535)
    MAX-ACCESS      read-only
    STATUS          current
    DESCRIPTION     
            "Next hop TSAP port number."
    ::= { sonusSipRegActGroupRegFromAnIpStatusSummaryEntry 7 }

sonusSipRegActGroupRegFromAnIpStatusSummaryNextZoneId OBJECT-TYPE
    SYNTAX          Integer32 (1..1000000)
    MAX-ACCESS      read-only
    STATUS          current
    DESCRIPTION     
            "The zone ID created for the registration session."
    ::= { sonusSipRegActGroupRegFromAnIpStatusSummaryEntry 8 }

sonusSipRegActGroupRegFromAnIpStatusSummaryPeerIp6Address OBJECT-TYPE
    SYNTAX          Ipv6Address
    MAX-ACCESS      read-only
    STATUS          current
    DESCRIPTION     
            "Next hop TSAP IPv6 Address."
    ::= { sonusSipRegActGroupRegFromAnIpStatusSummaryEntry 9 }

sonusSipRegActGroupRegFromAnIpStatusSummaryPeerIpVersion OBJECT-TYPE
    SYNTAX          INTEGER { afInet(2), afInet6(24) }
    MAX-ACCESS      read-only
    STATUS          current
    DESCRIPTION     
            "Next hop TSAP IP family"
    ::= { sonusSipRegActGroupRegFromAnIpStatusSummaryEntry 10 }

sonusSipRegistrationDeleteAorConfigObjects OBJECT IDENTIFIER
    ::= { sonusSipSignallingMIBObjects 49 }

sonusSipRegistrationDeleteAorHostName OBJECT-TYPE
    SYNTAX          DisplayString (SIZE(0..63))
    MAX-ACCESS      read-write
    STATUS          current
    DESCRIPTION     
            "Identifies the Hostname for deletion of SIP registration."
    ::= { sonusSipRegistrationDeleteAorConfigObjects 1 }

sonusSipRegistrationDeleteAorPhoneContext OBJECT-TYPE
    SYNTAX          DisplayString (SIZE(0..63))
    MAX-ACCESS      read-write
    STATUS          current
    DESCRIPTION     
            "Identifies the Phone Context"
    ::= { sonusSipRegistrationDeleteAorConfigObjects 2 }

sonusSipRegistrationDeleteAorUser OBJECT-TYPE
    SYNTAX          DisplayString (SIZE(0..63))
    MAX-ACCESS      read-write
    STATUS          current
    DESCRIPTION     
            "Identitifies the User part of AOR"
    ::= { sonusSipRegistrationDeleteAorConfigObjects 3 }

sonusSipOptionTagProfile OBJECT IDENTIFIER
    ::= { sonusSipSignallingMIBObjects 50 }

sonusSipOptionTagProfileNextIndex OBJECT-TYPE
    SYNTAX          Unsigned32
    MAX-ACCESS      not-accessible
    STATUS          current
    DESCRIPTION     
            "The next valid index to use when creating a new sonusSipOptionTagProfileEntry"
    ::= { sonusSipOptionTagProfile 1 }

sonusSipOptionTagProfileTable OBJECT-TYPE
    SYNTAX          SEQUENCE OF SonusSipOptionTagProfileEntry
    MAX-ACCESS      not-accessible
    STATUS          current
    DESCRIPTION     
            "This table contains information about each Option Tag
             Profile configured on the node."
    ::= { sonusSipOptionTagProfile 2 }

sonusSipOptionTagProfileEntry OBJECT-TYPE
    SYNTAX          SonusSipOptionTagProfileEntry
    MAX-ACCESS      not-accessible
    STATUS          current
    DESCRIPTION     
            "This table describes the Option Tag Profile."
    INDEX           { sonusSipOtagProfIndex }
    ::= { sonusSipOptionTagProfileTable 1 }

SonusSipOptionTagProfileEntry ::=
    SEQUENCE {
        sonusSipOtagProfIndex           Unsigned32,
        sonusSipOtagProfName            SonusName,
        sonusSipOtagProfRowStatus       RowStatus,
        sonusSipOtagProfPrefSupported   SonusAdminState,
        sonusSipOtagProfPrefRequire     SonusAdminState,
        sonusSipOtagProfRecipientlistinviteSupported            SonusAdminState,
        sonusSipOtagProfRecipientlistinviteRequire          SonusAdminState,
        sonusSipOtagProfMultiplereferSupported      SonusAdminState,
        sonusSipOtagProfMultiplereferRequire    SonusAdminState,
        sonusSipOtagProfNorefersubSupported   SonusAdminState,
        sonusSipOtagProfNorefersubRequire SonusAdminState,
        sonusSipOtagProfRecipientlistsubscribeSupported               SonusAdminState,
        sonusSipOtagProfRecipientlistsubscribeRequire             SonusAdminState,
        sonusSipOtagProfEventlistSupported  SonusAdminState,
        sonusSipOtagProfEventlistRequire SonusAdminState
    }

sonusSipOtagProfIndex OBJECT-TYPE
    SYNTAX          Unsigned32
    MAX-ACCESS      not-accessible
    STATUS          current
    DESCRIPTION     
            "The index of the SIP Option Tag table entry."
    ::= { sonusSipOptionTagProfileEntry 1 }

sonusSipOtagProfName OBJECT-TYPE
    SYNTAX          SonusName
    MAX-ACCESS      read-write
    STATUS          current
    DESCRIPTION     
            "The name of this SIP Option Tag Profile."
    ::= { sonusSipOptionTagProfileEntry 2 }

sonusSipOtagProfRowStatus OBJECT-TYPE
    SYNTAX          RowStatus
    MAX-ACCESS      read-write
    STATUS          current
    DESCRIPTION     
            "Test "
    ::= { sonusSipOptionTagProfileEntry 3 }

sonusSipOtagProfPrefSupported OBJECT-TYPE
    SYNTAX          SonusAdminState
    MAX-ACCESS      read-write
    STATUS          current
    DESCRIPTION     
            "This parameter controls whether Option Tag PREF is used or generated in SUPPORTED HEADER."
    DEFVAL          { enabled }
    ::= { sonusSipOptionTagProfileEntry 4 }

sonusSipOtagProfPrefRequire OBJECT-TYPE
    SYNTAX          SonusAdminState
    MAX-ACCESS      read-write
    STATUS          current
    DESCRIPTION     
            "This parameter controls whether Option Tag PREF is used or generated in REQUIRE HEADER."
    DEFVAL          { disabled }
    ::= { sonusSipOptionTagProfileEntry 5 }

sonusSipOtagProfRecipientlistinviteSupported OBJECT-TYPE
    SYNTAX          SonusAdminState
    MAX-ACCESS      read-write
    STATUS          current
    DESCRIPTION     
            "This parameter controls whether Option Tag RECIPIENT-LIST-INVITE is used or generated in SUPPORTED HEADER."
    DEFVAL          { enabled }
    ::= { sonusSipOptionTagProfileEntry 6 }

sonusSipOtagProfRecipientlistinviteRequire OBJECT-TYPE
    SYNTAX          SonusAdminState
    MAX-ACCESS      read-write
    STATUS          current
    DESCRIPTION     
            "This parameter controls whether Option Tag RECIPIENT-LIST-INVITE is used or generated in REQUIRE HEADER."
    DEFVAL          { disabled }
    ::= { sonusSipOptionTagProfileEntry 7 }

sonusSipOtagProfMultiplereferSupported OBJECT-TYPE
    SYNTAX          SonusAdminState
    MAX-ACCESS      read-write
    STATUS          current
    DESCRIPTION     
            "This parameter controls whether Option Tag MULTIPLEREFER is used or generated in SUPPORTED HEADER."
    DEFVAL          { enabled }
    ::= { sonusSipOptionTagProfileEntry 8 }

sonusSipOtagProfMultiplereferRequire OBJECT-TYPE
    SYNTAX          SonusAdminState
    MAX-ACCESS      read-write
    STATUS          current
    DESCRIPTION     
            "This parameter controls whether Option Tag MULTIPLEREFER is used or generated in REQUIRE HEADER."
    DEFVAL          { disabled }
    ::= { sonusSipOptionTagProfileEntry 9 }

sonusSipOtagProfNorefersubSupported OBJECT-TYPE
    SYNTAX          SonusAdminState
    MAX-ACCESS      read-write
    STATUS          current
    DESCRIPTION     
            "This parameter controls whether Option Tag NOREFERSUB is used or generated in SUPPORTED HEADER."
    DEFVAL          { enabled }
    ::= { sonusSipOptionTagProfileEntry 10 }

sonusSipOtagProfNorefersubRequire OBJECT-TYPE
    SYNTAX          SonusAdminState
    MAX-ACCESS      read-write
    STATUS          current
    DESCRIPTION     
            "This parameter controls whether Option Tag NOREFERSUB is used or generated in REQUIRE HEADER."
    DEFVAL          { disabled }
    ::= { sonusSipOptionTagProfileEntry 11 }

sonusSipOtagProfRecipientlistsubscribeSupported OBJECT-TYPE
    SYNTAX          SonusAdminState
    MAX-ACCESS      read-write
    STATUS          current
    DESCRIPTION     
            "This parameter controls whether Option Tag RECIPIENT-LIST-SUBSCRIBE is used or generated in SUPPORTED HEADER."
    DEFVAL          { enabled }
    ::= { sonusSipOptionTagProfileEntry 12 }

sonusSipOtagProfRecipientlistsubscribeRequire OBJECT-TYPE
    SYNTAX          SonusAdminState
    MAX-ACCESS      read-write
    STATUS          current
    DESCRIPTION     
            "This parameter controls whether Option Tag RECIPIENT-LIST-SUBSCRIBE is used or generated in REQUIRE HEADER."
    DEFVAL          { disabled }
    ::= { sonusSipOptionTagProfileEntry 13 }

sonusSipOtagProfEventlistSupported OBJECT-TYPE
    SYNTAX          SonusAdminState
    MAX-ACCESS      read-write
    STATUS          current
    DESCRIPTION     
            "This parameter controls whether Option Tag EVENTLIST is used or generated in SUPPORTED HEADER."
    DEFVAL          { enabled }
    ::= { sonusSipOptionTagProfileEntry 14 }

sonusSipOtagProfEventlistRequire OBJECT-TYPE
    SYNTAX          SonusAdminState
    MAX-ACCESS      read-write
    STATUS          current
    DESCRIPTION     
            "This parameter controls whether Option Tag EVENTLIST is used or generated in REQUIRE HEADER."
    DEFVAL          { disabled }
    ::= { sonusSipOptionTagProfileEntry 15 }

sonusSipJipProfile OBJECT IDENTIFIER
    ::= { sonusSipSignallingMIBObjects 51 }

sonusSipJipProfileNextIndex OBJECT-TYPE
    SYNTAX          Unsigned32
    MAX-ACCESS      not-accessible
    STATUS          current
    DESCRIPTION     
            "The next valid index to use when creating a new sonusSipJipProfileEntry"
    ::= { sonusSipJipProfile 1 }

sonusSipJipProfileTable OBJECT-TYPE
    SYNTAX          SEQUENCE OF SonusSipJipProfileEntry
    MAX-ACCESS      not-accessible
    STATUS          current
    DESCRIPTION     
            "This table contains information about each Jip
             Profile configured on the node."
    ::= { sonusSipJipProfile 2 }

sonusSipJipProfileEntry OBJECT-TYPE
    SYNTAX          SonusSipJipProfileEntry
    MAX-ACCESS      not-accessible
    STATUS          current
    DESCRIPTION     
            "This table describes the Jip Profile."
    INDEX           { sonusSipJipProfIndex }
    ::= { sonusSipJipProfileTable 1 }

SonusSipJipProfileEntry ::=
    SEQUENCE {
        sonusSipJipProfIndex            Unsigned32,
        sonusSipJipProfName             SonusName,
        sonusSipJipProfRowStatus        RowStatus,
        sonusSipUseJipFromPAIrn         SonusAdminState,
        sonusSipUseJipFromPAIjip        SonusAdminState,
        sonusSipUseJipFromFROM          SonusAdminState,
        sonusSipSendJipIn               INTEGER,
        sonusSipJipParameterAs          INTEGER,
        sonusSipUseJipFromPDCS          SonusAdminState
    }

sonusSipJipProfIndex OBJECT-TYPE
    SYNTAX          Unsigned32
    MAX-ACCESS      not-accessible
    STATUS          current
    DESCRIPTION     
            "The index of the SIP JIP Profile table entry."
    ::= { sonusSipJipProfileEntry 1 }

sonusSipJipProfName OBJECT-TYPE
    SYNTAX          SonusName
    MAX-ACCESS      read-write
    STATUS          current
    DESCRIPTION     
            "The name of this SIP JIP Profile."
    ::= { sonusSipJipProfileEntry 2 }

sonusSipJipProfRowStatus OBJECT-TYPE
    SYNTAX          RowStatus
    MAX-ACCESS      read-write
    STATUS          current
    DESCRIPTION     
            "Test "
    ::= { sonusSipJipProfileEntry 3 }

sonusSipUseJipFromPAIrn OBJECT-TYPE
    SYNTAX          SonusAdminState
    MAX-ACCESS      read-write
    STATUS          current
    DESCRIPTION     
            "This parameter controls whether JIP value should be extracted from rn parameter in PAI header."
    DEFVAL          { disabled }
    ::= { sonusSipJipProfileEntry 4 }

sonusSipUseJipFromPAIjip OBJECT-TYPE
    SYNTAX          SonusAdminState
    MAX-ACCESS      read-write
    STATUS          current
    DESCRIPTION     
            "This parameter controls whether JIP value should be extracted from jip parameter in PAI header."
    DEFVAL          { disabled }
    ::= { sonusSipJipProfileEntry 5 }

sonusSipUseJipFromFROM OBJECT-TYPE
    SYNTAX          SonusAdminState
    MAX-ACCESS      read-write
    STATUS          current
    DESCRIPTION     
            "This parameter controls whether JIP value should be extracted from rn parameter in FROM header."
    DEFVAL          { disabled }
    ::= { sonusSipJipProfileEntry 6 }

sonusSipSendJipIn OBJECT-TYPE
    SYNTAX          INTEGER { rnPAI(1), jipPAI(2), rnFROM(3), jipPDCS(4) }
    MAX-ACCESS      read-write
    STATUS          current
    DESCRIPTION     
            "This service group attribute specifies how the JIP value shall be send in egress SIP messgae. 
             Default: GSX SIP shall send the JIP value in rn parameter in PAI header."
    DEFVAL          { rnPAI }
    ::= { sonusSipJipProfileEntry 7 }

sonusSipJipParameterAs OBJECT-TYPE
    SYNTAX          INTEGER { userInfo(1), uriParam(2) }
    MAX-ACCESS      read-write
    STATUS          current
    DESCRIPTION     
            "This service group attribute specifies JIP value shall be send as USERINFO or URI PARAM. 
             Default: GSX SIP shall send the JIP value as user Info."
    DEFVAL          { userInfo }
    ::= { sonusSipJipProfileEntry 8 }

sonusSipUseJipFromPDCS OBJECT-TYPE
    SYNTAX          SonusAdminState
    MAX-ACCESS      read-write
    STATUS          current
    DESCRIPTION     
            "This parameter controls whether JIP value should be extracted from jip parameter in PDCS header."
    DEFVAL          { disabled }
    ::= { sonusSipJipProfileEntry 9 }

sonusE164Profile OBJECT IDENTIFIER
    ::= { sonusSipSignallingMIBObjects 52 }

sonusE164ProfileNextIndex OBJECT-TYPE
    SYNTAX          Unsigned32
    MAX-ACCESS      not-accessible
    STATUS          current
    DESCRIPTION     
            "The next valid index to use when creating a new sonusE164ProfileEntry"
    ::= { sonusE164Profile 1 }

sonusE164ProfileTable OBJECT-TYPE
    SYNTAX          SEQUENCE OF SonusE164ProfileEntry
    MAX-ACCESS      not-accessible
    STATUS          current
    DESCRIPTION     
            "This table contains information about each E164 Profile configured on the node."
    ::= { sonusE164Profile 2 }

sonusE164ProfileEntry OBJECT-TYPE
    SYNTAX          SonusE164ProfileEntry
    MAX-ACCESS      not-accessible
    STATUS          current
    DESCRIPTION     
            "This table describes the E164 Profile."
    INDEX           { sonusE164ProfIndex }
    ::= { sonusE164ProfileTable 1 }

SonusE164ProfileEntry ::=
    SEQUENCE {
        sonusE164ProfIndex              Unsigned32,
        sonusE164ProfName               SonusName,
        sonusE164ProfRowStatus          RowStatus,
        sonusE164ProfDigitA             SonusE164ProfileState,
        sonusE164ProfDigitB             SonusE164ProfileState,
        sonusE164ProfDigitC             SonusE164ProfileState,
        sonusE164ProfDigitD             SonusE164ProfileState,
        sonusE164ProfDigitE             SonusE164ProfileState,
        sonusE164ProfDigitF             SonusE164ProfileState,
        sonusE164ProfCharNonFirstPlus   SonusE164ProfileState,
        sonusE164ProfCharStar           SonusE164ProfileState,
        sonusE164ProfCharHash           SonusE164ProfileState,
        sonusE164ProfCharHyphen         SonusE164ProfileState,
        sonusE164ProfCharDot            SonusE164ProfileState,
        sonusE164ProfCharLeftCircularBracket    SonusE164ProfileState,
        sonusE164ProfCharRightCircularBracket     SonusE164ProfileState
    }

sonusE164ProfIndex OBJECT-TYPE
    SYNTAX          Unsigned32
    MAX-ACCESS      not-accessible
    STATUS          current
    DESCRIPTION     
            "The index of the E164 table entry."
    ::= { sonusE164ProfileEntry 1 }

sonusE164ProfName OBJECT-TYPE
    SYNTAX          SonusName
    MAX-ACCESS      read-write
    STATUS          current
    DESCRIPTION     
            "The name of this E164 Profile."
    ::= { sonusE164ProfileEntry 2 }

sonusE164ProfRowStatus OBJECT-TYPE
    SYNTAX          RowStatus
    MAX-ACCESS      read-write
    STATUS          current
    DESCRIPTION     
            "Test"
    ::= { sonusE164ProfileEntry 3 }

sonusE164ProfDigitA OBJECT-TYPE
    SYNTAX          SonusE164ProfileState
    MAX-ACCESS      read-write
    STATUS          current
    DESCRIPTION     
            "E164 profile digit A"
    DEFVAL          { truncate }
    ::= { sonusE164ProfileEntry 4 }

sonusE164ProfDigitB OBJECT-TYPE
    SYNTAX          SonusE164ProfileState
    MAX-ACCESS      read-write
    STATUS          current
    DESCRIPTION     
            "E164 profile digit B"
    DEFVAL          { truncate }
    ::= { sonusE164ProfileEntry 5 }

sonusE164ProfDigitC OBJECT-TYPE
    SYNTAX          SonusE164ProfileState
    MAX-ACCESS      read-write
    STATUS          current
    DESCRIPTION     
            "E164 profile digit C"
    DEFVAL          { truncate }
    ::= { sonusE164ProfileEntry 6 }

sonusE164ProfDigitD OBJECT-TYPE
    SYNTAX          SonusE164ProfileState
    MAX-ACCESS      read-write
    STATUS          current
    DESCRIPTION     
            "E164 profile digit D"
    DEFVAL          { truncate }
    ::= { sonusE164ProfileEntry 7 }

sonusE164ProfDigitE OBJECT-TYPE
    SYNTAX          SonusE164ProfileState
    MAX-ACCESS      read-write
    STATUS          current
    DESCRIPTION     
            "E164 profile digit E"
    DEFVAL          { truncate }
    ::= { sonusE164ProfileEntry 8 }

sonusE164ProfDigitF OBJECT-TYPE
    SYNTAX          SonusE164ProfileState
    MAX-ACCESS      read-write
    STATUS          current
    DESCRIPTION     
            "E164 profile digit F"
    DEFVAL          { truncate }
    ::= { sonusE164ProfileEntry 9 }

sonusE164ProfCharNonFirstPlus OBJECT-TYPE
    SYNTAX          SonusE164ProfileState
    MAX-ACCESS      read-write
    STATUS          current
    DESCRIPTION     
            "E164 profile digit NonFirstPlus"
    DEFVAL          { truncate }
    ::= { sonusE164ProfileEntry 10 }

sonusE164ProfCharStar OBJECT-TYPE
    SYNTAX          SonusE164ProfileState
    MAX-ACCESS      read-write
    STATUS          current
    DESCRIPTION     
            "E164 profile for *"
    DEFVAL          { truncate }
    ::= { sonusE164ProfileEntry 11 }

sonusE164ProfCharHash OBJECT-TYPE
    SYNTAX          SonusE164ProfileState
    MAX-ACCESS      read-write
    STATUS          current
    DESCRIPTION     
            "E164 profile for #"
    DEFVAL          { truncate }
    ::= { sonusE164ProfileEntry 12 }

sonusE164ProfCharHyphen OBJECT-TYPE
    SYNTAX          SonusE164ProfileState
    MAX-ACCESS      read-write
    STATUS          current
    DESCRIPTION     
            "E164 profile for -"
    DEFVAL          { remove }
    ::= { sonusE164ProfileEntry 13 }

sonusE164ProfCharDot OBJECT-TYPE
    SYNTAX          SonusE164ProfileState
    MAX-ACCESS      read-write
    STATUS          current
    DESCRIPTION     
            "E164 profile for ."
    DEFVAL          { remove }
    ::= { sonusE164ProfileEntry 14 }

sonusE164ProfCharLeftCircularBracket OBJECT-TYPE
    SYNTAX          SonusE164ProfileState
    MAX-ACCESS      read-write
    STATUS          current
    DESCRIPTION     
            "E164 profile for ("
    DEFVAL          { remove }
    ::= { sonusE164ProfileEntry 15 }

sonusE164ProfCharRightCircularBracket OBJECT-TYPE
    SYNTAX          SonusE164ProfileState
    MAX-ACCESS      read-write
    STATUS          current
    DESCRIPTION     
            "E164 profile for )"
    DEFVAL          { remove }
    ::= { sonusE164ProfileEntry 16 }

sonusSipTranspProfile OBJECT IDENTIFIER
    ::= { sonusSipSignallingMIBObjects 53 }

sonusSipTranspProfileNextIndex OBJECT-TYPE
    SYNTAX          Unsigned32
    MAX-ACCESS      not-accessible
    STATUS          current
    DESCRIPTION     
            "The next valid index to use when creating a new sonusSipTranspProfileEntry"
    ::= { sonusSipTranspProfile 1 }

sonusSipTranspProfileTable OBJECT-TYPE
    SYNTAX          SEQUENCE OF SonusSipTranspProfileEntry
    MAX-ACCESS      not-accessible
    STATUS          current
    DESCRIPTION     
            "This table contains information about each SIP HEADER TRANSPARENCY PROFILE
             configured to be a associated with a TRUNK GROUP"
    ::= { sonusSipTranspProfile 2 }

sonusSipTranspProfileEntry OBJECT-TYPE
    SYNTAX          SonusSipTranspProfileEntry
    MAX-ACCESS      not-accessible
    STATUS          current
    DESCRIPTION     
            "This table describes the SIP HEADER TRANSPARENCY PROFILE that interconnect
             GSX9000s"
    INDEX           { sonusSipTranspProfileListIndex }
    ::= { sonusSipTranspProfileTable 1 }

SonusSipTranspProfileEntry ::=
    SEQUENCE {
        sonusSipTranspProfileListIndex  Unsigned32,
        sonusSipTranspProfileName       SonusName,
        sonusSipTranspProfileRowStatus  RowStatus
    }

sonusSipTranspProfileListIndex OBJECT-TYPE
    SYNTAX          Unsigned32
    MAX-ACCESS      not-accessible
    STATUS          current
    DESCRIPTION     
            "The index of the SIP HEADER TRANSPARENCY PROFILE."
    ::= { sonusSipTranspProfileEntry 1 }

sonusSipTranspProfileName OBJECT-TYPE
    SYNTAX          SonusName
    MAX-ACCESS      read-write
    STATUS          current
    DESCRIPTION     
            "The name of this SIP HEADER TRANSPARENCY PROFILE."
    ::= { sonusSipTranspProfileEntry 2 }

sonusSipTranspProfileRowStatus OBJECT-TYPE
    SYNTAX          RowStatus
    MAX-ACCESS      read-write
    STATUS          current
    DESCRIPTION     
            ""
    ::= { sonusSipTranspProfileEntry 3 }

sonusSipTranspProfileHdrTable OBJECT-TYPE
    SYNTAX          SEQUENCE OF SonusSipTranspProfileHdrEntry
    MAX-ACCESS      not-accessible
    STATUS          current
    DESCRIPTION     
            "A list of SIP Header Profile entries."
    ::= { sonusSipSignallingMIBObjects 54 }

sonusSipTranspProfileHdrEntry OBJECT-TYPE
    SYNTAX          SonusSipTranspProfileHdrEntry
    MAX-ACCESS      not-accessible
    STATUS          current
    DESCRIPTION     
            " sonusSipTranspProfileHdrEntry contianing SIP Header Details"
    INDEX           { sonusSipTranspProfileHdrProfileIndex, 
                      sonusSipTranspProfileHdrIndex }
    ::= { sonusSipTranspProfileHdrTable 1 }

SonusSipTranspProfileHdrEntry ::=
    SEQUENCE {
        sonusSipTranspProfileHdrProfileIndex    Unsigned32,
        sonusSipTranspProfileHdrIndex   Unsigned32,
        sonusSipTranspProfileHdrRowStatus RowStatus,
        sonusSipTranspProfileHdrName    SonusExtendedName,
        sonusSipTranspProfileHdrIgnoreTransp    INTEGER,
        sonusSipTranspProfileHdrMethodInvite    INTEGER,
        sonusSipTranspProfileHdrMethodOptions     INTEGER,
        sonusSipTranspProfileHdrMethodRefer   INTEGER,
        sonusSipTranspProfileHdrMethodSubscribe       INTEGER,
        sonusSipTranspProfileHdrMethodNotify    INTEGER,
        sonusSipTranspProfileHdrMethodInfo  INTEGER,
        sonusSipTranspProfileHdrMethodRegister      INTEGER,
        sonusSipTranspProfileHdrMethodMessage     INTEGER,
        sonusSipTranspProfileHdrMethodUpdate    INTEGER,
        sonusSipTranspProfileHdrMethodPublish     INTEGER,
        sonusSipTranspProfileHdrMethodBye INTEGER
    }

sonusSipTranspProfileHdrProfileIndex OBJECT-TYPE
    SYNTAX          Unsigned32 (1..32)
    MAX-ACCESS      read-only
    STATUS          current
    DESCRIPTION     
            "Identifies the Transparency profile for this Header entry."
    ::= { sonusSipTranspProfileHdrEntry 1 }

sonusSipTranspProfileHdrIndex OBJECT-TYPE
    SYNTAX          Unsigned32 (1..32)
    MAX-ACCESS      read-only
    STATUS          current
    DESCRIPTION     
            "Identifies the Header within a Header Transparency profile."
    ::= { sonusSipTranspProfileHdrEntry 2 }

sonusSipTranspProfileHdrRowStatus OBJECT-TYPE
    SYNTAX          RowStatus
    MAX-ACCESS      read-write
    STATUS          current
    DESCRIPTION     
            "row status object"
    ::= { sonusSipTranspProfileHdrEntry 3 }

sonusSipTranspProfileHdrName OBJECT-TYPE
    SYNTAX          SonusExtendedName
    MAX-ACCESS      read-write
    STATUS          current
    DESCRIPTION     
            "The header name "
    ::= { sonusSipTranspProfileHdrEntry 4 }

sonusSipTranspProfileHdrIgnoreTransp OBJECT-TYPE
    SYNTAX          INTEGER { disable(0), enable(1) }
    MAX-ACCESS      read-write
    STATUS          current
    DESCRIPTION     
            "Flag to set/unset transparency for Ignore Transparency"
    DEFVAL          { 0 }
    ::= { sonusSipTranspProfileHdrEntry 5 }

sonusSipTranspProfileHdrMethodInvite OBJECT-TYPE
    SYNTAX          INTEGER { disable(0), enable(1) }
    MAX-ACCESS      read-write
    STATUS          current
    DESCRIPTION     
            "Flag to set/unset transparency for Invite Methods"
    DEFVAL          { 0 }
    ::= { sonusSipTranspProfileHdrEntry 6 }

sonusSipTranspProfileHdrMethodOptions OBJECT-TYPE
    SYNTAX          INTEGER { disable(0), enable(1) }
    MAX-ACCESS      read-write
    STATUS          current
    DESCRIPTION     
            "Flag to set/unset transparency for Options Methods"
    DEFVAL          { 0 }
    ::= { sonusSipTranspProfileHdrEntry 7 }

sonusSipTranspProfileHdrMethodRefer OBJECT-TYPE
    SYNTAX          INTEGER { disable(0), enable(1) }
    MAX-ACCESS      read-write
    STATUS          current
    DESCRIPTION     
            "Flag to set/unset transparency for Refer Methods"
    DEFVAL          { 0 }
    ::= { sonusSipTranspProfileHdrEntry 8 }

sonusSipTranspProfileHdrMethodSubscribe OBJECT-TYPE
    SYNTAX          INTEGER { disable(0), enable(1) }
    MAX-ACCESS      read-write
    STATUS          current
    DESCRIPTION     
            "Flag to set/unset transparency for Subscribe Methods"
    DEFVAL          { 0 }
    ::= { sonusSipTranspProfileHdrEntry 9 }

sonusSipTranspProfileHdrMethodNotify OBJECT-TYPE
    SYNTAX          INTEGER { disable(0), enable(1) }
    MAX-ACCESS      read-write
    STATUS          current
    DESCRIPTION     
            "Flag to set/unset transparency for Notify Methods"
    DEFVAL          { 0 }
    ::= { sonusSipTranspProfileHdrEntry 10 }

sonusSipTranspProfileHdrMethodInfo OBJECT-TYPE
    SYNTAX          INTEGER { disable(0), enable(1) }
    MAX-ACCESS      read-write
    STATUS          current
    DESCRIPTION     
            "Flag to set/unset transparency for Info Methods"
    DEFVAL          { 0 }
    ::= { sonusSipTranspProfileHdrEntry 11 }

sonusSipTranspProfileHdrMethodRegister OBJECT-TYPE
    SYNTAX          INTEGER { disable(0), enable(1) }
    MAX-ACCESS      read-write
    STATUS          current
    DESCRIPTION     
            "Flag to set/unset transparency for Register Methods"
    DEFVAL          { 0 }
    ::= { sonusSipTranspProfileHdrEntry 12 }

sonusSipTranspProfileHdrMethodMessage OBJECT-TYPE
    SYNTAX          INTEGER { disable(0), enable(1) }
    MAX-ACCESS      read-write
    STATUS          current
    DESCRIPTION     
            "Flag to set/unset transparency for Message Methods"
    DEFVAL          { 0 }
    ::= { sonusSipTranspProfileHdrEntry 13 }

sonusSipTranspProfileHdrMethodUpdate OBJECT-TYPE
    SYNTAX          INTEGER { disable(0), enable(1) }
    MAX-ACCESS      read-write
    STATUS          current
    DESCRIPTION     
            "Flag to set/unset transparency for Update Methods"
    DEFVAL          { 0 }
    ::= { sonusSipTranspProfileHdrEntry 14 }

sonusSipTranspProfileHdrMethodPublish OBJECT-TYPE
    SYNTAX          INTEGER { disable(0), enable(1) }
    MAX-ACCESS      read-write
    STATUS          current
    DESCRIPTION     
            "Flag to set/unset transparency for Publish Methods"
    DEFVAL          { 0 }
    ::= { sonusSipTranspProfileHdrEntry 15 }

sonusSipTranspProfileHdrMethodBye OBJECT-TYPE
    SYNTAX          INTEGER { disable(0), enable(1) }
    MAX-ACCESS      read-write
    STATUS          current
    DESCRIPTION     
            "Flag to set/unset transparency for Bye Methods"
    DEFVAL          { 0 }
    ::= { sonusSipTranspProfileHdrEntry 16 }

sonusSipSignallingMIBNotifications OBJECT IDENTIFIER
    ::= { sonusSipSignallingMIB 2 }

sonusSipSignallingMIBNotificationsPrefix OBJECT IDENTIFIER
    ::= { sonusSipSignallingMIBNotifications 0 }

sonusSipSignallingMIBNotificationsObjects OBJECT IDENTIFIER
    ::= { sonusSipSignallingMIBNotifications 1 }

sonusSipSigSvcGrpName OBJECT-TYPE
    SYNTAX          SonusNameReference
    MAX-ACCESS      read-only
    STATUS          current
    DESCRIPTION     
            "Name of the SIP service group."
    ::= { sonusSipSignallingMIBNotificationsObjects 1 }

sonusSipCallSigPortOpenNotification NOTIFICATION-TYPE
    OBJECTS         { sonusSipSigPortIpAddress, sonusSipSigPortNum, 
                      sonusEventDescription, sonusEventClass, 
                      sonusEventLevel, sonusSequenceId, sonusEventTime }
    STATUS          current
    DESCRIPTION     
            "This trap indicates that a call signaling port is opened."
    ::= { sonusSipSignallingMIBNotificationsPrefix 1 }

sonusSipCallSigPortCloseNotification NOTIFICATION-TYPE
    OBJECTS         { sonusSipSigPortIpAddress, sonusSipSigPortNum, 
                      sonusEventDescription, sonusEventClass, 
                      sonusEventLevel, sonusSequenceId, sonusEventTime }
    STATUS          current
    DESCRIPTION     
            "This trap indicates that a call signaling port is closed."
    ::= { sonusSipSignallingMIBNotificationsPrefix 2 }

sonusSipSigSvcGrpInServiceNotification NOTIFICATION-TYPE
    OBJECTS         { sonusSipSigSvcGrpName, sonusEventDescription, 
                      sonusEventClass, sonusEventLevel, sonusSequenceId, 
                      sonusEventTime }
    STATUS          current
    DESCRIPTION     
            "This trap indicates that the SIP Service Group was put
             into service by maintenance staff."
    ::= { sonusSipSignallingMIBNotificationsPrefix 3 }

sonusSipSigSvcGrpOutOfServiceNotification NOTIFICATION-TYPE
    OBJECTS         { sonusSipSigSvcGrpName, sonusEventDescription, 
                      sonusEventClass, sonusEventLevel, sonusSequenceId, 
                      sonusEventTime }
    STATUS          current
    DESCRIPTION     
            "This trap indicates that the SIP Service Group was taken
             out of service by maintenance staff."
    ::= { sonusSipSignallingMIBNotificationsPrefix 4 }

sonusSipRegistrantPortChangeNotification NOTIFICATION-TYPE
    OBJECTS         { sonusEventDescription, sonusEventClass, 
                      sonusEventLevel, sonusSequenceId, sonusEventTime }
    STATUS          current
    DESCRIPTION     
            "This trap indicates that at least one SIP registrant
             has a source port number that changed over two or more
             consecutive REGISTER refreshes, possibly indicating that
             the registrant was unreachable from the NBS for a time."
    ::= { sonusSipSignallingMIBNotificationsPrefix 5 }

sonusArsEndPointBlacklistedNotification NOTIFICATION-TYPE
    OBJECTS         { sonusSipArsStatEndpointIpAddress, 
                      sonusSipArsStatEndpointIpPortNum, 
                      sonusSipArsStatSigZoneId, 
                      sonusSipArsStatSigPortNum, 
                      sonusSipArsStatEndpointOwnerId, 
                      sonusEventDescription, sonusEventClass, 
                      sonusEventLevel, sonusSequenceId, sonusEventTime, 
                      sonusSipArsStatEndpointIpv6Address, 
                      sonusSipSigPeerZoneName }
    STATUS          current
    DESCRIPTION     
            "This trap indicates that  one SIP endpoint of the 
             specified ip address, port, sig zone has been blacklisted
             by the ARS service. This indicates the endpoint is unreachable"
    ::= { sonusSipSignallingMIBNotificationsPrefix 6 }

sonusArsEndPointRecoveredNotification NOTIFICATION-TYPE
    OBJECTS         { sonusSipArsStatEndpointIpAddress, 
                      sonusSipArsStatEndpointIpPortNum, 
                      sonusSipArsStatSigZoneId, 
                      sonusSipArsStatSigPortNum, 
                      sonusSipArsStatEndpointOwnerId, 
                      sonusEventDescription, sonusEventClass, 
                      sonusEventLevel, sonusSequenceId, sonusEventTime, 
                      sonusSipArsStatEndpointIpv6Address, 
                      sonusSipSigPeerZoneName }
    STATUS          current
    DESCRIPTION     
            "This trap indicates that  one SIP endpoint of the specified ip address,
             port, sig zone has been recovered from  blacklisting by the ARS service.
             This indicates the endpoint is now reachable"
    ::= { sonusSipSignallingMIBNotificationsPrefix 7 }

sonusArsEndPointsRecoveredNotification NOTIFICATION-TYPE
    OBJECTS         { sonusSipArsStatSigZoneId, 
                      sonusSipArsEndpointRecoveryAll, 
                      sonusEventDescription, sonusEventClass, 
                      sonusEventLevel, sonusSequenceId, sonusEventTime }
    STATUS          current
    DESCRIPTION     
            "This trap indicates that  all SIP endpoints in the specified zone,
             OR all the zones has been recovered from  blacklisting by the ARS service.
             This indicates these endpoints are  now reachable"
    ::= { sonusSipSignallingMIBNotificationsPrefix 8 }

sonusSipSctpAssociationDownNotification NOTIFICATION-TYPE
    OBJECTS         { sonusSipSigPortIpAddress, sonusSipSigPortNum, 
                      sonusEventDescription, sonusEventClass, 
                      sonusEventLevel, sonusSequenceId, sonusEventTime }
    STATUS          current
    DESCRIPTION     
            "This trap indicates that a SCTP association is down."
    ::= { sonusSipSignallingMIBNotificationsPrefix 9 }

sonusSipSctpAssociationFailureNotification NOTIFICATION-TYPE
    OBJECTS         { sonusSipSigPortIpAddress, sonusSipSigPortNum, 
                      sonusEventDescription, sonusEventClass, 
                      sonusEventLevel, sonusSequenceId, sonusEventTime }
    STATUS          current
    DESCRIPTION     
            "This trap indicates that it failed to establish SCTP association."
    ::= { sonusSipSignallingMIBNotificationsPrefix 10 }

sonusSipTgRegLimitReachedNotification NOTIFICATION-TYPE
    OBJECTS         { sonusSipSigServiceGroupTG, sonusEventDescription, 
                      sonusEventClass, sonusEventLevel, sonusSequenceId, 
                      sonusEventTime }
    STATUS          current
    DESCRIPTION     
            "This trap indicates that a Trunk Group's max registration limit
             has reached due to implicit or child registrations."
    ::= { sonusSipSignallingMIBNotificationsPrefix 11 }

sonusSipCallSigPortOpenNotificationV6 NOTIFICATION-TYPE
    OBJECTS         { sonusSipSigPortIp6Address, sonusSipSigPortNum, 
                      sonusEventDescription, sonusEventClass, 
                      sonusEventLevel, sonusSequenceId, sonusEventTime }
    STATUS          current
    DESCRIPTION     
            "This trap indicates that a call signaling port is opened."
    ::= { sonusSipSignallingMIBNotificationsPrefix 12 }

sonusSipCallSigPortCloseNotificationV6 NOTIFICATION-TYPE
    OBJECTS         { sonusSipSigPortIp6Address, sonusSipSigPortNum, 
                      sonusEventDescription, sonusEventClass, 
                      sonusEventLevel, sonusSequenceId, sonusEventTime }
    STATUS          current
    DESCRIPTION     
            "This trap indicates that a call signaling port is closed."
    ::= { sonusSipSignallingMIBNotificationsPrefix 13 }

sonusSipSctpAssociationDownNotificationV6 NOTIFICATION-TYPE
    OBJECTS         { sonusSipSigPortIp6Address, sonusSipSigPortNum, 
                      sonusEventDescription, sonusEventClass, 
                      sonusEventLevel, sonusSequenceId, sonusEventTime }
    STATUS          current
    DESCRIPTION     
            "This trap indicates that a SCTP association is down."
    ::= { sonusSipSignallingMIBNotificationsPrefix 14 }

sonusSipSctpAssociationFailureNotificationV6 NOTIFICATION-TYPE
    OBJECTS         { sonusSipSigPortIp6Address, sonusSipSigPortNum, 
                      sonusEventDescription, sonusEventClass, 
                      sonusEventLevel, sonusSequenceId, sonusEventTime }
    STATUS          current
    DESCRIPTION     
            "This trap indicates that it failed to establish SCTP association."
    ::= { sonusSipSignallingMIBNotificationsPrefix 15 }

sonusArsEndPointBlacklistedNotificationV6 NOTIFICATION-TYPE
    OBJECTS         { sonusSipArsStatEndpointIpv6Address, 
                      sonusSipArsStatEndpointIpPortNum, 
                      sonusSipArsStatSigZoneId, 
                      sonusSipArsStatSigPortNum, 
                      sonusSipArsStatEndpointOwnerId, 
                      sonusEventDescription, sonusEventClass, 
                      sonusEventLevel, sonusSequenceId, sonusEventTime }
    STATUS          current
    DESCRIPTION     
            "This trap indicates that  one SIP endpoint of the 
             specified ip address, port, sig zone has been blacklisted
             by the ARS service. This indicates the endpoint is unreachable"
    ::= { sonusSipSignallingMIBNotificationsPrefix 16 }

sonusArsEndPointRecoveredNotificationV6 NOTIFICATION-TYPE
    OBJECTS         { sonusSipArsStatEndpointIpv6Address, 
                      sonusSipArsStatEndpointIpPortNum, 
                      sonusSipArsStatSigZoneId, 
                      sonusSipArsStatSigPortNum, 
                      sonusSipArsStatEndpointOwnerId, 
                      sonusEventDescription, sonusEventClass, 
                      sonusEventLevel, sonusSequenceId, sonusEventTime }
    STATUS          current
    DESCRIPTION     
            "This trap indicates that  one SIP endpoint of the specified ip address,
             port, sig zone has been recovered from  blacklisting by the ARS service.
             This indicates the endpoint is now reachable"
    ::= { sonusSipSignallingMIBNotificationsPrefix 17 }

sonusSipTranspProfileISNotification NOTIFICATION-TYPE
    OBJECTS         { sonusSipTranspProfileName, sonusEventDescription, 
                      sonusEventClass, sonusEventLevel, sonusSequenceId, 
                      sonusEventTime }
    STATUS          current
    DESCRIPTION     
            "This trap indicates that the SIP Service Group was put
             into service by maintenance staff."
    ::= { sonusSipSignallingMIBNotificationsPrefix 18 }

sonusSipTranspProfileOOSNotification NOTIFICATION-TYPE
    OBJECTS         { sonusSipTranspProfileName, sonusEventDescription, 
                      sonusEventClass, sonusEventLevel, sonusSequenceId, 
                      sonusEventTime }
    STATUS          current
    DESCRIPTION     
            "This trap indicates that the SIP Service Group was taken
             out of service by maintenance staff."
    ::= { sonusSipSignallingMIBNotificationsPrefix 19 }

END -- end of module SONUS-SIP-SIGNALLING-MIB.
