--
-- This SMIv2 module has been generated by smidump 0.2-cvs. Do not edit.
--

SONUS-NODE-MIB DEFINITIONS ::= BEGIN

IMPORTS
    Ipv6Address
        FROM IPV6-TC
    Integer32, IpAddress, MODULE-IDENTITY, NOTIFICATION-TYPE, 
    OBJECT-TYPE
        FROM SNMPv2-SMI
    DateAndTime, DisplayString, RowStatus, TEXTUAL-CONVENTION
        FROM SNMPv2-TC
    sonusEventClass, sonusEventDescription, sonusEventLevel, 
    sonusEventTime, sonusPimIndex, sonusPortIndex, sonusSequenceId, 
    sonusShelfIndex, sonusSlotIndex
        FROM SONUS-COMMON-MIB
    sonusSystemMIBs
        FROM SONUS-SMI
    AdapterTypeID, HwTypeID, PimTypeID, ServerFunctionType, ServerTypeID, 
    SonusAccessLevel, SonusAdminAction, SonusAdminState, 
    SonusMnsSlotIndex, SonusName, SonusNameReference, SonusPimIndex, 
    SonusServiceState, SonusSfpIndex, SonusShelfIndex, SonusSlotIndex, 
    SonusSoftwareVersion
        FROM SONUS-TC;

sonusNodeMIB MODULE-IDENTITY
    LAST-UPDATED    "201509120000Z"
    ORGANIZATION    
            "Sonus Networks, Inc."
    CONTACT-INFO    
            "   Customer Support    
             Sonus Networks, Inc.
             7 Technology Park Drive
             Westford, MA 01886
             USA
             
             Tel: 978-614-8100
             Fax: 978-614-8609"
    DESCRIPTION     
            "The MIB Module for Node Management."
    ::= { sonusSystemMIBs 1 }


SonusSoftwareDownloadStatus ::= TEXTUAL-CONVENTION
    STATUS          current
    DESCRIPTION     
            "Status of Software download"
    SYNTAX          INTEGER { idle(0), success(1), busy(2), 
                        internalfailure(3), serverunreachable(4), 
                        loginfailure(5), dataconnectionfailure(6), 
                        filenotfound(7), datatransferfailure(8), 
                        invalidpackage(9), useraborted(10), 
                        systemaborted(11) }

sonusNodeMIBObjects OBJECT IDENTIFIER
    ::= { sonusNodeMIB 1 }

sonusNode OBJECT IDENTIFIER
    ::= { sonusNodeMIBObjects 1 }

sonusNodeAdmnObjects OBJECT IDENTIFIER
    ::= { sonusNode 1 }

sonusNodeAdmnShelves OBJECT-TYPE
    SYNTAX          Integer32 (1..6)
    MAX-ACCESS      read-only
    STATUS          current
    DESCRIPTION     
            "The number of shelves configured to be present in this 
             node."
    ::= { sonusNodeAdmnObjects 1 }

sonusNodeAdmnTelnetLogin OBJECT-TYPE
    SYNTAX          SonusAdminState
    MAX-ACCESS      read-write
    STATUS          current
    DESCRIPTION     
            "State of the CLI telnet listener"
    DEFVAL          { disabled }
    ::= { sonusNodeAdmnObjects 2 }

sonusNodeAdmnSshLogin OBJECT-TYPE
    SYNTAX          SonusAdminState
    MAX-ACCESS      read-write
    STATUS          current
    DESCRIPTION     
            "State of the CLI Ssh listener"
    DEFVAL          { enabled }
    ::= { sonusNodeAdmnObjects 3 }

sonusNodeAdmnTelnetNifGroupName OBJECT-TYPE
    SYNTAX          SonusNameReference
    MAX-ACCESS      read-write
    STATUS          current
    DESCRIPTION     
            "The NIF Group which this Telnet application port belongs to."
    ::= { sonusNodeAdmnObjects 4 }

sonusNodeAdmnSshNifGroupName OBJECT-TYPE
    SYNTAX          SonusNameReference
    MAX-ACCESS      read-write
    STATUS          current
    DESCRIPTION     
            "The NIF Group which this Ssh application port belongs to."
    ::= { sonusNodeAdmnObjects 5 }

sonusNodeAdmnNtpNifGroupName OBJECT-TYPE
    SYNTAX          SonusNameReference
    MAX-ACCESS      read-write
    STATUS          current
    DESCRIPTION     
            "The NIF Group which this NTP application port belongs to."
    ::= { sonusNodeAdmnObjects 6 }

sonusNodeAdmnSnmpAgentNifGroupName OBJECT-TYPE
    SYNTAX          SonusNameReference
    MAX-ACCESS      read-write
    STATUS          current
    DESCRIPTION     
            "The NIF Group which this SNMP Agent application port belongs to."
    ::= { sonusNodeAdmnObjects 7 }

sonusNodeAdmnSnmpTrapNifGroupName OBJECT-TYPE
    SYNTAX          SonusNameReference
    MAX-ACCESS      read-write
    STATUS          current
    DESCRIPTION     
            "The NIF Group which this Trap Manager (SNMP) application port belongs to."
    ::= { sonusNodeAdmnObjects 8 }

sonusNodeAdmnFtpServerNifGroupName OBJECT-TYPE
    SYNTAX          SonusNameReference
    MAX-ACCESS      read-write
    STATUS          current
    DESCRIPTION     
            "The NIF Group which this FTP Server application port belongs to."
    ::= { sonusNodeAdmnObjects 9 }

sonusNodeAdmnFtpClientNifGroupName OBJECT-TYPE
    SYNTAX          SonusNameReference
    MAX-ACCESS      read-write
    STATUS          current
    DESCRIPTION     
            "The NIF Group which this FTP Client application port belongs to."
    ::= { sonusNodeAdmnObjects 10 }

sonusNodeAdmnNfsClientNifGroupName OBJECT-TYPE
    SYNTAX          SonusNameReference
    MAX-ACCESS      read-write
    STATUS          current
    DESCRIPTION     
            "The NIF Group which this NFS Client application port belongs to."
    ::= { sonusNodeAdmnObjects 11 }

sonusNodeAdmnPortmapperNifGroupName OBJECT-TYPE
    SYNTAX          SonusNameReference
    MAX-ACCESS      read-write
    STATUS          current
    DESCRIPTION     
            "The NIF Group which this Portmapper application port belongs to."
    ::= { sonusNodeAdmnObjects 12 }

sonusNodeAdmnTelnetNetworkAccess OBJECT-TYPE
    SYNTAX          INTEGER { none(1), nifgroup(2), anynif(3) }
    MAX-ACCESS      read-write
    STATUS          current
    DESCRIPTION     
            "The Network access type of the telnet application. Option NONE is basically as good as disabled; NIFGROUP uses only the interfaces in the NIF group; ANYNIF would use any of the interfaces"
    DEFVAL          { nifgroup }
    ::= { sonusNodeAdmnObjects 13 }

sonusNodeAdmnSshNetworkAccess OBJECT-TYPE
    SYNTAX          INTEGER { none(1), nifgroup(2), anynif(3) }
    MAX-ACCESS      read-write
    STATUS          current
    DESCRIPTION     
            "The Network access type of the ssh application. Option NONE is basically as good as disabled; NIFGROUP uses only the interfaces in the NIF group; ANYNIF would use any of the interfaces"
    DEFVAL          { nifgroup }
    ::= { sonusNodeAdmnObjects 14 }

sonusNodeAdmnNtpNetworkAccess OBJECT-TYPE
    SYNTAX          INTEGER { none(1), nifgroup(2), anynif(3) }
    MAX-ACCESS      read-write
    STATUS          current
    DESCRIPTION     
            "The Network access type of  the NTP application. Option NONE is basically as good as disabled; NIFGROUP uses only the interfaces in the NIF group; ANYNIF would use any of the interfaces"
    DEFVAL          { nifgroup }
    ::= { sonusNodeAdmnObjects 15 }

sonusNodeAdmnSnmpAgentNetworkAccess OBJECT-TYPE
    SYNTAX          INTEGER { none(1), nifgroup(2), anynif(3) }
    MAX-ACCESS      read-write
    STATUS          current
    DESCRIPTION     
            "The Network access type of the SNMP Agent application. Option NONE is basically as good as disabled; NIFGROUP uses only the interfaces in the NIF group; ANYNIF would use any of the interfaces"
    DEFVAL          { nifgroup }
    ::= { sonusNodeAdmnObjects 16 }

sonusNodeAdmnSnmpTrapNetworkAccess OBJECT-TYPE
    SYNTAX          INTEGER { none(1), nifgroup(2), anynif(3) }
    MAX-ACCESS      read-write
    STATUS          current
    DESCRIPTION     
            "The Network access type of the TM (SNMP Trap) application. Option NONE is basically as good as disabled; NIFGROUP uses only the interfaces in the NIF group; ANYNIF would use any of the interfaces"
    DEFVAL          { nifgroup }
    ::= { sonusNodeAdmnObjects 17 }

sonusNodeAdmnFtpServerNetworkAccess OBJECT-TYPE
    SYNTAX          INTEGER { none(1), nifgroup(2), anynif(3) }
    MAX-ACCESS      read-write
    STATUS          current
    DESCRIPTION     
            "The Network access type of the FTP Server application. Option NONE is basically as good as disabled; NIFGROUP uses only the interfaces in the NIF group; ANYNIF would use any of the interfaces"
    DEFVAL          { nifgroup }
    ::= { sonusNodeAdmnObjects 18 }

sonusNodeAdmnFtpClientNetworkAccess OBJECT-TYPE
    SYNTAX          INTEGER { none(1), nifgroup(2), anynif(3) }
    MAX-ACCESS      read-write
    STATUS          current
    DESCRIPTION     
            "The Network access type of the FTP Client application. Option NONE is basically as good as disabled; NIFGROUP uses only the interfaces in the NIF group; ANYNIF would use any of the interfaces"
    DEFVAL          { nifgroup }
    ::= { sonusNodeAdmnObjects 19 }

sonusNodeAdmnNfsClientNetworkAccess OBJECT-TYPE
    SYNTAX          INTEGER { none(1), nifgroup(2), anynif(3) }
    MAX-ACCESS      read-write
    STATUS          current
    DESCRIPTION     
            "The Network access type of the NFS Client application. Option NONE is basically as good as disabled; NIFGROUP uses only the interfaces in the NIF group; ANYNIF would use any of the interfaces"
    DEFVAL          { nifgroup }
    ::= { sonusNodeAdmnObjects 20 }

sonusNodeAdmnPortmapperNetworkAccess OBJECT-TYPE
    SYNTAX          INTEGER { none(1), nifgroup(2), anynif(3) }
    MAX-ACCESS      read-write
    STATUS          current
    DESCRIPTION     
            "The Network access type of the Portmapper application. Option NONE is basically as good as disabled; NIFGROUP uses only the interfaces in the NIF group; ANYNIF would use any of the interfaces"
    DEFVAL          { nifgroup }
    ::= { sonusNodeAdmnObjects 21 }

sonusNodeAdmnSshCipherModeCbcState OBJECT-TYPE
    SYNTAX          SonusAdminState
    MAX-ACCESS      read-write
    STATUS          current
    DESCRIPTION     
            "State of ssh CBC Cipher MOde "
    DEFVAL          { enabled }
    ::= { sonusNodeAdmnObjects 22 }

sonusNodeTempSetDuration OBJECT-TYPE
    SYNTAX          Integer32 (0..65535)
    MAX-ACCESS      read-write
    STATUS          current
    DESCRIPTION     
            "Temperature set threshold duration limit for getting the critical alarm.The range is 0 to 65535 Sec"
    DEFVAL          { 0 }
    ::= { sonusNodeAdmnObjects 23 }

sonusNodeTempSetThresValue OBJECT-TYPE
    SYNTAX          Integer32 (31..59)
    MAX-ACCESS      read-write
    STATUS          current
    DESCRIPTION     
            "Temperature set threshold limit for getting the critical alarm.The range is 31 to 59"
    DEFVAL          { 55 }
    ::= { sonusNodeAdmnObjects 24 }

sonusNodeTempClearDuration OBJECT-TYPE
    SYNTAX          Integer32 (0..65535)
    MAX-ACCESS      read-write
    STATUS          current
    DESCRIPTION     
            "Temperature clear threshold duration limit for clearing the critical alarm.The range is 0 to 65535 Sec"
    DEFVAL          { 0 }
    ::= { sonusNodeAdmnObjects 25 }

sonusNodeTempClearThresValue OBJECT-TYPE
    SYNTAX          Integer32 (31..59)
    MAX-ACCESS      read-write
    STATUS          current
    DESCRIPTION     
            "Temperature clear threshold temperature limit for clearing the critical alarm.The range is 31 to 59"
    DEFVAL          { 53 }
    ::= { sonusNodeAdmnObjects 26 }

sonusNodeTempFeatureState OBJECT-TYPE
    SYNTAX          INTEGER { enabled(1), disabled(0) }
    MAX-ACCESS      read-write
    STATUS          current
    DESCRIPTION     
            "Temperature feature Enable or Disable"
    DEFVAL          { disabled }
    ::= { sonusNodeAdmnObjects 27 }

sonusNodeStatusObjects OBJECT IDENTIFIER
    ::= { sonusNode 2 }

sonusNodeStatShelvesPresent OBJECT-TYPE
    SYNTAX          Integer32 (1..6)
    MAX-ACCESS      read-only
    STATUS          current
    DESCRIPTION     
            "The number of shelves currently present in this node."
    ::= { sonusNodeStatusObjects 1 }

sonusNodeStatNextIfIndex OBJECT-TYPE
    SYNTAX          Integer32
    MAX-ACCESS      read-only
    STATUS          current
    DESCRIPTION     
            "This MIB object identifies the next ifIndex to
             use in the creation of an interface.  This MIB
             object directly corresponds to the ifIndex MIB
             object in the ifTable.  A value of 0 means that
             no next ifIndex is currently available."
    ::= { sonusNodeStatusObjects 2 }

sonusNodeStatMgmtStatus OBJECT-TYPE
    SYNTAX          INTEGER { manageable(1), 
                        softwareUpgradeInProgress(2), 
                        softwareUpgradeFailed(3) }
    MAX-ACCESS      read-only
    STATUS          current
    DESCRIPTION     
            "Identifies if this node can be effectively managed
             by a network management system.  A value of 'manageable'
             indicates that it can be; the other values indicate
             that a significant operation is in progress and that
             a network management system should minimize any
             requests of this node."
    ::= { sonusNodeStatusObjects 3 }

sonusNodeShelfAdmnTable OBJECT-TYPE
    SYNTAX          SEQUENCE OF SonusNodeShelfAdmnEntry
    MAX-ACCESS      not-accessible
    STATUS          current
    DESCRIPTION     
            "This table contains information about each shelf which is
             configured to be a member of the node.  This table describes 
             the configured characteristics of each shelf, including the
             shelve's identity (sonusNodeShelfAdmnIpaddr1 and
             sonusNodeShelfAdmnIpaddr2).  A row must be created by the 
             manager for every slave shelf that is to join the master shelf
             as part of the node.  Slave shelves which do not have correct
             entries in this table, can not join the node. 
             
             A management entity may create rows for shelves that are
             anticipated to join the node in the future."
    ::= { sonusNode 3 }

sonusNodeShelfAdmnEntry OBJECT-TYPE
    SYNTAX          SonusNodeShelfAdmnEntry
    MAX-ACCESS      not-accessible
    STATUS          current
    DESCRIPTION     
            "This table describes the shelves that are configured as members
             of the GSX9000 Switch node."
    INDEX           { sonusNodeShelfAdmnIndex }
    ::= { sonusNodeShelfAdmnTable 1 }

SonusNodeShelfAdmnEntry ::=
    SEQUENCE {
        sonusNodeShelfAdmnIndex         SonusShelfIndex,
        sonusNodeShelfAdmnState         SonusAdminState,
        sonusNodeShelfAdmnIpaddr1       IpAddress,
        sonusNodeShelfAdmnIpaddr2       IpAddress,
        sonusNodeShelfAdmn48VdcAState   SonusAdminState,
        sonusNodeShelfAdmn48VdcBState   SonusAdminState,
        sonusNodeShelfAdmnStatus        INTEGER,
        sonusNodeShelfAdmnRestart       INTEGER,
        sonusNodeShelfAdmnRowStatus     RowStatus,
        sonusNodeShelfAdmnMode          SonusServiceState
    }

sonusNodeShelfAdmnIndex OBJECT-TYPE
    SYNTAX          SonusShelfIndex
    MAX-ACCESS      read-only
    STATUS          current
    DESCRIPTION     
            "Identifies the target shelf in the node.  Each node may
             be compprised of one or more shelves.  The maximum number
             of shelves allowed in a node is six."
    ::= { sonusNodeShelfAdmnEntry 1 }

sonusNodeShelfAdmnState OBJECT-TYPE
    SYNTAX          SonusAdminState
    MAX-ACCESS      read-create
    STATUS          current
    DESCRIPTION     
            "The configured state of the target shelf in the node."
    ::= { sonusNodeShelfAdmnEntry 2 }

sonusNodeShelfAdmnIpaddr1 OBJECT-TYPE
    SYNTAX          IpAddress
    MAX-ACCESS      read-create
    STATUS          current
    DESCRIPTION     
            "The IP Address of the shelf.  This value identifies the shelf
             that may join the node.  Each shelf has two IP addresses that
             it may be reached by.  This is the first of those two addresses.
             Note that it is not possible to change this object on the master
             shelf.  That would be tantamount to changing that shelf's IP
             address."
    ::= { sonusNodeShelfAdmnEntry 3 }

sonusNodeShelfAdmnIpaddr2 OBJECT-TYPE
    SYNTAX          IpAddress
    MAX-ACCESS      read-create
    STATUS          current
    DESCRIPTION     
            "The IP Address of the shelf.  This value identifies the shelf
             that may join the node.  Each shelf has two IP addresses that
             it may be reached by.  This is the second of those two addresses.
             Note that it is not possible to change this object on the master
             shelf.  That would be tantamount to changing the shelf's IP
             address."
    ::= { sonusNodeShelfAdmnEntry 4 }

sonusNodeShelfAdmn48VdcAState OBJECT-TYPE
    SYNTAX          SonusAdminState
    MAX-ACCESS      read-create
    STATUS          current
    DESCRIPTION     
            "The configured state of the shelf's 48 VDC A-power supply.
             Indicates whether the A supply SHOULD be present.  This object
             is not capable of disabling a connected supply."
    ::= { sonusNodeShelfAdmnEntry 5 }

sonusNodeShelfAdmn48VdcBState OBJECT-TYPE
    SYNTAX          SonusAdminState
    MAX-ACCESS      read-create
    STATUS          current
    DESCRIPTION     
            "The configured state of the shelf's 48 VDC B-power supply.
             Indicates whether the B supply SHOULD be present.  This object
             is not capable of disabling a connected supply."
    ::= { sonusNodeShelfAdmnEntry 6 }

sonusNodeShelfAdmnStatus OBJECT-TYPE
    SYNTAX          INTEGER { absent(1), detected(2), accepted(3), 
                        shuttingDown(4) }
    MAX-ACCESS      read-only
    STATUS          current
    DESCRIPTION     
            "The status of the indexed shelf in the GSX9000 node.  If the value
             of this object is not accepted(3) or shuttingDown(4), then the objects
             			in Sonus Shelf Status table are unavailable.  The value of this object
             			does not reach accepted(3) until after the slave shelf has contacted
             			the master shelf, and has successfully joined the node.  A value of
             			shuttingDown(4) indicates the shelf will be unavailable shortly."
    ::= { sonusNodeShelfAdmnEntry 7 }

sonusNodeShelfAdmnRestart OBJECT-TYPE
    SYNTAX          INTEGER { unknown(1), restart(2), shutdown(3), 
                        restartForced(4) }
    MAX-ACCESS      read-create
    STATUS          current
    DESCRIPTION     
            "This object is used to reset a shelf in the node.  The object
             causes the management servers on the indexed shelf to perform the 
             indicated operation.  The restart(2) operation causes the management
             servers to reboot.  The shutdown(3) operation causes the management
             servers to disable power to all cards on the indexed shelf, including
             themselves.  
             
             The shutdown(3) operation requires physical intervention to re-power
             the shelf.
             
             This object always reads as unknown(1)."
    ::= { sonusNodeShelfAdmnEntry 8 }

sonusNodeShelfAdmnRowStatus OBJECT-TYPE
    SYNTAX          RowStatus
    MAX-ACCESS      read-create
    STATUS          current
    DESCRIPTION     
            "This object indicates the row status for this table."
    ::= { sonusNodeShelfAdmnEntry 9 }

sonusNodeShelfAdmnMode OBJECT-TYPE
    SYNTAX          SonusServiceState
    MAX-ACCESS      read-create
    STATUS          current
    DESCRIPTION     
            "A shelf that is outOfService will not accept any new calls.
             When taken out of service, its active calls will be allowed
             to dry up.  This object is not persistent across reboots."
    ::= { sonusNodeShelfAdmnEntry 10 }

sonusNodeShelfStatTable OBJECT-TYPE
    SYNTAX          SEQUENCE OF SonusNodeShelfStatEntry
    MAX-ACCESS      not-accessible
    STATUS          current
    DESCRIPTION     
            "This table contains status information about each shelf 
             in the GSX9000 Switch node.  Shelves within the node can
             can be configured before they are physically attached to
             the node.  Shelves that are attached may not be powered
             or correctly configured as a slave.  Therefore, it is possible
             that a slave shelf can not be detected, and is absent. 
             
             The value of sonusNodeShelfAdmnStatus indicates the availability
             of this shelf.  If the sonusNodeShelfAdmnStatus value for the
             index shelf does not indicate a status value of 'accepted', 
             then this status table is not available."
    ::= { sonusNode 4 }

sonusNodeShelfStatEntry OBJECT-TYPE
    SYNTAX          SonusNodeShelfStatEntry
    MAX-ACCESS      not-accessible
    STATUS          current
    DESCRIPTION     
            "This table describes the shelves that are configured as members
             of the GSX9000 Switch node."
    INDEX           { sonusNodeShelfStatIndex }
    ::= { sonusNodeShelfStatTable 1 }

SonusNodeShelfStatEntry ::=
    SEQUENCE {
        sonusNodeShelfStatIndex         SonusShelfIndex,
        sonusNodeShelfStatSlots         SonusSlotIndex,
        sonusNodeShelfStatSerialNumber  DisplayString,
        sonusNodeShelfStatType          INTEGER,
        sonusNodeShelfStatFan           INTEGER,
        sonusNodeShelfStat48VAStatus    INTEGER,
        sonusNodeShelfStat48VBStatus    INTEGER,
        sonusNodeShelfStatBackplane     HwTypeID,
        sonusNodeShelfStatBootCount     Integer32,
        sonusNodeShelfStatTemperature   Integer32,
        sonusNodeShelfStatFanSpeed      INTEGER,
        sonusNodeShelfStat48VAType      INTEGER,
        sonusNodeShelfStat48VBType      INTEGER
    }

sonusNodeShelfStatIndex OBJECT-TYPE
    SYNTAX          SonusShelfIndex
    MAX-ACCESS      read-only
    STATUS          current
    DESCRIPTION     
            "Identifies the target shelf within the node.  Returns the same 
             value as sonusNodeShelfStatIndex, the index into this instance."
    ::= { sonusNodeShelfStatEntry 1 }

sonusNodeShelfStatSlots OBJECT-TYPE
    SYNTAX          SonusSlotIndex
    MAX-ACCESS      read-only
    STATUS          current
    DESCRIPTION     
            "The number of physical slots present in this shelf."
    ::= { sonusNodeShelfStatEntry 2 }

sonusNodeShelfStatSerialNumber OBJECT-TYPE
    SYNTAX          DisplayString (SIZE(1..10))
    MAX-ACCESS      read-only
    STATUS          current
    DESCRIPTION     
            "Identifies the Sonus serial number for this shelf."
    ::= { sonusNodeShelfStatEntry 3 }

sonusNodeShelfStatType OBJECT-TYPE
    SYNTAX          INTEGER { slave(1), master(2) }
    MAX-ACCESS      read-only
    STATUS          current
    DESCRIPTION     
            "Identifies the Sonus shelf type.  A shelf may be either the master
             shelf for the node, or it may be one of several slave shelves in the
             node.  Every node contains exactly one master shelf.  The master shelf
             in the management focal point for the node."
    ::= { sonusNodeShelfStatEntry 4 }

sonusNodeShelfStatFan OBJECT-TYPE
    SYNTAX          INTEGER { notPresent(1), controllerFailure(2), 
                        singleFailure(3), multipleFailures(4), 
                        powerFailure(5), operational(6) }
    MAX-ACCESS      read-only
    STATUS          current
    DESCRIPTION     
            "Identifies the status of the shelf's fan tray.  A controllerFailure(2)
             indicates that the fan status can not be obtained.  In that case in can
             not be determined if the fans are operational, or experiencing other
             failures as well."
    ::= { sonusNodeShelfStatEntry 5 }

sonusNodeShelfStat48VAStatus OBJECT-TYPE
    SYNTAX          INTEGER { outOfSpec(1), normal(2) }
    MAX-ACCESS      read-only
    STATUS          current
    DESCRIPTION     
            "The status of the shelf's 48 VDC A-power supply.
             outOfSpec and normal were previously defined as absent and normal"
    ::= { sonusNodeShelfStatEntry 6 }

sonusNodeShelfStat48VBStatus OBJECT-TYPE
    SYNTAX          INTEGER { outOfSpec(1), normal(2) }
    MAX-ACCESS      read-only
    STATUS          current
    DESCRIPTION     
            "The status of the shelf's 48 VDC B-power supply.
             outOfSpec and normal were previously defined as absent and normal"
    ::= { sonusNodeShelfStatEntry 7 }

sonusNodeShelfStatBackplane OBJECT-TYPE
    SYNTAX          HwTypeID
    MAX-ACCESS      read-only
    STATUS          current
    DESCRIPTION     
            "The hardware type ID of the backplane in this shelf."
    ::= { sonusNodeShelfStatEntry 8 }

sonusNodeShelfStatBootCount OBJECT-TYPE
    SYNTAX          Integer32
    MAX-ACCESS      read-only
    STATUS          current
    DESCRIPTION     
            "Specifies the number of times that this shelf has been
             booted.  The boot count is specified from the perspective
             of the active management module running in the indexed
             shelf."
    ::= { sonusNodeShelfStatEntry 9 }

sonusNodeShelfStatTemperature OBJECT-TYPE
    SYNTAX          Integer32
    MAX-ACCESS      read-only
    STATUS          current
    DESCRIPTION     
            "Indicates the temperature being sensed at this shelf's intake
             manifold.  The temperature is indicated in Celcius."
    ::= { sonusNodeShelfStatEntry 10 }

sonusNodeShelfStatFanSpeed OBJECT-TYPE
    SYNTAX          INTEGER { normal(1), high(2) }
    MAX-ACCESS      read-only
    STATUS          current
    DESCRIPTION     
            "Indicates the speed of the fan."
    ::= { sonusNodeShelfStatEntry 11 }

sonusNodeShelfStat48VAType OBJECT-TYPE
    SYNTAX          INTEGER { absent(1), ac(2), dc(3) }
    MAX-ACCESS      read-only
    STATUS          current
    DESCRIPTION     
            "Identify chassis 48V A power supply type. "
    ::= { sonusNodeShelfStatEntry 12 }

sonusNodeShelfStat48VBType OBJECT-TYPE
    SYNTAX          INTEGER { absent(1), ac(2), dc(3) }
    MAX-ACCESS      read-only
    STATUS          current
    DESCRIPTION     
            "Identify chassis 48V B power supply type. "
    ::= { sonusNodeShelfStatEntry 13 }

sonusNodeSrvrAdmnTable OBJECT-TYPE
    SYNTAX          SEQUENCE OF SonusNodeSrvrAdmnEntry
    MAX-ACCESS      not-accessible
    STATUS          current
    DESCRIPTION     
            "The server module ADMN table describes the configuration of
             each server module slot in an indexed shelf.  A slot in a shelf,
             MUST be configured to accept a particular server module HWTYPE.
             If the wrong type of server module is detected in the slot, that
             server module will not be allowed to complete its boot process.
             
             			All server modules are held in the RESET state until that
             			server module's state is set to ENABLED.  A server module must
             have its state set to DISABLED, before the row can be deleted.
             
             The row must be deleted, and re-created in order to change the
             HWTYPE of the row.  The server module mode must be set to 
             OUTOFSERVICE before the row's state can be set to DISABLED.
             
             			Deleting a row in this table, clears the server module hardware
             type association for this slot.  THIS IS A MAJOR CONFIGURATION
             CHANGE.  All configured parameters associated with this slot are
             permanently lost when the server module is deleted.
             
             A server module can not be deleted, until it's state has been set
             to DISABLED.  A row's default value for state is DISABLED. The 
             server module located in the slot is immediately placed in reset 
             when its state is set to disabled."
    ::= { sonusNode 5 }

sonusNodeSrvrAdmnEntry OBJECT-TYPE
    SYNTAX          SonusNodeSrvrAdmnEntry
    MAX-ACCESS      not-accessible
    STATUS          current
    DESCRIPTION     
            ""
    INDEX           { sonusNodeSrvrAdmnShelfIndex, 
                      sonusNodeSrvrAdmnSlotIndex }
    ::= { sonusNodeSrvrAdmnTable 1 }

SonusNodeSrvrAdmnEntry ::=
    SEQUENCE {
        sonusNodeSrvrAdmnShelfIndex     SonusShelfIndex,
        sonusNodeSrvrAdmnSlotIndex      SonusSlotIndex,
        sonusNodeSrvrAdmnHwType         ServerTypeID,
        sonusNodeSrvrAdmnState          SonusAdminState,
        sonusNodeSrvrAdmnMode           SonusServiceState,
        sonusNodeSrvrAdmnAction         INTEGER,
        sonusNodeSrvrAdmnDryupLimit     Integer32,
        sonusNodeSrvrAdmnDumpState      SonusAdminState,
        sonusNodeSrvrAdmnRowStatus      RowStatus,
        sonusNodeSrvrAdmnRedundancyRole INTEGER,
        sonusNodeSrvrAdmnAdapHwType     AdapterTypeID,
        sonusNodeSrvrAdmnSpecialFunction ServerFunctionType
    }

sonusNodeSrvrAdmnShelfIndex OBJECT-TYPE
    SYNTAX          SonusShelfIndex
    MAX-ACCESS      read-only
    STATUS          current
    DESCRIPTION     
            "Identifies the target shelf.  Returns the same value as sonusNodeShelfStatIndex,
             which was used to index into this table."
    ::= { sonusNodeSrvrAdmnEntry 1 }

sonusNodeSrvrAdmnSlotIndex OBJECT-TYPE
    SYNTAX          SonusSlotIndex
    MAX-ACCESS      read-only
    STATUS          current
    DESCRIPTION     
            "Identifies the target slot within the shelf."
    ::= { sonusNodeSrvrAdmnEntry 2 }

sonusNodeSrvrAdmnHwType OBJECT-TYPE
    SYNTAX          ServerTypeID
    MAX-ACCESS      read-write
    STATUS          current
    DESCRIPTION     
            "Identifies the type of server module the indexed slot has been
             configured to accept.  Server modules other than this type are
             rejected by the System Manager.  This object is required to create
             a row instance."
    ::= { sonusNodeSrvrAdmnEntry 3 }

sonusNodeSrvrAdmnState OBJECT-TYPE
    SYNTAX          SonusAdminState
    MAX-ACCESS      read-write
    STATUS          current
    DESCRIPTION     
            "A server module must be enabled before System Manager will fully
             recognize it.  The server module must be disabled before the server
             module can be deleted."
    DEFVAL          { disabled }
    ::= { sonusNodeSrvrAdmnEntry 4 }

sonusNodeSrvrAdmnMode OBJECT-TYPE
    SYNTAX          SonusServiceState
    MAX-ACCESS      read-write
    STATUS          current
    DESCRIPTION     
            "A server module which is outOfService will not accept new calls.
             When taken out of service, its active calls may either be dried
             up or terminated, depending on the action specified.  Server
             modules are created with a mode of inService.  A server module
             must be outOfService in order to change its state to disabled."
    DEFVAL          { inService }
    ::= { sonusNodeSrvrAdmnEntry 5 }

sonusNodeSrvrAdmnAction OBJECT-TYPE
    SYNTAX          INTEGER { dryUp(1), force(2), undefined(3) }
    MAX-ACCESS      read-write
    STATUS          current
    DESCRIPTION     
            "The type of call termination action to perform when a server module 
             is taken out of service.  An action of dryUp or force can be specified.  
             The value, dryUp, allows the active calls on the server module to terminate
             on their own accord.   The value, force, causes the calls to be 
             immediately terminated.   The value, undefined, is an internal state.   
             Setting this object to, undefined, will result in a failure."
    DEFVAL          { force }
    ::= { sonusNodeSrvrAdmnEntry 6 }

sonusNodeSrvrAdmnDryupLimit OBJECT-TYPE
    SYNTAX          Integer32 (0..65535)
    MAX-ACCESS      read-write
    STATUS          current
    DESCRIPTION     
            "Server module dryup limit, specified in minutes.  If the server 
             module has not dried up by the time this limit expires, the
             remaining active calls are abruptly terminated.  A dryup limit of
             zero indicates that the system will wait forever for the dryup to
             complete."
    DEFVAL          { 0 }
    ::= { sonusNodeSrvrAdmnEntry 7 }

sonusNodeSrvrAdmnDumpState OBJECT-TYPE
    SYNTAX          SonusAdminState
    MAX-ACCESS      read-write
    STATUS          current
    DESCRIPTION     
            "Indicates if a server module will create a crashblock file when a
             critical error which prevents the module from continuing, has occured."
    DEFVAL          { enabled }
    ::= { sonusNodeSrvrAdmnEntry 8 }

sonusNodeSrvrAdmnRowStatus OBJECT-TYPE
    SYNTAX          RowStatus
    MAX-ACCESS      read-write
    STATUS          current
    DESCRIPTION     
            "Deleting a server module will place that slot in reset.  All 
             configuration parameters associated with the server module in
             this slot are destroyed."
    ::= { sonusNodeSrvrAdmnEntry 9 }

sonusNodeSrvrAdmnRedundancyRole OBJECT-TYPE
    SYNTAX          INTEGER { normal(1), redundant(2) }
    MAX-ACCESS      read-write
    STATUS          current
    DESCRIPTION     
            "Specifies the redundancy role this server module will play.  This
             object is required to create a row instance."
    ::= { sonusNodeSrvrAdmnEntry 10 }

sonusNodeSrvrAdmnAdapHwType OBJECT-TYPE
    SYNTAX          AdapterTypeID
    MAX-ACCESS      read-write
    STATUS          current
    DESCRIPTION     
            "Identifies the type of adapter module the indexed slot has been
             configured to accept.  Adapter modules other than this type are
             rejected by the System Manager.  This object is required to create
             a row instance."
    ::= { sonusNodeSrvrAdmnEntry 11 }

sonusNodeSrvrAdmnSpecialFunction OBJECT-TYPE
    SYNTAX          ServerFunctionType
    MAX-ACCESS      read-write
    STATUS          current
    DESCRIPTION     
            "Specifies the logical function for this server module.  This object may
             be specified only at row creation time, but is not required.   If not
             specified, an appropriate default value will be assigned based on the
             server and adapter hardware types.  A value of default(1) is not
             accepted or used."
    ::= { sonusNodeSrvrAdmnEntry 12 }

sonusNodeSlotTable OBJECT-TYPE
    SYNTAX          SEQUENCE OF SonusNodeSlotEntry
    MAX-ACCESS      not-accessible
    STATUS          current
    DESCRIPTION     
            "The node slot table describes"
    ::= { sonusNode 6 }

sonusNodeSlotEntry OBJECT-TYPE
    SYNTAX          SonusNodeSlotEntry
    MAX-ACCESS      not-accessible
    STATUS          current
    DESCRIPTION     
            ""
    INDEX           { sonusNodeSlotShelfIndex, sonusNodeSlotIndex }
    ::= { sonusNodeSlotTable 1 }

SonusNodeSlotEntry ::=
    SEQUENCE {
        sonusNodeSlotShelfIndex         SonusShelfIndex,
        sonusNodeSlotIndex              SonusSlotIndex,
        sonusNodeSlotState              INTEGER,
        sonusNodeSlotHwType             HwTypeID,
        sonusNodeSlotHwTypeRev          Integer32,
        sonusNodeSlotPower              INTEGER,
        sonusNodeSlotAdapState          INTEGER,
        sonusNodeSlotAdapHwType         HwTypeID
    }

sonusNodeSlotShelfIndex OBJECT-TYPE
    SYNTAX          SonusShelfIndex
    MAX-ACCESS      read-only
    STATUS          current
    DESCRIPTION     
            "Identifies the indexed shelf.  Returns the same value as 
             sonusNodeShelfStatIndex, which is used to index into this
             table."
    ::= { sonusNodeSlotEntry 1 }

sonusNodeSlotIndex OBJECT-TYPE
    SYNTAX          SonusSlotIndex
    MAX-ACCESS      read-only
    STATUS          current
    DESCRIPTION     
            "Identifies the indexed slot within the shelf."
    ::= { sonusNodeSlotEntry 2 }

sonusNodeSlotState OBJECT-TYPE
    SYNTAX          INTEGER { unknown(1), empty(2), inserted(3), 
                        reset(4), boot(5), sonicId(6), coreDump(7), 
                        holdOff(8), loading(9), activating(10), 
                        activated(11), running(12), faulted(13), 
                        powerOff(14), powerFail(15) }
    MAX-ACCESS      read-only
    STATUS          current
    DESCRIPTION     
            "Identifies the operational state of the indexed slot in the shelf."
    ::= { sonusNodeSlotEntry 3 }

sonusNodeSlotHwType OBJECT-TYPE
    SYNTAX          HwTypeID
    MAX-ACCESS      read-only
    STATUS          current
    DESCRIPTION     
            "Identifies the hardware type of the server module which
             was detected in the slot.  Valid only if the sonusNodeSlotState
             is greater than inserted(2)."
    ::= { sonusNodeSlotEntry 4 }

sonusNodeSlotHwTypeRev OBJECT-TYPE
    SYNTAX          Integer32
    MAX-ACCESS      read-only
    STATUS          current
    DESCRIPTION     
            "Identifies the hardware type revision of the server module which
             was detected in the slot.  Valid only if the sonusNodeSlotState
             is greater than inserted(2)."
    ::= { sonusNodeSlotEntry 5 }

sonusNodeSlotPower OBJECT-TYPE
    SYNTAX          INTEGER { unknown(1), powerFault(2), powerOK(3) }
    MAX-ACCESS      read-only
    STATUS          current
    DESCRIPTION     
            "Identifies the server modules power mode.  If the slot
             state is empty, the power status is unknown(1)."
    ::= { sonusNodeSlotEntry 6 }

sonusNodeSlotAdapState OBJECT-TYPE
    SYNTAX          INTEGER { unknown(1), empty(2), present(3), 
                        faulted(4) }
    MAX-ACCESS      read-only
    STATUS          current
    DESCRIPTION     
            "Identifies the adapter state of the indexed slot in the shelf."
    ::= { sonusNodeSlotEntry 7 }

sonusNodeSlotAdapHwType OBJECT-TYPE
    SYNTAX          HwTypeID
    MAX-ACCESS      read-only
    STATUS          current
    DESCRIPTION     
            "Identifies the hardware type of the adapter module which
             was detected in the slot.  Valid only if the sonusNodeSlotAdapState
             is present(3)."
    ::= { sonusNodeSlotEntry 8 }

sonusNodeSrvrStatTable OBJECT-TYPE
    SYNTAX          SEQUENCE OF SonusNodeSrvrStatEntry
    MAX-ACCESS      not-accessible
    STATUS          current
    DESCRIPTION     
            "The node server status table describes the status of the indexed
             server module in the node.  This table is unavailable if the 
             sonusNodeShelfStatStatus object indicates that this slot is 
             empty.
             
             			If the sonusNodeSrvrStatType object returns either 'absent' or 
             'unknown' the value of all other objects within this table are 
             indeterministic."
    ::= { sonusNode 7 }

sonusNodeSrvrStatEntry OBJECT-TYPE
    SYNTAX          SonusNodeSrvrStatEntry
    MAX-ACCESS      not-accessible
    STATUS          current
    DESCRIPTION     
            ""
    INDEX           { sonusNodeSrvrStatShelfIndex, 
                      sonusNodeSrvrStatSlotIndex }
    ::= { sonusNodeSrvrStatTable 1 }

SonusNodeSrvrStatEntry ::=
    SEQUENCE {
        sonusNodeSrvrStatShelfIndex     SonusShelfIndex,
        sonusNodeSrvrStatSlotIndex      SonusSlotIndex,
        sonusNodeSrvrStatMiddVersion    Integer32,
        sonusNodeSrvrStatHwType         HwTypeID,
        sonusNodeSrvrStatSerialNum      DisplayString,
        sonusNodeSrvrStatPartNum        DisplayString,
        sonusNodeSrvrStatPartNumRev     DisplayString,
        sonusNodeSrvrStatMfgDate        DisplayString,
        sonusNodeSrvrStatFlashVersion   DisplayString,
        sonusNodeSrvrStatSwVersion      DisplayString,
        sonusNodeSrvrStatBuildNum       Integer32,
        sonusNodeSrvrStatMode           INTEGER,
        sonusNodeSrvrStatTemperature    Integer32,
        sonusNodeSrvrStatMemUtilization Integer32,
        sonusNodeSrvrStatCpuUtilization Integer32,
        sonusNodeSrvrStatHwTypeRev      Integer32,
        sonusNodeSrvrStatSwVersionCode  SonusSoftwareVersion,
        sonusNodeSrvrStatEpldRev        Integer32,
        sonusNodeSrvrStatHostName       DisplayString,
        sonusNodeSrvrStatUserName       DisplayString,
        sonusNodeSrvrStatViewName       DisplayString,
        sonusNodeSrvrStatTotalMem       Integer32,
        sonusNodeSrvrStatFreeMem        Integer32,
        sonusNodeSrvrStatTotalSharedMem Integer32,
        sonusNodeSrvrStatFreeSharedMem  Integer32,
        sonusNodeSrvrStatUpTime         Integer32,
        sonusNodeSrvrAvgCpuUsageOneMinute Integer32,
        sonusNodeSrvrAvgCpuUsageFiveMinutes   Integer32,
        sonusNodeSrvrAvgMemUsageOneMinute Integer32,
        sonusNodeSrvrAvgMemUsageFiveMinutes   Integer32
    }

sonusNodeSrvrStatShelfIndex OBJECT-TYPE
    SYNTAX          SonusShelfIndex
    MAX-ACCESS      read-only
    STATUS          current
    DESCRIPTION     
            "Identifies the target shelf.  Returns the same value as sonusNodeShelfStatIndex,
             which was used to index into this table."
    ::= { sonusNodeSrvrStatEntry 1 }

sonusNodeSrvrStatSlotIndex OBJECT-TYPE
    SYNTAX          SonusSlotIndex
    MAX-ACCESS      read-only
    STATUS          current
    DESCRIPTION     
            "Identifies the target slot within the shelf."
    ::= { sonusNodeSrvrStatEntry 2 }

sonusNodeSrvrStatMiddVersion OBJECT-TYPE
    SYNTAX          Integer32
    MAX-ACCESS      read-only
    STATUS          current
    DESCRIPTION     
            "Identifies the version of the MIDD EEPROM on this server
             module."
    ::= { sonusNodeSrvrStatEntry 3 }

sonusNodeSrvrStatHwType OBJECT-TYPE
    SYNTAX          HwTypeID
    MAX-ACCESS      read-only
    STATUS          current
    DESCRIPTION     
            "Identifies the type of server module in the indexed slot."
    ::= { sonusNodeSrvrStatEntry 4 }

sonusNodeSrvrStatSerialNum OBJECT-TYPE
    SYNTAX          DisplayString (SIZE(1..10))
    MAX-ACCESS      read-only
    STATUS          current
    DESCRIPTION     
            "Identifies the serial number of the server module.  This is the
             serial number assigned to the server module at manufacture."
    ::= { sonusNodeSrvrStatEntry 5 }

sonusNodeSrvrStatPartNum OBJECT-TYPE
    SYNTAX          DisplayString (SIZE(1..10))
    MAX-ACCESS      read-only
    STATUS          current
    DESCRIPTION     
            "Identifies the part number of the module.  This is the
             part number assigned to the module at manufacture."
    ::= { sonusNodeSrvrStatEntry 6 }

sonusNodeSrvrStatPartNumRev OBJECT-TYPE
    SYNTAX          DisplayString (SIZE(1..2))
    MAX-ACCESS      read-only
    STATUS          current
    DESCRIPTION     
            "Identifies the manufacture part number revision level of 
             the server module."
    ::= { sonusNodeSrvrStatEntry 7 }

sonusNodeSrvrStatMfgDate OBJECT-TYPE
    SYNTAX          DisplayString (SIZE(1..10))
    MAX-ACCESS      read-only
    STATUS          current
    DESCRIPTION     
            "The date this server module assembly was manufactured."
    ::= { sonusNodeSrvrStatEntry 8 }

sonusNodeSrvrStatFlashVersion OBJECT-TYPE
    SYNTAX          DisplayString (SIZE(1..32))
    MAX-ACCESS      read-only
    STATUS          current
    DESCRIPTION     
            "Identifies the version of the firmware within the
             non-volatile FLASH device on this server module."
    ::= { sonusNodeSrvrStatEntry 9 }

sonusNodeSrvrStatSwVersion OBJECT-TYPE
    SYNTAX          DisplayString (SIZE(1..32))
    MAX-ACCESS      read-only
    STATUS          current
    DESCRIPTION     
            "Identifies the version of the runtime software
             application this is currently executing on this
             server module."
    ::= { sonusNodeSrvrStatEntry 10 }

sonusNodeSrvrStatBuildNum OBJECT-TYPE
    SYNTAX          Integer32
    MAX-ACCESS      read-only
    STATUS          current
    DESCRIPTION     
            "Identifies the build number of this software version."
    ::= { sonusNodeSrvrStatEntry 11 }

sonusNodeSrvrStatMode OBJECT-TYPE
    SYNTAX          INTEGER { standby(1), active(2) }
    MAX-ACCESS      read-only
    STATUS          current
    DESCRIPTION     
            "Identifies the operational status of the module in the 
             indexed slot."
    ::= { sonusNodeSrvrStatEntry 12 }

sonusNodeSrvrStatTemperature OBJECT-TYPE
    SYNTAX          Integer32
    MAX-ACCESS      read-only
    STATUS          current
    DESCRIPTION     
            "Indicates the current Celcius temperature being sensed by
             the server module in the indexed slot."
    ::= { sonusNodeSrvrStatEntry 13 }

sonusNodeSrvrStatMemUtilization OBJECT-TYPE
    SYNTAX          Integer32
    MAX-ACCESS      read-only
    STATUS          current
    DESCRIPTION     
            "The current memory utilization of this server module.  The
             value returned is a number from 0 to 100, representing the
             percentage of memory utilization.  Note that this number can be
             somewhat misleading as many data structures are pre-allocated
             to ensure that the server modules maximum load capacity can be 
             acheived and maintained.  This may result is relatively high
             memory utilizations under fairly low load."
    ::= { sonusNodeSrvrStatEntry 14 }

sonusNodeSrvrStatCpuUtilization OBJECT-TYPE
    SYNTAX          Integer32
    MAX-ACCESS      read-only
    STATUS          current
    DESCRIPTION     
            "The current CPU utilization of this server module.  The
             value returned is a number from 0 to 100, representing the
             percentage of CPU utilization."
    ::= { sonusNodeSrvrStatEntry 15 }

sonusNodeSrvrStatHwTypeRev OBJECT-TYPE
    SYNTAX          Integer32
    MAX-ACCESS      read-only
    STATUS          current
    DESCRIPTION     
            "The hardware type revision number of this server module."
    ::= { sonusNodeSrvrStatEntry 16 }

sonusNodeSrvrStatSwVersionCode OBJECT-TYPE
    SYNTAX          SonusSoftwareVersion
    MAX-ACCESS      read-only
    STATUS          current
    DESCRIPTION     
            "Octet string that identifies the version of the runtime
             software application that is currently executing on this
             server module:
             
             Byte(s)  Code
             -------  ----
             0        major version
             1        minor version
             2        release version
             3        type (1:alpha, 2:beta, 3:release, 4:special)
             4-5      type number"
    ::= { sonusNodeSrvrStatEntry 17 }

sonusNodeSrvrStatEpldRev OBJECT-TYPE
    SYNTAX          Integer32
    MAX-ACCESS      read-only
    STATUS          current
    DESCRIPTION     
            "The EPLD revision level of this server module.  An overall
             number which represents the total level of the server module."
    ::= { sonusNodeSrvrStatEntry 18 }

sonusNodeSrvrStatHostName OBJECT-TYPE
    SYNTAX          DisplayString (SIZE(1..64))
    MAX-ACCESS      read-only
    STATUS          current
    DESCRIPTION     
            "Identifies the host name that software load of this module
             had been built on."
    ::= { sonusNodeSrvrStatEntry 19 }

sonusNodeSrvrStatUserName OBJECT-TYPE
    SYNTAX          DisplayString (SIZE(1..32))
    MAX-ACCESS      read-only
    STATUS          current
    DESCRIPTION     
            "Identifies the user who builds software load of this module."
    ::= { sonusNodeSrvrStatEntry 20 }

sonusNodeSrvrStatViewName OBJECT-TYPE
    SYNTAX          DisplayString (SIZE(1..32))
    MAX-ACCESS      read-only
    STATUS          current
    DESCRIPTION     
            "Identifies the viewName used for software build."
    ::= { sonusNodeSrvrStatEntry 21 }

sonusNodeSrvrStatTotalMem OBJECT-TYPE
    SYNTAX          Integer32
    MAX-ACCESS      read-only
    STATUS          current
    DESCRIPTION     
            "Indicates the total memory size of the server module."
    ::= { sonusNodeSrvrStatEntry 22 }

sonusNodeSrvrStatFreeMem OBJECT-TYPE
    SYNTAX          Integer32
    MAX-ACCESS      read-only
    STATUS          current
    DESCRIPTION     
            "Indicates the total memory available on the server module."
    ::= { sonusNodeSrvrStatEntry 23 }

sonusNodeSrvrStatTotalSharedMem OBJECT-TYPE
    SYNTAX          Integer32
    MAX-ACCESS      read-only
    STATUS          current
    DESCRIPTION     
            "Indicates the total shared memory size of the server module."
    ::= { sonusNodeSrvrStatEntry 24 }

sonusNodeSrvrStatFreeSharedMem OBJECT-TYPE
    SYNTAX          Integer32
    MAX-ACCESS      read-only
    STATUS          current
    DESCRIPTION     
            "Indicates the total shared memory available on the server module."
    ::= { sonusNodeSrvrStatEntry 25 }

sonusNodeSrvrStatUpTime OBJECT-TYPE
    SYNTAX          Integer32
    MAX-ACCESS      read-only
    STATUS          current
    DESCRIPTION     
            "Indicates the server module uptime in seconds."
    ::= { sonusNodeSrvrStatEntry 26 }

sonusNodeSrvrAvgCpuUsageOneMinute OBJECT-TYPE
    SYNTAX          Integer32
    MAX-ACCESS      read-only
    STATUS          current
    DESCRIPTION     
            "Indicates the average CPU utilization for the last minute."
    ::= { sonusNodeSrvrStatEntry 27 }

sonusNodeSrvrAvgCpuUsageFiveMinutes OBJECT-TYPE
    SYNTAX          Integer32
    MAX-ACCESS      read-only
    STATUS          current
    DESCRIPTION     
            "Indicates the average CPU utilization for the last five minutes."
    ::= { sonusNodeSrvrStatEntry 28 }

sonusNodeSrvrAvgMemUsageOneMinute OBJECT-TYPE
    SYNTAX          Integer32
    MAX-ACCESS      read-only
    STATUS          current
    DESCRIPTION     
            "Indicates the average memory utilization for the last minute."
    ::= { sonusNodeSrvrStatEntry 29 }

sonusNodeSrvrAvgMemUsageFiveMinutes OBJECT-TYPE
    SYNTAX          Integer32
    MAX-ACCESS      read-only
    STATUS          current
    DESCRIPTION     
            "Indicates the average memory utilization for the last five minutes."
    ::= { sonusNodeSrvrStatEntry 30 }

sonusNodeAdapStatTable OBJECT-TYPE
    SYNTAX          SEQUENCE OF SonusNodeAdapStatEntry
    MAX-ACCESS      not-accessible
    STATUS          current
    DESCRIPTION     
            "The node adapter status table describes the status of the indexed
             adapter module in the node.  This table is unavailable if the 
             sonusNodeSlotAdapState object indicates that this slot is 
             unknown, empty or faulted."
    ::= { sonusNode 11 }

sonusNodeAdapStatEntry OBJECT-TYPE
    SYNTAX          SonusNodeAdapStatEntry
    MAX-ACCESS      not-accessible
    STATUS          current
    DESCRIPTION     
            ""
    INDEX           { sonusNodeAdapStatShelfIndex, 
                      sonusNodeAdapStatSlotIndex }
    ::= { sonusNodeAdapStatTable 1 }

SonusNodeAdapStatEntry ::=
    SEQUENCE {
        sonusNodeAdapStatShelfIndex     SonusShelfIndex,
        sonusNodeAdapStatSlotIndex      SonusSlotIndex,
        sonusNodeAdapStatMiddVersion    Integer32,
        sonusNodeAdapStatHwType         HwTypeID,
        sonusNodeAdapStatHwTypeRev      Integer32,
        sonusNodeAdapStatSerialNum      DisplayString,
        sonusNodeAdapStatPartNum        DisplayString,
        sonusNodeAdapStatPartNumRev     DisplayString,
        sonusNodeAdapStatMfgDate        DisplayString
    }

sonusNodeAdapStatShelfIndex OBJECT-TYPE
    SYNTAX          SonusShelfIndex
    MAX-ACCESS      read-only
    STATUS          current
    DESCRIPTION     
            "Identifies the target shelf."
    ::= { sonusNodeAdapStatEntry 1 }

sonusNodeAdapStatSlotIndex OBJECT-TYPE
    SYNTAX          SonusSlotIndex
    MAX-ACCESS      read-only
    STATUS          current
    DESCRIPTION     
            "Identifies the target slot within the shelf."
    ::= { sonusNodeAdapStatEntry 2 }

sonusNodeAdapStatMiddVersion OBJECT-TYPE
    SYNTAX          Integer32
    MAX-ACCESS      read-only
    STATUS          current
    DESCRIPTION     
            "Identifies the version of the MIDD EEPROM on this adapter
             module."
    ::= { sonusNodeAdapStatEntry 3 }

sonusNodeAdapStatHwType OBJECT-TYPE
    SYNTAX          HwTypeID
    MAX-ACCESS      read-only
    STATUS          current
    DESCRIPTION     
            "Identifies the type of adapter module in the indexed slot."
    ::= { sonusNodeAdapStatEntry 4 }

sonusNodeAdapStatHwTypeRev OBJECT-TYPE
    SYNTAX          Integer32
    MAX-ACCESS      read-only
    STATUS          current
    DESCRIPTION     
            "Identifies the hardware type revision of the adapter module
             detected in the slot."
    ::= { sonusNodeAdapStatEntry 5 }

sonusNodeAdapStatSerialNum OBJECT-TYPE
    SYNTAX          DisplayString (SIZE(1..10))
    MAX-ACCESS      read-only
    STATUS          current
    DESCRIPTION     
            "Identifies the serial number of the adapter module.  This is the
             serial number assigned to the card at manufacture."
    ::= { sonusNodeAdapStatEntry 6 }

sonusNodeAdapStatPartNum OBJECT-TYPE
    SYNTAX          DisplayString (SIZE(1..10))
    MAX-ACCESS      read-only
    STATUS          current
    DESCRIPTION     
            "Identifies the part number of the adapter module.  This is the
             part number assigned to the card at manufacture."
    ::= { sonusNodeAdapStatEntry 7 }

sonusNodeAdapStatPartNumRev OBJECT-TYPE
    SYNTAX          DisplayString (SIZE(1..2))
    MAX-ACCESS      read-only
    STATUS          current
    DESCRIPTION     
            "Identifies the assembly revision level of the adapter module."
    ::= { sonusNodeAdapStatEntry 8 }

sonusNodeAdapStatMfgDate OBJECT-TYPE
    SYNTAX          DisplayString (SIZE(1..10))
    MAX-ACCESS      read-only
    STATUS          current
    DESCRIPTION     
            "The date this adapter module was manufactured."
    ::= { sonusNodeAdapStatEntry 9 }

sonusNodeSlotAdmnTable OBJECT-TYPE
    SYNTAX          SEQUENCE OF SonusNodeSlotAdmnEntry
    MAX-ACCESS      not-accessible
    STATUS          current
    DESCRIPTION     
            "The node slot admn table provides physical manipulation
             of a slot location in a shelf."
    ::= { sonusNode 12 }

sonusNodeSlotAdmnEntry OBJECT-TYPE
    SYNTAX          SonusNodeSlotAdmnEntry
    MAX-ACCESS      not-accessible
    STATUS          current
    DESCRIPTION     
            ""
    INDEX           { sonusNodeSlotAdmnShelfIndex, 
                      sonusNodeSlotAdmnSlotIndex }
    ::= { sonusNodeSlotAdmnTable 1 }

SonusNodeSlotAdmnEntry ::=
    SEQUENCE {
        sonusNodeSlotAdmnShelfIndex     SonusShelfIndex,
        sonusNodeSlotAdmnSlotIndex      SonusSlotIndex,
        sonusNodeSlotAdmnReset          INTEGER
    }

sonusNodeSlotAdmnShelfIndex OBJECT-TYPE
    SYNTAX          SonusShelfIndex
    MAX-ACCESS      read-only
    STATUS          current
    DESCRIPTION     
            "Identifies the target shelf."
    ::= { sonusNodeSlotAdmnEntry 1 }

sonusNodeSlotAdmnSlotIndex OBJECT-TYPE
    SYNTAX          SonusSlotIndex
    MAX-ACCESS      read-only
    STATUS          current
    DESCRIPTION     
            "Identifies the target slot within the shelf."
    ::= { sonusNodeSlotAdmnEntry 2 }

sonusNodeSlotAdmnReset OBJECT-TYPE
    SYNTAX          INTEGER { undefined(1), reset(2), coredump(3) }
    MAX-ACCESS      read-write
    STATUS          current
    DESCRIPTION     
            "Setting this object to reset(2) or coredump(3), will physically reset 
             the server module installed in the indexed slot.  This
             object always reads as undefined(1).   This object bypasses
             all consistency and safety checks.  This object is 
             intended for evaluation testing."
    ::= { sonusNodeSlotAdmnEntry 3 }

sonusNodePimAdmnTable OBJECT-TYPE
    SYNTAX          SEQUENCE OF SonusNodePimAdmnEntry
    MAX-ACCESS      not-accessible
    STATUS          current
    DESCRIPTION     
            "The PIM module ADMN table describes the configuration of
             each Pim module in a slot. A pim modules MUST be configured 
             to accept a particular HWTYPE."
    ::= { sonusNode 13 }

sonusNodePimAdmnEntry OBJECT-TYPE
    SYNTAX          SonusNodePimAdmnEntry
    MAX-ACCESS      not-accessible
    STATUS          current
    DESCRIPTION     
            "An entry in PIM Admn table"
    INDEX           { sonusNodePimAdmnShelfIndex, 
                      sonusNodePimAdmnSlotIndex, 
                      sonusNodePimAdmnPimIndex }
    ::= { sonusNodePimAdmnTable 1 }

SonusNodePimAdmnEntry ::=
    SEQUENCE {
        sonusNodePimAdmnShelfIndex      SonusShelfIndex,
        sonusNodePimAdmnSlotIndex       SonusSlotIndex,
        sonusNodePimAdmnPimIndex        SonusPimIndex,
        sonusNodePimAdmnHwType          PimTypeID,
        sonusNodePimAdmnRowStatus       RowStatus
    }

sonusNodePimAdmnShelfIndex OBJECT-TYPE
    SYNTAX          SonusShelfIndex
    MAX-ACCESS      read-only
    STATUS          current
    DESCRIPTION     
            "Identifies the target shelf."
    ::= { sonusNodePimAdmnEntry 1 }

sonusNodePimAdmnSlotIndex OBJECT-TYPE
    SYNTAX          SonusSlotIndex
    MAX-ACCESS      read-only
    STATUS          current
    DESCRIPTION     
            "Identifies the target slot within the shelf."
    ::= { sonusNodePimAdmnEntry 2 }

sonusNodePimAdmnPimIndex OBJECT-TYPE
    SYNTAX          SonusPimIndex
    MAX-ACCESS      read-only
    STATUS          current
    DESCRIPTION     
            "Identifies the target pim within the slot."
    ::= { sonusNodePimAdmnEntry 3 }

sonusNodePimAdmnHwType OBJECT-TYPE
    SYNTAX          PimTypeID
    MAX-ACCESS      read-write
    STATUS          current
    DESCRIPTION     
            "Identifies the type of Pim module in the indexed pim slot."
    ::= { sonusNodePimAdmnEntry 4 }

sonusNodePimAdmnRowStatus OBJECT-TYPE
    SYNTAX          RowStatus
    MAX-ACCESS      read-write
    STATUS          current
    DESCRIPTION     
            "Row status object for this table"
    ::= { sonusNodePimAdmnEntry 5 }

sonusNodePimStatTable OBJECT-TYPE
    SYNTAX          SEQUENCE OF SonusNodePimStatEntry
    MAX-ACCESS      not-accessible
    STATUS          current
    DESCRIPTION     
            "The node Pim Status Table describes the status of indexed Pim module
             in the node. This table is unavailable if the 
             sonusNodeSlotAdapState object indicates that this slot is 
             unknown, empty or faulted."
    ::= { sonusNode 14 }

sonusNodePimStatEntry OBJECT-TYPE
    SYNTAX          SonusNodePimStatEntry
    MAX-ACCESS      not-accessible
    STATUS          current
    DESCRIPTION     
            ""
    INDEX           { sonusNodePimStatShelfIndex, 
                      sonusNodePimStatSlotIndex, 
                      sonusNodePimStatPimIndex }
    ::= { sonusNodePimStatTable 1 }

SonusNodePimStatEntry ::=
    SEQUENCE {
        sonusNodePimStatShelfIndex      SonusShelfIndex,
        sonusNodePimStatSlotIndex       SonusSlotIndex,
        sonusNodePimStatPimIndex        SonusPimIndex,
        sonusNodePimStatMiddVersion     Integer32,
        sonusNodePimStatHwType          HwTypeID,
        sonusNodePimStatHwTypeRev       Integer32,
        sonusNodePimStatSerialNum       DisplayString,
        sonusNodePimStatPartNum         DisplayString,
        sonusNodePimStatPartNumRev      DisplayString,
        sonusNodePimStatMfgDate         DisplayString,
        sonusNodePimStatState           INTEGER,
        sonusNodePimStatEpldRevNumber   Integer32
    }

sonusNodePimStatShelfIndex OBJECT-TYPE
    SYNTAX          SonusShelfIndex
    MAX-ACCESS      read-only
    STATUS          current
    DESCRIPTION     
            "Identifies the target shelf."
    ::= { sonusNodePimStatEntry 1 }

sonusNodePimStatSlotIndex OBJECT-TYPE
    SYNTAX          SonusSlotIndex
    MAX-ACCESS      read-only
    STATUS          current
    DESCRIPTION     
            "Identifies the target slot within the shelf."
    ::= { sonusNodePimStatEntry 2 }

sonusNodePimStatPimIndex OBJECT-TYPE
    SYNTAX          SonusPimIndex
    MAX-ACCESS      read-only
    STATUS          current
    DESCRIPTION     
            "Identifies the target Pim within the slot."
    ::= { sonusNodePimStatEntry 3 }

sonusNodePimStatMiddVersion OBJECT-TYPE
    SYNTAX          Integer32
    MAX-ACCESS      read-only
    STATUS          current
    DESCRIPTION     
            "Identifies the version of the MIDD EEPROM on this Pim
             module."
    ::= { sonusNodePimStatEntry 4 }

sonusNodePimStatHwType OBJECT-TYPE
    SYNTAX          HwTypeID
    MAX-ACCESS      read-only
    STATUS          current
    DESCRIPTION     
            "Identifies the type of Pim module in the indexed slot."
    ::= { sonusNodePimStatEntry 5 }

sonusNodePimStatHwTypeRev OBJECT-TYPE
    SYNTAX          Integer32
    MAX-ACCESS      read-only
    STATUS          current
    DESCRIPTION     
            "Identifies the hardware type revision of the Pim module
             detected in the slot."
    ::= { sonusNodePimStatEntry 6 }

sonusNodePimStatSerialNum OBJECT-TYPE
    SYNTAX          DisplayString (SIZE(1..10))
    MAX-ACCESS      read-only
    STATUS          current
    DESCRIPTION     
            "Identifies the serial number of the pim module.  This is the
             serial number assigned to the card at manufacture."
    ::= { sonusNodePimStatEntry 7 }

sonusNodePimStatPartNum OBJECT-TYPE
    SYNTAX          DisplayString (SIZE(1..10))
    MAX-ACCESS      read-only
    STATUS          current
    DESCRIPTION     
            "Identifies the part number of the pim module.  This is the
             part number assigned to the card at manufacture."
    ::= { sonusNodePimStatEntry 8 }

sonusNodePimStatPartNumRev OBJECT-TYPE
    SYNTAX          DisplayString (SIZE(1..2))
    MAX-ACCESS      read-only
    STATUS          current
    DESCRIPTION     
            "Identifies the assembly revision level of the pim module."
    ::= { sonusNodePimStatEntry 9 }

sonusNodePimStatMfgDate OBJECT-TYPE
    SYNTAX          DisplayString (SIZE(1..10))
    MAX-ACCESS      read-only
    STATUS          current
    DESCRIPTION     
            "The date this pim module was manufactured."
    ::= { sonusNodePimStatEntry 10 }

sonusNodePimStatState OBJECT-TYPE
    SYNTAX          INTEGER { unknown(1), empty(2), present(3), 
                        faulted(4) }
    MAX-ACCESS      read-only
    STATUS          current
    DESCRIPTION     
            "The pim module state in the indexed slot"
    ::= { sonusNodePimStatEntry 11 }

sonusNodePimStatEpldRevNumber OBJECT-TYPE
    SYNTAX          Integer32
    MAX-ACCESS      read-only
    STATUS          current
    DESCRIPTION     
            "Identifies the Epld revision of the Pim module
             detected in the slot."
    ::= { sonusNodePimStatEntry 12 }

sonusNodeSfpStatTable OBJECT-TYPE
    SYNTAX          SEQUENCE OF SonusNodeSfpStatEntry
    MAX-ACCESS      not-accessible
    STATUS          current
    DESCRIPTION     
            "The node Pim SFP Status Table describes the status of indexed Pim SFP module
             in the node. This table is unavailable if the 
             sonusNodePimStatState object indicates that this PIM is 
             unknown, empty or faulted."
    ::= { sonusNode 15 }

sonusNodeSfpStatEntry OBJECT-TYPE
    SYNTAX          SonusNodeSfpStatEntry
    MAX-ACCESS      not-accessible
    STATUS          current
    DESCRIPTION     
            ""
    INDEX           { sonusNodeSfpStatShelfIndex, 
                      sonusNodeSfpStatSlotIndex, 
                      sonusNodeSfpStatModuleIndex, 
                      sonusNodeSfpStatSfpIndex }
    ::= { sonusNodeSfpStatTable 1 }

SonusNodeSfpStatEntry ::=
    SEQUENCE {
        sonusNodeSfpStatShelfIndex      SonusShelfIndex,
        sonusNodeSfpStatSlotIndex       SonusSlotIndex,
        sonusNodeSfpStatModuleIndex     SonusPimIndex,
        sonusNodeSfpStatSfpIndex        SonusSfpIndex,
        sonusNodeSfpStatState           INTEGER,
        sonusNodeSfpStatHwTypeRev       Integer32,
        sonusNodeSfpStatSerialNum       DisplayString,
        sonusNodeSfpStatSonusPartNum    DisplayString,
        sonusNodeSfpStatPartNumRev      DisplayString,
        sonusNodeSfpStatMfgDate         DisplayString
    }

sonusNodeSfpStatShelfIndex OBJECT-TYPE
    SYNTAX          SonusShelfIndex
    MAX-ACCESS      read-only
    STATUS          current
    DESCRIPTION     
            "Identifies the target shelf."
    ::= { sonusNodeSfpStatEntry 1 }

sonusNodeSfpStatSlotIndex OBJECT-TYPE
    SYNTAX          SonusSlotIndex
    MAX-ACCESS      read-only
    STATUS          current
    DESCRIPTION     
            "Identifies the target slot within the shelf."
    ::= { sonusNodeSfpStatEntry 2 }

sonusNodeSfpStatModuleIndex OBJECT-TYPE
    SYNTAX          SonusPimIndex
    MAX-ACCESS      read-only
    STATUS          current
    DESCRIPTION     
            "Identifies the target Module within the slot."
    ::= { sonusNodeSfpStatEntry 3 }

sonusNodeSfpStatSfpIndex OBJECT-TYPE
    SYNTAX          SonusSfpIndex
    MAX-ACCESS      read-only
    STATUS          current
    DESCRIPTION     
            "Identifies the target SFP within the PIM."
    ::= { sonusNodeSfpStatEntry 4 }

sonusNodeSfpStatState OBJECT-TYPE
    SYNTAX          INTEGER { unknown(1), empty(2), invalid(3), 
                        present(4) }
    MAX-ACCESS      read-only
    STATUS          current
    DESCRIPTION     
            "The pim SFP module state in the indexed slot."
    ::= { sonusNodeSfpStatEntry 5 }

sonusNodeSfpStatHwTypeRev OBJECT-TYPE
    SYNTAX          Integer32
    MAX-ACCESS      read-only
    STATUS          current
    DESCRIPTION     
            "Identifies the hardware type revision of the pim SFP module
             detected in the slot."
    ::= { sonusNodeSfpStatEntry 6 }

sonusNodeSfpStatSerialNum OBJECT-TYPE
    SYNTAX          DisplayString (SIZE(1..10))
    MAX-ACCESS      read-only
    STATUS          current
    DESCRIPTION     
            "Identifies the serial number of the pim SFP module."
    ::= { sonusNodeSfpStatEntry 7 }

sonusNodeSfpStatSonusPartNum OBJECT-TYPE
    SYNTAX          DisplayString (SIZE(1..10))
    MAX-ACCESS      read-only
    STATUS          current
    DESCRIPTION     
            "Identifies the part number of the pim SFP module."
    ::= { sonusNodeSfpStatEntry 8 }

sonusNodeSfpStatPartNumRev OBJECT-TYPE
    SYNTAX          DisplayString (SIZE(1..2))
    MAX-ACCESS      read-only
    STATUS          current
    DESCRIPTION     
            "Identifies the assembly revision level of the SFP module."
    ::= { sonusNodeSfpStatEntry 9 }

sonusNodeSfpStatMfgDate OBJECT-TYPE
    SYNTAX          DisplayString (SIZE(1..10))
    MAX-ACCESS      read-only
    STATUS          current
    DESCRIPTION     
            "The date this SFP module was manufactured."
    ::= { sonusNodeSfpStatEntry 10 }

sonusNvsConfig OBJECT IDENTIFIER
    ::= { sonusNodeMIBObjects 2 }

sonusNvsConfigTable OBJECT-TYPE
    SYNTAX          SEQUENCE OF SonusNvsConfigEntry
    MAX-ACCESS      not-accessible
    STATUS          current
    DESCRIPTION     
            "This table specifies the Boot Parameters that apply only to
             the MNS present in the indexed shelf and slot.  The Boot
             Parameters can only be accessed if the shelf is actively
             part of the node."
    ::= { sonusNvsConfig 1 }

sonusNvsConfigEntry OBJECT-TYPE
    SYNTAX          SonusNvsConfigEntry
    MAX-ACCESS      not-accessible
    STATUS          current
    DESCRIPTION     
            ""
    INDEX           { sonusBparamShelfIndex }
    ::= { sonusNvsConfigTable 1 }

SonusNvsConfigEntry ::=
    SEQUENCE {
        sonusBparamShelfIndex           SonusShelfIndex,
        sonusBparamUnused               Integer32,
        sonusBparamPasswd               DisplayString,
        sonusBparamIpAddrSlot1Port0     IpAddress,
        sonusBparamIpMaskSlot1Port0     IpAddress,
        sonusBparamIpGatewaySlot1Port0  IpAddress,
        sonusBparamIfSpeedTypeSlot1Port0 INTEGER,
        sonusBparamIpAddrSlot1Port1     IpAddress,
        sonusBparamIpMaskSlot1Port1     IpAddress,
        sonusBparamIpGatewaySlot1Port1  IpAddress,
        sonusBparamIfSpeedTypeSlot1Port1 INTEGER,
        sonusBparamIpAddrSlot1Port2     IpAddress,
        sonusBparamIpMaskSlot1Port2     IpAddress,
        sonusBparamIpGatewaySlot1Port2  IpAddress,
        sonusBparamIfSpeedTypeSlot1Port2 INTEGER,
        sonusBparamIpAddrSlot2Port0     IpAddress,
        sonusBparamIpMaskSlot2Port0     IpAddress,
        sonusBparamIpGatewaySlot2Port0  IpAddress,
        sonusBparamIfSpeedTypeSlot2Port0 INTEGER,
        sonusBparamIpAddrSlot2Port1     IpAddress,
        sonusBparamIpMaskSlot2Port1     IpAddress,
        sonusBparamIpGatewaySlot2Port1  IpAddress,
        sonusBparamIfSpeedTypeSlot2Port1 INTEGER,
        sonusBparamIpAddrSlot2Port2     IpAddress,
        sonusBparamIpMaskSlot2Port2     IpAddress,
        sonusBparamIpGatewaySlot2Port2  IpAddress,
        sonusBparamIfSpeedTypeSlot2Port2 INTEGER,
        sonusBparamBootDelay            Integer32,
        sonusBparamCoreState            SonusAdminState,
        sonusBparamCoreLevel            INTEGER,
        sonusBparamBaudRate             Integer32,
        sonusBparamNfsPrimary           IpAddress,
        sonusBparamNfsSecondary         IpAddress,
        sonusBparamNfsMountPri          DisplayString,
        sonusBparamNfsMountSec          DisplayString,
        sonusBparamNfsPathUpgrade       DisplayString,
        sonusBparamNfsPathLoad          DisplayString,
        sonusBparamPrimName             DisplayString,
        sonusBparamSecName              DisplayString,
        sonusBparamMasterState          INTEGER,
        sonusBparamParamMode            INTEGER,
        sonusBparamCliScript            DisplayString,
        sonusBparamUId                  Integer32,
        sonusBparamGrpId                Integer32,
        sonusBparamCoreDumpLimit        Integer32,
        sonusBparamNfsPathSoftware      DisplayString,
        sonusBparamBootDisk             INTEGER,
        sonusBparamCoreDumpDisk         INTEGER,
        sonusBparamCoreDumpLocalDiskLimit Integer32,
        sonusBparamNfs6Secondary        Ipv6Address,
        sonusBparamNfs6Primary          Ipv6Address,
        sonusBparamNfsIpVersion         INTEGER,
        sonusBparamNfsSecondaryIpVersion INTEGER,
        sonusBparamIp6AddrSlot1Port1    Ipv6Address,
        sonusBparamIp6GatewaySlot1Port1 Ipv6Address,
        sonusBparamIp6PrefixSlot1Port1  Integer32,
        sonusBparamIp6AddrSlot1Port2    Ipv6Address,
        sonusBparamIp6GatewaySlot1Port2 Ipv6Address,
        sonusBparamIp6PrefixSlot1Port2  Integer32,
        sonusBparamIp6AddrSlot2Port1    Ipv6Address,
        sonusBparamIp6GatewaySlot2Port1 Ipv6Address,
        sonusBparamIp6PrefixSlot2Port1  Integer32,
        sonusBparamIp6AddrSlot2Port2    Ipv6Address,
        sonusBparamIp6GatewaySlot2Port2 Ipv6Address,
        sonusBparamIp6PrefixSlot2Port2  Integer32
    }

sonusBparamShelfIndex OBJECT-TYPE
    SYNTAX          SonusShelfIndex
    MAX-ACCESS      read-only
    STATUS          current
    DESCRIPTION     
            "Identifies the target shelf.  This object returns the value of
             sonusNodeShelfStatIndex which was used to index into this table."
    ::= { sonusNvsConfigEntry 1 }

sonusBparamUnused OBJECT-TYPE
    SYNTAX          Integer32
    MAX-ACCESS      not-accessible
    STATUS          current
    DESCRIPTION     
            "Unused"
    ::= { sonusNvsConfigEntry 2 }

sonusBparamPasswd OBJECT-TYPE
    SYNTAX          DisplayString (SIZE(0..23))
    MAX-ACCESS      read-write
    STATUS          current
    DESCRIPTION     
            "The secure password which is used to access the Boot
             PROM menu subsystem.  This object is not available through
             SNMP."
    ::= { sonusNvsConfigEntry 3 }

sonusBparamIpAddrSlot1Port0 OBJECT-TYPE
    SYNTAX          IpAddress
    MAX-ACCESS      read-write
    STATUS          current
    DESCRIPTION     
            "The IP address assigned to the field service port.  This 
             port is not intended for customer use."
    ::= { sonusNvsConfigEntry 4 }

sonusBparamIpMaskSlot1Port0 OBJECT-TYPE
    SYNTAX          IpAddress
    MAX-ACCESS      read-write
    STATUS          current
    DESCRIPTION     
            "The IP Address Mask assigned to the field service port."
    ::= { sonusNvsConfigEntry 5 }

sonusBparamIpGatewaySlot1Port0 OBJECT-TYPE
    SYNTAX          IpAddress
    MAX-ACCESS      read-write
    STATUS          current
    DESCRIPTION     
            "The default IP Gateway address used by the field service port."
    ::= { sonusNvsConfigEntry 6 }

sonusBparamIfSpeedTypeSlot1Port0 OBJECT-TYPE
    SYNTAX          INTEGER { autoNegotiate(1), fullDuplex100(2), 
                        halfDuplex100(3), fullDuplex10(4), 
                        halfDuplex10(5) }
    MAX-ACCESS      read-write
    STATUS          current
    DESCRIPTION     
            "The default link speed setting used by the field service port."
    ::= { sonusNvsConfigEntry 7 }

sonusBparamIpAddrSlot1Port1 OBJECT-TYPE
    SYNTAX          IpAddress
    MAX-ACCESS      read-write
    STATUS          current
    DESCRIPTION     
            "The IP address assigned to management port number one."
    ::= { sonusNvsConfigEntry 8 }

sonusBparamIpMaskSlot1Port1 OBJECT-TYPE
    SYNTAX          IpAddress
    MAX-ACCESS      read-write
    STATUS          current
    DESCRIPTION     
            "The IP address mask used by management port one."
    ::= { sonusNvsConfigEntry 9 }

sonusBparamIpGatewaySlot1Port1 OBJECT-TYPE
    SYNTAX          IpAddress
    MAX-ACCESS      read-write
    STATUS          current
    DESCRIPTION     
            "The default IP Gateway address used by management port one."
    ::= { sonusNvsConfigEntry 10 }

sonusBparamIfSpeedTypeSlot1Port1 OBJECT-TYPE
    SYNTAX          INTEGER { autoNegotiate(1), fullDuplex100(2), 
                        halfDuplex100(3), fullDuplex10(4), 
                        halfDuplex10(5) }
    MAX-ACCESS      read-write
    STATUS          current
    DESCRIPTION     
            "The default link speed setting used by management port one."
    ::= { sonusNvsConfigEntry 11 }

sonusBparamIpAddrSlot1Port2 OBJECT-TYPE
    SYNTAX          IpAddress
    MAX-ACCESS      read-write
    STATUS          current
    DESCRIPTION     
            "The IP address assigned to management port number two."
    ::= { sonusNvsConfigEntry 12 }

sonusBparamIpMaskSlot1Port2 OBJECT-TYPE
    SYNTAX          IpAddress
    MAX-ACCESS      read-write
    STATUS          current
    DESCRIPTION     
            "The IP address mask used by management port two."
    ::= { sonusNvsConfigEntry 13 }

sonusBparamIpGatewaySlot1Port2 OBJECT-TYPE
    SYNTAX          IpAddress
    MAX-ACCESS      read-write
    STATUS          current
    DESCRIPTION     
            "The default gateway address used by management port two."
    ::= { sonusNvsConfigEntry 14 }

sonusBparamIfSpeedTypeSlot1Port2 OBJECT-TYPE
    SYNTAX          INTEGER { autoNegotiate(1), fullDuplex100(2), 
                        halfDuplex100(3), fullDuplex10(4), 
                        halfDuplex10(5) }
    MAX-ACCESS      read-write
    STATUS          current
    DESCRIPTION     
            "The default link speed setting used by management port two."
    ::= { sonusNvsConfigEntry 15 }

sonusBparamIpAddrSlot2Port0 OBJECT-TYPE
    SYNTAX          IpAddress
    MAX-ACCESS      read-write
    STATUS          current
    DESCRIPTION     
            "The IP address assigned to the field service port.  This 
             port is not intended for customer use."
    ::= { sonusNvsConfigEntry 16 }

sonusBparamIpMaskSlot2Port0 OBJECT-TYPE
    SYNTAX          IpAddress
    MAX-ACCESS      read-write
    STATUS          current
    DESCRIPTION     
            "The IP Address Mask assigned to the field service port."
    ::= { sonusNvsConfigEntry 17 }

sonusBparamIpGatewaySlot2Port0 OBJECT-TYPE
    SYNTAX          IpAddress
    MAX-ACCESS      read-write
    STATUS          current
    DESCRIPTION     
            "The default IP Gateway address used by the field service port."
    ::= { sonusNvsConfigEntry 18 }

sonusBparamIfSpeedTypeSlot2Port0 OBJECT-TYPE
    SYNTAX          INTEGER { autoNegotiate(1), fullDuplex100(2), 
                        halfDuplex100(3), fullDuplex10(4), 
                        halfDuplex10(5) }
    MAX-ACCESS      read-write
    STATUS          current
    DESCRIPTION     
            "The default link speed setting used by the field service port."
    ::= { sonusNvsConfigEntry 19 }

sonusBparamIpAddrSlot2Port1 OBJECT-TYPE
    SYNTAX          IpAddress
    MAX-ACCESS      read-write
    STATUS          current
    DESCRIPTION     
            "The IP address assigned to management port number one."
    ::= { sonusNvsConfigEntry 20 }

sonusBparamIpMaskSlot2Port1 OBJECT-TYPE
    SYNTAX          IpAddress
    MAX-ACCESS      read-write
    STATUS          current
    DESCRIPTION     
            "The IP address mask used by management port one."
    ::= { sonusNvsConfigEntry 21 }

sonusBparamIpGatewaySlot2Port1 OBJECT-TYPE
    SYNTAX          IpAddress
    MAX-ACCESS      read-write
    STATUS          current
    DESCRIPTION     
            "The default IP Gateway address used by management port one."
    ::= { sonusNvsConfigEntry 22 }

sonusBparamIfSpeedTypeSlot2Port1 OBJECT-TYPE
    SYNTAX          INTEGER { autoNegotiate(1), fullDuplex100(2), 
                        halfDuplex100(3), fullDuplex10(4), 
                        halfDuplex10(5) }
    MAX-ACCESS      read-write
    STATUS          current
    DESCRIPTION     
            "The default link speed setting used by management port one."
    ::= { sonusNvsConfigEntry 23 }

sonusBparamIpAddrSlot2Port2 OBJECT-TYPE
    SYNTAX          IpAddress
    MAX-ACCESS      read-write
    STATUS          current
    DESCRIPTION     
            "The IP address assigned to management port number two."
    ::= { sonusNvsConfigEntry 24 }

sonusBparamIpMaskSlot2Port2 OBJECT-TYPE
    SYNTAX          IpAddress
    MAX-ACCESS      read-write
    STATUS          current
    DESCRIPTION     
            "The IP address mask used by management port two."
    ::= { sonusNvsConfigEntry 25 }

sonusBparamIpGatewaySlot2Port2 OBJECT-TYPE
    SYNTAX          IpAddress
    MAX-ACCESS      read-write
    STATUS          current
    DESCRIPTION     
            "The default gateway address used by management port two."
    ::= { sonusNvsConfigEntry 26 }

sonusBparamIfSpeedTypeSlot2Port2 OBJECT-TYPE
    SYNTAX          INTEGER { autoNegotiate(1), fullDuplex100(2), 
                        halfDuplex100(3), fullDuplex10(4), 
                        halfDuplex10(5) }
    MAX-ACCESS      read-write
    STATUS          current
    DESCRIPTION     
            "The default link speed setting used by management port two."
    ::= { sonusNvsConfigEntry 27 }

sonusBparamBootDelay OBJECT-TYPE
    SYNTAX          Integer32 (5..255)
    MAX-ACCESS      read-write
    STATUS          current
    DESCRIPTION     
            "The amount of delay used to allow an administrator to gain
             access to the NVS configuration menus before the runtime
             software is loaded.  The delay is specified in seconds.
             Increasing this delay, will increase the total system boot
             time by the same amount."
    ::= { sonusNvsConfigEntry 28 }

sonusBparamCoreState OBJECT-TYPE
    SYNTAX          SonusAdminState
    MAX-ACCESS      read-write
    STATUS          current
    DESCRIPTION     
            "Specifies whether core dumps are enabled.  If core dumps are
             disabled, a fatal software fault will result in a reboot without
             the overhead of performing the core dump operation."
    ::= { sonusNvsConfigEntry 29 }

sonusBparamCoreLevel OBJECT-TYPE
    SYNTAX          INTEGER { normal(1), sensitive(2) }
    MAX-ACCESS      read-write
    STATUS          current
    DESCRIPTION     
            "Specifies the type of core dump behavior the shelf will display.
             Under normal(1) behavior, the server modules will execute a core 
             dump only for fatal software errors.  Under sensitive(2) behavior, 
             the server modules will execute a core dump when the software
             recognizes a major, but non-fatal, software fault.  Normal(1) is
             the strongly recommended setting."
    ::= { sonusNvsConfigEntry 30 }

sonusBparamBaudRate OBJECT-TYPE
    SYNTAX          Integer32
    MAX-ACCESS      read-write
    STATUS          current
    DESCRIPTION     
            "The baud rate of a management port's physical interface."
    ::= { sonusNvsConfigEntry 31 }

sonusBparamNfsPrimary OBJECT-TYPE
    SYNTAX          IpAddress
    MAX-ACCESS      read-write
    STATUS          current
    DESCRIPTION     
            "The IP Address of the primary NFS Server for this switch."
    ::= { sonusNvsConfigEntry 32 }

sonusBparamNfsSecondary OBJECT-TYPE
    SYNTAX          IpAddress
    MAX-ACCESS      read-write
    STATUS          current
    DESCRIPTION     
            "The IP Address of the secondary NFS Server for this switch."
    ::= { sonusNvsConfigEntry 33 }

sonusBparamNfsMountPri OBJECT-TYPE
    SYNTAX          DisplayString (SIZE(2..31))
    MAX-ACCESS      read-write
    STATUS          current
    DESCRIPTION     
            "The NFS mount point exported by the Primary NFS server."
    ::= { sonusNvsConfigEntry 34 }

sonusBparamNfsMountSec OBJECT-TYPE
    SYNTAX          DisplayString (SIZE(2..31))
    MAX-ACCESS      read-write
    STATUS          current
    DESCRIPTION     
            "The NFS mount point exported by the Secondary NFS server."
    ::= { sonusNvsConfigEntry 35 }

sonusBparamNfsPathUpgrade OBJECT-TYPE
    SYNTAX          DisplayString (SIZE(0..15))
    MAX-ACCESS      read-only
    STATUS          current
    DESCRIPTION     
            "The name of the temporary load path override.  This path is
             tried before the sonusBparamNfsPathLoad when specified.  If the 
             sonusBparamNfsPathUpgrade fails to completely boot the switch 
             after three consecutive attempts, the path is automatically abandoned 
             in favor of the sonusBparamNfsPathLoad."
    ::= { sonusNvsConfigEntry 36 }

sonusBparamNfsPathLoad OBJECT-TYPE
    SYNTAX          DisplayString (SIZE(2..31))
    MAX-ACCESS      read-write
    STATUS          current
    DESCRIPTION     
            "The directory, beneath the exported NFS mount point or local disk,
             which contains the switch's operational directories."
    ::= { sonusNvsConfigEntry 37 }

sonusBparamPrimName OBJECT-TYPE
    SYNTAX          DisplayString (SIZE(1..15))
    MAX-ACCESS      read-write
    STATUS          current
    DESCRIPTION     
            "The primary load file name for this server module."
    ::= { sonusNvsConfigEntry 38 }

sonusBparamSecName OBJECT-TYPE
    SYNTAX          DisplayString (SIZE(0..15))
    MAX-ACCESS      read-write
    STATUS          current
    DESCRIPTION     
            "The secondary load file name for this server module.  The secondary
             file is tried when the primary file can not be opened or read."
    ::= { sonusNvsConfigEntry 39 }

sonusBparamMasterState OBJECT-TYPE
    SYNTAX          INTEGER { slave(1), master(2) }
    MAX-ACCESS      read-only
    STATUS          current
    DESCRIPTION     
            "Specifies whether this shelf will participate in the node
             as a master shelf, or as a slave shelf.  Each node contains
             exactly one master shelf, and may contain multiple slave
             shelves."
    ::= { sonusNvsConfigEntry 40 }

sonusBparamParamMode OBJECT-TYPE
    SYNTAX          INTEGER { disabled(1), binaryFile(2), defaults(3) }
    MAX-ACCESS      read-write
    STATUS          current
    DESCRIPTION     
            "Specifies the binary parameter file mode of the node.  This mode specifies
             whether the node will attempt to load a binary parameter file.  The paramMode
             can be set to disabled(1) which disables parameter file loading.
             The mode can be set to defaults(3), which temporarily disables binary
             parameter file loading, until after the next binary parameter file save
             cycle initiated by the runtime software.  In both of these disabled cases,
             the node boots with default parameters and automatically loads and executes 
             the CLI startup script.  The paramMode may be set to binaryFile(2),
             which enables binary parameter file loading and disables the automatic 
             CLI startup script loading.
             
             A binary parameter file must exist before the node can
             succesfully load a binary parameter file.  The node will load default
             parameters when a valid parameter file can not be loaded.  The node
             loads default parameters when either the parameter mode is set
             to disabled(1) or when the mode is set to defaults(3).  When the mode 
             is set to defaults(3), the mode is automatically updated to binaryFile(2)
             on the first parameter save cycle."
    ::= { sonusNvsConfigEntry 41 }

sonusBparamCliScript OBJECT-TYPE
    SYNTAX          DisplayString (SIZE(0..15))
    MAX-ACCESS      read-write
    STATUS          current
    DESCRIPTION     
            "The name of the CLI script which will be run automatically when
             the switch intentionally boots with default parameters.  The switch 
             will intentionally boot with default parameters when sonusBparamParamMode
             is set to either disabled(1) or defaults(3).  This CLI script will
             never be run when the sonusBparamParamMode is set to binaryFile(2).
             
             If the script is not specified, or if it can not be located, it is
             not run.  The switch expects to find the script file in the cli/sys
             directory, beneath the load path specified directory."
    ::= { sonusNvsConfigEntry 42 }

sonusBparamUId OBJECT-TYPE
    SYNTAX          Integer32
    MAX-ACCESS      read-write
    STATUS          current
    DESCRIPTION     
            "The UNIX user ID used for all file accesses on both the primary and
             secondary NFS servers."
    ::= { sonusNvsConfigEntry 43 }

sonusBparamGrpId OBJECT-TYPE
    SYNTAX          Integer32
    MAX-ACCESS      read-write
    STATUS          current
    DESCRIPTION     
            "The UNIX group ID used for all file accesses on both the primary and
             secondary NFS servers."
    ::= { sonusNvsConfigEntry 44 }

sonusBparamCoreDumpLimit OBJECT-TYPE
    SYNTAX          Integer32 (0..255)
    MAX-ACCESS      read-write
    STATUS          current
    DESCRIPTION     
            "Indicates the maximum number of core dump files which can be created on behalf
             of a Server which is requesting a core dump. Setting the value to zero indicates
             no limit. This object is intended to limit the number of core dumps (and the 
             amount of disk space used) when a Server repeatedly crashes."
    DEFVAL          { 6 }
    ::= { sonusNvsConfigEntry 45 }

sonusBparamNfsPathSoftware OBJECT-TYPE
    SYNTAX          DisplayString (SIZE(0..15))
    MAX-ACCESS      read-write
    STATUS          current
    DESCRIPTION     
            "The name of the software load path.  This path is
             is appended to the Boot Path.  This object may be NULL, in
             which case the software is loaded directly from the Boot Path.
             This object allows multiple revisions of software to be maintained
             below the Boot Path.  This object can be overridden by the 
             Upgrade Path object during a LSWU.
             
             During general operation the complete software load path is formed
             by concatenating this object to the Boot Path and any applicable
             file system mount point."
    ::= { sonusNvsConfigEntry 46 }

sonusBparamBootDisk OBJECT-TYPE
    SYNTAX          INTEGER { nfsServer(1), localDisk(2) }
    MAX-ACCESS      read-write
    STATUS          current
    DESCRIPTION     
            "Controls the location where the MNS obtains Boot Files, which
             includes images, parameter files, CLI files, and TCL scripts.
             MNS's without a local disk must be configured to use the nfsServer."
    ::= { sonusNvsConfigEntry 47 }

sonusBparamCoreDumpDisk OBJECT-TYPE
    SYNTAX          INTEGER { nfsServer(1), localDisk(2) }
    MAX-ACCESS      read-write
    STATUS          current
    DESCRIPTION     
            "Controls the location where core dump files are to be written.
             MNS's without a local disk must be configured to use the nfsServer."
    ::= { sonusNvsConfigEntry 48 }

sonusBparamCoreDumpLocalDiskLimit OBJECT-TYPE
    SYNTAX          Integer32 (1..2048)
    MAX-ACCESS      read-write
    STATUS          current
    DESCRIPTION     
            "Controls the maximum amount of disk space (in megabytes) that can be
             used for core dumps.  This limit applies only to the local MNS disk
             (when sonusBparamCoreDumpDisk is set to localDisk)."
    ::= { sonusNvsConfigEntry 49 }

sonusBparamNfs6Secondary OBJECT-TYPE
    SYNTAX          Ipv6Address
    MAX-ACCESS      read-write
    STATUS          current
    DESCRIPTION     
            "The IPV6Address of the secondary NFS Server for this switch."
    ::= { sonusNvsConfigEntry 50 }

sonusBparamNfs6Primary OBJECT-TYPE
    SYNTAX          Ipv6Address
    MAX-ACCESS      read-write
    STATUS          current
    DESCRIPTION     
            "The IPV6Address of the Primary NFS Server for this switch."
    ::= { sonusNvsConfigEntry 51 }

sonusBparamNfsIpVersion OBJECT-TYPE
    SYNTAX          INTEGER { afInet(2), afInet6(24) }
    MAX-ACCESS      read-only
    STATUS          current
    DESCRIPTION     
            "The IP type NFS Server for this switch."
    ::= { sonusNvsConfigEntry 52 }

sonusBparamNfsSecondaryIpVersion OBJECT-TYPE
    SYNTAX          INTEGER { afInet(2), afInet6(24) }
    MAX-ACCESS      read-only
    STATUS          current
    DESCRIPTION     
            "The IP type NFS Server for this switch."
    ::= { sonusNvsConfigEntry 53 }

sonusBparamIp6AddrSlot1Port1 OBJECT-TYPE
    SYNTAX          Ipv6Address
    MAX-ACCESS      read-write
    STATUS          current
    DESCRIPTION     
            "The IPv6 address assigned to management port number one."
    ::= { sonusNvsConfigEntry 54 }

sonusBparamIp6GatewaySlot1Port1 OBJECT-TYPE
    SYNTAX          Ipv6Address
    MAX-ACCESS      read-write
    STATUS          current
    DESCRIPTION     
            "The IPv6 Gateway address assigned to management port number one."
    ::= { sonusNvsConfigEntry 55 }

sonusBparamIp6PrefixSlot1Port1 OBJECT-TYPE
    SYNTAX          Integer32
    MAX-ACCESS      read-write
    STATUS          current
    DESCRIPTION     
            "The IPv6 Prefix Length assigned to management port number one."
    ::= { sonusNvsConfigEntry 56 }

sonusBparamIp6AddrSlot1Port2 OBJECT-TYPE
    SYNTAX          Ipv6Address
    MAX-ACCESS      read-write
    STATUS          current
    DESCRIPTION     
            "The IPv6 address assigned to management port number one."
    ::= { sonusNvsConfigEntry 57 }

sonusBparamIp6GatewaySlot1Port2 OBJECT-TYPE
    SYNTAX          Ipv6Address
    MAX-ACCESS      read-write
    STATUS          current
    DESCRIPTION     
            "The IPv6 Gateway address assigned to management port number one."
    ::= { sonusNvsConfigEntry 58 }

sonusBparamIp6PrefixSlot1Port2 OBJECT-TYPE
    SYNTAX          Integer32
    MAX-ACCESS      read-write
    STATUS          current
    DESCRIPTION     
            "The IPv6 Prefix Length assigned to management port number one."
    ::= { sonusNvsConfigEntry 59 }

sonusBparamIp6AddrSlot2Port1 OBJECT-TYPE
    SYNTAX          Ipv6Address
    MAX-ACCESS      read-write
    STATUS          current
    DESCRIPTION     
            "The IPv6 address assigned to management port number one."
    ::= { sonusNvsConfigEntry 60 }

sonusBparamIp6GatewaySlot2Port1 OBJECT-TYPE
    SYNTAX          Ipv6Address
    MAX-ACCESS      read-write
    STATUS          current
    DESCRIPTION     
            "The IPv6 Gateway address assigned to management port number one."
    ::= { sonusNvsConfigEntry 61 }

sonusBparamIp6PrefixSlot2Port1 OBJECT-TYPE
    SYNTAX          Integer32
    MAX-ACCESS      read-write
    STATUS          current
    DESCRIPTION     
            "The IPv6 Prefix Length assigned to management port number one."
    ::= { sonusNvsConfigEntry 62 }

sonusBparamIp6AddrSlot2Port2 OBJECT-TYPE
    SYNTAX          Ipv6Address
    MAX-ACCESS      read-write
    STATUS          current
    DESCRIPTION     
            "The IPv6 address assigned to management port number one."
    ::= { sonusNvsConfigEntry 63 }

sonusBparamIp6GatewaySlot2Port2 OBJECT-TYPE
    SYNTAX          Ipv6Address
    MAX-ACCESS      read-write
    STATUS          current
    DESCRIPTION     
            "The IPv6 Gateway address assigned to management port number one."
    ::= { sonusNvsConfigEntry 64 }

sonusBparamIp6PrefixSlot2Port2 OBJECT-TYPE
    SYNTAX          Integer32
    MAX-ACCESS      read-write
    STATUS          current
    DESCRIPTION     
            "The IPv6 Prefix Length assigned to management port number one."
    ::= { sonusNvsConfigEntry 65 }

sonusFlashConfigTable OBJECT-TYPE
    SYNTAX          SEQUENCE OF SonusFlashConfigEntry
    MAX-ACCESS      not-accessible
    STATUS          current
    DESCRIPTION     
            "This table specifies the FLASH Update parameters for the
             indexed server module.  The Boot Firmware for each server
             module is contained in the FLASH device.  It is essential
             that once the upgrade process is initiated, that it be allowed
             to complete without interruption.  Power loss or manually
             reseting the server module during the upgrade process will
             result in a loss of Boot Firmware."
    ::= { sonusNvsConfig 2 }

sonusFlashConfigEntry OBJECT-TYPE
    SYNTAX          SonusFlashConfigEntry
    MAX-ACCESS      not-accessible
    STATUS          current
    DESCRIPTION     
            ""
    INDEX           { sonusFlashAdmnShelfIndex, sonusFlashAdmnSlotIndex }
    ::= { sonusFlashConfigTable 1 }

SonusFlashConfigEntry ::=
    SEQUENCE {
        sonusFlashAdmnShelfIndex        SonusShelfIndex,
        sonusFlashAdmnSlotIndex         SonusSlotIndex,
        sonusFlashAdmnUpdateButton      INTEGER
    }

sonusFlashAdmnShelfIndex OBJECT-TYPE
    SYNTAX          SonusShelfIndex
    MAX-ACCESS      read-only
    STATUS          current
    DESCRIPTION     
            "Identifies the target shelf within the node."
    ::= { sonusFlashConfigEntry 1 }

sonusFlashAdmnSlotIndex OBJECT-TYPE
    SYNTAX          SonusSlotIndex
    MAX-ACCESS      read-only
    STATUS          current
    DESCRIPTION     
            "Identifies the target slot within the shelf."
    ::= { sonusFlashConfigEntry 2 }

sonusFlashAdmnUpdateButton OBJECT-TYPE
    SYNTAX          INTEGER { update(1) }
    MAX-ACCESS      read-write
    STATUS          current
    DESCRIPTION     
            "Initiate the update of the specified server module's
             FLASH PROM now.  This object always reads as the value
             update(1)."
    DEFVAL          { update }
    ::= { sonusFlashConfigEntry 3 }

sonusFlashStatusTable OBJECT-TYPE
    SYNTAX          SEQUENCE OF SonusFlashStatusEntry
    MAX-ACCESS      not-accessible
    STATUS          current
    DESCRIPTION     
            "This table specifies the status of the FLASH Update process."
    ::= { sonusNvsConfig 3 }

sonusFlashStatusEntry OBJECT-TYPE
    SYNTAX          SonusFlashStatusEntry
    MAX-ACCESS      not-accessible
    STATUS          current
    DESCRIPTION     
            ""
    INDEX           { sonusFlashStatShelfIndex, sonusFlashStatSlotIndex }
    ::= { sonusFlashStatusTable 1 }

SonusFlashStatusEntry ::=
    SEQUENCE {
        sonusFlashStatShelfIndex        SonusShelfIndex,
        sonusFlashStatSlotIndex         SonusSlotIndex,
        sonusFlashStatState             INTEGER,
        sonusFlashStatLastStatus        INTEGER
    }

sonusFlashStatShelfIndex OBJECT-TYPE
    SYNTAX          SonusShelfIndex
    MAX-ACCESS      read-only
    STATUS          current
    DESCRIPTION     
            "Identifies the target shelf within the node."
    ::= { sonusFlashStatusEntry 1 }

sonusFlashStatSlotIndex OBJECT-TYPE
    SYNTAX          SonusSlotIndex
    MAX-ACCESS      read-only
    STATUS          current
    DESCRIPTION     
            "Identifies the target slot within the shelf."
    ::= { sonusFlashStatusEntry 2 }

sonusFlashStatState OBJECT-TYPE
    SYNTAX          INTEGER { idle(1), waitReply(2), waitData(3), 
                        imageComplete(4), flashErase(5), flashWrite(6), 
                        done(7) }
    MAX-ACCESS      read-only
    STATUS          current
    DESCRIPTION     
            "The current state of the FLASH update process on the target
             server module."
    ::= { sonusFlashStatusEntry 3 }

sonusFlashStatLastStatus OBJECT-TYPE
    SYNTAX          INTEGER { success(1), unknown(2), inProgress(3), 
                        badRequest(4), noReply(5), managerNack(6), 
                        timerResources(7), dataTimeout(8), 
                        msgSequence(9), memoryResources(10), 
                        imageChecksum(11), badBlkType(12), 
                        flashErase(13), flashWrite(14), 
                        flashChecksum(15), mgrNack(16), badState(17) }
    MAX-ACCESS      read-only
    STATUS          current
    DESCRIPTION     
            "The status of the last FLASH update that was executed."
    ::= { sonusFlashStatusEntry 4 }

sonusUser OBJECT IDENTIFIER
    ::= { sonusNodeMIBObjects 3 }

sonusUserList OBJECT IDENTIFIER
    ::= { sonusUser 1 }

sonusUserListNextIndex OBJECT-TYPE
    SYNTAX          Integer32
    MAX-ACCESS      read-only
    STATUS          current
    DESCRIPTION     
            "The next valid index to use when creating a new sonusUserListEntry"
    ::= { sonusUserList 1 }

sonusUserListTable OBJECT-TYPE
    SYNTAX          SEQUENCE OF SonusUserListEntry
    MAX-ACCESS      not-accessible
    STATUS          current
    DESCRIPTION     
            "This table specifies the user access list for the node."
    ::= { sonusUserList 2 }

sonusUserListEntry OBJECT-TYPE
    SYNTAX          SonusUserListEntry
    MAX-ACCESS      not-accessible
    STATUS          current
    DESCRIPTION     
            ""
    INDEX           { sonusUserListIndex }
    ::= { sonusUserListTable 1 }

SonusUserListEntry ::=
    SEQUENCE {
        sonusUserListIndex              Integer32,
        sonusUserListState              SonusAdminState,
        sonusUserListUserName           SonusName,
        sonusUserListProfileName        DisplayString,
        sonusUserListPasswd             DisplayString,
        sonusUserListComment            DisplayString,
        sonusUserListAccess             INTEGER,
        sonusUserListRowStatus          RowStatus,
        sonusUserListAccountAgeThreshold Integer32,
        sonusUserListAccountAgeReset    INTEGER,
        sonusUserListPasswdAgeThreshold Integer32,
        sonusUserListLoginLockoutThreshold  Integer32,
        sonusUserListLoginLockoutDuration Integer32,
        sonusUserListCliIdleTimeout     Integer32
    }

sonusUserListIndex OBJECT-TYPE
    SYNTAX          Integer32 (1..32)
    MAX-ACCESS      read-only
    STATUS          current
    DESCRIPTION     
            "Identifies the target user list entry."
    ::= { sonusUserListEntry 1 }

sonusUserListState OBJECT-TYPE
    SYNTAX          SonusAdminState
    MAX-ACCESS      read-write
    STATUS          current
    DESCRIPTION     
            "The administrative state of this user entry."
    ::= { sonusUserListEntry 2 }

sonusUserListUserName OBJECT-TYPE
    SYNTAX          SonusName
    MAX-ACCESS      read-write
    STATUS          current
    DESCRIPTION     
            "The user name of this user."
    ::= { sonusUserListEntry 3 }

sonusUserListProfileName OBJECT-TYPE
    SYNTAX          DisplayString (SIZE(0..23))
    MAX-ACCESS      read-write
    STATUS          current
    DESCRIPTION     
            "The name of the profile applied to this user entry."
    ::= { sonusUserListEntry 4 }

sonusUserListPasswd OBJECT-TYPE
    SYNTAX          DisplayString (SIZE(4..16))
    MAX-ACCESS      read-write
    STATUS          current
    DESCRIPTION     
            "The password for this user."
    ::= { sonusUserListEntry 5 }

sonusUserListComment OBJECT-TYPE
    SYNTAX          DisplayString (SIZE(0..31))
    MAX-ACCESS      read-write
    STATUS          current
    DESCRIPTION     
            "A comment that is associated with this user."
    ::= { sonusUserListEntry 6 }

sonusUserListAccess OBJECT-TYPE
    SYNTAX          INTEGER { readOnly(1), readWrite(2), admin(3) }
    MAX-ACCESS      read-write
    STATUS          current
    DESCRIPTION     
            "The priviledge level of this user."
    DEFVAL          { readOnly }
    ::= { sonusUserListEntry 7 }

sonusUserListRowStatus OBJECT-TYPE
    SYNTAX          RowStatus
    MAX-ACCESS      read-write
    STATUS          current
    DESCRIPTION     
            "Row status object for this table."
    ::= { sonusUserListEntry 8 }

sonusUserListAccountAgeThreshold OBJECT-TYPE
    SYNTAX          Integer32 (0..999)
    MAX-ACCESS      read-write
    STATUS          current
    DESCRIPTION     
            "This object indicates how long in days an account is valid for.
             A value of 0 indicates aging is disabled."
    DEFVAL          { 0 }
    ::= { sonusUserListEntry 9 }

sonusUserListAccountAgeReset OBJECT-TYPE
    SYNTAX          INTEGER { undefined(1), reset(2) }
    MAX-ACCESS      read-write
    STATUS          current
    DESCRIPTION     
            "This object resets the age of an account. When read
             this object will always return noop(1)."
    ::= { sonusUserListEntry 10 }

sonusUserListPasswdAgeThreshold OBJECT-TYPE
    SYNTAX          Integer32 (0..999)
    MAX-ACCESS      read-write
    STATUS          current
    DESCRIPTION     
            "This object indicates how long in days a user password is valid for.
             A value of 0 indicates passowrd aging is disabled."
    DEFVAL          { 0 }
    ::= { sonusUserListEntry 11 }

sonusUserListLoginLockoutThreshold OBJECT-TYPE
    SYNTAX          Integer32 (0..15)
    MAX-ACCESS      read-write
    STATUS          current
    DESCRIPTION     
            "This object indicates how many succesive invalid login attempts
             can be made before an account is locked.  A value of 0 indicates
             lockout threshold is disabled."
    DEFVAL          { 0 }
    ::= { sonusUserListEntry 12 }

sonusUserListLoginLockoutDuration OBJECT-TYPE
    SYNTAX          Integer32 (0..360)
    MAX-ACCESS      read-write
    STATUS          current
    DESCRIPTION     
            "This object indicates how long in minutes an account is locked 
             after the lockout threshold has been exceeded."
    DEFVAL          { 1 }
    ::= { sonusUserListEntry 13 }

sonusUserListCliIdleTimeout OBJECT-TYPE
    SYNTAX          Integer32 (1..720)
    MAX-ACCESS      read-write
    STATUS          current
    DESCRIPTION     
            "This object indicates the inactivity timeout period
             in minutes before the users cli session is closed."
    DEFVAL          { 60 }
    ::= { sonusUserListEntry 14 }

sonusUserListStatusTable OBJECT-TYPE
    SYNTAX          SEQUENCE OF SonusUserListStatusEntry
    MAX-ACCESS      not-accessible
    STATUS          current
    DESCRIPTION     
            "This table specifies status of the user access list for the node."
    ::= { sonusUserList 3 }

sonusUserListStatusEntry OBJECT-TYPE
    SYNTAX          SonusUserListStatusEntry
    MAX-ACCESS      not-accessible
    STATUS          current
    DESCRIPTION     
            ""
    INDEX           { sonusUserListStatusIndex }
    ::= { sonusUserListStatusTable 1 }

SonusUserListStatusEntry ::=
    SEQUENCE {
        sonusUserListStatusIndex        Integer32,
        sonusUserListStatusLastConfigChange   DateAndTime,
        sonusUserListStatusInvalidLogins Integer32,
        sonusUserListStatusLoginLockedCount   Integer32,
        sonusUserListStatusLoginState   INTEGER,
        sonusUserListStatusAccountExpirationStr       OCTET STRING,
        sonusUserListStatusPasswdExpirationStr      OCTET STRING
    }

sonusUserListStatusIndex OBJECT-TYPE
    SYNTAX          Integer32 (1..8)
    MAX-ACCESS      not-accessible
    STATUS          current
    DESCRIPTION     
            "Identifies the target user list status entry."
    ::= { sonusUserListStatusEntry 1 }

sonusUserListStatusLastConfigChange OBJECT-TYPE
    SYNTAX          DateAndTime
    MAX-ACCESS      read-only
    STATUS          current
    DESCRIPTION     
            "Octet string that identifies the GMT timestamp of last
             successful SET PDU from this CLI user.
             
             field  octects  contents      range
             -----  -------  --------      -----
             1      1-2      year         0..65536
             2       3       month        1..12
             3       4       day          1..31
             4       5       hour         0..23
             5       6       minutes      0..59
             6       7       seconds      0..59
             7       8       deci-sec     0..9
             
             * Notes:
             - the value of year is in network-byte order"
    ::= { sonusUserListStatusEntry 2 }

sonusUserListStatusInvalidLogins OBJECT-TYPE
    SYNTAX          Integer32
    MAX-ACCESS      read-only
    STATUS          current
    DESCRIPTION     
            "This object indicates the number of invalid login attempts since last reboot."
    ::= { sonusUserListStatusEntry 3 }

sonusUserListStatusLoginLockedCount OBJECT-TYPE
    SYNTAX          Integer32
    MAX-ACCESS      read-only
    STATUS          current
    DESCRIPTION     
            "This object indicates the number of times an account has been locked due to invalid
             login attempts since last reboot."
    ::= { sonusUserListStatusEntry 4 }

sonusUserListStatusLoginState OBJECT-TYPE
    SYNTAX          INTEGER { disabled(1), enabled(2) }
    MAX-ACCESS      read-only
    STATUS          current
    DESCRIPTION     
            "This object indicates the login state of an account. The
             login state in locked when the number of invalid login attempts
              has been exceeded."
    ::= { sonusUserListStatusEntry 5 }

sonusUserListStatusAccountExpirationStr OBJECT-TYPE
    SYNTAX          OCTET STRING (SIZE(0..28))
    MAX-ACCESS      read-only
    STATUS          current
    DESCRIPTION     
            "This object displays the time at when this account expires."
    ::= { sonusUserListStatusEntry 6 }

sonusUserListStatusPasswdExpirationStr OBJECT-TYPE
    SYNTAX          OCTET STRING (SIZE(0..28))
    MAX-ACCESS      read-only
    STATUS          current
    DESCRIPTION     
            "This object displays the time when the password for this account
             expires."
    ::= { sonusUserListStatusEntry 7 }

sonusUserProfile OBJECT IDENTIFIER
    ::= { sonusUser 2 }

sonusUserProfileNextIndex OBJECT-TYPE
    SYNTAX          Integer32
    MAX-ACCESS      read-only
    STATUS          current
    DESCRIPTION     
            "The next valid index to use when creating an entry in
             the sonusUserProfileTable."
    ::= { sonusUserProfile 1 }

sonusUserProfileTable OBJECT-TYPE
    SYNTAX          SEQUENCE OF SonusUserProfileEntry
    MAX-ACCESS      not-accessible
    STATUS          current
    DESCRIPTION     
            "This table specifies the user access list for the node."
    ::= { sonusUserProfile 2 }

sonusUserProfileEntry OBJECT-TYPE
    SYNTAX          SonusUserProfileEntry
    MAX-ACCESS      not-accessible
    STATUS          current
    DESCRIPTION     
            ""
    INDEX           { sonusUserProfileIndex }
    ::= { sonusUserProfileTable 1 }

SonusUserProfileEntry ::=
    SEQUENCE {
        sonusUserProfileIndex           Integer32,
        sonusUserProfileName            SonusName,
        sonusUserProfileUserState       SonusAdminState,
        sonusUserProfileUserPasswd      DisplayString,
        sonusUserProfileUserComment     DisplayString,
        sonusUserProfileUserAccess      SonusAccessLevel,
        sonusUserProfileUserCommentState SonusAdminState,
        sonusUserProfileUserPasswdState SonusAdminState,
        sonusUserProfileUserAccessState SonusAdminState,
        sonusUserProfileUserStateState  SonusAdminState,
        sonusUserProfileRowStatus       RowStatus,
        sonusUserProfileUserAccountAgeThreshold       Integer32,
        sonusUserProfileUserPasswdAgeThreshold      Integer32,
        sonusUserProfileUserLoginLockoutThreshold         Integer32,
        sonusUserProfileUserLoginLockoutDuration        Integer32,
        sonusUserProfileUserCliIdleTimeout  Integer32,
        sonusUserProfileUserAccountAgeThresholdState            SonusAdminState,
        sonusUserProfileUserPasswdAgeThresholdState           SonusAdminState,
        sonusUserProfileUserLoginLockoutThresholdState              SonusAdminState,
        sonusUserProfileUserLoginLockoutDurationState             SonusAdminState,
        sonusUserProfileUserCliIdleTimeoutState       SonusAdminState
    }

sonusUserProfileIndex OBJECT-TYPE
    SYNTAX          Integer32 (1..6)
    MAX-ACCESS      read-only
    STATUS          current
    DESCRIPTION     
            "Identifies the target profile entry."
    ::= { sonusUserProfileEntry 1 }

sonusUserProfileName OBJECT-TYPE
    SYNTAX          SonusName
    MAX-ACCESS      read-write
    STATUS          current
    DESCRIPTION     
            "The name of this user profile.  This object is required to create the
             table entry."
    ::= { sonusUserProfileEntry 2 }

sonusUserProfileUserState OBJECT-TYPE
    SYNTAX          SonusAdminState
    MAX-ACCESS      read-write
    STATUS          current
    DESCRIPTION     
            "The administrative state of this profiled user entry."
    ::= { sonusUserProfileEntry 3 }

sonusUserProfileUserPasswd OBJECT-TYPE
    SYNTAX          DisplayString (SIZE(4..16))
    MAX-ACCESS      read-write
    STATUS          current
    DESCRIPTION     
            "The password for the profiled user entry."
    ::= { sonusUserProfileEntry 4 }

sonusUserProfileUserComment OBJECT-TYPE
    SYNTAX          DisplayString (SIZE(0..31))
    MAX-ACCESS      read-write
    STATUS          current
    DESCRIPTION     
            "The comment that is associated with the profiled user entry."
    ::= { sonusUserProfileEntry 5 }

sonusUserProfileUserAccess OBJECT-TYPE
    SYNTAX          SonusAccessLevel
    MAX-ACCESS      read-write
    STATUS          current
    DESCRIPTION     
            "The priviledge level of the profiled user entry."
    ::= { sonusUserProfileEntry 6 }

sonusUserProfileUserCommentState OBJECT-TYPE
    SYNTAX          SonusAdminState
    MAX-ACCESS      read-write
    STATUS          current
    DESCRIPTION     
            "Indicates whether the sonusUserProfileUserComment object is present 
             in this user profile."
    ::= { sonusUserProfileEntry 7 }

sonusUserProfileUserPasswdState OBJECT-TYPE
    SYNTAX          SonusAdminState
    MAX-ACCESS      read-write
    STATUS          current
    DESCRIPTION     
            "Indicates whether the sonusUserProfileUserPasswd object is present 
             in this user profile."
    ::= { sonusUserProfileEntry 8 }

sonusUserProfileUserAccessState OBJECT-TYPE
    SYNTAX          SonusAdminState
    MAX-ACCESS      read-write
    STATUS          current
    DESCRIPTION     
            "Indicates whether the sonusUserProfileUserAccess object is present 
             in this user profile."
    ::= { sonusUserProfileEntry 9 }

sonusUserProfileUserStateState OBJECT-TYPE
    SYNTAX          SonusAdminState
    MAX-ACCESS      read-write
    STATUS          current
    DESCRIPTION     
            "Indicates whether the sonusUserProfileUserState object is present 
             in this user profile."
    ::= { sonusUserProfileEntry 10 }

sonusUserProfileRowStatus OBJECT-TYPE
    SYNTAX          RowStatus
    MAX-ACCESS      read-write
    STATUS          current
    DESCRIPTION     
            "row status object"
    ::= { sonusUserProfileEntry 11 }

sonusUserProfileUserAccountAgeThreshold OBJECT-TYPE
    SYNTAX          Integer32 (0..999)
    MAX-ACCESS      read-write
    STATUS          current
    DESCRIPTION     
            "This object indicates how long in days an account is valid for.
             A value of 0 indicates aging is disabled."
    ::= { sonusUserProfileEntry 12 }

sonusUserProfileUserPasswdAgeThreshold OBJECT-TYPE
    SYNTAX          Integer32 (0..999)
    MAX-ACCESS      read-write
    STATUS          current
    DESCRIPTION     
            "This object indicates how long in days a user password is 
             valid for.  A value of 0 indicates passowrd aging is disabled."
    ::= { sonusUserProfileEntry 13 }

sonusUserProfileUserLoginLockoutThreshold OBJECT-TYPE
    SYNTAX          Integer32 (0..15)
    MAX-ACCESS      read-write
    STATUS          current
    DESCRIPTION     
            "This object indicates how many succesive invalid login attempts
             can be made before an account is locked.  A value of 0 indicates
             lockout threshold is disabled."
    ::= { sonusUserProfileEntry 14 }

sonusUserProfileUserLoginLockoutDuration OBJECT-TYPE
    SYNTAX          Integer32 (0..360)
    MAX-ACCESS      read-write
    STATUS          current
    DESCRIPTION     
            "This object indicates how long in minutes an account is locked 
             after the lockout threshold has been exceeded."
    ::= { sonusUserProfileEntry 15 }

sonusUserProfileUserCliIdleTimeout OBJECT-TYPE
    SYNTAX          Integer32 (1..720)
    MAX-ACCESS      read-write
    STATUS          current
    DESCRIPTION     
            "This object indicates the inactivity timeout period
             in minutes before the users cli session is closed."
    ::= { sonusUserProfileEntry 16 }

sonusUserProfileUserAccountAgeThresholdState OBJECT-TYPE
    SYNTAX          SonusAdminState
    MAX-ACCESS      read-write
    STATUS          current
    DESCRIPTION     
            "Indicates whether the sonusUserProfileUserAccountAgeThreshold object is present 
             in this user profile."
    ::= { sonusUserProfileEntry 17 }

sonusUserProfileUserPasswdAgeThresholdState OBJECT-TYPE
    SYNTAX          SonusAdminState
    MAX-ACCESS      read-write
    STATUS          current
    DESCRIPTION     
            "Indicates whether the sonusUserProfileUserPasswdAgeThreshold object is present 
             in this user profile."
    ::= { sonusUserProfileEntry 18 }

sonusUserProfileUserLoginLockoutThresholdState OBJECT-TYPE
    SYNTAX          SonusAdminState
    MAX-ACCESS      read-write
    STATUS          current
    DESCRIPTION     
            "Indicates whether the sonusUserProfileUserLoginLockoutThreshold object is present 
             in this user profile."
    ::= { sonusUserProfileEntry 19 }

sonusUserProfileUserLoginLockoutDurationState OBJECT-TYPE
    SYNTAX          SonusAdminState
    MAX-ACCESS      read-write
    STATUS          current
    DESCRIPTION     
            "Indicates whether the sonusUserProfileUserLoginLockoutDuration object is present 
             in this user profile."
    ::= { sonusUserProfileEntry 20 }

sonusUserProfileUserCliIdleTimeoutState OBJECT-TYPE
    SYNTAX          SonusAdminState
    MAX-ACCESS      read-write
    STATUS          current
    DESCRIPTION     
            "Indicates whether the sonusUserProfileUserCliIdleTimeout object is present 
             in this user profile."
    ::= { sonusUserProfileEntry 21 }

sonusSwLoad OBJECT IDENTIFIER
    ::= { sonusNodeMIBObjects 4 }

sonusSwLoadTable OBJECT-TYPE
    SYNTAX          SEQUENCE OF SonusSwLoadEntry
    MAX-ACCESS      not-accessible
    STATUS          current
    DESCRIPTION     
            "This table specifies the hardware type based software load table
             for the server modules in the node."
    ::= { sonusSwLoad 1 }

sonusSwLoadEntry OBJECT-TYPE
    SYNTAX          SonusSwLoadEntry
    MAX-ACCESS      not-accessible
    STATUS          current
    DESCRIPTION     
            ""
    INDEX           { sonusSwLoadAdmnIndex }
    ::= { sonusSwLoadTable 1 }

SonusSwLoadEntry ::=
    SEQUENCE {
        sonusSwLoadAdmnIndex            Integer32,
        sonusSwLoadAdmnImageName        DisplayString,
        sonusSwLoadAdmnHwType           ServerTypeID,
        sonusSwLoadAdmnRowStatus        RowStatus
    }

sonusSwLoadAdmnIndex OBJECT-TYPE
    SYNTAX          Integer32 (1..32)
    MAX-ACCESS      read-only
    STATUS          current
    DESCRIPTION     
            "Identifies the target software load entry."
    ::= { sonusSwLoadEntry 1 }

sonusSwLoadAdmnImageName OBJECT-TYPE
    SYNTAX          DisplayString (SIZE(1..15))
    MAX-ACCESS      read-write
    STATUS          current
    DESCRIPTION     
            "Identifies the name of the image to load for the hardware type
             identified by sonusSwLoadAdmnHwType."
    ::= { sonusSwLoadEntry 2 }

sonusSwLoadAdmnHwType OBJECT-TYPE
    SYNTAX          ServerTypeID
    MAX-ACCESS      read-write
    STATUS          current
    DESCRIPTION     
            "Identifies the target hardware type for the load image.  This object
             can only be written at row creation."
    ::= { sonusSwLoadEntry 3 }

sonusSwLoadAdmnRowStatus OBJECT-TYPE
    SYNTAX          RowStatus
    MAX-ACCESS      read-write
    STATUS          current
    DESCRIPTION     
            "The RowStatus object for this row."
    ::= { sonusSwLoadEntry 4 }

sonusSwLoadSpecTable OBJECT-TYPE
    SYNTAX          SEQUENCE OF SonusSwLoadSpecEntry
    MAX-ACCESS      not-accessible
    STATUS          current
    DESCRIPTION     
            "This table specifies the hardware type based software load table
             for the server modules in the node."
    ::= { sonusSwLoad 2 }

sonusSwLoadSpecEntry OBJECT-TYPE
    SYNTAX          SonusSwLoadSpecEntry
    MAX-ACCESS      not-accessible
    STATUS          current
    DESCRIPTION     
            ""
    INDEX           { sonusSwLoadSpecAdmnShelfIndex, 
                      sonusSwLoadSpecAdmnSlotIndex }
    ::= { sonusSwLoadSpecTable 1 }

SonusSwLoadSpecEntry ::=
    SEQUENCE {
        sonusSwLoadSpecAdmnShelfIndex   SonusShelfIndex,
        sonusSwLoadSpecAdmnSlotIndex    SonusSlotIndex,
        sonusSwLoadSpecAdmnImageName    DisplayString,
        sonusSwLoadSpecAdmnRowStatus    RowStatus
    }

sonusSwLoadSpecAdmnShelfIndex OBJECT-TYPE
    SYNTAX          SonusShelfIndex
    MAX-ACCESS      read-only
    STATUS          current
    DESCRIPTION     
            "Identifies the target shelf for this load entry entry."
    ::= { sonusSwLoadSpecEntry 1 }

sonusSwLoadSpecAdmnSlotIndex OBJECT-TYPE
    SYNTAX          SonusSlotIndex
    MAX-ACCESS      read-only
    STATUS          current
    DESCRIPTION     
            "Identifies the target slot within the chassis for this
             load entry."
    ::= { sonusSwLoadSpecEntry 2 }

sonusSwLoadSpecAdmnImageName OBJECT-TYPE
    SYNTAX          DisplayString (SIZE(0..15))
    MAX-ACCESS      read-write
    STATUS          current
    DESCRIPTION     
            "Identifies the name of the image to load."
    ::= { sonusSwLoadSpecEntry 3 }

sonusSwLoadSpecAdmnRowStatus OBJECT-TYPE
    SYNTAX          RowStatus
    MAX-ACCESS      read-write
    STATUS          current
    DESCRIPTION     
            "The RowStatus object for this row."
    ::= { sonusSwLoadSpecEntry 4 }

sonusParam OBJECT IDENTIFIER
    ::= { sonusNodeMIBObjects 5 }

sonusParamStatusObjects OBJECT IDENTIFIER
    ::= { sonusParam 1 }

sonusParamSaveSeqNumber OBJECT-TYPE
    SYNTAX          Integer32
    MAX-ACCESS      read-only
    STATUS          current
    DESCRIPTION     
            "The parameter save sequence number assigned to this parameter file.
             This value is unique within the current sequence epoch."
    ::= { sonusParamStatusObjects 1 }

sonusParamSaveTimeStart OBJECT-TYPE
    SYNTAX          Integer32
    MAX-ACCESS      read-only
    STATUS          current
    DESCRIPTION     
            "The system uptime, measured in milliseconds, when the last
             parameter save cycle started."
    ::= { sonusParamStatusObjects 2 }

sonusParamSaveTimeStop OBJECT-TYPE
    SYNTAX          Integer32
    MAX-ACCESS      read-only
    STATUS          current
    DESCRIPTION     
            "The system uptime, measured in milliseconds, when the last
             parameter save cycle ended."
    ::= { sonusParamStatusObjects 3 }

sonusParamSaveDuration OBJECT-TYPE
    SYNTAX          Integer32
    MAX-ACCESS      read-only
    STATUS          current
    DESCRIPTION     
            "The measured time in milliseconds to complete the last parameter
             save cycle."
    ::= { sonusParamStatusObjects 4 }

sonusParamSaveTotalBytes OBJECT-TYPE
    SYNTAX          Integer32
    MAX-ACCESS      read-only
    STATUS          current
    DESCRIPTION     
            "The number of bytes contained in the last binary parameter
             file saved."
    ::= { sonusParamStatusObjects 5 }

sonusParamSaveTotalRecords OBJECT-TYPE
    SYNTAX          Integer32
    MAX-ACCESS      read-only
    STATUS          current
    DESCRIPTION     
            "The number of individual parameter records contained in the last
             binary parameter file saved."
    ::= { sonusParamStatusObjects 6 }

sonusParamSaveFilename OBJECT-TYPE
    SYNTAX          DisplayString (SIZE(0..31))
    MAX-ACCESS      read-only
    STATUS          current
    DESCRIPTION     
            "Identifies the base filename of the parameter file being written."
    ::= { sonusParamStatusObjects 7 }

sonusParamSaveState OBJECT-TYPE
    SYNTAX          INTEGER { idle(1), synchronize(2), lock(3), 
                        holdoff(4), fopen(5), collect(6), fclose(7), 
                        done(8), retry(9), check(10) }
    MAX-ACCESS      read-only
    STATUS          current
    DESCRIPTION     
            "The current state of the active Management Server's parameter
             saving process."
    ::= { sonusParamStatusObjects 8 }

sonusParamLoadServer OBJECT-TYPE
    SYNTAX          IpAddress
    MAX-ACCESS      read-only
    STATUS          current
    DESCRIPTION     
            "The IP Address of the NFS server from which parameters were
             loaded from."
    ::= { sonusParamStatusObjects 9 }

sonusParamLoadFileType OBJECT-TYPE
    SYNTAX          INTEGER { primary(1), backup(2), temporary(3), 
                        none(4) }
    MAX-ACCESS      read-only
    STATUS          current
    DESCRIPTION     
            "The type of binary parameter which was loaded.  Under normal
             circumstances, the primary(1) parameter file will always be
             loaded.  When default parameters are used, no parameter file
             is loaded, and the value none(4) is used for the file type."
    ::= { sonusParamStatusObjects 10 }

sonusParamLoadStatus OBJECT-TYPE
    SYNTAX          INTEGER { defaults(1), success(2), paramError(3) }
    MAX-ACCESS      read-only
    STATUS          current
    DESCRIPTION     
            "Indicates the status of the last binary parameter file load.
             The value defaults(1) indicates that parameters were not loaded
             and that the node began with default parameters.  The value
             success(2) indicates that a binary parameter file was 
             successfully loaded when the node booted.  The value paramError(3)
             indicates that the node attempted to load a binary parameter file
             and that there was an error in the processing of the file.  The
             node may be running with a partial parameter file when this error
             is indicated."
    ::= { sonusParamStatusObjects 11 }

sonusParamLoadSeqNumber OBJECT-TYPE
    SYNTAX          Integer32
    MAX-ACCESS      read-only
    STATUS          current
    DESCRIPTION     
            "The sequence number of the parameter file that was loaded.
             This value is unique for the sequence epoch in which it was saved."
    ::= { sonusParamStatusObjects 12 }

sonusParamLoadTotalRecords OBJECT-TYPE
    SYNTAX          Integer32
    MAX-ACCESS      read-only
    STATUS          current
    DESCRIPTION     
            ""
    ::= { sonusParamStatusObjects 13 }

sonusParamLoadTotalBytes OBJECT-TYPE
    SYNTAX          Integer32
    MAX-ACCESS      read-only
    STATUS          current
    DESCRIPTION     
            ""
    ::= { sonusParamStatusObjects 14 }

sonusParamLoadDuration OBJECT-TYPE
    SYNTAX          Integer32
    MAX-ACCESS      read-only
    STATUS          current
    DESCRIPTION     
            ""
    ::= { sonusParamStatusObjects 15 }

sonusParamLoadSerialNum OBJECT-TYPE
    SYNTAX          DisplayString (SIZE(0..31))
    MAX-ACCESS      read-only
    STATUS          current
    DESCRIPTION     
            "Identifies the serial number of the node which created the
             parameter file loaded by this node."
    ::= { sonusParamStatusObjects 16 }

sonusParamSavePrimarySrvrState OBJECT-TYPE
    SYNTAX          INTEGER { unknown(1), failed(2), failing(3), 
                        behind(4), current(5), ahead(6), inactive(7) }
    MAX-ACCESS      read-only
    STATUS          current
    DESCRIPTION     
            "The current state of parameter saving to this NFS server."
    ::= { sonusParamStatusObjects 17 }

sonusParamSavePrimarySrvrReason OBJECT-TYPE
    SYNTAX          INTEGER { success(1), create(2), fopen(3), header(4), 
                        timer(5), nfs(6), flush(7), write(8), close(9), 
                        move(10), memory(11), none(12) }
    MAX-ACCESS      read-only
    STATUS          current
    DESCRIPTION     
            "The failure code associated with the last parameter save
             pass to this NFS server."
    ::= { sonusParamStatusObjects 18 }

sonusParamSaveSecondarySrvrState OBJECT-TYPE
    SYNTAX          INTEGER { unknown(1), failed(2), failing(3), 
                        behind(4), current(5), ahead(6), inactive(7) }
    MAX-ACCESS      read-only
    STATUS          current
    DESCRIPTION     
            "The current state of parameter saving to this NFS server."
    ::= { sonusParamStatusObjects 19 }

sonusParamSaveSecondarySrvrReason OBJECT-TYPE
    SYNTAX          INTEGER { success(1), create(2), fopen(3), header(4), 
                        timer(5), nfs(6), flush(7), write(8), close(9), 
                        move(10), memory(11), none(12) }
    MAX-ACCESS      read-only
    STATUS          current
    DESCRIPTION     
            "The failure code associated with the last parameter save
             pass to this NFS server."
    ::= { sonusParamStatusObjects 20 }

sonusParamLastSaveTime OBJECT-TYPE
    SYNTAX          DateAndTime
    MAX-ACCESS      read-only
    STATUS          current
    DESCRIPTION     
            "Octet string that identifies the GMT timestamp of last
             successful PIF write.
             
             field  octects  contents      range
             -----  -------  --------      -----
              1      1-2      year         0..65536
              2       3       month        1..12
              3       4       day          1..31
              4       5       hour         0..23
              5       6       minutes      0..59
              6       7       seconds      0..59
              7       8       deci-sec     0..9
             
              * Notes:
              - the value of year is in network-byte order "
    ::= { sonusParamStatusObjects 21 }

sonusParamSaveSeqEpoch OBJECT-TYPE
    SYNTAX          Integer32
    MAX-ACCESS      read-only
    STATUS          current
    DESCRIPTION     
            "The epoch in which this parameter file's save sequence number belongs."
    ::= { sonusParamStatusObjects 22 }

sonusParamLoadSeqEpoch OBJECT-TYPE
    SYNTAX          Integer32
    MAX-ACCESS      read-only
    STATUS          current
    DESCRIPTION     
            "The sequence epoch of the parameter file that was loaded."
    ::= { sonusParamStatusObjects 23 }

sonusParamLoadDisk OBJECT-TYPE
    SYNTAX          INTEGER { none(0), nfsServer(1), localDisk(2) }
    MAX-ACCESS      read-only
    STATUS          current
    DESCRIPTION     
            "The location where the parameter file was loaded from."
    ::= { sonusParamStatusObjects 24 }

sonusParamSaveLocalDiskState OBJECT-TYPE
    SYNTAX          INTEGER { unknown(1), failed(2), failing(3), 
                        behind(4), current(5), ahead(6), inactive(7) }
    MAX-ACCESS      read-only
    STATUS          current
    DESCRIPTION     
            "The current state of parameter saving to the local MNS disk (if one exists)."
    ::= { sonusParamStatusObjects 25 }

sonusParamSaveLocalDiskReason OBJECT-TYPE
    SYNTAX          INTEGER { success(1), create(2), fopen(3), header(4), 
                        timer(5), nfs(6), flush(7), write(8), close(9), 
                        move(10), memory(11), none(12) }
    MAX-ACCESS      read-only
    STATUS          current
    DESCRIPTION     
            "The failure code associated with the last parameter save
             pass to the local MNS disk (if one exists)."
    ::= { sonusParamStatusObjects 26 }

sonusParamAdminObject OBJECT IDENTIFIER
    ::= { sonusParam 2 }

sonusParamAdmnMaxIncrPifs OBJECT-TYPE
    SYNTAX          Integer32 (0..10)
    MAX-ACCESS      read-write
    STATUS          current
    DESCRIPTION     
            "The maximum of Incremental PIF files saved"
    ::= { sonusParamAdminObject 1 }

sonusParamAdmnCheck OBJECT-TYPE
    SYNTAX          INTEGER { noop(1), sync(2) }
    MAX-ACCESS      read-write
    STATUS          current
    DESCRIPTION     
            "When set to sync(2), this will cause the system to re-sync all
             parmeter files as needed.  When read this object will return noop(1)."
    DEFVAL          { noop }
    ::= { sonusParamAdminObject 2 }

sonusParamAdmnHoldoffTime OBJECT-TYPE
    SYNTAX          Integer32 (15..1800)
    MAX-ACCESS      read-write
    STATUS          current
    DESCRIPTION     
            "When configured, the system waits for holdoff time (in seconds) before
             writing the parameter file.  Note that the default value is larger on a
             management server module with a local disk."
    DEFVAL          { 15 }
    ::= { sonusParamAdminObject 3 }

sonusParamAdmnFlushSaveCycle OBJECT-TYPE
    SYNTAX          INTEGER { noop(1), flush(2) }
    MAX-ACCESS      read-write
    STATUS          current
    DESCRIPTION     
            "When set to flush(2), this will force param file save only if a save cycle 
             is pending.  When read this object will return noop(1)."
    DEFVAL          { noop }
    ::= { sonusParamAdminObject 4 }

sonusNfs OBJECT IDENTIFIER
    ::= { sonusNodeMIBObjects 6 }

sonusNfsAdmnTable OBJECT-TYPE
    SYNTAX          SEQUENCE OF SonusNfsAdmnEntry
    MAX-ACCESS      not-accessible
    STATUS          current
    DESCRIPTION     
            "This table specifies the configurable NFS options for each MNS in each shelf."
    ::= { sonusNfs 1 }

sonusNfsAdmnEntry OBJECT-TYPE
    SYNTAX          SonusNfsAdmnEntry
    MAX-ACCESS      not-accessible
    STATUS          current
    DESCRIPTION     
            ""
    INDEX           { sonusNfsAdmnShelfIndex, sonusNfsAdmnSlotIndex }
    ::= { sonusNfsAdmnTable 1 }

SonusNfsAdmnEntry ::=
    SEQUENCE {
        sonusNfsAdmnShelfIndex          SonusShelfIndex,
        sonusNfsAdmnSlotIndex           SonusMnsSlotIndex,
        sonusNfsAdmnMountServer         INTEGER,
        sonusNfsAdmnUnmountServer       INTEGER,
        sonusNfsAdmnToggleActiveServer  INTEGER,
        sonusNfsAdmnSetWritable         INTEGER
    }

sonusNfsAdmnShelfIndex OBJECT-TYPE
    SYNTAX          SonusShelfIndex
    MAX-ACCESS      read-only
    STATUS          current
    DESCRIPTION     
            "Identifies the target shelf.  This object returns the value of
             sonusNodeShelfStatIndex which was used to index into this table."
    ::= { sonusNfsAdmnEntry 1 }

sonusNfsAdmnSlotIndex OBJECT-TYPE
    SYNTAX          SonusMnsSlotIndex
    MAX-ACCESS      read-only
    STATUS          current
    DESCRIPTION     
            "Identifies the target MNS module slot within the shelf."
    ::= { sonusNfsAdmnEntry 2 }

sonusNfsAdmnMountServer OBJECT-TYPE
    SYNTAX          INTEGER { noop(1), primary(2), secondary(3) }
    MAX-ACCESS      read-write
    STATUS          current
    DESCRIPTION     
            "Mounts the Primary or Secondary NFS server using mount parameters
             obtained from the NVS Boot parameters sonusBparamNfsPrimary or
             sonusBparamNfsSecondary, and sonusBparamNfsMountPri or
             sonusBparamNfsMountSec.  Continuous retries will occur until the mount
             succeeds.  This object is always read as noop(1)."
    ::= { sonusNfsAdmnEntry 3 }

sonusNfsAdmnUnmountServer OBJECT-TYPE
    SYNTAX          INTEGER { noop(1), standby(2), active(3) }
    MAX-ACCESS      read-write
    STATUS          current
    DESCRIPTION     
            "Unmounts the active or standby NFS server.  The active NFS
             server can only be unmounted if there is a standby NFS server to
             switch to or if it is not in use, such as when an MNS25 is using
             its local disk exclusively.  Continuous retries will occur until
             the unmount succeeds.  This object is always read as noop(1)."
    ::= { sonusNfsAdmnEntry 4 }

sonusNfsAdmnToggleActiveServer OBJECT-TYPE
    SYNTAX          INTEGER { noop(1), toggle(2) }
    MAX-ACCESS      read-write
    STATUS          current
    DESCRIPTION     
            "Toggles the Active NFS server between the Primary and Secondary,
             provided both servers are currently mounted.  This object is always
             read as noop(1)."
    ::= { sonusNfsAdmnEntry 5 }

sonusNfsAdmnSetWritable OBJECT-TYPE
    SYNTAX          INTEGER { noop(1), primary(2), secondary(3) }
    MAX-ACCESS      read-write
    STATUS          current
    DESCRIPTION     
            "Clears the perception of a read-only condition on the Primary or
             Secondary NFS server, so that server will be considered viable as
             the Active server.  This object is always read as noop(1)."
    ::= { sonusNfsAdmnEntry 6 }

sonusNfsStatTable OBJECT-TYPE
    SYNTAX          SEQUENCE OF SonusNfsStatEntry
    MAX-ACCESS      not-accessible
    STATUS          current
    DESCRIPTION     
            "This table specifies NFS status objects for each MNS in each shelf."
    ::= { sonusNfs 2 }

sonusNfsStatEntry OBJECT-TYPE
    SYNTAX          SonusNfsStatEntry
    MAX-ACCESS      not-accessible
    STATUS          current
    DESCRIPTION     
            ""
    INDEX           { sonusNfsStatShelfIndex, sonusNfsStatSlotIndex }
    ::= { sonusNfsStatTable 1 }

SonusNfsStatEntry ::=
    SEQUENCE {
        sonusNfsStatShelfIndex          SonusShelfIndex,
        sonusNfsStatSlotIndex           SonusMnsSlotIndex,
        sonusNfsStatPrimaryStatus       INTEGER,
        sonusNfsStatSecondaryStatus     INTEGER,
        sonusNfsStatActiveServer        INTEGER,
        sonusNfsStatStandbyServer       INTEGER,
        sonusNfsStatPrimaryIP           IpAddress,
        sonusNfsStatSecondaryIP         IpAddress,
        sonusNfsStatPrimaryMount        DisplayString,
        sonusNfsStatSecondaryMount      DisplayString,
        sonusNfsStatPrimaryLastError    INTEGER,
        sonusNfsStatSecondaryLastError  INTEGER,
        sonusNfsStatPrimaryIP6          Ipv6Address,
        sonusNfsStatSecondaryIP6        Ipv6Address,
        sonusNfsStatPrimaryIpVersion    INTEGER,
        sonusNfsStatSecondaryIpVersion  INTEGER
    }

sonusNfsStatShelfIndex OBJECT-TYPE
    SYNTAX          SonusShelfIndex
    MAX-ACCESS      read-only
    STATUS          current
    DESCRIPTION     
            "Identifies the target shelf.  This object returns the value of
             sonusNodeShelfStatIndex which was used to index into this table."
    ::= { sonusNfsStatEntry 1 }

sonusNfsStatSlotIndex OBJECT-TYPE
    SYNTAX          SonusMnsSlotIndex
    MAX-ACCESS      read-only
    STATUS          current
    DESCRIPTION     
            "Identifies the target MNS module slot within the shelf."
    ::= { sonusNfsStatEntry 2 }

sonusNfsStatPrimaryStatus OBJECT-TYPE
    SYNTAX          INTEGER { mounted(1), mounting(2), unmounted(3), 
                        unmounting(4), readOnly(5), testing(6), 
                        failed(7), invalid(8) }
    MAX-ACCESS      read-only
    STATUS          current
    DESCRIPTION     
            "Indicates the mount status of the Primary NFS server: mounted and
             functioning properly, attemping to mount, indefinitely unmounted,
             attempting to unmount, mounted but read-only, testing connectivity,
             server failure, or invalid NFS parameters."
    ::= { sonusNfsStatEntry 7 }

sonusNfsStatSecondaryStatus OBJECT-TYPE
    SYNTAX          INTEGER { mounted(1), mounting(2), unmounted(3), 
                        unmounting(4), readOnly(5), testing(6), 
                        failed(7), invalid(8) }
    MAX-ACCESS      read-only
    STATUS          current
    DESCRIPTION     
            "Indicates the mount status of the Secondary NFS server: mounted and
             functioning properly, attemping to mount, indefinitely unmounted,
             attempting to unmount, mounted but read-only, testing connectivity,
             server failure, or invalid NFS parameters."
    ::= { sonusNfsStatEntry 8 }

sonusNfsStatActiveServer OBJECT-TYPE
    SYNTAX          INTEGER { none(1), primary(2), secondary(3) }
    MAX-ACCESS      read-only
    STATUS          current
    DESCRIPTION     
            "Indicates the current Active NFS server.  This may change due to NFS
             failures or NFS administrative operations."
    ::= { sonusNfsStatEntry 9 }

sonusNfsStatStandbyServer OBJECT-TYPE
    SYNTAX          INTEGER { none(1), primary(2), secondary(3) }
    MAX-ACCESS      read-only
    STATUS          current
    DESCRIPTION     
            "Indicates the current Standby NFS server.  This may change due to NFS
             failures or NFS administrative operations."
    ::= { sonusNfsStatEntry 10 }

sonusNfsStatPrimaryIP OBJECT-TYPE
    SYNTAX          IpAddress
    MAX-ACCESS      read-only
    STATUS          current
    DESCRIPTION     
            "The IP Address of the currently mounted Primary NFS server.  This may
             differ from the NVS settings if the user modified sonusBparamNfsPrimary
             without unmounting and remounting the Primary server."
    ::= { sonusNfsStatEntry 11 }

sonusNfsStatSecondaryIP OBJECT-TYPE
    SYNTAX          IpAddress
    MAX-ACCESS      read-only
    STATUS          current
    DESCRIPTION     
            "The IP Address of the currently mounted Secondary NFS server.  This
             may differ from the NVS settings if the user modified
             sonusBparamNfsSecondary without unmounting and remounting the Secondary
             server."
    ::= { sonusNfsStatEntry 12 }

sonusNfsStatPrimaryMount OBJECT-TYPE
    SYNTAX          DisplayString (SIZE(2..32))
    MAX-ACCESS      read-only
    STATUS          current
    DESCRIPTION     
            "The mount point currently in use on the Primary NFS server.  This may
             differ from the NVS settings if the user modified sonusBparamNfsMountPri
             without unmounting and remounting the Primary server."
    ::= { sonusNfsStatEntry 13 }

sonusNfsStatSecondaryMount OBJECT-TYPE
    SYNTAX          DisplayString (SIZE(2..32))
    MAX-ACCESS      read-only
    STATUS          current
    DESCRIPTION     
            "The mount point currently in use on the Secondary NFS server.  This may
             differ from the NVS settings if the user modified sonusBparamNfsMountSec
             without unmounting and remounting the Secondary server."
    ::= { sonusNfsStatEntry 14 }

sonusNfsStatPrimaryLastError OBJECT-TYPE
    SYNTAX          INTEGER { none(1), badVolumeStructure(2), 
                        tooManyFiles(3), volumeFull(4), 
                        serverHardError(5), quotaExceeded(6), 
                        staleNfsHandle(7), nfsTimeout(8), 
                        rpcCanNotSend(9), noAccess(10), other(11), 
                        nosuchfileordevice(12) }
    MAX-ACCESS      read-only
    STATUS          current
    DESCRIPTION     
            "Last consequential error received from the Primary NFS server.
             This object is reset to none(1) if the server is remounted."
    ::= { sonusNfsStatEntry 15 }

sonusNfsStatSecondaryLastError OBJECT-TYPE
    SYNTAX          INTEGER { none(1), badVolumeStructure(2), 
                        tooManyFiles(3), volumeFull(4), 
                        serverHardError(5), quotaExceeded(6), 
                        staleNfsHandle(7), nfsTimeout(8), 
                        rpcCanNotSend(9), noAccess(10), other(11), 
                        nosuchfileordevice(12) }
    MAX-ACCESS      read-only
    STATUS          current
    DESCRIPTION     
            "Last consequential error received from the Secondary NFS server.
             This object is reset to none(1) if the server is remounted."
    ::= { sonusNfsStatEntry 16 }

sonusNfsStatPrimaryIP6 OBJECT-TYPE
    SYNTAX          Ipv6Address
    MAX-ACCESS      read-only
    STATUS          current
    DESCRIPTION     
            "The IPV6 Address of the currently mounted Primary NFS server.  This may
             differ from the NVS settings if the user modified sonusBparamNfsPrimary
             without unmounting and remounting the Primary server."
    ::= { sonusNfsStatEntry 17 }

sonusNfsStatSecondaryIP6 OBJECT-TYPE
    SYNTAX          Ipv6Address
    MAX-ACCESS      read-only
    STATUS          current
    DESCRIPTION     
            "The IPV6 Address of the currently mounted Secondary NFS server.  This
             may differ from the NVS settings if the user modified
             sonusBparamNfsSecondary without unmounting and remounting the Secondary
             server."
    ::= { sonusNfsStatEntry 18 }

sonusNfsStatPrimaryIpVersion OBJECT-TYPE
    SYNTAX          INTEGER { afInet(2), afInet6(24) }
    MAX-ACCESS      read-only
    STATUS          current
    DESCRIPTION     
            "The IP Address type of the NFS Stat Primary."
    ::= { sonusNfsStatEntry 19 }

sonusNfsStatSecondaryIpVersion OBJECT-TYPE
    SYNTAX          INTEGER { afInet(2), afInet6(24) }
    MAX-ACCESS      read-only
    STATUS          current
    DESCRIPTION     
            "The IP Address type  of the NFS stat Secondary."
    ::= { sonusNfsStatEntry 20 }

sonusNfsShelfAdmnTable OBJECT-TYPE
    SYNTAX          SEQUENCE OF SonusNfsShelfAdmnEntry
    MAX-ACCESS      not-accessible
    STATUS          current
    DESCRIPTION     
            "This table specifies the configurable NFS redundancy options common to 
             both management server modules in a chassis."
    ::= { sonusNfs 3 }

sonusNfsShelfAdmnEntry OBJECT-TYPE
    SYNTAX          SonusNfsShelfAdmnEntry
    MAX-ACCESS      not-accessible
    STATUS          current
    DESCRIPTION     
            ""
    INDEX           { sonusNfsShelfAdmnShelfIndex }
    ::= { sonusNfsShelfAdmnTable 1 }

SonusNfsShelfAdmnEntry ::=
    SEQUENCE {
        sonusNfsShelfAdmnShelfIndex     SonusShelfIndex,
        sonusNfsShelfAdmnFallbackCntrl  INTEGER,
        sonusNfsShelfAdmnWaitToRevertTime Integer32
    }

sonusNfsShelfAdmnShelfIndex OBJECT-TYPE
    SYNTAX          SonusShelfIndex
    MAX-ACCESS      read-only
    STATUS          current
    DESCRIPTION     
            "Identifies the target chassis"
    ::= { sonusNfsShelfAdmnEntry 1 }

sonusNfsShelfAdmnFallbackCntrl OBJECT-TYPE
    SYNTAX          INTEGER { nonrevertive(1), revertive(2) }
    MAX-ACCESS      read-write
    STATUS          current
    DESCRIPTION     
            "The fallback control of NFS server redundancy. If the secondary NFS is active,
             revertive indicates that it will automatically revert back to primary NFS after
             the Wait To Revert time when the primary NFS becomes healthy. This setting is 
             common to both management server modules."
    DEFVAL          { nonrevertive }
    ::= { sonusNfsShelfAdmnEntry 2 }

sonusNfsShelfAdmnWaitToRevertTime OBJECT-TYPE
    SYNTAX          Integer32 (5..120)
    MAX-ACCESS      read-write
    STATUS          current
    DESCRIPTION     
            "The Wait to Revert Time (in minutes) of NFS server redundancy. This setting is
             applicable only in the revertive mode. In revertive mode, if the secondary NFS is
             active it will automatically revert back to primary NFS after Wait To Revert time
             when the primary NFS becomes healthy. This setting is common to both management 
             server modules."
    DEFVAL          { 5 }
    ::= { sonusNfsShelfAdmnEntry 3 }

sonusNfsNonFatalErrAdmnTable OBJECT-TYPE
    SYNTAX          SEQUENCE OF SonusNfsNonFatalErrAdmnEntry
    MAX-ACCESS      not-accessible
    STATUS          current
    DESCRIPTION     
            "This table specifies the configurable NFS Non Fatal Error counts."
    ::= { sonusNfs 4 }

sonusNfsNonFatalErrAdmnEntry OBJECT-TYPE
    SYNTAX          SonusNfsNonFatalErrAdmnEntry
    MAX-ACCESS      not-accessible
    STATUS          current
    DESCRIPTION     
            ""
    INDEX           { sonusNfsShelfIndex }
    ::= { sonusNfsNonFatalErrAdmnTable 1 }

SonusNfsNonFatalErrAdmnEntry ::=
    SEQUENCE {
        sonusNfsShelfIndex              SonusShelfIndex,
        nfsErrorPriNfsAdminTimeoutThreshold   Integer32,
        nfsErrorPriNfsAdminTimerValue   Integer32,
        nfsErrorAdminState              INTEGER
    }

sonusNfsShelfIndex OBJECT-TYPE
    SYNTAX          SonusShelfIndex
    MAX-ACCESS      read-only
    STATUS          current
    DESCRIPTION     
            "Identifies the target chassis"
    ::= { sonusNfsNonFatalErrAdmnEntry 1 }

nfsErrorPriNfsAdminTimeoutThreshold OBJECT-TYPE
    SYNTAX          Integer32
    MAX-ACCESS      read-write
    STATUS          current
    DESCRIPTION     
            "Threshold value for number of timeouts in the configured duration"
    ::= { sonusNfsNonFatalErrAdmnEntry 2 }

nfsErrorPriNfsAdminTimerValue OBJECT-TYPE
    SYNTAX          Integer32
    MAX-ACCESS      read-write
    STATUS          current
    DESCRIPTION     
            "Duration for which the number of write failures are observed (in seconds)."
    ::= { sonusNfsNonFatalErrAdmnEntry 3 }

nfsErrorAdminState OBJECT-TYPE
    SYNTAX          INTEGER { disabled(0), enabled(1) }
    MAX-ACCESS      read-write
    STATUS          current
    DESCRIPTION     
            "Admin state for this feature."
    ::= { sonusNfsNonFatalErrAdmnEntry 4 }

sonusNfsNonFatalErrStatTable OBJECT-TYPE
    SYNTAX          SEQUENCE OF SonusNfsNonFatalErrStatEntry
    MAX-ACCESS      not-accessible
    STATUS          current
    DESCRIPTION     
            "This table specifies the configurable NFS Non Fatal Error counts."
    ::= { sonusNfs 5 }

sonusNfsNonFatalErrStatEntry OBJECT-TYPE
    SYNTAX          SonusNfsNonFatalErrStatEntry
    MAX-ACCESS      not-accessible
    STATUS          current
    DESCRIPTION     
            ""
    INDEX           { sonusNfsStatsShelfIndex }
    ::= { sonusNfsNonFatalErrStatTable 1 }

SonusNfsNonFatalErrStatEntry ::=
    SEQUENCE {
        sonusNfsStatsShelfIndex         SonusShelfIndex,
        nfsErrorSbyNfsState             SonusAdminState,
        nfsErrorPriNfsTimeoutRunningCounter   Integer32,
        nfsErrorSwitchoverCounter       Integer32
    }

sonusNfsStatsShelfIndex OBJECT-TYPE
    SYNTAX          SonusShelfIndex
    MAX-ACCESS      read-only
    STATUS          current
    DESCRIPTION     
            "Identifies the target chassis"
    ::= { sonusNfsNonFatalErrStatEntry 1 }

nfsErrorSbyNfsState OBJECT-TYPE
    SYNTAX          SonusAdminState
    MAX-ACCESS      read-write
    STATUS          current
    DESCRIPTION     
            "State of standby NFS server."
    ::= { sonusNfsNonFatalErrStatEntry 2 }

nfsErrorPriNfsTimeoutRunningCounter OBJECT-TYPE
    SYNTAX          Integer32
    MAX-ACCESS      read-write
    STATUS          current
    DESCRIPTION     
            "Count of number of timeout errors
             encountered in the configured duration."
    ::= { sonusNfsNonFatalErrStatEntry 3 }

nfsErrorSwitchoverCounter OBJECT-TYPE
    SYNTAX          Integer32
    MAX-ACCESS      read-write
    STATUS          current
    DESCRIPTION     
            "Number of switchovers from last GSX restart."
    ::= { sonusNfsNonFatalErrStatEntry 4 }

sonusLocalDisk OBJECT IDENTIFIER
    ::= { sonusNodeMIBObjects 7 }

sonusLocalDiskStatTable OBJECT-TYPE
    SYNTAX          SEQUENCE OF SonusLocalDiskStatEntry
    MAX-ACCESS      not-accessible
    STATUS          current
    DESCRIPTION     
            "This table specifies Local Disk status objects for the MNS's in each shelf."
    ::= { sonusLocalDisk 1 }

sonusLocalDiskStatEntry OBJECT-TYPE
    SYNTAX          SonusLocalDiskStatEntry
    MAX-ACCESS      not-accessible
    STATUS          current
    DESCRIPTION     
            ""
    INDEX           { sonusLocalDiskStatShelfIndex }
    ::= { sonusLocalDiskStatTable 1 }

SonusLocalDiskStatEntry ::=
    SEQUENCE {
        sonusLocalDiskStatShelfIndex    SonusShelfIndex,
        sonusLocalDiskStatActiveDiskStatus  INTEGER,
        sonusLocalDiskStatStandbyDiskStatus   INTEGER,
        sonusLocalDiskStatDiskSyncStatus INTEGER,
        sonusLocalDiskStatActiveDiskSize Integer32,
        sonusLocalDiskStatStandbyDiskSize Integer32,
        sonusLocalDiskStatUsableDiskSpace Integer32,
        sonusLocalDiskStatActiveDiskFree Integer32,
        sonusLocalDiskStatStandbyDiskFree Integer32,
        sonusLocalDiskStatActiveDiskPercentUsed       Integer32,
        sonusLocalDiskStatStandbyDiskPercentUsed        Integer32
    }

sonusLocalDiskStatShelfIndex OBJECT-TYPE
    SYNTAX          SonusShelfIndex
    MAX-ACCESS      read-only
    STATUS          current
    DESCRIPTION     
            "Identifies the target shelf.  This object returns the value of
             sonusNodeShelfStatIndex which was used to index into this table."
    ::= { sonusLocalDiskStatEntry 1 }

sonusLocalDiskStatActiveDiskStatus OBJECT-TYPE
    SYNTAX          INTEGER { unavailable(0), unmounted(1), 
                        unmounting(2), mounted(3), mounting(4) }
    MAX-ACCESS      read-only
    STATUS          current
    DESCRIPTION     
            "Indicates the status of the Active MNS disk."
    ::= { sonusLocalDiskStatEntry 2 }

sonusLocalDiskStatStandbyDiskStatus OBJECT-TYPE
    SYNTAX          INTEGER { unavailable(0), unmounted(1), 
                        unmounting(2), mounted(3), mounting(4) }
    MAX-ACCESS      read-only
    STATUS          current
    DESCRIPTION     
            "Indicates the status of the Standby MNS disk."
    ::= { sonusLocalDiskStatEntry 3 }

sonusLocalDiskStatDiskSyncStatus OBJECT-TYPE
    SYNTAX          INTEGER { notSynced(0), syncing(1), 
                        operationalSynced(2), fullSynced(3), 
                        mirroring(4) }
    MAX-ACCESS      read-only
    STATUS          current
    DESCRIPTION     
            "Indicates the synchronization status between the Active and Standby
             MNS disks."
    ::= { sonusLocalDiskStatEntry 4 }

sonusLocalDiskStatActiveDiskSize OBJECT-TYPE
    SYNTAX          Integer32
    MAX-ACCESS      read-only
    STATUS          current
    DESCRIPTION     
            "Indicates the physical size of the Active MNS disk in kilobytes."
    ::= { sonusLocalDiskStatEntry 5 }

sonusLocalDiskStatStandbyDiskSize OBJECT-TYPE
    SYNTAX          Integer32
    MAX-ACCESS      read-only
    STATUS          current
    DESCRIPTION     
            "Indicates the physical size of the Standby MNS disk in kilobytes."
    ::= { sonusLocalDiskStatEntry 6 }

sonusLocalDiskStatUsableDiskSpace OBJECT-TYPE
    SYNTAX          Integer32
    MAX-ACCESS      read-only
    STATUS          current
    DESCRIPTION     
            "Indicates the usable disk space on both Active and Standby MNS disks
             in kilobytes."
    ::= { sonusLocalDiskStatEntry 7 }

sonusLocalDiskStatActiveDiskFree OBJECT-TYPE
    SYNTAX          Integer32
    MAX-ACCESS      read-only
    STATUS          current
    DESCRIPTION     
            "Indicates the free disk space on the Active MNS in kilobytes."
    ::= { sonusLocalDiskStatEntry 8 }

sonusLocalDiskStatStandbyDiskFree OBJECT-TYPE
    SYNTAX          Integer32
    MAX-ACCESS      read-only
    STATUS          current
    DESCRIPTION     
            "Indicates the free disk space on the Standby MNS in kilobytes."
    ::= { sonusLocalDiskStatEntry 9 }

sonusLocalDiskStatActiveDiskPercentUsed OBJECT-TYPE
    SYNTAX          Integer32
    MAX-ACCESS      read-only
    STATUS          current
    DESCRIPTION     
            "Indicates the percentage of the usable disk space in use on the
             Active MNS."
    ::= { sonusLocalDiskStatEntry 10 }

sonusLocalDiskStatStandbyDiskPercentUsed OBJECT-TYPE
    SYNTAX          Integer32
    MAX-ACCESS      read-only
    STATUS          current
    DESCRIPTION     
            "Indicates the percentage of the usable disk space in use on the
             Standby MNS."
    ::= { sonusLocalDiskStatEntry 11 }

sonusCli OBJECT IDENTIFIER
    ::= { sonusNodeMIBObjects 8 }

sonusCliConfigObjects OBJECT IDENTIFIER
    ::= { sonusCli 1 }

sonusCliDefaultBannerState OBJECT-TYPE
    SYNTAX          SonusAdminState
    MAX-ACCESS      read-write
    STATUS          current
    DESCRIPTION     
            "Toggle default (internal) CLI login banner"
    DEFVAL          { enabled }
    ::= { sonusCliConfigObjects 1 }

sonusDflush OBJECT IDENTIFIER
    ::= { sonusNodeMIBObjects 9 }

sonusDflushConfigObjects OBJECT IDENTIFIER
    ::= { sonusDflush 1 }

sonusSoftwareDownloadEntityType OBJECT-TYPE
    SYNTAX          INTEGER { bootfile(1), announcement(2), scripts(3) }
    MAX-ACCESS      read-write
    STATUS          current
    DESCRIPTION     
            "This object configures the filetype to be downloaded, 
             as a part of Software version download.It could be either 
             Bootfile,announcements or scripts."
    DEFVAL          { bootfile }
    ::= { sonusDflushConfigObjects 1 }

sonusSoftwareDownloadServerIpAddress OBJECT-TYPE
    SYNTAX          IpAddress
    MAX-ACCESS      read-write
    STATUS          current
    DESCRIPTION     
            "This object configures the IpAddress from where the software 
             package needs to be FTP-ed"
    ::= { sonusDflushConfigObjects 2 }

sonusSoftwareDownloadServerUserName OBJECT-TYPE
    SYNTAX          DisplayString (SIZE(0..255))
    MAX-ACCESS      read-write
    STATUS          current
    DESCRIPTION     
            "This object configures the username for the server to
             download software package"
    ::= { sonusDflushConfigObjects 3 }

sonusSoftwareDownloadServerPassword OBJECT-TYPE
    SYNTAX          DisplayString (SIZE(0..31))
    MAX-ACCESS      read-write
    STATUS          current
    DESCRIPTION     
            "This object configures the password of the username 
             provided do download software package"
    ::= { sonusDflushConfigObjects 4 }

sonusSoftwareDownloadEntityName OBJECT-TYPE
    SYNTAX          DisplayString (SIZE(0..255))
    MAX-ACCESS      read-write
    STATUS          current
    DESCRIPTION     
            "This object configures the entity/file to be downloaded.
             It could be either bootfile,announcement or scripts"
    ::= { sonusDflushConfigObjects 5 }

sonusSoftwareDownloadHalt OBJECT-TYPE
    SYNTAX          INTEGER { ready(1), halt(2) }
    MAX-ACCESS      read-write
    STATUS          current
    DESCRIPTION     
            "This object halts Software Download initiated by the user"
    DEFVAL          { ready }
    ::= { sonusDflushConfigObjects 6 }

sonusSoftwareDownloadStatus OBJECT-TYPE
    SYNTAX          SonusSoftwareDownloadStatus
    MAX-ACCESS      read-write
    STATUS          current
    DESCRIPTION     
            "Status of Software download"
    ::= { sonusDflushConfigObjects 7 }

sonusDflushSoftwareVersionStatTable OBJECT-TYPE
    SYNTAX          SEQUENCE OF SonusDflushSoftwareVersionStatEntry
    MAX-ACCESS      not-accessible
    STATUS          current
    DESCRIPTION     
            "This table specifies Dflush Software Version status objects"
    ::= { sonusDflush 2 }

sonusDflushSoftwareVersionStatEntry OBJECT-TYPE
    SYNTAX          SonusDflushSoftwareVersionStatEntry
    MAX-ACCESS      not-accessible
    STATUS          current
    DESCRIPTION     
            ""
    INDEX           { sonusDflushStatSoftwareVersionDirCount }
    ::= { sonusDflushSoftwareVersionStatTable 1 }

SonusDflushSoftwareVersionStatEntry ::=
    SEQUENCE {
        sonusDflushStatSoftwareVersionDirName     DisplayString,
        sonusDflushStatSoftwareVersionAction    INTEGER,
        sonusDflushStatSoftwareVersionDirCount      Integer32
    }

sonusDflushStatSoftwareVersionDirName OBJECT-TYPE
    SYNTAX          DisplayString (SIZE(1..128))
    MAX-ACCESS      read-only
    STATUS          current
    DESCRIPTION     
            "This object stores the directory name, 
             for the versions present in LocalDisk"
    ::= { sonusDflushSoftwareVersionStatEntry 1 }

sonusDflushStatSoftwareVersionAction OBJECT-TYPE
    SYNTAX          INTEGER { delete(1) }
    MAX-ACCESS      read-write
    STATUS          current
    DESCRIPTION     
            "This object  stores currect action, 
             to delete a version from localdisk."
    ::= { sonusDflushSoftwareVersionStatEntry 2 }

sonusDflushStatSoftwareVersionDirCount OBJECT-TYPE
    SYNTAX          Integer32
    MAX-ACCESS      read-write
    STATUS          current
    DESCRIPTION     
            "This object maintains the count of directories that have been
             read/displayed"
    ::= { sonusDflushSoftwareVersionStatEntry 3 }

sonusDflushSoftwareVersionConfigObjects OBJECT IDENTIFIER
    ::= { sonusDflush 3 }

sonusDflushSoftwareVersionAdmnAction OBJECT-TYPE
    SYNTAX          INTEGER { delete(1) }
    MAX-ACCESS      read-write
    STATUS          current
    DESCRIPTION     
            "This object configures the delete action for software version,
             delete the software version directory from local disk."
    ::= { sonusDflushSoftwareVersionConfigObjects 1 }

sonusDflushSoftwareVersionAdmnDirName OBJECT-TYPE
    SYNTAX          DisplayString (SIZE(0..255))
    MAX-ACCESS      read-write
    STATUS          current
    DESCRIPTION     
            "This object configures the Directory Name that needs to be 
             deleted from local disk."
    ::= { sonusDflushSoftwareVersionConfigObjects 2 }

sonusDflushNetworkFailureEventLogTable OBJECT-TYPE
    SYNTAX          SEQUENCE OF SonusDflushNetworkFailureEventLogEntry
    MAX-ACCESS      not-accessible
    STATUS          current
    DESCRIPTION     
            "Event log configuration table for Network Failure"
    ::= { sonusDflush 5 }

sonusDflushNetworkFailureEventLogEntry OBJECT-TYPE
    SYNTAX          SonusDflushNetworkFailureEventLogEntry
    MAX-ACCESS      not-accessible
    STATUS          current
    DESCRIPTION     
            "An entry of Event Log configuration related to each
             event log destination type."
    INDEX           { sonusEventLogNetworkFailureType }
    ::= { sonusDflushNetworkFailureEventLogTable 1 }

SonusDflushNetworkFailureEventLogEntry ::=
    SEQUENCE {
        sonusEventLogNetworkFailureType INTEGER,
        sonusEventLogNetworkFailureServerIpAddress          IpAddress,
        sonusEventLogNetworkFailureServerUserName         DisplayString,
        sonusEventLogNetworkFailureServerPassword         DisplayString,
        sonusEventLogNetworkFailurePrimaryPath      DisplayString,
        sonusEventLogNetworkFailureSecondaryPath        DisplayString,
        sonusEventLogNetworkFailureState SonusAdminState,
        sonusEventLogNetworkFailureInheritIpAddress           SonusAdminState
    }

sonusEventLogNetworkFailureType OBJECT-TYPE
    SYNTAX          INTEGER { log(1), pms(2) }
    MAX-ACCESS      read-only
    STATUS          current
    DESCRIPTION     
            "The type of the event log.  Each type has separate
             configuration parameters and logs to different destination."
    ::= { sonusDflushNetworkFailureEventLogEntry 1 }

sonusEventLogNetworkFailureServerIpAddress OBJECT-TYPE
    SYNTAX          IpAddress
    MAX-ACCESS      read-write
    STATUS          current
    DESCRIPTION     
            "IP Address of PMS/Log fail over ftp server"
    ::= { sonusDflushNetworkFailureEventLogEntry 2 }

sonusEventLogNetworkFailureServerUserName OBJECT-TYPE
    SYNTAX          DisplayString (SIZE(0..127))
    MAX-ACCESS      read-write
    STATUS          current
    DESCRIPTION     
            "Name of the user for the FTP server."
    ::= { sonusDflushNetworkFailureEventLogEntry 3 }

sonusEventLogNetworkFailureServerPassword OBJECT-TYPE
    SYNTAX          DisplayString (SIZE(0..31))
    MAX-ACCESS      read-write
    STATUS          current
    DESCRIPTION     
            "password of the user for the FTP server"
    ::= { sonusDflushNetworkFailureEventLogEntry 4 }

sonusEventLogNetworkFailurePrimaryPath OBJECT-TYPE
    SYNTAX          DisplayString (SIZE(0..255))
    MAX-ACCESS      read-write
    STATUS          current
    DESCRIPTION     
            "Needs the path of the destination server, where we want to 
             FTP the cached data."
    ::= { sonusDflushNetworkFailureEventLogEntry 5 }

sonusEventLogNetworkFailureSecondaryPath OBJECT-TYPE
    SYNTAX          DisplayString (SIZE(0..255))
    MAX-ACCESS      read-write
    STATUS          current
    DESCRIPTION     
            "Needs the alternate path(used by DSI), where we want to 
             FTP the cached data"
    ::= { sonusDflushNetworkFailureEventLogEntry 6 }

sonusEventLogNetworkFailureState OBJECT-TYPE
    SYNTAX          SonusAdminState
    MAX-ACCESS      read-write
    STATUS          current
    DESCRIPTION     
            "Configure the state for to trigger NFO related Admn changes."
    DEFVAL          { disabled }
    ::= { sonusDflushNetworkFailureEventLogEntry 7 }

sonusEventLogNetworkFailureInheritIpAddress OBJECT-TYPE
    SYNTAX          SonusAdminState
    MAX-ACCESS      read-write
    STATUS          current
    DESCRIPTION     
            "Inherit Ipaddress from DSI or NFS which is already configured."
    DEFVAL          { disabled }
    ::= { sonusDflushNetworkFailureEventLogEntry 8 }

sonusDflushNetworkFailureTable OBJECT-TYPE
    SYNTAX          SEQUENCE OF SonusDflushNetworkFailureEntry
    MAX-ACCESS      not-accessible
    STATUS          current
    DESCRIPTION     
            "Network Failover Admin table for Network Failure"
    ::= { sonusDflush 6 }

sonusDflushNetworkFailureEntry OBJECT-TYPE
    SYNTAX          SonusDflushNetworkFailureEntry
    MAX-ACCESS      not-accessible
    STATUS          current
    DESCRIPTION     
            "An entry of Network Failure Admin"
    INDEX           { sonusDflushNetworkFailureIndex }
    ::= { sonusDflushNetworkFailureTable 1 }

SonusDflushNetworkFailureEntry ::=
    SEQUENCE {
        sonusDflushNetworkFailureIndex  Integer32,
        sonusDflushNetworkFailureState  SonusAdminState,
        sonusDflushNetworkFailureMode   SonusServiceState,
        sonusDflushNetworkFailureAction SonusAdminAction,
        sonusDflushNetworkFailureDryupTimeout     Integer32,
        sonusDflushNetworkFailureCamRecordCount       Integer32,
        sonusDflushNetworkFailureCamFileSize    Integer32,
        sonusDflushNetworkFailureLogFileSize    Integer32,
        sonusDflushNetworkFailureFileKeepCount      Integer32
    }

sonusDflushNetworkFailureIndex OBJECT-TYPE
    SYNTAX          Integer32
    MAX-ACCESS      read-only
    STATUS          current
    DESCRIPTION     
            "NFO index, there will only be one entry for NFO."
    DEFVAL          { 1 }
    ::= { sonusDflushNetworkFailureEntry 1 }

sonusDflushNetworkFailureState OBJECT-TYPE
    SYNTAX          SonusAdminState
    MAX-ACCESS      read-write
    STATUS          current
    DESCRIPTION     
            "Configure the state for EventLog Network Failover"
    DEFVAL          { disabled }
    ::= { sonusDflushNetworkFailureEntry 2 }

sonusDflushNetworkFailureMode OBJECT-TYPE
    SYNTAX          SonusServiceState
    MAX-ACCESS      read-write
    STATUS          current
    DESCRIPTION     
            "The mode of operation for EventLog Network Failover"
    DEFVAL          { outOfService }
    ::= { sonusDflushNetworkFailureEntry 3 }

sonusDflushNetworkFailureAction OBJECT-TYPE
    SYNTAX          SonusAdminAction
    MAX-ACCESS      read-write
    STATUS          current
    DESCRIPTION     
            "The type of action dryup/forced during on Local Disk logging during EventLog Network Failover"
    DEFVAL          { force }
    ::= { sonusDflushNetworkFailureEntry 4 }

sonusDflushNetworkFailureDryupTimeout OBJECT-TYPE
    SYNTAX          Integer32 (1..300)
    MAX-ACCESS      read-write
    STATUS          current
    DESCRIPTION     
            "The timeout in minutes for dryup action on EventLog Network Failover"
    DEFVAL          { 10 }
    ::= { sonusDflushNetworkFailureEntry 5 }

sonusDflushNetworkFailureCamRecordCount OBJECT-TYPE
    SYNTAX          Integer32
    MAX-ACCESS      read-write
    STATUS          current
    DESCRIPTION     
            "Configuration for Cam Record Count"
    DEFVAL          { 2000 }
    ::= { sonusDflushNetworkFailureEntry 6 }

sonusDflushNetworkFailureCamFileSize OBJECT-TYPE
    SYNTAX          Integer32
    MAX-ACCESS      read-write
    STATUS          current
    DESCRIPTION     
            "Configuration for Cam File Size"
    DEFVAL          { 1000 }
    ::= { sonusDflushNetworkFailureEntry 7 }

sonusDflushNetworkFailureLogFileSize OBJECT-TYPE
    SYNTAX          Integer32
    MAX-ACCESS      read-write
    STATUS          current
    DESCRIPTION     
            "Configuration for Log File Size"
    DEFVAL          { 1000 }
    ::= { sonusDflushNetworkFailureEntry 8 }

sonusDflushNetworkFailureFileKeepCount OBJECT-TYPE
    SYNTAX          Integer32
    MAX-ACCESS      read-write
    STATUS          current
    DESCRIPTION     
            "Configuration for Log File Size"
    DEFVAL          { 512 }
    ::= { sonusDflushNetworkFailureEntry 9 }

sonusDflushNfoStatisticsTable OBJECT-TYPE
    SYNTAX          SEQUENCE OF SonusDflushNfoStatisticsEntry
    MAX-ACCESS      not-accessible
    STATUS          current
    DESCRIPTION     
            "This table specifies Dflush Network Failover status objects"
    ::= { sonusDflush 7 }

sonusDflushNfoStatisticsEntry OBJECT-TYPE
    SYNTAX          SonusDflushNfoStatisticsEntry
    MAX-ACCESS      not-accessible
    STATUS          current
    DESCRIPTION     
            "This object contains the statistics
             related to the EVENTS generated during
             NFO"
    INDEX           { sonusDflushLogType }
    ::= { sonusDflushNfoStatisticsTable 1 }

SonusDflushNfoStatisticsEntry ::=
    SEQUENCE {
        sonusDflushLogType              INTEGER,
        sonusDflushNumOfFilesSent       Integer32,
        sonusDflushNumOfFilesRemaining  Integer32,
        sonusDflushFtpServerIpAddress   IpAddress,
        sonusDflushFtpPath              DisplayString,
        sonusDflushCurrentFile          DisplayString,
        sonusDflushLoginStatus          INTEGER
    }

sonusDflushLogType OBJECT-TYPE
    SYNTAX          INTEGER { sys(0), dbg(1), trc(2), act(3), pfm(4) }
    MAX-ACCESS      read-only
    STATUS          current
    DESCRIPTION     
            "This object defines the type of log for which
             the statistics are being displayed now "
    DEFVAL          { 0 }
    ::= { sonusDflushNfoStatisticsEntry 1 }

sonusDflushNumOfFilesSent OBJECT-TYPE
    SYNTAX          Integer32
    MAX-ACCESS      read-only
    STATUS          current
    DESCRIPTION     
            "This object defines the number of files 
             sent by the Network Failover Feature since
             the admin state was set to ENABLED"
    DEFVAL          { 0 }
    ::= { sonusDflushNfoStatisticsEntry 2 }

sonusDflushNumOfFilesRemaining OBJECT-TYPE
    SYNTAX          Integer32
    MAX-ACCESS      read-only
    STATUS          current
    DESCRIPTION     
            "This object defines the number of files of the  
             specified log type that are remaining to be sent"
    DEFVAL          { 0 }
    ::= { sonusDflushNfoStatisticsEntry 3 }

sonusDflushFtpServerIpAddress OBJECT-TYPE
    SYNTAX          IpAddress
    MAX-ACCESS      read-only
    STATUS          current
    DESCRIPTION     
            "This object defines the IP address to which
             the file belonging to the specified log type
             is being sent to"
    ::= { sonusDflushNfoStatisticsEntry 4 }

sonusDflushFtpPath OBJECT-TYPE
    SYNTAX          DisplayString (SIZE(0..128))
    MAX-ACCESS      read-only
    STATUS          current
    DESCRIPTION     
            "This object defines the  path to which the file
             belonging to the specified log type is being 
             uploaded to"
    ::= { sonusDflushNfoStatisticsEntry 5 }

sonusDflushCurrentFile OBJECT-TYPE
    SYNTAX          DisplayString (SIZE(0..128))
    MAX-ACCESS      read-only
    STATUS          current
    DESCRIPTION     
            "This object defines the file belonging to
             the specified log type being transferred now"
    ::= { sonusDflushNfoStatisticsEntry 6 }

sonusDflushLoginStatus OBJECT-TYPE
    SYNTAX          INTEGER { unavailable(0), failure(1), success(2), 
                        unreachable(3) }
    MAX-ACCESS      read-only
    STATUS          current
    DESCRIPTION     
            "This object defines the status of login"
    DEFVAL          { 1 }
    ::= { sonusDflushNfoStatisticsEntry 7 }

sonusDflushNetworkFailoverDiskUsageStatTable OBJECT-TYPE
    SYNTAX          SEQUENCE OF SonusDflushNetworkFailoverDiskUsageStatEntry
    MAX-ACCESS      not-accessible
    STATUS          current
    DESCRIPTION     
            "This table specifies Disk Usage for ACT SYS PFM and
             TRC directory"
    ::= { sonusDflush 8 }

sonusDflushNetworkFailoverDiskUsageStatEntry OBJECT-TYPE
    SYNTAX          SonusDflushNetworkFailoverDiskUsageStatEntry
    MAX-ACCESS      not-accessible
    STATUS          current
    DESCRIPTION     
            "This object holds the amount of disk
             space used by each log type during
             NFO"
    INDEX           { sonusDflushDiskLogType }
    ::= { sonusDflushNetworkFailoverDiskUsageStatTable 1 }

SonusDflushNetworkFailoverDiskUsageStatEntry ::=
    SEQUENCE {
        sonusDflushDiskLogType          INTEGER,
        sonusDflushActiveDiskUsage      Integer32,
        sonusDflushStandbyDiskUsage     Integer32
    }

sonusDflushDiskLogType OBJECT-TYPE
    SYNTAX          INTEGER { sys(0), dbg(1), trc(2), act(3), pfm(4) }
    MAX-ACCESS      read-only
    STATUS          current
    DESCRIPTION     
            "This object defines the number of ACT files 
             sent by the Network Failover Feature since
             the admin state was set to ENABLED"
    DEFVAL          { 0 }
    ::= { sonusDflushNetworkFailoverDiskUsageStatEntry 1 }

sonusDflushActiveDiskUsage OBJECT-TYPE
    SYNTAX          Integer32
    MAX-ACCESS      read-only
    STATUS          current
    DESCRIPTION     
            "This object defines the disk space used by
             directory storing the specified log type on
             the active flash disk"
    DEFVAL          { 0 }
    ::= { sonusDflushNetworkFailoverDiskUsageStatEntry 2 }

sonusDflushStandbyDiskUsage OBJECT-TYPE
    SYNTAX          Integer32
    MAX-ACCESS      read-only
    STATUS          current
    DESCRIPTION     
            "This object defines the disk space used by
             directory storing the specified log type on
             the standby flash disk"
    DEFVAL          { 0 }
    ::= { sonusDflushNetworkFailoverDiskUsageStatEntry 3 }

sonusNodeMIBNotifications OBJECT IDENTIFIER
    ::= { sonusNodeMIB 2 }

sonusNodeMIBNotificationsPrefix OBJECT IDENTIFIER
    ::= { sonusNodeMIBNotifications 0 }

sonusNodeMIBNotificationsObjects OBJECT IDENTIFIER
    ::= { sonusNodeMIBNotifications 1 }

sonusNfsServer OBJECT-TYPE
    SYNTAX          INTEGER { primary(1), secondary(2) }
    MAX-ACCESS      read-only
    STATUS          current
    DESCRIPTION     
            "The NFS server referred to by the trap."
    ::= { sonusNodeMIBNotificationsObjects 1 }

sonusNfsRole OBJECT-TYPE
    SYNTAX          INTEGER { active(1), standby(2) }
    MAX-ACCESS      read-only
    STATUS          current
    DESCRIPTION     
            "Role assumed by the NFS server referred to by the trap."
    ::= { sonusNodeMIBNotificationsObjects 2 }

sonusNfsServerIp OBJECT-TYPE
    SYNTAX          IpAddress
    MAX-ACCESS      read-only
    STATUS          current
    DESCRIPTION     
            "The IP address of the NFS server referred to by the trap."
    ::= { sonusNodeMIBNotificationsObjects 3 }

sonusNfsServerMount OBJECT-TYPE
    SYNTAX          DisplayString (SIZE(2..32))
    MAX-ACCESS      read-only
    STATUS          current
    DESCRIPTION     
            "The mount point used on the NFS server referred to by the trap."
    ::= { sonusNodeMIBNotificationsObjects 4 }

sonusNfsReason OBJECT-TYPE
    SYNTAX          INTEGER { adminOperation(1), serverFailure(2), 
                        serverNotWritable(3), serverRecovery(4), 
                        serverLinkNotStable(5) }
    MAX-ACCESS      read-only
    STATUS          current
    DESCRIPTION     
            "The reason for the generation of the trap - administrative
             operation (mount, unmount, or toggle), server failure, server
             not writable, or server recovery."
    ::= { sonusNodeMIBNotificationsObjects 5 }

sonusNfsErrorCode OBJECT-TYPE
    SYNTAX          INTEGER { none(1), badVolumeStructure(2), 
                        tooManyFiles(3), volumeFull(4), 
                        serverHardError(5), quotaExceeded(6), 
                        staleNfsHandle(7), nfsTimeout(8), 
                        rpcCanNotSend(9), noAccess(10), other(11), 
                        nosuchfileordevice(12) }
    MAX-ACCESS      read-only
    STATUS          current
    DESCRIPTION     
            "The NFS error that occurred."
    ::= { sonusNodeMIBNotificationsObjects 6 }

sonusParamWriteIncrementalStatus OBJECT-TYPE
    SYNTAX          INTEGER { success(1), noFile(2), fileOpenError(3), 
                        fileCloseError(4), fileWriteError(5), 
                        fileSaveError(6), maxObjectDeletes(7) }
    MAX-ACCESS      read-only
    STATUS          current
    DESCRIPTION     
            "The status of the writing the incremental parameter file."
    ::= { sonusNodeMIBNotificationsObjects 7 }

sonusSbySlotIndex OBJECT-TYPE
    SYNTAX          Integer32 (1..18)
    MAX-ACCESS      read-only
    STATUS          current
    DESCRIPTION     
            "The index for the standby slot."
    ::= { sonusNodeMIBNotificationsObjects 8 }

sonusActSlotIndex OBJECT-TYPE
    SYNTAX          Integer32 (1..18)
    MAX-ACCESS      read-only
    STATUS          current
    DESCRIPTION     
            "The index for the active slot."
    ::= { sonusNodeMIBNotificationsObjects 9 }

sonusOverloadLevel OBJECT-TYPE
    SYNTAX          INTEGER { noOverload(0), levelOne(1), levelTwo(2), 
                        levelThree(3) }
    MAX-ACCESS      read-only
    STATUS          current
    DESCRIPTION     
            "The overload level."
    ::= { sonusNodeMIBNotificationsObjects 10 }

sonusSlot1MnsDiskPresent OBJECT-TYPE
    SYNTAX          INTEGER { none(0), localDiskPresent(1) }
    MAX-ACCESS      read-only
    STATUS          current
    DESCRIPTION     
            "Active MNS Local Disk Setting."
    ::= { sonusNodeMIBNotificationsObjects 11 }

sonusSlot1MnsDiskSize OBJECT-TYPE
    SYNTAX          Integer32
    MAX-ACCESS      read-only
    STATUS          current
    DESCRIPTION     
            "Active MNS Local Disk Size (KBytes)."
    ::= { sonusNodeMIBNotificationsObjects 12 }

sonusSlot2MnsDiskPresent OBJECT-TYPE
    SYNTAX          INTEGER { none(0), localDiskPresent(1) }
    MAX-ACCESS      read-only
    STATUS          current
    DESCRIPTION     
            "Standby MNS Local Disk Setting."
    ::= { sonusNodeMIBNotificationsObjects 13 }

sonusSlot2MnsDiskSize OBJECT-TYPE
    SYNTAX          Integer32
    MAX-ACCESS      read-only
    STATUS          current
    DESCRIPTION     
            "Standby MNS Local Disk Size (KBytes)."
    ::= { sonusNodeMIBNotificationsObjects 14 }

sonusParamPathFilename OBJECT-TYPE
    SYNTAX          DisplayString (SIZE(1..63))
    MAX-ACCESS      read-only
    STATUS          current
    DESCRIPTION     
            "The complete path and filename of the parameter file."
    ::= { sonusNodeMIBNotificationsObjects 15 }

sonusMnsDisk OBJECT-TYPE
    SYNTAX          INTEGER { activeMnsDisk(1), standbyMnsDisk(2) }
    MAX-ACCESS      read-only
    STATUS          current
    DESCRIPTION     
            "The local disk this trap refers to."
    ::= { sonusNodeMIBNotificationsObjects 16 }

sonusErrorType OBJECT-TYPE
    SYNTAX          DisplayString (SIZE(1..63))
    MAX-ACCESS      read-only
    STATUS          current
    DESCRIPTION     
            "The Network Processor General Error type."
    ::= { sonusNodeMIBNotificationsObjects 17 }

sonusErrorCount OBJECT-TYPE
    SYNTAX          Integer32
    MAX-ACCESS      read-only
    STATUS          current
    DESCRIPTION     
            "The Network Processor Error Count."
    ::= { sonusNodeMIBNotificationsObjects 18 }

sonusOverloadResourceMask OBJECT-TYPE
    SYNTAX          BITS { cpu(0), mem(1), psx(2), cps(3), invalid(4), 
                        log(5), icm(6), cdr(7) }
    MAX-ACCESS      read-only
    STATUS          current
    DESCRIPTION     
            "A bitmask specifying the overload resource types"
    ::= { sonusNodeMIBNotificationsObjects 19 }

sonusNfsServerIpAddrV6 OBJECT-TYPE
    SYNTAX          Ipv6Address
    MAX-ACCESS      read-only
    STATUS          current
    DESCRIPTION     
            "The IP address of the NFS server referred to by the trap."
    ::= { sonusNodeMIBNotificationsObjects 20 }

sonusNodeShelfPowerA48VdcNormalNotification NOTIFICATION-TYPE
    OBJECTS         { sonusShelfIndex, sonusEventDescription, 
                      sonusEventClass, sonusEventLevel, sonusSequenceId, 
                      sonusEventTime }
    STATUS          current
    DESCRIPTION     
            "A sonusShelfPowerA48VdcNormal trap indicates that 48V DC
             source A is operating normally for the specified shelf."
    ::= { sonusNodeMIBNotificationsPrefix 1 }

sonusNodeShelfPowerB48VdcNormalNotification NOTIFICATION-TYPE
    OBJECTS         { sonusShelfIndex, sonusEventDescription, 
                      sonusEventClass, sonusEventLevel, sonusSequenceId, 
                      sonusEventTime }
    STATUS          current
    DESCRIPTION     
            "A sonusShelfPowerB48VdcNormal trap indicates that 48V DC
             source B is operating normally for the specified shelf."
    ::= { sonusNodeMIBNotificationsPrefix 2 }

sonusNodeShelfPowerA48VdcFailureNotification NOTIFICATION-TYPE
    OBJECTS         { sonusShelfIndex, sonusEventDescription, 
                      sonusEventClass, sonusEventLevel, sonusSequenceId, 
                      sonusEventTime }
    STATUS          current
    DESCRIPTION     
            "A sonusShelfPowerA48VdcFailure trap indicates that 48V DC
             source A has failed for the specified shelf."
    ::= { sonusNodeMIBNotificationsPrefix 3 }

sonusNodeShelfPowerB48VdcFailureNotification NOTIFICATION-TYPE
    OBJECTS         { sonusShelfIndex, sonusEventDescription, 
                      sonusEventClass, sonusEventLevel, sonusSequenceId, 
                      sonusEventTime }
    STATUS          current
    DESCRIPTION     
            "A sonusShelfPowerB48VdcFailure trap indicates that 48V DC
             source A has failed for the specified shelf."
    ::= { sonusNodeMIBNotificationsPrefix 4 }

sonusNodeShelfFanTrayFailureNotification NOTIFICATION-TYPE
    OBJECTS         { sonusShelfIndex, sonusEventDescription, 
                      sonusEventClass, sonusEventLevel, sonusSequenceId, 
                      sonusEventTime }
    STATUS          current
    DESCRIPTION     
            "A sonusNodeShelfFanTrayFailure trap indicates that the fan
             controller on the specified shelf is indicating a problem.
             The Event Log should be examined for more detail.  The
             fan tray should be replaced immediately."
    ::= { sonusNodeMIBNotificationsPrefix 5 }

sonusNodeShelfFanTrayOperationalNotification NOTIFICATION-TYPE
    OBJECTS         { sonusShelfIndex, sonusEventDescription, 
                      sonusEventClass, sonusEventLevel, sonusSequenceId, 
                      sonusEventTime }
    STATUS          current
    DESCRIPTION     
            "A sonusNodeShelfFanTrayOperational trap indicates that
             the fan controller is fully operational on the specified
             shelf."
    ::= { sonusNodeMIBNotificationsPrefix 6 }

sonusNodeShelfFanTrayRemovedNotification NOTIFICATION-TYPE
    OBJECTS         { sonusShelfIndex, sonusEventDescription, 
                      sonusEventClass, sonusEventLevel, sonusSequenceId, 
                      sonusEventTime }
    STATUS          current
    DESCRIPTION     
            "A sonusNodeShelfFanTrayRemoved trap indicates that the fan
             tray has been removed from the specified shelf.  The fan
             tray should be replaced as soon as possible to avoid damage
             to the equipment as a result of overheating."
    ::= { sonusNodeMIBNotificationsPrefix 7 }

sonusNodeShelfFanTrayPresentNotification NOTIFICATION-TYPE
    OBJECTS         { sonusShelfIndex, sonusEventDescription, 
                      sonusEventClass, sonusEventLevel, sonusSequenceId, 
                      sonusEventTime }
    STATUS          current
    DESCRIPTION     
            "A sonusNodeShelfFanTrayPresent trap indicates that a fan
             tray is present for the specified shelf."
    ::= { sonusNodeMIBNotificationsPrefix 8 }

sonusNodeShelfIntakeTempWarningNotification NOTIFICATION-TYPE
    OBJECTS         { sonusShelfIndex, sonusEventDescription, 
                      sonusEventClass, sonusEventLevel, sonusSequenceId, 
                      sonusEventTime }
    STATUS          current
    DESCRIPTION     
            "A sonusNodeShelfIntakeTempWarning trap indicates that
             the intake temperature of the specified shelf has
             exceeded 45C degrees or dropped below 0C degrees."
    ::= { sonusNodeMIBNotificationsPrefix 9 }

sonusNodeServerTempWarningNotification NOTIFICATION-TYPE
    OBJECTS         { sonusShelfIndex, sonusSlotIndex, 
                      sonusEventDescription, sonusEventClass, 
                      sonusEventLevel, sonusSequenceId, sonusEventTime }
    STATUS          current
    DESCRIPTION     
            "A sonusNodeServerTempWarning trap indicates that the
             operating temperature of the specified shelf and slot
             has exceeded 60C degrees or dropped below 0C degrees."
    ::= { sonusNodeMIBNotificationsPrefix 10 }

sonusNodeServerTempFailureNotification NOTIFICATION-TYPE
    OBJECTS         { sonusShelfIndex, sonusSlotIndex, 
                      sonusEventDescription, sonusEventClass, 
                      sonusEventLevel, sonusSequenceId, sonusEventTime }
    STATUS          current
    DESCRIPTION     
            "A sonusNodeServerTempFailure trap indicates that the
             operating temperature of the specified shelf and slot
             has exceeded 70C degrees.  A server module operating for
             any length of time at this temperature is in danger of
             being physically damaged.  The specified module should
             be disabled and/or removed from the shelf."
    ::= { sonusNodeMIBNotificationsPrefix 11 }

sonusNodeServerTempNormalNotification NOTIFICATION-TYPE
    OBJECTS         { sonusShelfIndex, sonusSlotIndex, 
                      sonusEventDescription, sonusEventClass, 
                      sonusEventLevel, sonusSequenceId, sonusEventTime }
    STATUS          current
    DESCRIPTION     
            "A sonusNodeServerTempNormal trap indicates that the
             operating temperature of the specified shelf and slot
             is between 0C and 60C degrees."
    ::= { sonusNodeMIBNotificationsPrefix 12 }

sonusNodeServerInsertedNotification NOTIFICATION-TYPE
    OBJECTS         { sonusShelfIndex, sonusSlotIndex, 
                      sonusEventDescription, sonusEventClass, 
                      sonusEventLevel, sonusSequenceId, sonusEventTime }
    STATUS          current
    DESCRIPTION     
            "A sonusNodeServerInserted trap indicates that a server module
             has been inserted in the specified shelf and slot."
    ::= { sonusNodeMIBNotificationsPrefix 13 }

sonusNodeServerRemovedNotification NOTIFICATION-TYPE
    OBJECTS         { sonusShelfIndex, sonusSlotIndex, 
                      sonusEventDescription, sonusEventClass, 
                      sonusEventLevel, sonusSequenceId, sonusEventTime }
    STATUS          current
    DESCRIPTION     
            "A sonusNodeServerRemoved trap indicates that a server module
             has been removed from the specified shelf and slot."
    ::= { sonusNodeMIBNotificationsPrefix 14 }

sonusNodeServerResetNotification NOTIFICATION-TYPE
    OBJECTS         { sonusShelfIndex, sonusSlotIndex, 
                      sonusEventDescription, sonusEventClass, 
                      sonusEventLevel, sonusSequenceId, sonusEventTime }
    STATUS          current
    DESCRIPTION     
            "A sonusNodeServerReset trap indicates that the server module
             in the specified shelf and slot has been reset."
    ::= { sonusNodeMIBNotificationsPrefix 15 }

sonusNodeServerOperationalNotification NOTIFICATION-TYPE
    OBJECTS         { sonusShelfIndex, sonusSlotIndex, 
                      sonusEventDescription, sonusEventClass, 
                      sonusEventLevel, sonusSequenceId, sonusEventTime }
    STATUS          current
    DESCRIPTION     
            "A sonusNodeServerOperational trap indicates that the booting
             and initialization has completed successfully for the server
             module in the specified shelf and slot."
    ::= { sonusNodeMIBNotificationsPrefix 16 }

sonusNodeServerPowerFailureNotification NOTIFICATION-TYPE
    OBJECTS         { sonusShelfIndex, sonusSlotIndex, 
                      sonusEventDescription, sonusEventClass, 
                      sonusEventLevel, sonusSequenceId, sonusEventTime }
    STATUS          current
    DESCRIPTION     
            "A sonusNodeServerPowerFailure trap indicates that a power
             failure has been detected for the server module in the
             specified shelf and slot."
    ::= { sonusNodeMIBNotificationsPrefix 17 }

sonusNodeServerSoftwareFailureNotification NOTIFICATION-TYPE
    OBJECTS         { sonusShelfIndex, sonusSlotIndex, 
                      sonusEventDescription, sonusEventClass, 
                      sonusEventLevel, sonusSequenceId, sonusEventTime }
    STATUS          current
    DESCRIPTION     
            "A sonusNodeServerSoftwareFailure trap indicates that a
             software failure has occurred or the server module in the
             specified shelf and slot.  The EventLog should be viewed
             for possible additional information."
    ::= { sonusNodeMIBNotificationsPrefix 18 }

sonusNodeServerHardwareFailureNotification NOTIFICATION-TYPE
    OBJECTS         { sonusShelfIndex, sonusSlotIndex, 
                      sonusEventDescription, sonusEventClass, 
                      sonusEventLevel, sonusSequenceId, sonusEventTime }
    STATUS          current
    DESCRIPTION     
            "A sonusNodeServerHardwareFailure trap indicates that a
             hardware failure has occurred or the server module in the
             specified shelf and slot.  The EventLog should be viewed
             for possible additional information."
    ::= { sonusNodeMIBNotificationsPrefix 19 }

sonusNodeAdapterInsertedNotification NOTIFICATION-TYPE
    OBJECTS         { sonusShelfIndex, sonusSlotIndex, 
                      sonusEventDescription, sonusEventClass, 
                      sonusEventLevel, sonusSequenceId, sonusEventTime }
    STATUS          current
    DESCRIPTION     
            "A sonusNodeAdapterInserted trap indicates that an adapter
             module has been inserted in the specified shelf and slot."
    ::= { sonusNodeMIBNotificationsPrefix 20 }

sonusNodeAdapterRemovedNotification NOTIFICATION-TYPE
    OBJECTS         { sonusShelfIndex, sonusSlotIndex, 
                      sonusEventDescription, sonusEventClass, 
                      sonusEventLevel, sonusSequenceId, sonusEventTime }
    STATUS          current
    DESCRIPTION     
            "A sonusNodeAdpaterRemoved trap indicates that an adapter
             module has been removed from the specified shelf and slot."
    ::= { sonusNodeMIBNotificationsPrefix 21 }

sonusNodeMtaInsertedNotification NOTIFICATION-TYPE
    OBJECTS         { sonusShelfIndex, sonusSlotIndex, 
                      sonusEventDescription, sonusEventClass, 
                      sonusEventLevel, sonusSequenceId, sonusEventTime }
    STATUS          current
    DESCRIPTION     
            "A sonusNodeMtaInserted trap indicates that a Management
             Timing Adapter has been inserted in the specified shelf
             and slot."
    ::= { sonusNodeMIBNotificationsPrefix 22 }

sonusNodeMtaRemovedNotification NOTIFICATION-TYPE
    OBJECTS         { sonusShelfIndex, sonusSlotIndex, 
                      sonusEventDescription, sonusEventClass, 
                      sonusEventLevel, sonusSequenceId, sonusEventTime }
    STATUS          current
    DESCRIPTION     
            "A sonusNodeMtaRemoved trap indicates that a Management
             Timing Adapter has been removed from the specified shelf
             and slot."
    ::= { sonusNodeMIBNotificationsPrefix 23 }

sonusNodeEthernetActiveNotification NOTIFICATION-TYPE
    OBJECTS         { sonusShelfIndex, sonusSlotIndex, sonusPortIndex, 
                      sonusEventDescription, sonusEventClass, 
                      sonusEventLevel, sonusSequenceId, sonusEventTime }
    STATUS          current
    DESCRIPTION     
            "A sonusNodeEthernetActive trap indicates that an
             Ethernet link is active for the specified shelf, slot
             and port."
    ::= { sonusNodeMIBNotificationsPrefix 24 }

sonusNodeEthernetInactiveNotification NOTIFICATION-TYPE
    OBJECTS         { sonusShelfIndex, sonusSlotIndex, sonusPortIndex, 
                      sonusEventDescription, sonusEventClass, 
                      sonusEventLevel, sonusSequenceId, sonusEventTime }
    STATUS          current
    DESCRIPTION     
            "A sonusNodeEthernetInactive trap indicates that an
             Ethernet link is inactive for the specified shelf, slot
             and port."
    ::= { sonusNodeMIBNotificationsPrefix 25 }

sonusNodeEthernetDegradedNotification NOTIFICATION-TYPE
    OBJECTS         { sonusShelfIndex, sonusSlotIndex, sonusPortIndex, 
                      sonusEventDescription, sonusEventClass, 
                      sonusEventLevel, sonusSequenceId, sonusEventTime }
    STATUS          current
    DESCRIPTION     
            "A sonusNodeEthernetDegraded trap indicates that an
             Ethernet link is detecting network errors for the
             specified shelf, slot and port.  The EventLog should
             be viewed for possible additional information."
    ::= { sonusNodeMIBNotificationsPrefix 26 }

sonusNodeBootNotification NOTIFICATION-TYPE
    OBJECTS         { sonusEventDescription, sonusEventClass, 
                      sonusEventLevel, sonusSequenceId, sonusEventTime }
    STATUS          current
    DESCRIPTION     
            "The Management Node Server module, in the node's master shelf,
             has begun the Node Boot process."
    ::= { sonusNodeMIBNotificationsPrefix 27 }

sonusNodeSlaveShelfBootNotification NOTIFICATION-TYPE
    OBJECTS         { sonusShelfIndex, sonusEventDescription, 
                      sonusEventClass, sonusEventLevel, sonusSequenceId, 
                      sonusEventTime }
    STATUS          current
    DESCRIPTION     
            "The Management Node Server module, in a node's slave shelf,
             has begun the Node Boot process."
    ::= { sonusNodeMIBNotificationsPrefix 28 }

sonusNodeNfsServerSwitchoverNotification NOTIFICATION-TYPE
    OBJECTS         { sonusShelfIndex, sonusSlotIndex, sonusNfsServer, 
                      sonusNfsServerIp, sonusNfsServerMount, 
                      sonusNfsReason, sonusEventDescription, 
                      sonusEventClass, sonusEventLevel, sonusSequenceId, 
                      sonusEventTime }
    STATUS          current
    DESCRIPTION     
            "Indicates that the Active NFS server has switched over to
             the Standby for the specified reason on the MNS in the given
             shelf and slot.  The NFS server specified is the new Active."
    ::= { sonusNodeMIBNotificationsPrefix 29 }

sonusNodeNfsServerOutOfServiceNotification NOTIFICATION-TYPE
    OBJECTS         { sonusShelfIndex, sonusSlotIndex, sonusNfsServer, 
                      sonusNfsServerIp, sonusNfsServerMount, 
                      sonusNfsReason, sonusNfsErrorCode, 
                      sonusEventDescription, sonusEventClass, 
                      sonusEventLevel, sonusSequenceId, sonusEventTime }
    STATUS          current
    DESCRIPTION     
            "Indicates that the NFS server specified went out-of-service
             for the reason provided on the MNS in the given shelf and
             slot.  If it was the result of a server failure, the error
             that caused the failure is also specified."
    ::= { sonusNodeMIBNotificationsPrefix 30 }

sonusNodeNfsServerInServiceNotification NOTIFICATION-TYPE
    OBJECTS         { sonusShelfIndex, sonusSlotIndex, sonusNfsServer, 
                      sonusNfsServerIp, sonusNfsServerMount, 
                      sonusNfsReason, sonusNfsRole, 
                      sonusEventDescription, sonusEventClass, 
                      sonusEventLevel, sonusSequenceId, sonusEventTime }
    STATUS          current
    DESCRIPTION     
            "Indicates that the NFS server specified came in-service for the
             reason provided on the MNS in the given shelf and slot.  The
             Active/Standby role assumed by the server is also provided."
    ::= { sonusNodeMIBNotificationsPrefix 31 }

sonusNodeNfsServerNotWritableNotification NOTIFICATION-TYPE
    OBJECTS         { sonusShelfIndex, sonusSlotIndex, sonusNfsServer, 
                      sonusNfsServerIp, sonusNfsServerMount, 
                      sonusNfsErrorCode, sonusEventDescription, 
                      sonusEventClass, sonusEventLevel, sonusSequenceId, 
                      sonusEventTime }
    STATUS          current
    DESCRIPTION     
            "Indicates that the NFS server specified is no longer writable by the
             MNS in the given shelf and slot.  The error code received is provided."
    ::= { sonusNodeMIBNotificationsPrefix 32 }

sonusNodeServerDisabledNotification NOTIFICATION-TYPE
    OBJECTS         { sonusShelfIndex, sonusSlotIndex, 
                      sonusEventDescription, sonusEventClass, 
                      sonusEventLevel, sonusSequenceId, sonusEventTime }
    STATUS          current
    DESCRIPTION     
            "The server modules administrative state has been set to
             disabled."
    ::= { sonusNodeMIBNotificationsPrefix 33 }

sonusNodeServerEnabledNotification NOTIFICATION-TYPE
    OBJECTS         { sonusShelfIndex, sonusSlotIndex, 
                      sonusEventDescription, sonusEventClass, 
                      sonusEventLevel, sonusSequenceId, sonusEventTime }
    STATUS          current
    DESCRIPTION     
            "The server modules administrative state has been set to
             enabled."
    ::= { sonusNodeMIBNotificationsPrefix 34 }

sonusNodeServerDeletedNotification NOTIFICATION-TYPE
    OBJECTS         { sonusShelfIndex, sonusSlotIndex, 
                      sonusEventDescription, sonusEventClass, 
                      sonusEventLevel, sonusSequenceId, sonusEventTime }
    STATUS          current
    DESCRIPTION     
            "The server module has been deleted from the node's
             configuration.  All configuration data associated with
             the server module has been deleted."
    ::= { sonusNodeMIBNotificationsPrefix 35 }

sonusParamBackupLoadNotification NOTIFICATION-TYPE
    OBJECTS         { sonusEventDescription, sonusEventClass, 
                      sonusEventLevel, sonusSequenceId, sonusEventTime }
    STATUS          current
    DESCRIPTION     
            "The backup parameter file was loaded.  This indicates that
             the primary parameter file was lost or corrupted.  The backup 
             parameter file may contain data which is older than what the
             primary parameter file contains."
    ::= { sonusNodeMIBNotificationsPrefix 36 }

sonusParamCorruptionNotification NOTIFICATION-TYPE
    OBJECTS         { sonusParamLoadFileType, sonusEventDescription, 
                      sonusEventClass, sonusEventLevel, sonusSequenceId, 
                      sonusEventTime }
    STATUS          current
    DESCRIPTION     
            "The binary parameter inspected was corrupted.  The indicated file
             was skipped due to corruption.  This trap is only transmitted if a
             valid backup parameter file is located and successfully loaded."
    ::= { sonusNodeMIBNotificationsPrefix 37 }

sonusNodeAdapterMissingNotification NOTIFICATION-TYPE
    OBJECTS         { sonusShelfIndex, sonusSlotIndex, 
                      sonusEventDescription, sonusEventClass, 
                      sonusEventLevel, sonusSequenceId, sonusEventTime }
    STATUS          current
    DESCRIPTION     
            "A sonusNodeAdpaterMissing trap indicates that an adapter
             module has not been detected in a specific shelf and slot."
    ::= { sonusNodeMIBNotificationsPrefix 38 }

sonusNodeAdapterFailureNotification NOTIFICATION-TYPE
    OBJECTS         { sonusShelfIndex, sonusSlotIndex, 
                      sonusEventDescription, sonusEventClass, 
                      sonusEventLevel, sonusSequenceId, sonusEventTime }
    STATUS          current
    DESCRIPTION     
            "A sonusNodeAdpaterFailure trap indicates that an adapter
             module has been detected but is not operational."
    ::= { sonusNodeMIBNotificationsPrefix 39 }

sonusNodeSlotResetNotification NOTIFICATION-TYPE
    OBJECTS         { sonusShelfIndex, sonusSlotIndex, 
                      sonusEventDescription, sonusEventClass, 
                      sonusEventLevel, sonusSequenceId, sonusEventTime }
    STATUS          current
    DESCRIPTION     
            "A sonusNodeSlotReset trap indicates that a server
             module in the designated slot was reset."
    ::= { sonusNodeMIBNotificationsPrefix 40 }

sonusNodeParamWriteCompleteNotification NOTIFICATION-TYPE
    OBJECTS         { sonusParamSaveFilename, sonusParamSaveSeqNumber, 
                      sonusParamLastSaveTime, sonusEventDescription, 
                      sonusEventClass, sonusEventLevel, 
                      sonusParamWriteIncrementalStatus, sonusSequenceId, 
                      sonusEventTime, sonusParamSaveSeqEpoch }
    STATUS          deprecated
    DESCRIPTION     
            "This trap has been replaced by sonusNodeParamWriteSuccessNotification.
             
             A sonusNodeParamWriteComplete trap indicates that NFS server
             successfully complete PIF write."
    ::= { sonusNodeMIBNotificationsPrefix 41 }

sonusNodeParamWriteErrorNotification NOTIFICATION-TYPE
    OBJECTS         { sonusParamSavePrimarySrvrReason, 
                      sonusEventDescription, sonusEventClass, 
                      sonusEventLevel, sonusNfsAdmnMountServer, 
                      sonusParamSaveFilename, sonusParamSaveSeqNumber, 
                      sonusSequenceId, sonusEventTime }
    STATUS          deprecated
    DESCRIPTION     
            "This trap has been replaced by sonusNodeParamWriteFailureNotification.
             
             A sonusNodeParamWriteError trap indicates that error
             occured during PIF write."
    ::= { sonusNodeMIBNotificationsPrefix 42 }

sonusNodeBootMnsActiveNotification NOTIFICATION-TYPE
    OBJECTS         { sonusShelfIndex, sonusSlotIndex, 
                      sonusEventDescription, sonusEventClass, 
                      sonusEventLevel, sonusSequenceId, sonusEventTime }
    STATUS          current
    DESCRIPTION     
            "The Management Node Server module in the specified shelf
             and slot has become active following a Node Boot."
    ::= { sonusNodeMIBNotificationsPrefix 43 }

sonusNodeShelfIntakeTempNormalNotification NOTIFICATION-TYPE
    OBJECTS         { sonusShelfIndex, sonusEventDescription, 
                      sonusEventClass, sonusEventLevel, sonusSequenceId, 
                      sonusEventTime }
    STATUS          current
    DESCRIPTION     
            "A sonusNodeShelfIntakeTempNormal trap indicates that
             the intake temperature of the specified shelf is
             between 0C and 45C degrees."
    ::= { sonusNodeMIBNotificationsPrefix 44 }

sonusNodeRtmUnsyncedNotification NOTIFICATION-TYPE
    OBJECTS         { sonusShelfIndex, sonusSbySlotIndex, 
                      sonusActSlotIndex, sonusEventDescription, 
                      sonusEventClass, sonusEventLevel, sonusSequenceId, 
                      sonusEventTime }
    STATUS          current
    DESCRIPTION     
            "Standby Slot is no longer synchronized with designated active
             slot."
    ::= { sonusNodeMIBNotificationsPrefix 45 }

sonusNodePimFailureNotification NOTIFICATION-TYPE
    OBJECTS         { sonusShelfIndex, sonusSlotIndex, sonusPimIndex, 
                      sonusEventDescription, sonusEventClass, 
                      sonusEventLevel, sonusSequenceId, sonusEventTime }
    STATUS          current
    DESCRIPTION     
            "A sonusNodePimFailure trap indicates that a Pim
             module has been detected but is not operational."
    ::= { sonusNodeMIBNotificationsPrefix 46 }

sonusNodePimInsertedNotification NOTIFICATION-TYPE
    OBJECTS         { sonusShelfIndex, sonusSlotIndex, sonusPimIndex, 
                      sonusNodePimStatHwType, sonusNodePimStatHwTypeRev, 
                      sonusNodePimStatEpldRevNumber, 
                      sonusEventDescription, sonusEventClass, 
                      sonusEventLevel, sonusSequenceId, sonusEventTime }
    STATUS          current
    DESCRIPTION     
            "A sonusNodePimInserted trap indicates that a Pim
             module has been inserted in specified pimIndex in
             		 specified shelf, slot."
    ::= { sonusNodeMIBNotificationsPrefix 47 }

sonusNodePimRemovedNotification NOTIFICATION-TYPE
    OBJECTS         { sonusShelfIndex, sonusSlotIndex, sonusPimIndex, 
                      sonusEventDescription, sonusEventClass, 
                      sonusEventLevel, sonusSequenceId, sonusEventTime }
    STATUS          current
    DESCRIPTION     
            "A sonusNodePimRemoved trap indicates that a Pim
             module has been removed from specified pimIndex
             		 in specified shelf, slot."
    ::= { sonusNodeMIBNotificationsPrefix 48 }

sonusNodeMiddWriteFailureNotification NOTIFICATION-TYPE
    OBJECTS         { sonusEventDescription, sonusEventClass, 
                      sonusEventLevel, sonusSequenceId, sonusEventTime }
    STATUS          current
    DESCRIPTION     
            "Writing to the SonicPlane MIDD failed."
    ::= { sonusNodeMIBNotificationsPrefix 49 }

sonusNodeParamHoldoffTimeChangedNotification NOTIFICATION-TYPE
    OBJECTS         { sonusShelfIndex, sonusParamAdmnHoldoffTime, 
                      sonusEventDescription, sonusEventClass, 
                      sonusEventLevel, sonusSequenceId, sonusEventTime }
    STATUS          current
    DESCRIPTION     
            "Wait for holdoff duration before writing parameter file."
    ::= { sonusNodeMIBNotificationsPrefix 50 }

sonusNodeMachineCongestionNotification NOTIFICATION-TYPE
    OBJECTS         { sonusShelfIndex, sonusOverloadLevel, 
                      sonusEventDescription, sonusEventClass, 
                      sonusEventLevel, sonusSequenceId, sonusEventTime, 
                      sonusOverloadResourceMask }
    STATUS          current
    DESCRIPTION     
            "The sonusNodeMachineCongestionNotification indicates
             GSX Machine congestion level changes."
    ::= { sonusNodeMIBNotificationsPrefix 51 }

sonusNodeServerCongestionNotification NOTIFICATION-TYPE
    OBJECTS         { sonusShelfIndex, sonusSlotIndex, 
                      sonusOverloadLevel, sonusEventDescription, 
                      sonusEventClass, sonusEventLevel, sonusSequenceId, 
                      sonusEventTime }
    STATUS          current
    DESCRIPTION     
            "The sonusNodeServerCongestionNotification indicates
             a congestion level changes on a server module."
    ::= { sonusNodeMIBNotificationsPrefix 52 }

sonusNodeLocalDiskMismatchNotification NOTIFICATION-TYPE
    OBJECTS         { sonusShelfIndex, sonusSlot1MnsDiskPresent, 
                      sonusSlot1MnsDiskSize, sonusSlot2MnsDiskPresent, 
                      sonusSlot2MnsDiskSize, sonusEventDescription, 
                      sonusEventClass, sonusEventLevel, sonusSequenceId, 
                      sonusEventTime }
    STATUS          current
    DESCRIPTION     
            "Active MNS Local Disk and Standby MNS Local Disk do not match."
    ::= { sonusNodeMIBNotificationsPrefix 53 }

sonusNodeParamWriteSuccessNotification NOTIFICATION-TYPE
    OBJECTS         { sonusParamPathFilename, sonusBparamBootDisk, 
                      sonusNfsServerIp, sonusNfsServerMount, 
                      sonusParamWriteIncrementalStatus, 
                      sonusParamSaveSeqNumber, sonusParamSaveSeqEpoch, 
                      sonusEventDescription, sonusEventClass, 
                      sonusEventLevel, sonusSequenceId, sonusEventTime }
    STATUS          current
    DESCRIPTION     
            "This trap indicates that a parameter file has been successfully written
             to the specified location."
    ::= { sonusNodeMIBNotificationsPrefix 54 }

sonusNodeParamWriteFailureNotification NOTIFICATION-TYPE
    OBJECTS         { sonusParamPathFilename, sonusBparamBootDisk, 
                      sonusNfsServerIp, sonusNfsServerMount, 
                      sonusParamSavePrimarySrvrReason, 
                      sonusParamSaveSeqNumber, sonusParamSaveSeqEpoch, 
                      sonusEventDescription, sonusEventClass, 
                      sonusEventLevel, sonusSequenceId, sonusEventTime }
    STATUS          current
    DESCRIPTION     
            "This trap indicates that an error occured during PIF write to the
             specified location."
    ::= { sonusNodeMIBNotificationsPrefix 55 }

sonusNodeAdapterRedundantPathFailureNotification NOTIFICATION-TYPE
    OBJECTS         { sonusShelfIndex, sonusSlotIndex, 
                      sonusEventDescription, sonusEventClass, 
                      sonusEventLevel, sonusSequenceId, sonusEventTime }
    STATUS          current
    DESCRIPTION     
            "A sonusNodeAdapterRedundantPathFailure trap indicates that an adapter module has 
             been detected but that the path to the redundant server card is not operational."
    ::= { sonusNodeMIBNotificationsPrefix 56 }

sonusNodeLocalDiskUnavailableNotification NOTIFICATION-TYPE
    OBJECTS         { sonusMnsDisk, sonusEventDescription, 
                      sonusEventClass, sonusEventLevel, sonusSequenceId, 
                      sonusEventTime }
    STATUS          current
    DESCRIPTION     
            "This trap indicates that the specified MNS's local disk is
             unavailable because it has been manually unmounted."
    ::= { sonusNodeMIBNotificationsPrefix 57 }

sonusNodeLocalDiskAvailableNotification NOTIFICATION-TYPE
    OBJECTS         { sonusMnsDisk, sonusEventDescription, 
                      sonusEventClass, sonusEventLevel, sonusSequenceId, 
                      sonusEventTime }
    STATUS          current
    DESCRIPTION     
            "This trap indicates that the specified MNS's local disk has
             been mounted and is now available."
    ::= { sonusNodeMIBNotificationsPrefix 58 }

sonusNodeLocalDiskSpaceReadOnlyNotification NOTIFICATION-TYPE
    OBJECTS         { sonusLocalDiskStatActiveDiskFree, 
                      sonusLocalDiskStatStandbyDiskFree, 
                      sonusEventDescription, sonusEventClass, 
                      sonusEventLevel, sonusSequenceId, sonusEventTime }
    STATUS          current
    DESCRIPTION     
            "This trap indicates that the MNS local disks have transitioned
             to read-only because of critically low disk space on one or
             both MNS disks.  Disk space must be cleaned up to allow writes
             again."
    ::= { sonusNodeMIBNotificationsPrefix 59 }

sonusNodeLocalDiskSpaceWarningNotification NOTIFICATION-TYPE
    OBJECTS         { sonusLocalDiskStatActiveDiskFree, 
                      sonusLocalDiskStatStandbyDiskFree, 
                      sonusEventDescription, sonusEventClass, 
                      sonusEventLevel, sonusSequenceId, sonusEventTime }
    STATUS          current
    DESCRIPTION     
            "This trap warns that disk space is running low on one or both
             MNS local disks.  No action has been taken yet, but if the free
             disk space falls below the critical limit, it will transition
             to read-only.  Clean up disk space."
    ::= { sonusNodeMIBNotificationsPrefix 60 }

sonusNodeLocalDiskSpaceOkNotification NOTIFICATION-TYPE
    OBJECTS         { sonusLocalDiskStatActiveDiskFree, 
                      sonusLocalDiskStatStandbyDiskFree, 
                      sonusEventDescription, sonusEventClass, 
                      sonusEventLevel, sonusSequenceId, sonusEventTime }
    STATUS          current
    DESCRIPTION     
            "This trap indicates that disk space is not critical or running
             low on either MNS local disks anymore."
    ::= { sonusNodeMIBNotificationsPrefix 61 }

sonusNodeLocalDiskWritableNotification NOTIFICATION-TYPE
    OBJECTS         { sonusEventDescription, sonusEventClass, 
                      sonusEventLevel, sonusSequenceId, sonusEventTime }
    STATUS          current
    DESCRIPTION     
            "This trap indicates that the MNS local disks have transitioned
             back to read-write because there is sufficient free disk
             space."
    ::= { sonusNodeMIBNotificationsPrefix 62 }

sonusNodeLocalDiskTooManyFilesNotification NOTIFICATION-TYPE
    OBJECTS         { sonusMnsDisk, sonusEventDescription, 
                      sonusEventClass, sonusEventLevel, sonusSequenceId, 
                      sonusEventTime }
    STATUS          current
    DESCRIPTION     
            "This trap indicates that the specified MNS's local disk has an
             excessive number of files.  The read-only condition will
             persist until some files are removed."
    ::= { sonusNodeMIBNotificationsPrefix 63 }

sonusNodeLocalDiskBadVolumeNotification NOTIFICATION-TYPE
    OBJECTS         { sonusMnsDisk, sonusEventDescription, 
                      sonusEventClass, sonusEventLevel, sonusSequenceId, 
                      sonusEventTime }
    STATUS          current
    DESCRIPTION     
            "This trap indicates that the specified MNS's local disk volume
             has inconsistent or corrupted data. Volume must be fixed or
             reformatted."
    ::= { sonusNodeMIBNotificationsPrefix 64 }

sonusNetworkProcessorGeneralErrorNotification NOTIFICATION-TYPE
    OBJECTS         { sonusErrorType, sonusErrorCount, 
                      sonusEventDescription, sonusEventClass, 
                      sonusEventLevel, sonusSequenceId, sonusEventTime }
    STATUS          current
    DESCRIPTION     
            "This trap indicates that the NP or NPIO is reporting errors
             that usually should not happen. It could be a HW problem. 
             RMA the card is suggested."
    ::= { sonusNodeMIBNotificationsPrefix 65 }

sonusNodeParamWriteSuccessNotificationV6 NOTIFICATION-TYPE
    OBJECTS         { sonusParamPathFilename, sonusBparamBootDisk, 
                      sonusNfsServerIpAddrV6, sonusNfsServerMount, 
                      sonusParamWriteIncrementalStatus, 
                      sonusParamSaveSeqNumber, sonusParamSaveSeqEpoch, 
                      sonusEventDescription, sonusEventClass, 
                      sonusEventLevel, sonusSequenceId, sonusEventTime }
    STATUS          current
    DESCRIPTION     
            "This trap indicates that a parameter file has been successfully written
             to the specified location."
    ::= { sonusNodeMIBNotificationsPrefix 67 }

sonusNodeParamWriteFailureNotificationV6 NOTIFICATION-TYPE
    OBJECTS         { sonusParamPathFilename, sonusBparamBootDisk, 
                      sonusNfsServerIpAddrV6, sonusNfsServerMount, 
                      sonusParamSavePrimarySrvrReason, 
                      sonusParamSaveSeqNumber, sonusParamSaveSeqEpoch, 
                      sonusEventDescription, sonusEventClass, 
                      sonusEventLevel, sonusSequenceId, sonusEventTime }
    STATUS          current
    DESCRIPTION     
            "This trap indicates that an error occured during PIF write to the
             specified location."
    ::= { sonusNodeMIBNotificationsPrefix 68 }

sonusNodeNfsServerOutOfServiceNotificationV6 NOTIFICATION-TYPE
    OBJECTS         { sonusShelfIndex, sonusSlotIndex, sonusNfsServer, 
                      sonusNfsServerIpAddrV6, sonusNfsServerMount, 
                      sonusNfsReason, sonusNfsErrorCode, 
                      sonusEventDescription, sonusEventClass, 
                      sonusEventLevel, sonusSequenceId, sonusEventTime }
    STATUS          current
    DESCRIPTION     
            "Indicates that the NFS server specified went out-of-service
             for the reason provided on the MNS in the given shelf and
             slot.  If it was the result of a server failure, the error
             that caused the failure is also specified."
    ::= { sonusNodeMIBNotificationsPrefix 69 }

sonusNodeNfsServerInServiceNotificationV6 NOTIFICATION-TYPE
    OBJECTS         { sonusShelfIndex, sonusSlotIndex, sonusNfsServer, 
                      sonusNfsServerIpAddrV6, sonusNfsServerMount, 
                      sonusNfsReason, sonusNfsRole, 
                      sonusEventDescription, sonusEventClass, 
                      sonusEventLevel, sonusSequenceId, sonusEventTime }
    STATUS          current
    DESCRIPTION     
            "Indicates that the NFS server specified came in-service for the
             reason provided on the MNS in the given shelf and slot.  The
             Active/Standby role assumed by the server is also provided."
    ::= { sonusNodeMIBNotificationsPrefix 70 }

sonusNodeCoreDumpNotGeneratedNotification NOTIFICATION-TYPE
    OBJECTS         { sonusEventDescription, sonusEventClass, 
                      sonusEventLevel, sonusSequenceId, sonusEventTime, 
                      sonusShelfIndex, sonusSlotIndex }
    STATUS          current
    DESCRIPTION     
            "This trap indicates that a cored dump was denied"
    ::= { sonusNodeMIBNotificationsPrefix 71 }

sonusNodeCoreDumpGeneratedNotification NOTIFICATION-TYPE
    OBJECTS         { sonusEventDescription, sonusEventClass, 
                      sonusEventLevel, sonusSequenceId, sonusEventTime, 
                      sonusShelfIndex, sonusSlotIndex }
    STATUS          current
    DESCRIPTION     
            "This trap indicates that a cored dump was generated"
    ::= { sonusNodeMIBNotificationsPrefix 72 }

sonusNodeDflushStatusNotification NOTIFICATION-TYPE
    OBJECTS         { sonusEventDescription, sonusEventClass, 
                      sonusEventLevel, sonusSequenceId, sonusEventTime, 
                      sonusSoftwareDownloadEntityName, 
                      sonusSoftwareDownloadEntityType, 
                      sonusSoftwareDownloadStatus }
    STATUS          current
    DESCRIPTION     
            "This trap indicates the status of the software
             download"
    ::= { sonusNodeMIBNotificationsPrefix 73 }

sonusNodeNetworkFailoverActiveNotification NOTIFICATION-TYPE
    OBJECTS         { sonusEventDescription, sonusEventClass, 
                      sonusEventLevel, sonusSequenceId, sonusEventTime }
    STATUS          current
    DESCRIPTION     
            "This trap indicates that Network failover has started."
    ::= { sonusNodeMIBNotificationsPrefix 74 }

sonusNodeNetworkFailoverClearNotification NOTIFICATION-TYPE
    OBJECTS         { sonusEventDescription, sonusEventClass, 
                      sonusEventLevel, sonusSequenceId, sonusEventTime }
    STATUS          current
    DESCRIPTION     
            "This trap indicates that Network failover has been cleared."
    ::= { sonusNodeMIBNotificationsPrefix 75 }

sonusNetworkProcessorIpdhGeneralErrorNotification NOTIFICATION-TYPE
    OBJECTS         { sonusErrorType, sonusErrorCount, 
                      sonusEventDescription, sonusEventClass, 
                      sonusEventLevel, sonusSequenceId, sonusEventTime }
    STATUS          current
    DESCRIPTION     
            "This trap indicates that the NP or NPIO is reporting errors
             that usually should not happen."
    ::= { sonusNodeMIBNotificationsPrefix 76 }

sonusNodeNfsServerSwitchoverFailureNotification NOTIFICATION-TYPE
    OBJECTS         { sonusShelfIndex, sonusSlotIndex, sonusNfsServer, 
                      sonusNfsServerIp, sonusNfsServerMount, 
                      sonusNfsReason, sonusEventDescription, 
                      sonusEventClass, sonusEventLevel, sonusSequenceId, 
                      sonusEventTime }
    STATUS          current
    DESCRIPTION     
            "Indicates that the Active NFS server switchover has failed."
    ::= { sonusNodeMIBNotificationsPrefix 77 }

sonusSonetLoginThresholdNotification NOTIFICATION-TYPE
    OBJECTS         { sonusUserListUserName, sonusEventDescription, 
                      sonusEventClass, sonusEventLevel }
    STATUS          current
    DESCRIPTION     
            "This trap will get generated on excessive invalid login attempts"
    ::= { sonusNodeMIBNotificationsPrefix 78 }

sonusNodeServerTempThresholdWarningNotification NOTIFICATION-TYPE
    OBJECTS         { sonusShelfIndex, sonusSlotIndex, 
                      sonusEventDescription, sonusEventClass, 
                      sonusEventLevel, sonusSequenceId, sonusEventTime }
    STATUS          current
    DESCRIPTION     
            "A sonusNodeServerTempThresholdWarning trap indicates that the
             operating temperature of the specified shelf and slot
             has exceeded configured threshold for configured duration"
    ::= { sonusNodeMIBNotificationsPrefix 79 }

sonusNodeServerTempClearThresholdNotification NOTIFICATION-TYPE
    OBJECTS         { sonusShelfIndex, sonusSlotIndex, 
                      sonusEventDescription, sonusEventClass, 
                      sonusEventLevel, sonusSequenceId, sonusEventTime }
    STATUS          current
    DESCRIPTION     
            "A sonusNodeServerTempClearThreshold trap indicates that the
             operating temperature of the specified shelf and slot
             is below configured clear threshold for configured duration"
    ::= { sonusNodeMIBNotificationsPrefix 80 }

END -- end of module SONUS-NODE-MIB.
