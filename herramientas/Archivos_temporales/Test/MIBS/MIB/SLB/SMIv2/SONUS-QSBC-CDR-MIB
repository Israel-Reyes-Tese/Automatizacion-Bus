--
-- This SMIv2 module has been generated by smidump 0.2-cvs. Do not edit.
--

SONUS-QSBC-CDR-MIB DEFINITIONS ::= BEGIN

IMPORTS
    Counter32, Counter64, Gauge32, Integer32, IpAddress, MODULE-IDENTITY, 
    OBJECT-TYPE, Unsigned32
        FROM SNMPv2-SMI
    DateAndTime, RowStatus, TEXTUAL-CONVENTION, TruthValue
        FROM SNMPv2-TC
    sonusCommonSoftwarePlatformServicesMIBs
        FROM SONUS-SMI;

sonusQSbcCdrMIB MODULE-IDENTITY
    LAST-UPDATED    "201902070000Z"
    ORGANIZATION    
            "Ribbon Communications, Inc."
    CONTACT-INFO    
            "Customer Support        
             Ribbon Communications, Inc. 
             4 Technology Park Drive 
             Westford, MA 01886      
             USA                     
                                     
             Tel: 978-614-8100       
             Fax: 978-614-8609"
    DESCRIPTION     
            "Configuration for Q Series SBC Format Accounting Records."
    REVISION        "201902070000Z"
    DESCRIPTION     
            "Auto generated MIB."
    ::= { sonusCommonSoftwarePlatformServicesMIBs 24 }


String ::= TEXTUAL-CONVENTION
    DISPLAY-HINT    "1t"
    STATUS          current
    DESCRIPTION     
            "xs:string"
    SYNTAX          OCTET STRING

SonusQSbcCdrChecksumKey ::= TEXTUAL-CONVENTION
    DISPLAY-HINT    "1t"
    STATUS          current
    DESCRIPTION     
            "
             Enter checksum key between 16 and 64 characters in length and
             consisting of digits and upper or lower-case letters.
             "
    SYNTAX          OCTET STRING (SIZE(16..64))

sonusQSbcCdr OBJECT IDENTIFIER
    ::= { sonusQSbcCdrMIB 1 }

sonusQSbcCdrAdmin OBJECT IDENTIFIER
    ::= { sonusQSbcCdr 1 }

END -- end of module SONUS-QSBC-CDR-MIB.
