--
-- ZTE-zte-MIB_V3.0.mib
-- MIB generated by MG-SOFT Visual MIB Builder Version 6.0  Build 88
-- Tuesday, February 10, 2017 at 17:17:05
--

--  ZTE-DCIM-MIB_V2.0.mib
-- MIB generated by MG-SOFT Visual MIB Builder Version 6.0  Build 88
-- Wednesday, November 12, 2014 at 17:27:00
-- 
--  ZTE-DCIM-MIB1.mib
-- MIB generated by MG-SOFT Visual MIB Builder Version 5.0  Build 250
-- Thursday, August 01, 2013 at 19:16:13
-- 
--  ZTE-DCIM-MIB_V1.0.0723.mib
-- MIB generated by MG-SOFT Visual MIB Builder Version 6.0  Build 88
-- Thursday, July 25, 2013 at 18:34:54
-- 

	ZTE-DCIM-MIB DEFINITIONS ::= BEGIN
 
		IMPORTS
			MODULE-IDENTITY,enterprises, Integer32, OBJECT-TYPE, OBJECT-IDENTITY, NOTIFICATION-TYPE,snmpModules			
				FROM SNMPv2-SMI			
			DisplayString, DateAndTime, TEXTUAL-CONVENTION			
				FROM SNMPv2-TC;
	
	  
		zteSnmpMIB MODULE-IDENTITY
       LAST-UPDATED "9901190000Z"            -- 19 January 2017
       ORGANIZATION "iDCIM Working Group"
       CONTACT-INFO "iDCIM "
       DESCRIPTION  "The SNMP Management Architecture MIB"
   -- Revision History

       REVISION     "9901190000Z"            -- 19 January 2014
       DESCRIPTION  "Updated editors' addresses, fixed typos.
                     Published as RFC2571.
                    "
       REVISION     "9711200000Z"            -- 20 November 1997
       DESCRIPTION  "The initial version, published in RFC 2271.
                    "
       ::= { snmpModules 10 }
--
-- Textual conventions
--
	
--  Textual conventions
-- 
-- Textual conventions
-- 
-- Textual conventions
-- 
				
		AlarmLevel ::= TEXTUAL-CONVENTION
			STATUS current
			DESCRIPTION 
				"
				indeterminate(0)
                critical(1)
                major(2)
                minor(3)
                warning(4)
                cleared(5)
				"
			SYNTAX INTEGER
				{
				indeterminate(0),
                critical(1),
                major(2),
                minor(3),
                warning(4),
                cleared(5)
				}

	
--
-- Node definitions
--
	
--  Node definitions
-- 
-- Node definitions
-- 
-- Node definitions
-- 
-- 1.3.6.1.4.1.39026
-- 1.3.6.1.4.1.39026
-- 1.3.6.1.4.1.39026
		-- 1.3.6.1.4.1.39026
		zte OBJECT-IDENTITY
			STATUS current
			DESCRIPTION 
				"The root of the OID sub-tree assigned to Company by the Internet Assigned Numbers Authority (IANA)"
			::= { enterprises 39026 }

		
--    1.3.6.1.4.1.39026.3
-- 1.3.6.1.4.1.39026.3
-- 1.3.6.1.4.1.39026.3
		-- 1.3.6.1.4.1.39026.3
		products OBJECT-IDENTITY
			STATUS current
			DESCRIPTION 
				"Sub-tree for specific object and event definitions"
			::= { zte 3 }

		
--    1.3.6.1.4.1.39026.3.1
-- 1.3.6.1.4.1.39026.3.1
-- 1.3.6.1.4.1.39026.3.1
		-- 1.3.6.1.4.1.39026.3.1
		dcim OBJECT-IDENTITY
			STATUS current
			DESCRIPTION 
				"Description: ZTE dcim."
			::= { products 1 }

		
--    1.3.6.1.4.1.39026.3.1.1
-- 1.3.6.1.4.1.39026.3.1.1
-- 1.3.6.1.4.1.39026.3.1.1
		-- 1.3.6.1.4.1.39026.3.1.1
		dcimSystem OBJECT IDENTIFIER ::= { dcim 1 }

		
--    1.3.6.1.4.1.39026.3.1.1.1
-- 1.3.6.1.4.1.39026.3.1.1.1
-- 1.3.6.1.4.1.39026.3.1.1.1
		-- 1.3.6.1.4.1.39026.3.1.1.1
		dcimSysName OBJECT-TYPE
			SYNTAX DisplayString
			MAX-ACCESS read-only
			STATUS current
			DESCRIPTION
				"Description: dcim system name. "
			::= { dcimSystem 1 }

		
--  
-- 
-- 1.3.6.1.4.1.39026.3.1.1.2
-- 1.3.6.1.4.1.39026.3.1.1.2
-- 1.3.6.1.4.1.39026.3.1.1.2
		-- 1.3.6.1.4.1.39026.3.1.1.2
		dcimSysDesc OBJECT-TYPE
			SYNTAX DisplayString
			MAX-ACCESS read-only
			STATUS current
			DESCRIPTION
				"Description: MDC system description."
			::= { dcimSystem 2 }

		
--    1.3.6.1.4.1.39026.3.1.1.3
-- 1.3.6.1.4.1.39026.3.1.1.3
-- 1.3.6.1.4.1.39026.3.1.1.3
		-- 1.3.6.1.4.1.39026.3.1.1.3
		dcimSysLocation OBJECT-TYPE
			SYNTAX DisplayString
			MAX-ACCESS read-only
			STATUS current
			DESCRIPTION
				"Description: The location of the MDC, using IDC encoding: room number-MDC number."
			::= { dcimSystem 3 }

		
--    1.3.6.1.4.1.39026.3.1.1.4
-- 1.3.6.1.4.1.39026.3.1.1.4
-- 1.3.6.1.4.1.39026.3.1.1.4
		-- 1.3.6.1.4.1.39026.3.1.1.4
		dcimSysManufacturer OBJECT-TYPE
			SYNTAX DisplayString
			MAX-ACCESS read-only
			STATUS current
			DESCRIPTION
				"Description: MDC manufacturer."
			::= { dcimSystem 4 }

		
--    1.3.6.1.4.1.39026.3.1.1.5
-- 1.3.6.1.4.1.39026.3.1.1.5
-- 1.3.6.1.4.1.39026.3.1.1.5
		-- 1.3.6.1.4.1.39026.3.1.1.5
		dcimSysTime OBJECT-TYPE
			SYNTAX DisplayString
			MAX-ACCESS read-only
			STATUS current
			DESCRIPTION
				"Description: The current system time.
				eg. 20100607T152000+08"
			::= { dcimSystem 5 }


--    1.3.6.1.4.1.39026.3.1.1.6
-- 1.3.6.1.4.1.39026.3.1.1.6
-- 1.3.6.1.4.1.39026.3.1.1.6
		-- 1.3.6.1.4.1.39026.3.1.1.6
		dcimEquipsTable OBJECT-TYPE
			SYNTAX SEQUENCE OF DcimEquipsEntry
			MAX-ACCESS not-accessible
			STATUS current
			DESCRIPTION
				"Description."
			::= { dcimSystem 6 }

--    1.3.6.1.4.1.39026.3.1.1.6.1
-- 1.3.6.1.4.1.39026.3.1.1.6.1
-- 1.3.6.1.4.1.39026.3.1.1.6.1
		-- 1.3.6.1.4.1.39026.3.1.1.6.1
		dcimEquipsEntry OBJECT-TYPE
			SYNTAX DcimEquipsEntry
			MAX-ACCESS not-accessible
			STATUS current
			DESCRIPTION
				"Description."
			INDEX { equipIndex }
			::= { dcimEquipsTable 1 }

		
		DcimEquipsEntry ::=
			SEQUENCE { 
				equipIndex
					Integer32,
				equipType
					DisplayString,
				equipName
					DisplayString,
				equipManufacturer
					DisplayString,
				equipModel
					DisplayString,
				equipCommStat
					Integer32,
				equipAlarmStat
					Integer32,
				equipTimestamp
					DisplayString,
				equipOid
					DisplayString,
				equipInst
					DisplayString,
				equipPosition
					DisplayString,
				equipProtocolType
					DisplayString,
				equipIpAddress
					DisplayString,
				equipPort
					DisplayString
					
			 }

--    1.3.6.1.4.1.39026.3.1.1.6.1.1
-- 1.3.6.1.4.1.39026.3.1.1.6.1.1
-- 1.3.6.1.4.1.39026.3.1.1.6.1.1
		-- 1.3.6.1.4.1.39026.3.1.1.6.1.1
		equipIndex OBJECT-TYPE
			SYNTAX Integer32 (1..2147483647)
			MAX-ACCESS read-only
			STATUS current
			DESCRIPTION
				"Description: Equipment index. Used to uniquely identify a device. starting from 1."
			::= { dcimEquipsEntry 1 }

		
--    1.3.6.1.4.1.39026.3.1.1.6.1.2
-- 1.3.6.1.4.1.39026.3.1.1.6.1.2
-- 1.3.6.1.4.1.39026.3.1.1.6.1.2
		-- 1.3.6.1.4.1.39026.3.1.1.6.1.2
		equipType OBJECT-TYPE
			SYNTAX DisplayString
			MAX-ACCESS read-only
			STATUS current
			DESCRIPTION
				"Description: The classification of equipment. As defined in the relevant conventions."
			::= { dcimEquipsEntry 2 }

		
--    1.3.6.1.4.1.39026.3.1.1.6.1.3
-- 1.3.6.1.4.1.39026.3.1.1.6.1.3
-- 1.3.6.1.4.1.39026.3.1.1.6.1.3
		-- 1.3.6.1.4.1.39026.3.1.1.6.1.3
		equipName OBJECT-TYPE
			SYNTAX DisplayString
			MAX-ACCESS read-only
			STATUS current
			DESCRIPTION
				"Description: The device name."
			::= { dcimEquipsEntry 3 }

		
--    1.3.6.1.4.1.39026.3.1.1.6.1.4
-- 1.3.6.1.4.1.39026.3.1.1.6.1.4
-- 1.3.6.1.4.1.39026.3.1.1.6.1.4
		-- 1.3.6.1.4.1.39026.3.1.1.6.1.4
		equipManufacturer OBJECT-TYPE
			SYNTAX DisplayString
			MAX-ACCESS read-only
			STATUS current
			DESCRIPTION
				"Description: Equipment manufacturers."
			::= { dcimEquipsEntry 4 }

		
--    1.3.6.1.4.1.39026.3.1.1.6.1.5
-- 1.3.6.1.4.1.39026.3.1.1.6.1.5
-- 1.3.6.1.4.1.39026.3.1.1.6.1.5
		-- 1.3.6.1.4.1.39026.3.1.1.6.1.5
		equipModel OBJECT-TYPE
			SYNTAX DisplayString
			MAX-ACCESS read-only
			STATUS current
			DESCRIPTION
				"Description: Equipment model."
			::= { dcimEquipsEntry 5 }

		
--    1.3.6.1.4.1.39026.3.1.1.6.1.6
-- 1.3.6.1.4.1.39026.3.1.1.6.1.6
-- 1.3.6.1.4.1.39026.3.1.1.6.1.6
		-- 1.3.6.1.4.1.39026.3.1.1.6.1.6
		equipCommStat OBJECT-TYPE
			SYNTAX Integer32
			MAX-ACCESS read-only
			STATUS current
			DESCRIPTION
				"Description: Communication status.
				Values: 0-ok, 1-Interrupt"
			::= { dcimEquipsEntry 6 }

		
--    1.3.6.1.4.1.39026.3.1.1.6.1.7
-- 1.3.6.1.4.1.39026.3.1.1.6.1.7
-- 1.3.6.1.4.1.39026.3.1.1.6.1.7
		-- 1.3.6.1.4.1.39026.3.1.1.6.1.7
		equipAlarmStat OBJECT-TYPE
			SYNTAX Integer32
			MAX-ACCESS read-only
			STATUS current
			DESCRIPTION
				"Description: Alarm status.
				Values: 0-ok, 1-Alarm"
			::= { dcimEquipsEntry 7 }
			
--    1.3.6.1.4.1.39026.3.1.1.6.1.8
-- 1.3.6.1.4.1.39026.3.1.1.6.1.8		
-- 1.3.6.1.4.1.39026.3.1.1.6.1.8
		-- 1.3.6.1.4.1.39026.3.1.1.6.1.8
		equipTimestamp OBJECT-TYPE
			SYNTAX DisplayString
			MAX-ACCESS read-only
			STATUS current
			DESCRIPTION
				"Description: The timestamp of the last update.
				eg. 20100607T152000+08"
			::= { dcimEquipsEntry 8 }
			
--    1.3.6.1.4.1.39026.3.1.1.6.1.9
-- 1.3.6.1.4.1.39026.3.1.1.6.1.9		
-- 1.3.6.1.4.1.39026.3.1.1.6.1.9
		-- 1.3.6.1.4.1.39026.3.1.1.6.1.9
		equipOid OBJECT-TYPE
			SYNTAX DisplayString
			MAX-ACCESS read-only
			STATUS current
			DESCRIPTION
				"Description: The equip oid in iDCIM."
			::= { dcimEquipsEntry 9 }
			
--    1.3.6.1.4.1.39026.3.1.1.6.1.10
-- 1.3.6.1.4.1.39026.3.1.1.6.1.10		
-- 1.3.6.1.4.1.39026.3.1.1.6.1.10
		-- 1.3.6.1.4.1.39026.3.1.1.6.1.10
		equipInst OBJECT-TYPE
			SYNTAX DisplayString
			MAX-ACCESS read-only
			STATUS current
			DESCRIPTION
				"Description: The name of the device belongs to the micro module or the name of the room"
			::= { dcimEquipsEntry 10 }
			
--    1.3.6.1.4.1.39026.3.1.1.6.1.11
-- 1.3.6.1.4.1.39026.3.1.1.6.1.11		
-- 1.3.6.1.4.1.39026.3.1.1.6.1.11
		-- 1.3.6.1.4.1.39026.3.1.1.6.1.11
		equipPosition OBJECT-TYPE
			SYNTAX DisplayString
			MAX-ACCESS read-only
			STATUS current
			DESCRIPTION
				"Description: The equip position.
				eg. 20100607T152000+08"
			::= { dcimEquipsEntry 11 }
			
--    1.3.6.1.4.1.39026.3.1.1.6.1.12
-- 1.3.6.1.4.1.39026.3.1.1.6.1.12		
-- 1.3.6.1.4.1.39026.3.1.1.6.1.12
		-- 1.3.6.1.4.1.39026.3.1.1.6.1.12
		equipProtocolType OBJECT-TYPE
			SYNTAX DisplayString
			MAX-ACCESS read-only
			STATUS current
			DESCRIPTION
				"Description: The equip ProtocolType.
				eg. 20100607T152000+08"
			::= { dcimEquipsEntry 12 }
			
--    1.3.6.1.4.1.39026.3.1.1.6.1.13
-- 1.3.6.1.4.1.39026.3.1.1.6.1.13		
-- 1.3.6.1.4.1.39026.3.1.1.6.1.13
		-- 1.3.6.1.4.1.39026.3.1.1.6.1.13
		equipIpAddress OBJECT-TYPE
			SYNTAX DisplayString
			MAX-ACCESS read-only
			STATUS current
			DESCRIPTION
				"Description: The equip Ip Address.
				eg. 20100607T152000+08"
			::= { dcimEquipsEntry 13 }
			
--    1.3.6.1.4.1.39026.3.1.1.6.1.14
-- 1.3.6.1.4.1.39026.3.1.1.6.1.14		
-- 1.3.6.1.4.1.39026.3.1.1.6.1.14
		-- 1.3.6.1.4.1.39026.3.1.1.6.1.
		equipPort OBJECT-TYPE
			SYNTAX DisplayString
			MAX-ACCESS read-only
			STATUS current
			DESCRIPTION
				"Description: The equip Port.
				eg. 20100607T152000+08"
			::= { dcimEquipsEntry 14 }
			
--    1.3.6.1.4.1.39026.3.1.2
-- 1.3.6.1.4.1.39026.3.1.2
-- 1.3.6.1.4.1.39026.3.1.2
		-- 1.3.6.1.4.1.39026.3.1.2
		dcimAlarm OBJECT IDENTIFIER ::= { dcim 2 }

		
--    1.3.6.1.4.1.39026.3.1.2.1
-- 1.3.6.1.4.1.39026.3.1.2.1
-- 1.3.6.1.4.1.39026.3.1.2.1
		-- 1.3.6.1.4.1.39026.3.1.2.1
		dcimNotifications OBJECT IDENTIFIER ::= { dcimAlarm 1 }

		
--    1.3.6.1.4.1.39026.3.1.2.1.1
-- 1.3.6.1.4.1.39026.3.1.2.1.1
-- 1.3.6.1.4.1.39026.3.1.2.1.1
		-- 1.3.6.1.4.1.39026.3.1.2.1.1
		dcimAlarmTrapDefine NOTIFICATION-TYPE
			OBJECTS {alarmTrapIndex,alarmTrapEquipType,alarmTrapEquipOid,alarmTrapOid,alarmTrapStatus,alarmTrapLevel,alarmTrapTime,alarmTrapValue,alarmTrapText,
alarmTrapUserAction,alarmTrapInst,alarmEquipName,alarmKey,alarmCode,alarmEquipIndex}
			STATUS current
			DESCRIPTION 
				"Description: trap oid."
			::= { dcimNotifications 1 }


--    1.3.6.1.4.1.39026.3.1.2.1.3
-- 1.3.6.1.4.1.39026.3.1.2.1.3
-- 1.3.6.1.4.1.39026.3.1.2.1.3
		-- 1.3.6.1.4.1.39026.3.1.2.1.3
		alarmTrapTable OBJECT-TYPE
			SYNTAX SEQUENCE OF AlarmTrapEntry
			MAX-ACCESS not-accessible
			STATUS current
			DESCRIPTION
				"Description."
			::= { dcimNotifications 3 }

		
--    1.3.6.1.4.1.39026.3.1.2.1.3.1
-- 1.3.6.1.4.1.39026.3.1.2.1.3.1
-- 1.3.6.1.4.1.39026.3.1.2.1.3.1
		-- 1.3.6.1.4.1.39026.3.1.2.1.3.1
		alarmTrapEntry OBJECT-TYPE
			SYNTAX AlarmTrapEntry
			MAX-ACCESS not-accessible
			STATUS current
			DESCRIPTION
				"Description."
			INDEX { alarmTrapIndex }
			::= { alarmTrapTable 1 }

		
		AlarmTrapEntry ::=
			SEQUENCE { 
				alarmTrapIndex
					Integer32,
				alarmTrapEquipType
					DisplayString,
				alarmTrapEquipOid
					DisplayString,
				alarmTrapOid
					DisplayString,
				alarmTrapStatus
					Integer32,
				alarmTrapLevel
					Integer32,
				alarmTrapTime
					DateAndTime,
				alarmTrapValue
					DisplayString,
				alarmTrapText
					DisplayString,
				alarmTrapUserAction
					DisplayString,
				alarmTrapInst
					DisplayString,
				alarmEquipName
					DisplayString,
				alarmKey
					DisplayString,
				alarmCode
					DisplayString
			 }

--    1.3.6.1.4.1.39026.3.1.2.1.3.1.1
-- 1.3.6.1.4.1.39026.3.1.2.1.3.1.1
-- 1.3.6.1.4.1.39026.3.1.2.1.3.1.1
		-- 1.3.6.1.4.1.39026.3.1.2.1.3.1.1
		alarmTrapIndex OBJECT-TYPE
			SYNTAX Integer32 (1..2147483647)
			MAX-ACCESS read-only
			STATUS current
			DESCRIPTION
				"Description: The serial number, starting from 1."
			::= { alarmTrapEntry 1 }

		
--    1.3.6.1.4.1.39026.3.1.2.1.3.1.2
-- 1.3.6.1.4.1.39026.3.1.2.1.3.1.2
-- 1.3.6.1.4.1.39026.3.1.2.1.3.1.2
		-- 1.3.6.1.4.1.39026.3.1.3.1.2.1.2
		alarmTrapEquipType OBJECT-TYPE
			SYNTAX DisplayString
			MAX-ACCESS read-only
			STATUS current
			DESCRIPTION
				"Description: The classification of equipment. As defined in the iDCIM."
			::= { alarmTrapEntry 2 }

		
--    1.3.6.1.4.1.39026.3.1.2.1.3.1.3
-- 1.3.6.1.4.1.39026.3.1.2.1.3.1.3
-- 1.3.6.1.4.1.39026.3.1.2.1.3.1.3
		-- 1.3.6.1.4.1.39026.3.1.2.1.3.1.3
		alarmTrapEquipOid OBJECT-TYPE
			SYNTAX DisplayString
			MAX-ACCESS read-only
			STATUS current
			DESCRIPTION
				"Description: Equipment OID. Used to uniquely identify a device. "
			::= { alarmTrapEntry 3 }

		
--    1.3.6.1.4.1.39026.3.1.2.1.3.1.4
-- 1.3.6.1.4.1.39026.3.1.2.1.3.1.4
-- 1.3.6.1.4.1.39026.3.1.2.1.3.1.4
		-- 1.3.6.1.4.1.39026.3.1.2.1.3.1.4
		alarmTrapOid OBJECT-TYPE
			SYNTAX DisplayString
			MAX-ACCESS read-only
			STATUS current
			DESCRIPTION
				"Description: Alarm object OID."
			::= { alarmTrapEntry 4 }

		
-- 1.3.6.1.4.1.39026.3.1.2.1.3.1.5
-- 1.3.6.1.4.1.39026.3.1.2.1.3.1.5
-- 1.3.6.1.4.1.39026.3.1.2.1.3.1.5
		-- 1.3.6.1.4.1.39026.3.1.2.1.3.1.5
		alarmTrapStatus OBJECT-TYPE
			SYNTAX Integer32
			MAX-ACCESS read-only
			STATUS current
			DESCRIPTION
				"Description: Alarm type
				Values: 1-alarm, 2-restore"
			::= { alarmTrapEntry 5 }

		
--    1.3.6.1.4.1.39026.3.1.2.1.3.1.6
-- 1.3.6.1.4.1.39026.3.1.2.1.3.1.6
-- 1.3.6.1.4.1.39026.3.1.2.1.3.1.6
		-- 1.3.6.1.4.1.39026.3.1.2.1.3.1.6
		alarmTrapLevel OBJECT-TYPE
			SYNTAX Integer32
			MAX-ACCESS read-only
			STATUS current
			DESCRIPTION
				"Description: Alarm level, as defined in the iDCIM."
			::= { alarmTrapEntry 6 }

		
--    1.3.6.1.4.1.39026.3.1.2.1.3.1.7
-- 1.3.6.1.4.1.39026.3.1.2.1.3.1.7
-- 1.3.6.1.4.1.39026.3.1.2.1.3.1.7
		-- 1.3.6.1.4.1.39026.3.1.2.1.3.1.7
		alarmTrapTime OBJECT-TYPE
			SYNTAX DisplayString
			MAX-ACCESS read-only
			STATUS current
			DESCRIPTION
				"Description: Alarm time."
			::= { alarmTrapEntry 7 }

		
--  eg:2013-07-22 12:00:00
-- 1.3.6.1.4.1.39026.3.1.2.1.3.1.8
-- 1.3.6.1.4.1.39026.3.1.2.1.3.1.8
-- 1.3.6.1.4.1.39026.3.1.2.1.3.1.8
		-- 1.3.6.1.4.1.39026.3.1.2.1.3.1.8
		alarmTrapValue OBJECT-TYPE
			SYNTAX DisplayString
			MAX-ACCESS read-only
			STATUS current
			DESCRIPTION
				"Description: Values in the alarm occurs."
			::= { alarmTrapEntry 8 }

		
--    1.3.6.1.4.1.39026.3.1.2.1.3.1.9
-- 1.3.6.1.4.1.39026.3.1.2.1.3.1.9
-- 1.3.6.1.4.1.39026.3.1.2.1.3.1.9
		-- 1.3.6.1.4.1.39026.3.1.2.1.3.1.9
		alarmTrapText OBJECT-TYPE
			SYNTAX DisplayString
			MAX-ACCESS read-only
			STATUS current
			DESCRIPTION
				"Description: Warning description information."
			::= { alarmTrapEntry 9 }

		
--    1.3.6.1.4.1.39026.3.1.2.1.3.1.10
-- 1.3.6.1.4.1.39026.3.1.2.1.3.1.10
-- 1.3.6.1.4.1.39026.3.1.2.1.3.1.10
		-- 1.3.6.1.4.1.39026.3.1.2.1.3.1.10
		alarmTrapUserAction OBJECT-TYPE
			SYNTAX DisplayString
			MAX-ACCESS read-only
			STATUS current
			DESCRIPTION
				"Description: Some suggestions for user handling."
			::= { alarmTrapEntry 10 }

--    1.3.6.1.4.1.39026.3.1.2.1.3.1.11
-- 1.3.6.1.4.1.39026.3.1.2.1.3.1.11
-- 1.3.6.1.4.1.39026.3.1.2.1.3.1.11
		-- 1.3.6.1.4.1.39026.3.1.2.1.3.1.11
		alarmTrapInst OBJECT-TYPE
			SYNTAX DisplayString
			MAX-ACCESS read-only
			STATUS current
			DESCRIPTION
				"Description: The mdc's name or room's name."
			::= { alarmTrapEntry 11 }
			
--    1.3.6.1.4.1.39026.3.1.2.1.3.1.12
-- 1.3.6.1.4.1.39026.3.1.2.1.3.1.12
-- 1.3.6.1.4.1.39026.3.1.2.1.3.1.12
		-- 1.3.6.1.4.1.39026.3.1.2.1.3.1.12
		alarmEquipName OBJECT-TYPE
			SYNTAX DisplayString
			MAX-ACCESS read-only
			STATUS current
			DESCRIPTION
				"Description: Equipment name."
			::= { alarmTrapEntry 12 }

--    1.3.6.1.4.1.39026.3.1.2.1.3.1.13
-- 1.3.6.1.4.1.39026.3.1.2.1.3.1.13
-- 1.3.6.1.4.1.39026.3.1.2.1.3.1.13
		-- 1.3.6.1.4.1.39026.3.1.2.1.3.1.13
		alarmKey OBJECT-TYPE
			SYNTAX DisplayString
			MAX-ACCESS read-only
			STATUS current
			DESCRIPTION
				"Description: Used to uniquely identify a alarm."
			::= { alarmTrapEntry 13 }
			
--    1.3.6.1.4.1.39026.3.1.2.1.3.1.14
-- 1.3.6.1.4.1.39026.3.1.2.1.3.1.14
-- 1.3.6.1.4.1.39026.3.1.2.1.3.1.14
		-- 1.3.6.1.4.1.39026.3.1.2.1.3.1.14
		alarmCode OBJECT-TYPE
			SYNTAX DisplayString
			MAX-ACCESS read-only
			STATUS current
			DESCRIPTION
				"Description: The code for the alarm."
			::= { alarmTrapEntry 14 }
			
--    1.3.6.1.4.1.39026.3.1.2.1.3.1.15
-- 1.3.6.1.4.1.39026.3.1.2.1.3.1.15
-- 1.3.6.1.4.1.39026.3.1.2.1.3.1.15
		-- 1.3.6.1.4.1.39026.3.1.2.1.3.1.15
		alarmEquipIndex OBJECT-TYPE
			SYNTAX DisplayString
			MAX-ACCESS read-only
			STATUS current
			DESCRIPTION
				"Description: The equip index"
			::= { alarmTrapEntry 15 }
		
--    1.3.6.1.4.1.39026.3.1.3
-- 1.3.6.1.4.1.39026.3.1.3
-- 1.3.6.1.4.1.39026.3.1.3
		-- 1.3.6.1.4.1.39026.3.1.3
		dcimStatistic OBJECT IDENTIFIER ::= { dcim 3 }

		
--    1.3.6.1.4.1.39026.3.1.3.1
-- 1.3.6.1.4.1.39026.3.1.3.1
-- 1.3.6.1.4.1.39026.3.1.3.1
		-- 1.3.6.1.4.1.39026.3.1.3.1
		dcimPUE OBJECT-TYPE
			SYNTAX Integer32
			MAX-ACCESS read-only
			STATUS current
			DESCRIPTION
				"Description: The current PUE."
			::= { dcimStatistic 1 }

		
--    1.3.6.1.4.1.39026.3.1.3.2
-- 1.3.6.1.4.1.39026.3.1.3.2
-- 1.3.6.1.4.1.39026.3.1.3.2
		-- 1.3.6.1.4.1.39026.3.1.3.2
		dcimLoad OBJECT-TYPE
			SYNTAX Integer32
			UNITS "kW"
			MAX-ACCESS read-only
			STATUS current
			DESCRIPTION
				"Description: The current system load."
			::= { dcimStatistic 2 }

		
--    1.3.6.1.4.1.39026.3.1.3.3
-- 1.3.6.1.4.1.39026.3.1.3.3
-- 1.3.6.1.4.1.39026.3.1.3.3
		-- 1.3.6.1.4.1.39026.3.1.3.3
		dcimLoadall OBJECT-TYPE
			SYNTAX Integer32
			UNITS "kW"
			MAX-ACCESS read-only
			STATUS current
			DESCRIPTION
				"Description: total load."
			::= { dcimStatistic 3 }

		
--    1.3.6.1.4.1.39026.3.1.3.4
-- 1.3.6.1.4.1.39026.3.1.3.4
-- 1.3.6.1.4.1.39026.3.1.3.4
		-- 1.3.6.1.4.1.39026.3.1.3.4
		dcimMaxpower OBJECT-TYPE
			SYNTAX Integer32
			UNITS "kW"
			MAX-ACCESS read-only
			STATUS current
			DESCRIPTION
				"Description: "
			::= { dcimStatistic 4 }

		
--    1.3.6.1.4.1.39026.3.1.3.5
-- 1.3.6.1.4.1.39026.3.1.3.5
-- 1.3.6.1.4.1.39026.3.1.3.5
		-- 1.3.6.1.4.1.39026.3.1.3.5
		dcimLoadrate OBJECT-TYPE
			SYNTAX Integer32
			UNITS "%"
			MAX-ACCESS read-only
			STATUS current
			DESCRIPTION
				"Description: "
			::= { dcimStatistic 5 }

		
--    1.3.6.1.4.1.39026.3.1.3.6
-- 1.3.6.1.4.1.39026.3.1.3.6
-- 1.3.6.1.4.1.39026.3.1.3.6
		-- 1.3.6.1.4.1.39026.3.1.3.6
		dcimEnergy OBJECT-TYPE
			SYNTAX Integer32
			UNITS "KWh"
			MAX-ACCESS read-only
			STATUS current
			DESCRIPTION
				"Description: "
			::= { dcimStatistic 6 }

		
--    1.3.6.1.4.1.39026.3.1.3.7
-- 1.3.6.1.4.1.39026.3.1.3.7
-- 1.3.6.1.4.1.39026.3.1.3.7
		-- 1.3.6.1.4.1.39026.3.1.3.7
		dcimITEnergy OBJECT-TYPE
			SYNTAX Integer32
			UNITS "KWh"
			MAX-ACCESS read-only
			STATUS current
			DESCRIPTION
				"Description: "
			::= { dcimStatistic 7 }

--    1.3.6.1.4.1.39026.3.1.4
-- 1.3.6.1.4.1.39026.3.1.4
-- 1.3.6.1.4.1.39026.3.1.4
		-- 1.3.6.1.4.1.39026.3.1.4
		dcimMonObjects OBJECT IDENTIFIER ::= { dcim 4 }
		

--    1.3.6.1.4.1.39026.3.1.4.1
-- 1.3.6.1.4.1.39026.3.1.4.1
-- 1.3.6.1.4.1.39026.3.1.4.1
		-- 1.3.6.1.4.1.39026.3.1.4.1
		powerMeter OBJECT IDENTIFIER ::= { dcimMonObjects 1 }

		
--    1.3.6.1.4.1.39026.3.1.4.1.1
-- 1.3.6.1.4.1.39026.3.1.4.1.1
-- 1.3.6.1.4.1.39026.3.1.4.1.1
		-- 1.3.6.1.4.1.39026.3.1.4.1.1
		powerMeterAMYDMTable OBJECT-TYPE
			SYNTAX SEQUENCE OF powerMeterAMYDMEntry
			MAX-ACCESS not-accessible
			STATUS current
			DESCRIPTION
				"Description."
			::= { powerMeter 1 }

--    1.3.6.1.4.1.39026.3.1.4.1.1.1
-- 1.3.6.1.4.1.39026.3.1.4.1.1.1
-- 1.3.6.1.4.1.39026.3.1.4.1.1.1
		-- 1.3.6.1.4.1.39026.3.1.4.1.1.1
		powerMeterAMYDMEntry OBJECT-TYPE
			SYNTAX powerMeterAMYDMEntry
			MAX-ACCESS not-accessible
			STATUS current
			DESCRIPTION
				"Description."
			INDEX { pmYdmIndex }
			::= { powerMeterAMYDMTable 1 }


		powerMeterAMYDMEntry ::=
			SEQUENCE { 
				pmYdmIndex
					Integer32,
				pmYdmEquipOid
					DisplayString,
				pmYdmEquipName
					DisplayString,
				pmYdmCollectionTime
					DisplayString,
				aVoltage1
					Integer32,
				aVoltage2
					Integer32,
				aVoltage3
					Integer32,
				aAvgVoltage
					Integer32,
				aLineVoltage12
					Integer32,
				aLineVoltage23
					Integer32,
				aLineVoltage31
					Integer32,
				aAvgLineVoltage
					Integer32,
				aCurrent1
					Integer32,
				aCurrent2
					Integer32,
				aCurrent3
					Integer32,
				aAvgCurrent
					Integer32,
				aZeroLineCurrent
					Integer32,
				aActivePower1
					Integer32,
				aActivePower2
					Integer32,
				aActivePower3
					Integer32,
				aActivePower
					Integer32,
				aReactivePower1
					Integer32,
				bReactivePower1
					Integer32,
				cReactivePower1
					Integer32,
				aReactivePower
					Integer32,
				aPowerFactor1
					Integer32,
				aPowerFactor2
					Integer32,
				aPowerFactor3
					Integer32,
				aPowerFactor
					Integer32,
				aFrequency
					Integer32,
				aVoltageUnbalance
					Integer32,
				aCurrentUnbalance
					Integer32,
				aPositiveActiveEnergy
					Integer32,
				aNegativeActiveEnergy
					Integer32,
				aPositiveReactiveEnergy
					Integer32,
				aNegativeReactiveEnergy
					Integer32,
				bVoltage1
					Integer32,
				bVoltage2
					Integer32,
				bVoltage3
					Integer32,
				bAvgVoltage
					Integer32,
				bLineVoltage12
					Integer32,
				bLineVoltage23
					Integer32,
				bLineVoltage31
					Integer32,
				bAvgLineVoltage
					Integer32,
				bCurrent1
					Integer32,
				bCurrent2
					Integer32,
				bCurrent3
					Integer32,
				bAvgCurrent
					Integer32,
				bZeroLineCurrent
					Integer32,
				bActivePower1
					Integer32,
				bActivePower2
					Integer32,
				bActivePower3
					Integer32,
				bActivePower
					Integer32,
				bReactivePower1
					Integer32,
				bReactivePower1
					Integer32,
				bReactivePower1
					Integer32,
				bReactivePower
					Integer32,
				bPowerFactor1
					Integer32,
				bPowerFactor2
					Integer32,
				bPowerFactor3
					Integer32,
				bPowerFactor
					Integer32,
				bFrequency
					Integer32,
				bVoltageUnbalance
					Integer32,
				bCurrentUnbalance
					Integer32,
				bPositiveActiveEnergy
					Integer32,
				bNegativeActiveEnergy
					Integer32,
				bPositiveReactiveEnergy
					Integer32,
				bNegativeReactiveEnergy
					Integer32,
				aFundamentalV1OrV12
					Integer32,
				aFundamentalV2OrV23
					Integer32,
				aFundamentalV3OrV31
					Integer32,
				aVolAvgHarmonicsDistortion
					Integer32,
				aHarmonicsDistortion1
					Integer32,
				aHarmonicsDistortion2
					Integer32,
				aHarmonicsDistortion3
					Integer32,
				aCurAvgHarmonicsDistortion
					Integer32,
				bFundamentalV1OrV12
					Integer32,
				bFundamentalV2OrV23
					Integer32,
				bFundamentalV3OrV31
					Integer32,
				bVolAvgHarmonicsDistortion
					Integer32,
				bHarmonicsDistortion1
					Integer32,
				bHarmonicsDistortion2
					Integer32,
				bHarmonicsDistortion3
					Integer32,
				bCurAvgHarmonicsDistortion
					Integer32,
				aMianSwiftOf
					Integer32,
				aMianSwiftSd
					Integer32,
				aMianThunderPreventerSwift
					Integer32,
				bMianSwiftOf
					Integer32,
				bMianSwiftSd
					Integer32,
				bMianThunderPreventerSwift
					Integer32,
				ofSwiftState1
					Integer32,
				ofSwiftState2
					Integer32,
				ofSwiftState3
					Integer32,
				ofSwiftState4
					Integer32,
				ofSwiftState5
					Integer32,
				ofSwiftState6
					Integer32,
				ofSwiftState7
					Integer32,
				ofSwiftState8
					Integer32,
				ofSwiftState9
					Integer32,
				ofSwiftState10
					Integer32,
				ofSwiftState11
					Integer32,
				ofSwiftState12
					Integer32,
				ofSwiftState13
					Integer32,
				ofSwiftState14
					Integer32,
				ofSwiftState15
					Integer32,
				ofSwiftState16
					Integer32,
				ofSwiftState17
					Integer32,
				ofSwiftState18
					Integer32,
				ofSwiftState19
					Integer32,
				ofSwiftState20
					Integer32,
				ofSwiftState21
					Integer32,
				ofSwiftState22
					Integer32,
				ofSwiftState23
					Integer32,
				ofSwiftState24
					Integer32,
				ofSwiftState25
					Integer32,
				ofSwiftState26
					Integer32,
				ofSwiftState27
					Integer32,
				ofSwiftState28
					Integer32,
				ofSwiftState29
					Integer32,
				ofSwiftState30
					Integer32,
				ofSwiftState31
					Integer32,
				ofSwiftState32
					Integer32,
				ofSwiftState33
					Integer32,
				ofSwiftState34
					Integer32,
				ofSwiftState35
					Integer32,
				ofSwiftState36
					Integer32,
				ofSwiftState37
					Integer32,
				ofSwiftState38
					Integer32,
				ofSwiftState39
					Integer32,
				ofSwiftState40
					Integer32,
				ofSwiftState41
					Integer32,
				ofSwiftState42
					Integer32,
				ofSwiftState43
					Integer32,
				ofSwiftState44
					Integer32,
				ofSwiftState45
					Integer32,
				ofSwiftState46
					Integer32,
				ofSwiftState47
					Integer32,
				ofSwiftState48
					Integer32,
				ofSwiftState49
					Integer32,
				ofSwiftState50
					Integer32,
				ofSwiftState51
					Integer32,
				ofSwiftState52
					Integer32,
				ofSwiftState53
					Integer32,
				ofSwiftState54
					Integer32,
				ofSwiftState55
					Integer32,
				ofSwiftState56
					Integer32,
				ofSwiftState57
					Integer32,
				ofSwiftState58
					Integer32,
				ofSwiftState59
					Integer32,
				ofSwiftState60
					Integer32,
				ofSwiftState61
					Integer32,
				ofSwiftState62
					Integer32,
				ofSwiftState63
					Integer32,
				ofSwiftState64
					Integer32,
				ofSwiftState65
					Integer32,
				ofSwiftState66
					Integer32,
				ofSwiftState67
					Integer32,
				ofSwiftState68
					Integer32,
				ofSwiftState69
					Integer32,
				ofSwiftState70
					Integer32,
				ofSwiftState71
					Integer32,
				ofSwiftState72
					Integer32,
				ofSwiftState73
					Integer32,
				ofSwiftState74
					Integer32,
				ofSwiftState75
					Integer32,
				ofSwiftState76
					Integer32,
				ofSwiftState77
					Integer32,
				ofSwiftState78
					Integer32,
				ofSwiftState79
					Integer32,
				ofSwiftState80
					Integer32,
				ofSwiftState81
					Integer32,
				ofSwiftState82
					Integer32,
				ofSwiftState83
					Integer32,
				ofSwiftState84
					Integer32,
				ofSwiftState85
					Integer32,
				ofSwiftState86
					Integer32,
				ofSwiftState87
					Integer32,
				ofSwiftState88
					Integer32,
				ofSwiftState89
					Integer32,
				ofSwiftState90
					Integer32,
				ofSwiftState91
					Integer32,
				ofSwiftState92
					Integer32,
				ofSwiftState93
					Integer32,
				ofSwiftState94
					Integer32,
				ofSwiftState95
					Integer32,
				ofSwiftState96
					Integer32,
				ofSwiftState97
					Integer32,
				ofSwiftState98
					Integer32,
				ofSwiftState99
					Integer32,
				ofSwiftState100
					Integer32,
				ofSwiftState101
					Integer32,
				ofSwiftState102
					Integer32,
				ofSwiftState103
					Integer32,
				ofSwiftState104
					Integer32,
				ofSwiftState105
					Integer32,
				ofSwiftState106
					Integer32,
				ofSwiftState107
					Integer32,
				ofSwiftState108
					Integer32
				

			}
-- .1.3.6.1.4.1.39026.3.1.4.1.1.1.1
-- .1.3.6.1.4.1.39026.3.1.4.1.1.1.1
-- .1.3.6.1.4.1.39026.3.1.4.1.1.1.1
-- .1.3.6.1.4.1.39026.3.1.4.1.1.1.1
	pmYdmIndex OBJECT-TYPE
	SYNTAX Integer32
	MAX-ACCESS read-only
	STATUS current
	DESCRIPTION
	"Description: "
	::= { powerMeterAMYDMEntry 1 }

-- .1.3.6.1.4.1.39026.3.1.4.1.1.1.2
-- .1.3.6.1.4.1.39026.3.1.4.1.1.1.2
-- .1.3.6.1.4.1.39026.3.1.4.1.1.1.2
-- .1.3.6.1.4.1.39026.3.1.4.1.1.1.2
	pmYdmEquipOid OBJECT-TYPE
	SYNTAX Integer32
	MAX-ACCESS read-only
	STATUS current
	DESCRIPTION
	"Description: "
	::= { powerMeterAMYDMEntry 2 }

-- .1.3.6.1.4.1.39026.3.1.4.1.1.1.3
-- .1.3.6.1.4.1.39026.3.1.4.1.1.1.3
-- .1.3.6.1.4.1.39026.3.1.4.1.1.1.3
-- .1.3.6.1.4.1.39026.3.1.4.1.1.1.3
	pmYdmEquipName OBJECT-TYPE
	SYNTAX Integer32
	MAX-ACCESS read-only
	STATUS current
	DESCRIPTION
	"Description: "
	::= { powerMeterAMYDMEntry 3 }

-- .1.3.6.1.4.1.39026.3.1.4.1.1.1.4
-- .1.3.6.1.4.1.39026.3.1.4.1.1.1.4
-- .1.3.6.1.4.1.39026.3.1.4.1.1.1.4
-- .1.3.6.1.4.1.39026.3.1.4.1.1.1.4
	pmYdmCollectionTime OBJECT-TYPE
	SYNTAX Integer32
	MAX-ACCESS read-only
	STATUS current
	DESCRIPTION
	"Description: "
	::= { powerMeterAMYDMEntry 4 }

-- .1.3.6.1.4.1.39026.3.1.4.1.1.1.5
-- .1.3.6.1.4.1.39026.3.1.4.1.1.1.5
-- .1.3.6.1.4.1.39026.3.1.4.1.1.1.5
-- .1.3.6.1.4.1.39026.3.1.4.1.1.1.5
	aVoltage1 OBJECT-TYPE
	SYNTAX Integer32
	MAX-ACCESS read-only
	STATUS current
	DESCRIPTION
	"Description: "
	::= { powerMeterAMYDMEntry 5 }

-- .1.3.6.1.4.1.39026.3.1.4.1.1.1.6
-- .1.3.6.1.4.1.39026.3.1.4.1.1.1.6
-- .1.3.6.1.4.1.39026.3.1.4.1.1.1.6
-- .1.3.6.1.4.1.39026.3.1.4.1.1.1.6
	aVoltage2 OBJECT-TYPE
	SYNTAX Integer32
	MAX-ACCESS read-only
	STATUS current
	DESCRIPTION
	"Description: "
	::= { powerMeterAMYDMEntry 6 }

-- .1.3.6.1.4.1.39026.3.1.4.1.1.1.7
-- .1.3.6.1.4.1.39026.3.1.4.1.1.1.7
-- .1.3.6.1.4.1.39026.3.1.4.1.1.1.7
-- .1.3.6.1.4.1.39026.3.1.4.1.1.1.7
	aVoltage3 OBJECT-TYPE
	SYNTAX Integer32
	MAX-ACCESS read-only
	STATUS current
	DESCRIPTION
	"Description: "
	::= { powerMeterAMYDMEntry 7 }

-- .1.3.6.1.4.1.39026.3.1.4.1.1.1.8
-- .1.3.6.1.4.1.39026.3.1.4.1.1.1.8
-- .1.3.6.1.4.1.39026.3.1.4.1.1.1.8
-- .1.3.6.1.4.1.39026.3.1.4.1.1.1.8
	aAvgVoltage OBJECT-TYPE
	SYNTAX Integer32
	MAX-ACCESS read-only
	STATUS current
	DESCRIPTION
	"Description: "
	::= { powerMeterAMYDMEntry 8 }

-- .1.3.6.1.4.1.39026.3.1.4.1.1.1.9
-- .1.3.6.1.4.1.39026.3.1.4.1.1.1.9
-- .1.3.6.1.4.1.39026.3.1.4.1.1.1.9
-- .1.3.6.1.4.1.39026.3.1.4.1.1.1.9
	aLineVoltage12 OBJECT-TYPE
	SYNTAX Integer32
	MAX-ACCESS read-only
	STATUS current
	DESCRIPTION
	"Description: "
	::= { powerMeterAMYDMEntry 9 }

-- .1.3.6.1.4.1.39026.3.1.4.1.1.1.10
-- .1.3.6.1.4.1.39026.3.1.4.1.1.1.10
-- .1.3.6.1.4.1.39026.3.1.4.1.1.1.10
-- .1.3.6.1.4.1.39026.3.1.4.1.1.1.10
	aLineVoltage23 OBJECT-TYPE
	SYNTAX Integer32
	MAX-ACCESS read-only
	STATUS current
	DESCRIPTION
	"Description: "
	::= { powerMeterAMYDMEntry 10 }

-- .1.3.6.1.4.1.39026.3.1.4.1.1.1.11
-- .1.3.6.1.4.1.39026.3.1.4.1.1.1.11
-- .1.3.6.1.4.1.39026.3.1.4.1.1.1.11
-- .1.3.6.1.4.1.39026.3.1.4.1.1.1.11
	aLineVoltage31 OBJECT-TYPE
	SYNTAX Integer32
	MAX-ACCESS read-only
	STATUS current
	DESCRIPTION
	"Description: "
	::= { powerMeterAMYDMEntry 11 }

-- .1.3.6.1.4.1.39026.3.1.4.1.1.1.12
-- .1.3.6.1.4.1.39026.3.1.4.1.1.1.12
-- .1.3.6.1.4.1.39026.3.1.4.1.1.1.12
-- .1.3.6.1.4.1.39026.3.1.4.1.1.1.12
	aAvgLineVoltage OBJECT-TYPE
	SYNTAX Integer32
	MAX-ACCESS read-only
	STATUS current
	DESCRIPTION
	"Description: "
	::= { powerMeterAMYDMEntry 12 }

-- .1.3.6.1.4.1.39026.3.1.4.1.1.1.13
-- .1.3.6.1.4.1.39026.3.1.4.1.1.1.13
-- .1.3.6.1.4.1.39026.3.1.4.1.1.1.13
-- .1.3.6.1.4.1.39026.3.1.4.1.1.1.13
	aCurrent1 OBJECT-TYPE
	SYNTAX Integer32
	MAX-ACCESS read-only
	STATUS current
	DESCRIPTION
	"Description: "
	::= { powerMeterAMYDMEntry 13 }

-- .1.3.6.1.4.1.39026.3.1.4.1.1.1.14
-- .1.3.6.1.4.1.39026.3.1.4.1.1.1.14
-- .1.3.6.1.4.1.39026.3.1.4.1.1.1.14
-- .1.3.6.1.4.1.39026.3.1.4.1.1.1.14
	aCurrent2 OBJECT-TYPE
	SYNTAX Integer32
	MAX-ACCESS read-only
	STATUS current
	DESCRIPTION
	"Description: "
	::= { powerMeterAMYDMEntry 14 }

-- .1.3.6.1.4.1.39026.3.1.4.1.1.1.15
-- .1.3.6.1.4.1.39026.3.1.4.1.1.1.15
-- .1.3.6.1.4.1.39026.3.1.4.1.1.1.15
-- .1.3.6.1.4.1.39026.3.1.4.1.1.1.15
	aCurrent3 OBJECT-TYPE
	SYNTAX Integer32
	MAX-ACCESS read-only
	STATUS current
	DESCRIPTION
	"Description: "
	::= { powerMeterAMYDMEntry 15 }

-- .1.3.6.1.4.1.39026.3.1.4.1.1.1.16
-- .1.3.6.1.4.1.39026.3.1.4.1.1.1.16
-- .1.3.6.1.4.1.39026.3.1.4.1.1.1.16
-- .1.3.6.1.4.1.39026.3.1.4.1.1.1.16
	aAvgCurrent OBJECT-TYPE
	SYNTAX Integer32
	MAX-ACCESS read-only
	STATUS current
	DESCRIPTION
	"Description: "
	::= { powerMeterAMYDMEntry 16 }

-- .1.3.6.1.4.1.39026.3.1.4.1.1.1.17
-- .1.3.6.1.4.1.39026.3.1.4.1.1.1.17
-- .1.3.6.1.4.1.39026.3.1.4.1.1.1.17
-- .1.3.6.1.4.1.39026.3.1.4.1.1.1.17
	aZeroLineCurrent OBJECT-TYPE
	SYNTAX Integer32
	MAX-ACCESS read-only
	STATUS current
	DESCRIPTION
	"Description: "
	::= { powerMeterAMYDMEntry 17 }

-- .1.3.6.1.4.1.39026.3.1.4.1.1.1.18
-- .1.3.6.1.4.1.39026.3.1.4.1.1.1.18
-- .1.3.6.1.4.1.39026.3.1.4.1.1.1.18
-- .1.3.6.1.4.1.39026.3.1.4.1.1.1.18
	aActivePower1 OBJECT-TYPE
	SYNTAX Integer32
	MAX-ACCESS read-only
	STATUS current
	DESCRIPTION
	"Description: "
	::= { powerMeterAMYDMEntry 18 }

-- .1.3.6.1.4.1.39026.3.1.4.1.1.1.19
-- .1.3.6.1.4.1.39026.3.1.4.1.1.1.19
-- .1.3.6.1.4.1.39026.3.1.4.1.1.1.19
-- .1.3.6.1.4.1.39026.3.1.4.1.1.1.19
	aActivePower2 OBJECT-TYPE
	SYNTAX Integer32
	MAX-ACCESS read-only
	STATUS current
	DESCRIPTION
	"Description: "
	::= { powerMeterAMYDMEntry 19 }

-- .1.3.6.1.4.1.39026.3.1.4.1.1.1.20
-- .1.3.6.1.4.1.39026.3.1.4.1.1.1.20
-- .1.3.6.1.4.1.39026.3.1.4.1.1.1.20
-- .1.3.6.1.4.1.39026.3.1.4.1.1.1.20
	aActivePower3 OBJECT-TYPE
	SYNTAX Integer32
	MAX-ACCESS read-only
	STATUS current
	DESCRIPTION
	"Description: "
	::= { powerMeterAMYDMEntry 20 }

-- .1.3.6.1.4.1.39026.3.1.4.1.1.1.21
-- .1.3.6.1.4.1.39026.3.1.4.1.1.1.21
-- .1.3.6.1.4.1.39026.3.1.4.1.1.1.21
-- .1.3.6.1.4.1.39026.3.1.4.1.1.1.21
	aActivePower OBJECT-TYPE
	SYNTAX Integer32
	MAX-ACCESS read-only
	STATUS current
	DESCRIPTION
	"Description: "
	::= { powerMeterAMYDMEntry 21 }

-- .1.3.6.1.4.1.39026.3.1.4.1.1.1.22
-- .1.3.6.1.4.1.39026.3.1.4.1.1.1.22
-- .1.3.6.1.4.1.39026.3.1.4.1.1.1.22
-- .1.3.6.1.4.1.39026.3.1.4.1.1.1.22
	aReactivePower1 OBJECT-TYPE
	SYNTAX Integer32
	MAX-ACCESS read-only
	STATUS current
	DESCRIPTION
	"Description: "
	::= { powerMeterAMYDMEntry 22 }

-- .1.3.6.1.4.1.39026.3.1.4.1.1.1.23
-- .1.3.6.1.4.1.39026.3.1.4.1.1.1.23
-- .1.3.6.1.4.1.39026.3.1.4.1.1.1.23
-- .1.3.6.1.4.1.39026.3.1.4.1.1.1.23
	bReactivePower1 OBJECT-TYPE
	SYNTAX Integer32
	MAX-ACCESS read-only
	STATUS current
	DESCRIPTION
	"Description: "
	::= { powerMeterAMYDMEntry 23 }

-- .1.3.6.1.4.1.39026.3.1.4.1.1.1.24
-- .1.3.6.1.4.1.39026.3.1.4.1.1.1.24
-- .1.3.6.1.4.1.39026.3.1.4.1.1.1.24
-- .1.3.6.1.4.1.39026.3.1.4.1.1.1.24
	cReactivePower1 OBJECT-TYPE
	SYNTAX Integer32
	MAX-ACCESS read-only
	STATUS current
	DESCRIPTION
	"Description: "
	::= { powerMeterAMYDMEntry 24 }

-- .1.3.6.1.4.1.39026.3.1.4.1.1.1.25
-- .1.3.6.1.4.1.39026.3.1.4.1.1.1.25
-- .1.3.6.1.4.1.39026.3.1.4.1.1.1.25
-- .1.3.6.1.4.1.39026.3.1.4.1.1.1.25
	aReactivePower OBJECT-TYPE
	SYNTAX Integer32
	MAX-ACCESS read-only
	STATUS current
	DESCRIPTION
	"Description: "
	::= { powerMeterAMYDMEntry 25 }

-- .1.3.6.1.4.1.39026.3.1.4.1.1.1.26
-- .1.3.6.1.4.1.39026.3.1.4.1.1.1.26
-- .1.3.6.1.4.1.39026.3.1.4.1.1.1.26
-- .1.3.6.1.4.1.39026.3.1.4.1.1.1.26
	aPowerFactor1 OBJECT-TYPE
	SYNTAX Integer32
	MAX-ACCESS read-only
	STATUS current
	DESCRIPTION
	"Description: "
	::= { powerMeterAMYDMEntry 26 }

-- .1.3.6.1.4.1.39026.3.1.4.1.1.1.27
-- .1.3.6.1.4.1.39026.3.1.4.1.1.1.27
-- .1.3.6.1.4.1.39026.3.1.4.1.1.1.27
-- .1.3.6.1.4.1.39026.3.1.4.1.1.1.27
	aPowerFactor2 OBJECT-TYPE
	SYNTAX Integer32
	MAX-ACCESS read-only
	STATUS current
	DESCRIPTION
	"Description: "
	::= { powerMeterAMYDMEntry 27 }

-- .1.3.6.1.4.1.39026.3.1.4.1.1.1.28
-- .1.3.6.1.4.1.39026.3.1.4.1.1.1.28
-- .1.3.6.1.4.1.39026.3.1.4.1.1.1.28
-- .1.3.6.1.4.1.39026.3.1.4.1.1.1.28
	aPowerFactor3 OBJECT-TYPE
	SYNTAX Integer32
	MAX-ACCESS read-only
	STATUS current
	DESCRIPTION
	"Description: "
	::= { powerMeterAMYDMEntry 28 }

-- .1.3.6.1.4.1.39026.3.1.4.1.1.1.29
-- .1.3.6.1.4.1.39026.3.1.4.1.1.1.29
-- .1.3.6.1.4.1.39026.3.1.4.1.1.1.29
-- .1.3.6.1.4.1.39026.3.1.4.1.1.1.29
	aPowerFactor OBJECT-TYPE
	SYNTAX Integer32
	MAX-ACCESS read-only
	STATUS current
	DESCRIPTION
	"Description: "
	::= { powerMeterAMYDMEntry 29 }

-- .1.3.6.1.4.1.39026.3.1.4.1.1.1.30
-- .1.3.6.1.4.1.39026.3.1.4.1.1.1.30
-- .1.3.6.1.4.1.39026.3.1.4.1.1.1.30
-- .1.3.6.1.4.1.39026.3.1.4.1.1.1.30
	aFrequency OBJECT-TYPE
	SYNTAX Integer32
	MAX-ACCESS read-only
	STATUS current
	DESCRIPTION
	"Description: "
	::= { powerMeterAMYDMEntry 30 }

-- .1.3.6.1.4.1.39026.3.1.4.1.1.1.31
-- .1.3.6.1.4.1.39026.3.1.4.1.1.1.31
-- .1.3.6.1.4.1.39026.3.1.4.1.1.1.31
-- .1.3.6.1.4.1.39026.3.1.4.1.1.1.31
	aVoltageUnbalance OBJECT-TYPE
	SYNTAX Integer32
	MAX-ACCESS read-only
	STATUS current
	DESCRIPTION
	"Description: "
	::= { powerMeterAMYDMEntry 31 }

-- .1.3.6.1.4.1.39026.3.1.4.1.1.1.32
-- .1.3.6.1.4.1.39026.3.1.4.1.1.1.32
-- .1.3.6.1.4.1.39026.3.1.4.1.1.1.32
-- .1.3.6.1.4.1.39026.3.1.4.1.1.1.32
	aCurrentUnbalance OBJECT-TYPE
	SYNTAX Integer32
	MAX-ACCESS read-only
	STATUS current
	DESCRIPTION
	"Description: "
	::= { powerMeterAMYDMEntry 32 }

-- .1.3.6.1.4.1.39026.3.1.4.1.1.1.33
-- .1.3.6.1.4.1.39026.3.1.4.1.1.1.33
-- .1.3.6.1.4.1.39026.3.1.4.1.1.1.33
-- .1.3.6.1.4.1.39026.3.1.4.1.1.1.33
	aPositiveActiveEnergy OBJECT-TYPE
	SYNTAX Integer32
	MAX-ACCESS read-only
	STATUS current
	DESCRIPTION
	"Description: "
	::= { powerMeterAMYDMEntry 33 }

-- .1.3.6.1.4.1.39026.3.1.4.1.1.1.34
-- .1.3.6.1.4.1.39026.3.1.4.1.1.1.34
-- .1.3.6.1.4.1.39026.3.1.4.1.1.1.34
-- .1.3.6.1.4.1.39026.3.1.4.1.1.1.34
	aNegativeActiveEnergy OBJECT-TYPE
	SYNTAX Integer32
	MAX-ACCESS read-only
	STATUS current
	DESCRIPTION
	"Description: "
	::= { powerMeterAMYDMEntry 34 }

-- .1.3.6.1.4.1.39026.3.1.4.1.1.1.35
-- .1.3.6.1.4.1.39026.3.1.4.1.1.1.35
-- .1.3.6.1.4.1.39026.3.1.4.1.1.1.35
-- .1.3.6.1.4.1.39026.3.1.4.1.1.1.35
	aPositiveReactiveEnergy OBJECT-TYPE
	SYNTAX Integer32
	MAX-ACCESS read-only
	STATUS current
	DESCRIPTION
	"Description: "
	::= { powerMeterAMYDMEntry 35 }

-- .1.3.6.1.4.1.39026.3.1.4.1.1.1.36
-- .1.3.6.1.4.1.39026.3.1.4.1.1.1.36
-- .1.3.6.1.4.1.39026.3.1.4.1.1.1.36
-- .1.3.6.1.4.1.39026.3.1.4.1.1.1.36
	aNegativeReactiveEnergy OBJECT-TYPE
	SYNTAX Integer32
	MAX-ACCESS read-only
	STATUS current
	DESCRIPTION
	"Description: "
	::= { powerMeterAMYDMEntry 36 }

-- .1.3.6.1.4.1.39026.3.1.4.1.1.1.37
-- .1.3.6.1.4.1.39026.3.1.4.1.1.1.37
-- .1.3.6.1.4.1.39026.3.1.4.1.1.1.37
-- .1.3.6.1.4.1.39026.3.1.4.1.1.1.37
	bVoltage1 OBJECT-TYPE
	SYNTAX Integer32
	MAX-ACCESS read-only
	STATUS current
	DESCRIPTION
	"Description: "
	::= { powerMeterAMYDMEntry 37 }

-- .1.3.6.1.4.1.39026.3.1.4.1.1.1.38
-- .1.3.6.1.4.1.39026.3.1.4.1.1.1.38
-- .1.3.6.1.4.1.39026.3.1.4.1.1.1.38
-- .1.3.6.1.4.1.39026.3.1.4.1.1.1.38
	bVoltage2 OBJECT-TYPE
	SYNTAX Integer32
	MAX-ACCESS read-only
	STATUS current
	DESCRIPTION
	"Description: "
	::= { powerMeterAMYDMEntry 38 }

-- .1.3.6.1.4.1.39026.3.1.4.1.1.1.39
-- .1.3.6.1.4.1.39026.3.1.4.1.1.1.39
-- .1.3.6.1.4.1.39026.3.1.4.1.1.1.39
-- .1.3.6.1.4.1.39026.3.1.4.1.1.1.39
	bVoltage3 OBJECT-TYPE
	SYNTAX Integer32
	MAX-ACCESS read-only
	STATUS current
	DESCRIPTION
	"Description: "
	::= { powerMeterAMYDMEntry 39 }

-- .1.3.6.1.4.1.39026.3.1.4.1.1.1.40
-- .1.3.6.1.4.1.39026.3.1.4.1.1.1.40
-- .1.3.6.1.4.1.39026.3.1.4.1.1.1.40
-- .1.3.6.1.4.1.39026.3.1.4.1.1.1.40
	bAvgVoltage OBJECT-TYPE
	SYNTAX Integer32
	MAX-ACCESS read-only
	STATUS current
	DESCRIPTION
	"Description: "
	::= { powerMeterAMYDMEntry 40 }

-- .1.3.6.1.4.1.39026.3.1.4.1.1.1.41
-- .1.3.6.1.4.1.39026.3.1.4.1.1.1.41
-- .1.3.6.1.4.1.39026.3.1.4.1.1.1.41
-- .1.3.6.1.4.1.39026.3.1.4.1.1.1.41
	bLineVoltage12 OBJECT-TYPE
	SYNTAX Integer32
	MAX-ACCESS read-only
	STATUS current
	DESCRIPTION
	"Description: "
	::= { powerMeterAMYDMEntry 41 }

-- .1.3.6.1.4.1.39026.3.1.4.1.1.1.42
-- .1.3.6.1.4.1.39026.3.1.4.1.1.1.42
-- .1.3.6.1.4.1.39026.3.1.4.1.1.1.42
-- .1.3.6.1.4.1.39026.3.1.4.1.1.1.42
	bLineVoltage23 OBJECT-TYPE
	SYNTAX Integer32
	MAX-ACCESS read-only
	STATUS current
	DESCRIPTION
	"Description: "
	::= { powerMeterAMYDMEntry 42 }

-- .1.3.6.1.4.1.39026.3.1.4.1.1.1.43
-- .1.3.6.1.4.1.39026.3.1.4.1.1.1.43
-- .1.3.6.1.4.1.39026.3.1.4.1.1.1.43
-- .1.3.6.1.4.1.39026.3.1.4.1.1.1.43
	bLineVoltage31 OBJECT-TYPE
	SYNTAX Integer32
	MAX-ACCESS read-only
	STATUS current
	DESCRIPTION
	"Description: "
	::= { powerMeterAMYDMEntry 43 }

-- .1.3.6.1.4.1.39026.3.1.4.1.1.1.44
-- .1.3.6.1.4.1.39026.3.1.4.1.1.1.44
-- .1.3.6.1.4.1.39026.3.1.4.1.1.1.44
-- .1.3.6.1.4.1.39026.3.1.4.1.1.1.44
	bAvgLineVoltage OBJECT-TYPE
	SYNTAX Integer32
	MAX-ACCESS read-only
	STATUS current
	DESCRIPTION
	"Description: "
	::= { powerMeterAMYDMEntry 44 }

-- .1.3.6.1.4.1.39026.3.1.4.1.1.1.45
-- .1.3.6.1.4.1.39026.3.1.4.1.1.1.45
-- .1.3.6.1.4.1.39026.3.1.4.1.1.1.45
-- .1.3.6.1.4.1.39026.3.1.4.1.1.1.45
	bCurrent1 OBJECT-TYPE
	SYNTAX Integer32
	MAX-ACCESS read-only
	STATUS current
	DESCRIPTION
	"Description: "
	::= { powerMeterAMYDMEntry 45 }

-- .1.3.6.1.4.1.39026.3.1.4.1.1.1.46
-- .1.3.6.1.4.1.39026.3.1.4.1.1.1.46
-- .1.3.6.1.4.1.39026.3.1.4.1.1.1.46
-- .1.3.6.1.4.1.39026.3.1.4.1.1.1.46
	bCurrent2 OBJECT-TYPE
	SYNTAX Integer32
	MAX-ACCESS read-only
	STATUS current
	DESCRIPTION
	"Description: "
	::= { powerMeterAMYDMEntry 46 }

-- .1.3.6.1.4.1.39026.3.1.4.1.1.1.47
-- .1.3.6.1.4.1.39026.3.1.4.1.1.1.47
-- .1.3.6.1.4.1.39026.3.1.4.1.1.1.47
-- .1.3.6.1.4.1.39026.3.1.4.1.1.1.47
	bCurrent3 OBJECT-TYPE
	SYNTAX Integer32
	MAX-ACCESS read-only
	STATUS current
	DESCRIPTION
	"Description: "
	::= { powerMeterAMYDMEntry 47 }

-- .1.3.6.1.4.1.39026.3.1.4.1.1.1.48
-- .1.3.6.1.4.1.39026.3.1.4.1.1.1.48
-- .1.3.6.1.4.1.39026.3.1.4.1.1.1.48
-- .1.3.6.1.4.1.39026.3.1.4.1.1.1.48
	bAvgCurrent OBJECT-TYPE
	SYNTAX Integer32
	MAX-ACCESS read-only
	STATUS current
	DESCRIPTION
	"Description: "
	::= { powerMeterAMYDMEntry 48 }

-- .1.3.6.1.4.1.39026.3.1.4.1.1.1.49
-- .1.3.6.1.4.1.39026.3.1.4.1.1.1.49
-- .1.3.6.1.4.1.39026.3.1.4.1.1.1.49
-- .1.3.6.1.4.1.39026.3.1.4.1.1.1.49
	bZeroLineCurrent OBJECT-TYPE
	SYNTAX Integer32
	MAX-ACCESS read-only
	STATUS current
	DESCRIPTION
	"Description: "
	::= { powerMeterAMYDMEntry 49 }

-- .1.3.6.1.4.1.39026.3.1.4.1.1.1.50
-- .1.3.6.1.4.1.39026.3.1.4.1.1.1.50
-- .1.3.6.1.4.1.39026.3.1.4.1.1.1.50
-- .1.3.6.1.4.1.39026.3.1.4.1.1.1.50
	bActivePower1 OBJECT-TYPE
	SYNTAX Integer32
	MAX-ACCESS read-only
	STATUS current
	DESCRIPTION
	"Description: "
	::= { powerMeterAMYDMEntry 50 }

-- .1.3.6.1.4.1.39026.3.1.4.1.1.1.51
-- .1.3.6.1.4.1.39026.3.1.4.1.1.1.51
-- .1.3.6.1.4.1.39026.3.1.4.1.1.1.51
-- .1.3.6.1.4.1.39026.3.1.4.1.1.1.51
	bActivePower2 OBJECT-TYPE
	SYNTAX Integer32
	MAX-ACCESS read-only
	STATUS current
	DESCRIPTION
	"Description: "
	::= { powerMeterAMYDMEntry 51 }

-- .1.3.6.1.4.1.39026.3.1.4.1.1.1.52
-- .1.3.6.1.4.1.39026.3.1.4.1.1.1.52
-- .1.3.6.1.4.1.39026.3.1.4.1.1.1.52
-- .1.3.6.1.4.1.39026.3.1.4.1.1.1.52
	bActivePower3 OBJECT-TYPE
	SYNTAX Integer32
	MAX-ACCESS read-only
	STATUS current
	DESCRIPTION
	"Description: "
	::= { powerMeterAMYDMEntry 52 }

-- .1.3.6.1.4.1.39026.3.1.4.1.1.1.53
-- .1.3.6.1.4.1.39026.3.1.4.1.1.1.53
-- .1.3.6.1.4.1.39026.3.1.4.1.1.1.53
-- .1.3.6.1.4.1.39026.3.1.4.1.1.1.53
	bActivePower OBJECT-TYPE
	SYNTAX Integer32
	MAX-ACCESS read-only
	STATUS current
	DESCRIPTION
	"Description: "
	::= { powerMeterAMYDMEntry 53 }

-- .1.3.6.1.4.1.39026.3.1.4.1.1.1.54
-- .1.3.6.1.4.1.39026.3.1.4.1.1.1.54
-- .1.3.6.1.4.1.39026.3.1.4.1.1.1.54
-- .1.3.6.1.4.1.39026.3.1.4.1.1.1.54
	bReactivePower1 OBJECT-TYPE
	SYNTAX Integer32
	MAX-ACCESS read-only
	STATUS current
	DESCRIPTION
	"Description: "
	::= { powerMeterAMYDMEntry 54 }

-- .1.3.6.1.4.1.39026.3.1.4.1.1.1.55
-- .1.3.6.1.4.1.39026.3.1.4.1.1.1.55
-- .1.3.6.1.4.1.39026.3.1.4.1.1.1.55
-- .1.3.6.1.4.1.39026.3.1.4.1.1.1.55
	bReactivePower1 OBJECT-TYPE
	SYNTAX Integer32
	MAX-ACCESS read-only
	STATUS current
	DESCRIPTION
	"Description: "
	::= { powerMeterAMYDMEntry 55 }

-- .1.3.6.1.4.1.39026.3.1.4.1.1.1.56
-- .1.3.6.1.4.1.39026.3.1.4.1.1.1.56
-- .1.3.6.1.4.1.39026.3.1.4.1.1.1.56
-- .1.3.6.1.4.1.39026.3.1.4.1.1.1.56
	bReactivePower1 OBJECT-TYPE
	SYNTAX Integer32
	MAX-ACCESS read-only
	STATUS current
	DESCRIPTION
	"Description: "
	::= { powerMeterAMYDMEntry 56 }

-- .1.3.6.1.4.1.39026.3.1.4.1.1.1.57
-- .1.3.6.1.4.1.39026.3.1.4.1.1.1.57
-- .1.3.6.1.4.1.39026.3.1.4.1.1.1.57
-- .1.3.6.1.4.1.39026.3.1.4.1.1.1.57
	bReactivePower OBJECT-TYPE
	SYNTAX Integer32
	MAX-ACCESS read-only
	STATUS current
	DESCRIPTION
	"Description: "
	::= { powerMeterAMYDMEntry 57 }

-- .1.3.6.1.4.1.39026.3.1.4.1.1.1.58
-- .1.3.6.1.4.1.39026.3.1.4.1.1.1.58
-- .1.3.6.1.4.1.39026.3.1.4.1.1.1.58
-- .1.3.6.1.4.1.39026.3.1.4.1.1.1.58
	bPowerFactor1 OBJECT-TYPE
	SYNTAX Integer32
	MAX-ACCESS read-only
	STATUS current
	DESCRIPTION
	"Description: "
	::= { powerMeterAMYDMEntry 58 }

-- .1.3.6.1.4.1.39026.3.1.4.1.1.1.59
-- .1.3.6.1.4.1.39026.3.1.4.1.1.1.59
-- .1.3.6.1.4.1.39026.3.1.4.1.1.1.59
-- .1.3.6.1.4.1.39026.3.1.4.1.1.1.59
	bPowerFactor2 OBJECT-TYPE
	SYNTAX Integer32
	MAX-ACCESS read-only
	STATUS current
	DESCRIPTION
	"Description: "
	::= { powerMeterAMYDMEntry 59 }

-- .1.3.6.1.4.1.39026.3.1.4.1.1.1.60
-- .1.3.6.1.4.1.39026.3.1.4.1.1.1.60
-- .1.3.6.1.4.1.39026.3.1.4.1.1.1.60
-- .1.3.6.1.4.1.39026.3.1.4.1.1.1.60
	bPowerFactor3 OBJECT-TYPE
	SYNTAX Integer32
	MAX-ACCESS read-only
	STATUS current
	DESCRIPTION
	"Description: "
	::= { powerMeterAMYDMEntry 60 }

-- .1.3.6.1.4.1.39026.3.1.4.1.1.1.61
-- .1.3.6.1.4.1.39026.3.1.4.1.1.1.61
-- .1.3.6.1.4.1.39026.3.1.4.1.1.1.61
-- .1.3.6.1.4.1.39026.3.1.4.1.1.1.61
	bPowerFactor OBJECT-TYPE
	SYNTAX Integer32
	MAX-ACCESS read-only
	STATUS current
	DESCRIPTION
	"Description: "
	::= { powerMeterAMYDMEntry 61 }

-- .1.3.6.1.4.1.39026.3.1.4.1.1.1.62
-- .1.3.6.1.4.1.39026.3.1.4.1.1.1.62
-- .1.3.6.1.4.1.39026.3.1.4.1.1.1.62
-- .1.3.6.1.4.1.39026.3.1.4.1.1.1.62
	bFrequency OBJECT-TYPE
	SYNTAX Integer32
	MAX-ACCESS read-only
	STATUS current
	DESCRIPTION
	"Description: "
	::= { powerMeterAMYDMEntry 62 }

-- .1.3.6.1.4.1.39026.3.1.4.1.1.1.63
-- .1.3.6.1.4.1.39026.3.1.4.1.1.1.63
-- .1.3.6.1.4.1.39026.3.1.4.1.1.1.63
-- .1.3.6.1.4.1.39026.3.1.4.1.1.1.63
	bVoltageUnbalance OBJECT-TYPE
	SYNTAX Integer32
	MAX-ACCESS read-only
	STATUS current
	DESCRIPTION
	"Description: "
	::= { powerMeterAMYDMEntry 63 }

-- .1.3.6.1.4.1.39026.3.1.4.1.1.1.64
-- .1.3.6.1.4.1.39026.3.1.4.1.1.1.64
-- .1.3.6.1.4.1.39026.3.1.4.1.1.1.64
-- .1.3.6.1.4.1.39026.3.1.4.1.1.1.64
	bCurrentUnbalance OBJECT-TYPE
	SYNTAX Integer32
	MAX-ACCESS read-only
	STATUS current
	DESCRIPTION
	"Description: "
	::= { powerMeterAMYDMEntry 64 }

-- .1.3.6.1.4.1.39026.3.1.4.1.1.1.65
-- .1.3.6.1.4.1.39026.3.1.4.1.1.1.65
-- .1.3.6.1.4.1.39026.3.1.4.1.1.1.65
-- .1.3.6.1.4.1.39026.3.1.4.1.1.1.65
	bPositiveActiveEnergy OBJECT-TYPE
	SYNTAX Integer32
	MAX-ACCESS read-only
	STATUS current
	DESCRIPTION
	"Description: "
	::= { powerMeterAMYDMEntry 65 }

-- .1.3.6.1.4.1.39026.3.1.4.1.1.1.66
-- .1.3.6.1.4.1.39026.3.1.4.1.1.1.66
-- .1.3.6.1.4.1.39026.3.1.4.1.1.1.66
-- .1.3.6.1.4.1.39026.3.1.4.1.1.1.66
	bNegativeActiveEnergy OBJECT-TYPE
	SYNTAX Integer32
	MAX-ACCESS read-only
	STATUS current
	DESCRIPTION
	"Description: "
	::= { powerMeterAMYDMEntry 66 }

-- .1.3.6.1.4.1.39026.3.1.4.1.1.1.67
-- .1.3.6.1.4.1.39026.3.1.4.1.1.1.67
-- .1.3.6.1.4.1.39026.3.1.4.1.1.1.67
-- .1.3.6.1.4.1.39026.3.1.4.1.1.1.67
	bPositiveReactiveEnergy OBJECT-TYPE
	SYNTAX Integer32
	MAX-ACCESS read-only
	STATUS current
	DESCRIPTION
	"Description: "
	::= { powerMeterAMYDMEntry 67 }

-- .1.3.6.1.4.1.39026.3.1.4.1.1.1.68
-- .1.3.6.1.4.1.39026.3.1.4.1.1.1.68
-- .1.3.6.1.4.1.39026.3.1.4.1.1.1.68
-- .1.3.6.1.4.1.39026.3.1.4.1.1.1.68
	bNegativeReactiveEnergy OBJECT-TYPE
	SYNTAX Integer32
	MAX-ACCESS read-only
	STATUS current
	DESCRIPTION
	"Description: "
	::= { powerMeterAMYDMEntry 68 }

-- .1.3.6.1.4.1.39026.3.1.4.1.1.1.69
-- .1.3.6.1.4.1.39026.3.1.4.1.1.1.69
-- .1.3.6.1.4.1.39026.3.1.4.1.1.1.69
-- .1.3.6.1.4.1.39026.3.1.4.1.1.1.69
	aFundamentalV1OrV12 OBJECT-TYPE
	SYNTAX Integer32
	MAX-ACCESS read-only
	STATUS current
	DESCRIPTION
	"Description: "
	::= { powerMeterAMYDMEntry 69 }

-- .1.3.6.1.4.1.39026.3.1.4.1.1.1.70
-- .1.3.6.1.4.1.39026.3.1.4.1.1.1.70
-- .1.3.6.1.4.1.39026.3.1.4.1.1.1.70
-- .1.3.6.1.4.1.39026.3.1.4.1.1.1.70
	aFundamentalV2OrV23 OBJECT-TYPE
	SYNTAX Integer32
	MAX-ACCESS read-only
	STATUS current
	DESCRIPTION
	"Description: "
	::= { powerMeterAMYDMEntry 70 }

-- .1.3.6.1.4.1.39026.3.1.4.1.1.1.71
-- .1.3.6.1.4.1.39026.3.1.4.1.1.1.71
-- .1.3.6.1.4.1.39026.3.1.4.1.1.1.71
-- .1.3.6.1.4.1.39026.3.1.4.1.1.1.71
	aFundamentalV3OrV31 OBJECT-TYPE
	SYNTAX Integer32
	MAX-ACCESS read-only
	STATUS current
	DESCRIPTION
	"Description: "
	::= { powerMeterAMYDMEntry 71 }

-- .1.3.6.1.4.1.39026.3.1.4.1.1.1.72
-- .1.3.6.1.4.1.39026.3.1.4.1.1.1.72
-- .1.3.6.1.4.1.39026.3.1.4.1.1.1.72
-- .1.3.6.1.4.1.39026.3.1.4.1.1.1.72
	aVolAvgHarmonicsDistortion OBJECT-TYPE
	SYNTAX Integer32
	MAX-ACCESS read-only
	STATUS current
	DESCRIPTION
	"Description: "
	::= { powerMeterAMYDMEntry 72 }

-- .1.3.6.1.4.1.39026.3.1.4.1.1.1.73
-- .1.3.6.1.4.1.39026.3.1.4.1.1.1.73
-- .1.3.6.1.4.1.39026.3.1.4.1.1.1.73
-- .1.3.6.1.4.1.39026.3.1.4.1.1.1.73
	aHarmonicsDistortion1 OBJECT-TYPE
	SYNTAX Integer32
	MAX-ACCESS read-only
	STATUS current
	DESCRIPTION
	"Description: "
	::= { powerMeterAMYDMEntry 73 }

-- .1.3.6.1.4.1.39026.3.1.4.1.1.1.74
-- .1.3.6.1.4.1.39026.3.1.4.1.1.1.74
-- .1.3.6.1.4.1.39026.3.1.4.1.1.1.74
-- .1.3.6.1.4.1.39026.3.1.4.1.1.1.74
	aHarmonicsDistortion2 OBJECT-TYPE
	SYNTAX Integer32
	MAX-ACCESS read-only
	STATUS current
	DESCRIPTION
	"Description: "
	::= { powerMeterAMYDMEntry 74 }

-- .1.3.6.1.4.1.39026.3.1.4.1.1.1.75
-- .1.3.6.1.4.1.39026.3.1.4.1.1.1.75
-- .1.3.6.1.4.1.39026.3.1.4.1.1.1.75
-- .1.3.6.1.4.1.39026.3.1.4.1.1.1.75
	aHarmonicsDistortion3 OBJECT-TYPE
	SYNTAX Integer32
	MAX-ACCESS read-only
	STATUS current
	DESCRIPTION
	"Description: "
	::= { powerMeterAMYDMEntry 75 }

-- .1.3.6.1.4.1.39026.3.1.4.1.1.1.76
-- .1.3.6.1.4.1.39026.3.1.4.1.1.1.76
-- .1.3.6.1.4.1.39026.3.1.4.1.1.1.76
-- .1.3.6.1.4.1.39026.3.1.4.1.1.1.76
	aCurAvgHarmonicsDistortion OBJECT-TYPE
	SYNTAX Integer32
	MAX-ACCESS read-only
	STATUS current
	DESCRIPTION
	"Description: "
	::= { powerMeterAMYDMEntry 76 }

-- .1.3.6.1.4.1.39026.3.1.4.1.1.1.77
-- .1.3.6.1.4.1.39026.3.1.4.1.1.1.77
-- .1.3.6.1.4.1.39026.3.1.4.1.1.1.77
-- .1.3.6.1.4.1.39026.3.1.4.1.1.1.77
	bFundamentalV1OrV12 OBJECT-TYPE
	SYNTAX Integer32
	MAX-ACCESS read-only
	STATUS current
	DESCRIPTION
	"Description: "
	::= { powerMeterAMYDMEntry 77 }

-- .1.3.6.1.4.1.39026.3.1.4.1.1.1.78
-- .1.3.6.1.4.1.39026.3.1.4.1.1.1.78
-- .1.3.6.1.4.1.39026.3.1.4.1.1.1.78
-- .1.3.6.1.4.1.39026.3.1.4.1.1.1.78
	bFundamentalV2OrV23 OBJECT-TYPE
	SYNTAX Integer32
	MAX-ACCESS read-only
	STATUS current
	DESCRIPTION
	"Description: "
	::= { powerMeterAMYDMEntry 78 }

-- .1.3.6.1.4.1.39026.3.1.4.1.1.1.79
-- .1.3.6.1.4.1.39026.3.1.4.1.1.1.79
-- .1.3.6.1.4.1.39026.3.1.4.1.1.1.79
-- .1.3.6.1.4.1.39026.3.1.4.1.1.1.79
	bFundamentalV3OrV31 OBJECT-TYPE
	SYNTAX Integer32
	MAX-ACCESS read-only
	STATUS current
	DESCRIPTION
	"Description: "
	::= { powerMeterAMYDMEntry 79 }

-- .1.3.6.1.4.1.39026.3.1.4.1.1.1.80
-- .1.3.6.1.4.1.39026.3.1.4.1.1.1.80
-- .1.3.6.1.4.1.39026.3.1.4.1.1.1.80
-- .1.3.6.1.4.1.39026.3.1.4.1.1.1.80
	bVolAvgHarmonicsDistortion OBJECT-TYPE
	SYNTAX Integer32
	MAX-ACCESS read-only
	STATUS current
	DESCRIPTION
	"Description: "
	::= { powerMeterAMYDMEntry 80 }

-- .1.3.6.1.4.1.39026.3.1.4.1.1.1.81
-- .1.3.6.1.4.1.39026.3.1.4.1.1.1.81
-- .1.3.6.1.4.1.39026.3.1.4.1.1.1.81
-- .1.3.6.1.4.1.39026.3.1.4.1.1.1.81
	bHarmonicsDistortion1 OBJECT-TYPE
	SYNTAX Integer32
	MAX-ACCESS read-only
	STATUS current
	DESCRIPTION
	"Description: "
	::= { powerMeterAMYDMEntry 81 }

-- .1.3.6.1.4.1.39026.3.1.4.1.1.1.82
-- .1.3.6.1.4.1.39026.3.1.4.1.1.1.82
-- .1.3.6.1.4.1.39026.3.1.4.1.1.1.82
-- .1.3.6.1.4.1.39026.3.1.4.1.1.1.82
	bHarmonicsDistortion2 OBJECT-TYPE
	SYNTAX Integer32
	MAX-ACCESS read-only
	STATUS current
	DESCRIPTION
	"Description: "
	::= { powerMeterAMYDMEntry 82 }

-- .1.3.6.1.4.1.39026.3.1.4.1.1.1.83
-- .1.3.6.1.4.1.39026.3.1.4.1.1.1.83
-- .1.3.6.1.4.1.39026.3.1.4.1.1.1.83
-- .1.3.6.1.4.1.39026.3.1.4.1.1.1.83
	bHarmonicsDistortion3 OBJECT-TYPE
	SYNTAX Integer32
	MAX-ACCESS read-only
	STATUS current
	DESCRIPTION
	"Description: "
	::= { powerMeterAMYDMEntry 83 }

-- .1.3.6.1.4.1.39026.3.1.4.1.1.1.84
-- .1.3.6.1.4.1.39026.3.1.4.1.1.1.84
-- .1.3.6.1.4.1.39026.3.1.4.1.1.1.84
-- .1.3.6.1.4.1.39026.3.1.4.1.1.1.84
	bCurAvgHarmonicsDistortion OBJECT-TYPE
	SYNTAX Integer32
	MAX-ACCESS read-only
	STATUS current
	DESCRIPTION
	"Description: "
	::= { powerMeterAMYDMEntry 84 }

-- .1.3.6.1.4.1.39026.3.1.4.1.1.1.85
-- .1.3.6.1.4.1.39026.3.1.4.1.1.1.85
-- .1.3.6.1.4.1.39026.3.1.4.1.1.1.85
-- .1.3.6.1.4.1.39026.3.1.4.1.1.1.85
	aMianSwiftOf OBJECT-TYPE
	SYNTAX Integer32
	MAX-ACCESS read-only
	STATUS current
	DESCRIPTION
	"Description: "
	::= { powerMeterAMYDMEntry 85 }

-- .1.3.6.1.4.1.39026.3.1.4.1.1.1.86
-- .1.3.6.1.4.1.39026.3.1.4.1.1.1.86
-- .1.3.6.1.4.1.39026.3.1.4.1.1.1.86
-- .1.3.6.1.4.1.39026.3.1.4.1.1.1.86
	aMianSwiftSd OBJECT-TYPE
	SYNTAX Integer32
	MAX-ACCESS read-only
	STATUS current
	DESCRIPTION
	"Description: "
	::= { powerMeterAMYDMEntry 86 }

-- .1.3.6.1.4.1.39026.3.1.4.1.1.1.87
-- .1.3.6.1.4.1.39026.3.1.4.1.1.1.87
-- .1.3.6.1.4.1.39026.3.1.4.1.1.1.87
-- .1.3.6.1.4.1.39026.3.1.4.1.1.1.87
	aMianThunderPreventerSwift OBJECT-TYPE
	SYNTAX Integer32
	MAX-ACCESS read-only
	STATUS current
	DESCRIPTION
	"Description: "
	::= { powerMeterAMYDMEntry 87 }

-- .1.3.6.1.4.1.39026.3.1.4.1.1.1.88
-- .1.3.6.1.4.1.39026.3.1.4.1.1.1.88
-- .1.3.6.1.4.1.39026.3.1.4.1.1.1.88
-- .1.3.6.1.4.1.39026.3.1.4.1.1.1.88
	bMianSwiftOf OBJECT-TYPE
	SYNTAX Integer32
	MAX-ACCESS read-only
	STATUS current
	DESCRIPTION
	"Description: "
	::= { powerMeterAMYDMEntry 88 }

-- .1.3.6.1.4.1.39026.3.1.4.1.1.1.89
-- .1.3.6.1.4.1.39026.3.1.4.1.1.1.89
-- .1.3.6.1.4.1.39026.3.1.4.1.1.1.89
-- .1.3.6.1.4.1.39026.3.1.4.1.1.1.89
	bMianSwiftSd OBJECT-TYPE
	SYNTAX Integer32
	MAX-ACCESS read-only
	STATUS current
	DESCRIPTION
	"Description: "
	::= { powerMeterAMYDMEntry 89 }

-- .1.3.6.1.4.1.39026.3.1.4.1.1.1.90
-- .1.3.6.1.4.1.39026.3.1.4.1.1.1.90
-- .1.3.6.1.4.1.39026.3.1.4.1.1.1.90
-- .1.3.6.1.4.1.39026.3.1.4.1.1.1.90
	bMianThunderPreventerSwift OBJECT-TYPE
	SYNTAX Integer32
	MAX-ACCESS read-only
	STATUS current
	DESCRIPTION
	"Description: "
	::= { powerMeterAMYDMEntry 90 }

-- .1.3.6.1.4.1.39026.3.1.4.1.1.1.91
-- .1.3.6.1.4.1.39026.3.1.4.1.1.1.91
-- .1.3.6.1.4.1.39026.3.1.4.1.1.1.91
-- .1.3.6.1.4.1.39026.3.1.4.1.1.1.91
	ofSwiftState1 OBJECT-TYPE
	SYNTAX Integer32
	MAX-ACCESS read-only
	STATUS current
	DESCRIPTION
	"Description: "
	::= { powerMeterAMYDMEntry 91 }

-- .1.3.6.1.4.1.39026.3.1.4.1.1.1.92
-- .1.3.6.1.4.1.39026.3.1.4.1.1.1.92
-- .1.3.6.1.4.1.39026.3.1.4.1.1.1.92
-- .1.3.6.1.4.1.39026.3.1.4.1.1.1.92
	ofSwiftState2 OBJECT-TYPE
	SYNTAX Integer32
	MAX-ACCESS read-only
	STATUS current
	DESCRIPTION
	"Description: "
	::= { powerMeterAMYDMEntry 92 }

-- .1.3.6.1.4.1.39026.3.1.4.1.1.1.93
-- .1.3.6.1.4.1.39026.3.1.4.1.1.1.93
-- .1.3.6.1.4.1.39026.3.1.4.1.1.1.93
-- .1.3.6.1.4.1.39026.3.1.4.1.1.1.93
	ofSwiftState3 OBJECT-TYPE
	SYNTAX Integer32
	MAX-ACCESS read-only
	STATUS current
	DESCRIPTION
	"Description: "
	::= { powerMeterAMYDMEntry 93 }

-- .1.3.6.1.4.1.39026.3.1.4.1.1.1.94
-- .1.3.6.1.4.1.39026.3.1.4.1.1.1.94
-- .1.3.6.1.4.1.39026.3.1.4.1.1.1.94
-- .1.3.6.1.4.1.39026.3.1.4.1.1.1.94
	ofSwiftState4 OBJECT-TYPE
	SYNTAX Integer32
	MAX-ACCESS read-only
	STATUS current
	DESCRIPTION
	"Description: "
	::= { powerMeterAMYDMEntry 94 }

-- .1.3.6.1.4.1.39026.3.1.4.1.1.1.95
-- .1.3.6.1.4.1.39026.3.1.4.1.1.1.95
-- .1.3.6.1.4.1.39026.3.1.4.1.1.1.95
-- .1.3.6.1.4.1.39026.3.1.4.1.1.1.95
	ofSwiftState5 OBJECT-TYPE
	SYNTAX Integer32
	MAX-ACCESS read-only
	STATUS current
	DESCRIPTION
	"Description: "
	::= { powerMeterAMYDMEntry 95 }

-- .1.3.6.1.4.1.39026.3.1.4.1.1.1.96
-- .1.3.6.1.4.1.39026.3.1.4.1.1.1.96
-- .1.3.6.1.4.1.39026.3.1.4.1.1.1.96
-- .1.3.6.1.4.1.39026.3.1.4.1.1.1.96
	ofSwiftState6 OBJECT-TYPE
	SYNTAX Integer32
	MAX-ACCESS read-only
	STATUS current
	DESCRIPTION
	"Description: "
	::= { powerMeterAMYDMEntry 96 }

-- .1.3.6.1.4.1.39026.3.1.4.1.1.1.97
-- .1.3.6.1.4.1.39026.3.1.4.1.1.1.97
-- .1.3.6.1.4.1.39026.3.1.4.1.1.1.97
-- .1.3.6.1.4.1.39026.3.1.4.1.1.1.97
	ofSwiftState7 OBJECT-TYPE
	SYNTAX Integer32
	MAX-ACCESS read-only
	STATUS current
	DESCRIPTION
	"Description: "
	::= { powerMeterAMYDMEntry 97 }

-- .1.3.6.1.4.1.39026.3.1.4.1.1.1.98
-- .1.3.6.1.4.1.39026.3.1.4.1.1.1.98
-- .1.3.6.1.4.1.39026.3.1.4.1.1.1.98
-- .1.3.6.1.4.1.39026.3.1.4.1.1.1.98
	ofSwiftState8 OBJECT-TYPE
	SYNTAX Integer32
	MAX-ACCESS read-only
	STATUS current
	DESCRIPTION
	"Description: "
	::= { powerMeterAMYDMEntry 98 }

-- .1.3.6.1.4.1.39026.3.1.4.1.1.1.99
-- .1.3.6.1.4.1.39026.3.1.4.1.1.1.99
-- .1.3.6.1.4.1.39026.3.1.4.1.1.1.99
-- .1.3.6.1.4.1.39026.3.1.4.1.1.1.99
	ofSwiftState9 OBJECT-TYPE
	SYNTAX Integer32
	MAX-ACCESS read-only
	STATUS current
	DESCRIPTION
	"Description: "
	::= { powerMeterAMYDMEntry 99 }

-- .1.3.6.1.4.1.39026.3.1.4.1.1.1.100
-- .1.3.6.1.4.1.39026.3.1.4.1.1.1.100
-- .1.3.6.1.4.1.39026.3.1.4.1.1.1.100
-- .1.3.6.1.4.1.39026.3.1.4.1.1.1.100
	ofSwiftState10 OBJECT-TYPE
	SYNTAX Integer32
	MAX-ACCESS read-only
	STATUS current
	DESCRIPTION
	"Description: "
	::= { powerMeterAMYDMEntry 100 }

-- .1.3.6.1.4.1.39026.3.1.4.1.1.1.101
-- .1.3.6.1.4.1.39026.3.1.4.1.1.1.101
-- .1.3.6.1.4.1.39026.3.1.4.1.1.1.101
-- .1.3.6.1.4.1.39026.3.1.4.1.1.1.101
	ofSwiftState11 OBJECT-TYPE
	SYNTAX Integer32
	MAX-ACCESS read-only
	STATUS current
	DESCRIPTION
	"Description: "
	::= { powerMeterAMYDMEntry 101 }

-- .1.3.6.1.4.1.39026.3.1.4.1.1.1.102
-- .1.3.6.1.4.1.39026.3.1.4.1.1.1.102
-- .1.3.6.1.4.1.39026.3.1.4.1.1.1.102
-- .1.3.6.1.4.1.39026.3.1.4.1.1.1.102
	ofSwiftState12 OBJECT-TYPE
	SYNTAX Integer32
	MAX-ACCESS read-only
	STATUS current
	DESCRIPTION
	"Description: "
	::= { powerMeterAMYDMEntry 102 }

-- .1.3.6.1.4.1.39026.3.1.4.1.1.1.103
-- .1.3.6.1.4.1.39026.3.1.4.1.1.1.103
-- .1.3.6.1.4.1.39026.3.1.4.1.1.1.103
-- .1.3.6.1.4.1.39026.3.1.4.1.1.1.103
	ofSwiftState13 OBJECT-TYPE
	SYNTAX Integer32
	MAX-ACCESS read-only
	STATUS current
	DESCRIPTION
	"Description: "
	::= { powerMeterAMYDMEntry 103 }

-- .1.3.6.1.4.1.39026.3.1.4.1.1.1.104
-- .1.3.6.1.4.1.39026.3.1.4.1.1.1.104
-- .1.3.6.1.4.1.39026.3.1.4.1.1.1.104
-- .1.3.6.1.4.1.39026.3.1.4.1.1.1.104
	ofSwiftState14 OBJECT-TYPE
	SYNTAX Integer32
	MAX-ACCESS read-only
	STATUS current
	DESCRIPTION
	"Description: "
	::= { powerMeterAMYDMEntry 104 }

-- .1.3.6.1.4.1.39026.3.1.4.1.1.1.105
-- .1.3.6.1.4.1.39026.3.1.4.1.1.1.105
-- .1.3.6.1.4.1.39026.3.1.4.1.1.1.105
-- .1.3.6.1.4.1.39026.3.1.4.1.1.1.105
	ofSwiftState15 OBJECT-TYPE
	SYNTAX Integer32
	MAX-ACCESS read-only
	STATUS current
	DESCRIPTION
	"Description: "
	::= { powerMeterAMYDMEntry 105 }

-- .1.3.6.1.4.1.39026.3.1.4.1.1.1.106
-- .1.3.6.1.4.1.39026.3.1.4.1.1.1.106
-- .1.3.6.1.4.1.39026.3.1.4.1.1.1.106
-- .1.3.6.1.4.1.39026.3.1.4.1.1.1.106
	ofSwiftState16 OBJECT-TYPE
	SYNTAX Integer32
	MAX-ACCESS read-only
	STATUS current
	DESCRIPTION
	"Description: "
	::= { powerMeterAMYDMEntry 106 }

-- .1.3.6.1.4.1.39026.3.1.4.1.1.1.107
-- .1.3.6.1.4.1.39026.3.1.4.1.1.1.107
-- .1.3.6.1.4.1.39026.3.1.4.1.1.1.107
-- .1.3.6.1.4.1.39026.3.1.4.1.1.1.107
	ofSwiftState17 OBJECT-TYPE
	SYNTAX Integer32
	MAX-ACCESS read-only
	STATUS current
	DESCRIPTION
	"Description: "
	::= { powerMeterAMYDMEntry 107 }

-- .1.3.6.1.4.1.39026.3.1.4.1.1.1.108
-- .1.3.6.1.4.1.39026.3.1.4.1.1.1.108
-- .1.3.6.1.4.1.39026.3.1.4.1.1.1.108
-- .1.3.6.1.4.1.39026.3.1.4.1.1.1.108
	ofSwiftState18 OBJECT-TYPE
	SYNTAX Integer32
	MAX-ACCESS read-only
	STATUS current
	DESCRIPTION
	"Description: "
	::= { powerMeterAMYDMEntry 108 }

-- .1.3.6.1.4.1.39026.3.1.4.1.1.1.109
-- .1.3.6.1.4.1.39026.3.1.4.1.1.1.109
-- .1.3.6.1.4.1.39026.3.1.4.1.1.1.109
-- .1.3.6.1.4.1.39026.3.1.4.1.1.1.109
	ofSwiftState19 OBJECT-TYPE
	SYNTAX Integer32
	MAX-ACCESS read-only
	STATUS current
	DESCRIPTION
	"Description: "
	::= { powerMeterAMYDMEntry 109 }

-- .1.3.6.1.4.1.39026.3.1.4.1.1.1.110
-- .1.3.6.1.4.1.39026.3.1.4.1.1.1.110
-- .1.3.6.1.4.1.39026.3.1.4.1.1.1.110
-- .1.3.6.1.4.1.39026.3.1.4.1.1.1.110
	ofSwiftState20 OBJECT-TYPE
	SYNTAX Integer32
	MAX-ACCESS read-only
	STATUS current
	DESCRIPTION
	"Description: "
	::= { powerMeterAMYDMEntry 110 }

-- .1.3.6.1.4.1.39026.3.1.4.1.1.1.111
-- .1.3.6.1.4.1.39026.3.1.4.1.1.1.111
-- .1.3.6.1.4.1.39026.3.1.4.1.1.1.111
-- .1.3.6.1.4.1.39026.3.1.4.1.1.1.111
	ofSwiftState21 OBJECT-TYPE
	SYNTAX Integer32
	MAX-ACCESS read-only
	STATUS current
	DESCRIPTION
	"Description: "
	::= { powerMeterAMYDMEntry 111 }

-- .1.3.6.1.4.1.39026.3.1.4.1.1.1.112
-- .1.3.6.1.4.1.39026.3.1.4.1.1.1.112
-- .1.3.6.1.4.1.39026.3.1.4.1.1.1.112
-- .1.3.6.1.4.1.39026.3.1.4.1.1.1.112
	ofSwiftState22 OBJECT-TYPE
	SYNTAX Integer32
	MAX-ACCESS read-only
	STATUS current
	DESCRIPTION
	"Description: "
	::= { powerMeterAMYDMEntry 112 }

-- .1.3.6.1.4.1.39026.3.1.4.1.1.1.113
-- .1.3.6.1.4.1.39026.3.1.4.1.1.1.113
-- .1.3.6.1.4.1.39026.3.1.4.1.1.1.113
-- .1.3.6.1.4.1.39026.3.1.4.1.1.1.113
	ofSwiftState23 OBJECT-TYPE
	SYNTAX Integer32
	MAX-ACCESS read-only
	STATUS current
	DESCRIPTION
	"Description: "
	::= { powerMeterAMYDMEntry 113 }

-- .1.3.6.1.4.1.39026.3.1.4.1.1.1.114
-- .1.3.6.1.4.1.39026.3.1.4.1.1.1.114
-- .1.3.6.1.4.1.39026.3.1.4.1.1.1.114
-- .1.3.6.1.4.1.39026.3.1.4.1.1.1.114
	ofSwiftState24 OBJECT-TYPE
	SYNTAX Integer32
	MAX-ACCESS read-only
	STATUS current
	DESCRIPTION
	"Description: "
	::= { powerMeterAMYDMEntry 114 }

-- .1.3.6.1.4.1.39026.3.1.4.1.1.1.115
-- .1.3.6.1.4.1.39026.3.1.4.1.1.1.115
-- .1.3.6.1.4.1.39026.3.1.4.1.1.1.115
-- .1.3.6.1.4.1.39026.3.1.4.1.1.1.115
	ofSwiftState25 OBJECT-TYPE
	SYNTAX Integer32
	MAX-ACCESS read-only
	STATUS current
	DESCRIPTION
	"Description: "
	::= { powerMeterAMYDMEntry 115 }

-- .1.3.6.1.4.1.39026.3.1.4.1.1.1.116
-- .1.3.6.1.4.1.39026.3.1.4.1.1.1.116
-- .1.3.6.1.4.1.39026.3.1.4.1.1.1.116
-- .1.3.6.1.4.1.39026.3.1.4.1.1.1.116
	ofSwiftState26 OBJECT-TYPE
	SYNTAX Integer32
	MAX-ACCESS read-only
	STATUS current
	DESCRIPTION
	"Description: "
	::= { powerMeterAMYDMEntry 116 }

-- .1.3.6.1.4.1.39026.3.1.4.1.1.1.117
-- .1.3.6.1.4.1.39026.3.1.4.1.1.1.117
-- .1.3.6.1.4.1.39026.3.1.4.1.1.1.117
-- .1.3.6.1.4.1.39026.3.1.4.1.1.1.117
	ofSwiftState27 OBJECT-TYPE
	SYNTAX Integer32
	MAX-ACCESS read-only
	STATUS current
	DESCRIPTION
	"Description: "
	::= { powerMeterAMYDMEntry 117 }

-- .1.3.6.1.4.1.39026.3.1.4.1.1.1.118
-- .1.3.6.1.4.1.39026.3.1.4.1.1.1.118
-- .1.3.6.1.4.1.39026.3.1.4.1.1.1.118
-- .1.3.6.1.4.1.39026.3.1.4.1.1.1.118
	ofSwiftState28 OBJECT-TYPE
	SYNTAX Integer32
	MAX-ACCESS read-only
	STATUS current
	DESCRIPTION
	"Description: "
	::= { powerMeterAMYDMEntry 118 }

-- .1.3.6.1.4.1.39026.3.1.4.1.1.1.119
-- .1.3.6.1.4.1.39026.3.1.4.1.1.1.119
-- .1.3.6.1.4.1.39026.3.1.4.1.1.1.119
-- .1.3.6.1.4.1.39026.3.1.4.1.1.1.119
	ofSwiftState29 OBJECT-TYPE
	SYNTAX Integer32
	MAX-ACCESS read-only
	STATUS current
	DESCRIPTION
	"Description: "
	::= { powerMeterAMYDMEntry 119 }

-- .1.3.6.1.4.1.39026.3.1.4.1.1.1.120
-- .1.3.6.1.4.1.39026.3.1.4.1.1.1.120
-- .1.3.6.1.4.1.39026.3.1.4.1.1.1.120
-- .1.3.6.1.4.1.39026.3.1.4.1.1.1.120
	ofSwiftState30 OBJECT-TYPE
	SYNTAX Integer32
	MAX-ACCESS read-only
	STATUS current
	DESCRIPTION
	"Description: "
	::= { powerMeterAMYDMEntry 120 }

-- .1.3.6.1.4.1.39026.3.1.4.1.1.1.121
-- .1.3.6.1.4.1.39026.3.1.4.1.1.1.121
-- .1.3.6.1.4.1.39026.3.1.4.1.1.1.121
-- .1.3.6.1.4.1.39026.3.1.4.1.1.1.121
	ofSwiftState31 OBJECT-TYPE
	SYNTAX Integer32
	MAX-ACCESS read-only
	STATUS current
	DESCRIPTION
	"Description: "
	::= { powerMeterAMYDMEntry 121 }

-- .1.3.6.1.4.1.39026.3.1.4.1.1.1.122
-- .1.3.6.1.4.1.39026.3.1.4.1.1.1.122
-- .1.3.6.1.4.1.39026.3.1.4.1.1.1.122
-- .1.3.6.1.4.1.39026.3.1.4.1.1.1.122
	ofSwiftState32 OBJECT-TYPE
	SYNTAX Integer32
	MAX-ACCESS read-only
	STATUS current
	DESCRIPTION
	"Description: "
	::= { powerMeterAMYDMEntry 122 }

-- .1.3.6.1.4.1.39026.3.1.4.1.1.1.123
-- .1.3.6.1.4.1.39026.3.1.4.1.1.1.123
-- .1.3.6.1.4.1.39026.3.1.4.1.1.1.123
-- .1.3.6.1.4.1.39026.3.1.4.1.1.1.123
	ofSwiftState33 OBJECT-TYPE
	SYNTAX Integer32
	MAX-ACCESS read-only
	STATUS current
	DESCRIPTION
	"Description: "
	::= { powerMeterAMYDMEntry 123 }

-- .1.3.6.1.4.1.39026.3.1.4.1.1.1.124
-- .1.3.6.1.4.1.39026.3.1.4.1.1.1.124
-- .1.3.6.1.4.1.39026.3.1.4.1.1.1.124
-- .1.3.6.1.4.1.39026.3.1.4.1.1.1.124
	ofSwiftState34 OBJECT-TYPE
	SYNTAX Integer32
	MAX-ACCESS read-only
	STATUS current
	DESCRIPTION
	"Description: "
	::= { powerMeterAMYDMEntry 124 }

-- .1.3.6.1.4.1.39026.3.1.4.1.1.1.125
-- .1.3.6.1.4.1.39026.3.1.4.1.1.1.125
-- .1.3.6.1.4.1.39026.3.1.4.1.1.1.125
-- .1.3.6.1.4.1.39026.3.1.4.1.1.1.125
	ofSwiftState35 OBJECT-TYPE
	SYNTAX Integer32
	MAX-ACCESS read-only
	STATUS current
	DESCRIPTION
	"Description: "
	::= { powerMeterAMYDMEntry 125 }

-- .1.3.6.1.4.1.39026.3.1.4.1.1.1.126
-- .1.3.6.1.4.1.39026.3.1.4.1.1.1.126
-- .1.3.6.1.4.1.39026.3.1.4.1.1.1.126
-- .1.3.6.1.4.1.39026.3.1.4.1.1.1.126
	ofSwiftState36 OBJECT-TYPE
	SYNTAX Integer32
	MAX-ACCESS read-only
	STATUS current
	DESCRIPTION
	"Description: "
	::= { powerMeterAMYDMEntry 126 }

-- .1.3.6.1.4.1.39026.3.1.4.1.1.1.127
-- .1.3.6.1.4.1.39026.3.1.4.1.1.1.127
-- .1.3.6.1.4.1.39026.3.1.4.1.1.1.127
-- .1.3.6.1.4.1.39026.3.1.4.1.1.1.127
	ofSwiftState37 OBJECT-TYPE
	SYNTAX Integer32
	MAX-ACCESS read-only
	STATUS current
	DESCRIPTION
	"Description: "
	::= { powerMeterAMYDMEntry 127 }

-- .1.3.6.1.4.1.39026.3.1.4.1.1.1.128
-- .1.3.6.1.4.1.39026.3.1.4.1.1.1.128
-- .1.3.6.1.4.1.39026.3.1.4.1.1.1.128
-- .1.3.6.1.4.1.39026.3.1.4.1.1.1.128
	ofSwiftState38 OBJECT-TYPE
	SYNTAX Integer32
	MAX-ACCESS read-only
	STATUS current
	DESCRIPTION
	"Description: "
	::= { powerMeterAMYDMEntry 128 }

-- .1.3.6.1.4.1.39026.3.1.4.1.1.1.129
-- .1.3.6.1.4.1.39026.3.1.4.1.1.1.129
-- .1.3.6.1.4.1.39026.3.1.4.1.1.1.129
-- .1.3.6.1.4.1.39026.3.1.4.1.1.1.129
	ofSwiftState39 OBJECT-TYPE
	SYNTAX Integer32
	MAX-ACCESS read-only
	STATUS current
	DESCRIPTION
	"Description: "
	::= { powerMeterAMYDMEntry 129 }

-- .1.3.6.1.4.1.39026.3.1.4.1.1.1.130
-- .1.3.6.1.4.1.39026.3.1.4.1.1.1.130
-- .1.3.6.1.4.1.39026.3.1.4.1.1.1.130
-- .1.3.6.1.4.1.39026.3.1.4.1.1.1.130
	ofSwiftState40 OBJECT-TYPE
	SYNTAX Integer32
	MAX-ACCESS read-only
	STATUS current
	DESCRIPTION
	"Description: "
	::= { powerMeterAMYDMEntry 130 }

-- .1.3.6.1.4.1.39026.3.1.4.1.1.1.131
-- .1.3.6.1.4.1.39026.3.1.4.1.1.1.131
-- .1.3.6.1.4.1.39026.3.1.4.1.1.1.131
-- .1.3.6.1.4.1.39026.3.1.4.1.1.1.131
	ofSwiftState41 OBJECT-TYPE
	SYNTAX Integer32
	MAX-ACCESS read-only
	STATUS current
	DESCRIPTION
	"Description: "
	::= { powerMeterAMYDMEntry 131 }

-- .1.3.6.1.4.1.39026.3.1.4.1.1.1.132
-- .1.3.6.1.4.1.39026.3.1.4.1.1.1.132
-- .1.3.6.1.4.1.39026.3.1.4.1.1.1.132
-- .1.3.6.1.4.1.39026.3.1.4.1.1.1.132
	ofSwiftState42 OBJECT-TYPE
	SYNTAX Integer32
	MAX-ACCESS read-only
	STATUS current
	DESCRIPTION
	"Description: "
	::= { powerMeterAMYDMEntry 132 }

-- .1.3.6.1.4.1.39026.3.1.4.1.1.1.133
-- .1.3.6.1.4.1.39026.3.1.4.1.1.1.133
-- .1.3.6.1.4.1.39026.3.1.4.1.1.1.133
-- .1.3.6.1.4.1.39026.3.1.4.1.1.1.133
	ofSwiftState43 OBJECT-TYPE
	SYNTAX Integer32
	MAX-ACCESS read-only
	STATUS current
	DESCRIPTION
	"Description: "
	::= { powerMeterAMYDMEntry 133 }

-- .1.3.6.1.4.1.39026.3.1.4.1.1.1.134
-- .1.3.6.1.4.1.39026.3.1.4.1.1.1.134
-- .1.3.6.1.4.1.39026.3.1.4.1.1.1.134
-- .1.3.6.1.4.1.39026.3.1.4.1.1.1.134
	ofSwiftState44 OBJECT-TYPE
	SYNTAX Integer32
	MAX-ACCESS read-only
	STATUS current
	DESCRIPTION
	"Description: "
	::= { powerMeterAMYDMEntry 134 }

-- .1.3.6.1.4.1.39026.3.1.4.1.1.1.135
-- .1.3.6.1.4.1.39026.3.1.4.1.1.1.135
-- .1.3.6.1.4.1.39026.3.1.4.1.1.1.135
-- .1.3.6.1.4.1.39026.3.1.4.1.1.1.135
	ofSwiftState45 OBJECT-TYPE
	SYNTAX Integer32
	MAX-ACCESS read-only
	STATUS current
	DESCRIPTION
	"Description: "
	::= { powerMeterAMYDMEntry 135 }

-- .1.3.6.1.4.1.39026.3.1.4.1.1.1.136
-- .1.3.6.1.4.1.39026.3.1.4.1.1.1.136
-- .1.3.6.1.4.1.39026.3.1.4.1.1.1.136
-- .1.3.6.1.4.1.39026.3.1.4.1.1.1.136
	ofSwiftState46 OBJECT-TYPE
	SYNTAX Integer32
	MAX-ACCESS read-only
	STATUS current
	DESCRIPTION
	"Description: "
	::= { powerMeterAMYDMEntry 136 }

-- .1.3.6.1.4.1.39026.3.1.4.1.1.1.137
-- .1.3.6.1.4.1.39026.3.1.4.1.1.1.137
-- .1.3.6.1.4.1.39026.3.1.4.1.1.1.137
-- .1.3.6.1.4.1.39026.3.1.4.1.1.1.137
	ofSwiftState47 OBJECT-TYPE
	SYNTAX Integer32
	MAX-ACCESS read-only
	STATUS current
	DESCRIPTION
	"Description: "
	::= { powerMeterAMYDMEntry 137 }

-- .1.3.6.1.4.1.39026.3.1.4.1.1.1.138
-- .1.3.6.1.4.1.39026.3.1.4.1.1.1.138
-- .1.3.6.1.4.1.39026.3.1.4.1.1.1.138
-- .1.3.6.1.4.1.39026.3.1.4.1.1.1.138
	ofSwiftState48 OBJECT-TYPE
	SYNTAX Integer32
	MAX-ACCESS read-only
	STATUS current
	DESCRIPTION
	"Description: "
	::= { powerMeterAMYDMEntry 138 }

-- .1.3.6.1.4.1.39026.3.1.4.1.1.1.139
-- .1.3.6.1.4.1.39026.3.1.4.1.1.1.139
-- .1.3.6.1.4.1.39026.3.1.4.1.1.1.139
-- .1.3.6.1.4.1.39026.3.1.4.1.1.1.139
	ofSwiftState49 OBJECT-TYPE
	SYNTAX Integer32
	MAX-ACCESS read-only
	STATUS current
	DESCRIPTION
	"Description: "
	::= { powerMeterAMYDMEntry 139 }

-- .1.3.6.1.4.1.39026.3.1.4.1.1.1.140
-- .1.3.6.1.4.1.39026.3.1.4.1.1.1.140
-- .1.3.6.1.4.1.39026.3.1.4.1.1.1.140
-- .1.3.6.1.4.1.39026.3.1.4.1.1.1.140
	ofSwiftState50 OBJECT-TYPE
	SYNTAX Integer32
	MAX-ACCESS read-only
	STATUS current
	DESCRIPTION
	"Description: "
	::= { powerMeterAMYDMEntry 140 }

-- .1.3.6.1.4.1.39026.3.1.4.1.1.1.141
-- .1.3.6.1.4.1.39026.3.1.4.1.1.1.141
-- .1.3.6.1.4.1.39026.3.1.4.1.1.1.141
-- .1.3.6.1.4.1.39026.3.1.4.1.1.1.141
	ofSwiftState51 OBJECT-TYPE
	SYNTAX Integer32
	MAX-ACCESS read-only
	STATUS current
	DESCRIPTION
	"Description: "
	::= { powerMeterAMYDMEntry 141 }

-- .1.3.6.1.4.1.39026.3.1.4.1.1.1.142
-- .1.3.6.1.4.1.39026.3.1.4.1.1.1.142
-- .1.3.6.1.4.1.39026.3.1.4.1.1.1.142
-- .1.3.6.1.4.1.39026.3.1.4.1.1.1.142
	ofSwiftState52 OBJECT-TYPE
	SYNTAX Integer32
	MAX-ACCESS read-only
	STATUS current
	DESCRIPTION
	"Description: "
	::= { powerMeterAMYDMEntry 142 }

-- .1.3.6.1.4.1.39026.3.1.4.1.1.1.143
-- .1.3.6.1.4.1.39026.3.1.4.1.1.1.143
-- .1.3.6.1.4.1.39026.3.1.4.1.1.1.143
-- .1.3.6.1.4.1.39026.3.1.4.1.1.1.143
	ofSwiftState53 OBJECT-TYPE
	SYNTAX Integer32
	MAX-ACCESS read-only
	STATUS current
	DESCRIPTION
	"Description: "
	::= { powerMeterAMYDMEntry 143 }

-- .1.3.6.1.4.1.39026.3.1.4.1.1.1.144
-- .1.3.6.1.4.1.39026.3.1.4.1.1.1.144
-- .1.3.6.1.4.1.39026.3.1.4.1.1.1.144
-- .1.3.6.1.4.1.39026.3.1.4.1.1.1.144
	ofSwiftState54 OBJECT-TYPE
	SYNTAX Integer32
	MAX-ACCESS read-only
	STATUS current
	DESCRIPTION
	"Description: "
	::= { powerMeterAMYDMEntry 144 }

-- .1.3.6.1.4.1.39026.3.1.4.1.1.1.145
-- .1.3.6.1.4.1.39026.3.1.4.1.1.1.145
-- .1.3.6.1.4.1.39026.3.1.4.1.1.1.145
-- .1.3.6.1.4.1.39026.3.1.4.1.1.1.145
	ofSwiftState55 OBJECT-TYPE
	SYNTAX Integer32
	MAX-ACCESS read-only
	STATUS current
	DESCRIPTION
	"Description: "
	::= { powerMeterAMYDMEntry 145 }

-- .1.3.6.1.4.1.39026.3.1.4.1.1.1.146
-- .1.3.6.1.4.1.39026.3.1.4.1.1.1.146
-- .1.3.6.1.4.1.39026.3.1.4.1.1.1.146
-- .1.3.6.1.4.1.39026.3.1.4.1.1.1.146
	ofSwiftState56 OBJECT-TYPE
	SYNTAX Integer32
	MAX-ACCESS read-only
	STATUS current
	DESCRIPTION
	"Description: "
	::= { powerMeterAMYDMEntry 146 }

-- .1.3.6.1.4.1.39026.3.1.4.1.1.1.147
-- .1.3.6.1.4.1.39026.3.1.4.1.1.1.147
-- .1.3.6.1.4.1.39026.3.1.4.1.1.1.147
-- .1.3.6.1.4.1.39026.3.1.4.1.1.1.147
	ofSwiftState57 OBJECT-TYPE
	SYNTAX Integer32
	MAX-ACCESS read-only
	STATUS current
	DESCRIPTION
	"Description: "
	::= { powerMeterAMYDMEntry 147 }

-- .1.3.6.1.4.1.39026.3.1.4.1.1.1.148
-- .1.3.6.1.4.1.39026.3.1.4.1.1.1.148
-- .1.3.6.1.4.1.39026.3.1.4.1.1.1.148
-- .1.3.6.1.4.1.39026.3.1.4.1.1.1.148
	ofSwiftState58 OBJECT-TYPE
	SYNTAX Integer32
	MAX-ACCESS read-only
	STATUS current
	DESCRIPTION
	"Description: "
	::= { powerMeterAMYDMEntry 148 }

-- .1.3.6.1.4.1.39026.3.1.4.1.1.1.149
-- .1.3.6.1.4.1.39026.3.1.4.1.1.1.149
-- .1.3.6.1.4.1.39026.3.1.4.1.1.1.149
-- .1.3.6.1.4.1.39026.3.1.4.1.1.1.149
	ofSwiftState59 OBJECT-TYPE
	SYNTAX Integer32
	MAX-ACCESS read-only
	STATUS current
	DESCRIPTION
	"Description: "
	::= { powerMeterAMYDMEntry 149 }

-- .1.3.6.1.4.1.39026.3.1.4.1.1.1.150
-- .1.3.6.1.4.1.39026.3.1.4.1.1.1.150
-- .1.3.6.1.4.1.39026.3.1.4.1.1.1.150
-- .1.3.6.1.4.1.39026.3.1.4.1.1.1.150
	ofSwiftState60 OBJECT-TYPE
	SYNTAX Integer32
	MAX-ACCESS read-only
	STATUS current
	DESCRIPTION
	"Description: "
	::= { powerMeterAMYDMEntry 150 }

-- .1.3.6.1.4.1.39026.3.1.4.1.1.1.151
-- .1.3.6.1.4.1.39026.3.1.4.1.1.1.151
-- .1.3.6.1.4.1.39026.3.1.4.1.1.1.151
-- .1.3.6.1.4.1.39026.3.1.4.1.1.1.151
	ofSwiftState61 OBJECT-TYPE
	SYNTAX Integer32
	MAX-ACCESS read-only
	STATUS current
	DESCRIPTION
	"Description: "
	::= { powerMeterAMYDMEntry 151 }

-- .1.3.6.1.4.1.39026.3.1.4.1.1.1.152
-- .1.3.6.1.4.1.39026.3.1.4.1.1.1.152
-- .1.3.6.1.4.1.39026.3.1.4.1.1.1.152
-- .1.3.6.1.4.1.39026.3.1.4.1.1.1.152
	ofSwiftState62 OBJECT-TYPE
	SYNTAX Integer32
	MAX-ACCESS read-only
	STATUS current
	DESCRIPTION
	"Description: "
	::= { powerMeterAMYDMEntry 152 }

-- .1.3.6.1.4.1.39026.3.1.4.1.1.1.153
-- .1.3.6.1.4.1.39026.3.1.4.1.1.1.153
-- .1.3.6.1.4.1.39026.3.1.4.1.1.1.153
-- .1.3.6.1.4.1.39026.3.1.4.1.1.1.153
	ofSwiftState63 OBJECT-TYPE
	SYNTAX Integer32
	MAX-ACCESS read-only
	STATUS current
	DESCRIPTION
	"Description: "
	::= { powerMeterAMYDMEntry 153 }

-- .1.3.6.1.4.1.39026.3.1.4.1.1.1.154
-- .1.3.6.1.4.1.39026.3.1.4.1.1.1.154
-- .1.3.6.1.4.1.39026.3.1.4.1.1.1.154
-- .1.3.6.1.4.1.39026.3.1.4.1.1.1.154
	ofSwiftState64 OBJECT-TYPE
	SYNTAX Integer32
	MAX-ACCESS read-only
	STATUS current
	DESCRIPTION
	"Description: "
	::= { powerMeterAMYDMEntry 154 }

-- .1.3.6.1.4.1.39026.3.1.4.1.1.1.155
-- .1.3.6.1.4.1.39026.3.1.4.1.1.1.155
-- .1.3.6.1.4.1.39026.3.1.4.1.1.1.155
-- .1.3.6.1.4.1.39026.3.1.4.1.1.1.155
	ofSwiftState65 OBJECT-TYPE
	SYNTAX Integer32
	MAX-ACCESS read-only
	STATUS current
	DESCRIPTION
	"Description: "
	::= { powerMeterAMYDMEntry 155 }

-- .1.3.6.1.4.1.39026.3.1.4.1.1.1.156
-- .1.3.6.1.4.1.39026.3.1.4.1.1.1.156
-- .1.3.6.1.4.1.39026.3.1.4.1.1.1.156
-- .1.3.6.1.4.1.39026.3.1.4.1.1.1.156
	ofSwiftState66 OBJECT-TYPE
	SYNTAX Integer32
	MAX-ACCESS read-only
	STATUS current
	DESCRIPTION
	"Description: "
	::= { powerMeterAMYDMEntry 156 }

-- .1.3.6.1.4.1.39026.3.1.4.1.1.1.157
-- .1.3.6.1.4.1.39026.3.1.4.1.1.1.157
-- .1.3.6.1.4.1.39026.3.1.4.1.1.1.157
-- .1.3.6.1.4.1.39026.3.1.4.1.1.1.157
	ofSwiftState67 OBJECT-TYPE
	SYNTAX Integer32
	MAX-ACCESS read-only
	STATUS current
	DESCRIPTION
	"Description: "
	::= { powerMeterAMYDMEntry 157 }

-- .1.3.6.1.4.1.39026.3.1.4.1.1.1.158
-- .1.3.6.1.4.1.39026.3.1.4.1.1.1.158
-- .1.3.6.1.4.1.39026.3.1.4.1.1.1.158
-- .1.3.6.1.4.1.39026.3.1.4.1.1.1.158
	ofSwiftState68 OBJECT-TYPE
	SYNTAX Integer32
	MAX-ACCESS read-only
	STATUS current
	DESCRIPTION
	"Description: "
	::= { powerMeterAMYDMEntry 158 }

-- .1.3.6.1.4.1.39026.3.1.4.1.1.1.159
-- .1.3.6.1.4.1.39026.3.1.4.1.1.1.159
-- .1.3.6.1.4.1.39026.3.1.4.1.1.1.159
-- .1.3.6.1.4.1.39026.3.1.4.1.1.1.159
	ofSwiftState69 OBJECT-TYPE
	SYNTAX Integer32
	MAX-ACCESS read-only
	STATUS current
	DESCRIPTION
	"Description: "
	::= { powerMeterAMYDMEntry 159 }

-- .1.3.6.1.4.1.39026.3.1.4.1.1.1.160
-- .1.3.6.1.4.1.39026.3.1.4.1.1.1.160
-- .1.3.6.1.4.1.39026.3.1.4.1.1.1.160
-- .1.3.6.1.4.1.39026.3.1.4.1.1.1.160
	ofSwiftState70 OBJECT-TYPE
	SYNTAX Integer32
	MAX-ACCESS read-only
	STATUS current
	DESCRIPTION
	"Description: "
	::= { powerMeterAMYDMEntry 160 }

-- .1.3.6.1.4.1.39026.3.1.4.1.1.1.161
-- .1.3.6.1.4.1.39026.3.1.4.1.1.1.161
-- .1.3.6.1.4.1.39026.3.1.4.1.1.1.161
-- .1.3.6.1.4.1.39026.3.1.4.1.1.1.161
	ofSwiftState71 OBJECT-TYPE
	SYNTAX Integer32
	MAX-ACCESS read-only
	STATUS current
	DESCRIPTION
	"Description: "
	::= { powerMeterAMYDMEntry 161 }

-- .1.3.6.1.4.1.39026.3.1.4.1.1.1.162
-- .1.3.6.1.4.1.39026.3.1.4.1.1.1.162
-- .1.3.6.1.4.1.39026.3.1.4.1.1.1.162
-- .1.3.6.1.4.1.39026.3.1.4.1.1.1.162
	ofSwiftState72 OBJECT-TYPE
	SYNTAX Integer32
	MAX-ACCESS read-only
	STATUS current
	DESCRIPTION
	"Description: "
	::= { powerMeterAMYDMEntry 162 }

-- .1.3.6.1.4.1.39026.3.1.4.1.1.1.163
-- .1.3.6.1.4.1.39026.3.1.4.1.1.1.163
-- .1.3.6.1.4.1.39026.3.1.4.1.1.1.163
-- .1.3.6.1.4.1.39026.3.1.4.1.1.1.163
	ofSwiftState73 OBJECT-TYPE
	SYNTAX Integer32
	MAX-ACCESS read-only
	STATUS current
	DESCRIPTION
	"Description: "
	::= { powerMeterAMYDMEntry 163 }

-- .1.3.6.1.4.1.39026.3.1.4.1.1.1.164
-- .1.3.6.1.4.1.39026.3.1.4.1.1.1.164
-- .1.3.6.1.4.1.39026.3.1.4.1.1.1.164
-- .1.3.6.1.4.1.39026.3.1.4.1.1.1.164
	ofSwiftState74 OBJECT-TYPE
	SYNTAX Integer32
	MAX-ACCESS read-only
	STATUS current
	DESCRIPTION
	"Description: "
	::= { powerMeterAMYDMEntry 164 }

-- .1.3.6.1.4.1.39026.3.1.4.1.1.1.165
-- .1.3.6.1.4.1.39026.3.1.4.1.1.1.165
-- .1.3.6.1.4.1.39026.3.1.4.1.1.1.165
-- .1.3.6.1.4.1.39026.3.1.4.1.1.1.165
	ofSwiftState75 OBJECT-TYPE
	SYNTAX Integer32
	MAX-ACCESS read-only
	STATUS current
	DESCRIPTION
	"Description: "
	::= { powerMeterAMYDMEntry 165 }

-- .1.3.6.1.4.1.39026.3.1.4.1.1.1.166
-- .1.3.6.1.4.1.39026.3.1.4.1.1.1.166
-- .1.3.6.1.4.1.39026.3.1.4.1.1.1.166
-- .1.3.6.1.4.1.39026.3.1.4.1.1.1.166
	ofSwiftState76 OBJECT-TYPE
	SYNTAX Integer32
	MAX-ACCESS read-only
	STATUS current
	DESCRIPTION
	"Description: "
	::= { powerMeterAMYDMEntry 166 }

-- .1.3.6.1.4.1.39026.3.1.4.1.1.1.167
-- .1.3.6.1.4.1.39026.3.1.4.1.1.1.167
-- .1.3.6.1.4.1.39026.3.1.4.1.1.1.167
-- .1.3.6.1.4.1.39026.3.1.4.1.1.1.167
	ofSwiftState77 OBJECT-TYPE
	SYNTAX Integer32
	MAX-ACCESS read-only
	STATUS current
	DESCRIPTION
	"Description: "
	::= { powerMeterAMYDMEntry 167 }

-- .1.3.6.1.4.1.39026.3.1.4.1.1.1.168
-- .1.3.6.1.4.1.39026.3.1.4.1.1.1.168
-- .1.3.6.1.4.1.39026.3.1.4.1.1.1.168
-- .1.3.6.1.4.1.39026.3.1.4.1.1.1.168
	ofSwiftState78 OBJECT-TYPE
	SYNTAX Integer32
	MAX-ACCESS read-only
	STATUS current
	DESCRIPTION
	"Description: "
	::= { powerMeterAMYDMEntry 168 }

-- .1.3.6.1.4.1.39026.3.1.4.1.1.1.169
-- .1.3.6.1.4.1.39026.3.1.4.1.1.1.169
-- .1.3.6.1.4.1.39026.3.1.4.1.1.1.169
-- .1.3.6.1.4.1.39026.3.1.4.1.1.1.169
	ofSwiftState79 OBJECT-TYPE
	SYNTAX Integer32
	MAX-ACCESS read-only
	STATUS current
	DESCRIPTION
	"Description: "
	::= { powerMeterAMYDMEntry 169 }

-- .1.3.6.1.4.1.39026.3.1.4.1.1.1.170
-- .1.3.6.1.4.1.39026.3.1.4.1.1.1.170
-- .1.3.6.1.4.1.39026.3.1.4.1.1.1.170
-- .1.3.6.1.4.1.39026.3.1.4.1.1.1.170
	ofSwiftState80 OBJECT-TYPE
	SYNTAX Integer32
	MAX-ACCESS read-only
	STATUS current
	DESCRIPTION
	"Description: "
	::= { powerMeterAMYDMEntry 170 }

-- .1.3.6.1.4.1.39026.3.1.4.1.1.1.171
-- .1.3.6.1.4.1.39026.3.1.4.1.1.1.171
-- .1.3.6.1.4.1.39026.3.1.4.1.1.1.171
-- .1.3.6.1.4.1.39026.3.1.4.1.1.1.171
	ofSwiftState81 OBJECT-TYPE
	SYNTAX Integer32
	MAX-ACCESS read-only
	STATUS current
	DESCRIPTION
	"Description: "
	::= { powerMeterAMYDMEntry 171 }

-- .1.3.6.1.4.1.39026.3.1.4.1.1.1.172
-- .1.3.6.1.4.1.39026.3.1.4.1.1.1.172
-- .1.3.6.1.4.1.39026.3.1.4.1.1.1.172
-- .1.3.6.1.4.1.39026.3.1.4.1.1.1.172
	ofSwiftState82 OBJECT-TYPE
	SYNTAX Integer32
	MAX-ACCESS read-only
	STATUS current
	DESCRIPTION
	"Description: "
	::= { powerMeterAMYDMEntry 172 }

-- .1.3.6.1.4.1.39026.3.1.4.1.1.1.173
-- .1.3.6.1.4.1.39026.3.1.4.1.1.1.173
-- .1.3.6.1.4.1.39026.3.1.4.1.1.1.173
-- .1.3.6.1.4.1.39026.3.1.4.1.1.1.173
	ofSwiftState83 OBJECT-TYPE
	SYNTAX Integer32
	MAX-ACCESS read-only
	STATUS current
	DESCRIPTION
	"Description: "
	::= { powerMeterAMYDMEntry 173 }

-- .1.3.6.1.4.1.39026.3.1.4.1.1.1.174
-- .1.3.6.1.4.1.39026.3.1.4.1.1.1.174
-- .1.3.6.1.4.1.39026.3.1.4.1.1.1.174
-- .1.3.6.1.4.1.39026.3.1.4.1.1.1.174
	ofSwiftState84 OBJECT-TYPE
	SYNTAX Integer32
	MAX-ACCESS read-only
	STATUS current
	DESCRIPTION
	"Description: "
	::= { powerMeterAMYDMEntry 174 }

-- .1.3.6.1.4.1.39026.3.1.4.1.1.1.175
-- .1.3.6.1.4.1.39026.3.1.4.1.1.1.175
-- .1.3.6.1.4.1.39026.3.1.4.1.1.1.175
-- .1.3.6.1.4.1.39026.3.1.4.1.1.1.175
	ofSwiftState85 OBJECT-TYPE
	SYNTAX Integer32
	MAX-ACCESS read-only
	STATUS current
	DESCRIPTION
	"Description: "
	::= { powerMeterAMYDMEntry 175 }

-- .1.3.6.1.4.1.39026.3.1.4.1.1.1.176
-- .1.3.6.1.4.1.39026.3.1.4.1.1.1.176
-- .1.3.6.1.4.1.39026.3.1.4.1.1.1.176
-- .1.3.6.1.4.1.39026.3.1.4.1.1.1.176
	ofSwiftState86 OBJECT-TYPE
	SYNTAX Integer32
	MAX-ACCESS read-only
	STATUS current
	DESCRIPTION
	"Description: "
	::= { powerMeterAMYDMEntry 176 }

-- .1.3.6.1.4.1.39026.3.1.4.1.1.1.177
-- .1.3.6.1.4.1.39026.3.1.4.1.1.1.177
-- .1.3.6.1.4.1.39026.3.1.4.1.1.1.177
-- .1.3.6.1.4.1.39026.3.1.4.1.1.1.177
	ofSwiftState87 OBJECT-TYPE
	SYNTAX Integer32
	MAX-ACCESS read-only
	STATUS current
	DESCRIPTION
	"Description: "
	::= { powerMeterAMYDMEntry 177 }

-- .1.3.6.1.4.1.39026.3.1.4.1.1.1.178
-- .1.3.6.1.4.1.39026.3.1.4.1.1.1.178
-- .1.3.6.1.4.1.39026.3.1.4.1.1.1.178
-- .1.3.6.1.4.1.39026.3.1.4.1.1.1.178
	ofSwiftState88 OBJECT-TYPE
	SYNTAX Integer32
	MAX-ACCESS read-only
	STATUS current
	DESCRIPTION
	"Description: "
	::= { powerMeterAMYDMEntry 178 }

-- .1.3.6.1.4.1.39026.3.1.4.1.1.1.179
-- .1.3.6.1.4.1.39026.3.1.4.1.1.1.179
-- .1.3.6.1.4.1.39026.3.1.4.1.1.1.179
-- .1.3.6.1.4.1.39026.3.1.4.1.1.1.179
	ofSwiftState89 OBJECT-TYPE
	SYNTAX Integer32
	MAX-ACCESS read-only
	STATUS current
	DESCRIPTION
	"Description: "
	::= { powerMeterAMYDMEntry 179 }

-- .1.3.6.1.4.1.39026.3.1.4.1.1.1.180
-- .1.3.6.1.4.1.39026.3.1.4.1.1.1.180
-- .1.3.6.1.4.1.39026.3.1.4.1.1.1.180
-- .1.3.6.1.4.1.39026.3.1.4.1.1.1.180
	ofSwiftState90 OBJECT-TYPE
	SYNTAX Integer32
	MAX-ACCESS read-only
	STATUS current
	DESCRIPTION
	"Description: "
	::= { powerMeterAMYDMEntry 180 }

-- .1.3.6.1.4.1.39026.3.1.4.1.1.1.181
-- .1.3.6.1.4.1.39026.3.1.4.1.1.1.181
-- .1.3.6.1.4.1.39026.3.1.4.1.1.1.181
-- .1.3.6.1.4.1.39026.3.1.4.1.1.1.181
	ofSwiftState91 OBJECT-TYPE
	SYNTAX Integer32
	MAX-ACCESS read-only
	STATUS current
	DESCRIPTION
	"Description: "
	::= { powerMeterAMYDMEntry 181 }

-- .1.3.6.1.4.1.39026.3.1.4.1.1.1.182
-- .1.3.6.1.4.1.39026.3.1.4.1.1.1.182
-- .1.3.6.1.4.1.39026.3.1.4.1.1.1.182
-- .1.3.6.1.4.1.39026.3.1.4.1.1.1.182
	ofSwiftState92 OBJECT-TYPE
	SYNTAX Integer32
	MAX-ACCESS read-only
	STATUS current
	DESCRIPTION
	"Description: "
	::= { powerMeterAMYDMEntry 182 }

-- .1.3.6.1.4.1.39026.3.1.4.1.1.1.183
-- .1.3.6.1.4.1.39026.3.1.4.1.1.1.183
-- .1.3.6.1.4.1.39026.3.1.4.1.1.1.183
-- .1.3.6.1.4.1.39026.3.1.4.1.1.1.183
	ofSwiftState93 OBJECT-TYPE
	SYNTAX Integer32
	MAX-ACCESS read-only
	STATUS current
	DESCRIPTION
	"Description: "
	::= { powerMeterAMYDMEntry 183 }

-- .1.3.6.1.4.1.39026.3.1.4.1.1.1.184
-- .1.3.6.1.4.1.39026.3.1.4.1.1.1.184
-- .1.3.6.1.4.1.39026.3.1.4.1.1.1.184
-- .1.3.6.1.4.1.39026.3.1.4.1.1.1.184
	ofSwiftState94 OBJECT-TYPE
	SYNTAX Integer32
	MAX-ACCESS read-only
	STATUS current
	DESCRIPTION
	"Description: "
	::= { powerMeterAMYDMEntry 184 }

-- .1.3.6.1.4.1.39026.3.1.4.1.1.1.185
-- .1.3.6.1.4.1.39026.3.1.4.1.1.1.185
-- .1.3.6.1.4.1.39026.3.1.4.1.1.1.185
-- .1.3.6.1.4.1.39026.3.1.4.1.1.1.185
	ofSwiftState95 OBJECT-TYPE
	SYNTAX Integer32
	MAX-ACCESS read-only
	STATUS current
	DESCRIPTION
	"Description: "
	::= { powerMeterAMYDMEntry 185 }

-- .1.3.6.1.4.1.39026.3.1.4.1.1.1.186
-- .1.3.6.1.4.1.39026.3.1.4.1.1.1.186
-- .1.3.6.1.4.1.39026.3.1.4.1.1.1.186
-- .1.3.6.1.4.1.39026.3.1.4.1.1.1.186
	ofSwiftState96 OBJECT-TYPE
	SYNTAX Integer32
	MAX-ACCESS read-only
	STATUS current
	DESCRIPTION
	"Description: "
	::= { powerMeterAMYDMEntry 186 }

-- .1.3.6.1.4.1.39026.3.1.4.1.1.1.187
-- .1.3.6.1.4.1.39026.3.1.4.1.1.1.187
-- .1.3.6.1.4.1.39026.3.1.4.1.1.1.187
-- .1.3.6.1.4.1.39026.3.1.4.1.1.1.187
	ofSwiftState97 OBJECT-TYPE
	SYNTAX Integer32
	MAX-ACCESS read-only
	STATUS current
	DESCRIPTION
	"Description: "
	::= { powerMeterAMYDMEntry 187 }

-- .1.3.6.1.4.1.39026.3.1.4.1.1.1.188
-- .1.3.6.1.4.1.39026.3.1.4.1.1.1.188
-- .1.3.6.1.4.1.39026.3.1.4.1.1.1.188
-- .1.3.6.1.4.1.39026.3.1.4.1.1.1.188
	ofSwiftState98 OBJECT-TYPE
	SYNTAX Integer32
	MAX-ACCESS read-only
	STATUS current
	DESCRIPTION
	"Description: "
	::= { powerMeterAMYDMEntry 188 }

-- .1.3.6.1.4.1.39026.3.1.4.1.1.1.189
-- .1.3.6.1.4.1.39026.3.1.4.1.1.1.189
-- .1.3.6.1.4.1.39026.3.1.4.1.1.1.189
-- .1.3.6.1.4.1.39026.3.1.4.1.1.1.189
	ofSwiftState99 OBJECT-TYPE
	SYNTAX Integer32
	MAX-ACCESS read-only
	STATUS current
	DESCRIPTION
	"Description: "
	::= { powerMeterAMYDMEntry 189 }

-- .1.3.6.1.4.1.39026.3.1.4.1.1.1.190
-- .1.3.6.1.4.1.39026.3.1.4.1.1.1.190
-- .1.3.6.1.4.1.39026.3.1.4.1.1.1.190
-- .1.3.6.1.4.1.39026.3.1.4.1.1.1.190
	ofSwiftState100 OBJECT-TYPE
	SYNTAX Integer32
	MAX-ACCESS read-only
	STATUS current
	DESCRIPTION
	"Description: "
	::= { powerMeterAMYDMEntry 190 }

-- .1.3.6.1.4.1.39026.3.1.4.1.1.1.191
-- .1.3.6.1.4.1.39026.3.1.4.1.1.1.191
-- .1.3.6.1.4.1.39026.3.1.4.1.1.1.191
-- .1.3.6.1.4.1.39026.3.1.4.1.1.1.191
	ofSwiftState101 OBJECT-TYPE
	SYNTAX Integer32
	MAX-ACCESS read-only
	STATUS current
	DESCRIPTION
	"Description: "
	::= { powerMeterAMYDMEntry 191 }

-- .1.3.6.1.4.1.39026.3.1.4.1.1.1.192
-- .1.3.6.1.4.1.39026.3.1.4.1.1.1.192
-- .1.3.6.1.4.1.39026.3.1.4.1.1.1.192
-- .1.3.6.1.4.1.39026.3.1.4.1.1.1.192
	ofSwiftState102 OBJECT-TYPE
	SYNTAX Integer32
	MAX-ACCESS read-only
	STATUS current
	DESCRIPTION
	"Description: "
	::= { powerMeterAMYDMEntry 192 }

-- .1.3.6.1.4.1.39026.3.1.4.1.1.1.193
-- .1.3.6.1.4.1.39026.3.1.4.1.1.1.193
-- .1.3.6.1.4.1.39026.3.1.4.1.1.1.193
-- .1.3.6.1.4.1.39026.3.1.4.1.1.1.193
	ofSwiftState103 OBJECT-TYPE
	SYNTAX Integer32
	MAX-ACCESS read-only
	STATUS current
	DESCRIPTION
	"Description: "
	::= { powerMeterAMYDMEntry 193 }

-- .1.3.6.1.4.1.39026.3.1.4.1.1.1.194
-- .1.3.6.1.4.1.39026.3.1.4.1.1.1.194
-- .1.3.6.1.4.1.39026.3.1.4.1.1.1.194
-- .1.3.6.1.4.1.39026.3.1.4.1.1.1.194
	ofSwiftState104 OBJECT-TYPE
	SYNTAX Integer32
	MAX-ACCESS read-only
	STATUS current
	DESCRIPTION
	"Description: "
	::= { powerMeterAMYDMEntry 194 }

-- .1.3.6.1.4.1.39026.3.1.4.1.1.1.195
-- .1.3.6.1.4.1.39026.3.1.4.1.1.1.195
-- .1.3.6.1.4.1.39026.3.1.4.1.1.1.195
-- .1.3.6.1.4.1.39026.3.1.4.1.1.1.195
	ofSwiftState105 OBJECT-TYPE
	SYNTAX Integer32
	MAX-ACCESS read-only
	STATUS current
	DESCRIPTION
	"Description: "
	::= { powerMeterAMYDMEntry 195 }

-- .1.3.6.1.4.1.39026.3.1.4.1.1.1.196
-- .1.3.6.1.4.1.39026.3.1.4.1.1.1.196
-- .1.3.6.1.4.1.39026.3.1.4.1.1.1.196
-- .1.3.6.1.4.1.39026.3.1.4.1.1.1.196
	ofSwiftState106 OBJECT-TYPE
	SYNTAX Integer32
	MAX-ACCESS read-only
	STATUS current
	DESCRIPTION
	"Description: "
	::= { powerMeterAMYDMEntry 196 }

-- .1.3.6.1.4.1.39026.3.1.4.1.1.1.197
-- .1.3.6.1.4.1.39026.3.1.4.1.1.1.197
-- .1.3.6.1.4.1.39026.3.1.4.1.1.1.197
-- .1.3.6.1.4.1.39026.3.1.4.1.1.1.197
	ofSwiftState107 OBJECT-TYPE
	SYNTAX Integer32
	MAX-ACCESS read-only
	STATUS current
	DESCRIPTION
	"Description: "
	::= { powerMeterAMYDMEntry 197 }

-- .1.3.6.1.4.1.39026.3.1.4.1.1.1.198
-- .1.3.6.1.4.1.39026.3.1.4.1.1.1.198
-- .1.3.6.1.4.1.39026.3.1.4.1.1.1.198
-- .1.3.6.1.4.1.39026.3.1.4.1.1.1.198
	ofSwiftState108 OBJECT-TYPE
	SYNTAX Integer32
	MAX-ACCESS read-only
	STATUS current
	DESCRIPTION
	"Description: "
	::= { powerMeterAMYDMEntry 198 }

--    1.3.6.1.4.1.39026.3.1.4.1.2
-- 1.3.6.1.4.1.39026.3.1.4.1.2
-- 1.3.6.1.4.1.39026.3.1.4.1.2
		-- 1.3.6.1.4.1.39026.3.1.4.1.2
		powerMeterAMYDBTable OBJECT-TYPE
			SYNTAX SEQUENCE OF powerMeterAMYDBEntry
			MAX-ACCESS not-accessible
			STATUS current
			DESCRIPTION
				"Description."
			::= { powerMeter 2 }

--    1.3.6.1.4.1.39026.3.1.4.1.2.1
-- 1.3.6.1.4.1.39026.3.1.4.1.2.1
-- 1.3.6.1.4.1.39026.3.1.4.1.2.1
		-- 1.3.6.1.4.1.39026.3.1.4.1.2.1
		powerMeterAMYDBEntry OBJECT-TYPE
			SYNTAX powerMeterAMYDBEntry
			MAX-ACCESS not-accessible
			STATUS current
			DESCRIPTION
				"Description."
			INDEX { pmYdbIndex }
			::= { powerMeterAMYDBTable 1 }


		powerMeterAMYDBEntry ::=
			SEQUENCE { 	
				pmYdbIndex
					Integer32,
				pmYdbEquipOid
					DisplayString,
				pmYdbEquipName
					DisplayString,
				pmYdbCollectionTime
					DisplayString,
				branchVoltage1
					Integer32,
				branchCurrent1
					Integer32,
				branchActivePower1
					Integer32,
				branchActiveEnergy1
					Integer32,
				branchVoltage2
					Integer32,
				branchCurrent2
					Integer32,
				branchActivePower2
					Integer32,
				branchActiveEnergy2
					Integer32,
				branchVoltage3
					Integer32,
				branchCurrent3
					Integer32,
				branchActivePower3
					Integer32,
				branchActiveEnergy3
					Integer32,
				branchVoltage4
					Integer32,
				branchCurrent4
					Integer32,
				branchActivePower4
					Integer32,
				branchActiveEnergy4
					Integer32,
				branchVoltage5
					Integer32,
				branchCurrent5
					Integer32,
				branchActivePower5
					Integer32,
				branchActiveEnergy5
					Integer32,
				branchVoltage6
					Integer32,
				branchCurrent6
					Integer32,
				branchActivePower6
					Integer32,
				branchActiveEnergy6
					Integer32,
				branchVoltage7
					Integer32,
				branchCurrent7
					Integer32,
				branchActivePower7
					Integer32,
				branchActiveEnergy7
					Integer32,
				branchVoltage8
					Integer32,
				branchCurrent8
					Integer32,
				branchActivePower8
					Integer32,
				branchActiveEnergy8
					Integer32,
				branchVoltage9
					Integer32,
				branchCurrent9
					Integer32,
				branchActivePower9
					Integer32,
				branchActiveEnergy9
					Integer32,
				branchVoltage10
					Integer32,
				branchCurrent10
					Integer32,
				branchActivePower10
					Integer32,
				branchActiveEnergy10
					Integer32,
				branchVoltage11
					Integer32,
				branchCurrent11
					Integer32,
				branchActivePower11
					Integer32,
				branchActiveEnergy11
					Integer32,
				branchVoltage12
					Integer32,
				branchCurrent12
					Integer32,
				branchActivePower12
					Integer32,
				branchActiveEnergy12
					Integer32,
				branchVoltage13
					Integer32,
				branchCurrent13
					Integer32,
				branchActivePower13
					Integer32,
				branchActiveEnergy13
					Integer32,
				branchVoltage14
					Integer32,
				branchCurrent14
					Integer32,
				branchActivePower14
					Integer32,
				branchActiveEnergy14
					Integer32,
				branchVoltage15
					Integer32,
				branchCurrent15
					Integer32,
				branchActivePower15
					Integer32,
				branchActiveEnergy15
					Integer32,
				branchVoltage16
					Integer32,
				branchCurrent16
					Integer32,
				branchActivePower16
					Integer32,
				branchActiveEnergy16
					Integer32,
				branchVoltage17
					Integer32,
				branchCurrent17
					Integer32,
				branchActivePower17
					Integer32,
				branchActiveEnergy17
					Integer32,
				branchVoltage18
					Integer32,
				branchCurrent18
					Integer32,
				branchActivePower18
					Integer32,
				branchActiveEnergy18
					Integer32,
				branchVoltage19
					Integer32,
				branchCurrent19
					Integer32,
				branchActivePower19
					Integer32,
				branchActiveEnergy19
					Integer32,
				branchVoltage20
					Integer32,
				branchCurrent20
					Integer32,
				branchActivePower20
					Integer32,
				branchActiveEnergy20
					Integer32,
				branchVoltage21
					Integer32,
				branchCurrent21
					Integer32,
				branchActivePower21
					Integer32,
				branchActiveEnergy21
					Integer32,
				branchVoltage22
					Integer32,
				branchCurrent22
					Integer32,
				branchActivePower22
					Integer32,
				branchActiveEnergy22
					Integer32,
				branchVoltage23
					Integer32,
				branchCurrent23
					Integer32,
				branchActivePower23
					Integer32,
				branchActiveEnergy23
					Integer32,
				branchVoltage24
					Integer32,
				branchCurrent24
					Integer32,
				branchActivePower24
					Integer32,
				branchActiveEnergy24
					Integer32,
				branchVoltage25
					Integer32,
				branchCurrent25
					Integer32,
				branchActivePower25
					Integer32,
				branchActiveEnergy25
					Integer32,
				branchVoltage26
					Integer32,
				branchCurrent26
					Integer32,
				branchActivePower26
					Integer32,
				branchActiveEnergy26
					Integer32,
				branchVoltage27
					Integer32,
				branchCurrent27
					Integer32,
				branchActivePower27
					Integer32,
				branchActiveEnergy27
					Integer32,
				branchVoltage28
					Integer32,
				branchCurrent28
					Integer32,
				branchActivePower28
					Integer32,
				branchActiveEnergy28
					Integer32,
				branchVoltage29
					Integer32,
				branchCurrent29
					Integer32,
				branchActivePower29
					Integer32,
				branchActiveEnergy29
					Integer32,
				branchVoltage30
					Integer32,
				branchCurrent30
					Integer32,
				branchActivePower30
					Integer32,
				branchActiveEnergy30
					Integer32,
				branchVoltage31
					Integer32,
				branchCurrent31
					Integer32,
				branchActivePower31
					Integer32,
				branchActiveEnergy31
					Integer32,
				branchVoltage32
					Integer32,
				branchCurrent32
					Integer32,
				branchActivePower32
					Integer32,
				branchActiveEnergy32
					Integer32,
				branchVoltage33
					Integer32,
				branchCurrent33
					Integer32,
				branchActivePower33
					Integer32,
				branchActiveEnergy33
					Integer32,
				branchVoltage34
					Integer32,
				branchCurrent34
					Integer32,
				branchActivePower34
					Integer32,
				branchActiveEnergy34
					Integer32,
				branchVoltage35
					Integer32,
				branchCurrent35
					Integer32,
				branchActivePower35
					Integer32,
				branchActiveEnergy35
					Integer32,
				branchVoltage36
					Integer32,
				branchCurrent36
					Integer32,
				branchActivePower36
					Integer32,
				branchActiveEnergy36
					Integer32,
				branchVoltage37
					Integer32,
				branchCurrent37
					Integer32,
				branchActivePower37
					Integer32,
				branchActiveEnergy37
					Integer32,
				branchVoltage38
					Integer32,
				branchCurrent38
					Integer32,
				branchActivePower38
					Integer32,
				branchActiveEnergy38
					Integer32,
				branchVoltage39
					Integer32,
				branchCurrent39
					Integer32,
				branchActivePower39
					Integer32,
				branchActiveEnergy39
					Integer32,
				branchVoltage40
					Integer32,
				branchCurrent40
					Integer32,
				branchActivePower40
					Integer32,
				branchActiveEnergy40
					Integer32,
				branchVoltage41
					Integer32,
				branchCurrent41
					Integer32,
				branchActivePower41
					Integer32,
				branchActiveEnergy41
					Integer32,
				branchVoltage42
					Integer32,
				branchCurrent42
					Integer32,
				branchActivePower42
					Integer32,
				branchActiveEnergy42
					Integer32,
				branchVoltage43
					Integer32,
				branchCurrent43
					Integer32,
				branchActivePower43
					Integer32,
				branchActiveEnergy43
					Integer32,
				branchVoltage44
					Integer32,
				branchCurrent44
					Integer32,
				branchActivePower44
					Integer32,
				branchActiveEnergy44
					Integer32,
				branchVoltage45
					Integer32,
				branchCurrent45
					Integer32,
				branchActivePower45
					Integer32,
				branchActiveEnergy45
					Integer32,
				branchVoltage46
					Integer32,
				branchCurrent46
					Integer32,
				branchActivePower46
					Integer32,
				branchActiveEnergy46
					Integer32,
				branchVoltage47
					Integer32,
				branchCurrent47
					Integer32,
				branchActivePower47
					Integer32,
				branchActiveEnergy47
					Integer32,
				branchVoltage48
					Integer32,
				branchCurrent48
					Integer32,
				branchActivePower48
					Integer32,
				branchActiveEnergy48
					Integer32,
				branchVoltage49
					Integer32,
				branchCurrent49
					Integer32,
				branchActivePower49
					Integer32,
				branchActiveEnergy49
					Integer32,
				branchVoltage50
					Integer32,
				branchCurrent50
					Integer32,
				branchActivePower50
					Integer32,
				branchActiveEnergy50
					Integer32,
				branchVoltage51
					Integer32,
				branchCurrent51
					Integer32,
				branchActivePower51
					Integer32,
				branchActiveEnergy51
					Integer32,
				branchVoltage52
					Integer32,
				branchCurrent52
					Integer32,
				branchActivePower52
					Integer32,
				branchActiveEnergy52
					Integer32,
				branchVoltage53
					Integer32,
				branchCurrent53
					Integer32,
				branchActivePower53
					Integer32,
				branchActiveEnergy53
					Integer32,
				branchVoltage54
					Integer32,
				branchCurrent54
					Integer32,
				branchActivePower54
					Integer32,
				branchActiveEnergy54
					Integer32,
				branchVoltage55
					Integer32,
				branchCurrent55
					Integer32,
				branchActivePower55
					Integer32,
				branchActiveEnergy55
					Integer32,
				branchVoltage56
					Integer32,
				branchCurrent56
					Integer32,
				branchActivePower56
					Integer32,
				branchActiveEnergy56
					Integer32,
				branchVoltage57
					Integer32,
				branchCurrent57
					Integer32,
				branchActivePower57
					Integer32,
				branchActiveEnergy57
					Integer32,
				branchVoltage58
					Integer32,
				branchCurrent58
					Integer32,
				branchActivePower58
					Integer32,
				branchActiveEnergy58
					Integer32,
				branchVoltage59
					Integer32,
				branchCurrent59
					Integer32,
				branchActivePower59
					Integer32,
				branchActiveEnergy59
					Integer32,
				branchVoltage60
					Integer32,
				branchCurrent60
					Integer32,
				branchActivePower60
					Integer32,
				branchActiveEnergy60
					Integer32,
				branchVoltage61
					Integer32,
				branchCurrent61
					Integer32,
				branchActivePower61
					Integer32,
				branchActiveEnergy61
					Integer32,
				branchVoltage62
					Integer32,
				branchCurrent62
					Integer32,
				branchActivePower62
					Integer32,
				branchActiveEnergy62
					Integer32,
				branchVoltage63
					Integer32,
				branchCurrent63
					Integer32,
				branchActivePower63
					Integer32,
				branchActiveEnergy63
					Integer32,
				branchVoltage64
					Integer32,
				branchCurrent64
					Integer32,
				branchActivePower64
					Integer32,
				branchActiveEnergy64
					Integer32,
				branchVoltage65
					Integer32,
				branchCurrent65
					Integer32,
				branchActivePower65
					Integer32,
				branchActiveEnergy65
					Integer32,
				branchVoltage66
					Integer32,
				branchCurrent66
					Integer32,
				branchActivePower66
					Integer32,
				branchActiveEnergy66
					Integer32,
				branchVoltage67
					Integer32,
				branchCurrent67
					Integer32,
				branchActivePower67
					Integer32,
				branchActiveEnergy67
					Integer32,
				branchVoltage68
					Integer32,
				branchCurrent68
					Integer32,
				branchActivePower68
					Integer32,
				branchActiveEnergy68
					Integer32,
				branchVoltage69
					Integer32,
				branchCurrent69
					Integer32,
				branchActivePower69
					Integer32,
				branchActiveEnergy69
					Integer32,
				branchVoltage70
					Integer32,
				branchCurrent70
					Integer32,
				branchActivePower70
					Integer32,
				branchActiveEnergy70
					Integer32,
				branchVoltage71
					Integer32,
				branchCurrent71
					Integer32,
				branchActivePower71
					Integer32,
				branchActiveEnergy71
					Integer32,
				branchVoltage72
					Integer32,
				branchCurrent72
					Integer32,
				branchActivePower72
					Integer32,
				branchActiveEnergy72
					Integer32,
				branchVoltage73
					Integer32,
				branchCurrent73
					Integer32,
				branchActivePower73
					Integer32,
				branchActiveEnergy73
					Integer32,
				branchVoltage74
					Integer32,
				branchCurrent74
					Integer32,
				branchActivePower74
					Integer32,
				branchActiveEnergy74
					Integer32,
				branchVoltage75
					Integer32,
				branchCurrent75
					Integer32,
				branchActivePower75
					Integer32,
				branchActiveEnergy75
					Integer32,
				branchVoltage76
					Integer32,
				branchCurrent76
					Integer32,
				branchActivePower76
					Integer32,
				branchActiveEnergy76
					Integer32,
				branchVoltage77
					Integer32,
				branchCurrent77
					Integer32,
				branchActivePower77
					Integer32,
				branchActiveEnergy77
					Integer32,
				branchVoltage78
					Integer32,
				branchCurrent78
					Integer32,
				branchActivePower78
					Integer32,
				branchActiveEnergy78
					Integer32,
				branchVoltage79
					Integer32,
				branchCurrent79
					Integer32,
				branchActivePower79
					Integer32,
				branchActiveEnergy79
					Integer32,
				branchVoltage80
					Integer32,
				branchCurrent80
					Integer32,
				branchActivePower80
					Integer32,
				branchActiveEnergy80
					Integer32,
				branchVoltage81
					Integer32,
				branchCurrent81
					Integer32,
				branchActivePower81
					Integer32,
				branchActiveEnergy81
					Integer32,
				branchVoltage82
					Integer32,
				branchCurrent82
					Integer32,
				branchActivePower82
					Integer32,
				branchActiveEnergy82
					Integer32,
				branchVoltage83
					Integer32,
				branchCurrent83
					Integer32,
				branchActivePower83
					Integer32,
				branchActiveEnergy83
					Integer32,
				branchVoltage84
					Integer32,
				branchCurrent84
					Integer32,
				branchActivePower84
					Integer32,
				branchActiveEnergy84
					Integer32,
				branchVoltage85
					Integer32,
				branchCurrent85
					Integer32,
				branchActivePower85
					Integer32,
				branchActiveEnergy85
					Integer32,
				branchVoltage86
					Integer32,
				branchCurrent86
					Integer32,
				branchActivePower86
					Integer32,
				branchActiveEnergy86
					Integer32,
				branchVoltage87
					Integer32,
				branchCurrent87
					Integer32,
				branchActivePower87
					Integer32,
				branchActiveEnergy87
					Integer32,
				branchVoltage88
					Integer32,
				branchCurrent88
					Integer32,
				branchActivePower88
					Integer32,
				branchActiveEnergy88
					Integer32,
				branchVoltage89
					Integer32,
				branchCurrent89
					Integer32,
				branchActivePower89
					Integer32,
				branchActiveEnergy89
					Integer32,
				branchVoltage90
					Integer32,
				branchCurrent90
					Integer32,
				branchActivePower90
					Integer32,
				branchActiveEnergy90
					Integer32,
				branchVoltage91
					Integer32,
				branchCurrent91
					Integer32,
				branchActivePower91
					Integer32,
				branchActiveEnergy91
					Integer32,
				branchVoltage92
					Integer32,
				branchCurrent92
					Integer32,
				branchActivePower92
					Integer32,
				branchActiveEnergy92
					Integer32,
				branchVoltage93
					Integer32,
				branchCurrent93
					Integer32,
				branchActivePower93
					Integer32,
				branchActiveEnergy93
					Integer32,
				branchVoltage94
					Integer32,
				branchCurrent94
					Integer32,
				branchActivePower94
					Integer32,
				branchActiveEnergy94
					Integer32,
				branchVoltage95
					Integer32,
				branchCurrent95
					Integer32,
				branchActivePower95
					Integer32,
				branchActiveEnergy95
					Integer32,
				branchVoltage96
					Integer32,
				branchCurrent96
					Integer32,
				branchActivePower96
					Integer32,
				branchActiveEnergy96
					Integer32,
				branchVoltage97
					Integer32,
				branchCurrent97
					Integer32,
				branchActivePower97
					Integer32,
				branchActiveEnergy97
					Integer32,
				branchVoltage98
					Integer32,
				branchCurrent98
					Integer32,
				branchActivePower98
					Integer32,
				branchActiveEnergy98
					Integer32,
				branchVoltage99
					Integer32,
				branchCurrent99
					Integer32,
				branchActivePower99
					Integer32,
				branchActiveEnergy99
					Integer32,
				branchVoltage100
					Integer32,
				branchCurrent100
					Integer32,
				branchActivePower100
					Integer32,
				branchActiveEnergy100
					Integer32,
				branchVoltage101
					Integer32,
				branchCurrent101
					Integer32,
				branchActivePower101
					Integer32,
				branchActiveEnergy101
					Integer32,
				branchVoltage102
					Integer32,
				branchCurrent102
					Integer32,
				branchActivePower102
					Integer32,
				branchActiveEnergy102
					Integer32,
				branchVoltage103
					Integer32,
				branchCurrent103
					Integer32,
				branchActivePower103
					Integer32,
				branchActiveEnergy103
					Integer32,
				branchVoltage104
					Integer32,
				branchCurrent104
					Integer32,
				branchActivePower104
					Integer32,
				branchActiveEnergy104
					Integer32,
				branchVoltage105
					Integer32,
				branchCurrent105
					Integer32,
				branchActivePower105
					Integer32,
				branchActiveEnergy105
					Integer32,
				branchVoltage106
					Integer32,
				branchCurrent106
					Integer32,
				branchActivePower106
					Integer32,
				branchActiveEnergy106
					Integer32,
				branchVoltage107
					Integer32,
				branchCurrent107
					Integer32,
				branchActivePower107
					Integer32,
				branchActiveEnergy107
					Integer32,
				branchVoltage108
					Integer32,
				branchCurrent108
					Integer32,
				branchActivePower108
					Integer32,
				branchActiveEnergy108
					Integer32
			}	
			-- .1.3.6.1.4.1.39026.3.1.4.1.2.1.1
-- .1.3.6.1.4.1.39026.3.1.4.1.2.1.1
-- .1.3.6.1.4.1.39026.3.1.4.1.2.1.1
-- .1.3.6.1.4.1.39026.3.1.4.1.2.1.1
	pmYdbIndex OBJECT-TYPE
	SYNTAX Integer32
	MAX-ACCESS read-only
	STATUS current
	DESCRIPTION
	"Description: "
	::= { powerMeterAMYDBEntry 1 }

-- .1.3.6.1.4.1.39026.3.1.4.1.2.1.2
-- .1.3.6.1.4.1.39026.3.1.4.1.2.1.2
-- .1.3.6.1.4.1.39026.3.1.4.1.2.1.2
-- .1.3.6.1.4.1.39026.3.1.4.1.2.1.2
	pmYdbEquipOid OBJECT-TYPE
	SYNTAX DisplayString
	MAX-ACCESS read-only
	STATUS current
	DESCRIPTION
	"Description: "
	::= { powerMeterAMYDBEntry 2 }

-- .1.3.6.1.4.1.39026.3.1.4.1.2.1.3
-- .1.3.6.1.4.1.39026.3.1.4.1.2.1.3
-- .1.3.6.1.4.1.39026.3.1.4.1.2.1.3
-- .1.3.6.1.4.1.39026.3.1.4.1.2.1.3
	pmYdbEquipName OBJECT-TYPE
	SYNTAX DisplayString
	MAX-ACCESS read-only
	STATUS current
	DESCRIPTION
	"Description: "
	::= { powerMeterAMYDBEntry 3 }

-- .1.3.6.1.4.1.39026.3.1.4.1.2.1.4
-- .1.3.6.1.4.1.39026.3.1.4.1.2.1.4
-- .1.3.6.1.4.1.39026.3.1.4.1.2.1.4
-- .1.3.6.1.4.1.39026.3.1.4.1.2.1.4
	pmYdbCollectionTime OBJECT-TYPE
	SYNTAX DisplayString
	MAX-ACCESS read-only
	STATUS current
	DESCRIPTION
	"Description: "
	::= { powerMeterAMYDBEntry 4 }

-- .1.3.6.1.4.1.39026.3.1.4.1.2.1.5
-- .1.3.6.1.4.1.39026.3.1.4.1.2.1.5
-- .1.3.6.1.4.1.39026.3.1.4.1.2.1.5
-- .1.3.6.1.4.1.39026.3.1.4.1.2.1.5
	branchVoltage1 OBJECT-TYPE
	SYNTAX Integer32
	MAX-ACCESS read-only
	STATUS current
	DESCRIPTION
	"Description: "
	::= { powerMeterAMYDBEntry 5 }

-- .1.3.6.1.4.1.39026.3.1.4.1.2.1.6
-- .1.3.6.1.4.1.39026.3.1.4.1.2.1.6
-- .1.3.6.1.4.1.39026.3.1.4.1.2.1.6
-- .1.3.6.1.4.1.39026.3.1.4.1.2.1.6
	branchCurrent1 OBJECT-TYPE
	SYNTAX Integer32
	MAX-ACCESS read-only
	STATUS current
	DESCRIPTION
	"Description: "
	::= { powerMeterAMYDBEntry 6 }

-- .1.3.6.1.4.1.39026.3.1.4.1.2.1.7
-- .1.3.6.1.4.1.39026.3.1.4.1.2.1.7
-- .1.3.6.1.4.1.39026.3.1.4.1.2.1.7
-- .1.3.6.1.4.1.39026.3.1.4.1.2.1.7
	branchActivePower1 OBJECT-TYPE
	SYNTAX Integer32
	MAX-ACCESS read-only
	STATUS current
	DESCRIPTION
	"Description: "
	::= { powerMeterAMYDBEntry 7 }

-- .1.3.6.1.4.1.39026.3.1.4.1.2.1.8
-- .1.3.6.1.4.1.39026.3.1.4.1.2.1.8
-- .1.3.6.1.4.1.39026.3.1.4.1.2.1.8
-- .1.3.6.1.4.1.39026.3.1.4.1.2.1.8
	branchActiveEnergy1 OBJECT-TYPE
	SYNTAX Integer32
	MAX-ACCESS read-only
	STATUS current
	DESCRIPTION
	"Description: "
	::= { powerMeterAMYDBEntry 8 }

-- .1.3.6.1.4.1.39026.3.1.4.1.2.1.9
-- .1.3.6.1.4.1.39026.3.1.4.1.2.1.9
-- .1.3.6.1.4.1.39026.3.1.4.1.2.1.9
-- .1.3.6.1.4.1.39026.3.1.4.1.2.1.9
	branchVoltage2 OBJECT-TYPE
	SYNTAX Integer32
	MAX-ACCESS read-only
	STATUS current
	DESCRIPTION
	"Description: "
	::= { powerMeterAMYDBEntry 9 }

-- .1.3.6.1.4.1.39026.3.1.4.1.2.1.10
-- .1.3.6.1.4.1.39026.3.1.4.1.2.1.10
-- .1.3.6.1.4.1.39026.3.1.4.1.2.1.10
-- .1.3.6.1.4.1.39026.3.1.4.1.2.1.10
	branchCurrent2 OBJECT-TYPE
	SYNTAX Integer32
	MAX-ACCESS read-only
	STATUS current
	DESCRIPTION
	"Description: "
	::= { powerMeterAMYDBEntry 10 }

-- .1.3.6.1.4.1.39026.3.1.4.1.2.1.11
-- .1.3.6.1.4.1.39026.3.1.4.1.2.1.11
-- .1.3.6.1.4.1.39026.3.1.4.1.2.1.11
-- .1.3.6.1.4.1.39026.3.1.4.1.2.1.11
	branchActivePower2 OBJECT-TYPE
	SYNTAX Integer32
	MAX-ACCESS read-only
	STATUS current
	DESCRIPTION
	"Description: "
	::= { powerMeterAMYDBEntry 11 }

-- .1.3.6.1.4.1.39026.3.1.4.1.2.1.12
-- .1.3.6.1.4.1.39026.3.1.4.1.2.1.12
-- .1.3.6.1.4.1.39026.3.1.4.1.2.1.12
-- .1.3.6.1.4.1.39026.3.1.4.1.2.1.12
	branchActiveEnergy2 OBJECT-TYPE
	SYNTAX Integer32
	MAX-ACCESS read-only
	STATUS current
	DESCRIPTION
	"Description: "
	::= { powerMeterAMYDBEntry 12 }

-- .1.3.6.1.4.1.39026.3.1.4.1.2.1.13
-- .1.3.6.1.4.1.39026.3.1.4.1.2.1.13
-- .1.3.6.1.4.1.39026.3.1.4.1.2.1.13
-- .1.3.6.1.4.1.39026.3.1.4.1.2.1.13
	branchVoltage3 OBJECT-TYPE
	SYNTAX Integer32
	MAX-ACCESS read-only
	STATUS current
	DESCRIPTION
	"Description: "
	::= { powerMeterAMYDBEntry 13 }

-- .1.3.6.1.4.1.39026.3.1.4.1.2.1.14
-- .1.3.6.1.4.1.39026.3.1.4.1.2.1.14
-- .1.3.6.1.4.1.39026.3.1.4.1.2.1.14
-- .1.3.6.1.4.1.39026.3.1.4.1.2.1.14
	branchCurrent3 OBJECT-TYPE
	SYNTAX Integer32
	MAX-ACCESS read-only
	STATUS current
	DESCRIPTION
	"Description: "
	::= { powerMeterAMYDBEntry 14 }

-- .1.3.6.1.4.1.39026.3.1.4.1.2.1.15
-- .1.3.6.1.4.1.39026.3.1.4.1.2.1.15
-- .1.3.6.1.4.1.39026.3.1.4.1.2.1.15
-- .1.3.6.1.4.1.39026.3.1.4.1.2.1.15
	branchActivePower3 OBJECT-TYPE
	SYNTAX Integer32
	MAX-ACCESS read-only
	STATUS current
	DESCRIPTION
	"Description: "
	::= { powerMeterAMYDBEntry 15 }

-- .1.3.6.1.4.1.39026.3.1.4.1.2.1.16
-- .1.3.6.1.4.1.39026.3.1.4.1.2.1.16
-- .1.3.6.1.4.1.39026.3.1.4.1.2.1.16
-- .1.3.6.1.4.1.39026.3.1.4.1.2.1.16
	branchActiveEnergy3 OBJECT-TYPE
	SYNTAX Integer32
	MAX-ACCESS read-only
	STATUS current
	DESCRIPTION
	"Description: "
	::= { powerMeterAMYDBEntry 16 }

-- .1.3.6.1.4.1.39026.3.1.4.1.2.1.17
-- .1.3.6.1.4.1.39026.3.1.4.1.2.1.17
-- .1.3.6.1.4.1.39026.3.1.4.1.2.1.17
-- .1.3.6.1.4.1.39026.3.1.4.1.2.1.17
	branchVoltage4 OBJECT-TYPE
	SYNTAX Integer32
	MAX-ACCESS read-only
	STATUS current
	DESCRIPTION
	"Description: "
	::= { powerMeterAMYDBEntry 17 }

-- .1.3.6.1.4.1.39026.3.1.4.1.2.1.18
-- .1.3.6.1.4.1.39026.3.1.4.1.2.1.18
-- .1.3.6.1.4.1.39026.3.1.4.1.2.1.18
-- .1.3.6.1.4.1.39026.3.1.4.1.2.1.18
	branchCurrent4 OBJECT-TYPE
	SYNTAX Integer32
	MAX-ACCESS read-only
	STATUS current
	DESCRIPTION
	"Description: "
	::= { powerMeterAMYDBEntry 18 }

-- .1.3.6.1.4.1.39026.3.1.4.1.2.1.19
-- .1.3.6.1.4.1.39026.3.1.4.1.2.1.19
-- .1.3.6.1.4.1.39026.3.1.4.1.2.1.19
-- .1.3.6.1.4.1.39026.3.1.4.1.2.1.19
	branchActivePower4 OBJECT-TYPE
	SYNTAX Integer32
	MAX-ACCESS read-only
	STATUS current
	DESCRIPTION
	"Description: "
	::= { powerMeterAMYDBEntry 19 }

-- .1.3.6.1.4.1.39026.3.1.4.1.2.1.20
-- .1.3.6.1.4.1.39026.3.1.4.1.2.1.20
-- .1.3.6.1.4.1.39026.3.1.4.1.2.1.20
-- .1.3.6.1.4.1.39026.3.1.4.1.2.1.20
	branchActiveEnergy4 OBJECT-TYPE
	SYNTAX Integer32
	MAX-ACCESS read-only
	STATUS current
	DESCRIPTION
	"Description: "
	::= { powerMeterAMYDBEntry 20 }

-- .1.3.6.1.4.1.39026.3.1.4.1.2.1.21
-- .1.3.6.1.4.1.39026.3.1.4.1.2.1.21
-- .1.3.6.1.4.1.39026.3.1.4.1.2.1.21
-- .1.3.6.1.4.1.39026.3.1.4.1.2.1.21
	branchVoltage5 OBJECT-TYPE
	SYNTAX Integer32
	MAX-ACCESS read-only
	STATUS current
	DESCRIPTION
	"Description: "
	::= { powerMeterAMYDBEntry 21 }

-- .1.3.6.1.4.1.39026.3.1.4.1.2.1.22
-- .1.3.6.1.4.1.39026.3.1.4.1.2.1.22
-- .1.3.6.1.4.1.39026.3.1.4.1.2.1.22
-- .1.3.6.1.4.1.39026.3.1.4.1.2.1.22
	branchCurrent5 OBJECT-TYPE
	SYNTAX Integer32
	MAX-ACCESS read-only
	STATUS current
	DESCRIPTION
	"Description: "
	::= { powerMeterAMYDBEntry 22 }

-- .1.3.6.1.4.1.39026.3.1.4.1.2.1.23
-- .1.3.6.1.4.1.39026.3.1.4.1.2.1.23
-- .1.3.6.1.4.1.39026.3.1.4.1.2.1.23
-- .1.3.6.1.4.1.39026.3.1.4.1.2.1.23
	branchActivePower5 OBJECT-TYPE
	SYNTAX Integer32
	MAX-ACCESS read-only
	STATUS current
	DESCRIPTION
	"Description: "
	::= { powerMeterAMYDBEntry 23 }

-- .1.3.6.1.4.1.39026.3.1.4.1.2.1.24
-- .1.3.6.1.4.1.39026.3.1.4.1.2.1.24
-- .1.3.6.1.4.1.39026.3.1.4.1.2.1.24
-- .1.3.6.1.4.1.39026.3.1.4.1.2.1.24
	branchActiveEnergy5 OBJECT-TYPE
	SYNTAX Integer32
	MAX-ACCESS read-only
	STATUS current
	DESCRIPTION
	"Description: "
	::= { powerMeterAMYDBEntry 24 }

-- .1.3.6.1.4.1.39026.3.1.4.1.2.1.25
-- .1.3.6.1.4.1.39026.3.1.4.1.2.1.25
-- .1.3.6.1.4.1.39026.3.1.4.1.2.1.25
-- .1.3.6.1.4.1.39026.3.1.4.1.2.1.25
	branchVoltage6 OBJECT-TYPE
	SYNTAX Integer32
	MAX-ACCESS read-only
	STATUS current
	DESCRIPTION
	"Description: "
	::= { powerMeterAMYDBEntry 25 }

-- .1.3.6.1.4.1.39026.3.1.4.1.2.1.26
-- .1.3.6.1.4.1.39026.3.1.4.1.2.1.26
-- .1.3.6.1.4.1.39026.3.1.4.1.2.1.26
-- .1.3.6.1.4.1.39026.3.1.4.1.2.1.26
	branchCurrent6 OBJECT-TYPE
	SYNTAX Integer32
	MAX-ACCESS read-only
	STATUS current
	DESCRIPTION
	"Description: "
	::= { powerMeterAMYDBEntry 26 }

-- .1.3.6.1.4.1.39026.3.1.4.1.2.1.27
-- .1.3.6.1.4.1.39026.3.1.4.1.2.1.27
-- .1.3.6.1.4.1.39026.3.1.4.1.2.1.27
-- .1.3.6.1.4.1.39026.3.1.4.1.2.1.27
	branchActivePower6 OBJECT-TYPE
	SYNTAX Integer32
	MAX-ACCESS read-only
	STATUS current
	DESCRIPTION
	"Description: "
	::= { powerMeterAMYDBEntry 27 }

-- .1.3.6.1.4.1.39026.3.1.4.1.2.1.28
-- .1.3.6.1.4.1.39026.3.1.4.1.2.1.28
-- .1.3.6.1.4.1.39026.3.1.4.1.2.1.28
-- .1.3.6.1.4.1.39026.3.1.4.1.2.1.28
	branchActiveEnergy6 OBJECT-TYPE
	SYNTAX Integer32
	MAX-ACCESS read-only
	STATUS current
	DESCRIPTION
	"Description: "
	::= { powerMeterAMYDBEntry 28 }

-- .1.3.6.1.4.1.39026.3.1.4.1.2.1.29
-- .1.3.6.1.4.1.39026.3.1.4.1.2.1.29
-- .1.3.6.1.4.1.39026.3.1.4.1.2.1.29
-- .1.3.6.1.4.1.39026.3.1.4.1.2.1.29
	branchVoltage7 OBJECT-TYPE
	SYNTAX Integer32
	MAX-ACCESS read-only
	STATUS current
	DESCRIPTION
	"Description: "
	::= { powerMeterAMYDBEntry 29 }

-- .1.3.6.1.4.1.39026.3.1.4.1.2.1.30
-- .1.3.6.1.4.1.39026.3.1.4.1.2.1.30
-- .1.3.6.1.4.1.39026.3.1.4.1.2.1.30
-- .1.3.6.1.4.1.39026.3.1.4.1.2.1.30
	branchCurrent7 OBJECT-TYPE
	SYNTAX Integer32
	MAX-ACCESS read-only
	STATUS current
	DESCRIPTION
	"Description: "
	::= { powerMeterAMYDBEntry 30 }

-- .1.3.6.1.4.1.39026.3.1.4.1.2.1.31
-- .1.3.6.1.4.1.39026.3.1.4.1.2.1.31
-- .1.3.6.1.4.1.39026.3.1.4.1.2.1.31
-- .1.3.6.1.4.1.39026.3.1.4.1.2.1.31
	branchActivePower7 OBJECT-TYPE
	SYNTAX Integer32
	MAX-ACCESS read-only
	STATUS current
	DESCRIPTION
	"Description: "
	::= { powerMeterAMYDBEntry 31 }

-- .1.3.6.1.4.1.39026.3.1.4.1.2.1.32
-- .1.3.6.1.4.1.39026.3.1.4.1.2.1.32
-- .1.3.6.1.4.1.39026.3.1.4.1.2.1.32
-- .1.3.6.1.4.1.39026.3.1.4.1.2.1.32
	branchActiveEnergy7 OBJECT-TYPE
	SYNTAX Integer32
	MAX-ACCESS read-only
	STATUS current
	DESCRIPTION
	"Description: "
	::= { powerMeterAMYDBEntry 32 }

-- .1.3.6.1.4.1.39026.3.1.4.1.2.1.33
-- .1.3.6.1.4.1.39026.3.1.4.1.2.1.33
-- .1.3.6.1.4.1.39026.3.1.4.1.2.1.33
-- .1.3.6.1.4.1.39026.3.1.4.1.2.1.33
	branchVoltage8 OBJECT-TYPE
	SYNTAX Integer32
	MAX-ACCESS read-only
	STATUS current
	DESCRIPTION
	"Description: "
	::= { powerMeterAMYDBEntry 33 }

-- .1.3.6.1.4.1.39026.3.1.4.1.2.1.34
-- .1.3.6.1.4.1.39026.3.1.4.1.2.1.34
-- .1.3.6.1.4.1.39026.3.1.4.1.2.1.34
-- .1.3.6.1.4.1.39026.3.1.4.1.2.1.34
	branchCurrent8 OBJECT-TYPE
	SYNTAX Integer32
	MAX-ACCESS read-only
	STATUS current
	DESCRIPTION
	"Description: "
	::= { powerMeterAMYDBEntry 34 }

-- .1.3.6.1.4.1.39026.3.1.4.1.2.1.35
-- .1.3.6.1.4.1.39026.3.1.4.1.2.1.35
-- .1.3.6.1.4.1.39026.3.1.4.1.2.1.35
-- .1.3.6.1.4.1.39026.3.1.4.1.2.1.35
	branchActivePower8 OBJECT-TYPE
	SYNTAX Integer32
	MAX-ACCESS read-only
	STATUS current
	DESCRIPTION
	"Description: "
	::= { powerMeterAMYDBEntry 35 }

-- .1.3.6.1.4.1.39026.3.1.4.1.2.1.36
-- .1.3.6.1.4.1.39026.3.1.4.1.2.1.36
-- .1.3.6.1.4.1.39026.3.1.4.1.2.1.36
-- .1.3.6.1.4.1.39026.3.1.4.1.2.1.36
	branchActiveEnergy8 OBJECT-TYPE
	SYNTAX Integer32
	MAX-ACCESS read-only
	STATUS current
	DESCRIPTION
	"Description: "
	::= { powerMeterAMYDBEntry 36 }

-- .1.3.6.1.4.1.39026.3.1.4.1.2.1.37
-- .1.3.6.1.4.1.39026.3.1.4.1.2.1.37
-- .1.3.6.1.4.1.39026.3.1.4.1.2.1.37
-- .1.3.6.1.4.1.39026.3.1.4.1.2.1.37
	branchVoltage9 OBJECT-TYPE
	SYNTAX Integer32
	MAX-ACCESS read-only
	STATUS current
	DESCRIPTION
	"Description: "
	::= { powerMeterAMYDBEntry 37 }

-- .1.3.6.1.4.1.39026.3.1.4.1.2.1.38
-- .1.3.6.1.4.1.39026.3.1.4.1.2.1.38
-- .1.3.6.1.4.1.39026.3.1.4.1.2.1.38
-- .1.3.6.1.4.1.39026.3.1.4.1.2.1.38
	branchCurrent9 OBJECT-TYPE
	SYNTAX Integer32
	MAX-ACCESS read-only
	STATUS current
	DESCRIPTION
	"Description: "
	::= { powerMeterAMYDBEntry 38 }

-- .1.3.6.1.4.1.39026.3.1.4.1.2.1.39
-- .1.3.6.1.4.1.39026.3.1.4.1.2.1.39
-- .1.3.6.1.4.1.39026.3.1.4.1.2.1.39
-- .1.3.6.1.4.1.39026.3.1.4.1.2.1.39
	branchActivePower9 OBJECT-TYPE
	SYNTAX Integer32
	MAX-ACCESS read-only
	STATUS current
	DESCRIPTION
	"Description: "
	::= { powerMeterAMYDBEntry 39 }

-- .1.3.6.1.4.1.39026.3.1.4.1.2.1.40
-- .1.3.6.1.4.1.39026.3.1.4.1.2.1.40
-- .1.3.6.1.4.1.39026.3.1.4.1.2.1.40
-- .1.3.6.1.4.1.39026.3.1.4.1.2.1.40
	branchActiveEnergy9 OBJECT-TYPE
	SYNTAX Integer32
	MAX-ACCESS read-only
	STATUS current
	DESCRIPTION
	"Description: "
	::= { powerMeterAMYDBEntry 40 }

-- .1.3.6.1.4.1.39026.3.1.4.1.2.1.41
-- .1.3.6.1.4.1.39026.3.1.4.1.2.1.41
-- .1.3.6.1.4.1.39026.3.1.4.1.2.1.41
-- .1.3.6.1.4.1.39026.3.1.4.1.2.1.41
	branchVoltage10 OBJECT-TYPE
	SYNTAX Integer32
	MAX-ACCESS read-only
	STATUS current
	DESCRIPTION
	"Description: "
	::= { powerMeterAMYDBEntry 41 }

-- .1.3.6.1.4.1.39026.3.1.4.1.2.1.42
-- .1.3.6.1.4.1.39026.3.1.4.1.2.1.42
-- .1.3.6.1.4.1.39026.3.1.4.1.2.1.42
-- .1.3.6.1.4.1.39026.3.1.4.1.2.1.42
	branchCurrent10 OBJECT-TYPE
	SYNTAX Integer32
	MAX-ACCESS read-only
	STATUS current
	DESCRIPTION
	"Description: "
	::= { powerMeterAMYDBEntry 42 }

-- .1.3.6.1.4.1.39026.3.1.4.1.2.1.43
-- .1.3.6.1.4.1.39026.3.1.4.1.2.1.43
-- .1.3.6.1.4.1.39026.3.1.4.1.2.1.43
-- .1.3.6.1.4.1.39026.3.1.4.1.2.1.43
	branchActivePower10 OBJECT-TYPE
	SYNTAX Integer32
	MAX-ACCESS read-only
	STATUS current
	DESCRIPTION
	"Description: "
	::= { powerMeterAMYDBEntry 43 }

-- .1.3.6.1.4.1.39026.3.1.4.1.2.1.44
-- .1.3.6.1.4.1.39026.3.1.4.1.2.1.44
-- .1.3.6.1.4.1.39026.3.1.4.1.2.1.44
-- .1.3.6.1.4.1.39026.3.1.4.1.2.1.44
	branchActiveEnergy10 OBJECT-TYPE
	SYNTAX Integer32
	MAX-ACCESS read-only
	STATUS current
	DESCRIPTION
	"Description: "
	::= { powerMeterAMYDBEntry 44 }

-- .1.3.6.1.4.1.39026.3.1.4.1.2.1.45
-- .1.3.6.1.4.1.39026.3.1.4.1.2.1.45
-- .1.3.6.1.4.1.39026.3.1.4.1.2.1.45
-- .1.3.6.1.4.1.39026.3.1.4.1.2.1.45
	branchVoltage11 OBJECT-TYPE
	SYNTAX Integer32
	MAX-ACCESS read-only
	STATUS current
	DESCRIPTION
	"Description: "
	::= { powerMeterAMYDBEntry 45 }

-- .1.3.6.1.4.1.39026.3.1.4.1.2.1.46
-- .1.3.6.1.4.1.39026.3.1.4.1.2.1.46
-- .1.3.6.1.4.1.39026.3.1.4.1.2.1.46
-- .1.3.6.1.4.1.39026.3.1.4.1.2.1.46
	branchCurrent11 OBJECT-TYPE
	SYNTAX Integer32
	MAX-ACCESS read-only
	STATUS current
	DESCRIPTION
	"Description: "
	::= { powerMeterAMYDBEntry 46 }

-- .1.3.6.1.4.1.39026.3.1.4.1.2.1.47
-- .1.3.6.1.4.1.39026.3.1.4.1.2.1.47
-- .1.3.6.1.4.1.39026.3.1.4.1.2.1.47
-- .1.3.6.1.4.1.39026.3.1.4.1.2.1.47
	branchActivePower11 OBJECT-TYPE
	SYNTAX Integer32
	MAX-ACCESS read-only
	STATUS current
	DESCRIPTION
	"Description: "
	::= { powerMeterAMYDBEntry 47 }

-- .1.3.6.1.4.1.39026.3.1.4.1.2.1.48
-- .1.3.6.1.4.1.39026.3.1.4.1.2.1.48
-- .1.3.6.1.4.1.39026.3.1.4.1.2.1.48
-- .1.3.6.1.4.1.39026.3.1.4.1.2.1.48
	branchActiveEnergy11 OBJECT-TYPE
	SYNTAX Integer32
	MAX-ACCESS read-only
	STATUS current
	DESCRIPTION
	"Description: "
	::= { powerMeterAMYDBEntry 48 }

-- .1.3.6.1.4.1.39026.3.1.4.1.2.1.49
-- .1.3.6.1.4.1.39026.3.1.4.1.2.1.49
-- .1.3.6.1.4.1.39026.3.1.4.1.2.1.49
-- .1.3.6.1.4.1.39026.3.1.4.1.2.1.49
	branchVoltage12 OBJECT-TYPE
	SYNTAX Integer32
	MAX-ACCESS read-only
	STATUS current
	DESCRIPTION
	"Description: "
	::= { powerMeterAMYDBEntry 49 }

-- .1.3.6.1.4.1.39026.3.1.4.1.2.1.50
-- .1.3.6.1.4.1.39026.3.1.4.1.2.1.50
-- .1.3.6.1.4.1.39026.3.1.4.1.2.1.50
-- .1.3.6.1.4.1.39026.3.1.4.1.2.1.50
	branchCurrent12 OBJECT-TYPE
	SYNTAX Integer32
	MAX-ACCESS read-only
	STATUS current
	DESCRIPTION
	"Description: "
	::= { powerMeterAMYDBEntry 50 }

-- .1.3.6.1.4.1.39026.3.1.4.1.2.1.51
-- .1.3.6.1.4.1.39026.3.1.4.1.2.1.51
-- .1.3.6.1.4.1.39026.3.1.4.1.2.1.51
-- .1.3.6.1.4.1.39026.3.1.4.1.2.1.51
	branchActivePower12 OBJECT-TYPE
	SYNTAX Integer32
	MAX-ACCESS read-only
	STATUS current
	DESCRIPTION
	"Description: "
	::= { powerMeterAMYDBEntry 51 }

-- .1.3.6.1.4.1.39026.3.1.4.1.2.1.52
-- .1.3.6.1.4.1.39026.3.1.4.1.2.1.52
-- .1.3.6.1.4.1.39026.3.1.4.1.2.1.52
-- .1.3.6.1.4.1.39026.3.1.4.1.2.1.52
	branchActiveEnergy12 OBJECT-TYPE
	SYNTAX Integer32
	MAX-ACCESS read-only
	STATUS current
	DESCRIPTION
	"Description: "
	::= { powerMeterAMYDBEntry 52 }

-- .1.3.6.1.4.1.39026.3.1.4.1.2.1.53
-- .1.3.6.1.4.1.39026.3.1.4.1.2.1.53
-- .1.3.6.1.4.1.39026.3.1.4.1.2.1.53
-- .1.3.6.1.4.1.39026.3.1.4.1.2.1.53
	branchVoltage13 OBJECT-TYPE
	SYNTAX Integer32
	MAX-ACCESS read-only
	STATUS current
	DESCRIPTION
	"Description: "
	::= { powerMeterAMYDBEntry 53 }

-- .1.3.6.1.4.1.39026.3.1.4.1.2.1.54
-- .1.3.6.1.4.1.39026.3.1.4.1.2.1.54
-- .1.3.6.1.4.1.39026.3.1.4.1.2.1.54
-- .1.3.6.1.4.1.39026.3.1.4.1.2.1.54
	branchCurrent13 OBJECT-TYPE
	SYNTAX Integer32
	MAX-ACCESS read-only
	STATUS current
	DESCRIPTION
	"Description: "
	::= { powerMeterAMYDBEntry 54 }

-- .1.3.6.1.4.1.39026.3.1.4.1.2.1.55
-- .1.3.6.1.4.1.39026.3.1.4.1.2.1.55
-- .1.3.6.1.4.1.39026.3.1.4.1.2.1.55
-- .1.3.6.1.4.1.39026.3.1.4.1.2.1.55
	branchActivePower13 OBJECT-TYPE
	SYNTAX Integer32
	MAX-ACCESS read-only
	STATUS current
	DESCRIPTION
	"Description: "
	::= { powerMeterAMYDBEntry 55 }

-- .1.3.6.1.4.1.39026.3.1.4.1.2.1.56
-- .1.3.6.1.4.1.39026.3.1.4.1.2.1.56
-- .1.3.6.1.4.1.39026.3.1.4.1.2.1.56
-- .1.3.6.1.4.1.39026.3.1.4.1.2.1.56
	branchActiveEnergy13 OBJECT-TYPE
	SYNTAX Integer32
	MAX-ACCESS read-only
	STATUS current
	DESCRIPTION
	"Description: "
	::= { powerMeterAMYDBEntry 56 }

-- .1.3.6.1.4.1.39026.3.1.4.1.2.1.57
-- .1.3.6.1.4.1.39026.3.1.4.1.2.1.57
-- .1.3.6.1.4.1.39026.3.1.4.1.2.1.57
-- .1.3.6.1.4.1.39026.3.1.4.1.2.1.57
	branchVoltage14 OBJECT-TYPE
	SYNTAX Integer32
	MAX-ACCESS read-only
	STATUS current
	DESCRIPTION
	"Description: "
	::= { powerMeterAMYDBEntry 57 }

-- .1.3.6.1.4.1.39026.3.1.4.1.2.1.58
-- .1.3.6.1.4.1.39026.3.1.4.1.2.1.58
-- .1.3.6.1.4.1.39026.3.1.4.1.2.1.58
-- .1.3.6.1.4.1.39026.3.1.4.1.2.1.58
	branchCurrent14 OBJECT-TYPE
	SYNTAX Integer32
	MAX-ACCESS read-only
	STATUS current
	DESCRIPTION
	"Description: "
	::= { powerMeterAMYDBEntry 58 }

-- .1.3.6.1.4.1.39026.3.1.4.1.2.1.59
-- .1.3.6.1.4.1.39026.3.1.4.1.2.1.59
-- .1.3.6.1.4.1.39026.3.1.4.1.2.1.59
-- .1.3.6.1.4.1.39026.3.1.4.1.2.1.59
	branchActivePower14 OBJECT-TYPE
	SYNTAX Integer32
	MAX-ACCESS read-only
	STATUS current
	DESCRIPTION
	"Description: "
	::= { powerMeterAMYDBEntry 59 }

-- .1.3.6.1.4.1.39026.3.1.4.1.2.1.60
-- .1.3.6.1.4.1.39026.3.1.4.1.2.1.60
-- .1.3.6.1.4.1.39026.3.1.4.1.2.1.60
-- .1.3.6.1.4.1.39026.3.1.4.1.2.1.60
	branchActiveEnergy14 OBJECT-TYPE
	SYNTAX Integer32
	MAX-ACCESS read-only
	STATUS current
	DESCRIPTION
	"Description: "
	::= { powerMeterAMYDBEntry 60 }

-- .1.3.6.1.4.1.39026.3.1.4.1.2.1.61
-- .1.3.6.1.4.1.39026.3.1.4.1.2.1.61
-- .1.3.6.1.4.1.39026.3.1.4.1.2.1.61
-- .1.3.6.1.4.1.39026.3.1.4.1.2.1.61
	branchVoltage15 OBJECT-TYPE
	SYNTAX Integer32
	MAX-ACCESS read-only
	STATUS current
	DESCRIPTION
	"Description: "
	::= { powerMeterAMYDBEntry 61 }

-- .1.3.6.1.4.1.39026.3.1.4.1.2.1.62
-- .1.3.6.1.4.1.39026.3.1.4.1.2.1.62
-- .1.3.6.1.4.1.39026.3.1.4.1.2.1.62
-- .1.3.6.1.4.1.39026.3.1.4.1.2.1.62
	branchCurrent15 OBJECT-TYPE
	SYNTAX Integer32
	MAX-ACCESS read-only
	STATUS current
	DESCRIPTION
	"Description: "
	::= { powerMeterAMYDBEntry 62 }

-- .1.3.6.1.4.1.39026.3.1.4.1.2.1.63
-- .1.3.6.1.4.1.39026.3.1.4.1.2.1.63
-- .1.3.6.1.4.1.39026.3.1.4.1.2.1.63
-- .1.3.6.1.4.1.39026.3.1.4.1.2.1.63
	branchActivePower15 OBJECT-TYPE
	SYNTAX Integer32
	MAX-ACCESS read-only
	STATUS current
	DESCRIPTION
	"Description: "
	::= { powerMeterAMYDBEntry 63 }

-- .1.3.6.1.4.1.39026.3.1.4.1.2.1.64
-- .1.3.6.1.4.1.39026.3.1.4.1.2.1.64
-- .1.3.6.1.4.1.39026.3.1.4.1.2.1.64
-- .1.3.6.1.4.1.39026.3.1.4.1.2.1.64
	branchActiveEnergy15 OBJECT-TYPE
	SYNTAX Integer32
	MAX-ACCESS read-only
	STATUS current
	DESCRIPTION
	"Description: "
	::= { powerMeterAMYDBEntry 64 }

-- .1.3.6.1.4.1.39026.3.1.4.1.2.1.65
-- .1.3.6.1.4.1.39026.3.1.4.1.2.1.65
-- .1.3.6.1.4.1.39026.3.1.4.1.2.1.65
-- .1.3.6.1.4.1.39026.3.1.4.1.2.1.65
	branchVoltage16 OBJECT-TYPE
	SYNTAX Integer32
	MAX-ACCESS read-only
	STATUS current
	DESCRIPTION
	"Description: "
	::= { powerMeterAMYDBEntry 65 }

-- .1.3.6.1.4.1.39026.3.1.4.1.2.1.66
-- .1.3.6.1.4.1.39026.3.1.4.1.2.1.66
-- .1.3.6.1.4.1.39026.3.1.4.1.2.1.66
-- .1.3.6.1.4.1.39026.3.1.4.1.2.1.66
	branchCurrent16 OBJECT-TYPE
	SYNTAX Integer32
	MAX-ACCESS read-only
	STATUS current
	DESCRIPTION
	"Description: "
	::= { powerMeterAMYDBEntry 66 }

-- .1.3.6.1.4.1.39026.3.1.4.1.2.1.67
-- .1.3.6.1.4.1.39026.3.1.4.1.2.1.67
-- .1.3.6.1.4.1.39026.3.1.4.1.2.1.67
-- .1.3.6.1.4.1.39026.3.1.4.1.2.1.67
	branchActivePower16 OBJECT-TYPE
	SYNTAX Integer32
	MAX-ACCESS read-only
	STATUS current
	DESCRIPTION
	"Description: "
	::= { powerMeterAMYDBEntry 67 }

-- .1.3.6.1.4.1.39026.3.1.4.1.2.1.68
-- .1.3.6.1.4.1.39026.3.1.4.1.2.1.68
-- .1.3.6.1.4.1.39026.3.1.4.1.2.1.68
-- .1.3.6.1.4.1.39026.3.1.4.1.2.1.68
	branchActiveEnergy16 OBJECT-TYPE
	SYNTAX Integer32
	MAX-ACCESS read-only
	STATUS current
	DESCRIPTION
	"Description: "
	::= { powerMeterAMYDBEntry 68 }

-- .1.3.6.1.4.1.39026.3.1.4.1.2.1.69
-- .1.3.6.1.4.1.39026.3.1.4.1.2.1.69
-- .1.3.6.1.4.1.39026.3.1.4.1.2.1.69
-- .1.3.6.1.4.1.39026.3.1.4.1.2.1.69
	branchVoltage17 OBJECT-TYPE
	SYNTAX Integer32
	MAX-ACCESS read-only
	STATUS current
	DESCRIPTION
	"Description: "
	::= { powerMeterAMYDBEntry 69 }

-- .1.3.6.1.4.1.39026.3.1.4.1.2.1.70
-- .1.3.6.1.4.1.39026.3.1.4.1.2.1.70
-- .1.3.6.1.4.1.39026.3.1.4.1.2.1.70
-- .1.3.6.1.4.1.39026.3.1.4.1.2.1.70
	branchCurrent17 OBJECT-TYPE
	SYNTAX Integer32
	MAX-ACCESS read-only
	STATUS current
	DESCRIPTION
	"Description: "
	::= { powerMeterAMYDBEntry 70 }

-- .1.3.6.1.4.1.39026.3.1.4.1.2.1.71
-- .1.3.6.1.4.1.39026.3.1.4.1.2.1.71
-- .1.3.6.1.4.1.39026.3.1.4.1.2.1.71
-- .1.3.6.1.4.1.39026.3.1.4.1.2.1.71
	branchActivePower17 OBJECT-TYPE
	SYNTAX Integer32
	MAX-ACCESS read-only
	STATUS current
	DESCRIPTION
	"Description: "
	::= { powerMeterAMYDBEntry 71 }

-- .1.3.6.1.4.1.39026.3.1.4.1.2.1.72
-- .1.3.6.1.4.1.39026.3.1.4.1.2.1.72
-- .1.3.6.1.4.1.39026.3.1.4.1.2.1.72
-- .1.3.6.1.4.1.39026.3.1.4.1.2.1.72
	branchActiveEnergy17 OBJECT-TYPE
	SYNTAX Integer32
	MAX-ACCESS read-only
	STATUS current
	DESCRIPTION
	"Description: "
	::= { powerMeterAMYDBEntry 72 }

-- .1.3.6.1.4.1.39026.3.1.4.1.2.1.73
-- .1.3.6.1.4.1.39026.3.1.4.1.2.1.73
-- .1.3.6.1.4.1.39026.3.1.4.1.2.1.73
-- .1.3.6.1.4.1.39026.3.1.4.1.2.1.73
	branchVoltage18 OBJECT-TYPE
	SYNTAX Integer32
	MAX-ACCESS read-only
	STATUS current
	DESCRIPTION
	"Description: "
	::= { powerMeterAMYDBEntry 73 }

-- .1.3.6.1.4.1.39026.3.1.4.1.2.1.74
-- .1.3.6.1.4.1.39026.3.1.4.1.2.1.74
-- .1.3.6.1.4.1.39026.3.1.4.1.2.1.74
-- .1.3.6.1.4.1.39026.3.1.4.1.2.1.74
	branchCurrent18 OBJECT-TYPE
	SYNTAX Integer32
	MAX-ACCESS read-only
	STATUS current
	DESCRIPTION
	"Description: "
	::= { powerMeterAMYDBEntry 74 }

-- .1.3.6.1.4.1.39026.3.1.4.1.2.1.75
-- .1.3.6.1.4.1.39026.3.1.4.1.2.1.75
-- .1.3.6.1.4.1.39026.3.1.4.1.2.1.75
-- .1.3.6.1.4.1.39026.3.1.4.1.2.1.75
	branchActivePower18 OBJECT-TYPE
	SYNTAX Integer32
	MAX-ACCESS read-only
	STATUS current
	DESCRIPTION
	"Description: "
	::= { powerMeterAMYDBEntry 75 }

-- .1.3.6.1.4.1.39026.3.1.4.1.2.1.76
-- .1.3.6.1.4.1.39026.3.1.4.1.2.1.76
-- .1.3.6.1.4.1.39026.3.1.4.1.2.1.76
-- .1.3.6.1.4.1.39026.3.1.4.1.2.1.76
	branchActiveEnergy18 OBJECT-TYPE
	SYNTAX Integer32
	MAX-ACCESS read-only
	STATUS current
	DESCRIPTION
	"Description: "
	::= { powerMeterAMYDBEntry 76 }

-- .1.3.6.1.4.1.39026.3.1.4.1.2.1.77
-- .1.3.6.1.4.1.39026.3.1.4.1.2.1.77
-- .1.3.6.1.4.1.39026.3.1.4.1.2.1.77
-- .1.3.6.1.4.1.39026.3.1.4.1.2.1.77
	branchVoltage19 OBJECT-TYPE
	SYNTAX Integer32
	MAX-ACCESS read-only
	STATUS current
	DESCRIPTION
	"Description: "
	::= { powerMeterAMYDBEntry 77 }

-- .1.3.6.1.4.1.39026.3.1.4.1.2.1.78
-- .1.3.6.1.4.1.39026.3.1.4.1.2.1.78
-- .1.3.6.1.4.1.39026.3.1.4.1.2.1.78
-- .1.3.6.1.4.1.39026.3.1.4.1.2.1.78
	branchCurrent19 OBJECT-TYPE
	SYNTAX Integer32
	MAX-ACCESS read-only
	STATUS current
	DESCRIPTION
	"Description: "
	::= { powerMeterAMYDBEntry 78 }

-- .1.3.6.1.4.1.39026.3.1.4.1.2.1.79
-- .1.3.6.1.4.1.39026.3.1.4.1.2.1.79
-- .1.3.6.1.4.1.39026.3.1.4.1.2.1.79
-- .1.3.6.1.4.1.39026.3.1.4.1.2.1.79
	branchActivePower19 OBJECT-TYPE
	SYNTAX Integer32
	MAX-ACCESS read-only
	STATUS current
	DESCRIPTION
	"Description: "
	::= { powerMeterAMYDBEntry 79 }

-- .1.3.6.1.4.1.39026.3.1.4.1.2.1.80
-- .1.3.6.1.4.1.39026.3.1.4.1.2.1.80
-- .1.3.6.1.4.1.39026.3.1.4.1.2.1.80
-- .1.3.6.1.4.1.39026.3.1.4.1.2.1.80
	branchActiveEnergy19 OBJECT-TYPE
	SYNTAX Integer32
	MAX-ACCESS read-only
	STATUS current
	DESCRIPTION
	"Description: "
	::= { powerMeterAMYDBEntry 80 }

-- .1.3.6.1.4.1.39026.3.1.4.1.2.1.81
-- .1.3.6.1.4.1.39026.3.1.4.1.2.1.81
-- .1.3.6.1.4.1.39026.3.1.4.1.2.1.81
-- .1.3.6.1.4.1.39026.3.1.4.1.2.1.81
	branchVoltage20 OBJECT-TYPE
	SYNTAX Integer32
	MAX-ACCESS read-only
	STATUS current
	DESCRIPTION
	"Description: "
	::= { powerMeterAMYDBEntry 81 }

-- .1.3.6.1.4.1.39026.3.1.4.1.2.1.82
-- .1.3.6.1.4.1.39026.3.1.4.1.2.1.82
-- .1.3.6.1.4.1.39026.3.1.4.1.2.1.82
-- .1.3.6.1.4.1.39026.3.1.4.1.2.1.82
	branchCurrent20 OBJECT-TYPE
	SYNTAX Integer32
	MAX-ACCESS read-only
	STATUS current
	DESCRIPTION
	"Description: "
	::= { powerMeterAMYDBEntry 82 }

-- .1.3.6.1.4.1.39026.3.1.4.1.2.1.83
-- .1.3.6.1.4.1.39026.3.1.4.1.2.1.83
-- .1.3.6.1.4.1.39026.3.1.4.1.2.1.83
-- .1.3.6.1.4.1.39026.3.1.4.1.2.1.83
	branchActivePower20 OBJECT-TYPE
	SYNTAX Integer32
	MAX-ACCESS read-only
	STATUS current
	DESCRIPTION
	"Description: "
	::= { powerMeterAMYDBEntry 83 }

-- .1.3.6.1.4.1.39026.3.1.4.1.2.1.84
-- .1.3.6.1.4.1.39026.3.1.4.1.2.1.84
-- .1.3.6.1.4.1.39026.3.1.4.1.2.1.84
-- .1.3.6.1.4.1.39026.3.1.4.1.2.1.84
	branchActiveEnergy20 OBJECT-TYPE
	SYNTAX Integer32
	MAX-ACCESS read-only
	STATUS current
	DESCRIPTION
	"Description: "
	::= { powerMeterAMYDBEntry 84 }

-- .1.3.6.1.4.1.39026.3.1.4.1.2.1.85
-- .1.3.6.1.4.1.39026.3.1.4.1.2.1.85
-- .1.3.6.1.4.1.39026.3.1.4.1.2.1.85
-- .1.3.6.1.4.1.39026.3.1.4.1.2.1.85
	branchVoltage21 OBJECT-TYPE
	SYNTAX Integer32
	MAX-ACCESS read-only
	STATUS current
	DESCRIPTION
	"Description: "
	::= { powerMeterAMYDBEntry 85 }

-- .1.3.6.1.4.1.39026.3.1.4.1.2.1.86
-- .1.3.6.1.4.1.39026.3.1.4.1.2.1.86
-- .1.3.6.1.4.1.39026.3.1.4.1.2.1.86
-- .1.3.6.1.4.1.39026.3.1.4.1.2.1.86
	branchCurrent21 OBJECT-TYPE
	SYNTAX Integer32
	MAX-ACCESS read-only
	STATUS current
	DESCRIPTION
	"Description: "
	::= { powerMeterAMYDBEntry 86 }

-- .1.3.6.1.4.1.39026.3.1.4.1.2.1.87
-- .1.3.6.1.4.1.39026.3.1.4.1.2.1.87
-- .1.3.6.1.4.1.39026.3.1.4.1.2.1.87
-- .1.3.6.1.4.1.39026.3.1.4.1.2.1.87
	branchActivePower21 OBJECT-TYPE
	SYNTAX Integer32
	MAX-ACCESS read-only
	STATUS current
	DESCRIPTION
	"Description: "
	::= { powerMeterAMYDBEntry 87 }

-- .1.3.6.1.4.1.39026.3.1.4.1.2.1.88
-- .1.3.6.1.4.1.39026.3.1.4.1.2.1.88
-- .1.3.6.1.4.1.39026.3.1.4.1.2.1.88
-- .1.3.6.1.4.1.39026.3.1.4.1.2.1.88
	branchActiveEnergy21 OBJECT-TYPE
	SYNTAX Integer32
	MAX-ACCESS read-only
	STATUS current
	DESCRIPTION
	"Description: "
	::= { powerMeterAMYDBEntry 88 }

-- .1.3.6.1.4.1.39026.3.1.4.1.2.1.89
-- .1.3.6.1.4.1.39026.3.1.4.1.2.1.89
-- .1.3.6.1.4.1.39026.3.1.4.1.2.1.89
-- .1.3.6.1.4.1.39026.3.1.4.1.2.1.89
	branchVoltage22 OBJECT-TYPE
	SYNTAX Integer32
	MAX-ACCESS read-only
	STATUS current
	DESCRIPTION
	"Description: "
	::= { powerMeterAMYDBEntry 89 }

-- .1.3.6.1.4.1.39026.3.1.4.1.2.1.90
-- .1.3.6.1.4.1.39026.3.1.4.1.2.1.90
-- .1.3.6.1.4.1.39026.3.1.4.1.2.1.90
-- .1.3.6.1.4.1.39026.3.1.4.1.2.1.90
	branchCurrent22 OBJECT-TYPE
	SYNTAX Integer32
	MAX-ACCESS read-only
	STATUS current
	DESCRIPTION
	"Description: "
	::= { powerMeterAMYDBEntry 90 }

-- .1.3.6.1.4.1.39026.3.1.4.1.2.1.91
-- .1.3.6.1.4.1.39026.3.1.4.1.2.1.91
-- .1.3.6.1.4.1.39026.3.1.4.1.2.1.91
-- .1.3.6.1.4.1.39026.3.1.4.1.2.1.91
	branchActivePower22 OBJECT-TYPE
	SYNTAX Integer32
	MAX-ACCESS read-only
	STATUS current
	DESCRIPTION
	"Description: "
	::= { powerMeterAMYDBEntry 91 }

-- .1.3.6.1.4.1.39026.3.1.4.1.2.1.92
-- .1.3.6.1.4.1.39026.3.1.4.1.2.1.92
-- .1.3.6.1.4.1.39026.3.1.4.1.2.1.92
-- .1.3.6.1.4.1.39026.3.1.4.1.2.1.92
	branchActiveEnergy22 OBJECT-TYPE
	SYNTAX Integer32
	MAX-ACCESS read-only
	STATUS current
	DESCRIPTION
	"Description: "
	::= { powerMeterAMYDBEntry 92 }

-- .1.3.6.1.4.1.39026.3.1.4.1.2.1.93
-- .1.3.6.1.4.1.39026.3.1.4.1.2.1.93
-- .1.3.6.1.4.1.39026.3.1.4.1.2.1.93
-- .1.3.6.1.4.1.39026.3.1.4.1.2.1.93
	branchVoltage23 OBJECT-TYPE
	SYNTAX Integer32
	MAX-ACCESS read-only
	STATUS current
	DESCRIPTION
	"Description: "
	::= { powerMeterAMYDBEntry 93 }

-- .1.3.6.1.4.1.39026.3.1.4.1.2.1.94
-- .1.3.6.1.4.1.39026.3.1.4.1.2.1.94
-- .1.3.6.1.4.1.39026.3.1.4.1.2.1.94
-- .1.3.6.1.4.1.39026.3.1.4.1.2.1.94
	branchCurrent23 OBJECT-TYPE
	SYNTAX Integer32
	MAX-ACCESS read-only
	STATUS current
	DESCRIPTION
	"Description: "
	::= { powerMeterAMYDBEntry 94 }

-- .1.3.6.1.4.1.39026.3.1.4.1.2.1.95
-- .1.3.6.1.4.1.39026.3.1.4.1.2.1.95
-- .1.3.6.1.4.1.39026.3.1.4.1.2.1.95
-- .1.3.6.1.4.1.39026.3.1.4.1.2.1.95
	branchActivePower23 OBJECT-TYPE
	SYNTAX Integer32
	MAX-ACCESS read-only
	STATUS current
	DESCRIPTION
	"Description: "
	::= { powerMeterAMYDBEntry 95 }

-- .1.3.6.1.4.1.39026.3.1.4.1.2.1.96
-- .1.3.6.1.4.1.39026.3.1.4.1.2.1.96
-- .1.3.6.1.4.1.39026.3.1.4.1.2.1.96
-- .1.3.6.1.4.1.39026.3.1.4.1.2.1.96
	branchActiveEnergy23 OBJECT-TYPE
	SYNTAX Integer32
	MAX-ACCESS read-only
	STATUS current
	DESCRIPTION
	"Description: "
	::= { powerMeterAMYDBEntry 96 }

-- .1.3.6.1.4.1.39026.3.1.4.1.2.1.97
-- .1.3.6.1.4.1.39026.3.1.4.1.2.1.97
-- .1.3.6.1.4.1.39026.3.1.4.1.2.1.97
-- .1.3.6.1.4.1.39026.3.1.4.1.2.1.97
	branchVoltage24 OBJECT-TYPE
	SYNTAX Integer32
	MAX-ACCESS read-only
	STATUS current
	DESCRIPTION
	"Description: "
	::= { powerMeterAMYDBEntry 97 }

-- .1.3.6.1.4.1.39026.3.1.4.1.2.1.98
-- .1.3.6.1.4.1.39026.3.1.4.1.2.1.98
-- .1.3.6.1.4.1.39026.3.1.4.1.2.1.98
-- .1.3.6.1.4.1.39026.3.1.4.1.2.1.98
	branchCurrent24 OBJECT-TYPE
	SYNTAX Integer32
	MAX-ACCESS read-only
	STATUS current
	DESCRIPTION
	"Description: "
	::= { powerMeterAMYDBEntry 98 }

-- .1.3.6.1.4.1.39026.3.1.4.1.2.1.99
-- .1.3.6.1.4.1.39026.3.1.4.1.2.1.99
-- .1.3.6.1.4.1.39026.3.1.4.1.2.1.99
-- .1.3.6.1.4.1.39026.3.1.4.1.2.1.99
	branchActivePower24 OBJECT-TYPE
	SYNTAX Integer32
	MAX-ACCESS read-only
	STATUS current
	DESCRIPTION
	"Description: "
	::= { powerMeterAMYDBEntry 99 }

-- .1.3.6.1.4.1.39026.3.1.4.1.2.1.100
-- .1.3.6.1.4.1.39026.3.1.4.1.2.1.100
-- .1.3.6.1.4.1.39026.3.1.4.1.2.1.100
-- .1.3.6.1.4.1.39026.3.1.4.1.2.1.100
	branchActiveEnergy24 OBJECT-TYPE
	SYNTAX Integer32
	MAX-ACCESS read-only
	STATUS current
	DESCRIPTION
	"Description: "
	::= { powerMeterAMYDBEntry 100 }

-- .1.3.6.1.4.1.39026.3.1.4.1.2.1.101
-- .1.3.6.1.4.1.39026.3.1.4.1.2.1.101
-- .1.3.6.1.4.1.39026.3.1.4.1.2.1.101
-- .1.3.6.1.4.1.39026.3.1.4.1.2.1.101
	branchVoltage25 OBJECT-TYPE
	SYNTAX Integer32
	MAX-ACCESS read-only
	STATUS current
	DESCRIPTION
	"Description: "
	::= { powerMeterAMYDBEntry 101 }

-- .1.3.6.1.4.1.39026.3.1.4.1.2.1.102
-- .1.3.6.1.4.1.39026.3.1.4.1.2.1.102
-- .1.3.6.1.4.1.39026.3.1.4.1.2.1.102
-- .1.3.6.1.4.1.39026.3.1.4.1.2.1.102
	branchCurrent25 OBJECT-TYPE
	SYNTAX Integer32
	MAX-ACCESS read-only
	STATUS current
	DESCRIPTION
	"Description: "
	::= { powerMeterAMYDBEntry 102 }

-- .1.3.6.1.4.1.39026.3.1.4.1.2.1.103
-- .1.3.6.1.4.1.39026.3.1.4.1.2.1.103
-- .1.3.6.1.4.1.39026.3.1.4.1.2.1.103
-- .1.3.6.1.4.1.39026.3.1.4.1.2.1.103
	branchActivePower25 OBJECT-TYPE
	SYNTAX Integer32
	MAX-ACCESS read-only
	STATUS current
	DESCRIPTION
	"Description: "
	::= { powerMeterAMYDBEntry 103 }

-- .1.3.6.1.4.1.39026.3.1.4.1.2.1.104
-- .1.3.6.1.4.1.39026.3.1.4.1.2.1.104
-- .1.3.6.1.4.1.39026.3.1.4.1.2.1.104
-- .1.3.6.1.4.1.39026.3.1.4.1.2.1.104
	branchActiveEnergy25 OBJECT-TYPE
	SYNTAX Integer32
	MAX-ACCESS read-only
	STATUS current
	DESCRIPTION
	"Description: "
	::= { powerMeterAMYDBEntry 104 }

-- .1.3.6.1.4.1.39026.3.1.4.1.2.1.105
-- .1.3.6.1.4.1.39026.3.1.4.1.2.1.105
-- .1.3.6.1.4.1.39026.3.1.4.1.2.1.105
-- .1.3.6.1.4.1.39026.3.1.4.1.2.1.105
	branchVoltage26 OBJECT-TYPE
	SYNTAX Integer32
	MAX-ACCESS read-only
	STATUS current
	DESCRIPTION
	"Description: "
	::= { powerMeterAMYDBEntry 105 }

-- .1.3.6.1.4.1.39026.3.1.4.1.2.1.106
-- .1.3.6.1.4.1.39026.3.1.4.1.2.1.106
-- .1.3.6.1.4.1.39026.3.1.4.1.2.1.106
-- .1.3.6.1.4.1.39026.3.1.4.1.2.1.106
	branchCurrent26 OBJECT-TYPE
	SYNTAX Integer32
	MAX-ACCESS read-only
	STATUS current
	DESCRIPTION
	"Description: "
	::= { powerMeterAMYDBEntry 106 }

-- .1.3.6.1.4.1.39026.3.1.4.1.2.1.107
-- .1.3.6.1.4.1.39026.3.1.4.1.2.1.107
-- .1.3.6.1.4.1.39026.3.1.4.1.2.1.107
-- .1.3.6.1.4.1.39026.3.1.4.1.2.1.107
	branchActivePower26 OBJECT-TYPE
	SYNTAX Integer32
	MAX-ACCESS read-only
	STATUS current
	DESCRIPTION
	"Description: "
	::= { powerMeterAMYDBEntry 107 }

-- .1.3.6.1.4.1.39026.3.1.4.1.2.1.108
-- .1.3.6.1.4.1.39026.3.1.4.1.2.1.108
-- .1.3.6.1.4.1.39026.3.1.4.1.2.1.108
-- .1.3.6.1.4.1.39026.3.1.4.1.2.1.108
	branchActiveEnergy26 OBJECT-TYPE
	SYNTAX Integer32
	MAX-ACCESS read-only
	STATUS current
	DESCRIPTION
	"Description: "
	::= { powerMeterAMYDBEntry 108 }

-- .1.3.6.1.4.1.39026.3.1.4.1.2.1.109
-- .1.3.6.1.4.1.39026.3.1.4.1.2.1.109
-- .1.3.6.1.4.1.39026.3.1.4.1.2.1.109
-- .1.3.6.1.4.1.39026.3.1.4.1.2.1.109
	branchVoltage27 OBJECT-TYPE
	SYNTAX Integer32
	MAX-ACCESS read-only
	STATUS current
	DESCRIPTION
	"Description: "
	::= { powerMeterAMYDBEntry 109 }

-- .1.3.6.1.4.1.39026.3.1.4.1.2.1.110
-- .1.3.6.1.4.1.39026.3.1.4.1.2.1.110
-- .1.3.6.1.4.1.39026.3.1.4.1.2.1.110
-- .1.3.6.1.4.1.39026.3.1.4.1.2.1.110
	branchCurrent27 OBJECT-TYPE
	SYNTAX Integer32
	MAX-ACCESS read-only
	STATUS current
	DESCRIPTION
	"Description: "
	::= { powerMeterAMYDBEntry 110 }

-- .1.3.6.1.4.1.39026.3.1.4.1.2.1.111
-- .1.3.6.1.4.1.39026.3.1.4.1.2.1.111
-- .1.3.6.1.4.1.39026.3.1.4.1.2.1.111
-- .1.3.6.1.4.1.39026.3.1.4.1.2.1.111
	branchActivePower27 OBJECT-TYPE
	SYNTAX Integer32
	MAX-ACCESS read-only
	STATUS current
	DESCRIPTION
	"Description: "
	::= { powerMeterAMYDBEntry 111 }

-- .1.3.6.1.4.1.39026.3.1.4.1.2.1.112
-- .1.3.6.1.4.1.39026.3.1.4.1.2.1.112
-- .1.3.6.1.4.1.39026.3.1.4.1.2.1.112
-- .1.3.6.1.4.1.39026.3.1.4.1.2.1.112
	branchActiveEnergy27 OBJECT-TYPE
	SYNTAX Integer32
	MAX-ACCESS read-only
	STATUS current
	DESCRIPTION
	"Description: "
	::= { powerMeterAMYDBEntry 112 }

-- .1.3.6.1.4.1.39026.3.1.4.1.2.1.113
-- .1.3.6.1.4.1.39026.3.1.4.1.2.1.113
-- .1.3.6.1.4.1.39026.3.1.4.1.2.1.113
-- .1.3.6.1.4.1.39026.3.1.4.1.2.1.113
	branchVoltage28 OBJECT-TYPE
	SYNTAX Integer32
	MAX-ACCESS read-only
	STATUS current
	DESCRIPTION
	"Description: "
	::= { powerMeterAMYDBEntry 113 }

-- .1.3.6.1.4.1.39026.3.1.4.1.2.1.114
-- .1.3.6.1.4.1.39026.3.1.4.1.2.1.114
-- .1.3.6.1.4.1.39026.3.1.4.1.2.1.114
-- .1.3.6.1.4.1.39026.3.1.4.1.2.1.114
	branchCurrent28 OBJECT-TYPE
	SYNTAX Integer32
	MAX-ACCESS read-only
	STATUS current
	DESCRIPTION
	"Description: "
	::= { powerMeterAMYDBEntry 114 }

-- .1.3.6.1.4.1.39026.3.1.4.1.2.1.115
-- .1.3.6.1.4.1.39026.3.1.4.1.2.1.115
-- .1.3.6.1.4.1.39026.3.1.4.1.2.1.115
-- .1.3.6.1.4.1.39026.3.1.4.1.2.1.115
	branchActivePower28 OBJECT-TYPE
	SYNTAX Integer32
	MAX-ACCESS read-only
	STATUS current
	DESCRIPTION
	"Description: "
	::= { powerMeterAMYDBEntry 115 }

-- .1.3.6.1.4.1.39026.3.1.4.1.2.1.116
-- .1.3.6.1.4.1.39026.3.1.4.1.2.1.116
-- .1.3.6.1.4.1.39026.3.1.4.1.2.1.116
-- .1.3.6.1.4.1.39026.3.1.4.1.2.1.116
	branchActiveEnergy28 OBJECT-TYPE
	SYNTAX Integer32
	MAX-ACCESS read-only
	STATUS current
	DESCRIPTION
	"Description: "
	::= { powerMeterAMYDBEntry 116 }

-- .1.3.6.1.4.1.39026.3.1.4.1.2.1.117
-- .1.3.6.1.4.1.39026.3.1.4.1.2.1.117
-- .1.3.6.1.4.1.39026.3.1.4.1.2.1.117
-- .1.3.6.1.4.1.39026.3.1.4.1.2.1.117
	branchVoltage29 OBJECT-TYPE
	SYNTAX Integer32
	MAX-ACCESS read-only
	STATUS current
	DESCRIPTION
	"Description: "
	::= { powerMeterAMYDBEntry 117 }

-- .1.3.6.1.4.1.39026.3.1.4.1.2.1.118
-- .1.3.6.1.4.1.39026.3.1.4.1.2.1.118
-- .1.3.6.1.4.1.39026.3.1.4.1.2.1.118
-- .1.3.6.1.4.1.39026.3.1.4.1.2.1.118
	branchCurrent29 OBJECT-TYPE
	SYNTAX Integer32
	MAX-ACCESS read-only
	STATUS current
	DESCRIPTION
	"Description: "
	::= { powerMeterAMYDBEntry 118 }

-- .1.3.6.1.4.1.39026.3.1.4.1.2.1.119
-- .1.3.6.1.4.1.39026.3.1.4.1.2.1.119
-- .1.3.6.1.4.1.39026.3.1.4.1.2.1.119
-- .1.3.6.1.4.1.39026.3.1.4.1.2.1.119
	branchActivePower29 OBJECT-TYPE
	SYNTAX Integer32
	MAX-ACCESS read-only
	STATUS current
	DESCRIPTION
	"Description: "
	::= { powerMeterAMYDBEntry 119 }

-- .1.3.6.1.4.1.39026.3.1.4.1.2.1.120
-- .1.3.6.1.4.1.39026.3.1.4.1.2.1.120
-- .1.3.6.1.4.1.39026.3.1.4.1.2.1.120
-- .1.3.6.1.4.1.39026.3.1.4.1.2.1.120
	branchActiveEnergy29 OBJECT-TYPE
	SYNTAX Integer32
	MAX-ACCESS read-only
	STATUS current
	DESCRIPTION
	"Description: "
	::= { powerMeterAMYDBEntry 120 }

-- .1.3.6.1.4.1.39026.3.1.4.1.2.1.121
-- .1.3.6.1.4.1.39026.3.1.4.1.2.1.121
-- .1.3.6.1.4.1.39026.3.1.4.1.2.1.121
-- .1.3.6.1.4.1.39026.3.1.4.1.2.1.121
	branchVoltage30 OBJECT-TYPE
	SYNTAX Integer32
	MAX-ACCESS read-only
	STATUS current
	DESCRIPTION
	"Description: "
	::= { powerMeterAMYDBEntry 121 }

-- .1.3.6.1.4.1.39026.3.1.4.1.2.1.122
-- .1.3.6.1.4.1.39026.3.1.4.1.2.1.122
-- .1.3.6.1.4.1.39026.3.1.4.1.2.1.122
-- .1.3.6.1.4.1.39026.3.1.4.1.2.1.122
	branchCurrent30 OBJECT-TYPE
	SYNTAX Integer32
	MAX-ACCESS read-only
	STATUS current
	DESCRIPTION
	"Description: "
	::= { powerMeterAMYDBEntry 122 }

-- .1.3.6.1.4.1.39026.3.1.4.1.2.1.123
-- .1.3.6.1.4.1.39026.3.1.4.1.2.1.123
-- .1.3.6.1.4.1.39026.3.1.4.1.2.1.123
-- .1.3.6.1.4.1.39026.3.1.4.1.2.1.123
	branchActivePower30 OBJECT-TYPE
	SYNTAX Integer32
	MAX-ACCESS read-only
	STATUS current
	DESCRIPTION
	"Description: "
	::= { powerMeterAMYDBEntry 123 }

-- .1.3.6.1.4.1.39026.3.1.4.1.2.1.124
-- .1.3.6.1.4.1.39026.3.1.4.1.2.1.124
-- .1.3.6.1.4.1.39026.3.1.4.1.2.1.124
-- .1.3.6.1.4.1.39026.3.1.4.1.2.1.124
	branchActiveEnergy30 OBJECT-TYPE
	SYNTAX Integer32
	MAX-ACCESS read-only
	STATUS current
	DESCRIPTION
	"Description: "
	::= { powerMeterAMYDBEntry 124 }

-- .1.3.6.1.4.1.39026.3.1.4.1.2.1.125
-- .1.3.6.1.4.1.39026.3.1.4.1.2.1.125
-- .1.3.6.1.4.1.39026.3.1.4.1.2.1.125
-- .1.3.6.1.4.1.39026.3.1.4.1.2.1.125
	branchVoltage31 OBJECT-TYPE
	SYNTAX Integer32
	MAX-ACCESS read-only
	STATUS current
	DESCRIPTION
	"Description: "
	::= { powerMeterAMYDBEntry 125 }

-- .1.3.6.1.4.1.39026.3.1.4.1.2.1.126
-- .1.3.6.1.4.1.39026.3.1.4.1.2.1.126
-- .1.3.6.1.4.1.39026.3.1.4.1.2.1.126
-- .1.3.6.1.4.1.39026.3.1.4.1.2.1.126
	branchCurrent31 OBJECT-TYPE
	SYNTAX Integer32
	MAX-ACCESS read-only
	STATUS current
	DESCRIPTION
	"Description: "
	::= { powerMeterAMYDBEntry 126 }

-- .1.3.6.1.4.1.39026.3.1.4.1.2.1.127
-- .1.3.6.1.4.1.39026.3.1.4.1.2.1.127
-- .1.3.6.1.4.1.39026.3.1.4.1.2.1.127
-- .1.3.6.1.4.1.39026.3.1.4.1.2.1.127
	branchActivePower31 OBJECT-TYPE
	SYNTAX Integer32
	MAX-ACCESS read-only
	STATUS current
	DESCRIPTION
	"Description: "
	::= { powerMeterAMYDBEntry 127 }

-- .1.3.6.1.4.1.39026.3.1.4.1.2.1.128
-- .1.3.6.1.4.1.39026.3.1.4.1.2.1.128
-- .1.3.6.1.4.1.39026.3.1.4.1.2.1.128
-- .1.3.6.1.4.1.39026.3.1.4.1.2.1.128
	branchActiveEnergy31 OBJECT-TYPE
	SYNTAX Integer32
	MAX-ACCESS read-only
	STATUS current
	DESCRIPTION
	"Description: "
	::= { powerMeterAMYDBEntry 128 }

-- .1.3.6.1.4.1.39026.3.1.4.1.2.1.129
-- .1.3.6.1.4.1.39026.3.1.4.1.2.1.129
-- .1.3.6.1.4.1.39026.3.1.4.1.2.1.129
-- .1.3.6.1.4.1.39026.3.1.4.1.2.1.129
	branchVoltage32 OBJECT-TYPE
	SYNTAX Integer32
	MAX-ACCESS read-only
	STATUS current
	DESCRIPTION
	"Description: "
	::= { powerMeterAMYDBEntry 129 }

-- .1.3.6.1.4.1.39026.3.1.4.1.2.1.130
-- .1.3.6.1.4.1.39026.3.1.4.1.2.1.130
-- .1.3.6.1.4.1.39026.3.1.4.1.2.1.130
-- .1.3.6.1.4.1.39026.3.1.4.1.2.1.130
	branchCurrent32 OBJECT-TYPE
	SYNTAX Integer32
	MAX-ACCESS read-only
	STATUS current
	DESCRIPTION
	"Description: "
	::= { powerMeterAMYDBEntry 130 }

-- .1.3.6.1.4.1.39026.3.1.4.1.2.1.131
-- .1.3.6.1.4.1.39026.3.1.4.1.2.1.131
-- .1.3.6.1.4.1.39026.3.1.4.1.2.1.131
-- .1.3.6.1.4.1.39026.3.1.4.1.2.1.131
	branchActivePower32 OBJECT-TYPE
	SYNTAX Integer32
	MAX-ACCESS read-only
	STATUS current
	DESCRIPTION
	"Description: "
	::= { powerMeterAMYDBEntry 131 }

-- .1.3.6.1.4.1.39026.3.1.4.1.2.1.132
-- .1.3.6.1.4.1.39026.3.1.4.1.2.1.132
-- .1.3.6.1.4.1.39026.3.1.4.1.2.1.132
-- .1.3.6.1.4.1.39026.3.1.4.1.2.1.132
	branchActiveEnergy32 OBJECT-TYPE
	SYNTAX Integer32
	MAX-ACCESS read-only
	STATUS current
	DESCRIPTION
	"Description: "
	::= { powerMeterAMYDBEntry 132 }

-- .1.3.6.1.4.1.39026.3.1.4.1.2.1.133
-- .1.3.6.1.4.1.39026.3.1.4.1.2.1.133
-- .1.3.6.1.4.1.39026.3.1.4.1.2.1.133
-- .1.3.6.1.4.1.39026.3.1.4.1.2.1.133
	branchVoltage33 OBJECT-TYPE
	SYNTAX Integer32
	MAX-ACCESS read-only
	STATUS current
	DESCRIPTION
	"Description: "
	::= { powerMeterAMYDBEntry 133 }

-- .1.3.6.1.4.1.39026.3.1.4.1.2.1.134
-- .1.3.6.1.4.1.39026.3.1.4.1.2.1.134
-- .1.3.6.1.4.1.39026.3.1.4.1.2.1.134
-- .1.3.6.1.4.1.39026.3.1.4.1.2.1.134
	branchCurrent33 OBJECT-TYPE
	SYNTAX Integer32
	MAX-ACCESS read-only
	STATUS current
	DESCRIPTION
	"Description: "
	::= { powerMeterAMYDBEntry 134 }

-- .1.3.6.1.4.1.39026.3.1.4.1.2.1.135
-- .1.3.6.1.4.1.39026.3.1.4.1.2.1.135
-- .1.3.6.1.4.1.39026.3.1.4.1.2.1.135
-- .1.3.6.1.4.1.39026.3.1.4.1.2.1.135
	branchActivePower33 OBJECT-TYPE
	SYNTAX Integer32
	MAX-ACCESS read-only
	STATUS current
	DESCRIPTION
	"Description: "
	::= { powerMeterAMYDBEntry 135 }

-- .1.3.6.1.4.1.39026.3.1.4.1.2.1.136
-- .1.3.6.1.4.1.39026.3.1.4.1.2.1.136
-- .1.3.6.1.4.1.39026.3.1.4.1.2.1.136
-- .1.3.6.1.4.1.39026.3.1.4.1.2.1.136
	branchActiveEnergy33 OBJECT-TYPE
	SYNTAX Integer32
	MAX-ACCESS read-only
	STATUS current
	DESCRIPTION
	"Description: "
	::= { powerMeterAMYDBEntry 136 }

-- .1.3.6.1.4.1.39026.3.1.4.1.2.1.137
-- .1.3.6.1.4.1.39026.3.1.4.1.2.1.137
-- .1.3.6.1.4.1.39026.3.1.4.1.2.1.137
-- .1.3.6.1.4.1.39026.3.1.4.1.2.1.137
	branchVoltage34 OBJECT-TYPE
	SYNTAX Integer32
	MAX-ACCESS read-only
	STATUS current
	DESCRIPTION
	"Description: "
	::= { powerMeterAMYDBEntry 137 }

-- .1.3.6.1.4.1.39026.3.1.4.1.2.1.138
-- .1.3.6.1.4.1.39026.3.1.4.1.2.1.138
-- .1.3.6.1.4.1.39026.3.1.4.1.2.1.138
-- .1.3.6.1.4.1.39026.3.1.4.1.2.1.138
	branchCurrent34 OBJECT-TYPE
	SYNTAX Integer32
	MAX-ACCESS read-only
	STATUS current
	DESCRIPTION
	"Description: "
	::= { powerMeterAMYDBEntry 138 }

-- .1.3.6.1.4.1.39026.3.1.4.1.2.1.139
-- .1.3.6.1.4.1.39026.3.1.4.1.2.1.139
-- .1.3.6.1.4.1.39026.3.1.4.1.2.1.139
-- .1.3.6.1.4.1.39026.3.1.4.1.2.1.139
	branchActivePower34 OBJECT-TYPE
	SYNTAX Integer32
	MAX-ACCESS read-only
	STATUS current
	DESCRIPTION
	"Description: "
	::= { powerMeterAMYDBEntry 139 }

-- .1.3.6.1.4.1.39026.3.1.4.1.2.1.140
-- .1.3.6.1.4.1.39026.3.1.4.1.2.1.140
-- .1.3.6.1.4.1.39026.3.1.4.1.2.1.140
-- .1.3.6.1.4.1.39026.3.1.4.1.2.1.140
	branchActiveEnergy34 OBJECT-TYPE
	SYNTAX Integer32
	MAX-ACCESS read-only
	STATUS current
	DESCRIPTION
	"Description: "
	::= { powerMeterAMYDBEntry 140 }

-- .1.3.6.1.4.1.39026.3.1.4.1.2.1.141
-- .1.3.6.1.4.1.39026.3.1.4.1.2.1.141
-- .1.3.6.1.4.1.39026.3.1.4.1.2.1.141
-- .1.3.6.1.4.1.39026.3.1.4.1.2.1.141
	branchVoltage35 OBJECT-TYPE
	SYNTAX Integer32
	MAX-ACCESS read-only
	STATUS current
	DESCRIPTION
	"Description: "
	::= { powerMeterAMYDBEntry 141 }

-- .1.3.6.1.4.1.39026.3.1.4.1.2.1.142
-- .1.3.6.1.4.1.39026.3.1.4.1.2.1.142
-- .1.3.6.1.4.1.39026.3.1.4.1.2.1.142
-- .1.3.6.1.4.1.39026.3.1.4.1.2.1.142
	branchCurrent35 OBJECT-TYPE
	SYNTAX Integer32
	MAX-ACCESS read-only
	STATUS current
	DESCRIPTION
	"Description: "
	::= { powerMeterAMYDBEntry 142 }

-- .1.3.6.1.4.1.39026.3.1.4.1.2.1.143
-- .1.3.6.1.4.1.39026.3.1.4.1.2.1.143
-- .1.3.6.1.4.1.39026.3.1.4.1.2.1.143
-- .1.3.6.1.4.1.39026.3.1.4.1.2.1.143
	branchActivePower35 OBJECT-TYPE
	SYNTAX Integer32
	MAX-ACCESS read-only
	STATUS current
	DESCRIPTION
	"Description: "
	::= { powerMeterAMYDBEntry 143 }

-- .1.3.6.1.4.1.39026.3.1.4.1.2.1.144
-- .1.3.6.1.4.1.39026.3.1.4.1.2.1.144
-- .1.3.6.1.4.1.39026.3.1.4.1.2.1.144
-- .1.3.6.1.4.1.39026.3.1.4.1.2.1.144
	branchActiveEnergy35 OBJECT-TYPE
	SYNTAX Integer32
	MAX-ACCESS read-only
	STATUS current
	DESCRIPTION
	"Description: "
	::= { powerMeterAMYDBEntry 144 }

-- .1.3.6.1.4.1.39026.3.1.4.1.2.1.145
-- .1.3.6.1.4.1.39026.3.1.4.1.2.1.145
-- .1.3.6.1.4.1.39026.3.1.4.1.2.1.145
-- .1.3.6.1.4.1.39026.3.1.4.1.2.1.145
	branchVoltage36 OBJECT-TYPE
	SYNTAX Integer32
	MAX-ACCESS read-only
	STATUS current
	DESCRIPTION
	"Description: "
	::= { powerMeterAMYDBEntry 145 }

-- .1.3.6.1.4.1.39026.3.1.4.1.2.1.146
-- .1.3.6.1.4.1.39026.3.1.4.1.2.1.146
-- .1.3.6.1.4.1.39026.3.1.4.1.2.1.146
-- .1.3.6.1.4.1.39026.3.1.4.1.2.1.146
	branchCurrent36 OBJECT-TYPE
	SYNTAX Integer32
	MAX-ACCESS read-only
	STATUS current
	DESCRIPTION
	"Description: "
	::= { powerMeterAMYDBEntry 146 }

-- .1.3.6.1.4.1.39026.3.1.4.1.2.1.147
-- .1.3.6.1.4.1.39026.3.1.4.1.2.1.147
-- .1.3.6.1.4.1.39026.3.1.4.1.2.1.147
-- .1.3.6.1.4.1.39026.3.1.4.1.2.1.147
	branchActivePower36 OBJECT-TYPE
	SYNTAX Integer32
	MAX-ACCESS read-only
	STATUS current
	DESCRIPTION
	"Description: "
	::= { powerMeterAMYDBEntry 147 }

-- .1.3.6.1.4.1.39026.3.1.4.1.2.1.148
-- .1.3.6.1.4.1.39026.3.1.4.1.2.1.148
-- .1.3.6.1.4.1.39026.3.1.4.1.2.1.148
-- .1.3.6.1.4.1.39026.3.1.4.1.2.1.148
	branchActiveEnergy36 OBJECT-TYPE
	SYNTAX Integer32
	MAX-ACCESS read-only
	STATUS current
	DESCRIPTION
	"Description: "
	::= { powerMeterAMYDBEntry 148 }

-- .1.3.6.1.4.1.39026.3.1.4.1.2.1.149
-- .1.3.6.1.4.1.39026.3.1.4.1.2.1.149
-- .1.3.6.1.4.1.39026.3.1.4.1.2.1.149
-- .1.3.6.1.4.1.39026.3.1.4.1.2.1.149
	branchVoltage37 OBJECT-TYPE
	SYNTAX Integer32
	MAX-ACCESS read-only
	STATUS current
	DESCRIPTION
	"Description: "
	::= { powerMeterAMYDBEntry 149 }

-- .1.3.6.1.4.1.39026.3.1.4.1.2.1.150
-- .1.3.6.1.4.1.39026.3.1.4.1.2.1.150
-- .1.3.6.1.4.1.39026.3.1.4.1.2.1.150
-- .1.3.6.1.4.1.39026.3.1.4.1.2.1.150
	branchCurrent37 OBJECT-TYPE
	SYNTAX Integer32
	MAX-ACCESS read-only
	STATUS current
	DESCRIPTION
	"Description: "
	::= { powerMeterAMYDBEntry 150 }

-- .1.3.6.1.4.1.39026.3.1.4.1.2.1.151
-- .1.3.6.1.4.1.39026.3.1.4.1.2.1.151
-- .1.3.6.1.4.1.39026.3.1.4.1.2.1.151
-- .1.3.6.1.4.1.39026.3.1.4.1.2.1.151
	branchActivePower37 OBJECT-TYPE
	SYNTAX Integer32
	MAX-ACCESS read-only
	STATUS current
	DESCRIPTION
	"Description: "
	::= { powerMeterAMYDBEntry 151 }

-- .1.3.6.1.4.1.39026.3.1.4.1.2.1.152
-- .1.3.6.1.4.1.39026.3.1.4.1.2.1.152
-- .1.3.6.1.4.1.39026.3.1.4.1.2.1.152
-- .1.3.6.1.4.1.39026.3.1.4.1.2.1.152
	branchActiveEnergy37 OBJECT-TYPE
	SYNTAX Integer32
	MAX-ACCESS read-only
	STATUS current
	DESCRIPTION
	"Description: "
	::= { powerMeterAMYDBEntry 152 }

-- .1.3.6.1.4.1.39026.3.1.4.1.2.1.153
-- .1.3.6.1.4.1.39026.3.1.4.1.2.1.153
-- .1.3.6.1.4.1.39026.3.1.4.1.2.1.153
-- .1.3.6.1.4.1.39026.3.1.4.1.2.1.153
	branchVoltage38 OBJECT-TYPE
	SYNTAX Integer32
	MAX-ACCESS read-only
	STATUS current
	DESCRIPTION
	"Description: "
	::= { powerMeterAMYDBEntry 153 }

-- .1.3.6.1.4.1.39026.3.1.4.1.2.1.154
-- .1.3.6.1.4.1.39026.3.1.4.1.2.1.154
-- .1.3.6.1.4.1.39026.3.1.4.1.2.1.154
-- .1.3.6.1.4.1.39026.3.1.4.1.2.1.154
	branchCurrent38 OBJECT-TYPE
	SYNTAX Integer32
	MAX-ACCESS read-only
	STATUS current
	DESCRIPTION
	"Description: "
	::= { powerMeterAMYDBEntry 154 }

-- .1.3.6.1.4.1.39026.3.1.4.1.2.1.155
-- .1.3.6.1.4.1.39026.3.1.4.1.2.1.155
-- .1.3.6.1.4.1.39026.3.1.4.1.2.1.155
-- .1.3.6.1.4.1.39026.3.1.4.1.2.1.155
	branchActivePower38 OBJECT-TYPE
	SYNTAX Integer32
	MAX-ACCESS read-only
	STATUS current
	DESCRIPTION
	"Description: "
	::= { powerMeterAMYDBEntry 155 }

-- .1.3.6.1.4.1.39026.3.1.4.1.2.1.156
-- .1.3.6.1.4.1.39026.3.1.4.1.2.1.156
-- .1.3.6.1.4.1.39026.3.1.4.1.2.1.156
-- .1.3.6.1.4.1.39026.3.1.4.1.2.1.156
	branchActiveEnergy38 OBJECT-TYPE
	SYNTAX Integer32
	MAX-ACCESS read-only
	STATUS current
	DESCRIPTION
	"Description: "
	::= { powerMeterAMYDBEntry 156 }

-- .1.3.6.1.4.1.39026.3.1.4.1.2.1.157
-- .1.3.6.1.4.1.39026.3.1.4.1.2.1.157
-- .1.3.6.1.4.1.39026.3.1.4.1.2.1.157
-- .1.3.6.1.4.1.39026.3.1.4.1.2.1.157
	branchVoltage39 OBJECT-TYPE
	SYNTAX Integer32
	MAX-ACCESS read-only
	STATUS current
	DESCRIPTION
	"Description: "
	::= { powerMeterAMYDBEntry 157 }

-- .1.3.6.1.4.1.39026.3.1.4.1.2.1.158
-- .1.3.6.1.4.1.39026.3.1.4.1.2.1.158
-- .1.3.6.1.4.1.39026.3.1.4.1.2.1.158
-- .1.3.6.1.4.1.39026.3.1.4.1.2.1.158
	branchCurrent39 OBJECT-TYPE
	SYNTAX Integer32
	MAX-ACCESS read-only
	STATUS current
	DESCRIPTION
	"Description: "
	::= { powerMeterAMYDBEntry 158 }

-- .1.3.6.1.4.1.39026.3.1.4.1.2.1.159
-- .1.3.6.1.4.1.39026.3.1.4.1.2.1.159
-- .1.3.6.1.4.1.39026.3.1.4.1.2.1.159
-- .1.3.6.1.4.1.39026.3.1.4.1.2.1.159
	branchActivePower39 OBJECT-TYPE
	SYNTAX Integer32
	MAX-ACCESS read-only
	STATUS current
	DESCRIPTION
	"Description: "
	::= { powerMeterAMYDBEntry 159 }

-- .1.3.6.1.4.1.39026.3.1.4.1.2.1.160
-- .1.3.6.1.4.1.39026.3.1.4.1.2.1.160
-- .1.3.6.1.4.1.39026.3.1.4.1.2.1.160
-- .1.3.6.1.4.1.39026.3.1.4.1.2.1.160
	branchActiveEnergy39 OBJECT-TYPE
	SYNTAX Integer32
	MAX-ACCESS read-only
	STATUS current
	DESCRIPTION
	"Description: "
	::= { powerMeterAMYDBEntry 160 }

-- .1.3.6.1.4.1.39026.3.1.4.1.2.1.161
-- .1.3.6.1.4.1.39026.3.1.4.1.2.1.161
-- .1.3.6.1.4.1.39026.3.1.4.1.2.1.161
-- .1.3.6.1.4.1.39026.3.1.4.1.2.1.161
	branchVoltage40 OBJECT-TYPE
	SYNTAX Integer32
	MAX-ACCESS read-only
	STATUS current
	DESCRIPTION
	"Description: "
	::= { powerMeterAMYDBEntry 161 }

-- .1.3.6.1.4.1.39026.3.1.4.1.2.1.162
-- .1.3.6.1.4.1.39026.3.1.4.1.2.1.162
-- .1.3.6.1.4.1.39026.3.1.4.1.2.1.162
-- .1.3.6.1.4.1.39026.3.1.4.1.2.1.162
	branchCurrent40 OBJECT-TYPE
	SYNTAX Integer32
	MAX-ACCESS read-only
	STATUS current
	DESCRIPTION
	"Description: "
	::= { powerMeterAMYDBEntry 162 }

-- .1.3.6.1.4.1.39026.3.1.4.1.2.1.163
-- .1.3.6.1.4.1.39026.3.1.4.1.2.1.163
-- .1.3.6.1.4.1.39026.3.1.4.1.2.1.163
-- .1.3.6.1.4.1.39026.3.1.4.1.2.1.163
	branchActivePower40 OBJECT-TYPE
	SYNTAX Integer32
	MAX-ACCESS read-only
	STATUS current
	DESCRIPTION
	"Description: "
	::= { powerMeterAMYDBEntry 163 }

-- .1.3.6.1.4.1.39026.3.1.4.1.2.1.164
-- .1.3.6.1.4.1.39026.3.1.4.1.2.1.164
-- .1.3.6.1.4.1.39026.3.1.4.1.2.1.164
-- .1.3.6.1.4.1.39026.3.1.4.1.2.1.164
	branchActiveEnergy40 OBJECT-TYPE
	SYNTAX Integer32
	MAX-ACCESS read-only
	STATUS current
	DESCRIPTION
	"Description: "
	::= { powerMeterAMYDBEntry 164 }

-- .1.3.6.1.4.1.39026.3.1.4.1.2.1.165
-- .1.3.6.1.4.1.39026.3.1.4.1.2.1.165
-- .1.3.6.1.4.1.39026.3.1.4.1.2.1.165
-- .1.3.6.1.4.1.39026.3.1.4.1.2.1.165
	branchVoltage41 OBJECT-TYPE
	SYNTAX Integer32
	MAX-ACCESS read-only
	STATUS current
	DESCRIPTION
	"Description: "
	::= { powerMeterAMYDBEntry 165 }

-- .1.3.6.1.4.1.39026.3.1.4.1.2.1.166
-- .1.3.6.1.4.1.39026.3.1.4.1.2.1.166
-- .1.3.6.1.4.1.39026.3.1.4.1.2.1.166
-- .1.3.6.1.4.1.39026.3.1.4.1.2.1.166
	branchCurrent41 OBJECT-TYPE
	SYNTAX Integer32
	MAX-ACCESS read-only
	STATUS current
	DESCRIPTION
	"Description: "
	::= { powerMeterAMYDBEntry 166 }

-- .1.3.6.1.4.1.39026.3.1.4.1.2.1.167
-- .1.3.6.1.4.1.39026.3.1.4.1.2.1.167
-- .1.3.6.1.4.1.39026.3.1.4.1.2.1.167
-- .1.3.6.1.4.1.39026.3.1.4.1.2.1.167
	branchActivePower41 OBJECT-TYPE
	SYNTAX Integer32
	MAX-ACCESS read-only
	STATUS current
	DESCRIPTION
	"Description: "
	::= { powerMeterAMYDBEntry 167 }

-- .1.3.6.1.4.1.39026.3.1.4.1.2.1.168
-- .1.3.6.1.4.1.39026.3.1.4.1.2.1.168
-- .1.3.6.1.4.1.39026.3.1.4.1.2.1.168
-- .1.3.6.1.4.1.39026.3.1.4.1.2.1.168
	branchActiveEnergy41 OBJECT-TYPE
	SYNTAX Integer32
	MAX-ACCESS read-only
	STATUS current
	DESCRIPTION
	"Description: "
	::= { powerMeterAMYDBEntry 168 }

-- .1.3.6.1.4.1.39026.3.1.4.1.2.1.169
-- .1.3.6.1.4.1.39026.3.1.4.1.2.1.169
-- .1.3.6.1.4.1.39026.3.1.4.1.2.1.169
-- .1.3.6.1.4.1.39026.3.1.4.1.2.1.169
	branchVoltage42 OBJECT-TYPE
	SYNTAX Integer32
	MAX-ACCESS read-only
	STATUS current
	DESCRIPTION
	"Description: "
	::= { powerMeterAMYDBEntry 169 }

-- .1.3.6.1.4.1.39026.3.1.4.1.2.1.170
-- .1.3.6.1.4.1.39026.3.1.4.1.2.1.170
-- .1.3.6.1.4.1.39026.3.1.4.1.2.1.170
-- .1.3.6.1.4.1.39026.3.1.4.1.2.1.170
	branchCurrent42 OBJECT-TYPE
	SYNTAX Integer32
	MAX-ACCESS read-only
	STATUS current
	DESCRIPTION
	"Description: "
	::= { powerMeterAMYDBEntry 170 }

-- .1.3.6.1.4.1.39026.3.1.4.1.2.1.171
-- .1.3.6.1.4.1.39026.3.1.4.1.2.1.171
-- .1.3.6.1.4.1.39026.3.1.4.1.2.1.171
-- .1.3.6.1.4.1.39026.3.1.4.1.2.1.171
	branchActivePower42 OBJECT-TYPE
	SYNTAX Integer32
	MAX-ACCESS read-only
	STATUS current
	DESCRIPTION
	"Description: "
	::= { powerMeterAMYDBEntry 171 }

-- .1.3.6.1.4.1.39026.3.1.4.1.2.1.172
-- .1.3.6.1.4.1.39026.3.1.4.1.2.1.172
-- .1.3.6.1.4.1.39026.3.1.4.1.2.1.172
-- .1.3.6.1.4.1.39026.3.1.4.1.2.1.172
	branchActiveEnergy42 OBJECT-TYPE
	SYNTAX Integer32
	MAX-ACCESS read-only
	STATUS current
	DESCRIPTION
	"Description: "
	::= { powerMeterAMYDBEntry 172 }

-- .1.3.6.1.4.1.39026.3.1.4.1.2.1.173
-- .1.3.6.1.4.1.39026.3.1.4.1.2.1.173
-- .1.3.6.1.4.1.39026.3.1.4.1.2.1.173
-- .1.3.6.1.4.1.39026.3.1.4.1.2.1.173
	branchVoltage43 OBJECT-TYPE
	SYNTAX Integer32
	MAX-ACCESS read-only
	STATUS current
	DESCRIPTION
	"Description: "
	::= { powerMeterAMYDBEntry 173 }

-- .1.3.6.1.4.1.39026.3.1.4.1.2.1.174
-- .1.3.6.1.4.1.39026.3.1.4.1.2.1.174
-- .1.3.6.1.4.1.39026.3.1.4.1.2.1.174
-- .1.3.6.1.4.1.39026.3.1.4.1.2.1.174
	branchCurrent43 OBJECT-TYPE
	SYNTAX Integer32
	MAX-ACCESS read-only
	STATUS current
	DESCRIPTION
	"Description: "
	::= { powerMeterAMYDBEntry 174 }

-- .1.3.6.1.4.1.39026.3.1.4.1.2.1.175
-- .1.3.6.1.4.1.39026.3.1.4.1.2.1.175
-- .1.3.6.1.4.1.39026.3.1.4.1.2.1.175
-- .1.3.6.1.4.1.39026.3.1.4.1.2.1.175
	branchActivePower43 OBJECT-TYPE
	SYNTAX Integer32
	MAX-ACCESS read-only
	STATUS current
	DESCRIPTION
	"Description: "
	::= { powerMeterAMYDBEntry 175 }

-- .1.3.6.1.4.1.39026.3.1.4.1.2.1.176
-- .1.3.6.1.4.1.39026.3.1.4.1.2.1.176
-- .1.3.6.1.4.1.39026.3.1.4.1.2.1.176
-- .1.3.6.1.4.1.39026.3.1.4.1.2.1.176
	branchActiveEnergy43 OBJECT-TYPE
	SYNTAX Integer32
	MAX-ACCESS read-only
	STATUS current
	DESCRIPTION
	"Description: "
	::= { powerMeterAMYDBEntry 176 }

-- .1.3.6.1.4.1.39026.3.1.4.1.2.1.177
-- .1.3.6.1.4.1.39026.3.1.4.1.2.1.177
-- .1.3.6.1.4.1.39026.3.1.4.1.2.1.177
-- .1.3.6.1.4.1.39026.3.1.4.1.2.1.177
	branchVoltage44 OBJECT-TYPE
	SYNTAX Integer32
	MAX-ACCESS read-only
	STATUS current
	DESCRIPTION
	"Description: "
	::= { powerMeterAMYDBEntry 177 }

-- .1.3.6.1.4.1.39026.3.1.4.1.2.1.178
-- .1.3.6.1.4.1.39026.3.1.4.1.2.1.178
-- .1.3.6.1.4.1.39026.3.1.4.1.2.1.178
-- .1.3.6.1.4.1.39026.3.1.4.1.2.1.178
	branchCurrent44 OBJECT-TYPE
	SYNTAX Integer32
	MAX-ACCESS read-only
	STATUS current
	DESCRIPTION
	"Description: "
	::= { powerMeterAMYDBEntry 178 }

-- .1.3.6.1.4.1.39026.3.1.4.1.2.1.179
-- .1.3.6.1.4.1.39026.3.1.4.1.2.1.179
-- .1.3.6.1.4.1.39026.3.1.4.1.2.1.179
-- .1.3.6.1.4.1.39026.3.1.4.1.2.1.179
	branchActivePower44 OBJECT-TYPE
	SYNTAX Integer32
	MAX-ACCESS read-only
	STATUS current
	DESCRIPTION
	"Description: "
	::= { powerMeterAMYDBEntry 179 }

-- .1.3.6.1.4.1.39026.3.1.4.1.2.1.180
-- .1.3.6.1.4.1.39026.3.1.4.1.2.1.180
-- .1.3.6.1.4.1.39026.3.1.4.1.2.1.180
-- .1.3.6.1.4.1.39026.3.1.4.1.2.1.180
	branchActiveEnergy44 OBJECT-TYPE
	SYNTAX Integer32
	MAX-ACCESS read-only
	STATUS current
	DESCRIPTION
	"Description: "
	::= { powerMeterAMYDBEntry 180 }

-- .1.3.6.1.4.1.39026.3.1.4.1.2.1.181
-- .1.3.6.1.4.1.39026.3.1.4.1.2.1.181
-- .1.3.6.1.4.1.39026.3.1.4.1.2.1.181
-- .1.3.6.1.4.1.39026.3.1.4.1.2.1.181
	branchVoltage45 OBJECT-TYPE
	SYNTAX Integer32
	MAX-ACCESS read-only
	STATUS current
	DESCRIPTION
	"Description: "
	::= { powerMeterAMYDBEntry 181 }

-- .1.3.6.1.4.1.39026.3.1.4.1.2.1.182
-- .1.3.6.1.4.1.39026.3.1.4.1.2.1.182
-- .1.3.6.1.4.1.39026.3.1.4.1.2.1.182
-- .1.3.6.1.4.1.39026.3.1.4.1.2.1.182
	branchCurrent45 OBJECT-TYPE
	SYNTAX Integer32
	MAX-ACCESS read-only
	STATUS current
	DESCRIPTION
	"Description: "
	::= { powerMeterAMYDBEntry 182 }

-- .1.3.6.1.4.1.39026.3.1.4.1.2.1.183
-- .1.3.6.1.4.1.39026.3.1.4.1.2.1.183
-- .1.3.6.1.4.1.39026.3.1.4.1.2.1.183
-- .1.3.6.1.4.1.39026.3.1.4.1.2.1.183
	branchActivePower45 OBJECT-TYPE
	SYNTAX Integer32
	MAX-ACCESS read-only
	STATUS current
	DESCRIPTION
	"Description: "
	::= { powerMeterAMYDBEntry 183 }

-- .1.3.6.1.4.1.39026.3.1.4.1.2.1.184
-- .1.3.6.1.4.1.39026.3.1.4.1.2.1.184
-- .1.3.6.1.4.1.39026.3.1.4.1.2.1.184
-- .1.3.6.1.4.1.39026.3.1.4.1.2.1.184
	branchActiveEnergy45 OBJECT-TYPE
	SYNTAX Integer32
	MAX-ACCESS read-only
	STATUS current
	DESCRIPTION
	"Description: "
	::= { powerMeterAMYDBEntry 184 }

-- .1.3.6.1.4.1.39026.3.1.4.1.2.1.185
-- .1.3.6.1.4.1.39026.3.1.4.1.2.1.185
-- .1.3.6.1.4.1.39026.3.1.4.1.2.1.185
-- .1.3.6.1.4.1.39026.3.1.4.1.2.1.185
	branchVoltage46 OBJECT-TYPE
	SYNTAX Integer32
	MAX-ACCESS read-only
	STATUS current
	DESCRIPTION
	"Description: "
	::= { powerMeterAMYDBEntry 185 }

-- .1.3.6.1.4.1.39026.3.1.4.1.2.1.186
-- .1.3.6.1.4.1.39026.3.1.4.1.2.1.186
-- .1.3.6.1.4.1.39026.3.1.4.1.2.1.186
-- .1.3.6.1.4.1.39026.3.1.4.1.2.1.186
	branchCurrent46 OBJECT-TYPE
	SYNTAX Integer32
	MAX-ACCESS read-only
	STATUS current
	DESCRIPTION
	"Description: "
	::= { powerMeterAMYDBEntry 186 }

-- .1.3.6.1.4.1.39026.3.1.4.1.2.1.187
-- .1.3.6.1.4.1.39026.3.1.4.1.2.1.187
-- .1.3.6.1.4.1.39026.3.1.4.1.2.1.187
-- .1.3.6.1.4.1.39026.3.1.4.1.2.1.187
	branchActivePower46 OBJECT-TYPE
	SYNTAX Integer32
	MAX-ACCESS read-only
	STATUS current
	DESCRIPTION
	"Description: "
	::= { powerMeterAMYDBEntry 187 }

-- .1.3.6.1.4.1.39026.3.1.4.1.2.1.188
-- .1.3.6.1.4.1.39026.3.1.4.1.2.1.188
-- .1.3.6.1.4.1.39026.3.1.4.1.2.1.188
-- .1.3.6.1.4.1.39026.3.1.4.1.2.1.188
	branchActiveEnergy46 OBJECT-TYPE
	SYNTAX Integer32
	MAX-ACCESS read-only
	STATUS current
	DESCRIPTION
	"Description: "
	::= { powerMeterAMYDBEntry 188 }

-- .1.3.6.1.4.1.39026.3.1.4.1.2.1.189
-- .1.3.6.1.4.1.39026.3.1.4.1.2.1.189
-- .1.3.6.1.4.1.39026.3.1.4.1.2.1.189
-- .1.3.6.1.4.1.39026.3.1.4.1.2.1.189
	branchVoltage47 OBJECT-TYPE
	SYNTAX Integer32
	MAX-ACCESS read-only
	STATUS current
	DESCRIPTION
	"Description: "
	::= { powerMeterAMYDBEntry 189 }

-- .1.3.6.1.4.1.39026.3.1.4.1.2.1.190
-- .1.3.6.1.4.1.39026.3.1.4.1.2.1.190
-- .1.3.6.1.4.1.39026.3.1.4.1.2.1.190
-- .1.3.6.1.4.1.39026.3.1.4.1.2.1.190
	branchCurrent47 OBJECT-TYPE
	SYNTAX Integer32
	MAX-ACCESS read-only
	STATUS current
	DESCRIPTION
	"Description: "
	::= { powerMeterAMYDBEntry 190 }

-- .1.3.6.1.4.1.39026.3.1.4.1.2.1.191
-- .1.3.6.1.4.1.39026.3.1.4.1.2.1.191
-- .1.3.6.1.4.1.39026.3.1.4.1.2.1.191
-- .1.3.6.1.4.1.39026.3.1.4.1.2.1.191
	branchActivePower47 OBJECT-TYPE
	SYNTAX Integer32
	MAX-ACCESS read-only
	STATUS current
	DESCRIPTION
	"Description: "
	::= { powerMeterAMYDBEntry 191 }

-- .1.3.6.1.4.1.39026.3.1.4.1.2.1.192
-- .1.3.6.1.4.1.39026.3.1.4.1.2.1.192
-- .1.3.6.1.4.1.39026.3.1.4.1.2.1.192
-- .1.3.6.1.4.1.39026.3.1.4.1.2.1.192
	branchActiveEnergy47 OBJECT-TYPE
	SYNTAX Integer32
	MAX-ACCESS read-only
	STATUS current
	DESCRIPTION
	"Description: "
	::= { powerMeterAMYDBEntry 192 }

-- .1.3.6.1.4.1.39026.3.1.4.1.2.1.193
-- .1.3.6.1.4.1.39026.3.1.4.1.2.1.193
-- .1.3.6.1.4.1.39026.3.1.4.1.2.1.193
-- .1.3.6.1.4.1.39026.3.1.4.1.2.1.193
	branchVoltage48 OBJECT-TYPE
	SYNTAX Integer32
	MAX-ACCESS read-only
	STATUS current
	DESCRIPTION
	"Description: "
	::= { powerMeterAMYDBEntry 193 }

-- .1.3.6.1.4.1.39026.3.1.4.1.2.1.194
-- .1.3.6.1.4.1.39026.3.1.4.1.2.1.194
-- .1.3.6.1.4.1.39026.3.1.4.1.2.1.194
-- .1.3.6.1.4.1.39026.3.1.4.1.2.1.194
	branchCurrent48 OBJECT-TYPE
	SYNTAX Integer32
	MAX-ACCESS read-only
	STATUS current
	DESCRIPTION
	"Description: "
	::= { powerMeterAMYDBEntry 194 }

-- .1.3.6.1.4.1.39026.3.1.4.1.2.1.195
-- .1.3.6.1.4.1.39026.3.1.4.1.2.1.195
-- .1.3.6.1.4.1.39026.3.1.4.1.2.1.195
-- .1.3.6.1.4.1.39026.3.1.4.1.2.1.195
	branchActivePower48 OBJECT-TYPE
	SYNTAX Integer32
	MAX-ACCESS read-only
	STATUS current
	DESCRIPTION
	"Description: "
	::= { powerMeterAMYDBEntry 195 }

-- .1.3.6.1.4.1.39026.3.1.4.1.2.1.196
-- .1.3.6.1.4.1.39026.3.1.4.1.2.1.196
-- .1.3.6.1.4.1.39026.3.1.4.1.2.1.196
-- .1.3.6.1.4.1.39026.3.1.4.1.2.1.196
	branchActiveEnergy48 OBJECT-TYPE
	SYNTAX Integer32
	MAX-ACCESS read-only
	STATUS current
	DESCRIPTION
	"Description: "
	::= { powerMeterAMYDBEntry 196 }

-- .1.3.6.1.4.1.39026.3.1.4.1.2.1.197
-- .1.3.6.1.4.1.39026.3.1.4.1.2.1.197
-- .1.3.6.1.4.1.39026.3.1.4.1.2.1.197
-- .1.3.6.1.4.1.39026.3.1.4.1.2.1.197
	branchVoltage49 OBJECT-TYPE
	SYNTAX Integer32
	MAX-ACCESS read-only
	STATUS current
	DESCRIPTION
	"Description: "
	::= { powerMeterAMYDBEntry 197 }

-- .1.3.6.1.4.1.39026.3.1.4.1.2.1.198
-- .1.3.6.1.4.1.39026.3.1.4.1.2.1.198
-- .1.3.6.1.4.1.39026.3.1.4.1.2.1.198
-- .1.3.6.1.4.1.39026.3.1.4.1.2.1.198
	branchCurrent49 OBJECT-TYPE
	SYNTAX Integer32
	MAX-ACCESS read-only
	STATUS current
	DESCRIPTION
	"Description: "
	::= { powerMeterAMYDBEntry 198 }

-- .1.3.6.1.4.1.39026.3.1.4.1.2.1.199
-- .1.3.6.1.4.1.39026.3.1.4.1.2.1.199
-- .1.3.6.1.4.1.39026.3.1.4.1.2.1.199
-- .1.3.6.1.4.1.39026.3.1.4.1.2.1.199
	branchActivePower49 OBJECT-TYPE
	SYNTAX Integer32
	MAX-ACCESS read-only
	STATUS current
	DESCRIPTION
	"Description: "
	::= { powerMeterAMYDBEntry 199 }

-- .1.3.6.1.4.1.39026.3.1.4.1.2.1.200
-- .1.3.6.1.4.1.39026.3.1.4.1.2.1.200
-- .1.3.6.1.4.1.39026.3.1.4.1.2.1.200
-- .1.3.6.1.4.1.39026.3.1.4.1.2.1.200
	branchActiveEnergy49 OBJECT-TYPE
	SYNTAX Integer32
	MAX-ACCESS read-only
	STATUS current
	DESCRIPTION
	"Description: "
	::= { powerMeterAMYDBEntry 200 }

-- .1.3.6.1.4.1.39026.3.1.4.1.2.1.201
-- .1.3.6.1.4.1.39026.3.1.4.1.2.1.201
-- .1.3.6.1.4.1.39026.3.1.4.1.2.1.201
-- .1.3.6.1.4.1.39026.3.1.4.1.2.1.201
	branchVoltage50 OBJECT-TYPE
	SYNTAX Integer32
	MAX-ACCESS read-only
	STATUS current
	DESCRIPTION
	"Description: "
	::= { powerMeterAMYDBEntry 201 }

-- .1.3.6.1.4.1.39026.3.1.4.1.2.1.202
-- .1.3.6.1.4.1.39026.3.1.4.1.2.1.202
-- .1.3.6.1.4.1.39026.3.1.4.1.2.1.202
-- .1.3.6.1.4.1.39026.3.1.4.1.2.1.202
	branchCurrent50 OBJECT-TYPE
	SYNTAX Integer32
	MAX-ACCESS read-only
	STATUS current
	DESCRIPTION
	"Description: "
	::= { powerMeterAMYDBEntry 202 }

-- .1.3.6.1.4.1.39026.3.1.4.1.2.1.203
-- .1.3.6.1.4.1.39026.3.1.4.1.2.1.203
-- .1.3.6.1.4.1.39026.3.1.4.1.2.1.203
-- .1.3.6.1.4.1.39026.3.1.4.1.2.1.203
	branchActivePower50 OBJECT-TYPE
	SYNTAX Integer32
	MAX-ACCESS read-only
	STATUS current
	DESCRIPTION
	"Description: "
	::= { powerMeterAMYDBEntry 203 }

-- .1.3.6.1.4.1.39026.3.1.4.1.2.1.204
-- .1.3.6.1.4.1.39026.3.1.4.1.2.1.204
-- .1.3.6.1.4.1.39026.3.1.4.1.2.1.204
-- .1.3.6.1.4.1.39026.3.1.4.1.2.1.204
	branchActiveEnergy50 OBJECT-TYPE
	SYNTAX Integer32
	MAX-ACCESS read-only
	STATUS current
	DESCRIPTION
	"Description: "
	::= { powerMeterAMYDBEntry 204 }

-- .1.3.6.1.4.1.39026.3.1.4.1.2.1.205
-- .1.3.6.1.4.1.39026.3.1.4.1.2.1.205
-- .1.3.6.1.4.1.39026.3.1.4.1.2.1.205
-- .1.3.6.1.4.1.39026.3.1.4.1.2.1.205
	branchVoltage51 OBJECT-TYPE
	SYNTAX Integer32
	MAX-ACCESS read-only
	STATUS current
	DESCRIPTION
	"Description: "
	::= { powerMeterAMYDBEntry 205 }

-- .1.3.6.1.4.1.39026.3.1.4.1.2.1.206
-- .1.3.6.1.4.1.39026.3.1.4.1.2.1.206
-- .1.3.6.1.4.1.39026.3.1.4.1.2.1.206
-- .1.3.6.1.4.1.39026.3.1.4.1.2.1.206
	branchCurrent51 OBJECT-TYPE
	SYNTAX Integer32
	MAX-ACCESS read-only
	STATUS current
	DESCRIPTION
	"Description: "
	::= { powerMeterAMYDBEntry 206 }

-- .1.3.6.1.4.1.39026.3.1.4.1.2.1.207
-- .1.3.6.1.4.1.39026.3.1.4.1.2.1.207
-- .1.3.6.1.4.1.39026.3.1.4.1.2.1.207
-- .1.3.6.1.4.1.39026.3.1.4.1.2.1.207
	branchActivePower51 OBJECT-TYPE
	SYNTAX Integer32
	MAX-ACCESS read-only
	STATUS current
	DESCRIPTION
	"Description: "
	::= { powerMeterAMYDBEntry 207 }

-- .1.3.6.1.4.1.39026.3.1.4.1.2.1.208
-- .1.3.6.1.4.1.39026.3.1.4.1.2.1.208
-- .1.3.6.1.4.1.39026.3.1.4.1.2.1.208
-- .1.3.6.1.4.1.39026.3.1.4.1.2.1.208
	branchActiveEnergy51 OBJECT-TYPE
	SYNTAX Integer32
	MAX-ACCESS read-only
	STATUS current
	DESCRIPTION
	"Description: "
	::= { powerMeterAMYDBEntry 208 }

-- .1.3.6.1.4.1.39026.3.1.4.1.2.1.209
-- .1.3.6.1.4.1.39026.3.1.4.1.2.1.209
-- .1.3.6.1.4.1.39026.3.1.4.1.2.1.209
-- .1.3.6.1.4.1.39026.3.1.4.1.2.1.209
	branchVoltage52 OBJECT-TYPE
	SYNTAX Integer32
	MAX-ACCESS read-only
	STATUS current
	DESCRIPTION
	"Description: "
	::= { powerMeterAMYDBEntry 209 }

-- .1.3.6.1.4.1.39026.3.1.4.1.2.1.210
-- .1.3.6.1.4.1.39026.3.1.4.1.2.1.210
-- .1.3.6.1.4.1.39026.3.1.4.1.2.1.210
-- .1.3.6.1.4.1.39026.3.1.4.1.2.1.210
	branchCurrent52 OBJECT-TYPE
	SYNTAX Integer32
	MAX-ACCESS read-only
	STATUS current
	DESCRIPTION
	"Description: "
	::= { powerMeterAMYDBEntry 210 }

-- .1.3.6.1.4.1.39026.3.1.4.1.2.1.211
-- .1.3.6.1.4.1.39026.3.1.4.1.2.1.211
-- .1.3.6.1.4.1.39026.3.1.4.1.2.1.211
-- .1.3.6.1.4.1.39026.3.1.4.1.2.1.211
	branchActivePower52 OBJECT-TYPE
	SYNTAX Integer32
	MAX-ACCESS read-only
	STATUS current
	DESCRIPTION
	"Description: "
	::= { powerMeterAMYDBEntry 211 }

-- .1.3.6.1.4.1.39026.3.1.4.1.2.1.212
-- .1.3.6.1.4.1.39026.3.1.4.1.2.1.212
-- .1.3.6.1.4.1.39026.3.1.4.1.2.1.212
-- .1.3.6.1.4.1.39026.3.1.4.1.2.1.212
	branchActiveEnergy52 OBJECT-TYPE
	SYNTAX Integer32
	MAX-ACCESS read-only
	STATUS current
	DESCRIPTION
	"Description: "
	::= { powerMeterAMYDBEntry 212 }

-- .1.3.6.1.4.1.39026.3.1.4.1.2.1.213
-- .1.3.6.1.4.1.39026.3.1.4.1.2.1.213
-- .1.3.6.1.4.1.39026.3.1.4.1.2.1.213
-- .1.3.6.1.4.1.39026.3.1.4.1.2.1.213
	branchVoltage53 OBJECT-TYPE
	SYNTAX Integer32
	MAX-ACCESS read-only
	STATUS current
	DESCRIPTION
	"Description: "
	::= { powerMeterAMYDBEntry 213 }

-- .1.3.6.1.4.1.39026.3.1.4.1.2.1.214
-- .1.3.6.1.4.1.39026.3.1.4.1.2.1.214
-- .1.3.6.1.4.1.39026.3.1.4.1.2.1.214
-- .1.3.6.1.4.1.39026.3.1.4.1.2.1.214
	branchCurrent53 OBJECT-TYPE
	SYNTAX Integer32
	MAX-ACCESS read-only
	STATUS current
	DESCRIPTION
	"Description: "
	::= { powerMeterAMYDBEntry 214 }

-- .1.3.6.1.4.1.39026.3.1.4.1.2.1.215
-- .1.3.6.1.4.1.39026.3.1.4.1.2.1.215
-- .1.3.6.1.4.1.39026.3.1.4.1.2.1.215
-- .1.3.6.1.4.1.39026.3.1.4.1.2.1.215
	branchActivePower53 OBJECT-TYPE
	SYNTAX Integer32
	MAX-ACCESS read-only
	STATUS current
	DESCRIPTION
	"Description: "
	::= { powerMeterAMYDBEntry 215 }

-- .1.3.6.1.4.1.39026.3.1.4.1.2.1.216
-- .1.3.6.1.4.1.39026.3.1.4.1.2.1.216
-- .1.3.6.1.4.1.39026.3.1.4.1.2.1.216
-- .1.3.6.1.4.1.39026.3.1.4.1.2.1.216
	branchActiveEnergy53 OBJECT-TYPE
	SYNTAX Integer32
	MAX-ACCESS read-only
	STATUS current
	DESCRIPTION
	"Description: "
	::= { powerMeterAMYDBEntry 216 }

-- .1.3.6.1.4.1.39026.3.1.4.1.2.1.217
-- .1.3.6.1.4.1.39026.3.1.4.1.2.1.217
-- .1.3.6.1.4.1.39026.3.1.4.1.2.1.217
-- .1.3.6.1.4.1.39026.3.1.4.1.2.1.217
	branchVoltage54 OBJECT-TYPE
	SYNTAX Integer32
	MAX-ACCESS read-only
	STATUS current
	DESCRIPTION
	"Description: "
	::= { powerMeterAMYDBEntry 217 }

-- .1.3.6.1.4.1.39026.3.1.4.1.2.1.218
-- .1.3.6.1.4.1.39026.3.1.4.1.2.1.218
-- .1.3.6.1.4.1.39026.3.1.4.1.2.1.218
-- .1.3.6.1.4.1.39026.3.1.4.1.2.1.218
	branchCurrent54 OBJECT-TYPE
	SYNTAX Integer32
	MAX-ACCESS read-only
	STATUS current
	DESCRIPTION
	"Description: "
	::= { powerMeterAMYDBEntry 218 }

-- .1.3.6.1.4.1.39026.3.1.4.1.2.1.219
-- .1.3.6.1.4.1.39026.3.1.4.1.2.1.219
-- .1.3.6.1.4.1.39026.3.1.4.1.2.1.219
-- .1.3.6.1.4.1.39026.3.1.4.1.2.1.219
	branchActivePower54 OBJECT-TYPE
	SYNTAX Integer32
	MAX-ACCESS read-only
	STATUS current
	DESCRIPTION
	"Description: "
	::= { powerMeterAMYDBEntry 219 }

-- .1.3.6.1.4.1.39026.3.1.4.1.2.1.220
-- .1.3.6.1.4.1.39026.3.1.4.1.2.1.220
-- .1.3.6.1.4.1.39026.3.1.4.1.2.1.220
-- .1.3.6.1.4.1.39026.3.1.4.1.2.1.220
	branchActiveEnergy54 OBJECT-TYPE
	SYNTAX Integer32
	MAX-ACCESS read-only
	STATUS current
	DESCRIPTION
	"Description: "
	::= { powerMeterAMYDBEntry 220 }

-- .1.3.6.1.4.1.39026.3.1.4.1.2.1.221
-- .1.3.6.1.4.1.39026.3.1.4.1.2.1.221
-- .1.3.6.1.4.1.39026.3.1.4.1.2.1.221
-- .1.3.6.1.4.1.39026.3.1.4.1.2.1.221
	branchVoltage55 OBJECT-TYPE
	SYNTAX Integer32
	MAX-ACCESS read-only
	STATUS current
	DESCRIPTION
	"Description: "
	::= { powerMeterAMYDBEntry 221 }

-- .1.3.6.1.4.1.39026.3.1.4.1.2.1.222
-- .1.3.6.1.4.1.39026.3.1.4.1.2.1.222
-- .1.3.6.1.4.1.39026.3.1.4.1.2.1.222
-- .1.3.6.1.4.1.39026.3.1.4.1.2.1.222
	branchCurrent55 OBJECT-TYPE
	SYNTAX Integer32
	MAX-ACCESS read-only
	STATUS current
	DESCRIPTION
	"Description: "
	::= { powerMeterAMYDBEntry 222 }

-- .1.3.6.1.4.1.39026.3.1.4.1.2.1.223
-- .1.3.6.1.4.1.39026.3.1.4.1.2.1.223
-- .1.3.6.1.4.1.39026.3.1.4.1.2.1.223
-- .1.3.6.1.4.1.39026.3.1.4.1.2.1.223
	branchActivePower55 OBJECT-TYPE
	SYNTAX Integer32
	MAX-ACCESS read-only
	STATUS current
	DESCRIPTION
	"Description: "
	::= { powerMeterAMYDBEntry 223 }

-- .1.3.6.1.4.1.39026.3.1.4.1.2.1.224
-- .1.3.6.1.4.1.39026.3.1.4.1.2.1.224
-- .1.3.6.1.4.1.39026.3.1.4.1.2.1.224
-- .1.3.6.1.4.1.39026.3.1.4.1.2.1.224
	branchActiveEnergy55 OBJECT-TYPE
	SYNTAX Integer32
	MAX-ACCESS read-only
	STATUS current
	DESCRIPTION
	"Description: "
	::= { powerMeterAMYDBEntry 224 }

-- .1.3.6.1.4.1.39026.3.1.4.1.2.1.225
-- .1.3.6.1.4.1.39026.3.1.4.1.2.1.225
-- .1.3.6.1.4.1.39026.3.1.4.1.2.1.225
-- .1.3.6.1.4.1.39026.3.1.4.1.2.1.225
	branchVoltage56 OBJECT-TYPE
	SYNTAX Integer32
	MAX-ACCESS read-only
	STATUS current
	DESCRIPTION
	"Description: "
	::= { powerMeterAMYDBEntry 225 }

-- .1.3.6.1.4.1.39026.3.1.4.1.2.1.226
-- .1.3.6.1.4.1.39026.3.1.4.1.2.1.226
-- .1.3.6.1.4.1.39026.3.1.4.1.2.1.226
-- .1.3.6.1.4.1.39026.3.1.4.1.2.1.226
	branchCurrent56 OBJECT-TYPE
	SYNTAX Integer32
	MAX-ACCESS read-only
	STATUS current
	DESCRIPTION
	"Description: "
	::= { powerMeterAMYDBEntry 226 }

-- .1.3.6.1.4.1.39026.3.1.4.1.2.1.227
-- .1.3.6.1.4.1.39026.3.1.4.1.2.1.227
-- .1.3.6.1.4.1.39026.3.1.4.1.2.1.227
-- .1.3.6.1.4.1.39026.3.1.4.1.2.1.227
	branchActivePower56 OBJECT-TYPE
	SYNTAX Integer32
	MAX-ACCESS read-only
	STATUS current
	DESCRIPTION
	"Description: "
	::= { powerMeterAMYDBEntry 227 }

-- .1.3.6.1.4.1.39026.3.1.4.1.2.1.228
-- .1.3.6.1.4.1.39026.3.1.4.1.2.1.228
-- .1.3.6.1.4.1.39026.3.1.4.1.2.1.228
-- .1.3.6.1.4.1.39026.3.1.4.1.2.1.228
	branchActiveEnergy56 OBJECT-TYPE
	SYNTAX Integer32
	MAX-ACCESS read-only
	STATUS current
	DESCRIPTION
	"Description: "
	::= { powerMeterAMYDBEntry 228 }

-- .1.3.6.1.4.1.39026.3.1.4.1.2.1.229
-- .1.3.6.1.4.1.39026.3.1.4.1.2.1.229
-- .1.3.6.1.4.1.39026.3.1.4.1.2.1.229
-- .1.3.6.1.4.1.39026.3.1.4.1.2.1.229
	branchVoltage57 OBJECT-TYPE
	SYNTAX Integer32
	MAX-ACCESS read-only
	STATUS current
	DESCRIPTION
	"Description: "
	::= { powerMeterAMYDBEntry 229 }

-- .1.3.6.1.4.1.39026.3.1.4.1.2.1.230
-- .1.3.6.1.4.1.39026.3.1.4.1.2.1.230
-- .1.3.6.1.4.1.39026.3.1.4.1.2.1.230
-- .1.3.6.1.4.1.39026.3.1.4.1.2.1.230
	branchCurrent57 OBJECT-TYPE
	SYNTAX Integer32
	MAX-ACCESS read-only
	STATUS current
	DESCRIPTION
	"Description: "
	::= { powerMeterAMYDBEntry 230 }

-- .1.3.6.1.4.1.39026.3.1.4.1.2.1.231
-- .1.3.6.1.4.1.39026.3.1.4.1.2.1.231
-- .1.3.6.1.4.1.39026.3.1.4.1.2.1.231
-- .1.3.6.1.4.1.39026.3.1.4.1.2.1.231
	branchActivePower57 OBJECT-TYPE
	SYNTAX Integer32
	MAX-ACCESS read-only
	STATUS current
	DESCRIPTION
	"Description: "
	::= { powerMeterAMYDBEntry 231 }

-- .1.3.6.1.4.1.39026.3.1.4.1.2.1.232
-- .1.3.6.1.4.1.39026.3.1.4.1.2.1.232
-- .1.3.6.1.4.1.39026.3.1.4.1.2.1.232
-- .1.3.6.1.4.1.39026.3.1.4.1.2.1.232
	branchActiveEnergy57 OBJECT-TYPE
	SYNTAX Integer32
	MAX-ACCESS read-only
	STATUS current
	DESCRIPTION
	"Description: "
	::= { powerMeterAMYDBEntry 232 }

-- .1.3.6.1.4.1.39026.3.1.4.1.2.1.233
-- .1.3.6.1.4.1.39026.3.1.4.1.2.1.233
-- .1.3.6.1.4.1.39026.3.1.4.1.2.1.233
-- .1.3.6.1.4.1.39026.3.1.4.1.2.1.233
	branchVoltage58 OBJECT-TYPE
	SYNTAX Integer32
	MAX-ACCESS read-only
	STATUS current
	DESCRIPTION
	"Description: "
	::= { powerMeterAMYDBEntry 233 }

-- .1.3.6.1.4.1.39026.3.1.4.1.2.1.234
-- .1.3.6.1.4.1.39026.3.1.4.1.2.1.234
-- .1.3.6.1.4.1.39026.3.1.4.1.2.1.234
-- .1.3.6.1.4.1.39026.3.1.4.1.2.1.234
	branchCurrent58 OBJECT-TYPE
	SYNTAX Integer32
	MAX-ACCESS read-only
	STATUS current
	DESCRIPTION
	"Description: "
	::= { powerMeterAMYDBEntry 234 }

-- .1.3.6.1.4.1.39026.3.1.4.1.2.1.235
-- .1.3.6.1.4.1.39026.3.1.4.1.2.1.235
-- .1.3.6.1.4.1.39026.3.1.4.1.2.1.235
-- .1.3.6.1.4.1.39026.3.1.4.1.2.1.235
	branchActivePower58 OBJECT-TYPE
	SYNTAX Integer32
	MAX-ACCESS read-only
	STATUS current
	DESCRIPTION
	"Description: "
	::= { powerMeterAMYDBEntry 235 }

-- .1.3.6.1.4.1.39026.3.1.4.1.2.1.236
-- .1.3.6.1.4.1.39026.3.1.4.1.2.1.236
-- .1.3.6.1.4.1.39026.3.1.4.1.2.1.236
-- .1.3.6.1.4.1.39026.3.1.4.1.2.1.236
	branchActiveEnergy58 OBJECT-TYPE
	SYNTAX Integer32
	MAX-ACCESS read-only
	STATUS current
	DESCRIPTION
	"Description: "
	::= { powerMeterAMYDBEntry 236 }

-- .1.3.6.1.4.1.39026.3.1.4.1.2.1.237
-- .1.3.6.1.4.1.39026.3.1.4.1.2.1.237
-- .1.3.6.1.4.1.39026.3.1.4.1.2.1.237
-- .1.3.6.1.4.1.39026.3.1.4.1.2.1.237
	branchVoltage59 OBJECT-TYPE
	SYNTAX Integer32
	MAX-ACCESS read-only
	STATUS current
	DESCRIPTION
	"Description: "
	::= { powerMeterAMYDBEntry 237 }

-- .1.3.6.1.4.1.39026.3.1.4.1.2.1.238
-- .1.3.6.1.4.1.39026.3.1.4.1.2.1.238
-- .1.3.6.1.4.1.39026.3.1.4.1.2.1.238
-- .1.3.6.1.4.1.39026.3.1.4.1.2.1.238
	branchCurrent59 OBJECT-TYPE
	SYNTAX Integer32
	MAX-ACCESS read-only
	STATUS current
	DESCRIPTION
	"Description: "
	::= { powerMeterAMYDBEntry 238 }

-- .1.3.6.1.4.1.39026.3.1.4.1.2.1.239
-- .1.3.6.1.4.1.39026.3.1.4.1.2.1.239
-- .1.3.6.1.4.1.39026.3.1.4.1.2.1.239
-- .1.3.6.1.4.1.39026.3.1.4.1.2.1.239
	branchActivePower59 OBJECT-TYPE
	SYNTAX Integer32
	MAX-ACCESS read-only
	STATUS current
	DESCRIPTION
	"Description: "
	::= { powerMeterAMYDBEntry 239 }

-- .1.3.6.1.4.1.39026.3.1.4.1.2.1.240
-- .1.3.6.1.4.1.39026.3.1.4.1.2.1.240
-- .1.3.6.1.4.1.39026.3.1.4.1.2.1.240
-- .1.3.6.1.4.1.39026.3.1.4.1.2.1.240
	branchActiveEnergy59 OBJECT-TYPE
	SYNTAX Integer32
	MAX-ACCESS read-only
	STATUS current
	DESCRIPTION
	"Description: "
	::= { powerMeterAMYDBEntry 240 }

-- .1.3.6.1.4.1.39026.3.1.4.1.2.1.241
-- .1.3.6.1.4.1.39026.3.1.4.1.2.1.241
-- .1.3.6.1.4.1.39026.3.1.4.1.2.1.241
-- .1.3.6.1.4.1.39026.3.1.4.1.2.1.241
	branchVoltage60 OBJECT-TYPE
	SYNTAX Integer32
	MAX-ACCESS read-only
	STATUS current
	DESCRIPTION
	"Description: "
	::= { powerMeterAMYDBEntry 241 }

-- .1.3.6.1.4.1.39026.3.1.4.1.2.1.242
-- .1.3.6.1.4.1.39026.3.1.4.1.2.1.242
-- .1.3.6.1.4.1.39026.3.1.4.1.2.1.242
-- .1.3.6.1.4.1.39026.3.1.4.1.2.1.242
	branchCurrent60 OBJECT-TYPE
	SYNTAX Integer32
	MAX-ACCESS read-only
	STATUS current
	DESCRIPTION
	"Description: "
	::= { powerMeterAMYDBEntry 242 }

-- .1.3.6.1.4.1.39026.3.1.4.1.2.1.243
-- .1.3.6.1.4.1.39026.3.1.4.1.2.1.243
-- .1.3.6.1.4.1.39026.3.1.4.1.2.1.243
-- .1.3.6.1.4.1.39026.3.1.4.1.2.1.243
	branchActivePower60 OBJECT-TYPE
	SYNTAX Integer32
	MAX-ACCESS read-only
	STATUS current
	DESCRIPTION
	"Description: "
	::= { powerMeterAMYDBEntry 243 }

-- .1.3.6.1.4.1.39026.3.1.4.1.2.1.244
-- .1.3.6.1.4.1.39026.3.1.4.1.2.1.244
-- .1.3.6.1.4.1.39026.3.1.4.1.2.1.244
-- .1.3.6.1.4.1.39026.3.1.4.1.2.1.244
	branchActiveEnergy60 OBJECT-TYPE
	SYNTAX Integer32
	MAX-ACCESS read-only
	STATUS current
	DESCRIPTION
	"Description: "
	::= { powerMeterAMYDBEntry 244 }

-- .1.3.6.1.4.1.39026.3.1.4.1.2.1.245
-- .1.3.6.1.4.1.39026.3.1.4.1.2.1.245
-- .1.3.6.1.4.1.39026.3.1.4.1.2.1.245
-- .1.3.6.1.4.1.39026.3.1.4.1.2.1.245
	branchVoltage61 OBJECT-TYPE
	SYNTAX Integer32
	MAX-ACCESS read-only
	STATUS current
	DESCRIPTION
	"Description: "
	::= { powerMeterAMYDBEntry 245 }

-- .1.3.6.1.4.1.39026.3.1.4.1.2.1.246
-- .1.3.6.1.4.1.39026.3.1.4.1.2.1.246
-- .1.3.6.1.4.1.39026.3.1.4.1.2.1.246
-- .1.3.6.1.4.1.39026.3.1.4.1.2.1.246
	branchCurrent61 OBJECT-TYPE
	SYNTAX Integer32
	MAX-ACCESS read-only
	STATUS current
	DESCRIPTION
	"Description: "
	::= { powerMeterAMYDBEntry 246 }

-- .1.3.6.1.4.1.39026.3.1.4.1.2.1.247
-- .1.3.6.1.4.1.39026.3.1.4.1.2.1.247
-- .1.3.6.1.4.1.39026.3.1.4.1.2.1.247
-- .1.3.6.1.4.1.39026.3.1.4.1.2.1.247
	branchActivePower61 OBJECT-TYPE
	SYNTAX Integer32
	MAX-ACCESS read-only
	STATUS current
	DESCRIPTION
	"Description: "
	::= { powerMeterAMYDBEntry 247 }

-- .1.3.6.1.4.1.39026.3.1.4.1.2.1.248
-- .1.3.6.1.4.1.39026.3.1.4.1.2.1.248
-- .1.3.6.1.4.1.39026.3.1.4.1.2.1.248
-- .1.3.6.1.4.1.39026.3.1.4.1.2.1.248
	branchActiveEnergy61 OBJECT-TYPE
	SYNTAX Integer32
	MAX-ACCESS read-only
	STATUS current
	DESCRIPTION
	"Description: "
	::= { powerMeterAMYDBEntry 248 }

-- .1.3.6.1.4.1.39026.3.1.4.1.2.1.249
-- .1.3.6.1.4.1.39026.3.1.4.1.2.1.249
-- .1.3.6.1.4.1.39026.3.1.4.1.2.1.249
-- .1.3.6.1.4.1.39026.3.1.4.1.2.1.249
	branchVoltage62 OBJECT-TYPE
	SYNTAX Integer32
	MAX-ACCESS read-only
	STATUS current
	DESCRIPTION
	"Description: "
	::= { powerMeterAMYDBEntry 249 }

-- .1.3.6.1.4.1.39026.3.1.4.1.2.1.250
-- .1.3.6.1.4.1.39026.3.1.4.1.2.1.250
-- .1.3.6.1.4.1.39026.3.1.4.1.2.1.250
-- .1.3.6.1.4.1.39026.3.1.4.1.2.1.250
	branchCurrent62 OBJECT-TYPE
	SYNTAX Integer32
	MAX-ACCESS read-only
	STATUS current
	DESCRIPTION
	"Description: "
	::= { powerMeterAMYDBEntry 250 }

-- .1.3.6.1.4.1.39026.3.1.4.1.2.1.251
-- .1.3.6.1.4.1.39026.3.1.4.1.2.1.251
-- .1.3.6.1.4.1.39026.3.1.4.1.2.1.251
-- .1.3.6.1.4.1.39026.3.1.4.1.2.1.251
	branchActivePower62 OBJECT-TYPE
	SYNTAX Integer32
	MAX-ACCESS read-only
	STATUS current
	DESCRIPTION
	"Description: "
	::= { powerMeterAMYDBEntry 251 }

-- .1.3.6.1.4.1.39026.3.1.4.1.2.1.252
-- .1.3.6.1.4.1.39026.3.1.4.1.2.1.252
-- .1.3.6.1.4.1.39026.3.1.4.1.2.1.252
-- .1.3.6.1.4.1.39026.3.1.4.1.2.1.252
	branchActiveEnergy62 OBJECT-TYPE
	SYNTAX Integer32
	MAX-ACCESS read-only
	STATUS current
	DESCRIPTION
	"Description: "
	::= { powerMeterAMYDBEntry 252 }

-- .1.3.6.1.4.1.39026.3.1.4.1.2.1.253
-- .1.3.6.1.4.1.39026.3.1.4.1.2.1.253
-- .1.3.6.1.4.1.39026.3.1.4.1.2.1.253
-- .1.3.6.1.4.1.39026.3.1.4.1.2.1.253
	branchVoltage63 OBJECT-TYPE
	SYNTAX Integer32
	MAX-ACCESS read-only
	STATUS current
	DESCRIPTION
	"Description: "
	::= { powerMeterAMYDBEntry 253 }

-- .1.3.6.1.4.1.39026.3.1.4.1.2.1.254
-- .1.3.6.1.4.1.39026.3.1.4.1.2.1.254
-- .1.3.6.1.4.1.39026.3.1.4.1.2.1.254
-- .1.3.6.1.4.1.39026.3.1.4.1.2.1.254
	branchCurrent63 OBJECT-TYPE
	SYNTAX Integer32
	MAX-ACCESS read-only
	STATUS current
	DESCRIPTION
	"Description: "
	::= { powerMeterAMYDBEntry 254 }

-- .1.3.6.1.4.1.39026.3.1.4.1.2.1.255
-- .1.3.6.1.4.1.39026.3.1.4.1.2.1.255
-- .1.3.6.1.4.1.39026.3.1.4.1.2.1.255
-- .1.3.6.1.4.1.39026.3.1.4.1.2.1.255
	branchActivePower63 OBJECT-TYPE
	SYNTAX Integer32
	MAX-ACCESS read-only
	STATUS current
	DESCRIPTION
	"Description: "
	::= { powerMeterAMYDBEntry 255 }

-- .1.3.6.1.4.1.39026.3.1.4.1.2.1.256
-- .1.3.6.1.4.1.39026.3.1.4.1.2.1.256
-- .1.3.6.1.4.1.39026.3.1.4.1.2.1.256
-- .1.3.6.1.4.1.39026.3.1.4.1.2.1.256
	branchActiveEnergy63 OBJECT-TYPE
	SYNTAX Integer32
	MAX-ACCESS read-only
	STATUS current
	DESCRIPTION
	"Description: "
	::= { powerMeterAMYDBEntry 256 }

-- .1.3.6.1.4.1.39026.3.1.4.1.2.1.257
-- .1.3.6.1.4.1.39026.3.1.4.1.2.1.257
-- .1.3.6.1.4.1.39026.3.1.4.1.2.1.257
-- .1.3.6.1.4.1.39026.3.1.4.1.2.1.257
	branchVoltage64 OBJECT-TYPE
	SYNTAX Integer32
	MAX-ACCESS read-only
	STATUS current
	DESCRIPTION
	"Description: "
	::= { powerMeterAMYDBEntry 257 }

-- .1.3.6.1.4.1.39026.3.1.4.1.2.1.258
-- .1.3.6.1.4.1.39026.3.1.4.1.2.1.258
-- .1.3.6.1.4.1.39026.3.1.4.1.2.1.258
-- .1.3.6.1.4.1.39026.3.1.4.1.2.1.258
	branchCurrent64 OBJECT-TYPE
	SYNTAX Integer32
	MAX-ACCESS read-only
	STATUS current
	DESCRIPTION
	"Description: "
	::= { powerMeterAMYDBEntry 258 }

-- .1.3.6.1.4.1.39026.3.1.4.1.2.1.259
-- .1.3.6.1.4.1.39026.3.1.4.1.2.1.259
-- .1.3.6.1.4.1.39026.3.1.4.1.2.1.259
-- .1.3.6.1.4.1.39026.3.1.4.1.2.1.259
	branchActivePower64 OBJECT-TYPE
	SYNTAX Integer32
	MAX-ACCESS read-only
	STATUS current
	DESCRIPTION
	"Description: "
	::= { powerMeterAMYDBEntry 259 }

-- .1.3.6.1.4.1.39026.3.1.4.1.2.1.260
-- .1.3.6.1.4.1.39026.3.1.4.1.2.1.260
-- .1.3.6.1.4.1.39026.3.1.4.1.2.1.260
-- .1.3.6.1.4.1.39026.3.1.4.1.2.1.260
	branchActiveEnergy64 OBJECT-TYPE
	SYNTAX Integer32
	MAX-ACCESS read-only
	STATUS current
	DESCRIPTION
	"Description: "
	::= { powerMeterAMYDBEntry 260 }

-- .1.3.6.1.4.1.39026.3.1.4.1.2.1.261
-- .1.3.6.1.4.1.39026.3.1.4.1.2.1.261
-- .1.3.6.1.4.1.39026.3.1.4.1.2.1.261
-- .1.3.6.1.4.1.39026.3.1.4.1.2.1.261
	branchVoltage65 OBJECT-TYPE
	SYNTAX Integer32
	MAX-ACCESS read-only
	STATUS current
	DESCRIPTION
	"Description: "
	::= { powerMeterAMYDBEntry 261 }

-- .1.3.6.1.4.1.39026.3.1.4.1.2.1.262
-- .1.3.6.1.4.1.39026.3.1.4.1.2.1.262
-- .1.3.6.1.4.1.39026.3.1.4.1.2.1.262
-- .1.3.6.1.4.1.39026.3.1.4.1.2.1.262
	branchCurrent65 OBJECT-TYPE
	SYNTAX Integer32
	MAX-ACCESS read-only
	STATUS current
	DESCRIPTION
	"Description: "
	::= { powerMeterAMYDBEntry 262 }

-- .1.3.6.1.4.1.39026.3.1.4.1.2.1.263
-- .1.3.6.1.4.1.39026.3.1.4.1.2.1.263
-- .1.3.6.1.4.1.39026.3.1.4.1.2.1.263
-- .1.3.6.1.4.1.39026.3.1.4.1.2.1.263
	branchActivePower65 OBJECT-TYPE
	SYNTAX Integer32
	MAX-ACCESS read-only
	STATUS current
	DESCRIPTION
	"Description: "
	::= { powerMeterAMYDBEntry 263 }

-- .1.3.6.1.4.1.39026.3.1.4.1.2.1.264
-- .1.3.6.1.4.1.39026.3.1.4.1.2.1.264
-- .1.3.6.1.4.1.39026.3.1.4.1.2.1.264
-- .1.3.6.1.4.1.39026.3.1.4.1.2.1.264
	branchActiveEnergy65 OBJECT-TYPE
	SYNTAX Integer32
	MAX-ACCESS read-only
	STATUS current
	DESCRIPTION
	"Description: "
	::= { powerMeterAMYDBEntry 264 }

-- .1.3.6.1.4.1.39026.3.1.4.1.2.1.265
-- .1.3.6.1.4.1.39026.3.1.4.1.2.1.265
-- .1.3.6.1.4.1.39026.3.1.4.1.2.1.265
-- .1.3.6.1.4.1.39026.3.1.4.1.2.1.265
	branchVoltage66 OBJECT-TYPE
	SYNTAX Integer32
	MAX-ACCESS read-only
	STATUS current
	DESCRIPTION
	"Description: "
	::= { powerMeterAMYDBEntry 265 }

-- .1.3.6.1.4.1.39026.3.1.4.1.2.1.266
-- .1.3.6.1.4.1.39026.3.1.4.1.2.1.266
-- .1.3.6.1.4.1.39026.3.1.4.1.2.1.266
-- .1.3.6.1.4.1.39026.3.1.4.1.2.1.266
	branchCurrent66 OBJECT-TYPE
	SYNTAX Integer32
	MAX-ACCESS read-only
	STATUS current
	DESCRIPTION
	"Description: "
	::= { powerMeterAMYDBEntry 266 }

-- .1.3.6.1.4.1.39026.3.1.4.1.2.1.267
-- .1.3.6.1.4.1.39026.3.1.4.1.2.1.267
-- .1.3.6.1.4.1.39026.3.1.4.1.2.1.267
-- .1.3.6.1.4.1.39026.3.1.4.1.2.1.267
	branchActivePower66 OBJECT-TYPE
	SYNTAX Integer32
	MAX-ACCESS read-only
	STATUS current
	DESCRIPTION
	"Description: "
	::= { powerMeterAMYDBEntry 267 }

-- .1.3.6.1.4.1.39026.3.1.4.1.2.1.268
-- .1.3.6.1.4.1.39026.3.1.4.1.2.1.268
-- .1.3.6.1.4.1.39026.3.1.4.1.2.1.268
-- .1.3.6.1.4.1.39026.3.1.4.1.2.1.268
	branchActiveEnergy66 OBJECT-TYPE
	SYNTAX Integer32
	MAX-ACCESS read-only
	STATUS current
	DESCRIPTION
	"Description: "
	::= { powerMeterAMYDBEntry 268 }

-- .1.3.6.1.4.1.39026.3.1.4.1.2.1.269
-- .1.3.6.1.4.1.39026.3.1.4.1.2.1.269
-- .1.3.6.1.4.1.39026.3.1.4.1.2.1.269
-- .1.3.6.1.4.1.39026.3.1.4.1.2.1.269
	branchVoltage67 OBJECT-TYPE
	SYNTAX Integer32
	MAX-ACCESS read-only
	STATUS current
	DESCRIPTION
	"Description: "
	::= { powerMeterAMYDBEntry 269 }

-- .1.3.6.1.4.1.39026.3.1.4.1.2.1.270
-- .1.3.6.1.4.1.39026.3.1.4.1.2.1.270
-- .1.3.6.1.4.1.39026.3.1.4.1.2.1.270
-- .1.3.6.1.4.1.39026.3.1.4.1.2.1.270
	branchCurrent67 OBJECT-TYPE
	SYNTAX Integer32
	MAX-ACCESS read-only
	STATUS current
	DESCRIPTION
	"Description: "
	::= { powerMeterAMYDBEntry 270 }

-- .1.3.6.1.4.1.39026.3.1.4.1.2.1.271
-- .1.3.6.1.4.1.39026.3.1.4.1.2.1.271
-- .1.3.6.1.4.1.39026.3.1.4.1.2.1.271
-- .1.3.6.1.4.1.39026.3.1.4.1.2.1.271
	branchActivePower67 OBJECT-TYPE
	SYNTAX Integer32
	MAX-ACCESS read-only
	STATUS current
	DESCRIPTION
	"Description: "
	::= { powerMeterAMYDBEntry 271 }

-- .1.3.6.1.4.1.39026.3.1.4.1.2.1.272
-- .1.3.6.1.4.1.39026.3.1.4.1.2.1.272
-- .1.3.6.1.4.1.39026.3.1.4.1.2.1.272
-- .1.3.6.1.4.1.39026.3.1.4.1.2.1.272
	branchActiveEnergy67 OBJECT-TYPE
	SYNTAX Integer32
	MAX-ACCESS read-only
	STATUS current
	DESCRIPTION
	"Description: "
	::= { powerMeterAMYDBEntry 272 }

-- .1.3.6.1.4.1.39026.3.1.4.1.2.1.273
-- .1.3.6.1.4.1.39026.3.1.4.1.2.1.273
-- .1.3.6.1.4.1.39026.3.1.4.1.2.1.273
-- .1.3.6.1.4.1.39026.3.1.4.1.2.1.273
	branchVoltage68 OBJECT-TYPE
	SYNTAX Integer32
	MAX-ACCESS read-only
	STATUS current
	DESCRIPTION
	"Description: "
	::= { powerMeterAMYDBEntry 273 }

-- .1.3.6.1.4.1.39026.3.1.4.1.2.1.274
-- .1.3.6.1.4.1.39026.3.1.4.1.2.1.274
-- .1.3.6.1.4.1.39026.3.1.4.1.2.1.274
-- .1.3.6.1.4.1.39026.3.1.4.1.2.1.274
	branchCurrent68 OBJECT-TYPE
	SYNTAX Integer32
	MAX-ACCESS read-only
	STATUS current
	DESCRIPTION
	"Description: "
	::= { powerMeterAMYDBEntry 274 }

-- .1.3.6.1.4.1.39026.3.1.4.1.2.1.275
-- .1.3.6.1.4.1.39026.3.1.4.1.2.1.275
-- .1.3.6.1.4.1.39026.3.1.4.1.2.1.275
-- .1.3.6.1.4.1.39026.3.1.4.1.2.1.275
	branchActivePower68 OBJECT-TYPE
	SYNTAX Integer32
	MAX-ACCESS read-only
	STATUS current
	DESCRIPTION
	"Description: "
	::= { powerMeterAMYDBEntry 275 }

-- .1.3.6.1.4.1.39026.3.1.4.1.2.1.276
-- .1.3.6.1.4.1.39026.3.1.4.1.2.1.276
-- .1.3.6.1.4.1.39026.3.1.4.1.2.1.276
-- .1.3.6.1.4.1.39026.3.1.4.1.2.1.276
	branchActiveEnergy68 OBJECT-TYPE
	SYNTAX Integer32
	MAX-ACCESS read-only
	STATUS current
	DESCRIPTION
	"Description: "
	::= { powerMeterAMYDBEntry 276 }

-- .1.3.6.1.4.1.39026.3.1.4.1.2.1.277
-- .1.3.6.1.4.1.39026.3.1.4.1.2.1.277
-- .1.3.6.1.4.1.39026.3.1.4.1.2.1.277
-- .1.3.6.1.4.1.39026.3.1.4.1.2.1.277
	branchVoltage69 OBJECT-TYPE
	SYNTAX Integer32
	MAX-ACCESS read-only
	STATUS current
	DESCRIPTION
	"Description: "
	::= { powerMeterAMYDBEntry 277 }

-- .1.3.6.1.4.1.39026.3.1.4.1.2.1.278
-- .1.3.6.1.4.1.39026.3.1.4.1.2.1.278
-- .1.3.6.1.4.1.39026.3.1.4.1.2.1.278
-- .1.3.6.1.4.1.39026.3.1.4.1.2.1.278
	branchCurrent69 OBJECT-TYPE
	SYNTAX Integer32
	MAX-ACCESS read-only
	STATUS current
	DESCRIPTION
	"Description: "
	::= { powerMeterAMYDBEntry 278 }

-- .1.3.6.1.4.1.39026.3.1.4.1.2.1.279
-- .1.3.6.1.4.1.39026.3.1.4.1.2.1.279
-- .1.3.6.1.4.1.39026.3.1.4.1.2.1.279
-- .1.3.6.1.4.1.39026.3.1.4.1.2.1.279
	branchActivePower69 OBJECT-TYPE
	SYNTAX Integer32
	MAX-ACCESS read-only
	STATUS current
	DESCRIPTION
	"Description: "
	::= { powerMeterAMYDBEntry 279 }

-- .1.3.6.1.4.1.39026.3.1.4.1.2.1.280
-- .1.3.6.1.4.1.39026.3.1.4.1.2.1.280
-- .1.3.6.1.4.1.39026.3.1.4.1.2.1.280
-- .1.3.6.1.4.1.39026.3.1.4.1.2.1.280
	branchActiveEnergy69 OBJECT-TYPE
	SYNTAX Integer32
	MAX-ACCESS read-only
	STATUS current
	DESCRIPTION
	"Description: "
	::= { powerMeterAMYDBEntry 280 }

-- .1.3.6.1.4.1.39026.3.1.4.1.2.1.281
-- .1.3.6.1.4.1.39026.3.1.4.1.2.1.281
-- .1.3.6.1.4.1.39026.3.1.4.1.2.1.281
-- .1.3.6.1.4.1.39026.3.1.4.1.2.1.281
	branchVoltage70 OBJECT-TYPE
	SYNTAX Integer32
	MAX-ACCESS read-only
	STATUS current
	DESCRIPTION
	"Description: "
	::= { powerMeterAMYDBEntry 281 }

-- .1.3.6.1.4.1.39026.3.1.4.1.2.1.282
-- .1.3.6.1.4.1.39026.3.1.4.1.2.1.282
-- .1.3.6.1.4.1.39026.3.1.4.1.2.1.282
-- .1.3.6.1.4.1.39026.3.1.4.1.2.1.282
	branchCurrent70 OBJECT-TYPE
	SYNTAX Integer32
	MAX-ACCESS read-only
	STATUS current
	DESCRIPTION
	"Description: "
	::= { powerMeterAMYDBEntry 282 }

-- .1.3.6.1.4.1.39026.3.1.4.1.2.1.283
-- .1.3.6.1.4.1.39026.3.1.4.1.2.1.283
-- .1.3.6.1.4.1.39026.3.1.4.1.2.1.283
-- .1.3.6.1.4.1.39026.3.1.4.1.2.1.283
	branchActivePower70 OBJECT-TYPE
	SYNTAX Integer32
	MAX-ACCESS read-only
	STATUS current
	DESCRIPTION
	"Description: "
	::= { powerMeterAMYDBEntry 283 }

-- .1.3.6.1.4.1.39026.3.1.4.1.2.1.284
-- .1.3.6.1.4.1.39026.3.1.4.1.2.1.284
-- .1.3.6.1.4.1.39026.3.1.4.1.2.1.284
-- .1.3.6.1.4.1.39026.3.1.4.1.2.1.284
	branchActiveEnergy70 OBJECT-TYPE
	SYNTAX Integer32
	MAX-ACCESS read-only
	STATUS current
	DESCRIPTION
	"Description: "
	::= { powerMeterAMYDBEntry 284 }

-- .1.3.6.1.4.1.39026.3.1.4.1.2.1.285
-- .1.3.6.1.4.1.39026.3.1.4.1.2.1.285
-- .1.3.6.1.4.1.39026.3.1.4.1.2.1.285
-- .1.3.6.1.4.1.39026.3.1.4.1.2.1.285
	branchVoltage71 OBJECT-TYPE
	SYNTAX Integer32
	MAX-ACCESS read-only
	STATUS current
	DESCRIPTION
	"Description: "
	::= { powerMeterAMYDBEntry 285 }

-- .1.3.6.1.4.1.39026.3.1.4.1.2.1.286
-- .1.3.6.1.4.1.39026.3.1.4.1.2.1.286
-- .1.3.6.1.4.1.39026.3.1.4.1.2.1.286
-- .1.3.6.1.4.1.39026.3.1.4.1.2.1.286
	branchCurrent71 OBJECT-TYPE
	SYNTAX Integer32
	MAX-ACCESS read-only
	STATUS current
	DESCRIPTION
	"Description: "
	::= { powerMeterAMYDBEntry 286 }

-- .1.3.6.1.4.1.39026.3.1.4.1.2.1.287
-- .1.3.6.1.4.1.39026.3.1.4.1.2.1.287
-- .1.3.6.1.4.1.39026.3.1.4.1.2.1.287
-- .1.3.6.1.4.1.39026.3.1.4.1.2.1.287
	branchActivePower71 OBJECT-TYPE
	SYNTAX Integer32
	MAX-ACCESS read-only
	STATUS current
	DESCRIPTION
	"Description: "
	::= { powerMeterAMYDBEntry 287 }

-- .1.3.6.1.4.1.39026.3.1.4.1.2.1.288
-- .1.3.6.1.4.1.39026.3.1.4.1.2.1.288
-- .1.3.6.1.4.1.39026.3.1.4.1.2.1.288
-- .1.3.6.1.4.1.39026.3.1.4.1.2.1.288
	branchActiveEnergy71 OBJECT-TYPE
	SYNTAX Integer32
	MAX-ACCESS read-only
	STATUS current
	DESCRIPTION
	"Description: "
	::= { powerMeterAMYDBEntry 288 }

-- .1.3.6.1.4.1.39026.3.1.4.1.2.1.289
-- .1.3.6.1.4.1.39026.3.1.4.1.2.1.289
-- .1.3.6.1.4.1.39026.3.1.4.1.2.1.289
-- .1.3.6.1.4.1.39026.3.1.4.1.2.1.289
	branchVoltage72 OBJECT-TYPE
	SYNTAX Integer32
	MAX-ACCESS read-only
	STATUS current
	DESCRIPTION
	"Description: "
	::= { powerMeterAMYDBEntry 289 }

-- .1.3.6.1.4.1.39026.3.1.4.1.2.1.290
-- .1.3.6.1.4.1.39026.3.1.4.1.2.1.290
-- .1.3.6.1.4.1.39026.3.1.4.1.2.1.290
-- .1.3.6.1.4.1.39026.3.1.4.1.2.1.290
	branchCurrent72 OBJECT-TYPE
	SYNTAX Integer32
	MAX-ACCESS read-only
	STATUS current
	DESCRIPTION
	"Description: "
	::= { powerMeterAMYDBEntry 290 }

-- .1.3.6.1.4.1.39026.3.1.4.1.2.1.291
-- .1.3.6.1.4.1.39026.3.1.4.1.2.1.291
-- .1.3.6.1.4.1.39026.3.1.4.1.2.1.291
-- .1.3.6.1.4.1.39026.3.1.4.1.2.1.291
	branchActivePower72 OBJECT-TYPE
	SYNTAX Integer32
	MAX-ACCESS read-only
	STATUS current
	DESCRIPTION
	"Description: "
	::= { powerMeterAMYDBEntry 291 }

-- .1.3.6.1.4.1.39026.3.1.4.1.2.1.292
-- .1.3.6.1.4.1.39026.3.1.4.1.2.1.292
-- .1.3.6.1.4.1.39026.3.1.4.1.2.1.292
-- .1.3.6.1.4.1.39026.3.1.4.1.2.1.292
	branchActiveEnergy72 OBJECT-TYPE
	SYNTAX Integer32
	MAX-ACCESS read-only
	STATUS current
	DESCRIPTION
	"Description: "
	::= { powerMeterAMYDBEntry 292 }

-- .1.3.6.1.4.1.39026.3.1.4.1.2.1.293
-- .1.3.6.1.4.1.39026.3.1.4.1.2.1.293
-- .1.3.6.1.4.1.39026.3.1.4.1.2.1.293
-- .1.3.6.1.4.1.39026.3.1.4.1.2.1.293
	branchVoltage73 OBJECT-TYPE
	SYNTAX Integer32
	MAX-ACCESS read-only
	STATUS current
	DESCRIPTION
	"Description: "
	::= { powerMeterAMYDBEntry 293 }

-- .1.3.6.1.4.1.39026.3.1.4.1.2.1.294
-- .1.3.6.1.4.1.39026.3.1.4.1.2.1.294
-- .1.3.6.1.4.1.39026.3.1.4.1.2.1.294
-- .1.3.6.1.4.1.39026.3.1.4.1.2.1.294
	branchCurrent73 OBJECT-TYPE
	SYNTAX Integer32
	MAX-ACCESS read-only
	STATUS current
	DESCRIPTION
	"Description: "
	::= { powerMeterAMYDBEntry 294 }

-- .1.3.6.1.4.1.39026.3.1.4.1.2.1.295
-- .1.3.6.1.4.1.39026.3.1.4.1.2.1.295
-- .1.3.6.1.4.1.39026.3.1.4.1.2.1.295
-- .1.3.6.1.4.1.39026.3.1.4.1.2.1.295
	branchActivePower73 OBJECT-TYPE
	SYNTAX Integer32
	MAX-ACCESS read-only
	STATUS current
	DESCRIPTION
	"Description: "
	::= { powerMeterAMYDBEntry 295 }

-- .1.3.6.1.4.1.39026.3.1.4.1.2.1.296
-- .1.3.6.1.4.1.39026.3.1.4.1.2.1.296
-- .1.3.6.1.4.1.39026.3.1.4.1.2.1.296
-- .1.3.6.1.4.1.39026.3.1.4.1.2.1.296
	branchActiveEnergy73 OBJECT-TYPE
	SYNTAX Integer32
	MAX-ACCESS read-only
	STATUS current
	DESCRIPTION
	"Description: "
	::= { powerMeterAMYDBEntry 296 }

-- .1.3.6.1.4.1.39026.3.1.4.1.2.1.297
-- .1.3.6.1.4.1.39026.3.1.4.1.2.1.297
-- .1.3.6.1.4.1.39026.3.1.4.1.2.1.297
-- .1.3.6.1.4.1.39026.3.1.4.1.2.1.297
	branchVoltage74 OBJECT-TYPE
	SYNTAX Integer32
	MAX-ACCESS read-only
	STATUS current
	DESCRIPTION
	"Description: "
	::= { powerMeterAMYDBEntry 297 }

-- .1.3.6.1.4.1.39026.3.1.4.1.2.1.298
-- .1.3.6.1.4.1.39026.3.1.4.1.2.1.298
-- .1.3.6.1.4.1.39026.3.1.4.1.2.1.298
-- .1.3.6.1.4.1.39026.3.1.4.1.2.1.298
	branchCurrent74 OBJECT-TYPE
	SYNTAX Integer32
	MAX-ACCESS read-only
	STATUS current
	DESCRIPTION
	"Description: "
	::= { powerMeterAMYDBEntry 298 }

-- .1.3.6.1.4.1.39026.3.1.4.1.2.1.299
-- .1.3.6.1.4.1.39026.3.1.4.1.2.1.299
-- .1.3.6.1.4.1.39026.3.1.4.1.2.1.299
-- .1.3.6.1.4.1.39026.3.1.4.1.2.1.299
	branchActivePower74 OBJECT-TYPE
	SYNTAX Integer32
	MAX-ACCESS read-only
	STATUS current
	DESCRIPTION
	"Description: "
	::= { powerMeterAMYDBEntry 299 }

-- .1.3.6.1.4.1.39026.3.1.4.1.2.1.300
-- .1.3.6.1.4.1.39026.3.1.4.1.2.1.300
-- .1.3.6.1.4.1.39026.3.1.4.1.2.1.300
-- .1.3.6.1.4.1.39026.3.1.4.1.2.1.300
	branchActiveEnergy74 OBJECT-TYPE
	SYNTAX Integer32
	MAX-ACCESS read-only
	STATUS current
	DESCRIPTION
	"Description: "
	::= { powerMeterAMYDBEntry 300 }

-- .1.3.6.1.4.1.39026.3.1.4.1.2.1.301
-- .1.3.6.1.4.1.39026.3.1.4.1.2.1.301
-- .1.3.6.1.4.1.39026.3.1.4.1.2.1.301
-- .1.3.6.1.4.1.39026.3.1.4.1.2.1.301
	branchVoltage75 OBJECT-TYPE
	SYNTAX Integer32
	MAX-ACCESS read-only
	STATUS current
	DESCRIPTION
	"Description: "
	::= { powerMeterAMYDBEntry 301 }

-- .1.3.6.1.4.1.39026.3.1.4.1.2.1.302
-- .1.3.6.1.4.1.39026.3.1.4.1.2.1.302
-- .1.3.6.1.4.1.39026.3.1.4.1.2.1.302
-- .1.3.6.1.4.1.39026.3.1.4.1.2.1.302
	branchCurrent75 OBJECT-TYPE
	SYNTAX Integer32
	MAX-ACCESS read-only
	STATUS current
	DESCRIPTION
	"Description: "
	::= { powerMeterAMYDBEntry 302 }

-- .1.3.6.1.4.1.39026.3.1.4.1.2.1.303
-- .1.3.6.1.4.1.39026.3.1.4.1.2.1.303
-- .1.3.6.1.4.1.39026.3.1.4.1.2.1.303
-- .1.3.6.1.4.1.39026.3.1.4.1.2.1.303
	branchActivePower75 OBJECT-TYPE
	SYNTAX Integer32
	MAX-ACCESS read-only
	STATUS current
	DESCRIPTION
	"Description: "
	::= { powerMeterAMYDBEntry 303 }

-- .1.3.6.1.4.1.39026.3.1.4.1.2.1.304
-- .1.3.6.1.4.1.39026.3.1.4.1.2.1.304
-- .1.3.6.1.4.1.39026.3.1.4.1.2.1.304
-- .1.3.6.1.4.1.39026.3.1.4.1.2.1.304
	branchActiveEnergy75 OBJECT-TYPE
	SYNTAX Integer32
	MAX-ACCESS read-only
	STATUS current
	DESCRIPTION
	"Description: "
	::= { powerMeterAMYDBEntry 304 }

-- .1.3.6.1.4.1.39026.3.1.4.1.2.1.305
-- .1.3.6.1.4.1.39026.3.1.4.1.2.1.305
-- .1.3.6.1.4.1.39026.3.1.4.1.2.1.305
-- .1.3.6.1.4.1.39026.3.1.4.1.2.1.305
	branchVoltage76 OBJECT-TYPE
	SYNTAX Integer32
	MAX-ACCESS read-only
	STATUS current
	DESCRIPTION
	"Description: "
	::= { powerMeterAMYDBEntry 305 }

-- .1.3.6.1.4.1.39026.3.1.4.1.2.1.306
-- .1.3.6.1.4.1.39026.3.1.4.1.2.1.306
-- .1.3.6.1.4.1.39026.3.1.4.1.2.1.306
-- .1.3.6.1.4.1.39026.3.1.4.1.2.1.306
	branchCurrent76 OBJECT-TYPE
	SYNTAX Integer32
	MAX-ACCESS read-only
	STATUS current
	DESCRIPTION
	"Description: "
	::= { powerMeterAMYDBEntry 306 }

-- .1.3.6.1.4.1.39026.3.1.4.1.2.1.307
-- .1.3.6.1.4.1.39026.3.1.4.1.2.1.307
-- .1.3.6.1.4.1.39026.3.1.4.1.2.1.307
-- .1.3.6.1.4.1.39026.3.1.4.1.2.1.307
	branchActivePower76 OBJECT-TYPE
	SYNTAX Integer32
	MAX-ACCESS read-only
	STATUS current
	DESCRIPTION
	"Description: "
	::= { powerMeterAMYDBEntry 307 }

-- .1.3.6.1.4.1.39026.3.1.4.1.2.1.308
-- .1.3.6.1.4.1.39026.3.1.4.1.2.1.308
-- .1.3.6.1.4.1.39026.3.1.4.1.2.1.308
-- .1.3.6.1.4.1.39026.3.1.4.1.2.1.308
	branchActiveEnergy76 OBJECT-TYPE
	SYNTAX Integer32
	MAX-ACCESS read-only
	STATUS current
	DESCRIPTION
	"Description: "
	::= { powerMeterAMYDBEntry 308 }

-- .1.3.6.1.4.1.39026.3.1.4.1.2.1.309
-- .1.3.6.1.4.1.39026.3.1.4.1.2.1.309
-- .1.3.6.1.4.1.39026.3.1.4.1.2.1.309
-- .1.3.6.1.4.1.39026.3.1.4.1.2.1.309
	branchVoltage77 OBJECT-TYPE
	SYNTAX Integer32
	MAX-ACCESS read-only
	STATUS current
	DESCRIPTION
	"Description: "
	::= { powerMeterAMYDBEntry 309 }

-- .1.3.6.1.4.1.39026.3.1.4.1.2.1.310
-- .1.3.6.1.4.1.39026.3.1.4.1.2.1.310
-- .1.3.6.1.4.1.39026.3.1.4.1.2.1.310
-- .1.3.6.1.4.1.39026.3.1.4.1.2.1.310
	branchCurrent77 OBJECT-TYPE
	SYNTAX Integer32
	MAX-ACCESS read-only
	STATUS current
	DESCRIPTION
	"Description: "
	::= { powerMeterAMYDBEntry 310 }

-- .1.3.6.1.4.1.39026.3.1.4.1.2.1.311
-- .1.3.6.1.4.1.39026.3.1.4.1.2.1.311
-- .1.3.6.1.4.1.39026.3.1.4.1.2.1.311
-- .1.3.6.1.4.1.39026.3.1.4.1.2.1.311
	branchActivePower77 OBJECT-TYPE
	SYNTAX Integer32
	MAX-ACCESS read-only
	STATUS current
	DESCRIPTION
	"Description: "
	::= { powerMeterAMYDBEntry 311 }

-- .1.3.6.1.4.1.39026.3.1.4.1.2.1.312
-- .1.3.6.1.4.1.39026.3.1.4.1.2.1.312
-- .1.3.6.1.4.1.39026.3.1.4.1.2.1.312
-- .1.3.6.1.4.1.39026.3.1.4.1.2.1.312
	branchActiveEnergy77 OBJECT-TYPE
	SYNTAX Integer32
	MAX-ACCESS read-only
	STATUS current
	DESCRIPTION
	"Description: "
	::= { powerMeterAMYDBEntry 312 }

-- .1.3.6.1.4.1.39026.3.1.4.1.2.1.313
-- .1.3.6.1.4.1.39026.3.1.4.1.2.1.313
-- .1.3.6.1.4.1.39026.3.1.4.1.2.1.313
-- .1.3.6.1.4.1.39026.3.1.4.1.2.1.313
	branchVoltage78 OBJECT-TYPE
	SYNTAX Integer32
	MAX-ACCESS read-only
	STATUS current
	DESCRIPTION
	"Description: "
	::= { powerMeterAMYDBEntry 313 }

-- .1.3.6.1.4.1.39026.3.1.4.1.2.1.314
-- .1.3.6.1.4.1.39026.3.1.4.1.2.1.314
-- .1.3.6.1.4.1.39026.3.1.4.1.2.1.314
-- .1.3.6.1.4.1.39026.3.1.4.1.2.1.314
	branchCurrent78 OBJECT-TYPE
	SYNTAX Integer32
	MAX-ACCESS read-only
	STATUS current
	DESCRIPTION
	"Description: "
	::= { powerMeterAMYDBEntry 314 }

-- .1.3.6.1.4.1.39026.3.1.4.1.2.1.315
-- .1.3.6.1.4.1.39026.3.1.4.1.2.1.315
-- .1.3.6.1.4.1.39026.3.1.4.1.2.1.315
-- .1.3.6.1.4.1.39026.3.1.4.1.2.1.315
	branchActivePower78 OBJECT-TYPE
	SYNTAX Integer32
	MAX-ACCESS read-only
	STATUS current
	DESCRIPTION
	"Description: "
	::= { powerMeterAMYDBEntry 315 }

-- .1.3.6.1.4.1.39026.3.1.4.1.2.1.316
-- .1.3.6.1.4.1.39026.3.1.4.1.2.1.316
-- .1.3.6.1.4.1.39026.3.1.4.1.2.1.316
-- .1.3.6.1.4.1.39026.3.1.4.1.2.1.316
	branchActiveEnergy78 OBJECT-TYPE
	SYNTAX Integer32
	MAX-ACCESS read-only
	STATUS current
	DESCRIPTION
	"Description: "
	::= { powerMeterAMYDBEntry 316 }

-- .1.3.6.1.4.1.39026.3.1.4.1.2.1.317
-- .1.3.6.1.4.1.39026.3.1.4.1.2.1.317
-- .1.3.6.1.4.1.39026.3.1.4.1.2.1.317
-- .1.3.6.1.4.1.39026.3.1.4.1.2.1.317
	branchVoltage79 OBJECT-TYPE
	SYNTAX Integer32
	MAX-ACCESS read-only
	STATUS current
	DESCRIPTION
	"Description: "
	::= { powerMeterAMYDBEntry 317 }

-- .1.3.6.1.4.1.39026.3.1.4.1.2.1.318
-- .1.3.6.1.4.1.39026.3.1.4.1.2.1.318
-- .1.3.6.1.4.1.39026.3.1.4.1.2.1.318
-- .1.3.6.1.4.1.39026.3.1.4.1.2.1.318
	branchCurrent79 OBJECT-TYPE
	SYNTAX Integer32
	MAX-ACCESS read-only
	STATUS current
	DESCRIPTION
	"Description: "
	::= { powerMeterAMYDBEntry 318 }

-- .1.3.6.1.4.1.39026.3.1.4.1.2.1.319
-- .1.3.6.1.4.1.39026.3.1.4.1.2.1.319
-- .1.3.6.1.4.1.39026.3.1.4.1.2.1.319
-- .1.3.6.1.4.1.39026.3.1.4.1.2.1.319
	branchActivePower79 OBJECT-TYPE
	SYNTAX Integer32
	MAX-ACCESS read-only
	STATUS current
	DESCRIPTION
	"Description: "
	::= { powerMeterAMYDBEntry 319 }

-- .1.3.6.1.4.1.39026.3.1.4.1.2.1.320
-- .1.3.6.1.4.1.39026.3.1.4.1.2.1.320
-- .1.3.6.1.4.1.39026.3.1.4.1.2.1.320
-- .1.3.6.1.4.1.39026.3.1.4.1.2.1.320
	branchActiveEnergy79 OBJECT-TYPE
	SYNTAX Integer32
	MAX-ACCESS read-only
	STATUS current
	DESCRIPTION
	"Description: "
	::= { powerMeterAMYDBEntry 320 }

-- .1.3.6.1.4.1.39026.3.1.4.1.2.1.321
-- .1.3.6.1.4.1.39026.3.1.4.1.2.1.321
-- .1.3.6.1.4.1.39026.3.1.4.1.2.1.321
-- .1.3.6.1.4.1.39026.3.1.4.1.2.1.321
	branchVoltage80 OBJECT-TYPE
	SYNTAX Integer32
	MAX-ACCESS read-only
	STATUS current
	DESCRIPTION
	"Description: "
	::= { powerMeterAMYDBEntry 321 }

-- .1.3.6.1.4.1.39026.3.1.4.1.2.1.322
-- .1.3.6.1.4.1.39026.3.1.4.1.2.1.322
-- .1.3.6.1.4.1.39026.3.1.4.1.2.1.322
-- .1.3.6.1.4.1.39026.3.1.4.1.2.1.322
	branchCurrent80 OBJECT-TYPE
	SYNTAX Integer32
	MAX-ACCESS read-only
	STATUS current
	DESCRIPTION
	"Description: "
	::= { powerMeterAMYDBEntry 322 }

-- .1.3.6.1.4.1.39026.3.1.4.1.2.1.323
-- .1.3.6.1.4.1.39026.3.1.4.1.2.1.323
-- .1.3.6.1.4.1.39026.3.1.4.1.2.1.323
-- .1.3.6.1.4.1.39026.3.1.4.1.2.1.323
	branchActivePower80 OBJECT-TYPE
	SYNTAX Integer32
	MAX-ACCESS read-only
	STATUS current
	DESCRIPTION
	"Description: "
	::= { powerMeterAMYDBEntry 323 }

-- .1.3.6.1.4.1.39026.3.1.4.1.2.1.324
-- .1.3.6.1.4.1.39026.3.1.4.1.2.1.324
-- .1.3.6.1.4.1.39026.3.1.4.1.2.1.324
-- .1.3.6.1.4.1.39026.3.1.4.1.2.1.324
	branchActiveEnergy80 OBJECT-TYPE
	SYNTAX Integer32
	MAX-ACCESS read-only
	STATUS current
	DESCRIPTION
	"Description: "
	::= { powerMeterAMYDBEntry 324 }

-- .1.3.6.1.4.1.39026.3.1.4.1.2.1.325
-- .1.3.6.1.4.1.39026.3.1.4.1.2.1.325
-- .1.3.6.1.4.1.39026.3.1.4.1.2.1.325
-- .1.3.6.1.4.1.39026.3.1.4.1.2.1.325
	branchVoltage81 OBJECT-TYPE
	SYNTAX Integer32
	MAX-ACCESS read-only
	STATUS current
	DESCRIPTION
	"Description: "
	::= { powerMeterAMYDBEntry 325 }

-- .1.3.6.1.4.1.39026.3.1.4.1.2.1.326
-- .1.3.6.1.4.1.39026.3.1.4.1.2.1.326
-- .1.3.6.1.4.1.39026.3.1.4.1.2.1.326
-- .1.3.6.1.4.1.39026.3.1.4.1.2.1.326
	branchCurrent81 OBJECT-TYPE
	SYNTAX Integer32
	MAX-ACCESS read-only
	STATUS current
	DESCRIPTION
	"Description: "
	::= { powerMeterAMYDBEntry 326 }

-- .1.3.6.1.4.1.39026.3.1.4.1.2.1.327
-- .1.3.6.1.4.1.39026.3.1.4.1.2.1.327
-- .1.3.6.1.4.1.39026.3.1.4.1.2.1.327
-- .1.3.6.1.4.1.39026.3.1.4.1.2.1.327
	branchActivePower81 OBJECT-TYPE
	SYNTAX Integer32
	MAX-ACCESS read-only
	STATUS current
	DESCRIPTION
	"Description: "
	::= { powerMeterAMYDBEntry 327 }

-- .1.3.6.1.4.1.39026.3.1.4.1.2.1.328
-- .1.3.6.1.4.1.39026.3.1.4.1.2.1.328
-- .1.3.6.1.4.1.39026.3.1.4.1.2.1.328
-- .1.3.6.1.4.1.39026.3.1.4.1.2.1.328
	branchActiveEnergy81 OBJECT-TYPE
	SYNTAX Integer32
	MAX-ACCESS read-only
	STATUS current
	DESCRIPTION
	"Description: "
	::= { powerMeterAMYDBEntry 328 }

-- .1.3.6.1.4.1.39026.3.1.4.1.2.1.329
-- .1.3.6.1.4.1.39026.3.1.4.1.2.1.329
-- .1.3.6.1.4.1.39026.3.1.4.1.2.1.329
-- .1.3.6.1.4.1.39026.3.1.4.1.2.1.329
	branchVoltage82 OBJECT-TYPE
	SYNTAX Integer32
	MAX-ACCESS read-only
	STATUS current
	DESCRIPTION
	"Description: "
	::= { powerMeterAMYDBEntry 329 }

-- .1.3.6.1.4.1.39026.3.1.4.1.2.1.330
-- .1.3.6.1.4.1.39026.3.1.4.1.2.1.330
-- .1.3.6.1.4.1.39026.3.1.4.1.2.1.330
-- .1.3.6.1.4.1.39026.3.1.4.1.2.1.330
	branchCurrent82 OBJECT-TYPE
	SYNTAX Integer32
	MAX-ACCESS read-only
	STATUS current
	DESCRIPTION
	"Description: "
	::= { powerMeterAMYDBEntry 330 }

-- .1.3.6.1.4.1.39026.3.1.4.1.2.1.331
-- .1.3.6.1.4.1.39026.3.1.4.1.2.1.331
-- .1.3.6.1.4.1.39026.3.1.4.1.2.1.331
-- .1.3.6.1.4.1.39026.3.1.4.1.2.1.331
	branchActivePower82 OBJECT-TYPE
	SYNTAX Integer32
	MAX-ACCESS read-only
	STATUS current
	DESCRIPTION
	"Description: "
	::= { powerMeterAMYDBEntry 331 }

-- .1.3.6.1.4.1.39026.3.1.4.1.2.1.332
-- .1.3.6.1.4.1.39026.3.1.4.1.2.1.332
-- .1.3.6.1.4.1.39026.3.1.4.1.2.1.332
-- .1.3.6.1.4.1.39026.3.1.4.1.2.1.332
	branchActiveEnergy82 OBJECT-TYPE
	SYNTAX Integer32
	MAX-ACCESS read-only
	STATUS current
	DESCRIPTION
	"Description: "
	::= { powerMeterAMYDBEntry 332 }

-- .1.3.6.1.4.1.39026.3.1.4.1.2.1.333
-- .1.3.6.1.4.1.39026.3.1.4.1.2.1.333
-- .1.3.6.1.4.1.39026.3.1.4.1.2.1.333
-- .1.3.6.1.4.1.39026.3.1.4.1.2.1.333
	branchVoltage83 OBJECT-TYPE
	SYNTAX Integer32
	MAX-ACCESS read-only
	STATUS current
	DESCRIPTION
	"Description: "
	::= { powerMeterAMYDBEntry 333 }

-- .1.3.6.1.4.1.39026.3.1.4.1.2.1.334
-- .1.3.6.1.4.1.39026.3.1.4.1.2.1.334
-- .1.3.6.1.4.1.39026.3.1.4.1.2.1.334
-- .1.3.6.1.4.1.39026.3.1.4.1.2.1.334
	branchCurrent83 OBJECT-TYPE
	SYNTAX Integer32
	MAX-ACCESS read-only
	STATUS current
	DESCRIPTION
	"Description: "
	::= { powerMeterAMYDBEntry 334 }

-- .1.3.6.1.4.1.39026.3.1.4.1.2.1.335
-- .1.3.6.1.4.1.39026.3.1.4.1.2.1.335
-- .1.3.6.1.4.1.39026.3.1.4.1.2.1.335
-- .1.3.6.1.4.1.39026.3.1.4.1.2.1.335
	branchActivePower83 OBJECT-TYPE
	SYNTAX Integer32
	MAX-ACCESS read-only
	STATUS current
	DESCRIPTION
	"Description: "
	::= { powerMeterAMYDBEntry 335 }

-- .1.3.6.1.4.1.39026.3.1.4.1.2.1.336
-- .1.3.6.1.4.1.39026.3.1.4.1.2.1.336
-- .1.3.6.1.4.1.39026.3.1.4.1.2.1.336
-- .1.3.6.1.4.1.39026.3.1.4.1.2.1.336
	branchActiveEnergy83 OBJECT-TYPE
	SYNTAX Integer32
	MAX-ACCESS read-only
	STATUS current
	DESCRIPTION
	"Description: "
	::= { powerMeterAMYDBEntry 336 }

-- .1.3.6.1.4.1.39026.3.1.4.1.2.1.337
-- .1.3.6.1.4.1.39026.3.1.4.1.2.1.337
-- .1.3.6.1.4.1.39026.3.1.4.1.2.1.337
-- .1.3.6.1.4.1.39026.3.1.4.1.2.1.337
	branchVoltage84 OBJECT-TYPE
	SYNTAX Integer32
	MAX-ACCESS read-only
	STATUS current
	DESCRIPTION
	"Description: "
	::= { powerMeterAMYDBEntry 337 }

-- .1.3.6.1.4.1.39026.3.1.4.1.2.1.338
-- .1.3.6.1.4.1.39026.3.1.4.1.2.1.338
-- .1.3.6.1.4.1.39026.3.1.4.1.2.1.338
-- .1.3.6.1.4.1.39026.3.1.4.1.2.1.338
	branchCurrent84 OBJECT-TYPE
	SYNTAX Integer32
	MAX-ACCESS read-only
	STATUS current
	DESCRIPTION
	"Description: "
	::= { powerMeterAMYDBEntry 338 }

-- .1.3.6.1.4.1.39026.3.1.4.1.2.1.339
-- .1.3.6.1.4.1.39026.3.1.4.1.2.1.339
-- .1.3.6.1.4.1.39026.3.1.4.1.2.1.339
-- .1.3.6.1.4.1.39026.3.1.4.1.2.1.339
	branchActivePower84 OBJECT-TYPE
	SYNTAX Integer32
	MAX-ACCESS read-only
	STATUS current
	DESCRIPTION
	"Description: "
	::= { powerMeterAMYDBEntry 339 }

-- .1.3.6.1.4.1.39026.3.1.4.1.2.1.340
-- .1.3.6.1.4.1.39026.3.1.4.1.2.1.340
-- .1.3.6.1.4.1.39026.3.1.4.1.2.1.340
-- .1.3.6.1.4.1.39026.3.1.4.1.2.1.340
	branchActiveEnergy84 OBJECT-TYPE
	SYNTAX Integer32
	MAX-ACCESS read-only
	STATUS current
	DESCRIPTION
	"Description: "
	::= { powerMeterAMYDBEntry 340 }

-- .1.3.6.1.4.1.39026.3.1.4.1.2.1.341
-- .1.3.6.1.4.1.39026.3.1.4.1.2.1.341
-- .1.3.6.1.4.1.39026.3.1.4.1.2.1.341
-- .1.3.6.1.4.1.39026.3.1.4.1.2.1.341
	branchVoltage85 OBJECT-TYPE
	SYNTAX Integer32
	MAX-ACCESS read-only
	STATUS current
	DESCRIPTION
	"Description: "
	::= { powerMeterAMYDBEntry 341 }

-- .1.3.6.1.4.1.39026.3.1.4.1.2.1.342
-- .1.3.6.1.4.1.39026.3.1.4.1.2.1.342
-- .1.3.6.1.4.1.39026.3.1.4.1.2.1.342
-- .1.3.6.1.4.1.39026.3.1.4.1.2.1.342
	branchCurrent85 OBJECT-TYPE
	SYNTAX Integer32
	MAX-ACCESS read-only
	STATUS current
	DESCRIPTION
	"Description: "
	::= { powerMeterAMYDBEntry 342 }

-- .1.3.6.1.4.1.39026.3.1.4.1.2.1.343
-- .1.3.6.1.4.1.39026.3.1.4.1.2.1.343
-- .1.3.6.1.4.1.39026.3.1.4.1.2.1.343
-- .1.3.6.1.4.1.39026.3.1.4.1.2.1.343
	branchActivePower85 OBJECT-TYPE
	SYNTAX Integer32
	MAX-ACCESS read-only
	STATUS current
	DESCRIPTION
	"Description: "
	::= { powerMeterAMYDBEntry 343 }

-- .1.3.6.1.4.1.39026.3.1.4.1.2.1.344
-- .1.3.6.1.4.1.39026.3.1.4.1.2.1.344
-- .1.3.6.1.4.1.39026.3.1.4.1.2.1.344
-- .1.3.6.1.4.1.39026.3.1.4.1.2.1.344
	branchActiveEnergy85 OBJECT-TYPE
	SYNTAX Integer32
	MAX-ACCESS read-only
	STATUS current
	DESCRIPTION
	"Description: "
	::= { powerMeterAMYDBEntry 344 }

-- .1.3.6.1.4.1.39026.3.1.4.1.2.1.345
-- .1.3.6.1.4.1.39026.3.1.4.1.2.1.345
-- .1.3.6.1.4.1.39026.3.1.4.1.2.1.345
-- .1.3.6.1.4.1.39026.3.1.4.1.2.1.345
	branchVoltage86 OBJECT-TYPE
	SYNTAX Integer32
	MAX-ACCESS read-only
	STATUS current
	DESCRIPTION
	"Description: "
	::= { powerMeterAMYDBEntry 345 }

-- .1.3.6.1.4.1.39026.3.1.4.1.2.1.346
-- .1.3.6.1.4.1.39026.3.1.4.1.2.1.346
-- .1.3.6.1.4.1.39026.3.1.4.1.2.1.346
-- .1.3.6.1.4.1.39026.3.1.4.1.2.1.346
	branchCurrent86 OBJECT-TYPE
	SYNTAX Integer32
	MAX-ACCESS read-only
	STATUS current
	DESCRIPTION
	"Description: "
	::= { powerMeterAMYDBEntry 346 }

-- .1.3.6.1.4.1.39026.3.1.4.1.2.1.347
-- .1.3.6.1.4.1.39026.3.1.4.1.2.1.347
-- .1.3.6.1.4.1.39026.3.1.4.1.2.1.347
-- .1.3.6.1.4.1.39026.3.1.4.1.2.1.347
	branchActivePower86 OBJECT-TYPE
	SYNTAX Integer32
	MAX-ACCESS read-only
	STATUS current
	DESCRIPTION
	"Description: "
	::= { powerMeterAMYDBEntry 347 }

-- .1.3.6.1.4.1.39026.3.1.4.1.2.1.348
-- .1.3.6.1.4.1.39026.3.1.4.1.2.1.348
-- .1.3.6.1.4.1.39026.3.1.4.1.2.1.348
-- .1.3.6.1.4.1.39026.3.1.4.1.2.1.348
	branchActiveEnergy86 OBJECT-TYPE
	SYNTAX Integer32
	MAX-ACCESS read-only
	STATUS current
	DESCRIPTION
	"Description: "
	::= { powerMeterAMYDBEntry 348 }

-- .1.3.6.1.4.1.39026.3.1.4.1.2.1.349
-- .1.3.6.1.4.1.39026.3.1.4.1.2.1.349
-- .1.3.6.1.4.1.39026.3.1.4.1.2.1.349
-- .1.3.6.1.4.1.39026.3.1.4.1.2.1.349
	branchVoltage87 OBJECT-TYPE
	SYNTAX Integer32
	MAX-ACCESS read-only
	STATUS current
	DESCRIPTION
	"Description: "
	::= { powerMeterAMYDBEntry 349 }

-- .1.3.6.1.4.1.39026.3.1.4.1.2.1.350
-- .1.3.6.1.4.1.39026.3.1.4.1.2.1.350
-- .1.3.6.1.4.1.39026.3.1.4.1.2.1.350
-- .1.3.6.1.4.1.39026.3.1.4.1.2.1.350
	branchCurrent87 OBJECT-TYPE
	SYNTAX Integer32
	MAX-ACCESS read-only
	STATUS current
	DESCRIPTION
	"Description: "
	::= { powerMeterAMYDBEntry 350 }

-- .1.3.6.1.4.1.39026.3.1.4.1.2.1.351
-- .1.3.6.1.4.1.39026.3.1.4.1.2.1.351
-- .1.3.6.1.4.1.39026.3.1.4.1.2.1.351
-- .1.3.6.1.4.1.39026.3.1.4.1.2.1.351
	branchActivePower87 OBJECT-TYPE
	SYNTAX Integer32
	MAX-ACCESS read-only
	STATUS current
	DESCRIPTION
	"Description: "
	::= { powerMeterAMYDBEntry 351 }

-- .1.3.6.1.4.1.39026.3.1.4.1.2.1.352
-- .1.3.6.1.4.1.39026.3.1.4.1.2.1.352
-- .1.3.6.1.4.1.39026.3.1.4.1.2.1.352
-- .1.3.6.1.4.1.39026.3.1.4.1.2.1.352
	branchActiveEnergy87 OBJECT-TYPE
	SYNTAX Integer32
	MAX-ACCESS read-only
	STATUS current
	DESCRIPTION
	"Description: "
	::= { powerMeterAMYDBEntry 352 }

-- .1.3.6.1.4.1.39026.3.1.4.1.2.1.353
-- .1.3.6.1.4.1.39026.3.1.4.1.2.1.353
-- .1.3.6.1.4.1.39026.3.1.4.1.2.1.353
-- .1.3.6.1.4.1.39026.3.1.4.1.2.1.353
	branchVoltage88 OBJECT-TYPE
	SYNTAX Integer32
	MAX-ACCESS read-only
	STATUS current
	DESCRIPTION
	"Description: "
	::= { powerMeterAMYDBEntry 353 }

-- .1.3.6.1.4.1.39026.3.1.4.1.2.1.354
-- .1.3.6.1.4.1.39026.3.1.4.1.2.1.354
-- .1.3.6.1.4.1.39026.3.1.4.1.2.1.354
-- .1.3.6.1.4.1.39026.3.1.4.1.2.1.354
	branchCurrent88 OBJECT-TYPE
	SYNTAX Integer32
	MAX-ACCESS read-only
	STATUS current
	DESCRIPTION
	"Description: "
	::= { powerMeterAMYDBEntry 354 }

-- .1.3.6.1.4.1.39026.3.1.4.1.2.1.355
-- .1.3.6.1.4.1.39026.3.1.4.1.2.1.355
-- .1.3.6.1.4.1.39026.3.1.4.1.2.1.355
-- .1.3.6.1.4.1.39026.3.1.4.1.2.1.355
	branchActivePower88 OBJECT-TYPE
	SYNTAX Integer32
	MAX-ACCESS read-only
	STATUS current
	DESCRIPTION
	"Description: "
	::= { powerMeterAMYDBEntry 355 }

-- .1.3.6.1.4.1.39026.3.1.4.1.2.1.356
-- .1.3.6.1.4.1.39026.3.1.4.1.2.1.356
-- .1.3.6.1.4.1.39026.3.1.4.1.2.1.356
-- .1.3.6.1.4.1.39026.3.1.4.1.2.1.356
	branchActiveEnergy88 OBJECT-TYPE
	SYNTAX Integer32
	MAX-ACCESS read-only
	STATUS current
	DESCRIPTION
	"Description: "
	::= { powerMeterAMYDBEntry 356 }

-- .1.3.6.1.4.1.39026.3.1.4.1.2.1.357
-- .1.3.6.1.4.1.39026.3.1.4.1.2.1.357
-- .1.3.6.1.4.1.39026.3.1.4.1.2.1.357
-- .1.3.6.1.4.1.39026.3.1.4.1.2.1.357
	branchVoltage89 OBJECT-TYPE
	SYNTAX Integer32
	MAX-ACCESS read-only
	STATUS current
	DESCRIPTION
	"Description: "
	::= { powerMeterAMYDBEntry 357 }

-- .1.3.6.1.4.1.39026.3.1.4.1.2.1.358
-- .1.3.6.1.4.1.39026.3.1.4.1.2.1.358
-- .1.3.6.1.4.1.39026.3.1.4.1.2.1.358
-- .1.3.6.1.4.1.39026.3.1.4.1.2.1.358
	branchCurrent89 OBJECT-TYPE
	SYNTAX Integer32
	MAX-ACCESS read-only
	STATUS current
	DESCRIPTION
	"Description: "
	::= { powerMeterAMYDBEntry 358 }

-- .1.3.6.1.4.1.39026.3.1.4.1.2.1.359
-- .1.3.6.1.4.1.39026.3.1.4.1.2.1.359
-- .1.3.6.1.4.1.39026.3.1.4.1.2.1.359
-- .1.3.6.1.4.1.39026.3.1.4.1.2.1.359
	branchActivePower89 OBJECT-TYPE
	SYNTAX Integer32
	MAX-ACCESS read-only
	STATUS current
	DESCRIPTION
	"Description: "
	::= { powerMeterAMYDBEntry 359 }

-- .1.3.6.1.4.1.39026.3.1.4.1.2.1.360
-- .1.3.6.1.4.1.39026.3.1.4.1.2.1.360
-- .1.3.6.1.4.1.39026.3.1.4.1.2.1.360
-- .1.3.6.1.4.1.39026.3.1.4.1.2.1.360
	branchActiveEnergy89 OBJECT-TYPE
	SYNTAX Integer32
	MAX-ACCESS read-only
	STATUS current
	DESCRIPTION
	"Description: "
	::= { powerMeterAMYDBEntry 360 }

-- .1.3.6.1.4.1.39026.3.1.4.1.2.1.361
-- .1.3.6.1.4.1.39026.3.1.4.1.2.1.361
-- .1.3.6.1.4.1.39026.3.1.4.1.2.1.361
-- .1.3.6.1.4.1.39026.3.1.4.1.2.1.361
	branchVoltage90 OBJECT-TYPE
	SYNTAX Integer32
	MAX-ACCESS read-only
	STATUS current
	DESCRIPTION
	"Description: "
	::= { powerMeterAMYDBEntry 361 }

-- .1.3.6.1.4.1.39026.3.1.4.1.2.1.362
-- .1.3.6.1.4.1.39026.3.1.4.1.2.1.362
-- .1.3.6.1.4.1.39026.3.1.4.1.2.1.362
-- .1.3.6.1.4.1.39026.3.1.4.1.2.1.362
	branchCurrent90 OBJECT-TYPE
	SYNTAX Integer32
	MAX-ACCESS read-only
	STATUS current
	DESCRIPTION
	"Description: "
	::= { powerMeterAMYDBEntry 362 }

-- .1.3.6.1.4.1.39026.3.1.4.1.2.1.363
-- .1.3.6.1.4.1.39026.3.1.4.1.2.1.363
-- .1.3.6.1.4.1.39026.3.1.4.1.2.1.363
-- .1.3.6.1.4.1.39026.3.1.4.1.2.1.363
	branchActivePower90 OBJECT-TYPE
	SYNTAX Integer32
	MAX-ACCESS read-only
	STATUS current
	DESCRIPTION
	"Description: "
	::= { powerMeterAMYDBEntry 363 }

-- .1.3.6.1.4.1.39026.3.1.4.1.2.1.364
-- .1.3.6.1.4.1.39026.3.1.4.1.2.1.364
-- .1.3.6.1.4.1.39026.3.1.4.1.2.1.364
-- .1.3.6.1.4.1.39026.3.1.4.1.2.1.364
	branchActiveEnergy90 OBJECT-TYPE
	SYNTAX Integer32
	MAX-ACCESS read-only
	STATUS current
	DESCRIPTION
	"Description: "
	::= { powerMeterAMYDBEntry 364 }

-- .1.3.6.1.4.1.39026.3.1.4.1.2.1.365
-- .1.3.6.1.4.1.39026.3.1.4.1.2.1.365
-- .1.3.6.1.4.1.39026.3.1.4.1.2.1.365
-- .1.3.6.1.4.1.39026.3.1.4.1.2.1.365
	branchVoltage91 OBJECT-TYPE
	SYNTAX Integer32
	MAX-ACCESS read-only
	STATUS current
	DESCRIPTION
	"Description: "
	::= { powerMeterAMYDBEntry 365 }

-- .1.3.6.1.4.1.39026.3.1.4.1.2.1.366
-- .1.3.6.1.4.1.39026.3.1.4.1.2.1.366
-- .1.3.6.1.4.1.39026.3.1.4.1.2.1.366
-- .1.3.6.1.4.1.39026.3.1.4.1.2.1.366
	branchCurrent91 OBJECT-TYPE
	SYNTAX Integer32
	MAX-ACCESS read-only
	STATUS current
	DESCRIPTION
	"Description: "
	::= { powerMeterAMYDBEntry 366 }

-- .1.3.6.1.4.1.39026.3.1.4.1.2.1.367
-- .1.3.6.1.4.1.39026.3.1.4.1.2.1.367
-- .1.3.6.1.4.1.39026.3.1.4.1.2.1.367
-- .1.3.6.1.4.1.39026.3.1.4.1.2.1.367
	branchActivePower91 OBJECT-TYPE
	SYNTAX Integer32
	MAX-ACCESS read-only
	STATUS current
	DESCRIPTION
	"Description: "
	::= { powerMeterAMYDBEntry 367 }

-- .1.3.6.1.4.1.39026.3.1.4.1.2.1.368
-- .1.3.6.1.4.1.39026.3.1.4.1.2.1.368
-- .1.3.6.1.4.1.39026.3.1.4.1.2.1.368
-- .1.3.6.1.4.1.39026.3.1.4.1.2.1.368
	branchActiveEnergy91 OBJECT-TYPE
	SYNTAX Integer32
	MAX-ACCESS read-only
	STATUS current
	DESCRIPTION
	"Description: "
	::= { powerMeterAMYDBEntry 368 }

-- .1.3.6.1.4.1.39026.3.1.4.1.2.1.369
-- .1.3.6.1.4.1.39026.3.1.4.1.2.1.369
-- .1.3.6.1.4.1.39026.3.1.4.1.2.1.369
-- .1.3.6.1.4.1.39026.3.1.4.1.2.1.369
	branchVoltage92 OBJECT-TYPE
	SYNTAX Integer32
	MAX-ACCESS read-only
	STATUS current
	DESCRIPTION
	"Description: "
	::= { powerMeterAMYDBEntry 369 }

-- .1.3.6.1.4.1.39026.3.1.4.1.2.1.370
-- .1.3.6.1.4.1.39026.3.1.4.1.2.1.370
-- .1.3.6.1.4.1.39026.3.1.4.1.2.1.370
-- .1.3.6.1.4.1.39026.3.1.4.1.2.1.370
	branchCurrent92 OBJECT-TYPE
	SYNTAX Integer32
	MAX-ACCESS read-only
	STATUS current
	DESCRIPTION
	"Description: "
	::= { powerMeterAMYDBEntry 370 }

-- .1.3.6.1.4.1.39026.3.1.4.1.2.1.371
-- .1.3.6.1.4.1.39026.3.1.4.1.2.1.371
-- .1.3.6.1.4.1.39026.3.1.4.1.2.1.371
-- .1.3.6.1.4.1.39026.3.1.4.1.2.1.371
	branchActivePower92 OBJECT-TYPE
	SYNTAX Integer32
	MAX-ACCESS read-only
	STATUS current
	DESCRIPTION
	"Description: "
	::= { powerMeterAMYDBEntry 371 }

-- .1.3.6.1.4.1.39026.3.1.4.1.2.1.372
-- .1.3.6.1.4.1.39026.3.1.4.1.2.1.372
-- .1.3.6.1.4.1.39026.3.1.4.1.2.1.372
-- .1.3.6.1.4.1.39026.3.1.4.1.2.1.372
	branchActiveEnergy92 OBJECT-TYPE
	SYNTAX Integer32
	MAX-ACCESS read-only
	STATUS current
	DESCRIPTION
	"Description: "
	::= { powerMeterAMYDBEntry 372 }

-- .1.3.6.1.4.1.39026.3.1.4.1.2.1.373
-- .1.3.6.1.4.1.39026.3.1.4.1.2.1.373
-- .1.3.6.1.4.1.39026.3.1.4.1.2.1.373
-- .1.3.6.1.4.1.39026.3.1.4.1.2.1.373
	branchVoltage93 OBJECT-TYPE
	SYNTAX Integer32
	MAX-ACCESS read-only
	STATUS current
	DESCRIPTION
	"Description: "
	::= { powerMeterAMYDBEntry 373 }

-- .1.3.6.1.4.1.39026.3.1.4.1.2.1.374
-- .1.3.6.1.4.1.39026.3.1.4.1.2.1.374
-- .1.3.6.1.4.1.39026.3.1.4.1.2.1.374
-- .1.3.6.1.4.1.39026.3.1.4.1.2.1.374
	branchCurrent93 OBJECT-TYPE
	SYNTAX Integer32
	MAX-ACCESS read-only
	STATUS current
	DESCRIPTION
	"Description: "
	::= { powerMeterAMYDBEntry 374 }

-- .1.3.6.1.4.1.39026.3.1.4.1.2.1.375
-- .1.3.6.1.4.1.39026.3.1.4.1.2.1.375
-- .1.3.6.1.4.1.39026.3.1.4.1.2.1.375
-- .1.3.6.1.4.1.39026.3.1.4.1.2.1.375
	branchActivePower93 OBJECT-TYPE
	SYNTAX Integer32
	MAX-ACCESS read-only
	STATUS current
	DESCRIPTION
	"Description: "
	::= { powerMeterAMYDBEntry 375 }

-- .1.3.6.1.4.1.39026.3.1.4.1.2.1.376
-- .1.3.6.1.4.1.39026.3.1.4.1.2.1.376
-- .1.3.6.1.4.1.39026.3.1.4.1.2.1.376
-- .1.3.6.1.4.1.39026.3.1.4.1.2.1.376
	branchActiveEnergy93 OBJECT-TYPE
	SYNTAX Integer32
	MAX-ACCESS read-only
	STATUS current
	DESCRIPTION
	"Description: "
	::= { powerMeterAMYDBEntry 376 }

-- .1.3.6.1.4.1.39026.3.1.4.1.2.1.377
-- .1.3.6.1.4.1.39026.3.1.4.1.2.1.377
-- .1.3.6.1.4.1.39026.3.1.4.1.2.1.377
-- .1.3.6.1.4.1.39026.3.1.4.1.2.1.377
	branchVoltage94 OBJECT-TYPE
	SYNTAX Integer32
	MAX-ACCESS read-only
	STATUS current
	DESCRIPTION
	"Description: "
	::= { powerMeterAMYDBEntry 377 }

-- .1.3.6.1.4.1.39026.3.1.4.1.2.1.378
-- .1.3.6.1.4.1.39026.3.1.4.1.2.1.378
-- .1.3.6.1.4.1.39026.3.1.4.1.2.1.378
-- .1.3.6.1.4.1.39026.3.1.4.1.2.1.378
	branchCurrent94 OBJECT-TYPE
	SYNTAX Integer32
	MAX-ACCESS read-only
	STATUS current
	DESCRIPTION
	"Description: "
	::= { powerMeterAMYDBEntry 378 }

-- .1.3.6.1.4.1.39026.3.1.4.1.2.1.379
-- .1.3.6.1.4.1.39026.3.1.4.1.2.1.379
-- .1.3.6.1.4.1.39026.3.1.4.1.2.1.379
-- .1.3.6.1.4.1.39026.3.1.4.1.2.1.379
	branchActivePower94 OBJECT-TYPE
	SYNTAX Integer32
	MAX-ACCESS read-only
	STATUS current
	DESCRIPTION
	"Description: "
	::= { powerMeterAMYDBEntry 379 }

-- .1.3.6.1.4.1.39026.3.1.4.1.2.1.380
-- .1.3.6.1.4.1.39026.3.1.4.1.2.1.380
-- .1.3.6.1.4.1.39026.3.1.4.1.2.1.380
-- .1.3.6.1.4.1.39026.3.1.4.1.2.1.380
	branchActiveEnergy94 OBJECT-TYPE
	SYNTAX Integer32
	MAX-ACCESS read-only
	STATUS current
	DESCRIPTION
	"Description: "
	::= { powerMeterAMYDBEntry 380 }

-- .1.3.6.1.4.1.39026.3.1.4.1.2.1.381
-- .1.3.6.1.4.1.39026.3.1.4.1.2.1.381
-- .1.3.6.1.4.1.39026.3.1.4.1.2.1.381
-- .1.3.6.1.4.1.39026.3.1.4.1.2.1.381
	branchVoltage95 OBJECT-TYPE
	SYNTAX Integer32
	MAX-ACCESS read-only
	STATUS current
	DESCRIPTION
	"Description: "
	::= { powerMeterAMYDBEntry 381 }

-- .1.3.6.1.4.1.39026.3.1.4.1.2.1.382
-- .1.3.6.1.4.1.39026.3.1.4.1.2.1.382
-- .1.3.6.1.4.1.39026.3.1.4.1.2.1.382
-- .1.3.6.1.4.1.39026.3.1.4.1.2.1.382
	branchCurrent95 OBJECT-TYPE
	SYNTAX Integer32
	MAX-ACCESS read-only
	STATUS current
	DESCRIPTION
	"Description: "
	::= { powerMeterAMYDBEntry 382 }

-- .1.3.6.1.4.1.39026.3.1.4.1.2.1.383
-- .1.3.6.1.4.1.39026.3.1.4.1.2.1.383
-- .1.3.6.1.4.1.39026.3.1.4.1.2.1.383
-- .1.3.6.1.4.1.39026.3.1.4.1.2.1.383
	branchActivePower95 OBJECT-TYPE
	SYNTAX Integer32
	MAX-ACCESS read-only
	STATUS current
	DESCRIPTION
	"Description: "
	::= { powerMeterAMYDBEntry 383 }

-- .1.3.6.1.4.1.39026.3.1.4.1.2.1.384
-- .1.3.6.1.4.1.39026.3.1.4.1.2.1.384
-- .1.3.6.1.4.1.39026.3.1.4.1.2.1.384
-- .1.3.6.1.4.1.39026.3.1.4.1.2.1.384
	branchActiveEnergy95 OBJECT-TYPE
	SYNTAX Integer32
	MAX-ACCESS read-only
	STATUS current
	DESCRIPTION
	"Description: "
	::= { powerMeterAMYDBEntry 384 }

-- .1.3.6.1.4.1.39026.3.1.4.1.2.1.385
-- .1.3.6.1.4.1.39026.3.1.4.1.2.1.385
-- .1.3.6.1.4.1.39026.3.1.4.1.2.1.385
-- .1.3.6.1.4.1.39026.3.1.4.1.2.1.385
	branchVoltage96 OBJECT-TYPE
	SYNTAX Integer32
	MAX-ACCESS read-only
	STATUS current
	DESCRIPTION
	"Description: "
	::= { powerMeterAMYDBEntry 385 }

-- .1.3.6.1.4.1.39026.3.1.4.1.2.1.386
-- .1.3.6.1.4.1.39026.3.1.4.1.2.1.386
-- .1.3.6.1.4.1.39026.3.1.4.1.2.1.386
-- .1.3.6.1.4.1.39026.3.1.4.1.2.1.386
	branchCurrent96 OBJECT-TYPE
	SYNTAX Integer32
	MAX-ACCESS read-only
	STATUS current
	DESCRIPTION
	"Description: "
	::= { powerMeterAMYDBEntry 386 }

-- .1.3.6.1.4.1.39026.3.1.4.1.2.1.387
-- .1.3.6.1.4.1.39026.3.1.4.1.2.1.387
-- .1.3.6.1.4.1.39026.3.1.4.1.2.1.387
-- .1.3.6.1.4.1.39026.3.1.4.1.2.1.387
	branchActivePower96 OBJECT-TYPE
	SYNTAX Integer32
	MAX-ACCESS read-only
	STATUS current
	DESCRIPTION
	"Description: "
	::= { powerMeterAMYDBEntry 387 }

-- .1.3.6.1.4.1.39026.3.1.4.1.2.1.388
-- .1.3.6.1.4.1.39026.3.1.4.1.2.1.388
-- .1.3.6.1.4.1.39026.3.1.4.1.2.1.388
-- .1.3.6.1.4.1.39026.3.1.4.1.2.1.388
	branchActiveEnergy96 OBJECT-TYPE
	SYNTAX Integer32
	MAX-ACCESS read-only
	STATUS current
	DESCRIPTION
	"Description: "
	::= { powerMeterAMYDBEntry 388 }

-- .1.3.6.1.4.1.39026.3.1.4.1.2.1.389
-- .1.3.6.1.4.1.39026.3.1.4.1.2.1.389
-- .1.3.6.1.4.1.39026.3.1.4.1.2.1.389
-- .1.3.6.1.4.1.39026.3.1.4.1.2.1.389
	branchVoltage97 OBJECT-TYPE
	SYNTAX Integer32
	MAX-ACCESS read-only
	STATUS current
	DESCRIPTION
	"Description: "
	::= { powerMeterAMYDBEntry 389 }

-- .1.3.6.1.4.1.39026.3.1.4.1.2.1.390
-- .1.3.6.1.4.1.39026.3.1.4.1.2.1.390
-- .1.3.6.1.4.1.39026.3.1.4.1.2.1.390
-- .1.3.6.1.4.1.39026.3.1.4.1.2.1.390
	branchCurrent97 OBJECT-TYPE
	SYNTAX Integer32
	MAX-ACCESS read-only
	STATUS current
	DESCRIPTION
	"Description: "
	::= { powerMeterAMYDBEntry 390 }

-- .1.3.6.1.4.1.39026.3.1.4.1.2.1.391
-- .1.3.6.1.4.1.39026.3.1.4.1.2.1.391
-- .1.3.6.1.4.1.39026.3.1.4.1.2.1.391
-- .1.3.6.1.4.1.39026.3.1.4.1.2.1.391
	branchActivePower97 OBJECT-TYPE
	SYNTAX Integer32
	MAX-ACCESS read-only
	STATUS current
	DESCRIPTION
	"Description: "
	::= { powerMeterAMYDBEntry 391 }

-- .1.3.6.1.4.1.39026.3.1.4.1.2.1.392
-- .1.3.6.1.4.1.39026.3.1.4.1.2.1.392
-- .1.3.6.1.4.1.39026.3.1.4.1.2.1.392
-- .1.3.6.1.4.1.39026.3.1.4.1.2.1.392
	branchActiveEnergy97 OBJECT-TYPE
	SYNTAX Integer32
	MAX-ACCESS read-only
	STATUS current
	DESCRIPTION
	"Description: "
	::= { powerMeterAMYDBEntry 392 }

-- .1.3.6.1.4.1.39026.3.1.4.1.2.1.393
-- .1.3.6.1.4.1.39026.3.1.4.1.2.1.393
-- .1.3.6.1.4.1.39026.3.1.4.1.2.1.393
-- .1.3.6.1.4.1.39026.3.1.4.1.2.1.393
	branchVoltage98 OBJECT-TYPE
	SYNTAX Integer32
	MAX-ACCESS read-only
	STATUS current
	DESCRIPTION
	"Description: "
	::= { powerMeterAMYDBEntry 393 }

-- .1.3.6.1.4.1.39026.3.1.4.1.2.1.394
-- .1.3.6.1.4.1.39026.3.1.4.1.2.1.394
-- .1.3.6.1.4.1.39026.3.1.4.1.2.1.394
-- .1.3.6.1.4.1.39026.3.1.4.1.2.1.394
	branchCurrent98 OBJECT-TYPE
	SYNTAX Integer32
	MAX-ACCESS read-only
	STATUS current
	DESCRIPTION
	"Description: "
	::= { powerMeterAMYDBEntry 394 }

-- .1.3.6.1.4.1.39026.3.1.4.1.2.1.395
-- .1.3.6.1.4.1.39026.3.1.4.1.2.1.395
-- .1.3.6.1.4.1.39026.3.1.4.1.2.1.395
-- .1.3.6.1.4.1.39026.3.1.4.1.2.1.395
	branchActivePower98 OBJECT-TYPE
	SYNTAX Integer32
	MAX-ACCESS read-only
	STATUS current
	DESCRIPTION
	"Description: "
	::= { powerMeterAMYDBEntry 395 }

-- .1.3.6.1.4.1.39026.3.1.4.1.2.1.396
-- .1.3.6.1.4.1.39026.3.1.4.1.2.1.396
-- .1.3.6.1.4.1.39026.3.1.4.1.2.1.396
-- .1.3.6.1.4.1.39026.3.1.4.1.2.1.396
	branchActiveEnergy98 OBJECT-TYPE
	SYNTAX Integer32
	MAX-ACCESS read-only
	STATUS current
	DESCRIPTION
	"Description: "
	::= { powerMeterAMYDBEntry 396 }

-- .1.3.6.1.4.1.39026.3.1.4.1.2.1.397
-- .1.3.6.1.4.1.39026.3.1.4.1.2.1.397
-- .1.3.6.1.4.1.39026.3.1.4.1.2.1.397
-- .1.3.6.1.4.1.39026.3.1.4.1.2.1.397
	branchVoltage99 OBJECT-TYPE
	SYNTAX Integer32
	MAX-ACCESS read-only
	STATUS current
	DESCRIPTION
	"Description: "
	::= { powerMeterAMYDBEntry 397 }

-- .1.3.6.1.4.1.39026.3.1.4.1.2.1.398
-- .1.3.6.1.4.1.39026.3.1.4.1.2.1.398
-- .1.3.6.1.4.1.39026.3.1.4.1.2.1.398
-- .1.3.6.1.4.1.39026.3.1.4.1.2.1.398
	branchCurrent99 OBJECT-TYPE
	SYNTAX Integer32
	MAX-ACCESS read-only
	STATUS current
	DESCRIPTION
	"Description: "
	::= { powerMeterAMYDBEntry 398 }

-- .1.3.6.1.4.1.39026.3.1.4.1.2.1.399
-- .1.3.6.1.4.1.39026.3.1.4.1.2.1.399
-- .1.3.6.1.4.1.39026.3.1.4.1.2.1.399
-- .1.3.6.1.4.1.39026.3.1.4.1.2.1.399
	branchActivePower99 OBJECT-TYPE
	SYNTAX Integer32
	MAX-ACCESS read-only
	STATUS current
	DESCRIPTION
	"Description: "
	::= { powerMeterAMYDBEntry 399 }

-- .1.3.6.1.4.1.39026.3.1.4.1.2.1.400
-- .1.3.6.1.4.1.39026.3.1.4.1.2.1.400
-- .1.3.6.1.4.1.39026.3.1.4.1.2.1.400
-- .1.3.6.1.4.1.39026.3.1.4.1.2.1.400
	branchActiveEnergy99 OBJECT-TYPE
	SYNTAX Integer32
	MAX-ACCESS read-only
	STATUS current
	DESCRIPTION
	"Description: "
	::= { powerMeterAMYDBEntry 400 }

-- .1.3.6.1.4.1.39026.3.1.4.1.2.1.401
-- .1.3.6.1.4.1.39026.3.1.4.1.2.1.401
-- .1.3.6.1.4.1.39026.3.1.4.1.2.1.401
-- .1.3.6.1.4.1.39026.3.1.4.1.2.1.401
	branchVoltage100 OBJECT-TYPE
	SYNTAX Integer32
	MAX-ACCESS read-only
	STATUS current
	DESCRIPTION
	"Description: "
	::= { powerMeterAMYDBEntry 401 }

-- .1.3.6.1.4.1.39026.3.1.4.1.2.1.402
-- .1.3.6.1.4.1.39026.3.1.4.1.2.1.402
-- .1.3.6.1.4.1.39026.3.1.4.1.2.1.402
-- .1.3.6.1.4.1.39026.3.1.4.1.2.1.402
	branchCurrent100 OBJECT-TYPE
	SYNTAX Integer32
	MAX-ACCESS read-only
	STATUS current
	DESCRIPTION
	"Description: "
	::= { powerMeterAMYDBEntry 402 }

-- .1.3.6.1.4.1.39026.3.1.4.1.2.1.403
-- .1.3.6.1.4.1.39026.3.1.4.1.2.1.403
-- .1.3.6.1.4.1.39026.3.1.4.1.2.1.403
-- .1.3.6.1.4.1.39026.3.1.4.1.2.1.403
	branchActivePower100 OBJECT-TYPE
	SYNTAX Integer32
	MAX-ACCESS read-only
	STATUS current
	DESCRIPTION
	"Description: "
	::= { powerMeterAMYDBEntry 403 }

-- .1.3.6.1.4.1.39026.3.1.4.1.2.1.404
-- .1.3.6.1.4.1.39026.3.1.4.1.2.1.404
-- .1.3.6.1.4.1.39026.3.1.4.1.2.1.404
-- .1.3.6.1.4.1.39026.3.1.4.1.2.1.404
	branchActiveEnergy100 OBJECT-TYPE
	SYNTAX Integer32
	MAX-ACCESS read-only
	STATUS current
	DESCRIPTION
	"Description: "
	::= { powerMeterAMYDBEntry 404 }

-- .1.3.6.1.4.1.39026.3.1.4.1.2.1.405
-- .1.3.6.1.4.1.39026.3.1.4.1.2.1.405
-- .1.3.6.1.4.1.39026.3.1.4.1.2.1.405
-- .1.3.6.1.4.1.39026.3.1.4.1.2.1.405
	branchVoltage101 OBJECT-TYPE
	SYNTAX Integer32
	MAX-ACCESS read-only
	STATUS current
	DESCRIPTION
	"Description: "
	::= { powerMeterAMYDBEntry 405 }

-- .1.3.6.1.4.1.39026.3.1.4.1.2.1.406
-- .1.3.6.1.4.1.39026.3.1.4.1.2.1.406
-- .1.3.6.1.4.1.39026.3.1.4.1.2.1.406
-- .1.3.6.1.4.1.39026.3.1.4.1.2.1.406
	branchCurrent101 OBJECT-TYPE
	SYNTAX Integer32
	MAX-ACCESS read-only
	STATUS current
	DESCRIPTION
	"Description: "
	::= { powerMeterAMYDBEntry 406 }

-- .1.3.6.1.4.1.39026.3.1.4.1.2.1.407
-- .1.3.6.1.4.1.39026.3.1.4.1.2.1.407
-- .1.3.6.1.4.1.39026.3.1.4.1.2.1.407
-- .1.3.6.1.4.1.39026.3.1.4.1.2.1.407
	branchActivePower101 OBJECT-TYPE
	SYNTAX Integer32
	MAX-ACCESS read-only
	STATUS current
	DESCRIPTION
	"Description: "
	::= { powerMeterAMYDBEntry 407 }

-- .1.3.6.1.4.1.39026.3.1.4.1.2.1.408
-- .1.3.6.1.4.1.39026.3.1.4.1.2.1.408
-- .1.3.6.1.4.1.39026.3.1.4.1.2.1.408
-- .1.3.6.1.4.1.39026.3.1.4.1.2.1.408
	branchActiveEnergy101 OBJECT-TYPE
	SYNTAX Integer32
	MAX-ACCESS read-only
	STATUS current
	DESCRIPTION
	"Description: "
	::= { powerMeterAMYDBEntry 408 }

-- .1.3.6.1.4.1.39026.3.1.4.1.2.1.409
-- .1.3.6.1.4.1.39026.3.1.4.1.2.1.409
-- .1.3.6.1.4.1.39026.3.1.4.1.2.1.409
-- .1.3.6.1.4.1.39026.3.1.4.1.2.1.409
	branchVoltage102 OBJECT-TYPE
	SYNTAX Integer32
	MAX-ACCESS read-only
	STATUS current
	DESCRIPTION
	"Description: "
	::= { powerMeterAMYDBEntry 409 }

-- .1.3.6.1.4.1.39026.3.1.4.1.2.1.410
-- .1.3.6.1.4.1.39026.3.1.4.1.2.1.410
-- .1.3.6.1.4.1.39026.3.1.4.1.2.1.410
-- .1.3.6.1.4.1.39026.3.1.4.1.2.1.410
	branchCurrent102 OBJECT-TYPE
	SYNTAX Integer32
	MAX-ACCESS read-only
	STATUS current
	DESCRIPTION
	"Description: "
	::= { powerMeterAMYDBEntry 410 }

-- .1.3.6.1.4.1.39026.3.1.4.1.2.1.411
-- .1.3.6.1.4.1.39026.3.1.4.1.2.1.411
-- .1.3.6.1.4.1.39026.3.1.4.1.2.1.411
-- .1.3.6.1.4.1.39026.3.1.4.1.2.1.411
	branchActivePower102 OBJECT-TYPE
	SYNTAX Integer32
	MAX-ACCESS read-only
	STATUS current
	DESCRIPTION
	"Description: "
	::= { powerMeterAMYDBEntry 411 }

-- .1.3.6.1.4.1.39026.3.1.4.1.2.1.412
-- .1.3.6.1.4.1.39026.3.1.4.1.2.1.412
-- .1.3.6.1.4.1.39026.3.1.4.1.2.1.412
-- .1.3.6.1.4.1.39026.3.1.4.1.2.1.412
	branchActiveEnergy102 OBJECT-TYPE
	SYNTAX Integer32
	MAX-ACCESS read-only
	STATUS current
	DESCRIPTION
	"Description: "
	::= { powerMeterAMYDBEntry 412 }

-- .1.3.6.1.4.1.39026.3.1.4.1.2.1.413
-- .1.3.6.1.4.1.39026.3.1.4.1.2.1.413
-- .1.3.6.1.4.1.39026.3.1.4.1.2.1.413
-- .1.3.6.1.4.1.39026.3.1.4.1.2.1.413
	branchVoltage103 OBJECT-TYPE
	SYNTAX Integer32
	MAX-ACCESS read-only
	STATUS current
	DESCRIPTION
	"Description: "
	::= { powerMeterAMYDBEntry 413 }

-- .1.3.6.1.4.1.39026.3.1.4.1.2.1.414
-- .1.3.6.1.4.1.39026.3.1.4.1.2.1.414
-- .1.3.6.1.4.1.39026.3.1.4.1.2.1.414
-- .1.3.6.1.4.1.39026.3.1.4.1.2.1.414
	branchCurrent103 OBJECT-TYPE
	SYNTAX Integer32
	MAX-ACCESS read-only
	STATUS current
	DESCRIPTION
	"Description: "
	::= { powerMeterAMYDBEntry 414 }

-- .1.3.6.1.4.1.39026.3.1.4.1.2.1.415
-- .1.3.6.1.4.1.39026.3.1.4.1.2.1.415
-- .1.3.6.1.4.1.39026.3.1.4.1.2.1.415
-- .1.3.6.1.4.1.39026.3.1.4.1.2.1.415
	branchActivePower103 OBJECT-TYPE
	SYNTAX Integer32
	MAX-ACCESS read-only
	STATUS current
	DESCRIPTION
	"Description: "
	::= { powerMeterAMYDBEntry 415 }

-- .1.3.6.1.4.1.39026.3.1.4.1.2.1.416
-- .1.3.6.1.4.1.39026.3.1.4.1.2.1.416
-- .1.3.6.1.4.1.39026.3.1.4.1.2.1.416
-- .1.3.6.1.4.1.39026.3.1.4.1.2.1.416
	branchActiveEnergy103 OBJECT-TYPE
	SYNTAX Integer32
	MAX-ACCESS read-only
	STATUS current
	DESCRIPTION
	"Description: "
	::= { powerMeterAMYDBEntry 416 }

-- .1.3.6.1.4.1.39026.3.1.4.1.2.1.417
-- .1.3.6.1.4.1.39026.3.1.4.1.2.1.417
-- .1.3.6.1.4.1.39026.3.1.4.1.2.1.417
-- .1.3.6.1.4.1.39026.3.1.4.1.2.1.417
	branchVoltage104 OBJECT-TYPE
	SYNTAX Integer32
	MAX-ACCESS read-only
	STATUS current
	DESCRIPTION
	"Description: "
	::= { powerMeterAMYDBEntry 417 }

-- .1.3.6.1.4.1.39026.3.1.4.1.2.1.418
-- .1.3.6.1.4.1.39026.3.1.4.1.2.1.418
-- .1.3.6.1.4.1.39026.3.1.4.1.2.1.418
-- .1.3.6.1.4.1.39026.3.1.4.1.2.1.418
	branchCurrent104 OBJECT-TYPE
	SYNTAX Integer32
	MAX-ACCESS read-only
	STATUS current
	DESCRIPTION
	"Description: "
	::= { powerMeterAMYDBEntry 418 }

-- .1.3.6.1.4.1.39026.3.1.4.1.2.1.419
-- .1.3.6.1.4.1.39026.3.1.4.1.2.1.419
-- .1.3.6.1.4.1.39026.3.1.4.1.2.1.419
-- .1.3.6.1.4.1.39026.3.1.4.1.2.1.419
	branchActivePower104 OBJECT-TYPE
	SYNTAX Integer32
	MAX-ACCESS read-only
	STATUS current
	DESCRIPTION
	"Description: "
	::= { powerMeterAMYDBEntry 419 }

-- .1.3.6.1.4.1.39026.3.1.4.1.2.1.420
-- .1.3.6.1.4.1.39026.3.1.4.1.2.1.420
-- .1.3.6.1.4.1.39026.3.1.4.1.2.1.420
-- .1.3.6.1.4.1.39026.3.1.4.1.2.1.420
	branchActiveEnergy104 OBJECT-TYPE
	SYNTAX Integer32
	MAX-ACCESS read-only
	STATUS current
	DESCRIPTION
	"Description: "
	::= { powerMeterAMYDBEntry 420 }

-- .1.3.6.1.4.1.39026.3.1.4.1.2.1.421
-- .1.3.6.1.4.1.39026.3.1.4.1.2.1.421
-- .1.3.6.1.4.1.39026.3.1.4.1.2.1.421
-- .1.3.6.1.4.1.39026.3.1.4.1.2.1.421
	branchVoltage105 OBJECT-TYPE
	SYNTAX Integer32
	MAX-ACCESS read-only
	STATUS current
	DESCRIPTION
	"Description: "
	::= { powerMeterAMYDBEntry 421 }

-- .1.3.6.1.4.1.39026.3.1.4.1.2.1.422
-- .1.3.6.1.4.1.39026.3.1.4.1.2.1.422
-- .1.3.6.1.4.1.39026.3.1.4.1.2.1.422
-- .1.3.6.1.4.1.39026.3.1.4.1.2.1.422
	branchCurrent105 OBJECT-TYPE
	SYNTAX Integer32
	MAX-ACCESS read-only
	STATUS current
	DESCRIPTION
	"Description: "
	::= { powerMeterAMYDBEntry 422 }

-- .1.3.6.1.4.1.39026.3.1.4.1.2.1.423
-- .1.3.6.1.4.1.39026.3.1.4.1.2.1.423
-- .1.3.6.1.4.1.39026.3.1.4.1.2.1.423
-- .1.3.6.1.4.1.39026.3.1.4.1.2.1.423
	branchActivePower105 OBJECT-TYPE
	SYNTAX Integer32
	MAX-ACCESS read-only
	STATUS current
	DESCRIPTION
	"Description: "
	::= { powerMeterAMYDBEntry 423 }

-- .1.3.6.1.4.1.39026.3.1.4.1.2.1.424
-- .1.3.6.1.4.1.39026.3.1.4.1.2.1.424
-- .1.3.6.1.4.1.39026.3.1.4.1.2.1.424
-- .1.3.6.1.4.1.39026.3.1.4.1.2.1.424
	branchActiveEnergy105 OBJECT-TYPE
	SYNTAX Integer32
	MAX-ACCESS read-only
	STATUS current
	DESCRIPTION
	"Description: "
	::= { powerMeterAMYDBEntry 424 }

-- .1.3.6.1.4.1.39026.3.1.4.1.2.1.425
-- .1.3.6.1.4.1.39026.3.1.4.1.2.1.425
-- .1.3.6.1.4.1.39026.3.1.4.1.2.1.425
-- .1.3.6.1.4.1.39026.3.1.4.1.2.1.425
	branchVoltage106 OBJECT-TYPE
	SYNTAX Integer32
	MAX-ACCESS read-only
	STATUS current
	DESCRIPTION
	"Description: "
	::= { powerMeterAMYDBEntry 425 }

-- .1.3.6.1.4.1.39026.3.1.4.1.2.1.426
-- .1.3.6.1.4.1.39026.3.1.4.1.2.1.426
-- .1.3.6.1.4.1.39026.3.1.4.1.2.1.426
-- .1.3.6.1.4.1.39026.3.1.4.1.2.1.426
	branchCurrent106 OBJECT-TYPE
	SYNTAX Integer32
	MAX-ACCESS read-only
	STATUS current
	DESCRIPTION
	"Description: "
	::= { powerMeterAMYDBEntry 426 }

-- .1.3.6.1.4.1.39026.3.1.4.1.2.1.427
-- .1.3.6.1.4.1.39026.3.1.4.1.2.1.427
-- .1.3.6.1.4.1.39026.3.1.4.1.2.1.427
-- .1.3.6.1.4.1.39026.3.1.4.1.2.1.427
	branchActivePower106 OBJECT-TYPE
	SYNTAX Integer32
	MAX-ACCESS read-only
	STATUS current
	DESCRIPTION
	"Description: "
	::= { powerMeterAMYDBEntry 427 }

-- .1.3.6.1.4.1.39026.3.1.4.1.2.1.428
-- .1.3.6.1.4.1.39026.3.1.4.1.2.1.428
-- .1.3.6.1.4.1.39026.3.1.4.1.2.1.428
-- .1.3.6.1.4.1.39026.3.1.4.1.2.1.428
	branchActiveEnergy106 OBJECT-TYPE
	SYNTAX Integer32
	MAX-ACCESS read-only
	STATUS current
	DESCRIPTION
	"Description: "
	::= { powerMeterAMYDBEntry 428 }

-- .1.3.6.1.4.1.39026.3.1.4.1.2.1.429
-- .1.3.6.1.4.1.39026.3.1.4.1.2.1.429
-- .1.3.6.1.4.1.39026.3.1.4.1.2.1.429
-- .1.3.6.1.4.1.39026.3.1.4.1.2.1.429
	branchVoltage107 OBJECT-TYPE
	SYNTAX Integer32
	MAX-ACCESS read-only
	STATUS current
	DESCRIPTION
	"Description: "
	::= { powerMeterAMYDBEntry 429 }

-- .1.3.6.1.4.1.39026.3.1.4.1.2.1.430
-- .1.3.6.1.4.1.39026.3.1.4.1.2.1.430
-- .1.3.6.1.4.1.39026.3.1.4.1.2.1.430
-- .1.3.6.1.4.1.39026.3.1.4.1.2.1.430
	branchCurrent107 OBJECT-TYPE
	SYNTAX Integer32
	MAX-ACCESS read-only
	STATUS current
	DESCRIPTION
	"Description: "
	::= { powerMeterAMYDBEntry 430 }

-- .1.3.6.1.4.1.39026.3.1.4.1.2.1.431
-- .1.3.6.1.4.1.39026.3.1.4.1.2.1.431
-- .1.3.6.1.4.1.39026.3.1.4.1.2.1.431
-- .1.3.6.1.4.1.39026.3.1.4.1.2.1.431
	branchActivePower107 OBJECT-TYPE
	SYNTAX Integer32
	MAX-ACCESS read-only
	STATUS current
	DESCRIPTION
	"Description: "
	::= { powerMeterAMYDBEntry 431 }

-- .1.3.6.1.4.1.39026.3.1.4.1.2.1.432
-- .1.3.6.1.4.1.39026.3.1.4.1.2.1.432
-- .1.3.6.1.4.1.39026.3.1.4.1.2.1.432
-- .1.3.6.1.4.1.39026.3.1.4.1.2.1.432
	branchActiveEnergy107 OBJECT-TYPE
	SYNTAX Integer32
	MAX-ACCESS read-only
	STATUS current
	DESCRIPTION
	"Description: "
	::= { powerMeterAMYDBEntry 432 }

-- .1.3.6.1.4.1.39026.3.1.4.1.2.1.433
-- .1.3.6.1.4.1.39026.3.1.4.1.2.1.433
-- .1.3.6.1.4.1.39026.3.1.4.1.2.1.433
-- .1.3.6.1.4.1.39026.3.1.4.1.2.1.433
	branchVoltage108 OBJECT-TYPE
	SYNTAX Integer32
	MAX-ACCESS read-only
	STATUS current
	DESCRIPTION
	"Description: "
	::= { powerMeterAMYDBEntry 433 }

-- .1.3.6.1.4.1.39026.3.1.4.1.2.1.434
-- .1.3.6.1.4.1.39026.3.1.4.1.2.1.434
-- .1.3.6.1.4.1.39026.3.1.4.1.2.1.434
-- .1.3.6.1.4.1.39026.3.1.4.1.2.1.434
	branchCurrent108 OBJECT-TYPE
	SYNTAX Integer32
	MAX-ACCESS read-only
	STATUS current
	DESCRIPTION
	"Description: "
	::= { powerMeterAMYDBEntry 434 }

-- .1.3.6.1.4.1.39026.3.1.4.1.2.1.435
-- .1.3.6.1.4.1.39026.3.1.4.1.2.1.435
-- .1.3.6.1.4.1.39026.3.1.4.1.2.1.435
-- .1.3.6.1.4.1.39026.3.1.4.1.2.1.435
	branchActivePower108 OBJECT-TYPE
	SYNTAX Integer32
	MAX-ACCESS read-only
	STATUS current
	DESCRIPTION
	"Description: "
	::= { powerMeterAMYDBEntry 435 }

-- .1.3.6.1.4.1.39026.3.1.4.1.2.1.436
-- .1.3.6.1.4.1.39026.3.1.4.1.2.1.436
-- .1.3.6.1.4.1.39026.3.1.4.1.2.1.436
-- .1.3.6.1.4.1.39026.3.1.4.1.2.1.436
	branchActiveEnergy108 OBJECT-TYPE
	SYNTAX Integer32
	MAX-ACCESS read-only
	STATUS current
	DESCRIPTION
	"Description: "
	::= { powerMeterAMYDBEntry 436 }

--    1.3.6.1.4.1.39026.3.1.4.1.3
-- 1.3.6.1.4.1.39026.3.1.4.1.3
-- 1.3.6.1.4.1.39026.3.1.4.1.3
		-- 1.3.6.1.4.1.39026.3.1.4.1.3
		powerMeterAMPNDCTable OBJECT-TYPE
			SYNTAX SEQUENCE OF powerMeterAMPndcEntry
			MAX-ACCESS not-accessible
			STATUS current
			DESCRIPTION
				"Description."
			::= { powerMeter 3 }

--    1.3.6.1.4.1.39026.3.1.4.1.3.1
-- 1.3.6.1.4.1.39026.3.1.4.1.3.1
-- 1.3.6.1.4.1.39026.3.1.4.1.3.1
		-- 1.3.6.1.4.1.39026.3.1.4.1.3.1
		powerMeterAMPndcEntry OBJECT-TYPE
			SYNTAX powerMeterAMPndcEntry
			MAX-ACCESS not-accessible
			STATUS current
			DESCRIPTION
				"Description."
			INDEX { pmPndcIndex }
			::= { powerMeterAMPNDCTable 1 }


		powerMeterAMPndcEntry ::=
			SEQUENCE { 	
				pmPndcIndex
					Integer32,
				pmPndcEquipOid
					DisplayString,
				pmPndcEquipName
					DisplayString,
				pmPndCollectionTime
					DisplayString,
				current
					Integer32,
				voltage
					Integer32,
				activePower
					Integer32,
				reactivePower
					Integer32,
				powerFactor
					Integer32,
				frequency
					Integer32,
				switchPathD0
					Integer32,
				switchPathD1
					Integer32,
				relayPath
					Integer32,
				totalElectricPower
					Integer32,
				inputElectricPower
					Integer32,
				outputElectricPower
					Integer32,
				ctRatio
					Integer32
			}
-- .1.3.6.1.4.1.39026.3.1.4.1.3.1.1
-- .1.3.6.1.4.1.39026.3.1.4.1.3.1.1
-- .1.3.6.1.4.1.39026.3.1.4.1.3.1.1
-- .1.3.6.1.4.1.39026.3.1.4.1.3.1.1
	pmPndcIndex OBJECT-TYPE
	SYNTAX Integer32
	MAX-ACCESS read-only
	STATUS current
	DESCRIPTION
	"Description: "
	::= { powerMeterAMPndcEntry 1 }

-- .1.3.6.1.4.1.39026.3.1.4.1.3.1.2
-- .1.3.6.1.4.1.39026.3.1.4.1.3.1.2
-- .1.3.6.1.4.1.39026.3.1.4.1.3.1.2
-- .1.3.6.1.4.1.39026.3.1.4.1.3.1.2
	pmPndcEquipOid OBJECT-TYPE
	SYNTAX Integer32
	MAX-ACCESS read-only
	STATUS current
	DESCRIPTION
	"Description: "
	::= { powerMeterAMPndcEntry 2 }

-- .1.3.6.1.4.1.39026.3.1.4.1.3.1.3
-- .1.3.6.1.4.1.39026.3.1.4.1.3.1.3
-- .1.3.6.1.4.1.39026.3.1.4.1.3.1.3
-- .1.3.6.1.4.1.39026.3.1.4.1.3.1.3
	pmPndcEquipName OBJECT-TYPE
	SYNTAX Integer32
	MAX-ACCESS read-only
	STATUS current
	DESCRIPTION
	"Description: "
	::= { powerMeterAMPndcEntry 3 }

-- .1.3.6.1.4.1.39026.3.1.4.1.3.1.4
-- .1.3.6.1.4.1.39026.3.1.4.1.3.1.4
-- .1.3.6.1.4.1.39026.3.1.4.1.3.1.4
-- .1.3.6.1.4.1.39026.3.1.4.1.3.1.4
	pmPndcCollectionTime OBJECT-TYPE
	SYNTAX Integer32
	MAX-ACCESS read-only
	STATUS current
	DESCRIPTION
	"Description: "
	::= { powerMeterAMPndcEntry 4 }

-- .1.3.6.1.4.1.39026.3.1.4.1.3.1.5
-- .1.3.6.1.4.1.39026.3.1.4.1.3.1.5
-- .1.3.6.1.4.1.39026.3.1.4.1.3.1.5
-- .1.3.6.1.4.1.39026.3.1.4.1.3.1.5
	current OBJECT-TYPE
	SYNTAX Integer32
	MAX-ACCESS read-only
	STATUS current
	DESCRIPTION
	"Description: "
	::= { powerMeterAMPndcEntry 5 }

-- .1.3.6.1.4.1.39026.3.1.4.1.3.1.6
-- .1.3.6.1.4.1.39026.3.1.4.1.3.1.6
-- .1.3.6.1.4.1.39026.3.1.4.1.3.1.6
-- .1.3.6.1.4.1.39026.3.1.4.1.3.1.6
	voltage OBJECT-TYPE
	SYNTAX Integer32
	MAX-ACCESS read-only
	STATUS current
	DESCRIPTION
	"Description: "
	::= { powerMeterAMPndcEntry 6 }

-- .1.3.6.1.4.1.39026.3.1.4.1.3.1.7
-- .1.3.6.1.4.1.39026.3.1.4.1.3.1.7
-- .1.3.6.1.4.1.39026.3.1.4.1.3.1.7
-- .1.3.6.1.4.1.39026.3.1.4.1.3.1.7
	activePower OBJECT-TYPE
	SYNTAX Integer32
	MAX-ACCESS read-only
	STATUS current
	DESCRIPTION
	"Description: "
	::= { powerMeterAMPndcEntry 7 }

-- .1.3.6.1.4.1.39026.3.1.4.1.3.1.8
-- .1.3.6.1.4.1.39026.3.1.4.1.3.1.8
-- .1.3.6.1.4.1.39026.3.1.4.1.3.1.8
-- .1.3.6.1.4.1.39026.3.1.4.1.3.1.8
	reactivePower OBJECT-TYPE
	SYNTAX Integer32
	MAX-ACCESS read-only
	STATUS current
	DESCRIPTION
	"Description: "
	::= { powerMeterAMPndcEntry 8 }

-- .1.3.6.1.4.1.39026.3.1.4.1.3.1.9
-- .1.3.6.1.4.1.39026.3.1.4.1.3.1.9
-- .1.3.6.1.4.1.39026.3.1.4.1.3.1.9
-- .1.3.6.1.4.1.39026.3.1.4.1.3.1.9
	powerFactor OBJECT-TYPE
	SYNTAX Integer32
	MAX-ACCESS read-only
	STATUS current
	DESCRIPTION
	"Description: "
	::= { powerMeterAMPndcEntry 9 }

-- .1.3.6.1.4.1.39026.3.1.4.1.3.1.10
-- .1.3.6.1.4.1.39026.3.1.4.1.3.1.10
-- .1.3.6.1.4.1.39026.3.1.4.1.3.1.10
-- .1.3.6.1.4.1.39026.3.1.4.1.3.1.10
	frequency OBJECT-TYPE
	SYNTAX Integer32
	MAX-ACCESS read-only
	STATUS current
	DESCRIPTION
	"Description: "
	::= { powerMeterAMPndcEntry 10 }

-- .1.3.6.1.4.1.39026.3.1.4.1.3.1.11
-- .1.3.6.1.4.1.39026.3.1.4.1.3.1.11
-- .1.3.6.1.4.1.39026.3.1.4.1.3.1.11
-- .1.3.6.1.4.1.39026.3.1.4.1.3.1.11
	switchPathD0 OBJECT-TYPE
	SYNTAX Integer32
	MAX-ACCESS read-only
	STATUS current
	DESCRIPTION
	"Description: "
	::= { powerMeterAMPndcEntry 11 }

-- .1.3.6.1.4.1.39026.3.1.4.1.3.1.12
-- .1.3.6.1.4.1.39026.3.1.4.1.3.1.12
-- .1.3.6.1.4.1.39026.3.1.4.1.3.1.12
-- .1.3.6.1.4.1.39026.3.1.4.1.3.1.12
	switchPathD1 OBJECT-TYPE
	SYNTAX Integer32
	MAX-ACCESS read-only
	STATUS current
	DESCRIPTION
	"Description: "
	::= { powerMeterAMPndcEntry 12 }

-- .1.3.6.1.4.1.39026.3.1.4.1.3.1.13
-- .1.3.6.1.4.1.39026.3.1.4.1.3.1.13
-- .1.3.6.1.4.1.39026.3.1.4.1.3.1.13
-- .1.3.6.1.4.1.39026.3.1.4.1.3.1.13
	relayPath OBJECT-TYPE
	SYNTAX Integer32
	MAX-ACCESS read-only
	STATUS current
	DESCRIPTION
	"Description: "
	::= { powerMeterAMPndcEntry 13 }

-- .1.3.6.1.4.1.39026.3.1.4.1.3.1.14
-- .1.3.6.1.4.1.39026.3.1.4.1.3.1.14
-- .1.3.6.1.4.1.39026.3.1.4.1.3.1.14
-- .1.3.6.1.4.1.39026.3.1.4.1.3.1.14
	totalElectricPower OBJECT-TYPE
	SYNTAX Integer32
	MAX-ACCESS read-only
	STATUS current
	DESCRIPTION
	"Description: "
	::= { powerMeterAMPndcEntry 14 }

-- .1.3.6.1.4.1.39026.3.1.4.1.3.1.15
-- .1.3.6.1.4.1.39026.3.1.4.1.3.1.15
-- .1.3.6.1.4.1.39026.3.1.4.1.3.1.15
-- .1.3.6.1.4.1.39026.3.1.4.1.3.1.15
	inputElectricPower OBJECT-TYPE
	SYNTAX Integer32
	MAX-ACCESS read-only
	STATUS current
	DESCRIPTION
	"Description: "
	::= { powerMeterAMPndcEntry 15 }

-- .1.3.6.1.4.1.39026.3.1.4.1.3.1.16
-- .1.3.6.1.4.1.39026.3.1.4.1.3.1.16
-- .1.3.6.1.4.1.39026.3.1.4.1.3.1.16
-- .1.3.6.1.4.1.39026.3.1.4.1.3.1.16
	outputElectricPower OBJECT-TYPE
	SYNTAX Integer32
	MAX-ACCESS read-only
	STATUS current
	DESCRIPTION
	"Description: "
	::= { powerMeterAMPndcEntry 16 }

-- .1.3.6.1.4.1.39026.3.1.4.1.3.1.17
-- .1.3.6.1.4.1.39026.3.1.4.1.3.1.17
-- .1.3.6.1.4.1.39026.3.1.4.1.3.1.17
-- .1.3.6.1.4.1.39026.3.1.4.1.3.1.17
	ctRatio OBJECT-TYPE
	SYNTAX Integer32
	MAX-ACCESS read-only
	STATUS current
	DESCRIPTION
	"Description: "
	::= { powerMeterAMPndcEntry 17 }

--    1.3.6.1.4.1.39026.3.1.4.2
-- 1.3.6.1.4.1.39026.3.1.4.2
-- 1.3.6.1.4.1.39026.3.1.4.2
		-- 1.3.6.1.4.1.39026.3.1.4.2
		airConditoner OBJECT IDENTIFIER ::= { dcimMonObjects 2 }

		
--    1.3.6.1.4.1.39026.3.1.4.2.1
-- 1.3.6.1.4.1.39026.3.1.4.2.1
-- 1.3.6.1.4.1.39026.3.1.4.2.1
		-- 1.3.6.1.4.1.39026.3.1.4.2.1
		acSCUITable OBJECT-TYPE
			SYNTAX SEQUENCE OF acSCUIEntry
			MAX-ACCESS not-accessible
			STATUS current
			DESCRIPTION
				"Description."
			::= { airConditoner 1 }

--    1.3.6.1.4.1.39026.3.1.4.2.1.1
-- 1.3.6.1.4.1.39026.3.1.4.2.1.1
-- 1.3.6.1.4.1.39026.3.1.4.2.1.1
		-- 1.3.6.1.4.1.39026.3.1.4.2.1.1
		acSCUIEntry OBJECT-TYPE
			SYNTAX acSCUIEntry
			MAX-ACCESS not-accessible
			STATUS current
			DESCRIPTION
				"Description."
			INDEX { acIndex }
			::= { acSCUITable 1 }


		acSCUIEntry ::=
			SEQUENCE { 
				acIndex
					Integer32,
				acEquipOid
					DisplayString,
				acEquipName
					DisplayString,
				acCollectionTime
					DisplayString,
				openOperation
					Integer32,
				returnWindTempSet
					Integer32,
				returnWindHumSet
					Integer32,
				returnWindTemp
					Integer32,
				returnWindHum
					Integer32,
				addHumCurrent
					Integer32,
				electronicConductivity
					Integer32,
				openState
					Integer32,
				fanState
					Integer32,
				heatState
					Integer32,
				coolState
					Integer32,
				addHumState
					Integer32,
				delHumState
					Integer32,
				groupControlMode
					Integer32,
				outTempSet
					Integer32,
				outHumSet
					Integer32,
				outTemp
					Integer32,
				outHum
					Integer32,
				warterValveSignal
					Integer32,
				cabTemp1
					Integer32,
				fanSpeed
					Integer32,
				warterValveRate
					Integer32,
				cabTemp2
					Integer32,
				chilledWaterInTemp
					Integer32,
				chilledWaterOutTemp
					Integer32,
				powerFrequency
					Integer32
			}	

-- .1.3.6.1.4.1.39026.3.1.4.2.1.1.1
-- .1.3.6.1.4.1.39026.3.1.4.2.1.1.1
-- .1.3.6.1.4.1.39026.3.1.4.2.1.1.1
-- .1.3.6.1.4.1.39026.3.1.4.2.1.1.1
	acIndex OBJECT-TYPE
	SYNTAX Integer32
	MAX-ACCESS read-only
	STATUS current
	DESCRIPTION
	"Description: "
	::= { acSCUIEntry 1 }

-- .1.3.6.1.4.1.39026.3.1.4.2.1.1.2
-- .1.3.6.1.4.1.39026.3.1.4.2.1.1.2
-- .1.3.6.1.4.1.39026.3.1.4.2.1.1.2
-- .1.3.6.1.4.1.39026.3.1.4.2.1.1.2
	acEquipOid OBJECT-TYPE
	SYNTAX Integer32
	MAX-ACCESS read-only
	STATUS current
	DESCRIPTION
	"Description: "
	::= { acSCUIEntry 2 }

-- .1.3.6.1.4.1.39026.3.1.4.2.1.1.3
-- .1.3.6.1.4.1.39026.3.1.4.2.1.1.3
-- .1.3.6.1.4.1.39026.3.1.4.2.1.1.3
-- .1.3.6.1.4.1.39026.3.1.4.2.1.1.3
	acEquipName OBJECT-TYPE
	SYNTAX Integer32
	MAX-ACCESS read-only
	STATUS current
	DESCRIPTION
	"Description: "
	::= { acSCUIEntry 3 }

-- .1.3.6.1.4.1.39026.3.1.4.2.1.1.4
-- .1.3.6.1.4.1.39026.3.1.4.2.1.1.4
-- .1.3.6.1.4.1.39026.3.1.4.2.1.1.4
-- .1.3.6.1.4.1.39026.3.1.4.2.1.1.4
	acCollectionTime OBJECT-TYPE
	SYNTAX Integer32
	MAX-ACCESS read-only
	STATUS current
	DESCRIPTION
	"Description: "
	::= { acSCUIEntry 4 }

-- .1.3.6.1.4.1.39026.3.1.4.2.1.1.5
-- .1.3.6.1.4.1.39026.3.1.4.2.1.1.5
-- .1.3.6.1.4.1.39026.3.1.4.2.1.1.5
-- .1.3.6.1.4.1.39026.3.1.4.2.1.1.5
	openOperation OBJECT-TYPE
	SYNTAX Integer32
	MAX-ACCESS read-only
	STATUS current
	DESCRIPTION
	"Description: "
	::= { acSCUIEntry 5 }

-- .1.3.6.1.4.1.39026.3.1.4.2.1.1.6
-- .1.3.6.1.4.1.39026.3.1.4.2.1.1.6
-- .1.3.6.1.4.1.39026.3.1.4.2.1.1.6
-- .1.3.6.1.4.1.39026.3.1.4.2.1.1.6
	returnWindTempSet OBJECT-TYPE
	SYNTAX Integer32
	MAX-ACCESS read-only
	STATUS current
	DESCRIPTION
	"Description: "
	::= { acSCUIEntry 6 }

-- .1.3.6.1.4.1.39026.3.1.4.2.1.1.7
-- .1.3.6.1.4.1.39026.3.1.4.2.1.1.7
-- .1.3.6.1.4.1.39026.3.1.4.2.1.1.7
-- .1.3.6.1.4.1.39026.3.1.4.2.1.1.7
	returnWindHumSet OBJECT-TYPE
	SYNTAX Integer32
	MAX-ACCESS read-only
	STATUS current
	DESCRIPTION
	"Description: "
	::= { acSCUIEntry 7 }

-- .1.3.6.1.4.1.39026.3.1.4.2.1.1.8
-- .1.3.6.1.4.1.39026.3.1.4.2.1.1.8
-- .1.3.6.1.4.1.39026.3.1.4.2.1.1.8
-- .1.3.6.1.4.1.39026.3.1.4.2.1.1.8
	returnWindTemp OBJECT-TYPE
	SYNTAX Integer32
	MAX-ACCESS read-only
	STATUS current
	DESCRIPTION
	"Description: "
	::= { acSCUIEntry 8 }

-- .1.3.6.1.4.1.39026.3.1.4.2.1.1.9
-- .1.3.6.1.4.1.39026.3.1.4.2.1.1.9
-- .1.3.6.1.4.1.39026.3.1.4.2.1.1.9
-- .1.3.6.1.4.1.39026.3.1.4.2.1.1.9
	returnWindHum OBJECT-TYPE
	SYNTAX Integer32
	MAX-ACCESS read-only
	STATUS current
	DESCRIPTION
	"Description: "
	::= { acSCUIEntry 9 }

-- .1.3.6.1.4.1.39026.3.1.4.2.1.1.10
-- .1.3.6.1.4.1.39026.3.1.4.2.1.1.10
-- .1.3.6.1.4.1.39026.3.1.4.2.1.1.10
-- .1.3.6.1.4.1.39026.3.1.4.2.1.1.10
	addHumCurrent OBJECT-TYPE
	SYNTAX Integer32
	MAX-ACCESS read-only
	STATUS current
	DESCRIPTION
	"Description: "
	::= { acSCUIEntry 10 }

-- .1.3.6.1.4.1.39026.3.1.4.2.1.1.11
-- .1.3.6.1.4.1.39026.3.1.4.2.1.1.11
-- .1.3.6.1.4.1.39026.3.1.4.2.1.1.11
-- .1.3.6.1.4.1.39026.3.1.4.2.1.1.11
	electronicConductivity OBJECT-TYPE
	SYNTAX Integer32
	MAX-ACCESS read-only
	STATUS current
	DESCRIPTION
	"Description: "
	::= { acSCUIEntry 11 }

-- .1.3.6.1.4.1.39026.3.1.4.2.1.1.12
-- .1.3.6.1.4.1.39026.3.1.4.2.1.1.12
-- .1.3.6.1.4.1.39026.3.1.4.2.1.1.12
-- .1.3.6.1.4.1.39026.3.1.4.2.1.1.12
	openState OBJECT-TYPE
	SYNTAX Integer32
	MAX-ACCESS read-only
	STATUS current
	DESCRIPTION
	"Description: "
	::= { acSCUIEntry 12 }

-- .1.3.6.1.4.1.39026.3.1.4.2.1.1.13
-- .1.3.6.1.4.1.39026.3.1.4.2.1.1.13
-- .1.3.6.1.4.1.39026.3.1.4.2.1.1.13
-- .1.3.6.1.4.1.39026.3.1.4.2.1.1.13
	fanState OBJECT-TYPE
	SYNTAX Integer32
	MAX-ACCESS read-only
	STATUS current
	DESCRIPTION
	"Description: "
	::= { acSCUIEntry 13 }

-- .1.3.6.1.4.1.39026.3.1.4.2.1.1.14
-- .1.3.6.1.4.1.39026.3.1.4.2.1.1.14
-- .1.3.6.1.4.1.39026.3.1.4.2.1.1.14
-- .1.3.6.1.4.1.39026.3.1.4.2.1.1.14
	heatState OBJECT-TYPE
	SYNTAX Integer32
	MAX-ACCESS read-only
	STATUS current
	DESCRIPTION
	"Description: "
	::= { acSCUIEntry 14 }

-- .1.3.6.1.4.1.39026.3.1.4.2.1.1.15
-- .1.3.6.1.4.1.39026.3.1.4.2.1.1.15
-- .1.3.6.1.4.1.39026.3.1.4.2.1.1.15
-- .1.3.6.1.4.1.39026.3.1.4.2.1.1.15
	coolState OBJECT-TYPE
	SYNTAX Integer32
	MAX-ACCESS read-only
	STATUS current
	DESCRIPTION
	"Description: "
	::= { acSCUIEntry 15 }

-- .1.3.6.1.4.1.39026.3.1.4.2.1.1.16
-- .1.3.6.1.4.1.39026.3.1.4.2.1.1.16
-- .1.3.6.1.4.1.39026.3.1.4.2.1.1.16
-- .1.3.6.1.4.1.39026.3.1.4.2.1.1.16
	addHumState OBJECT-TYPE
	SYNTAX Integer32
	MAX-ACCESS read-only
	STATUS current
	DESCRIPTION
	"Description: "
	::= { acSCUIEntry 16 }

-- .1.3.6.1.4.1.39026.3.1.4.2.1.1.17
-- .1.3.6.1.4.1.39026.3.1.4.2.1.1.17
-- .1.3.6.1.4.1.39026.3.1.4.2.1.1.17
-- .1.3.6.1.4.1.39026.3.1.4.2.1.1.17
	delHumState OBJECT-TYPE
	SYNTAX Integer32
	MAX-ACCESS read-only
	STATUS current
	DESCRIPTION
	"Description: "
	::= { acSCUIEntry 17 }

-- .1.3.6.1.4.1.39026.3.1.4.2.1.1.18
-- .1.3.6.1.4.1.39026.3.1.4.2.1.1.18
-- .1.3.6.1.4.1.39026.3.1.4.2.1.1.18
-- .1.3.6.1.4.1.39026.3.1.4.2.1.1.18
	groupControlMode OBJECT-TYPE
	SYNTAX Integer32
	MAX-ACCESS read-only
	STATUS current
	DESCRIPTION
	"Description: "
	::= { acSCUIEntry 18 }	

-- .1.3.6.1.4.1.39026.3.1.4.2.1.1.19
-- .1.3.6.1.4.1.39026.3.1.4.2.1.1.19
-- .1.3.6.1.4.1.39026.3.1.4.2.1.1.19
-- .1.3.6.1.4.1.39026.3.1.4.2.1.1.19
	outTempSet OBJECT-TYPE
	SYNTAX Integer32
	MAX-ACCESS read-only
	STATUS current
	DESCRIPTION
	"Description: "
	::= { acSCUIEntry 19 }	

-- .1.3.6.1.4.1.39026.3.1.4.2.1.1.20
-- .1.3.6.1.4.1.39026.3.1.4.2.1.1.20
-- .1.3.6.1.4.1.39026.3.1.4.2.1.1.20
-- .1.3.6.1.4.1.39026.3.1.4.2.1.1.20
	outHumSet OBJECT-TYPE
	SYNTAX Integer32
	MAX-ACCESS read-only
	STATUS current
	DESCRIPTION
	"Description: "
	::= { acSCUIEntry 20 }		
	
-- .1.3.6.1.4.1.39026.3.1.4.2.1.1.21
-- .1.3.6.1.4.1.39026.3.1.4.2.1.1.21
-- .1.3.6.1.4.1.39026.3.1.4.2.1.1.21
-- .1.3.6.1.4.1.39026.3.1.4.2.1.1.21
	outTemp OBJECT-TYPE
	SYNTAX Integer32
	MAX-ACCESS read-only
	STATUS current
	DESCRIPTION
	"Description: "
	::= { acSCUIEntry 21 }	
	
-- .1.3.6.1.4.1.39026.3.1.4.2.1.1.22
-- .1.3.6.1.4.1.39026.3.1.4.2.1.1.22
-- .1.3.6.1.4.1.39026.3.1.4.2.1.1.22
-- .1.3.6.1.4.1.39026.3.1.4.2.1.1.22
	outHum OBJECT-TYPE
	SYNTAX Integer32
	MAX-ACCESS read-only
	STATUS current
	DESCRIPTION
	"Description: "
	::= { acSCUIEntry 22 }	
	
-- .1.3.6.1.4.1.39026.3.1.4.2.1.1.23
-- .1.3.6.1.4.1.39026.3.1.4.2.1.1.23
-- .1.3.6.1.4.1.39026.3.1.4.2.1.1.23
-- .1.3.6.1.4.1.39026.3.1.4.2.1.1.23
	warterValveSignal OBJECT-TYPE
	SYNTAX Integer32
	MAX-ACCESS read-only
	STATUS current
	DESCRIPTION
	"Description: "
	::= { acSCUIEntry 23 }	
	
-- .1.3.6.1.4.1.39026.3.1.4.2.1.1.24
-- .1.3.6.1.4.1.39026.3.1.4.2.1.1.24
-- .1.3.6.1.4.1.39026.3.1.4.2.1.1.24
-- .1.3.6.1.4.1.39026.3.1.4.2.1.1.24
	cabTemp1 OBJECT-TYPE
	SYNTAX Integer32
	MAX-ACCESS read-only
	STATUS current
	DESCRIPTION
	"Description: "
	::= { acSCUIEntry 24 }	
	
-- .1.3.6.1.4.1.39026.3.1.4.2.1.1.25
-- .1.3.6.1.4.1.39026.3.1.4.2.1.1.25
-- .1.3.6.1.4.1.39026.3.1.4.2.1.1.25
-- .1.3.6.1.4.1.39026.3.1.4.2.1.1.25
	fanSpeed OBJECT-TYPE
	SYNTAX Integer32
	MAX-ACCESS read-only
	STATUS current
	DESCRIPTION
	"Description: "
	::= { acSCUIEntry 25 }	

-- .1.3.6.1.4.1.39026.3.1.4.2.1.1.26
-- .1.3.6.1.4.1.39026.3.1.4.2.1.1.26
-- .1.3.6.1.4.1.39026.3.1.4.2.1.1.26
-- .1.3.6.1.4.1.39026.3.1.4.2.1.1.26
	warterValveRate OBJECT-TYPE
	SYNTAX Integer32
	MAX-ACCESS read-only
	STATUS current
	DESCRIPTION
	"Description: "
	::= { acSCUIEntry 26 }	
	
-- .1.3.6.1.4.1.39026.3.1.4.2.1.1.27
-- .1.3.6.1.4.1.39026.3.1.4.2.1.1.27
-- .1.3.6.1.4.1.39026.3.1.4.2.1.1.27
-- .1.3.6.1.4.1.39026.3.1.4.2.1.1.27
	cabTemp2 OBJECT-TYPE
	SYNTAX Integer32
	MAX-ACCESS read-only
	STATUS current
	DESCRIPTION
	"Description: "
	::= { acSCUIEntry 27 }	
	
-- .1.3.6.1.4.1.39026.3.1.4.2.1.1.28
-- .1.3.6.1.4.1.39026.3.1.4.2.1.1.28
-- .1.3.6.1.4.1.39026.3.1.4.2.1.1.28
-- .1.3.6.1.4.1.39026.3.1.4.2.1.1.28
	chilledWaterInTemp OBJECT-TYPE
	SYNTAX Integer32
	MAX-ACCESS read-only
	STATUS current
	DESCRIPTION
	"Description: "
	::= { acSCUIEntry 28 }	
	
-- .1.3.6.1.4.1.39026.3.1.4.2.1.1.29
-- .1.3.6.1.4.1.39026.3.1.4.2.1.1.29
-- .1.3.6.1.4.1.39026.3.1.4.2.1.1.29
-- .1.3.6.1.4.1.39026.3.1.4.2.1.1.29
	chilledWaterOutTemp OBJECT-TYPE
	SYNTAX Integer32
	MAX-ACCESS read-only
	STATUS current
	DESCRIPTION
	"Description: "
	::= { acSCUIEntry 29 }

-- .1.3.6.1.4.1.39026.3.1.4.2.1.1.30
-- .1.3.6.1.4.1.39026.3.1.4.2.1.1.30
-- .1.3.6.1.4.1.39026.3.1.4.2.1.1.30
-- .1.3.6.1.4.1.39026.3.1.4.2.1.1.30
	powerFrequency OBJECT-TYPE
	SYNTAX Integer32
	MAX-ACCESS read-only
	STATUS current
	DESCRIPTION
	"Description: "
	::= { acSCUIEntry 30 }	

--    1.3.6.1.4.1.39026.3.1.4.3
-- 1.3.6.1.4.1.39026.3.1.4.3
-- 1.3.6.1.4.1.39026.3.1.4.3
		-- 1.3.6.1.4.1.39026.3.1.4.3
		env OBJECT IDENTIFIER ::= { dcimMonObjects 3 }

		
--    1.3.6.1.4.1.39026.3.1.4.3.1
-- 1.3.6.1.4.1.39026.3.1.4.3.1
-- 1.3.6.1.4.1.39026.3.1.4.3.1
		-- 1.3.6.1.4.1.39026.3.1.4.3.1
		envThTable OBJECT-TYPE
			SYNTAX SEQUENCE OF envThEntry
			MAX-ACCESS not-accessible
			STATUS current
			DESCRIPTION
				"Description."
			::= { env 1 }

--    1.3.6.1.4.1.39026.3.1.4.3.1.1
-- 1.3.6.1.4.1.39026.3.1.4.3.1.1
-- 1.3.6.1.4.1.39026.3.1.4.3.1.1
		-- 1.3.6.1.4.1.39026.3.1.4.3.1.1
		envThEntry OBJECT-TYPE
			SYNTAX envThEntry
			MAX-ACCESS not-accessible
			STATUS current
			DESCRIPTION
				"Description."
			INDEX { envIndex }
			::= { envThTable 1 }


		envThEntry ::=
			SEQUENCE { 
				envIndex
					Integer32,
				envEquipOid
					DisplayString,
				envEquipName
					DisplayString,
				envCollectionTime
					DisplayString,
				envTemp
					Integer32,
				envHum
					Integer32
			}

-- .1.3.6.1.4.1.39026.3.1.4.3.1.1.1
-- .1.3.6.1.4.1.39026.3.1.4.3.1.1.1
-- .1.3.6.1.4.1.39026.3.1.4.3.1.1.1
-- .1.3.6.1.4.1.39026.3.1.4.3.1.1.1
	envIndex OBJECT-TYPE
	SYNTAX Integer32
	MAX-ACCESS read-only
	STATUS current
	DESCRIPTION
	"Description: "
	::= { envThEntry 1 }

-- .1.3.6.1.4.1.39026.3.1.4.3.1.1.2
-- .1.3.6.1.4.1.39026.3.1.4.3.1.1.2
-- .1.3.6.1.4.1.39026.3.1.4.3.1.1.2
-- .1.3.6.1.4.1.39026.3.1.4.3.1.1.2
	envEquipOid OBJECT-TYPE
	SYNTAX Integer32
	MAX-ACCESS read-only
	STATUS current
	DESCRIPTION
	"Description: "
	::= { envThEntry 2 }

-- .1.3.6.1.4.1.39026.3.1.4.3.1.1.3
-- .1.3.6.1.4.1.39026.3.1.4.3.1.1.3
-- .1.3.6.1.4.1.39026.3.1.4.3.1.1.3
-- .1.3.6.1.4.1.39026.3.1.4.3.1.1.3
	envEquipName OBJECT-TYPE
	SYNTAX Integer32
	MAX-ACCESS read-only
	STATUS current
	DESCRIPTION
	"Description: "
	::= { envThEntry 3 }

-- .1.3.6.1.4.1.39026.3.1.4.3.1.1.4
-- .1.3.6.1.4.1.39026.3.1.4.3.1.1.4
-- .1.3.6.1.4.1.39026.3.1.4.3.1.1.4
-- .1.3.6.1.4.1.39026.3.1.4.3.1.1.4
	envCollectionTime OBJECT-TYPE
	SYNTAX Integer32
	MAX-ACCESS read-only
	STATUS current
	DESCRIPTION
	"Description: "
	::= { envThEntry 4 }

-- .1.3.6.1.4.1.39026.3.1.4.3.1.1.5
-- .1.3.6.1.4.1.39026.3.1.4.3.1.1.5
-- .1.3.6.1.4.1.39026.3.1.4.3.1.1.5
-- .1.3.6.1.4.1.39026.3.1.4.3.1.1.5
	envTemp OBJECT-TYPE
	SYNTAX Integer32
	MAX-ACCESS read-only
	STATUS current
	DESCRIPTION
	"Description: "
	::= { envThEntry 5 }

-- .1.3.6.1.4.1.39026.3.1.4.3.1.1.6
-- .1.3.6.1.4.1.39026.3.1.4.3.1.1.6
-- .1.3.6.1.4.1.39026.3.1.4.3.1.1.6
-- .1.3.6.1.4.1.39026.3.1.4.3.1.1.6
	envHum OBJECT-TYPE
	SYNTAX Integer32
	MAX-ACCESS read-only
	STATUS current
	DESCRIPTION
	"Description: "
	::= { envThEntry 6 }		


--    1.3.6.1.4.1.39026.3.1.4.4
-- 1.3.6.1.4.1.39026.3.1.4.4
-- 1.3.6.1.4.1.39026.3.1.4.4
		-- 1.3.6.1.4.1.39026.3.1.4.4
		waterLeakage OBJECT IDENTIFIER ::= { dcimMonObjects 4}

		
--    1.3.6.1.4.1.39026.3.1.4.4.1
-- 1.3.6.1.4.1.39026.3.1.4.4.1
-- 1.3.6.1.4.1.39026.3.1.4.4.1
		-- 1.3.6.1.4.1.39026.3.1.4.4.1
		waterLeakageTable OBJECT-TYPE
			SYNTAX SEQUENCE OF waterLeakageEntry
			MAX-ACCESS not-accessible
			STATUS current
			DESCRIPTION
				"Description."
			::= { waterLeakage 1 }

--    1.3.6.1.4.1.39026.3.1.4.4.1.1
-- 1.3.6.1.4.1.39026.3.1.4.4.1.1
-- 1.3.6.1.4.1.39026.3.1.4.4.1.1
		-- 1.3.6.1.4.1.39026.3.1.4.4.1.1
		waterLeakageEntry OBJECT-TYPE
			SYNTAX waterLeakageEntry
			MAX-ACCESS not-accessible
			STATUS current
			DESCRIPTION
				"Description."
			INDEX { wlIndex }
			::= { waterLeakageTable 1 }


		waterLeakageEntry ::=
			SEQUENCE { 
				wlIndex
					Integer32,
				wlEquipOid
					DisplayString,
				wlEquipName
					DisplayString,
				wlCollectionTime
					DisplayString,
				waterAlarm
					Integer32

			}	

-- .1.3.6.1.4.1.39026.3.1.4.4.1.1.1
-- .1.3.6.1.4.1.39026.3.1.4.4.1.1.1
-- .1.3.6.1.4.1.39026.3.1.4.4.1.1.1
-- .1.3.6.1.4.1.39026.3.1.4.4.1.1.1
	wlIndex OBJECT-TYPE
	SYNTAX Integer32
	MAX-ACCESS read-only
	STATUS current
	DESCRIPTION
	"Description: "
	::= { waterLeakageEntry 1 }

-- .1.3.6.1.4.1.39026.3.1.4.4.1.1.2
-- .1.3.6.1.4.1.39026.3.1.4.4.1.1.2
-- .1.3.6.1.4.1.39026.3.1.4.4.1.1.2
-- .1.3.6.1.4.1.39026.3.1.4.4.1.1.2
	wlEquipOid OBJECT-TYPE
	SYNTAX Integer32
	MAX-ACCESS read-only
	STATUS current
	DESCRIPTION
	"Description: "
	::= { waterLeakageEntry 2 }

-- .1.3.6.1.4.1.39026.3.1.4.4.1.1.3
-- .1.3.6.1.4.1.39026.3.1.4.4.1.1.3
-- .1.3.6.1.4.1.39026.3.1.4.4.1.1.3
-- .1.3.6.1.4.1.39026.3.1.4.4.1.1.3
	wlEquipName OBJECT-TYPE
	SYNTAX Integer32
	MAX-ACCESS read-only
	STATUS current
	DESCRIPTION
	"Description: "
	::= { waterLeakageEntry 3 }

-- .1.3.6.1.4.1.39026.3.1.4.4.1.1.4
-- .1.3.6.1.4.1.39026.3.1.4.4.1.1.4
-- .1.3.6.1.4.1.39026.3.1.4.4.1.1.4
-- .1.3.6.1.4.1.39026.3.1.4.4.1.1.4
	wlCollectionTime OBJECT-TYPE
	SYNTAX Integer32
	MAX-ACCESS read-only
	STATUS current
	DESCRIPTION
	"Description: "
	::= { waterLeakageEntry 4 }

-- .1.3.6.1.4.1.39026.3.1.4.4.1.1.5
-- .1.3.6.1.4.1.39026.3.1.4.4.1.1.5
-- .1.3.6.1.4.1.39026.3.1.4.4.1.1.5
-- .1.3.6.1.4.1.39026.3.1.4.4.1.1.5
	waterAlarm OBJECT-TYPE
	SYNTAX Integer32
	MAX-ACCESS read-only
	STATUS current
	DESCRIPTION
	"Description: "
	::= { waterLeakageEntry 5 }	


END

--
-- ZTE-DCIM-MIB_V3.0.mib
--
