--
-- This SMIv1 module has been generated by smidump 0.2-cvs. Do not edit.
--

SONUS-RTCP-MIB DEFINITIONS ::= BEGIN

IMPORTS
    Ipv6Address
        FROM IPV6-TC
    OBJECT-TYPE
        FROM RFC-1212
    TRAP-TYPE
        FROM RFC-1215
    IpAddress
        FROM RFC1155-SMI
    DateAndTime
        FROM SNMPv2-TC
    sonusEventClass, sonusEventDescription, sonusEventLevel, 
    sonusEventTime, sonusSequenceId, sonusShelfIndex, sonusSlotIndex
        FROM SONUS-COMMON-MIB
    sonusResourcesMIBs
        FROM SONUS-SMI
    SonusBoolean, SonusShelfIndex, SonusSlotIndex
        FROM SONUS-TC;

sonusRtcpMIB OBJECT IDENTIFIER
    ::= { sonusResourcesMIBs 7 }

-- sonusRtcpMIB MODULE-IDENTITY
--     LAST-UPDATED    "201010030000Z"
--     ORGANIZATION    
--             "Sonus Networks, Inc."
--     CONTACT-INFO    
--             "   Customer Support    
--              Sonus Networks, Inc.
--              7 Technology Park Drive
--              Westford, MA 01886
--              USA
--              
--              Tel: 978-614-8100
--              Fax: 978-614-8609"
--     DESCRIPTION     
--             "The MIB Module for RTCP."
--     ::= { sonusResourcesMIBs 7 }


sonusRtcpMIBObjects OBJECT IDENTIFIER
    ::= { sonusRtcpMIB 1 }

sonusRtcpShelfAdmnTable OBJECT-TYPE
    SYNTAX          SEQUENCE OF SonusRtcpShelfAdmnEntry
    ACCESS          not-accessible
    STATUS          mandatory
    DESCRIPTION     
            "Table of Sonus Enterprise RTCP Admn information."
    ::= { sonusRtcpMIBObjects 1 }

sonusRtcpShelfAdmnEntry OBJECT-TYPE
    SYNTAX          SonusRtcpShelfAdmnEntry
    ACCESS          not-accessible
    STATUS          mandatory
    DESCRIPTION     
            "Entry in Table consisting of the Sonus RTCP ADMN information."
    INDEX           { sonusRtcpShelfAdmnIndex }
    ::= { sonusRtcpShelfAdmnTable 1 }

SonusRtcpShelfAdmnEntry ::=
    SEQUENCE {
        sonusRtcpShelfAdmnIndex         SonusShelfIndex,
        sonusRtcpShelfAdmnSrInterval    INTEGER,
        sonusRtcpShelfAdmnEstablishInterval   INTEGER,
        sonusRtcpShelfAdmnLossTrapHistoryEntries        INTEGER,
        sonusRtcpShelfAdmnAbsenceTrapHistoryEntries           INTEGER,
        sonusRtcpShelfAdmnLossTrapHistoryTableReset           INTEGER,
        sonusRtcpShelfAdmnAbsenceTrapHistoryTableReset              INTEGER
    }

sonusRtcpShelfAdmnIndex OBJECT-TYPE
    SYNTAX          SonusShelfIndex
    ACCESS          read-only
    STATUS          mandatory
    DESCRIPTION     
            "Shelf Index for Sonus RTCP table."
    ::= { sonusRtcpShelfAdmnEntry 1 }

sonusRtcpShelfAdmnSrInterval OBJECT-TYPE
    SYNTAX          INTEGER (5..40)
    ACCESS          read-write
    STATUS          mandatory
    DESCRIPTION     
            "Time interval between the transmition of RTCP Sender Reports."
    DEFVAL          { 5 }
    ::= { sonusRtcpShelfAdmnEntry 2 }

sonusRtcpShelfAdmnEstablishInterval OBJECT-TYPE
    SYNTAX          INTEGER (1..5)
    ACCESS          read-write
    STATUS          mandatory
    DESCRIPTION     
            "The number of SR Intervals to elapse before starting bearer plane connectivity checks."
    DEFVAL          { 2 }
    ::= { sonusRtcpShelfAdmnEntry 3 }

sonusRtcpShelfAdmnLossTrapHistoryEntries OBJECT-TYPE
    SYNTAX          INTEGER (0..50)
    ACCESS          read-write
    STATUS          mandatory
    DESCRIPTION     
            "The number of entries in the loss trap history table."
    DEFVAL          { 0 }
    ::= { sonusRtcpShelfAdmnEntry 4 }

sonusRtcpShelfAdmnAbsenceTrapHistoryEntries OBJECT-TYPE
    SYNTAX          INTEGER (0..50)
    ACCESS          read-write
    STATUS          mandatory
    DESCRIPTION     
            "The number of entries in the absence trap history table."
    DEFVAL          { 0 }
    ::= { sonusRtcpShelfAdmnEntry 5 }

sonusRtcpShelfAdmnLossTrapHistoryTableReset OBJECT-TYPE
    SYNTAX          INTEGER { unknown(1), reset(2) }
    ACCESS          read-write
    STATUS          mandatory
    DESCRIPTION     
            "This object is used to reset the loss trap history table.
             This object always reads as unknown(1)."
    DEFVAL          { unknown }
    ::= { sonusRtcpShelfAdmnEntry 6 }

sonusRtcpShelfAdmnAbsenceTrapHistoryTableReset OBJECT-TYPE
    SYNTAX          INTEGER { unknown(1), reset(2) }
    ACCESS          read-write
    STATUS          mandatory
    DESCRIPTION     
            "This object is used to reset the absence trap history table.
             This object always reads as unknown(1)."
    DEFVAL          { unknown }
    ::= { sonusRtcpShelfAdmnEntry 7 }

sonusRtcpSlotLinkLossTrapStatusTable OBJECT-TYPE
    SYNTAX          SEQUENCE OF SonusRtcpSlotLinkLossTrapStatusEntry
    ACCESS          not-accessible
    STATUS          mandatory
    DESCRIPTION     
            "This table contains RTCP packet loss trap statistics for a specific slot and link. 
             A link is an IP connection over which voice over IP calls are made. The 
             IP link is terminated on the PNS NIF. The RTCP instance runs on the CNS slot (collecting 
             RTP statistics from the DSP).  Every call made through this slot and link, and configured to 				
             trap for excessive packet loss, can contribute to the statistics in this entry. 
             
             This table is enabled when the configured number of entries is non-zero.
             
             Entries remain in the table indefinitely.  A link can displace the oldest entry in the table
             that is no longer active.  Also, the entire table can be reset."
    ::= { sonusRtcpMIBObjects 4 }

sonusRtcpSlotLinkLossTrapStatusEntry OBJECT-TYPE
    SYNTAX          SonusRtcpSlotLinkLossTrapStatusEntry
    ACCESS          not-accessible
    STATUS          mandatory
    DESCRIPTION     
            "The index into this table is composed of the shelf index, the slot index, 
             the source IP address and the destination IP address of the RTP connection."
    INDEX           { sonusRtcpSlotLinkLossTrapStatShelfIndex, 
                      sonusRtcpSlotLinkLossTrapStatSlotIndex, 
                      sonusRtcpSlotLinkLossTrapStatSrcIpAddress, 
                      sonusRtcpSlotLinkLossTrapStatDestIpAddress, 
                      sonusRtcpSlotLinkLossTrapStatSrcIp6Address, 
                      sonusRtcpSlotLinkLossTrapStatDestIp6Address, 
                      sonusRtcpSlotLinkLossTrapStatSrcIpVersion, 
                      sonusRtcpSlotLinkLossTrapStatDestIpVersion }
    ::= { sonusRtcpSlotLinkLossTrapStatusTable 1 }

SonusRtcpSlotLinkLossTrapStatusEntry ::=
    SEQUENCE {
        sonusRtcpSlotLinkLossTrapStatShelfIndex       SonusShelfIndex,
        sonusRtcpSlotLinkLossTrapStatSlotIndex      SonusSlotIndex,
        sonusRtcpSlotLinkLossTrapStatSrcIpAddress         IpAddress,
        sonusRtcpSlotLinkLossTrapStatDestIpAddress          IpAddress,
        sonusRtcpSlotLinkLossTrapStatCount  INTEGER,
        sonusRtcpSlotLinkLossTrapStatTotalCount       INTEGER,
        sonusRtcpSlotLinkLossTrapStatStartTime      DateAndTime,
        sonusRtcpSlotLinkLossTrapStatLastTime     DateAndTime,
        sonusRtcpSlotLinkLossTrapStatActive   SonusBoolean,
        sonusRtcpSlotLinkLossTrapStatSrcIp6Address          Ipv6Address,
        sonusRtcpSlotLinkLossTrapStatDestIp6Address           Ipv6Address,
        sonusRtcpSlotLinkLossTrapStatSrcIpVersion         INTEGER,
        sonusRtcpSlotLinkLossTrapStatDestIpVersion          INTEGER
    }

sonusRtcpSlotLinkLossTrapStatShelfIndex OBJECT-TYPE
    SYNTAX          SonusShelfIndex
    ACCESS          read-only
    STATUS          mandatory
    DESCRIPTION     
            "Shelf index for this table."
    ::= { sonusRtcpSlotLinkLossTrapStatusEntry 1 }

sonusRtcpSlotLinkLossTrapStatSlotIndex OBJECT-TYPE
    SYNTAX          SonusSlotIndex
    ACCESS          read-only
    STATUS          mandatory
    DESCRIPTION     
            "The slot index for the CNS server that hosts the RTCP instance maintaing this table."
    ::= { sonusRtcpSlotLinkLossTrapStatusEntry 2 }

sonusRtcpSlotLinkLossTrapStatSrcIpAddress OBJECT-TYPE
    SYNTAX          IpAddress
    ACCESS          read-only
    STATUS          mandatory
    DESCRIPTION     
            "Source IP address of the link.  RTCP detected excessive packet loss for a voice over IP call on this link
             for which trap generation is specified."
    ::= { sonusRtcpSlotLinkLossTrapStatusEntry 3 }

sonusRtcpSlotLinkLossTrapStatDestIpAddress OBJECT-TYPE
    SYNTAX          IpAddress
    ACCESS          read-only
    STATUS          mandatory
    DESCRIPTION     
            "Destination IP address of the link.  RTCP detected excessive packet loss for a voice over IP call on this link
             for which trap generation is specified."
    ::= { sonusRtcpSlotLinkLossTrapStatusEntry 4 }

sonusRtcpSlotLinkLossTrapStatCount OBJECT-TYPE
    SYNTAX          INTEGER
    ACCESS          read-only
    STATUS          mandatory
    DESCRIPTION     
            "This field reflects the number of times excessive loss was detected on voice over IP calls made through this
             slot and link during the period between the described start time and last time."
    ::= { sonusRtcpSlotLinkLossTrapStatusEntry 5 }

sonusRtcpSlotLinkLossTrapStatTotalCount OBJECT-TYPE
    SYNTAX          INTEGER
    ACCESS          read-only
    STATUS          mandatory
    DESCRIPTION     
            "This field indicates the total number of times excessive loss was detected on voice over IP calls made through 
             this slot and link."
    ::= { sonusRtcpSlotLinkLossTrapStatusEntry 6 }

sonusRtcpSlotLinkLossTrapStatStartTime OBJECT-TYPE
    SYNTAX          DateAndTime
    ACCESS          read-only
    STATUS          mandatory
    DESCRIPTION     
            "Indicates the time excessive packet loss started on a call made through this slot and link.  This field is 
             unchanged while excessive loss is active.  It is later updated if excessive packet loss resumes, after a 
             quiet period of 15 seconds is detected."
    ::= { sonusRtcpSlotLinkLossTrapStatusEntry 7 }

sonusRtcpSlotLinkLossTrapStatLastTime OBJECT-TYPE
    SYNTAX          DateAndTime
    ACCESS          read-only
    STATUS          mandatory
    DESCRIPTION     
            "Indicates the last time excessive packet loss was detected through this slot and link."
    ::= { sonusRtcpSlotLinkLossTrapStatusEntry 8 }

sonusRtcpSlotLinkLossTrapStatActive OBJECT-TYPE
    SYNTAX          SonusBoolean
    ACCESS          read-only
    STATUS          mandatory
    DESCRIPTION     
            "This field is TRUE if excessive loss is detected on a call through this slot and link. It is FALSE if 15 
             seconds have elapsed without excessive loss occuring."
    ::= { sonusRtcpSlotLinkLossTrapStatusEntry 9 }

sonusRtcpSlotLinkLossTrapStatSrcIp6Address OBJECT-TYPE
    SYNTAX          Ipv6Address
    ACCESS          read-write
    STATUS          mandatory
    DESCRIPTION     
            "Source IPv6 address of the link.  RTCP detected excessive packet loss for a voice over IP call on this link
             for which trap generation is specified."
    ::= { sonusRtcpSlotLinkLossTrapStatusEntry 10 }

sonusRtcpSlotLinkLossTrapStatDestIp6Address OBJECT-TYPE
    SYNTAX          Ipv6Address
    ACCESS          read-write
    STATUS          mandatory
    DESCRIPTION     
            "Destination IPV6 address of the link.  RTCP detected excessive packet loss for a voice over IP call on this link
             for which trap generation is specified."
    ::= { sonusRtcpSlotLinkLossTrapStatusEntry 11 }

sonusRtcpSlotLinkLossTrapStatSrcIpVersion OBJECT-TYPE
    SYNTAX          INTEGER { afInet(2), afInet6(24) }
    ACCESS          read-only
    STATUS          mandatory
    DESCRIPTION     
            "The IP address type  of this Rtcp loss table ."
    ::= { sonusRtcpSlotLinkLossTrapStatusEntry 12 }

sonusRtcpSlotLinkLossTrapStatDestIpVersion OBJECT-TYPE
    SYNTAX          INTEGER { afInet(2), afInet6(24) }
    ACCESS          read-only
    STATUS          mandatory
    DESCRIPTION     
            "The IP address type  of this Rtcp loss table ."
    ::= { sonusRtcpSlotLinkLossTrapStatusEntry 13 }

sonusRtcpSlotLinkAbsenceTrapStatusTable OBJECT-TYPE
    SYNTAX          SEQUENCE OF SonusRtcpSlotLinkAbsenceTrapStatusEntry
    ACCESS          not-accessible
    STATUS          mandatory
    DESCRIPTION     
            "This table contains RTCP packet loss trap statistics for a specific slot and link. 
             A link is an IP connection over which voice over IP calls are made. The 
             IP link is terminated on the PNS NIF. The RTCP instance runs on the CNS slot (collecting 
             RTP statistics from the DSP).  Every call made through this slot and link, and configured to 				
             trap in the absence of RTP and RTCP packets within the detection interval , can contribute 
             to the statistics in this entry.  The detection interval is two times the configured 
             Sender Report interval.
             
             This table is enabled when the configured number of entries is non-zero.
             
             Entries remain in the table indefinitely.  A link can displace the oldest entry in the table
             that is no longer active.  Also, the entire table can be reset."
    ::= { sonusRtcpMIBObjects 5 }

sonusRtcpSlotLinkAbsenceTrapStatusEntry OBJECT-TYPE
    SYNTAX          SonusRtcpSlotLinkAbsenceTrapStatusEntry
    ACCESS          not-accessible
    STATUS          mandatory
    DESCRIPTION     
            "The index into this table is composed of the shelf index, the slot index, 
             the source IP address and the destination IP address of the RTP connection."
    INDEX           { sonusRtcpSlotLinkAbsenceTrapStatShelfIndex, 
                      sonusRtcpSlotLinkAbsenceTrapStatSlotIndex, 
                      sonusRtcpSlotLinkAbsenceTrapStatSrcIpAddress, 
                      sonusRtcpSlotLinkAbsenceTrapStatDestIpAddress, 
                      sonusRtcpSlotLinkAbsenceTrapStatSrcIp6Address, 
                      sonusRtcpSlotLinkAbsenceTrapStatDestIp6Address, 
                      sonusRtcpSlotLinkAbsenceTrapStatSrcIpVersion, 
                      sonusRtcpSlotLinkAbsenceTrapStatDestIpVersion }
    ::= { sonusRtcpSlotLinkAbsenceTrapStatusTable 1 }

SonusRtcpSlotLinkAbsenceTrapStatusEntry ::=
    SEQUENCE {
        sonusRtcpSlotLinkAbsenceTrapStatShelfIndex          SonusShelfIndex,
        sonusRtcpSlotLinkAbsenceTrapStatSlotIndex         SonusSlotIndex,
        sonusRtcpSlotLinkAbsenceTrapStatSrcIpAddress            IpAddress,
        sonusRtcpSlotLinkAbsenceTrapStatDestIpAddress             IpAddress,
        sonusRtcpSlotLinkAbsenceTrapStatCount     INTEGER,
        sonusRtcpSlotLinkAbsenceTrapStatTotalCount          INTEGER,
        sonusRtcpSlotLinkAbsenceTrapStatStartTime         DateAndTime,
        sonusRtcpSlotLinkAbsenceTrapStatLastTime        DateAndTime,
        sonusRtcpSlotLinkAbsenceTrapStatActive      SonusBoolean,
        sonusRtcpSlotLinkAbsenceTrapStatSrcIp6Address             Ipv6Address,
        sonusRtcpSlotLinkAbsenceTrapStatDestIp6Address              Ipv6Address,
        sonusRtcpSlotLinkAbsenceTrapStatSrcIpVersion            INTEGER,
        sonusRtcpSlotLinkAbsenceTrapStatDestIpVersion             INTEGER
    }

sonusRtcpSlotLinkAbsenceTrapStatShelfIndex OBJECT-TYPE
    SYNTAX          SonusShelfIndex
    ACCESS          read-only
    STATUS          mandatory
    DESCRIPTION     
            "Shelf for this RTCP slot link table."
    ::= { sonusRtcpSlotLinkAbsenceTrapStatusEntry 1 }

sonusRtcpSlotLinkAbsenceTrapStatSlotIndex OBJECT-TYPE
    SYNTAX          SonusSlotIndex
    ACCESS          read-only
    STATUS          mandatory
    DESCRIPTION     
            "The slot index for the CNS server that hosts the RTCP instance maintaing this table."
    ::= { sonusRtcpSlotLinkAbsenceTrapStatusEntry 2 }

sonusRtcpSlotLinkAbsenceTrapStatSrcIpAddress OBJECT-TYPE
    SYNTAX          IpAddress
    ACCESS          read-only
    STATUS          mandatory
    DESCRIPTION     
            "Source IP address of the link.  RTCP detected absence for a voice over IP call on this link
             for which trap generation is specified."
    ::= { sonusRtcpSlotLinkAbsenceTrapStatusEntry 3 }

sonusRtcpSlotLinkAbsenceTrapStatDestIpAddress OBJECT-TYPE
    SYNTAX          IpAddress
    ACCESS          read-only
    STATUS          mandatory
    DESCRIPTION     
            "Destination IP address of the link.  RTCP detected absence for a voice over IP call on this link
             for which trap generation is specified."
    ::= { sonusRtcpSlotLinkAbsenceTrapStatusEntry 4 }

sonusRtcpSlotLinkAbsenceTrapStatCount OBJECT-TYPE
    SYNTAX          INTEGER
    ACCESS          read-only
    STATUS          mandatory
    DESCRIPTION     
            "This field reflects the number of times RTCP detected absence on voice over IP calls made through this
             slot and link during the period between the described start time and last time."
    ::= { sonusRtcpSlotLinkAbsenceTrapStatusEntry 5 }

sonusRtcpSlotLinkAbsenceTrapStatTotalCount OBJECT-TYPE
    SYNTAX          INTEGER
    ACCESS          read-only
    STATUS          mandatory
    DESCRIPTION     
            "This field indicates the total number of times RTCP detected absence  on voice over IP calls made through 
             this slot and link."
    ::= { sonusRtcpSlotLinkAbsenceTrapStatusEntry 6 }

sonusRtcpSlotLinkAbsenceTrapStatStartTime OBJECT-TYPE
    SYNTAX          DateAndTime
    ACCESS          read-only
    STATUS          mandatory
    DESCRIPTION     
            "Indicates the time RTCP detected absence on a call made through this slot and link.  This field is 
             unchanged while absence is active.  It is updated if excessive packet loss resumes, after a quiet 
             period of 15 seconds is detected."
    ::= { sonusRtcpSlotLinkAbsenceTrapStatusEntry 7 }

sonusRtcpSlotLinkAbsenceTrapStatLastTime OBJECT-TYPE
    SYNTAX          DateAndTime
    ACCESS          read-only
    STATUS          mandatory
    DESCRIPTION     
            "Indicates the last time absence was detected through this slot and link."
    ::= { sonusRtcpSlotLinkAbsenceTrapStatusEntry 8 }

sonusRtcpSlotLinkAbsenceTrapStatActive OBJECT-TYPE
    SYNTAX          SonusBoolean
    ACCESS          read-only
    STATUS          mandatory
    DESCRIPTION     
            "This field is TRUE if absence is detected on a call through this slot and link. It is FALSE if 15 
             seconds have elapsed without absence occuring."
    ::= { sonusRtcpSlotLinkAbsenceTrapStatusEntry 9 }

sonusRtcpSlotLinkAbsenceTrapStatSrcIp6Address OBJECT-TYPE
    SYNTAX          Ipv6Address
    ACCESS          read-write
    STATUS          mandatory
    DESCRIPTION     
            "Source IPV6 address of the link.  RTCP detected absence for a voice over IP call on this link
             for which trap generation is specified."
    ::= { sonusRtcpSlotLinkAbsenceTrapStatusEntry 10 }

sonusRtcpSlotLinkAbsenceTrapStatDestIp6Address OBJECT-TYPE
    SYNTAX          Ipv6Address
    ACCESS          read-write
    STATUS          mandatory
    DESCRIPTION     
            "Destination IPV6 address of the link.  RTCP detected absence for a voice over IP call on this link
             for which trap generation is specified."
    ::= { sonusRtcpSlotLinkAbsenceTrapStatusEntry 11 }

sonusRtcpSlotLinkAbsenceTrapStatSrcIpVersion OBJECT-TYPE
    SYNTAX          INTEGER { afInet(2), afInet6(24) }
    ACCESS          read-only
    STATUS          mandatory
    DESCRIPTION     
            "The IP address type  of this Rtcp Absence table ."
    ::= { sonusRtcpSlotLinkAbsenceTrapStatusEntry 12 }

sonusRtcpSlotLinkAbsenceTrapStatDestIpVersion OBJECT-TYPE
    SYNTAX          INTEGER { afInet(2), afInet6(24) }
    ACCESS          read-only
    STATUS          mandatory
    DESCRIPTION     
            "The IP address type  of this Rtcp Absence table ."
    ::= { sonusRtcpSlotLinkAbsenceTrapStatusEntry 13 }

sonusRtcpMIBNotifications OBJECT IDENTIFIER
    ::= { sonusRtcpMIB 2 }

sonusRtcpMIBNotificationsPrefix OBJECT IDENTIFIER
    ::= { sonusRtcpMIBNotifications 0 }

sonusRtcpMIBNotificationsObjects OBJECT IDENTIFIER
    ::= { sonusRtcpMIBNotifications 1 }

sonusRtcpLocalIpAddr OBJECT-TYPE
    SYNTAX          IpAddress
    ACCESS          read-only
    STATUS          mandatory
    DESCRIPTION     
            "Represents the local IP address for this RTP session."
    ::= { sonusRtcpMIBNotificationsObjects 1 }

sonusRtcpRemoteIpAddr OBJECT-TYPE
    SYNTAX          IpAddress
    ACCESS          read-only
    STATUS          mandatory
    DESCRIPTION     
            "Represents the remote IP address for this RTP session."
    ::= { sonusRtcpMIBNotificationsObjects 2 }

sonusRtcpCallGcid OBJECT-TYPE
    SYNTAX          INTEGER
    ACCESS          read-only
    STATUS          mandatory
    DESCRIPTION     
            "Represents the call GCID for this RTP session."
    ::= { sonusRtcpMIBNotificationsObjects 3 }

sonusRtcpPacketLossThresholdExceededNotification TRAP-TYPE
    ENTERPRISE      sonusRtcpMIBNotifications
    VARIABLES       { sonusShelfIndex, sonusSlotIndex, 
                      sonusEventDescription, sonusEventClass, 
                      sonusEventLevel, sonusSequenceId, sonusEventTime, 
                      sonusRtcpCallGcid }
--     STATUS          mandatory
    DESCRIPTION     
            "This trap indicates that the RTP packet loss count has exceeded
             a user-specified threshold in one or more RTP sessions on the
             specified shelf and slot."
    ::= 1

sonusRtcpPacketLossThresholdClearedNotification TRAP-TYPE
    ENTERPRISE      sonusRtcpMIBNotifications
    VARIABLES       { sonusShelfIndex, sonusSlotIndex, 
                      sonusEventDescription, sonusEventClass, 
                      sonusEventLevel, sonusSequenceId, sonusEventTime }
--     STATUS          mandatory
    DESCRIPTION     
            "This trap indicates that the RTP packet loss threshold
             was not exceeded in any RTP session on the specified shelf
             and slot for a period of 15 seconds."
    ::= 2

sonusRtcpNoRtpOrRtcpPacketsReceivedNotification TRAP-TYPE
    ENTERPRISE      sonusRtcpMIBNotifications
    VARIABLES       { sonusShelfIndex, sonusSlotIndex, 
                      sonusEventDescription, sonusEventClass, 
                      sonusEventLevel, sonusSequenceId, sonusEventTime, 
                      sonusRtcpCallGcid }
--     STATUS          mandatory
    DESCRIPTION     
            "This trap indicates that no RTP packets and no RTCP packets were received 
             on a session originating on the specified shelf and slot."
    ::= 3

sonusRtcpNoRtpOrRtcpPacketsClearedNotification TRAP-TYPE
    ENTERPRISE      sonusRtcpMIBNotifications
    VARIABLES       { sonusShelfIndex, sonusSlotIndex, 
                      sonusEventDescription, sonusEventClass, 
                      sonusEventLevel, sonusSequenceId, sonusEventTime }
--     STATUS          mandatory
    DESCRIPTION     
            "This trap indicates that the condition of no RTP or RTCP packets received
             has not occured on the specified shelf and slot for a period of 15 seconds."
    ::= 4

END -- end of module SONUS-RTCP-MIB.
