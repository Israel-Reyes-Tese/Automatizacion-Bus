--
-- This SMIv1 module has been generated by smidump 0.2-cvs. Do not edit.
--

SONUS-DATANODE-TRAP-MIB DEFINITIONS ::= BEGIN

IMPORTS
    TRAP-TYPE
        FROM RFC-1215
    Counter, IpAddress
        FROM RFC1155-SMI
    sonusAlarmDescription, sonusAlarmLevel, sonusAlarmNodeID, 
    sonusAlarmSequenceId, sonusAlarmTime
        FROM SONUS-COMMON-TRAP-MIB
    sonusDatanodeNotificationMIBs
        FROM SONUS-SMI;

sonusDatanodeTraps OBJECT IDENTIFIER
    ::= { sonusDatanodeNotificationMIBs 1 }

-- sonusDatanodeTraps MODULE-IDENTITY
--     LAST-UPDATED    "200911100000Z"
--     ORGANIZATION    
--             "Sonus Networks, Inc."
--     CONTACT-INFO    
--             "   Customer Support     
--              Sonus Networks, Inc. 
--              7 Technology Park Drive 
--              Westford, MA 01886 
--              USA     
--              
--              Tel: 978-614-8100 
--              Fax: 978-614-8609"
--     DESCRIPTION     
--             "The MIB Module for Datanode notifications"
--     REVISION        "200911100000Z"
--     DESCRIPTION     
--             "Last revision."
--     ::= { sonusDatanodeNotificationMIBs 1 }


sonusDatanodeMIBNotifications OBJECT IDENTIFIER
    ::= { sonusDatanodeTraps 1 }

sonusDatanodeMIBNotificationsPrefix OBJECT IDENTIFIER
    ::= { sonusDatanodeMIBNotifications 0 }

sonusDatanodeProcessFailed TRAP-TYPE
    ENTERPRISE      sonusDatanodeMIBNotifications
    VARIABLES       { sonusAlarmNodeID, sonusAlarmLevel, 
                      sonusAlarmSequenceId, sonusAlarmTime, 
                      sonusAlarmDescription }
--     STATUS          mandatory
    DESCRIPTION     
            "Processes has stopped running"
    ::= 2

sonusDatanodeProcessClear TRAP-TYPE
    ENTERPRISE      sonusDatanodeMIBNotifications
    VARIABLES       { sonusAlarmNodeID, sonusAlarmLevel, 
                      sonusAlarmSequenceId, sonusAlarmTime, 
                      sonusAlarmDescription }
--     STATUS          mandatory
    DESCRIPTION     
            "Processes has stopped running"
    ::= 3

sonusDatanodeSystemFailed TRAP-TYPE
    ENTERPRISE      sonusDatanodeMIBNotifications
    VARIABLES       { sonusAlarmNodeID, sonusAlarmLevel, 
                      sonusAlarmSequenceId, sonusAlarmTime, 
                      sonusAlarmDescription }
--     STATUS          mandatory
    DESCRIPTION     
            "Processes has stopped running"
    ::= 4

sonusDatanodeSystemClear TRAP-TYPE
    ENTERPRISE      sonusDatanodeMIBNotifications
    VARIABLES       { sonusAlarmNodeID, sonusAlarmLevel, 
                      sonusAlarmSequenceId, sonusAlarmTime, 
                      sonusAlarmDescription }
--     STATUS          mandatory
    DESCRIPTION     
            "Processes has stopped running"
    ::= 5

sonusDatanodeThresholdCPUAbove TRAP-TYPE
    ENTERPRISE      sonusDatanodeMIBNotifications
    VARIABLES       { sonusAlarmNodeID, sonusAlarmLevel, 
                      sonusAlarmSequenceId, sonusAlarmTime, 
                      sonusAlarmDescription }
--     STATUS          mandatory
    DESCRIPTION     
            "Processes has stopped running"
    ::= 6

sonusDatanodeThresholdCPUClear TRAP-TYPE
    ENTERPRISE      sonusDatanodeMIBNotifications
    VARIABLES       { sonusAlarmNodeID, sonusAlarmLevel, 
                      sonusAlarmSequenceId, sonusAlarmTime, 
                      sonusAlarmDescription }
--     STATUS          mandatory
    DESCRIPTION     
            "Processes has stopped running"
    ::= 8

sonusDatanodeThresholdMemoryAbove TRAP-TYPE
    ENTERPRISE      sonusDatanodeMIBNotifications
    VARIABLES       { sonusAlarmNodeID, sonusAlarmLevel, 
                      sonusAlarmSequenceId, sonusAlarmTime, 
                      sonusAlarmDescription }
--     STATUS          mandatory
    DESCRIPTION     
            "Processes has stopped running"
    ::= 9

sonusDatanodeThresholdMemoryClear TRAP-TYPE
    ENTERPRISE      sonusDatanodeMIBNotifications
    VARIABLES       { sonusAlarmNodeID, sonusAlarmLevel, 
                      sonusAlarmSequenceId, sonusAlarmTime, 
                      sonusAlarmDescription }
--     STATUS          mandatory
    DESCRIPTION     
            "Processes has stopped running"
    ::= 11

sonusDatanodeClusterNameChange TRAP-TYPE
    ENTERPRISE      sonusDatanodeMIBNotifications
    VARIABLES       { sonusAlarmNodeID, sonusAlarmLevel, 
                      sonusAlarmSequenceId, sonusAlarmTime, 
                      sonusAlarmDescription }
--     STATUS          mandatory
    DESCRIPTION     
            "Failed to modify cluster name"
    ::= 12

sonusDatanodeThresholdDiskAbove TRAP-TYPE
    ENTERPRISE      sonusDatanodeMIBNotifications
    VARIABLES       { sonusAlarmNodeID, sonusAlarmLevel, 
                      sonusAlarmSequenceId, sonusAlarmTime, 
                      sonusAlarmDescription }
--     STATUS          mandatory
    DESCRIPTION     
            "Processes has stopped running"
    ::= 13

sonusDatanodeThresholdDiskClear TRAP-TYPE
    ENTERPRISE      sonusDatanodeMIBNotifications
    VARIABLES       { sonusAlarmNodeID, sonusAlarmLevel, 
                      sonusAlarmSequenceId, sonusAlarmTime, 
                      sonusAlarmDescription }
--     STATUS          mandatory
    DESCRIPTION     
            "Processes has stopped running"
    ::= 14

END -- end of module SONUS-DATANODE-TRAP-MIB.
