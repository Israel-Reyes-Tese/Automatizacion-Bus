ZTE-CSIRP-MIB DEFINITIONS ::= BEGIN

IMPORTS
        MODULE-IDENTITY, OBJECT-TYPE, NOTIFICATION-TYPE,
        enterprises
                FROM SNMPv2-SMI
        TEXTUAL-CONVENTION, DisplayString
                FROM SNMPv2-TC
        OBJECT-GROUP, NOTIFICATION-GROUP, MODULE-COMPLIANCE
                FROM SNMPv2-CONF
        alarm
        	FROM ZTE-IRP-MIB;


csIRP 		              OBJECT IDENTIFIER ::= { alarm 4 }
csIRPInfo			  	  OBJECT IDENTIFIER ::= { csIRP 1 }
csNotifications  	      OBJECT IDENTIFIER ::= { csIRP 2 }
csNotificationProfile	  OBJECT IDENTIFIER ::= { csNotifications 1 }

--======================================================================
-- TEXTUAL CONVENTIONS
--======================================================================


--======================================================================
-- IRP VERSION INFORMATION
--======================================================================

csIRPVersion OBJECT-TYPE
        SYNTAX      DisplayString (SIZE (0..20))
        MAX-ACCESS  read-only
        STATUS      current
        DESCRIPTION
                "This object represents the version of the CS IRP
                 SNMPv2 Solution Set supported by the agent."
        ::= { csIRPInfo 1 }
        
csIRPHeartbeatPeriod OBJECT-TYPE
        SYNTAX      INTEGER
        MAX-ACCESS  read-write
        STATUS      current
        DESCRIPTION
                "It specifies the time between two emissions of heartbeat
				notifications. A value of zero implies there is no heartbeat
				emission. The unit is second.
				
				Range: value range of heartbeat period
					is from 5 second to 300 second, 0 is also a legal value."					
        ::= { csIRPInfo 2 }

--======================================================================
-- CS RELATED NOTIFICATIONS
--======================================================================

heartbeatNotification NOTIFICATION-TYPE
        OBJECTS {   
                    csIRPHeartbeatPeriod
                }
        STATUS      current
        DESCRIPTION 
                "If the value of csIRPHeartbeatPeriod equals 0,then 
                 no heartbeat notification will be generated.
                 
                 If the value of csIRPHeartbeatPeriod is bigger than 0
                 ,the heartbeat notification should be issued when the
                 inner timer of heartbeat has reached ,and the timer 
                 would be resetted."
        ::= { csNotificationProfile 1 }

END
