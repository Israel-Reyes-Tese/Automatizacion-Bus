--
-- This SMIv1 module has been generated by smidump 0.2-cvs. Do not edit.
--

SM10-R3-MIB DEFINITIONS ::= BEGIN

IMPORTS
    InetAddress, InetAddressType
        FROM INET-ADDRESS-MIB
    OBJECT-TYPE
        FROM RFC-1212
    TRAP-TYPE
        FROM RFC-1215
    enterprises
        FROM SNMPv2-SMI;

sm10R3 OBJECT IDENTIFIER
    ::= { storageManager 500 }

-- sm10R3 MODULE-IDENTITY
--     LAST-UPDATED    "201108051503Z"
--     ORGANIZATION    
--             "NetApp, Inc"
--     CONTACT-INFO    
--             "http://www.netapp.com/us/support/"
--     DESCRIPTION     
--             "SANtricity Storage Manager for E-Series Storage Systems"
--     REVISION        "201108051503Z"
--     DESCRIPTION     
--             "This is the third revision of the sm10 MIB. This revision of the sm10
--              MIB module has been converted to NetApp private enterprise number space."
--     ::= { storageManager 500 }


netapp OBJECT IDENTIFIER
    ::= { enterprises 789 }

eSeriesStorageSystem OBJECT IDENTIFIER
    ::= { netapp 1123 }

storageManager OBJECT IDENTIFIER
    ::= { eSeriesStorageSystem 1 }

smConformance OBJECT IDENTIFIER
    ::= { storageManager 8 }

smCompliance OBJECT IDENTIFIER
    ::= { smConformance 1 }

smGroups OBJECT IDENTIFIER
    ::= { smConformance 2 }

sm10R3TrapBase OBJECT IDENTIFIER
    ::= { sm10R3 0 }

infoTable OBJECT-TYPE
    SYNTAX          SEQUENCE OF InfoEntry
    ACCESS          not-accessible
    STATUS          mandatory
    DESCRIPTION     
            "Information for array traps."
    ::= { sm10R3 1 }

infoEntry OBJECT-TYPE
    SYNTAX          InfoEntry
    ACCESS          not-accessible
    STATUS          mandatory
    DESCRIPTION     
            "The data for array traps."
    INDEX           { deviceHostIPType }
    ::= { infoTable 1 }

InfoEntry ::=
    SEQUENCE {
        deviceHostIPType                InetAddressType,
        deviceHostIPAddr                InetAddress,
        deviceHostName                  DisplayString,
        deviceUserLabel                 DisplayString,
        deviceErrorCode                 DisplayString,
        eventTime                       DisplayString,
        trapDescription                 DisplayString,
        componentType                   DisplayString,
        componentLocation               DisplayString
    }

deviceHostIPType OBJECT-TYPE
    SYNTAX          InetAddressType
    ACCESS          read-only
    STATUS          mandatory
    DESCRIPTION     
            "Type of IP Address of the network-attached device or device host. 0 unknown, 1 ipv4, 2 ipv6"
    ::= { infoEntry 1 }

deviceHostIPAddr OBJECT-TYPE
    SYNTAX          InetAddress
    ACCESS          read-only
    STATUS          mandatory
    DESCRIPTION     
            "IP Address of the network-attached device or device host."
    ::= { infoEntry 2 }

deviceHostName OBJECT-TYPE
    SYNTAX          DisplayString (SIZE(0..17))
    ACCESS          read-only
    STATUS          mandatory
    DESCRIPTION     
            "The user label for the host of the device being reported on."
    ::= { infoEntry 3 }

deviceUserLabel OBJECT-TYPE
    SYNTAX          DisplayString (SIZE(0..30))
    ACCESS          read-only
    STATUS          mandatory
    DESCRIPTION     
            "The user label for the device being reported on."
    ::= { infoEntry 4 }

deviceErrorCode OBJECT-TYPE
    SYNTAX          DisplayString (SIZE(0..19))
    ACCESS          read-only
    STATUS          mandatory
    DESCRIPTION     
            "The error code as reported by the device or host."
    ::= { infoEntry 5 }

eventTime OBJECT-TYPE
    SYNTAX          DisplayString (SIZE(0..39))
    ACCESS          read-only
    STATUS          mandatory
    DESCRIPTION     
            "The time at which the event happen on the device."
    ::= { infoEntry 6 }

trapDescription OBJECT-TYPE
    SYNTAX          DisplayString (SIZE(0..69))
    ACCESS          read-only
    STATUS          mandatory
    DESCRIPTION     
            "A string to indicate the nature of the trap"
    ::= { infoEntry 7 }

componentType OBJECT-TYPE
    SYNTAX          DisplayString (SIZE(0..59))
    ACCESS          read-only
    STATUS          mandatory
    DESCRIPTION     
            "A string to identify the failing component type"
    ::= { infoEntry 8 }

componentLocation OBJECT-TYPE
    SYNTAX          DisplayString (SIZE(0..39))
    ACCESS          read-only
    STATUS          mandatory
    DESCRIPTION     
            "A string to identify the location of the failing component"
    ::= { infoEntry 9 }

storageServer OBJECT IDENTIFIER
    ::= { eSeriesStorageSystem 2 }

storageArrayCritical TRAP-TYPE
    ENTERPRISE      sm10R3
    VARIABLES       { deviceHostIPType, deviceHostIPAddr, deviceHostName, 
                      deviceUserLabel, deviceErrorCode, eventTime, 
                      trapDescription, componentType, componentLocation }
--     STATUS          mandatory
    DESCRIPTION     
            "This trap indicates an event where user-interaction is required immediately.
             Some example events are component failures or critical errors."
    ::= 2

smObjectGroup OBJECT IDENTIFIER
    ::= { smGroups 1 }

-- smObjectGroup OBJECT-GROUP
--     OBJECTS         { deviceHostIPType, deviceHostIPAddr, 
--                       deviceHostName, deviceUserLabel, 
--                       deviceErrorCode, eventTime, trapDescription, 
--                       componentType, componentLocation }
--     STATUS          mandatory
--     DESCRIPTION     
--             "A collection of objects that are current in this
--              MIB."
--     ::= { smGroups 1 }

smNotificationGroup OBJECT IDENTIFIER
    ::= { smGroups 2 }

-- smNotificationGroup NOTIFICATION-GROUP
--     NOTIFICATIONS   { storageArrayCritical }
--     STATUS          mandatory
--     DESCRIPTION     
--             "A collection of notifications that are current in this
--              MIB."
--     ::= { smGroups 2 }

smGrpCompliance OBJECT IDENTIFIER
    ::= { smCompliance 1 }

-- smGrpCompliance MODULE-COMPLIANCE
--     STATUS          mandatory
--     DESCRIPTION     
--             "The compliance statement for current SNMP entities in
--              the NetApp E-Series Storage Systems SM10-R3 MIB."

--     MODULE          -- -- this module

--         MANDATORY-GROUPS    { smObjectGroup, smNotificationGroup }

--     ::= { smCompliance 1 }

END -- end of module SM10-R3-MIB.
