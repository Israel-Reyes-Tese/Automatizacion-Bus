MIB-PNMSJ-IPASOLINK-400-CASCADE-MIB DEFINITIONS ::= BEGIN
    
    IMPORTS
        OBJECT-TYPE
            FROM RFC-1212
        IpAddress, Opaque
            FROM RFC1155-SMI
        enterprises
            FROM SNMPv2-SMI
        RowStatus
            FROM SNMPv2-TC;
    
    IpeCascadeShelfCount ::=
        INTEGER (1..4)
    
    
    IpeCascadeShelfIndex ::=
        INTEGER (1..4)
    
    
    -- 1.3.6.1.4.1.119
    nec OBJECT IDENTIFIER
        ::= { enterprises 119 }
    
    -- 1.3.6.1.4.1.119.2
    nec-mib OBJECT IDENTIFIER
        ::= { nec 2 }
    
    -- 1.3.6.1.4.1.119.2.3
    necProductDepend OBJECT IDENTIFIER
        ::= { nec-mib 3 }
    
    -- 1.3.6.1.4.1.119.2.3.69
    radioEquipment OBJECT IDENTIFIER
        ::= { necProductDepend 69 }
    
    -- 1.3.6.1.4.1.119.2.3.69.203
    commonPnms OBJECT IDENTIFIER
        ::= { radioEquipment 203 }
    
    -- 1.3.6.1.4.1.119.2.3.69.203.503
    ipasolink400 OBJECT IDENTIFIER
        ::= { commonPnms 503 }
    
    -- 1.3.6.1.4.1.119.2.3.69.203.503.5
    system5 OBJECT IDENTIFIER
        ::= { ipasolink400 5 }
    
    -- 1.3.6.1.4.1.119.2.3.69.203.503.5.3
    ipeConfigurationGroup OBJECT IDENTIFIER
        ::= { system5 3 }
    
    -- 1.3.6.1.4.1.119.2.3.69.203.503.5.3.26
    ipeCfgCascadeGroup OBJECT IDENTIFIER
        ::= { ipeConfigurationGroup 26 }
    
    -- 1.3.6.1.4.1.119.2.3.69.203.503.5.3.26.1
    ipeCfgCascadeTable OBJECT-TYPE
        SYNTAX      SEQUENCE OF IpeCfgCascadeEntry
        ACCESS      not-accessible
        STATUS      mandatory
        DESCRIPTION
            "this table configures cascade group information.
             the information contains total shelf counts and
             shelf id for the shelf."
        ::= { ipeCfgCascadeGroup 1 }
    
    -- 1.3.6.1.4.1.119.2.3.69.203.503.5.3.26.1.1
    ipeCfgCascadeEntry OBJECT-TYPE
        SYNTAX      IpeCfgCascadeEntry
        ACCESS      not-accessible
        STATUS      mandatory
        DESCRIPTION
            ""
        INDEX       { ipeCfgCascadeNEAddress, ipeCfgCascadeId }
        ::= { ipeCfgCascadeTable 1 }
    
    IpeCfgCascadeEntry ::= SEQUENCE {
        ipeCfgCascadeId         INTEGER,
        ipeCfgCascadeNEAddress  IpAddress,
        ipeCfgCascadeShelves    IpeCascadeShelfCount,
        ipeCfgCascadeMyShelfId  IpeCascadeShelfIndex
    }
    
    -- 1.3.6.1.4.1.119.2.3.69.203.503.5.3.26.1.1.1
    ipeCfgCascadeId OBJECT-TYPE
        SYNTAX      INTEGER (1)
        ACCESS      not-accessible
        STATUS      mandatory
        DESCRIPTION
            "Index for this table."
        ::= { ipeCfgCascadeEntry 1 }
    
    -- 1.3.6.1.4.1.119.2.3.69.203.503.5.3.26.1.1.2
    ipeCfgCascadeNEAddress OBJECT-TYPE
        SYNTAX      IpAddress
        ACCESS      not-accessible
        STATUS      mandatory
        DESCRIPTION
            "Reserved."
        ::= { ipeCfgCascadeEntry 2 }
    
    -- 1.3.6.1.4.1.119.2.3.69.203.503.5.3.26.1.1.3
    ipeCfgCascadeShelves OBJECT-TYPE
        SYNTAX      IpeCascadeShelfCount
        ACCESS      read-write
        STATUS      mandatory
        DESCRIPTION
            "The total count of cascaded shelves.
             This object must have same value among the cascaded
             shelves"
        ::= { ipeCfgCascadeEntry 3 }
    
    -- 1.3.6.1.4.1.119.2.3.69.203.503.5.3.26.1.1.4
    ipeCfgCascadeMyShelfId OBJECT-TYPE
        SYNTAX      IpeCascadeShelfIndex
        ACCESS      read-write
        STATUS      mandatory
        DESCRIPTION
            "the shelf id for this shelf.
             this object must not be larger than ipeCfgCascadeShelves.
             And this object must not have same value among the cascaded
             shelves."
        ::= { ipeCfgCascadeEntry 4 }
    
    -- 1.3.6.1.4.1.119.2.3.69.203.503.5.3.26.2
    ipeCfgCascadeShelfTable OBJECT-TYPE
        SYNTAX      SEQUENCE OF IpeCfgCascadeShelfEntry
        ACCESS      not-accessible
        STATUS      mandatory
        DESCRIPTION
            "this table configures the ip address for the cascade
             shelves."
        ::= { ipeCfgCascadeGroup 2 }
    
    -- 1.3.6.1.4.1.119.2.3.69.203.503.5.3.26.2.1
    ipeCfgCascadeShelfEntry OBJECT-TYPE
        SYNTAX      IpeCfgCascadeShelfEntry
        ACCESS      not-accessible
        STATUS      mandatory
        DESCRIPTION
            ""
        INDEX       { ipeCfgCascadeShelfNEAddress, ipeCfgCascadeShelfId }
        ::= { ipeCfgCascadeShelfTable 1 }
    
    IpeCfgCascadeShelfEntry ::= SEQUENCE {
        ipeCfgCascadeShelfId            IpeCascadeShelfIndex,
        ipeCfgCascadeShelfNEAddress     IpAddress,
        ipeCfgCascadeShelfRowStatus     RowStatus,
        ipeCfgCascadeShelfIpAddress     IpAddress
    }
    
    -- 1.3.6.1.4.1.119.2.3.69.203.503.5.3.26.2.1.1
    ipeCfgCascadeShelfId OBJECT-TYPE
        SYNTAX      IpeCascadeShelfIndex
        ACCESS      not-accessible
        STATUS      mandatory
        DESCRIPTION
            "index of this table.
             This value must not larger than ipeCfgCascadeShelves."
        ::= { ipeCfgCascadeShelfEntry 1 }
    
    -- 1.3.6.1.4.1.119.2.3.69.203.503.5.3.26.2.1.2
    ipeCfgCascadeShelfNEAddress OBJECT-TYPE
        SYNTAX      IpAddress
        ACCESS      not-accessible
        STATUS      mandatory
        DESCRIPTION
            "reserved"
        ::= { ipeCfgCascadeShelfEntry 2 }
    
    -- 1.3.6.1.4.1.119.2.3.69.203.503.5.3.26.2.1.3
    ipeCfgCascadeShelfRowStatus OBJECT-TYPE
        SYNTAX      RowStatus
        ACCESS      read-write
        STATUS      mandatory
        DESCRIPTION
            "RowStatus for this entry."
        ::= { ipeCfgCascadeShelfEntry 3 }
    
    -- 1.3.6.1.4.1.119.2.3.69.203.503.5.3.26.2.1.4
    ipeCfgCascadeShelfIpAddress OBJECT-TYPE
        SYNTAX      IpAddress
        ACCESS      read-write
        STATUS      mandatory
        DESCRIPTION
            "The IP Address of cascaded shelf whose shelf id is
             ipeCfgCascadeShelfId."
        ::= { ipeCfgCascadeShelfEntry 4 }
    
END -- end of module MIB-PNMSJ-IPASOLINK-400-CASCADE-MIB.
