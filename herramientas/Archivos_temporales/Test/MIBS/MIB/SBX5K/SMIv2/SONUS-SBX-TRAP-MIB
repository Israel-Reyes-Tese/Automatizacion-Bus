--
-- This SMIv2 module has been generated by smidump 0.2-cvs. Do not edit.
--

SONUS-SBX-TRAP-MIB DEFINITIONS ::= BEGIN

IMPORTS
    Ipv6Address
        FROM IPV6-TC
    Counter32, Integer32, IpAddress, MODULE-IDENTITY, NOTIFICATION-TYPE, 
    OBJECT-TYPE, Unsigned32
        FROM SNMPv2-SMI
    DisplayString
        FROM SNMPv2-TC
    SonusAdminState, SonusGMTTime, SonusName, SonusNameReference
        FROM SONUS-COMMON-TC
    sonusAlarmDescription, sonusAlarmLevel, sonusAlarmNodeID, 
    sonusAlarmSequenceId, sonusAlarmTime
        FROM SONUS-COMMON-TRAP-MIB
    sonusSBX5000NotificationMIBs
        FROM SONUS-SMI;

sonusSbxTraps MODULE-IDENTITY
    LAST-UPDATED    "201504040000Z"
    ORGANIZATION    
            "Sonus Networks, Inc."
    CONTACT-INFO    
            "   Customer Support     
             Sonus Networks, Inc. 
             7 Technology Park Drive 
                 Westford, MA 01886 
             USA 
             
             Tel: 978-614-8100 
                 Fax: 978-614-8609"
    DESCRIPTION     
            "The MIB Module for SBC notifications"
    REVISION        "200911100000Z"
    DESCRIPTION     
            "Last revision."
    ::= { sonusSBX5000NotificationMIBs 1 }


sonusSipSignallingMIBNotifications OBJECT IDENTIFIER
    ::= { sonusSbxTraps 1 }

sonusSipSignallingMIBNotificationsPrefix OBJECT IDENTIFIER
    ::= { sonusSipSignallingMIBNotifications 0 }

sonusSipSignallingMIBNotificationsObjects OBJECT IDENTIFIER
    ::= { sonusSipSignallingMIBNotifications 1 }

sonusSipTgName OBJECT-TYPE
    SYNTAX          SonusNameReference
    MAX-ACCESS      read-only
    STATUS          current
    DESCRIPTION     
            "Name of the SIP service group."
    ::= { sonusSipSignallingMIBNotificationsObjects 1 }

sonusSipSigPortIpAddress OBJECT-TYPE
    SYNTAX          IpAddress
    MAX-ACCESS      read-only
    STATUS          current
    DESCRIPTION     
            "
             IP Address of the Sip Signalling Port - mandatory parameter. 
             "
    ::= { sonusSipSignallingMIBNotificationsObjects 2 }

sonusSipSigPortNum OBJECT-TYPE
    SYNTAX          Integer32 (1..65535)
    MAX-ACCESS      read-only
    STATUS          current
    DESCRIPTION     
            "
             UDP/TCP port number of SIP Signalling Port (default is 5060).
             "
    ::= { sonusSipSignallingMIBNotificationsObjects 3 }

sonusSipArsStatSigZoneId OBJECT-TYPE
    SYNTAX          Unsigned32
    MAX-ACCESS      read-only
    STATUS          current
    DESCRIPTION     
            "The Id of the Signaling Zone where address reachability service status
             is being shown."
    ::= { sonusSipSignallingMIBNotificationsObjects 4 }

sonusSipArsStatEndpointIpAddress OBJECT-TYPE
    SYNTAX          IpAddress
    MAX-ACCESS      read-only
    STATUS          current
    DESCRIPTION     
            "
             Blacklisted endpoint's IP Address. 
             "
    ::= { sonusSipSignallingMIBNotificationsObjects 5 }

sonusSipArsStatEndpointIpPortNum OBJECT-TYPE
    SYNTAX          Integer32 (0..65535)
    MAX-ACCESS      read-only
    STATUS          current
    DESCRIPTION     
            "
             Blacklisted endpoint's UDP port number.
             "
    ::= { sonusSipSignallingMIBNotificationsObjects 6 }

sonusSipArsStatSigPortNum OBJECT-TYPE
    SYNTAX          Unsigned32
    MAX-ACCESS      read-only
    STATUS          current
    DESCRIPTION     
            "A signaling port in the signaling zone showing status."
    ::= { sonusSipSignallingMIBNotificationsObjects 7 }

sonusSipArsStatEndpointOwnerId OBJECT-TYPE
    SYNTAX          Unsigned32 (1..65535)
    MAX-ACCESS      read-only
    STATUS          current
    DESCRIPTION     
            "Blacklisted endpoints owner id. This is identifies the slot that originally  blacklisted the endpoint."
    ::= { sonusSipSignallingMIBNotificationsObjects 8 }

sonusSipArsEndpointRecoveryAll OBJECT-TYPE
    SYNTAX          INTEGER { none(0), oneSigZone(1), allSigZone(2), 
                        allinOneSlot(3) }
    MAX-ACCESS      read-only
    STATUS          current
    DESCRIPTION     
            "The flag for recovering a group of endpoints: all endpoints in one signaling
             zone or all endpoints in all signaling zones."
    ::= { sonusSipSignallingMIBNotificationsObjects 9 }

sonusSipSigProto OBJECT-TYPE
    SYNTAX          DisplayString
    MAX-ACCESS      read-only
    STATUS          current
    DESCRIPTION     
            " The signaling transport protocol."
    ::= { sonusSipSignallingMIBNotificationsObjects 10 }

sonusPingPeerIpAddress OBJECT-TYPE
    SYNTAX          IpAddress
    MAX-ACCESS      read-only
    STATUS          current
    DESCRIPTION     
            "IP Address of the SIP Peer."
    ::= { sonusSipSignallingMIBNotificationsObjects 11 }

sonusPingPeerPortNum OBJECT-TYPE
    SYNTAX          Integer32 (0..65535)
    MAX-ACCESS      read-only
    STATUS          current
    DESCRIPTION     
            "UDP/TCP port number of SIP Peer."
    ::= { sonusSipSignallingMIBNotificationsObjects 12 }

sonusPingPeerZoneId OBJECT-TYPE
    SYNTAX          Unsigned32
    MAX-ACCESS      read-only
    STATUS          current
    DESCRIPTION     
            "The Id of the Signaling Zone where OPTIONS is received from the SIP Peer."
    ::= { sonusSipSignallingMIBNotificationsObjects 13 }

sonusSipAorSigZoneId OBJECT-TYPE
    SYNTAX          Unsigned32
    MAX-ACCESS      read-only
    STATUS          current
    DESCRIPTION     
            "The Id of the Signaling Zone"
    ::= { sonusSipSignallingMIBNotificationsObjects 14 }

sonusSurrRegPeerIpAddress OBJECT-TYPE
    SYNTAX          IpAddress
    MAX-ACCESS      read-only
    STATUS          current
    DESCRIPTION     
            "IP Address of the SurrReg Peer."
    ::= { sonusSipSignallingMIBNotificationsObjects 15 }

sonusSurrRegPeerPortNum OBJECT-TYPE
    SYNTAX          Integer32 (1..65535)
    MAX-ACCESS      read-only
    STATUS          current
    DESCRIPTION     
            "port number of SurrReg Peer."
    ::= { sonusSipSignallingMIBNotificationsObjects 16 }

sonusSurrRegPeerZoneId OBJECT-TYPE
    SYNTAX          Unsigned32
    MAX-ACCESS      read-only
    STATUS          current
    DESCRIPTION     
            "The Id of the Signaling Zone where Surrogate Registration enabled for Sip Peer."
    ::= { sonusSipSignallingMIBNotificationsObjects 17 }

sonusSipArsStatEndpointIpAddressV6 OBJECT-TYPE
    SYNTAX          Ipv6Address
    MAX-ACCESS      read-only
    STATUS          current
    DESCRIPTION     
            "Blacklisted endpoint's IP Address."
    ::= { sonusSipSignallingMIBNotificationsObjects 18 }

sonusSipSigPortIpAddressV6 OBJECT-TYPE
    SYNTAX          Ipv6Address
    MAX-ACCESS      read-only
    STATUS          current
    DESCRIPTION     
            "IP Address of the Sip Signalling Port - mandatory parameter."
    ::= { sonusSipSignallingMIBNotificationsObjects 19 }

sonusPingPeerIpAddressV6 OBJECT-TYPE
    SYNTAX          Ipv6Address
    MAX-ACCESS      read-only
    STATUS          current
    DESCRIPTION     
            "IP Address of the SIP Peer."
    ::= { sonusSipSignallingMIBNotificationsObjects 20 }

sonusSurrRegPeerIpAddressV6 OBJECT-TYPE
    SYNTAX          Ipv6Address
    MAX-ACCESS      read-only
    STATUS          current
    DESCRIPTION     
            "IP Address of the SIP Peer."
    ::= { sonusSipSignallingMIBNotificationsObjects 21 }

sonusPingPeerFqdn OBJECT-TYPE
    SYNTAX          DisplayString
    MAX-ACCESS      read-only
    STATUS          current
    DESCRIPTION     
            "The Fully Qualified Domain Name of the SIP Peer."
    ::= { sonusSipSignallingMIBNotificationsObjects 22 }

sonusSurrRegMethodName OBJECT-TYPE
    SYNTAX          DisplayString
    MAX-ACCESS      read-only
    STATUS          current
    DESCRIPTION     
            "METHOD for which Surrogate Endpoint Authentication is failed."
    ::= { sonusSipSignallingMIBNotificationsObjects 23 }

sonusSurrRegPeerName OBJECT-TYPE
    SYNTAX          DisplayString
    MAX-ACCESS      read-only
    STATUS          current
    DESCRIPTION     
            "Peer Name of Surrogate Endpoint for which Authentication is failed."
    ::= { sonusSipSignallingMIBNotificationsObjects 24 }

sonusSurrRegUserPart OBJECT-TYPE
    SYNTAX          DisplayString
    MAX-ACCESS      read-only
    STATUS          current
    DESCRIPTION     
            "UserPart of Surrogate Endpoint for which Authentication is failed."
    ::= { sonusSipSignallingMIBNotificationsObjects 25 }

sonusCertReCheckSocketId OBJECT-TYPE
    SYNTAX          Unsigned32
    MAX-ACCESS      read-only
    STATUS          current
    DESCRIPTION     
            "The socketId of the session failing certificate recheck."
    ::= { sonusSipSignallingMIBNotificationsObjects 26 }

sonusCertReCheckName OBJECT-TYPE
    SYNTAX          DisplayString (SIZE(1..101))
    MAX-ACCESS      read-only
    STATUS          current
    DESCRIPTION     
            "The name of the certificate failing recheck."
    ::= { sonusSipSignallingMIBNotificationsObjects 27 }

sonusRecorderIpAddress OBJECT-TYPE
    SYNTAX          IpAddress
    MAX-ACCESS      read-only
    STATUS          current
    DESCRIPTION     
            "IP Address of the Recording Server."
    ::= { sonusSipSignallingMIBNotificationsObjects 28 }

sonusRecorderIpAddressV6 OBJECT-TYPE
    SYNTAX          Ipv6Address
    MAX-ACCESS      read-only
    STATUS          current
    DESCRIPTION     
            "IP V6 Address of the Recording Server."
    ::= { sonusSipSignallingMIBNotificationsObjects 29 }

sonusRecorderPortNum OBJECT-TYPE
    SYNTAX          Integer32 (1..65535)
    MAX-ACCESS      read-only
    STATUS          current
    DESCRIPTION     
            "Port number of Recording Server."
    ::= { sonusSipSignallingMIBNotificationsObjects 30 }

sonusRecCallGCID OBJECT-TYPE
    SYNTAX          Unsigned32
    MAX-ACCESS      read-only
    STATUS          current
    DESCRIPTION     
            "The GCID of the call being recorded."
    ::= { sonusSipSignallingMIBNotificationsObjects 31 }

sonusRecorderTrunkName OBJECT-TYPE
    SYNTAX          SonusNameReference
    MAX-ACCESS      read-only
    STATUS          current
    DESCRIPTION     
            "Name of the trunk group where recorder is configured."
    ::= { sonusSipSignallingMIBNotificationsObjects 32 }

sonusRecordingCallLeg OBJECT-TYPE
    SYNTAX          SonusNameReference
    MAX-ACCESS      read-only
    STATUS          current
    DESCRIPTION     
            "The call leg in communication session being recorded."
    ::= { sonusSipSignallingMIBNotificationsObjects 33 }

sonusNonRouteInviteRequestUri OBJECT-TYPE
    SYNTAX          DisplayString
    MAX-ACCESS      read-only
    STATUS          current
    DESCRIPTION     
            "
             reqUri of the non-routed invite. 
             "
    ::= { sonusSipSignallingMIBNotificationsObjects 34 }

sonusNonRouteInviteSourceIpAddress OBJECT-TYPE
    SYNTAX          DisplayString
    MAX-ACCESS      read-only
    STATUS          current
    DESCRIPTION     
            "
             Source Ip Address where the non-routed invite was originated from.
             "
    ::= { sonusSipSignallingMIBNotificationsObjects 35 }

sonusNonRouteInviteSourceIpPortNum OBJECT-TYPE
    SYNTAX          Integer32 (1..65535)
    MAX-ACCESS      read-only
    STATUS          current
    DESCRIPTION     
            "
             Source port number of the invite where non-routed invite was originated from.
             "
    ::= { sonusSipSignallingMIBNotificationsObjects 36 }

sonusTgTrunkGroupName OBJECT-TYPE
    SYNTAX          DisplayString
    MAX-ACCESS      read-only
    STATUS          current
    DESCRIPTION     
            "The trunk group name."
    ::= { sonusSipSignallingMIBNotificationsObjects 37 }

sonusDropSipMsgFromUnknowSrcAddress OBJECT-TYPE
    SYNTAX          DisplayString
    MAX-ACCESS      read-only
    STATUS          current
    DESCRIPTION     
            "
             Unknown source Ip address where sip message is originated from.
             "
    ::= { sonusSipSignallingMIBNotificationsObjects 38 }

sonusDropSipMsgFromUnknowSrcMsgType OBJECT-TYPE
    SYNTAX          DisplayString
    MAX-ACCESS      read-only
    STATUS          current
    DESCRIPTION     
            "
             SIP message type for which SIP message is being dropped.
             "
    ::= { sonusSipSignallingMIBNotificationsObjects 39 }

sonusSipIceGcid OBJECT-TYPE
    SYNTAX          Unsigned32
    MAX-ACCESS      read-only
    STATUS          current
    DESCRIPTION     
            "
             The GCID of the call for which the STUN message is processed for.
             "
    ::= { sonusSipSignallingMIBNotificationsObjects 40 }

sonusSipIceRemoteIpAddress OBJECT-TYPE
    SYNTAX          IpAddress
    MAX-ACCESS      read-only
    STATUS          current
    DESCRIPTION     
            "STUN Remote IP Address."
    ::= { sonusSipSignallingMIBNotificationsObjects 41 }

sonusSipIceRemotePort OBJECT-TYPE
    SYNTAX          Integer32 (1..65535)
    MAX-ACCESS      read-only
    STATUS          current
    DESCRIPTION     
            "
             STUN Remote Port number.
             "
    ::= { sonusSipSignallingMIBNotificationsObjects 42 }

sonusSipIceLocalIpAddress OBJECT-TYPE
    SYNTAX          IpAddress
    MAX-ACCESS      read-only
    STATUS          current
    DESCRIPTION     
            "
             STUN Local IP Address. 
             "
    ::= { sonusSipSignallingMIBNotificationsObjects 43 }

sonusSipIceLocalPort OBJECT-TYPE
    SYNTAX          Integer32 (1..65535)
    MAX-ACCESS      read-only
    STATUS          current
    DESCRIPTION     
            "
             STUN Local Port number.
             "
    ::= { sonusSipSignallingMIBNotificationsObjects 44 }

sonusSipIceFailReason OBJECT-TYPE
    SYNTAX          DisplayString
    MAX-ACCESS      read-only
    STATUS          current
    DESCRIPTION     
            "
             STUN message validation reason.
             "
    ::= { sonusSipSignallingMIBNotificationsObjects 45 }

sonusEmergencyMessageRejected OBJECT-TYPE
    SYNTAX          DisplayString
    MAX-ACCESS      read-only
    STATUS          current
    DESCRIPTION     
            "
             Emergency Message Rejected.
             "
    ::= { sonusSipSignallingMIBNotificationsObjects 46 }

sonusRPHNamespace OBJECT-TYPE
    SYNTAX          DisplayString
    MAX-ACCESS      read-only
    STATUS          current
    DESCRIPTION     
            "
             RPH namespace for which the emergency Message Rejected.
             "
    ::= { sonusSipSignallingMIBNotificationsObjects 47 }

sonusRPHPriority OBJECT-TYPE
    SYNTAX          DisplayString
    MAX-ACCESS      read-only
    STATUS          current
    DESCRIPTION     
            "
             Rph priority value for which emergency Message Rejected.
             "
    ::= { sonusSipSignallingMIBNotificationsObjects 48 }

sonusPrefixedNumber OBJECT-TYPE
    SYNTAX          DisplayString
    MAX-ACCESS      read-only
    STATUS          current
    DESCRIPTION     
            "
             Prefixed Number for which emergency Message Rejected.
             "
    ::= { sonusSipSignallingMIBNotificationsObjects 49 }

sonusSubscriptionId OBJECT-TYPE
    SYNTAX          Unsigned32
    MAX-ACCESS      read-only
    STATUS          current
    DESCRIPTION     
            "The subscription id of current subscription."
    ::= { sonusSipSignallingMIBNotificationsObjects 50 }

sonusZoneIdName OBJECT-TYPE
    SYNTAX          DisplayString
    MAX-ACCESS      read-only
    STATUS          current
    DESCRIPTION     
            "
             Zone Name for which emergency Message Rejected.
             "
    ::= { sonusSipSignallingMIBNotificationsObjects 51 }

sonusTrunkGroupName OBJECT-TYPE
    SYNTAX          DisplayString
    MAX-ACCESS      read-only
    STATUS          current
    DESCRIPTION     
            "
             Tg Name for which emergency Message Rejected.
             "
    ::= { sonusSipSignallingMIBNotificationsObjects 52 }

sonusPolicerName OBJECT-TYPE
    SYNTAX          DisplayString
    MAX-ACCESS      read-only
    STATUS          current
    DESCRIPTION     
            "
             Policer which rejects the emergency Message.
             "
    ::= { sonusSipSignallingMIBNotificationsObjects 53 }

sonusSipIceLocalIpV6Address OBJECT-TYPE
    SYNTAX          Ipv6Address
    MAX-ACCESS      read-only
    STATUS          current
    DESCRIPTION     
            "
             STUN Local IP V6 Address. 
             "
    ::= { sonusSipSignallingMIBNotificationsObjects 54 }

sonusSipIceRemoteIpV6Address OBJECT-TYPE
    SYNTAX          Ipv6Address
    MAX-ACCESS      read-only
    STATUS          current
    DESCRIPTION     
            "
             STUN Remote IP V6 Address. 
             "
    ::= { sonusSipSignallingMIBNotificationsObjects 55 }

sonusRecNumStreamsConfigured OBJECT-TYPE
    SYNTAX          Unsigned32
    MAX-ACCESS      read-only
    STATUS          current
    DESCRIPTION     
            "Number of recording streams configured for this gcid"
    ::= { sonusSipSignallingMIBNotificationsObjects 56 }

sonusRecInitFailureReason OBJECT-TYPE
    SYNTAX          DisplayString
    MAX-ACCESS      read-only
    STATUS          current
    DESCRIPTION     
            "Reason for failure to initiate SIPREC recording "
    ::= { sonusSipSignallingMIBNotificationsObjects 57 }

sonusMonIpAddress OBJECT-TYPE
    SYNTAX          IpAddress
    MAX-ACCESS      read-only
    STATUS          current
    DESCRIPTION     
            "IP Address of the Monitoring Server."
    ::= { sonusSipSignallingMIBNotificationsObjects 58 }

sonusMonPortNum OBJECT-TYPE
    SYNTAX          Integer32 (1..65535)
    MAX-ACCESS      read-only
    STATUS          current
    DESCRIPTION     
            "UDP/TCP port number of the Monitoring Server. "
    ::= { sonusSipSignallingMIBNotificationsObjects 59 }

sonusMonIpAddressV6 OBJECT-TYPE
    SYNTAX          Ipv6Address
    MAX-ACCESS      read-only
    STATUS          current
    DESCRIPTION     
            "IP Address of the Monitoring Server."
    ::= { sonusSipSignallingMIBNotificationsObjects 60 }

sonusMsbcIpAddress OBJECT-TYPE
    SYNTAX          IpAddress
    MAX-ACCESS      read-only
    STATUS          current
    DESCRIPTION     
            "IP Address of the MSBC."
    ::= { sonusSipSignallingMIBNotificationsObjects 61 }

sonusMsbcIpAddressV6 OBJECT-TYPE
    SYNTAX          Ipv6Address
    MAX-ACCESS      read-only
    STATUS          current
    DESCRIPTION     
            "IP Address of the MSBC."
    ::= { sonusSipSignallingMIBNotificationsObjects 62 }

sonusSipArsStatSigZoneName OBJECT-TYPE
    SYNTAX          DisplayString (SIZE(1..63))
    MAX-ACCESS      read-only
    STATUS          current
    DESCRIPTION     
            "The name of the ARS Zone"
    ::= { sonusSipSignallingMIBNotificationsObjects 63 }

sonusPingPeerZoneName OBJECT-TYPE
    SYNTAX          DisplayString (SIZE(1..63))
    MAX-ACCESS      read-only
    STATUS          current
    DESCRIPTION     
            "The name of the Peer Zone"
    ::= { sonusSipSignallingMIBNotificationsObjects 64 }

sonusPingPeerName OBJECT-TYPE
    SYNTAX          DisplayString (SIZE(1..63))
    MAX-ACCESS      read-only
    STATUS          current
    DESCRIPTION     
            "The name of the Peer"
    ::= { sonusSipSignallingMIBNotificationsObjects 65 }

sonusH323SignallingMIBNotifications OBJECT IDENTIFIER
    ::= { sonusSbxTraps 2 }

sonusH323SignallingMIBNotificationsPrefix OBJECT IDENTIFIER
    ::= { sonusH323SignallingMIBNotifications 0 }

sonusH323SignallingMIBNotificationsObjects OBJECT IDENTIFIER
    ::= { sonusH323SignallingMIBNotifications 1 }

sonusH323TrunkGrpName OBJECT-TYPE
    SYNTAX          SonusNameReference
    MAX-ACCESS      read-only
    STATUS          current
    DESCRIPTION     
            "Name of the H323 trunk group."
    ::= { sonusH323SignallingMIBNotificationsObjects 1 }

sonusSoftswitchClientServicesMIBNotifications OBJECT IDENTIFIER
    ::= { sonusSbxTraps 3 }

sonusSoftswitchClientServicesMIBNotificationsPrefix OBJECT IDENTIFIER
    ::= { sonusSoftswitchClientServicesMIBNotifications 0 }

sonusSoftswitchClientServicesMIBNotificationsObjects OBJECT IDENTIFIER
    ::= { sonusSoftswitchClientServicesMIBNotifications 1 }

sonusPscsPolicyServerName OBJECT-TYPE
    SYNTAX          SonusName
    MAX-ACCESS      read-only
    STATUS          current
    DESCRIPTION     
            "The name of this Softswitch."
    ::= { sonusSoftswitchClientServicesMIBNotificationsObjects 1 }

sonusPscsTranErrorReason OBJECT-TYPE
    SYNTAX          INTEGER { noSoftswitchAvailable(1), 
                        transactionTimeout(2), invalidParameters(3), 
                        receiveError(4), transmitError(5), 
                        encodeApiError(6), decodeApiError(7), 
                        noMatchingReplyCbFound(8) }
    MAX-ACCESS      read-only
    STATUS          current
    DESCRIPTION     
            "The reason why a transaction has failed."
    ::= { sonusSoftswitchClientServicesMIBNotificationsObjects 2 }

sonusPscsRejectIndReason OBJECT-TYPE
    SYNTAX          INTEGER { notRegistered(1), unknownGateway(2), 
                        errorAVPContent(3), errorMsgContent(4), 
                        maxClientAccount(5), miscRegFailure(6) }
    MAX-ACCESS      read-only
    STATUS          current
    DESCRIPTION     
            "The reason why a reject ind received."
    ::= { sonusSoftswitchClientServicesMIBNotificationsObjects 3 }

sonusPscsCalledNumber OBJECT-TYPE
    SYNTAX          DisplayString
    MAX-ACCESS      read-only
    STATUS          current
    DESCRIPTION     
            "Destination number."
    ::= { sonusSoftswitchClientServicesMIBNotificationsObjects 4 }

sonusPscsCallingNumber OBJECT-TYPE
    SYNTAX          DisplayString
    MAX-ACCESS      read-only
    STATUS          current
    DESCRIPTION     
            "Originating number."
    ::= { sonusSoftswitchClientServicesMIBNotificationsObjects 5 }

sonusPscsCarrierCode OBJECT-TYPE
    SYNTAX          DisplayString
    MAX-ACCESS      read-only
    STATUS          current
    DESCRIPTION     
            "Carrier code."
    ::= { sonusSoftswitchClientServicesMIBNotificationsObjects 6 }

sonusPscsRouteFailureReason OBJECT-TYPE
    SYNTAX          INTEGER { routeNotFound(1), noServiceConfigured(2), 
                        databaseError(3) }
    MAX-ACCESS      read-only
    STATUS          current
    DESCRIPTION     
            "The reason why a route look up has failed."
    ::= { sonusSoftswitchClientServicesMIBNotificationsObjects 7 }

sonusPscsGapNumber OBJECT-TYPE
    SYNTAX          DisplayString
    MAX-ACCESS      read-only
    STATUS          current
    DESCRIPTION     
            "Gap number. Valid only in the case of LNP number translation."
    ::= { sonusSoftswitchClientServicesMIBNotificationsObjects 8 }

sonusPscsOperState OBJECT-TYPE
    SYNTAX          INTEGER { active(1), standby(2), congested(3), 
                        down(4), dryingup(5), alternate(6), test(7) }
    MAX-ACCESS      read-only
    STATUS          current
    DESCRIPTION     
            "Operational state of the Softswitch"
    ::= { sonusSoftswitchClientServicesMIBNotificationsObjects 9 }

sonusPscsOutOfServiceReason OBJECT-TYPE
    SYNTAX          INTEGER { configured(1), connectionLoss(2), 
                        noConnection(3), nodeNameChang(4), 
                        incompatibleVersion(5) }
    MAX-ACCESS      read-only
    STATUS          current
    DESCRIPTION     
            "The reason why the softswitch is out of service"
    ::= { sonusSoftswitchClientServicesMIBNotificationsObjects 10 }

sonusPscsInServiceReason OBJECT-TYPE
    SYNTAX          INTEGER { configured(1), successfulReConnect(2), 
                        automatic(3) }
    MAX-ACCESS      read-only
    STATUS          current
    DESCRIPTION     
            "The reason why a softswitch is in service"
    ::= { sonusSoftswitchClientServicesMIBNotificationsObjects 11 }

sonusNodeResourcesMIBNotifications OBJECT IDENTIFIER
    ::= { sonusSbxTraps 4 }

sonusNodeResourcesMIBNotificationsPrefix OBJECT IDENTIFIER
    ::= { sonusNodeResourcesMIBNotifications 0 }

sonusNodeResourcesMIBNotificationsObjects OBJECT IDENTIFIER
    ::= { sonusNodeResourcesMIBNotifications 1 }

sonusCallAdmissionChangeReason OBJECT-TYPE
    SYNTAX          DisplayString (SIZE(1..101))
    MAX-ACCESS      read-only
    STATUS          current
    DESCRIPTION     
            "The reason why the call admission control state has changes."
    ::= { sonusNodeResourcesMIBNotificationsObjects 1 }

sonusFeatureName OBJECT-TYPE
    SYNTAX          DisplayString (SIZE(1..31))
    MAX-ACCESS      read-only
    STATUS          current
    DESCRIPTION     
            "Name of the feature in the context."
    ::= { sonusNodeResourcesMIBNotificationsObjects 2 }

sonusFeatureState OBJECT-TYPE
    SYNTAX          SonusAdminState
    MAX-ACCESS      read-only
    STATUS          current
    DESCRIPTION     
            "State of the feature in context"
    ::= { sonusNodeResourcesMIBNotificationsObjects 3 }

sonusCallTraceCalledNumber OBJECT-TYPE
    SYNTAX          DisplayString (SIZE(0..30))
    MAX-ACCESS      read-write
    STATUS          current
    DESCRIPTION     
            "The called number being traced."
    ::= { sonusNodeResourcesMIBNotificationsObjects 4 }

sonusActiveCallOrigCalledNum OBJECT-TYPE
    SYNTAX          DisplayString (SIZE(0..30))
    MAX-ACCESS      read-only
    STATUS          current
    DESCRIPTION     
            "If an address translation has been performed on the called party number, 
             this entry contains the original, untranslated number."
    ::= { sonusNodeResourcesMIBNotificationsObjects 5 }

sonusCallTraceCallingNumber OBJECT-TYPE
    SYNTAX          DisplayString (SIZE(0..30))
    MAX-ACCESS      read-only
    STATUS          current
    DESCRIPTION     
            "The calling number being traced."
    ::= { sonusNodeResourcesMIBNotificationsObjects 6 }

sonusActiveCallIngressPstnTrunk OBJECT-TYPE
    SYNTAX          DisplayString (SIZE(0..23))
    MAX-ACCESS      read-only
    STATUS          current
    DESCRIPTION     
            "For calls originating from the PSTN (circuit) side, specifies the trunk
             group name to which the Ingress Pstn Channel belongs."
    ::= { sonusNodeResourcesMIBNotificationsObjects 7 }

sonusNodeResourceIsupCircuit OBJECT-TYPE
    SYNTAX          Integer32 (0..16383)
    MAX-ACCESS      read-only
    STATUS          current
    DESCRIPTION     
            "Base circuit identity code (CIC) for the circuit."
    ::= { sonusNodeResourcesMIBNotificationsObjects 8 }

sonusActiveCallCallingNum OBJECT-TYPE
    SYNTAX          DisplayString (SIZE(0..30))
    MAX-ACCESS      read-only
    STATUS          current
    DESCRIPTION     
            "The E.164 number representing the Calling Party's telephone number."
    ::= { sonusNodeResourcesMIBNotificationsObjects 9 }

sonusActiveCallCalledNum OBJECT-TYPE
    SYNTAX          DisplayString (SIZE(0..30))
    MAX-ACCESS      read-only
    STATUS          current
    DESCRIPTION     
            "The E.164 number representing the Called Party's telephone number."
    ::= { sonusNodeResourcesMIBNotificationsObjects 10 }

sonusNumCallFailureNoDspExceedThreshold OBJECT-TYPE
    SYNTAX          Unsigned32
    MAX-ACCESS      read-only
    STATUS          current
    DESCRIPTION     
            "The number of times call failure due to lack of DSP resource exceeded threshold since last trap notification."
    ::= { sonusNodeResourcesMIBNotificationsObjects 11 }

sonusNumDspAvailabilityG729CrossThreshold OBJECT-TYPE
    SYNTAX          Unsigned32
    MAX-ACCESS      read-only
    STATUS          current
    DESCRIPTION     
            "The number of times the availability of G729 DSP resource crossed threshold since last trap notification."
    ::= { sonusNodeResourcesMIBNotificationsObjects 12 }

sonusNumDspAvailabilityG726CrossThreshold OBJECT-TYPE
    SYNTAX          Unsigned32
    MAX-ACCESS      read-only
    STATUS          current
    DESCRIPTION     
            "The number of times the availability of G726 DSP resource crossed threshold since last trap notification."
    ::= { sonusNodeResourcesMIBNotificationsObjects 13 }

sonusNumDspAvailabilityG711PacketCrossThreshold OBJECT-TYPE
    SYNTAX          Unsigned32
    MAX-ACCESS      read-only
    STATUS          current
    DESCRIPTION     
            "The number of times the availability of G711 Packet DSP resource crossed threshold since last trap notification."
    ::= { sonusNodeResourcesMIBNotificationsObjects 14 }

sonusNrmaCallGcid OBJECT-TYPE
    SYNTAX          Unsigned32
    MAX-ACCESS      read-only
    STATUS          current
    DESCRIPTION     
            "The GCID of the call for which trap notification is generated."
    ::= { sonusNodeResourcesMIBNotificationsObjects 15 }

sonusJSrcServerName OBJECT-TYPE
    SYNTAX          DisplayString (SIZE(1..255))
    MAX-ACCESS      read-only
    STATUS          current
    DESCRIPTION     
            "The JSRC Server name for which the trap notification is generated."
    ::= { sonusNodeResourcesMIBNotificationsObjects 16 }

sonusOverloadLevel OBJECT-TYPE
    SYNTAX          INTEGER { noOverload(0), levelOne(1), levelTwo(2), 
                        levelThree(3) }
    MAX-ACCESS      read-only
    STATUS          current
    DESCRIPTION     
            "The overload level."
    ::= { sonusNodeResourcesMIBNotificationsObjects 17 }

sonusCallTraceDisableReason OBJECT-TYPE
    SYNTAX          DisplayString (SIZE(0..100))
    MAX-ACCESS      read-write
    STATUS          current
    DESCRIPTION     
            "The reason for callTrace to be disabled."
    ::= { sonusNodeResourcesMIBNotificationsObjects 18 }

sonusCallCount OBJECT-TYPE
    SYNTAX          Unsigned32
    MAX-ACCESS      read-only
    STATUS          current
    DESCRIPTION     
            "The number of currently active calls on the system."
    ::= { sonusNodeResourcesMIBNotificationsObjects 19 }

sonusRegCount OBJECT-TYPE
    SYNTAX          Unsigned32
    MAX-ACCESS      read-only
    STATUS          current
    DESCRIPTION     
            "The number of currently active registrations on the system."
    ::= { sonusNodeResourcesMIBNotificationsObjects 20 }

sonusRelayCount OBJECT-TYPE
    SYNTAX          Unsigned32
    MAX-ACCESS      read-only
    STATUS          current
    DESCRIPTION     
            "The number of currently active relay control blocks on the system."
    ::= { sonusNodeResourcesMIBNotificationsObjects 21 }

sonusNrmaToneType OBJECT-TYPE
    SYNTAX          Unsigned32
    MAX-ACCESS      read-only
    STATUS          current
    DESCRIPTION     
            "The toneType for announcementBasedTone play failed."
    ::= { sonusNodeResourcesMIBNotificationsObjects 22 }

sonusNrmaCodecType OBJECT-TYPE
    SYNTAX          Unsigned32
    MAX-ACCESS      read-only
    STATUS          current
    DESCRIPTION     
            "The codecType for announcementBasedTone play failed."
    ::= { sonusNodeResourcesMIBNotificationsObjects 23 }

sonusNrmaCodecAttr OBJECT-TYPE
    SYNTAX          Unsigned32
    MAX-ACCESS      read-only
    STATUS          current
    DESCRIPTION     
            "The codec attrib for announcementBasedTone play failed."
    ::= { sonusNodeResourcesMIBNotificationsObjects 24 }

sonusScmInstanceId OBJECT-TYPE
    SYNTAX          Unsigned32
    MAX-ACCESS      read-only
    STATUS          current
    DESCRIPTION     
            "The SCM instance ID that performed decryption"
    ::= { sonusNodeResourcesMIBNotificationsObjects 25 }

sonusDecryptModuleId OBJECT-TYPE
    SYNTAX          Unsigned32
    MAX-ACCESS      read-only
    STATUS          current
    DESCRIPTION     
            "The identity of an module that performed decryption"
    ::= { sonusNodeResourcesMIBNotificationsObjects 26 }

sonusMrfpRealmId OBJECT-TYPE
    SYNTAX          DisplayString
    MAX-ACCESS      read-only
    STATUS          current
    DESCRIPTION     
            "The identity of an realm"
    ::= { sonusNodeResourcesMIBNotificationsObjects 27 }

sonusTrunkGroupResourcesMIBNotifications OBJECT IDENTIFIER
    ::= { sonusSbxTraps 5 }

sonusTrunkGroupResourcesMIBNotificationsPrefix OBJECT IDENTIFIER
    ::= { sonusTrunkGroupResourcesMIBNotifications 0 }

sonusTrunkGroupResourcesMIBNotificationsObjects OBJECT IDENTIFIER
    ::= { sonusTrunkGroupResourcesMIBNotifications 1 }

sonusTrunkOutOfServiceReason OBJECT-TYPE
    SYNTAX          INTEGER { configured(1), allResourcesBlocked(2) }
    MAX-ACCESS      read-only
    STATUS          current
    DESCRIPTION     
            "The reason why the Trunk Group is out of service."
    ::= { sonusTrunkGroupResourcesMIBNotificationsObjects 1 }

sonusTrunkGroupTCObject OBJECT-TYPE
    SYNTAX          INTEGER { sonusTgTCInboundReserved(1), 
                        sonusTgTCCirResvState(2), 
                        sonusTgTCPriorityCallReserve(3), 
                        sonusTgTCIncomingCallReserve(4), 
                        sonusTgTCOutgoingCallReserve(5), 
                        sonusTgTCSilcState(6), 
                        sonusTgTCSilcMC1Percent(7), 
                        sonusTgTCSilcMC2Percent(8) }
    MAX-ACCESS      read-only
    STATUS          current
    DESCRIPTION     
            "This object is a bit mask that indicates what traffic
             control object in the trunk group table has changed."
    ::= { sonusTrunkGroupResourcesMIBNotificationsObjects 2 }

sonusTrunkGroupManCon OBJECT-TYPE
    SYNTAX          BITS { skip(0), cant(1), canf(2), irr(3), sirr(4), 
                        orr(5), sorr(6) }
    MAX-ACCESS      read-only
    STATUS          current
    DESCRIPTION     
            "This object is a bit mask that indicates what 
             manual trunk group controls were active in the
             last 30 seconds."
    ::= { sonusTrunkGroupResourcesMIBNotificationsObjects 3 }

sonusTrunkGroupAutoCon OBJECT-TYPE
    SYNTAX          BITS { acc(0), str(1), silc(2), dre(3), pod(4), 
                        gwAcc(5), callPolicing(6), regPolicing(7) }
    MAX-ACCESS      read-only
    STATUS          current
    DESCRIPTION     
            "This object is a bit mask that indicates what 
             automatic trunk group controls were active in 
             the last 30 seconds."
    ::= { sonusTrunkGroupResourcesMIBNotificationsObjects 4 }

sonusHpcLimitCallAttemptsDenied OBJECT-TYPE
    SYNTAX          Unsigned32
    MAX-ACCESS      read-only
    STATUS          current
    DESCRIPTION     
            "The number of HPC call attempts that have been denied because of 
             exceeding the HPC limit associated with the trap since the last 
             instance of the trap"
    ::= { sonusTrunkGroupResourcesMIBNotificationsObjects 5 }

sonusTgName OBJECT-TYPE
    SYNTAX          SonusName
    MAX-ACCESS      read-only
    STATUS          current
    DESCRIPTION     
            "The name of the trunk group.  The trunk group name must be present when the
             instance is created.  A trunk group can be renamed by setting sonusTgName
             in an existing instance.  When sonusTgName is set in an existing instance,
             the prior value of this object is placed in sonusTgAlternateName.  The new
             name will placed in sonusIsupsgServiceGroupTG from sonusIsupsg.mib, 
             sonusIsdnsgServiceGroupTrunkGroup from sonusIsdnsg.mib, and 
             sonusCassgServiceGroupTG from sonusCassg.mib.  Both the name in sonusTgName and 
             sonusTgAlternateName will be accepted for routing requests.  No other
             trunk group table instance can use the name in sonusTgName or 
             sonusTgAlternateName."
    ::= { sonusTrunkGroupResourcesMIBNotificationsObjects 6 }

sonusTgAdditionalData OBJECT-TYPE
    SYNTAX          DisplayString (SIZE(1..63))
    MAX-ACCESS      read-write
    STATUS          deprecated
    DESCRIPTION     
            "Any additional data related to the trunk group. The data can be used to
             configure any meta data related to trunk group e.g. customer name.
             The Trunk Group related traps should carry this data so as to make the
                  traps more descriptive of the Trunk Group."
    ::= { sonusTrunkGroupResourcesMIBNotificationsObjects 7 }

sonusCurrentKpiValue OBJECT-TYPE
    SYNTAX          Unsigned32
    MAX-ACCESS      read-only
    STATUS          current
    DESCRIPTION     
            "The current KPI value for the trunk group"
    ::= { sonusTrunkGroupResourcesMIBNotificationsObjects 8 }

sonusKpi OBJECT-TYPE
    SYNTAX          DisplayString (SIZE(1..63))
    MAX-ACCESS      read-write
    STATUS          current
    DESCRIPTION     
            "The QOS KPI whose status is being reported."
    ::= { sonusTrunkGroupResourcesMIBNotificationsObjects 9 }

sonusAddressContextName OBJECT-TYPE
    SYNTAX          DisplayString (SIZE(1..63))
    MAX-ACCESS      read-write
    STATUS          current
    DESCRIPTION     
            "The name of the address contest to which the TG belongs."
    ::= { sonusTrunkGroupResourcesMIBNotificationsObjects 10 }

sonusZoneName OBJECT-TYPE
    SYNTAX          DisplayString (SIZE(1..63))
    MAX-ACCESS      read-write
    STATUS          current
    DESCRIPTION     
            "The name of the Zone to which the TG belongs."
    ::= { sonusTrunkGroupResourcesMIBNotificationsObjects 11 }

sonusCacLimitType OBJECT-TYPE
    SYNTAX          DisplayString (SIZE(1..63))
    MAX-ACCESS      read-write
    STATUS          current
    DESCRIPTION     
            "Type of the cac limit which is exhausted."
    ::= { sonusTrunkGroupResourcesMIBNotificationsObjects 12 }

sonusTrunkGroupManCon3 OBJECT-TYPE
    SYNTAX          DisplayString (SIZE(1..63))
    MAX-ACCESS      read-only
    STATUS          current
    DESCRIPTION     
            "This string is a concatenation of  
             manual trunk group controls that were active in the
             last 30 seconds."
    ::= { sonusTrunkGroupResourcesMIBNotificationsObjects 13 }

sonusTrunkGroupAutoCon3 OBJECT-TYPE
    SYNTAX          DisplayString (SIZE(1..63))
    MAX-ACCESS      read-only
    STATUS          current
    DESCRIPTION     
            "This string is a concatenation of 
             automatic trunk group controls that were active in 
             the last 30 seconds."
    ::= { sonusTrunkGroupResourcesMIBNotificationsObjects 14 }

sonusAccountingMIBNotifications OBJECT IDENTIFIER
    ::= { sonusSbxTraps 6 }

sonusAccountingMIBNotificationsPrefix OBJECT IDENTIFIER
    ::= { sonusAccountingMIBNotifications 0 }

sonusAccountingMIBNotificationsObjects OBJECT IDENTIFIER
    ::= { sonusAccountingMIBNotifications 1 }

sonusAcctOutOfServiceReason OBJECT-TYPE
    SYNTAX          INTEGER { configChange(1), eventLoggingError(2) }
    MAX-ACCESS      read-only
    STATUS          current
    DESCRIPTION     
            "The Reason for Call Accounting for the Node being
             Out-of-Service."
    ::= { sonusAccountingMIBNotificationsObjects 1 }

sonusAcctGcid OBJECT-TYPE
    SYNTAX          Integer32
    MAX-ACCESS      read-only
    STATUS          current
    DESCRIPTION     
            "GCID associated with the call which generated the trap.
             Corresponds to INTERMEDIATE accounting record, field 65."
    ::= { sonusAccountingMIBNotificationsObjects 2 }

sonusAcctOrigTrunkgroupType OBJECT-TYPE
    SYNTAX          Integer32
    MAX-ACCESS      read-only
    STATUS          current
    DESCRIPTION     
            "This value represents the originating trunk type as specified
             by customer. This field is associated with the corresponding
             field of trunk group screen on PSX.
             Corresponds to INTERMEDIATE accounting record, field 135."
    ::= { sonusAccountingMIBNotificationsObjects 3 }

sonusAcctIngressCep OBJECT-TYPE
    SYNTAX          DisplayString (SIZE(0..128))
    MAX-ACCESS      read-only
    STATUS          current
    DESCRIPTION     
            "Ingress Circuit End Point.
             If ingress is PSTN, then CEP string contains the following:
             <Shelf>:<Slot>:<Port>:<Ds0>:<Cic>:<LPC>:<RPC>
             If ingress is IP, then CEP string containst the following:
             <Local IP Address>:<Port>/<Remote IP Address>:<Port>
             Corresponds to INTERMEDIATE accounting record, fields 32 & 33."
    ::= { sonusAccountingMIBNotificationsObjects 4 }

sonusAcctTermTrunkgroupType OBJECT-TYPE
    SYNTAX          Integer32
    MAX-ACCESS      read-only
    STATUS          current
    DESCRIPTION     
            "This value represents the terminating trunk type as specified
             by customer. This field is associated with the corresponding
             field of trunk group screen on PSX.
             Corresponds to INTERMEDIATE accounting record, field 136."
    ::= { sonusAccountingMIBNotificationsObjects 5 }

sonusAcctEgressCep OBJECT-TYPE
    SYNTAX          DisplayString (SIZE(0..128))
    MAX-ACCESS      read-only
    STATUS          current
    DESCRIPTION     
            "Egress Circuit End Point.
             If egress is PSTN, then CEP string contains the following:
             <Shelf>:<Slot>:<Port>:<Ds0>:<Cic>:<LPC>:<RPC>
             If egress is IP, then CEP string containst the following:
             <Local IP Address>:<Port>/<Remote IP Address>:<Port>
              Corresponds to INTERMEDIATE accounting record, fields 34 & 35."
    ::= { sonusAccountingMIBNotificationsObjects 6 }

sonusAcctCallingPartyNumber OBJECT-TYPE
    SYNTAX          DisplayString (SIZE(0..31))
    MAX-ACCESS      read-only
    STATUS          current
    DESCRIPTION     
            "Calling Party Number associated with the call which generated the trap.
             Corresponds to INTERMEDIATE accounting record, field 17."
    ::= { sonusAccountingMIBNotificationsObjects 7 }

sonusAcctCalledPartyNumber OBJECT-TYPE
    SYNTAX          DisplayString (SIZE(0..31))
    MAX-ACCESS      read-only
    STATUS          current
    DESCRIPTION     
            "Called Party Number associated with the call which generated the trap.
             Corresponds to INTERMEDIATE accounting record, field 18."
    ::= { sonusAccountingMIBNotificationsObjects 8 }

sonusSelCdrReqRspTimeout OBJECT-TYPE
    SYNTAX          Unsigned32
    MAX-ACCESS      read-only
    STATUS          current
    DESCRIPTION     
            ""
    ::= { sonusAccountingMIBNotificationsObjects 9 }

sonusAcctGenerationMode OBJECT-TYPE
    SYNTAX          INTEGER { origination(1), destination(2), 
                        allcalls(3), none(4) }
    MAX-ACCESS      read-only
    STATUS          current
    DESCRIPTION     
            "This configures the accounting generation mode for the node"
    ::= { sonusAccountingMIBNotificationsObjects 10 }

sonusAcctLogDestination OBJECT-TYPE
    SYNTAX          INTEGER { nfs(1), streaming(2) }
    MAX-ACCESS      read-only
    STATUS          current
    DESCRIPTION     
            "The accounting log destination "
    ::= { sonusAccountingMIBNotificationsObjects 11 }

sonusAcctIntAcctState OBJECT-TYPE
    SYNTAX          SonusAdminState
    MAX-ACCESS      read-only
    STATUS          current
    DESCRIPTION     
            "This administrative Intermediate Accounting state"
    ::= { sonusAccountingMIBNotificationsObjects 12 }

sonusAcctIntAcctInterval OBJECT-TYPE
    SYNTAX          Integer32 (5..86400)
    MAX-ACCESS      read-only
    STATUS          current
    DESCRIPTION     
            "The Intermediate Accounting Interval in seconds"
    ::= { sonusAccountingMIBNotificationsObjects 13 }

sonusSelCdrSequenceNumber OBJECT-TYPE
    SYNTAX          Counter32
    MAX-ACCESS      read-only
    STATUS          current
    DESCRIPTION     
            "The sequence number of the GSX selectable CDR configuration of GSX-  
             DSI CDR streaming."
    ::= { sonusAccountingMIBNotificationsObjects 14 }

sonusSelCdrUpdateStatus OBJECT-TYPE
    SYNTAX          INTEGER { success(0), subsetStart(1), subsetStop(2), 
                        subsetStartStop(3), subsetAttempt(4), 
                        subsetStartAttempt(5), subsetStopAttempt(6), 
                        subsetStartStopAttempt(7), subsetIntermediate(8), 
                        subsetStartIntermediate(9), 
                        subsetStopIntermediate(10), 
                        subsetStartStopInter(11), subsetAttemptInter(12), 
                        subsetStartAttemptInter(13), 
                        subsetStopAttemptInter(14), 
                        subsetStartStopAtmpIntr(15) }
    MAX-ACCESS      read-only
    STATUS          current
    DESCRIPTION     
            "This field contains the update status of the selectable CDR configuration.
             
             Value 0 indicates GSX accepts all selectable CDR configurations 
             provisioned by DSI.
             
             Value 1 indicates GSX partially accepted the selectable CDR configuration 
             of START record type, and fully accepted all other configuration updates 
             on STOP, ATTEMPT and INTERMEDIATE record types.
             
             Value 2 indicates GSX partially accepted the selectable CDR configuration 
             on STOP record type, and fully accepted all other configuration updates 
             on START, ATTEMPT and INTERMEDIATE record types.
             
             Value 3 indicates GSX partially accepted the selectable CDR configuration 
             on START and STOP record types, and fully accepted all other configuration
             update on ATTEMPT and INTERMEDIATE record types.
             .. etc. "
    ::= { sonusAccountingMIBNotificationsObjects 15 }

sonusAcctIntAcctMode OBJECT-TYPE
    SYNTAX          INTEGER { interval(1), telcordia(2) }
    MAX-ACCESS      read-only
    STATUS          current
    DESCRIPTION     
            "This configures the intermediate record generation mode for
             the node.
             
             In INTERVAL(1) mode, intermediate records are generated
             a periodic intervals following call establishment.  This
             interval is defined by sonusAcctIntAcctInterval.
             
             In TELCORDIA(2) mode, intermediate records are geneated once
             per day for calls whose duration exceeds 24 hours.  The 
             scheduled generated time is defined by
             sonusAcctTelcoridaGenTime."
    ::= { sonusAccountingMIBNotificationsObjects 16 }

sonusAcctIntLongDurGenTime OBJECT-TYPE
    SYNTAX          SonusGMTTime
    MAX-ACCESS      read-only
    STATUS          current
    DESCRIPTION     
            "Octet string that identifies the GMT time to generate Telcordia
             Long Duration accounting records.  At the scheduled time an
             intermediate accounting record will be generated for all calls
             whose duration exceeds 24 hours.  Duration is measured from
             Service Established time to the current time.
             
                octet  contents      range
                -----  --------      -----
                  1    hour          0..23
                  2    minute        0..59
                  3    seconds       0..60
                  4    deci-seconds  0..9
             
             For example, 23:59:59.9 GMT is represented as 0x173B3B09.
             
             Note: this object is only applicable when sonusAcctIntAcctMode
                   is set to telcordia(2)."
    ::= { sonusAccountingMIBNotificationsObjects 17 }

sonusCommonCallProcessMIBNotifications OBJECT IDENTIFIER
    ::= { sonusSbxTraps 7 }

sonusCommonCallProcessMIBNotificationsPrefix OBJECT IDENTIFIER
    ::= { sonusCommonCallProcessMIBNotifications 0 }

sonusCommonCallProcessMIBNotificationsObjects OBJECT IDENTIFIER
    ::= { sonusCommonCallProcessMIBNotifications 1 }

sonusIngressTgName OBJECT-TYPE
    SYNTAX          DisplayString (SIZE(0..23))
    MAX-ACCESS      read-only
    STATUS          current
    DESCRIPTION     
            "Name of the ingress trunk group."
    ::= { sonusCommonCallProcessMIBNotificationsObjects 1 }

sonusIngressCep OBJECT-TYPE
    SYNTAX          DisplayString (SIZE(0..128))
    MAX-ACCESS      read-only
    STATUS          current
    DESCRIPTION     
            "Ingress circuit end point information, this could be PSTN or IP formatted."
    ::= { sonusCommonCallProcessMIBNotificationsObjects 2 }

sonusEgressTgName OBJECT-TYPE
    SYNTAX          DisplayString (SIZE(0..23))
    MAX-ACCESS      read-only
    STATUS          current
    DESCRIPTION     
            "Name of the egress trunk group."
    ::= { sonusCommonCallProcessMIBNotificationsObjects 3 }

sonusEgressCep OBJECT-TYPE
    SYNTAX          DisplayString (SIZE(0..128))
    MAX-ACCESS      read-only
    STATUS          current
    DESCRIPTION     
            "Egress circuit end point information, this could be PSTN or IP formatted."
    ::= { sonusCommonCallProcessMIBNotificationsObjects 4 }

sonusCalledNumber OBJECT-TYPE
    SYNTAX          DisplayString (SIZE(0..30))
    MAX-ACCESS      read-only
    STATUS          current
    DESCRIPTION     
            "Called Party Number."
    ::= { sonusCommonCallProcessMIBNotificationsObjects 5 }

sonusCallingNumber OBJECT-TYPE
    SYNTAX          DisplayString (SIZE(0..30))
    MAX-ACCESS      read-only
    STATUS          current
    DESCRIPTION     
            "Calling Party Number."
    ::= { sonusCommonCallProcessMIBNotificationsObjects 6 }

sonusLdcStatus OBJECT-TYPE
    SYNTAX          DisplayString (SIZE(0..13))
    MAX-ACCESS      read-only
    STATUS          current
    DESCRIPTION     
            "Is the LDC call to be disconnected or remain active."
    ::= { sonusCommonCallProcessMIBNotificationsObjects 7 }

sonusCep OBJECT-TYPE
    SYNTAX          DisplayString (SIZE(0..96))
    MAX-ACCESS      read-only
    STATUS          current
    DESCRIPTION     
            "Circuit end point information, this could be PSTN or IP formatted."
    ::= { sonusCommonCallProcessMIBNotificationsObjects 8 }

sonusStaticCallGcid OBJECT-TYPE
    SYNTAX          Integer32
    MAX-ACCESS      read-write
    STATUS          current
    DESCRIPTION     
            "The call identifier for a call to be deleted"
    ::= { sonusCommonCallProcessMIBNotificationsObjects 9 }

sonusCommonMIBNotifications OBJECT IDENTIFIER
    ::= { sonusSbxTraps 8 }

sonusCommonMIBNotificationsPrefix OBJECT IDENTIFIER
    ::= { sonusCommonMIBNotifications 0 }

sonusCommonMIBNotificationsObjects OBJECT IDENTIFIER
    ::= { sonusCommonMIBNotifications 1 }

sonusNetMgmtClientName OBJECT-TYPE
    SYNTAX          SonusName
    MAX-ACCESS      read-only
    STATUS          current
    DESCRIPTION     
            "The name of this administrative management client."
    ::= { sonusCommonMIBNotificationsObjects 1 }

sonusNetMgmtInformReqDiscards OBJECT-TYPE
    SYNTAX          Integer32 (0..100)
    MAX-ACCESS      read-only
    STATUS          current
    DESCRIPTION     
            "The number of InformRequest PDUs that were discarded
             for a Management Client."
    ::= { sonusCommonMIBNotificationsObjects 2 }

sonusIpmMIBNotifications OBJECT IDENTIFIER
    ::= { sonusSbxTraps 9 }

sonusIpmMIBNotificationsPrefix OBJECT IDENTIFIER
    ::= { sonusIpmMIBNotifications 0 }

sonusIpmMIBNotificationsObjects OBJECT IDENTIFIER
    ::= { sonusIpmMIBNotifications 1 }

sonusPolicerTypeStr OBJECT-TYPE
    SYNTAX          DisplayString (SIZE(1..32))
    MAX-ACCESS      read-only
    STATUS          current
    DESCRIPTION     
            "The policer type whose alarm state has changed."
    ::= { sonusIpmMIBNotificationsObjects 1 }

sonusPolicerLevelStr OBJECT-TYPE
    SYNTAX          DisplayString (SIZE(1..12))
    MAX-ACCESS      read-only
    STATUS          current
    DESCRIPTION     
            "The previous policer alarm level reported when the alarm 
             state has changed."
    ::= { sonusIpmMIBNotificationsObjects 2 }

sonusDBLAddressContextName OBJECT-TYPE
    SYNTAX          DisplayString (SIZE(1..32))
    MAX-ACCESS      read-only
    STATUS          current
    DESCRIPTION     
            "AddressContext name."
    ::= { sonusIpmMIBNotificationsObjects 3 }

sonusDBLEndPointInfo OBJECT-TYPE
    SYNTAX          DisplayString (SIZE(1..63))
    MAX-ACCESS      read-only
    STATUS          current
    DESCRIPTION     
            "Endpoint information"
    ::= { sonusIpmMIBNotificationsObjects 4 }

sonusDBLAction OBJECT-TYPE
    SYNTAX          DisplayString (SIZE(1..32))
    MAX-ACCESS      read-only
    STATUS          current
    DESCRIPTION     
            "Action type"
    ::= { sonusIpmMIBNotificationsObjects 5 }

sonusDBLDuration OBJECT-TYPE
    SYNTAX          Unsigned32
    MAX-ACCESS      read-only
    STATUS          current
    DESCRIPTION     
            "Endpoint action duration"
    ::= { sonusIpmMIBNotificationsObjects 6 }

sonusDBLCriteria OBJECT-TYPE
    SYNTAX          DisplayString (SIZE(1..255))
    MAX-ACCESS      read-only
    STATUS          current
    DESCRIPTION     
            "Criteria information"
    ::= { sonusIpmMIBNotificationsObjects 7 }

sonusDBLProfileRuleInfo OBJECT-TYPE
    SYNTAX          DisplayString (SIZE(1..63))
    MAX-ACCESS      read-only
    STATUS          current
    DESCRIPTION     
            "Profile and rule information"
    ::= { sonusIpmMIBNotificationsObjects 8 }

sonusDBLEventName OBJECT-TYPE
    SYNTAX          DisplayString (SIZE(1..63))
    MAX-ACCESS      read-only
    STATUS          current
    DESCRIPTION     
            "DBL Event Name"
    ::= { sonusIpmMIBNotificationsObjects 9 }

sonusSbxNotifications OBJECT IDENTIFIER
    ::= { sonusSbxTraps 10 }

sonusSbxNotificationPrefix OBJECT IDENTIFIER
    ::= { sonusSbxNotifications 2 }

sonusSbxNotificationObjects OBJECT IDENTIFIER
    ::= { sonusSbxNotifications 3 }

sonusNrsMIBNotifications OBJECT IDENTIFIER
    ::= { sonusSbxTraps 11 }

sonusNrsMIBNotificationsPrefix OBJECT IDENTIFIER
    ::= { sonusNrsMIBNotifications 0 }

sonusNrsMIBNotificationsObjects OBJECT IDENTIFIER
    ::= { sonusNrsMIBNotifications 1 }

sonusNrsAddressContextName OBJECT-TYPE
    SYNTAX          DisplayString (SIZE(1..24))
    MAX-ACCESS      read-only
    STATUS          current
    DESCRIPTION     
            "The name of the address context."
    ::= { sonusNrsMIBNotificationsObjects 1 }

sonusNrsIpInterfaceGroupName OBJECT-TYPE
    SYNTAX          DisplayString (SIZE(1..24))
    MAX-ACCESS      read-only
    STATUS          current
    DESCRIPTION     
            "The name of the IP interface group."
    ::= { sonusNrsMIBNotificationsObjects 2 }

sonusNrsIpInterfaceName OBJECT-TYPE
    SYNTAX          DisplayString (SIZE(1..24))
    MAX-ACCESS      read-only
    STATUS          current
    DESCRIPTION     
            "The name of the IP interface."
    ::= { sonusNrsMIBNotificationsObjects 3 }

sonusNrsPortName OBJECT-TYPE
    SYNTAX          DisplayString (SIZE(1..24))
    MAX-ACCESS      read-only
    STATUS          current
    DESCRIPTION     
            "The name of the port."
    ::= { sonusNrsMIBNotificationsObjects 4 }

sonusNrsCeName OBJECT-TYPE
    SYNTAX          DisplayString (SIZE(1..255))
    MAX-ACCESS      read-only
    STATUS          current
    DESCRIPTION     
            "The name of the compute element."
    ::= { sonusNrsMIBNotificationsObjects 5 }

sonusNrsIpAddress OBJECT-TYPE
    SYNTAX          IpAddress
    MAX-ACCESS      read-only
    STATUS          current
    DESCRIPTION     
            "
             IP Address. 
             "
    ::= { sonusNrsMIBNotificationsObjects 6 }

sonusNrsIpAddressV6 OBJECT-TYPE
    SYNTAX          Ipv6Address
    MAX-ACCESS      read-only
    STATUS          current
    DESCRIPTION     
            "IP Address."
    ::= { sonusNrsMIBNotificationsObjects 7 }

sonusNrsInvalidSfpReason OBJECT-TYPE
    SYNTAX          DisplayString
    MAX-ACCESS      read-only
    STATUS          current
    DESCRIPTION     
            "
             Reason SFP is invalid. 
             "
    ::= { sonusNrsMIBNotificationsObjects 8 }

sonusNifPort OBJECT-TYPE
    SYNTAX          Integer32 (1..65535)
    MAX-ACCESS      read-only
    STATUS          current
    DESCRIPTION     
            "
             The port ID. 
             "
    ::= { sonusNrsMIBNotificationsObjects 9 }

sonusNifIndex OBJECT-TYPE
    SYNTAX          Integer32 (1..65535)
    MAX-ACCESS      read-only
    STATUS          current
    DESCRIPTION     
            "
             The ifIndex of the interface. 
             "
    ::= { sonusNrsMIBNotificationsObjects 10 }

sonusBgfMIBNotifications OBJECT IDENTIFIER
    ::= { sonusSbxTraps 12 }

sonusBgfMIBNotificationsPrefix OBJECT IDENTIFIER
    ::= { sonusBgfMIBNotifications 0 }

sonusBgfMIBNotificationsObjects OBJECT IDENTIFIER
    ::= { sonusBgfMIBNotifications 1 }

sonusH248SigRemoteIpAddr OBJECT-TYPE
    SYNTAX          DisplayString
    MAX-ACCESS      read-only
    STATUS          current
    DESCRIPTION     
            "IP address of the SPDF."
    ::= { sonusBgfMIBNotificationsObjects 1 }

sonusH248SigLocalIpAddr OBJECT-TYPE
    SYNTAX          DisplayString
    MAX-ACCESS      read-only
    STATUS          current
    DESCRIPTION     
            "IP address of the VBGF."
    ::= { sonusBgfMIBNotificationsObjects 2 }

sonusH248SigScMethod OBJECT-TYPE
    SYNTAX          DisplayString
    MAX-ACCESS      read-only
    STATUS          current
    DESCRIPTION     
            "Service Change method."
    ::= { sonusBgfMIBNotificationsObjects 3 }

sonusH248SigMid OBJECT-TYPE
    SYNTAX          DisplayString
    MAX-ACCESS      read-only
    STATUS          current
    DESCRIPTION     
            "MID of SPDF."
    ::= { sonusBgfMIBNotificationsObjects 4 }

sonusH248SigStatus OBJECT-TYPE
    SYNTAX          DisplayString
    MAX-ACCESS      read-only
    STATUS          current
    DESCRIPTION     
            "Service change disconnected transmission status."
    ::= { sonusBgfMIBNotificationsObjects 5 }

sonusH248SpdfName OBJECT-TYPE
    SYNTAX          DisplayString
    MAX-ACCESS      read-only
    STATUS          current
    DESCRIPTION     
            "SPDF Name."
    ::= { sonusBgfMIBNotificationsObjects 6 }

sonusH248FeatureName OBJECT-TYPE
    SYNTAX          DisplayString
    MAX-ACCESS      read-only
    STATUS          deprecated
    DESCRIPTION     
            " Feature Name."
    ::= { sonusBgfMIBNotificationsObjects 7 }

sonusH248Version OBJECT-TYPE
    SYNTAX          Integer32 (1..3)
    MAX-ACCESS      read-only
    STATUS          deprecated
    DESCRIPTION     
            " H248 Version Number"
    ::= { sonusBgfMIBNotificationsObjects 8 }

sonusH248SigPortIpAddress OBJECT-TYPE
    SYNTAX          IpAddress
    MAX-ACCESS      read-only
    STATUS          current
    DESCRIPTION     
            "
             IP Address of the H248 Signalling Port - mandatory parameter. 
             "
    ::= { sonusBgfMIBNotificationsObjects 9 }

sonusH248SigPortNum OBJECT-TYPE
    SYNTAX          Integer32 (1..65535)
    MAX-ACCESS      read-only
    STATUS          current
    DESCRIPTION     
            "
             UDP/TCP port number of H248 Signalling Port (default is 2944).
             "
    ::= { sonusBgfMIBNotificationsObjects 10 }

sonusH248SigProto OBJECT-TYPE
    SYNTAX          DisplayString
    MAX-ACCESS      read-only
    STATUS          current
    DESCRIPTION     
            " The signaling transport protocol."
    ::= { sonusBgfMIBNotificationsObjects 11 }

sonusGatewaySignallingMIBNotifications OBJECT IDENTIFIER
    ::= { sonusSbxTraps 13 }

sonusGatewaySignallingMIBNotificationsPrefix OBJECT IDENTIFIER
    ::= { sonusGatewaySignallingMIBNotifications 0 }

sonusGatewaySignallingMIBNotificationsObjects OBJECT IDENTIFIER
    ::= { sonusGatewaySignallingMIBNotifications 1 }

sonusGwRemoteGwName OBJECT-TYPE
    SYNTAX          DisplayString (SIZE(0..23))
    MAX-ACCESS      read-only
    STATUS          deprecated
    DESCRIPTION     
            "Name of the remote Gateway."
    ::= { sonusGatewaySignallingMIBNotificationsObjects 1 }

sonusGwCloseReasonCode OBJECT-TYPE
    SYNTAX          INTEGER { administratorInitiatedClose(1), 
                        closeRequestReceivedFromRemote(2), 
                        remoteNotResponding(3), internalError(4), 
                        configError(5), recvCallSigReqFromUnknownGw(6), 
                        socketErrNetworkDown(7), 
                        socketErrNetworkUnreachable(8), 
                        socketErrNetworkReset(9), 
                        socketErrSoftwareConnectionAbort(10), 
                        socketErrConnectionResetByPeer(11), 
                        socketErrNoBufferSpaceAvail(12), 
                        socketErrAlreadyConnected(13), 
                        socketErrNotConnected(14), 
                        socketErrCantSendAfterShutdown(15), 
                        socketErrTooManyReferences(16), 
                        socketErrConnectionTimedOut(17), 
                        socketErrUnknown(18), 
                        recvDuplicateLinkOpenReq(19), 
                        socketErrExceptionEvent(20), 
                        linkXmtCongestion(21), 
                        openNackReceivedFromRemote(22), idleTimeout(23) }
    MAX-ACCESS      read-only
    STATUS          current
    DESCRIPTION     
            "Reason for close of Call Signaling Link."
    ::= { sonusGatewaySignallingMIBNotificationsObjects 2 }

sonusGwRemoteGwAddr OBJECT-TYPE
    SYNTAX          IpAddress
    MAX-ACCESS      read-only
    STATUS          current
    DESCRIPTION     
            "Ip Address of the remote Gateway."
    ::= { sonusGatewaySignallingMIBNotificationsObjects 3 }

sonusGwSigTgName OBJECT-TYPE
    SYNTAX          SonusNameReference
    MAX-ACCESS      read-only
    STATUS          current
    DESCRIPTION     
            "Name of the Gateway trunk group."
    ::= { sonusGatewaySignallingMIBNotificationsObjects 4 }

sonusGwRemoteGw6Addr OBJECT-TYPE
    SYNTAX          Ipv6Address
    MAX-ACCESS      read-only
    STATUS          current
    DESCRIPTION     
            "Ipv6 Address of the remote Gateway."
    ::= { sonusGatewaySignallingMIBNotificationsObjects 5 }

sonusOrcaLicenseMIBNotifications OBJECT IDENTIFIER
    ::= { sonusSbxTraps 14 }

sonusOrcaLicenseMIBNotificationsPrefix OBJECT IDENTIFIER
    ::= { sonusOrcaLicenseMIBNotifications 0 }

sonusOrcaLicenseMIBNotificationsObjects OBJECT IDENTIFIER
    ::= { sonusOrcaLicenseMIBNotifications 1 }

sonusSessLicenseLimit OBJECT-TYPE
    SYNTAX          Unsigned32
    MAX-ACCESS      read-only
    STATUS          current
    DESCRIPTION     
            "Licensed session limit"
    ::= { sonusOrcaLicenseMIBNotificationsObjects 1 }

sonusConcurrentCalls OBJECT-TYPE
    SYNTAX          Unsigned32
    MAX-ACCESS      read-only
    STATUS          current
    DESCRIPTION     
            "Concurrent calls"
    ::= { sonusOrcaLicenseMIBNotificationsObjects 2 }

sonusSessionsThreshold OBJECT-TYPE
    SYNTAX          Unsigned32
    MAX-ACCESS      read-only
    STATUS          current
    DESCRIPTION     
            "Sessions threshold"
    ::= { sonusOrcaLicenseMIBNotificationsObjects 3 }

sonusAlarmName OBJECT-TYPE
    SYNTAX          DisplayString
    MAX-ACCESS      read-only
    STATUS          current
    DESCRIPTION     
            "License Name."
    ::= { sonusOrcaLicenseMIBNotificationsObjects 4 }

sonusAlarmReason OBJECT-TYPE
    SYNTAX          DisplayString
    MAX-ACCESS      read-only
    STATUS          current
    DESCRIPTION     
            "call admission is suspended."
    ::= { sonusOrcaLicenseMIBNotificationsObjects 5 }

sonusActiveSessionCount OBJECT-TYPE
    SYNTAX          Unsigned32
    MAX-ACCESS      read-only
    STATUS          current
    DESCRIPTION     
            "Active Sessions count "
    ::= { sonusOrcaLicenseMIBNotificationsObjects 6 }

sonusDatabaseMIBNotifications OBJECT IDENTIFIER
    ::= { sonusSbxTraps 15 }

sonusDatabaseMIBNotificationsPrefix OBJECT IDENTIFIER
    ::= { sonusDatabaseMIBNotifications 0 }

sonusDatabaseMIBNotificationsObjects OBJECT IDENTIFIER
    ::= { sonusDatabaseMIBNotifications 1 }

sonusSbxSystemName OBJECT-TYPE
    SYNTAX          DisplayString
    MAX-ACCESS      read-only
    STATUS          current
    DESCRIPTION     
            "
             Name of the system
             "
    ::= { sonusDatabaseMIBNotificationsObjects 1 }

sonusSbxServerName OBJECT-TYPE
    SYNTAX          DisplayString
    MAX-ACCESS      read-only
    STATUS          current
    DESCRIPTION     
            "
             Name of the server
             "
    ::= { sonusDatabaseMIBNotificationsObjects 2 }

sonusSbxPeerServerName OBJECT-TYPE
    SYNTAX          DisplayString
    MAX-ACCESS      read-only
    STATUS          current
    DESCRIPTION     
            "
             Name of the peer server
             "
    ::= { sonusDatabaseMIBNotificationsObjects 3 }

sonusSbxRedundencyRole OBJECT-TYPE
    SYNTAX          DisplayString
    MAX-ACCESS      read-only
    STATUS          current
    DESCRIPTION     
            "
             Redundency role of the server.
             "
    ::= { sonusDatabaseMIBNotificationsObjects 4 }

sonusResourceMIBNotifications OBJECT IDENTIFIER
    ::= { sonusSbxTraps 16 }

sonusResourceMIBNotificationsPrefix OBJECT IDENTIFIER
    ::= { sonusResourceMIBNotifications 0 }

sonusResourceMIBNotificationsObjects OBJECT IDENTIFIER
    ::= { sonusResourceMIBNotifications 1 }

sonusResource OBJECT-TYPE
    SYNTAX          DisplayString
    MAX-ACCESS      read-only
    STATUS          current
    DESCRIPTION     
            "
             Concurrent calls or bandwidth.
             "
    ::= { sonusResourceMIBNotificationsObjects 1 }

sonusEntityType OBJECT-TYPE
    SYNTAX          DisplayString
    MAX-ACCESS      read-only
    STATUS          current
    DESCRIPTION     
            "
             Zone, TrunkGroup, IPPeer.
             "
    ::= { sonusResourceMIBNotificationsObjects 2 }

sonusEntityName OBJECT-TYPE
    SYNTAX          DisplayString
    MAX-ACCESS      read-only
    STATUS          current
    DESCRIPTION     
            "
             Zone, TrunkGroup, IPPeer name.
             "
    ::= { sonusResourceMIBNotificationsObjects 3 }

sonusSharedCacLimitPoolProfileId OBJECT-TYPE
    SYNTAX          DisplayString
    MAX-ACCESS      read-only
    STATUS          current
    DESCRIPTION     
            "
             Concurrent calls or bandwidthShared Cac Limit Pool Profile Id.
             "
    ::= { sonusResourceMIBNotificationsObjects 4 }

sonusResourceUsage OBJECT-TYPE
    SYNTAX          Unsigned32
    MAX-ACCESS      read-only
    STATUS          current
    DESCRIPTION     
            "
             Resource Usage.
             "
    ::= { sonusResourceMIBNotificationsObjects 5 }

sonusResourceLimit OBJECT-TYPE
    SYNTAX          Unsigned32
    MAX-ACCESS      read-only
    STATUS          current
    DESCRIPTION     
            "
             Resource Limit.
             "
    ::= { sonusResourceMIBNotificationsObjects 6 }

sonusResourceThreshold OBJECT-TYPE
    SYNTAX          Unsigned32
    MAX-ACCESS      read-only
    STATUS          current
    DESCRIPTION     
            "
             Resource Usage.
             "
    ::= { sonusResourceMIBNotificationsObjects 7 }

sonusPeerResourcesMIBNotifications OBJECT IDENTIFIER
    ::= { sonusSbxTraps 17 }

sonusPeerResourcesMIBNotificationsPrefix OBJECT IDENTIFIER
    ::= { sonusPeerResourcesMIBNotifications 0 }

sonusPeerResourcesMIBNotificationsObjects OBJECT IDENTIFIER
    ::= { sonusPeerResourcesMIBNotifications 1 }

sonusPeerName OBJECT-TYPE
    SYNTAX          DisplayString
    MAX-ACCESS      read-only
    STATUS          current
    DESCRIPTION     
            "
             Name of the IP PEER
             "
    ::= { sonusPeerResourcesMIBNotificationsObjects 1 }

sonusInterceptManagerMIBNotifications OBJECT IDENTIFIER
    ::= { sonusSbxTraps 18 }

sonusInterceptManagerMIBNotificationsPrefix OBJECT IDENTIFIER
    ::= { sonusInterceptManagerMIBNotifications 0 }

sonusInterceptManagerMIBNotificationsObjects OBJECT IDENTIFIER
    ::= { sonusInterceptManagerMIBNotifications 1 }

sonusImStatusPriOperState OBJECT-TYPE
    SYNTAX          INTEGER { inService(1), outOfService(2), standBy(3) }
    MAX-ACCESS      read-only
    STATUS          current
    DESCRIPTION     
            " Current operational state of the primary call data channel."
    ::= { sonusInterceptManagerMIBNotificationsObjects 1 }

sonusImStatusSecOperState OBJECT-TYPE
    SYNTAX          INTEGER { inService(1), outOfService(2), standBy(3) }
    MAX-ACCESS      read-only
    STATUS          current
    DESCRIPTION     
            " Current operational state of the Secondary call data channel."
    ::= { sonusInterceptManagerMIBNotificationsObjects 2 }

sonusImMediationServerName OBJECT-TYPE
    SYNTAX          DisplayString
    MAX-ACCESS      read-only
    STATUS          current
    DESCRIPTION     
            "Mediation Server Name"
    ::= { sonusInterceptManagerMIBNotificationsObjects 3 }

sonusImMediationServerState OBJECT-TYPE
    SYNTAX          SonusAdminState
    MAX-ACCESS      read-only
    STATUS          current
    DESCRIPTION     
            "This administrative state of the Mediation Server"
    ::= { sonusInterceptManagerMIBNotificationsObjects 4 }

sonusImMediationServerInterceptMediaType OBJECT-TYPE
    SYNTAX          DisplayString
    MAX-ACCESS      read-only
    STATUS          current
    DESCRIPTION     
            "Mediation Server Entity - Signaling or Media"
    ::= { sonusInterceptManagerMIBNotificationsObjects 5 }

sonusMtrmMIBNotifications OBJECT IDENTIFIER
    ::= { sonusSbxTraps 19 }

sonusMtrmMIBNotificationsPrefix OBJECT IDENTIFIER
    ::= { sonusMtrmMIBNotifications 0 }

sonusMtrmMIBNotificationsObjects OBJECT IDENTIFIER
    ::= { sonusMtrmMIBNotifications 1 }

sonusMtrmPortIndex OBJECT-TYPE
    SYNTAX          Unsigned32
    MAX-ACCESS      read-only
    STATUS          current
    DESCRIPTION     
            "This the MTRM connection port Index."
    ::= { sonusMtrmMIBNotificationsObjects 1 }

sonusMtrmServerAddr OBJECT-TYPE
    SYNTAX          IpAddress
    MAX-ACCESS      read-only
    STATUS          current
    DESCRIPTION     
            "This the MTRM Server address"
    ::= { sonusMtrmMIBNotificationsObjects 2 }

sonusSecurityMIBNotifications OBJECT IDENTIFIER
    ::= { sonusSbxTraps 20 }

sonusSecurityMIBNotificationsPrefix OBJECT IDENTIFIER
    ::= { sonusSecurityMIBNotifications 0 }

sonusSecurityMIBNotificationsObjects OBJECT IDENTIFIER
    ::= { sonusSecurityMIBNotifications 1 }

sonusSecurityOcspUrlName OBJECT-TYPE
    SYNTAX          DisplayString (SIZE(1..254))
    MAX-ACCESS      read-only
    STATUS          current
    DESCRIPTION     
            "OCSP responder URL."
    ::= { sonusSecurityMIBNotificationsObjects 1 }

sonusSecurityOcspResponseStatus OBJECT-TYPE
    SYNTAX          INTEGER { successful(0), malformedRequest(1), 
                        internalError(2), tryLater(3), sigRequired(5), 
                        unauthorized(6) }
    MAX-ACCESS      read-only
    STATUS          current
    DESCRIPTION     
            "OCSP responseStatus indicating the processing status."
    ::= { sonusSecurityMIBNotificationsObjects 2 }

sonusVnfmUrlName OBJECT-TYPE
    SYNTAX          DisplayString (SIZE(1..254))
    MAX-ACCESS      read-only
    STATUS          current
    DESCRIPTION     
            "VNFM  URL."
    ::= { sonusSecurityMIBNotificationsObjects 3 }

sonusLvmMIBNotifications OBJECT IDENTIFIER
    ::= { sonusSbxTraps 21 }

sonusLvmMIBNotificationsPrefix OBJECT IDENTIFIER
    ::= { sonusLvmMIBNotifications 0 }

sonusLvmMIBNotificationsObjects OBJECT IDENTIFIER
    ::= { sonusLvmMIBNotifications 1 }

sonusLvmPortSwitchReason OBJECT-TYPE
    SYNTAX          DisplayString
    MAX-ACCESS      read-only
    STATUS          current
    DESCRIPTION     
            "Reason for switch"
    ::= { sonusLvmMIBNotificationsObjects 1 }

sonusLvmLinkDetectionGroupName OBJECT-TYPE
    SYNTAX          DisplayString (SIZE(1..24))
    MAX-ACCESS      read-only
    STATUS          current
    DESCRIPTION     
            "The name of the link detection group."
    ::= { sonusLvmMIBNotificationsObjects 2 }

sonusLvmPortRedundancyGroupName OBJECT-TYPE
    SYNTAX          DisplayString (SIZE(1..24))
    MAX-ACCESS      read-only
    STATUS          current
    DESCRIPTION     
            "The name of the port redundancy group."
    ::= { sonusLvmMIBNotificationsObjects 3 }

sonusDiamMIBNotifications OBJECT IDENTIFIER
    ::= { sonusSbxTraps 22 }

sonusDiamMIBNotificationsPrefix OBJECT IDENTIFIER
    ::= { sonusDiamMIBNotifications 0 }

sonusDiamMIBNotificationsObjects OBJECT IDENTIFIER
    ::= { sonusDiamMIBNotifications 1 }

sonusRfAccountingServerName OBJECT-TYPE
    SYNTAX          DisplayString
    MAX-ACCESS      read-only
    STATUS          deprecated
    DESCRIPTION     
            "Rf Accounting Server Name."
    ::= { sonusDiamMIBNotificationsObjects 1 }

sonusDiamPeerName OBJECT-TYPE
    SYNTAX          DisplayString
    MAX-ACCESS      read-only
    STATUS          current
    DESCRIPTION     
            "Diameter Peer Name."
    ::= { sonusDiamMIBNotificationsObjects 2 }

sonusDiamPeerIpAddress OBJECT-TYPE
    SYNTAX          DisplayString
    MAX-ACCESS      read-only
    STATUS          current
    DESCRIPTION     
            "
             Diameter Peer Ip Address.
             "
    ::= { sonusDiamMIBNotificationsObjects 3 }

sonusDnsMIBNotifications OBJECT IDENTIFIER
    ::= { sonusSbxTraps 23 }

sonusDnsMIBNotificationsPrefix OBJECT IDENTIFIER
    ::= { sonusDnsMIBNotifications 0 }

sonusDnsMIBNotificationsObjects OBJECT IDENTIFIER
    ::= { sonusDnsMIBNotifications 1 }

sonusDnsServerIp OBJECT-TYPE
    SYNTAX          DisplayString
    MAX-ACCESS      read-only
    STATUS          current
    DESCRIPTION     
            "
             IP Address of the Dns server address  - mandatory parameter.
             "
    ::= { sonusDnsMIBNotificationsObjects 1 }

sonusDnsServerPortNum OBJECT-TYPE
    SYNTAX          Integer32 (1..65535)
    MAX-ACCESS      read-only
    STATUS          current
    DESCRIPTION     
            "
             transport port number of the Dns server   - mandatory parameter.
             "
    ::= { sonusDnsMIBNotificationsObjects 2 }

sonusDnsServerTransport OBJECT-TYPE
    SYNTAX          DisplayString
    MAX-ACCESS      read-only
    STATUS          current
    DESCRIPTION     
            "
             transport used to connect to  Dns server   - mandatory parameter.
             "
    ::= { sonusDnsMIBNotificationsObjects 3 }

sonusDnsIpAddr OBJECT-TYPE
    SYNTAX          IpAddress
    MAX-ACCESS      read-only
    STATUS          current
    DESCRIPTION     
            "
             IP Address of the Dns server address.
             "
    ::= { sonusDnsMIBNotificationsObjects 4 }

sonusDnsServerZoneId OBJECT-TYPE
    SYNTAX          DisplayString
    MAX-ACCESS      read-only
    STATUS          current
    DESCRIPTION     
            "
             DNS ZONE Name of the Dns zone.
             "
    ::= { sonusDnsMIBNotificationsObjects 5 }

sonusDomainName OBJECT-TYPE
    SYNTAX          DisplayString
    MAX-ACCESS      read-only
    STATUS          obsolete
    DESCRIPTION     
            "
             Domain Name for which the Query is been done.
             "
    ::= { sonusDnsMIBNotificationsObjects 6 }

sonusRecordType OBJECT-TYPE
    SYNTAX          DisplayString
    MAX-ACCESS      read-only
    STATUS          obsolete
    DESCRIPTION     
            "
             RecordType of the FQDN.
             "
    ::= { sonusDnsMIBNotificationsObjects 7 }

sonusRcodeError OBJECT-TYPE
    SYNTAX          DisplayString
    MAX-ACCESS      read-only
    STATUS          current
    DESCRIPTION     
            "
             RCODE ERROR format received.
             "
    ::= { sonusDnsMIBNotificationsObjects 8 }

sonusDnsIpV6Addr OBJECT-TYPE
    SYNTAX          Ipv6Address
    MAX-ACCESS      read-only
    STATUS          current
    DESCRIPTION     
            "Ipv6 Address of the Dns Server."
    ::= { sonusDnsMIBNotificationsObjects 9 }

sonusDnsServerType OBJECT-TYPE
    SYNTAX          DisplayString
    MAX-ACCESS      read-only
    STATUS          current
    DESCRIPTION     
            "
             Server Type: Named server or configured server.
             "
    ::= { sonusDnsMIBNotificationsObjects 10 }

sonusEdnsMIBNotifications OBJECT IDENTIFIER
    ::= { sonusSbxTraps 24 }

sonusEdnsMIBNotificationsPrefix OBJECT IDENTIFIER
    ::= { sonusEdnsMIBNotifications 0 }

sonusEdnsMIBNotificationsObjects OBJECT IDENTIFIER
    ::= { sonusEdnsMIBNotifications 1 }

sonusEdnsServerIp OBJECT-TYPE
    SYNTAX          IpAddress
    MAX-ACCESS      read-only
    STATUS          current
    DESCRIPTION     
            "
             IP Address of the Dns server address  - mandatory parameter.
             "
    ::= { sonusEdnsMIBNotificationsObjects 1 }

sonusDsbcSignallingMIBNotifications OBJECT IDENTIFIER
    ::= { sonusSbxTraps 25 }

sonusDsbcSignallingMIBNotificationsPrefix OBJECT IDENTIFIER
    ::= { sonusDsbcSignallingMIBNotifications 0 }

sonusDsbcSignallingMIBNotificationsObjects OBJECT IDENTIFIER
    ::= { sonusDsbcSignallingMIBNotifications 1 }

sonusDsbcCloseReasonCode OBJECT-TYPE
    SYNTAX          INTEGER { administratorInitiatedClose(1), 
                        closeRequestReceivedFromRemote(2), 
                        remoteNotResponding(3), internalError(4), 
                        configError(5), recvCallSigReqFromUnknownDsbc(6), 
                        socketErrNetworkDown(7), 
                        socketErrNetworkUnreachable(8), 
                        socketErrNetworkReset(9), 
                        socketErrSoftwareConnectionAbort(10), 
                        socketErrConnectionResetByPeer(11), 
                        socketErrNoBufferSpaceAvail(12), 
                        socketErrAlreadyConnected(13), 
                        socketErrNotConnected(14), 
                        socketErrCantSendAfterShutdown(15), 
                        socketErrTooManyReferences(16), 
                        socketErrConnectionTimedOut(17), 
                        socketErrUnknown(18), 
                        recvDuplicateLinkOpenReq(19), 
                        socketErrExceptionEvent(20), 
                        linkXmtCongestion(21), 
                        openNackReceivedFromRemote(22), idleTimeout(23) }
    MAX-ACCESS      read-only
    STATUS          current
    DESCRIPTION     
            "Reason for close of Control Channel Link."
    ::= { sonusDsbcSignallingMIBNotificationsObjects 1 }

sonusDsbcRemoteDsbcAddr OBJECT-TYPE
    SYNTAX          IpAddress
    MAX-ACCESS      read-only
    STATUS          current
    DESCRIPTION     
            "Ip Address of the remote Dsbc."
    ::= { sonusDsbcSignallingMIBNotificationsObjects 2 }

sonusDsbcRemoteDsbc6Addr OBJECT-TYPE
    SYNTAX          Ipv6Address
    MAX-ACCESS      read-only
    STATUS          current
    DESCRIPTION     
            "Ipv6 Address of the remote Dsbc."
    ::= { sonusDsbcSignallingMIBNotificationsObjects 3 }

sonusDsbcClusterFqdn OBJECT-TYPE
    SYNTAX          DisplayString
    MAX-ACCESS      read-only
    STATUS          current
    DESCRIPTION     
            "The Fully Qualified Domain Name of the Cluster."
    ::= { sonusDsbcSignallingMIBNotificationsObjects 4 }

sonusDsbcClusterType OBJECT-TYPE
    SYNTAX          DisplayString
    MAX-ACCESS      read-only
    STATUS          current
    DESCRIPTION     
            "Cluster Type, policer or dsp."
    ::= { sonusDsbcSignallingMIBNotificationsObjects 5 }

sonusDsbcCallsReleasedReasonCode OBJECT-TYPE
    SYNTAX          Unsigned32
    MAX-ACCESS      read-only
    STATUS          current
    DESCRIPTION     
            "Reason code for call release due to fault."
    ::= { sonusDsbcSignallingMIBNotificationsObjects 6 }

sonusDsbcCallsReleasedCount OBJECT-TYPE
    SYNTAX          Unsigned32
    MAX-ACCESS      read-only
    STATUS          current
    DESCRIPTION     
            "Released call count due to fault."
    ::= { sonusDsbcSignallingMIBNotificationsObjects 7 }

sonusDsbcAllocFailuresCount OBJECT-TYPE
    SYNTAX          Unsigned32
    MAX-ACCESS      read-only
    STATUS          current
    DESCRIPTION     
            "Released call count due to fault."
    ::= { sonusDsbcSignallingMIBNotificationsObjects 8 }

sonusThresholdCrossingCodec OBJECT-TYPE
    SYNTAX          DisplayString
    MAX-ACCESS      read-only
    STATUS          current
    DESCRIPTION     
            "Codec/s crossing the channel capacity threshold on GPU device"
    ::= { sonusDsbcSignallingMIBNotificationsObjects 9 }

sonusTrafficProfileActivationMsg OBJECT-TYPE
    SYNTAX          DisplayString
    MAX-ACCESS      read-only
    STATUS          current
    DESCRIPTION     
            "Reason of success/failure upon activation of a traffic profile."
    ::= { sonusDsbcSignallingMIBNotificationsObjects 10 }

sonusTrafficProfileActivationStatus OBJECT-TYPE
    SYNTAX          DisplayString
    MAX-ACCESS      read-only
    STATUS          current
    DESCRIPTION     
            "Status (success/failure) of activation of a traffic profile."
    ::= { sonusDsbcSignallingMIBNotificationsObjects 11 }

sonusConfigProfileActivationMsg OBJECT-TYPE
    SYNTAX          DisplayString
    MAX-ACCESS      read-only
    STATUS          current
    DESCRIPTION     
            "Reason of success/failure upon activation of a Config profile."
    ::= { sonusDsbcSignallingMIBNotificationsObjects 12 }

sonusConfigProfileActivationStatus OBJECT-TYPE
    SYNTAX          DisplayString
    MAX-ACCESS      read-only
    STATUS          current
    DESCRIPTION     
            "Status (success/failure) of activation of a Config profile."
    ::= { sonusDsbcSignallingMIBNotificationsObjects 13 }

sonusCacMIBNotifications OBJECT IDENTIFIER
    ::= { sonusSbxTraps 26 }

sonusCacMIBNotificationsPrefix OBJECT IDENTIFIER
    ::= { sonusCacMIBNotifications 0 }

sonusCacMIBNotificationsObjects OBJECT IDENTIFIER
    ::= { sonusCacMIBNotifications 1 }

sonusCacSrcIp OBJECT-TYPE
    SYNTAX          IpAddress
    MAX-ACCESS      read-only
    STATUS          current
    DESCRIPTION     
            " IP Address of end point  - mandatory parameter. "
    ::= { sonusCacMIBNotificationsObjects 1 }

sonusCcsMIBNotifications OBJECT IDENTIFIER
    ::= { sonusSbxTraps 27 }

sonusCcsMIBNotificationsPrefix OBJECT IDENTIFIER
    ::= { sonusCcsMIBNotifications 0 }

sonusCcsMIBNotificationsObjects OBJECT IDENTIFIER
    ::= { sonusCcsMIBNotifications 1 }

sonusOodMIBNotifications OBJECT IDENTIFIER
    ::= { sonusSbxTraps 28 }

sonusOodMIBNotificationsPrefix OBJECT IDENTIFIER
    ::= { sonusOodMIBNotifications 0 }

sonusOodMIBNotificationsObjects OBJECT IDENTIFIER
    ::= { sonusOodMIBNotifications 1 }

sonusActiveOodRate OBJECT-TYPE
    SYNTAX          Unsigned32
    MAX-ACCESS      read-only
    STATUS          current
    DESCRIPTION     
            "Active OOD Message Rate"
    ::= { sonusOodMIBNotificationsObjects 1 }

sonusOodRateLimit OBJECT-TYPE
    SYNTAX          Unsigned32
    MAX-ACCESS      read-only
    STATUS          current
    DESCRIPTION     
            "Configured OOD Message Rate Limit"
    ::= { sonusOodMIBNotificationsObjects 2 }

sonusOamMIBNotifications OBJECT IDENTIFIER
    ::= { sonusSbxTraps 29 }

sonusOamMIBNotificationsPrefix OBJECT IDENTIFIER
    ::= { sonusOamMIBNotifications 0 }

sonusOamMIBNotificationsObjects OBJECT IDENTIFIER
    ::= { sonusOamMIBNotifications 1 }

sonusManagedNodeCeName OBJECT-TYPE
    SYNTAX          DisplayString
    MAX-ACCESS      read-only
    STATUS          current
    DESCRIPTION     
            "Managed node compute element name"
    ::= { sonusOamMIBNotificationsObjects 1 }

sonusHpcCallLimitMIBNotifications OBJECT IDENTIFIER
    ::= { sonusSbxTraps 30 }

sonusHpcCallLimitMIBNotificationsPrefix OBJECT IDENTIFIER
    ::= { sonusHpcCallLimitMIBNotifications 0 }

sonusHpcCallLimitMIBNotificationsObjects OBJECT IDENTIFIER
    ::= { sonusHpcCallLimitMIBNotifications 1 }

sonusHpcCallLimitEntityName OBJECT-TYPE
    SYNTAX          DisplayString
    MAX-ACCESS      read-only
    STATUS          current
    DESCRIPTION     
            "Zone, TrunkGroup, IPPeer name"
    ::= { sonusHpcCallLimitMIBNotificationsObjects 1 }

sonusHpcCallLimitDeniedAttempts OBJECT-TYPE
    SYNTAX          Unsigned32
    MAX-ACCESS      read-only
    STATUS          current
    DESCRIPTION     
            "Number of calls denied being reported."
    ::= { sonusHpcCallLimitMIBNotificationsObjects 2 }

sonusHpcCallNoLicenseMIBNotifications OBJECT IDENTIFIER
    ::= { sonusSbxTraps 31 }

sonusHpcCallNoLicenseMIBNotificationsPrefix OBJECT IDENTIFIER
    ::= { sonusHpcCallNoLicenseMIBNotifications 0 }

sonusHpcCallNoLicenseMIBNotificationsObjects OBJECT IDENTIFIER
    ::= { sonusHpcCallNoLicenseMIBNotifications 1 }

sonusSlbMIBNotifications OBJECT IDENTIFIER
    ::= { sonusSbxTraps 32 }

sonusSlbMIBNotificationsPrefix OBJECT IDENTIFIER
    ::= { sonusSlbMIBNotifications 0 }

sonusSlbMIBNotificationsObjects OBJECT IDENTIFIER
    ::= { sonusSlbMIBNotifications 1 }

sonusVnfId OBJECT-TYPE
    SYNTAX          DisplayString
    MAX-ACCESS      read-only
    STATUS          current
    DESCRIPTION     
            "VNF Identifier"
    ::= { sonusSlbMIBNotificationsObjects 1 }

sonusVnfcInstanceId OBJECT-TYPE
    SYNTAX          Unsigned32
    MAX-ACCESS      read-only
    STATUS          current
    DESCRIPTION     
            "VNFC Instance Identifier"
    ::= { sonusSlbMIBNotificationsObjects 2 }

sonusSlbIpAddress OBJECT-TYPE
    SYNTAX          IpAddress
    MAX-ACCESS      read-only
    STATUS          current
    DESCRIPTION     
            "Ip Address of the SLB."
    ::= { sonusSlbMIBNotificationsObjects 3 }

sonusSlbIpv6Address OBJECT-TYPE
    SYNTAX          Ipv6Address
    MAX-ACCESS      read-only
    STATUS          current
    DESCRIPTION     
            "Ipv6 Address of the SLB."
    ::= { sonusSlbMIBNotificationsObjects 4 }

sonusCurrentGlobalLossRatio OBJECT-TYPE
    SYNTAX          Unsigned32
    MAX-ACCESS      read-only
    STATUS          current
    DESCRIPTION     
            "Current Global Loss Ratio"
    ::= { sonusSlbMIBNotificationsObjects 5 }

sonusGlobalLossRatioLimit OBJECT-TYPE
    SYNTAX          Unsigned32
    MAX-ACCESS      read-only
    STATUS          current
    DESCRIPTION     
            "Configured Global Los Ratio Limit"
    ::= { sonusSlbMIBNotificationsObjects 6 }

sonusSlbName OBJECT-TYPE
    SYNTAX          DisplayString
    MAX-ACCESS      read-only
    STATUS          current
    DESCRIPTION     
            "SLB Name"
    ::= { sonusSlbMIBNotificationsObjects 7 }

sonusCurrentGlobalUtilization OBJECT-TYPE
    SYNTAX          Unsigned32
    MAX-ACCESS      read-only
    STATUS          current
    DESCRIPTION     
            "Current Global Utilization"
    ::= { sonusSlbMIBNotificationsObjects 8 }

sonusGlobalUtilizationLimit OBJECT-TYPE
    SYNTAX          Unsigned32
    MAX-ACCESS      read-only
    STATUS          current
    DESCRIPTION     
            "Configured Global Utilization Limit"
    ::= { sonusSlbMIBNotificationsObjects 9 }

sonusMicroServiceMIBNotifications OBJECT IDENTIFIER
    ::= { sonusSbxTraps 33 }

sonusMicroServiceMIBNotificationsPrefix OBJECT IDENTIFIER
    ::= { sonusMicroServiceMIBNotifications 0 }

sonusMicroServiceMIBNotificationsObjects OBJECT IDENTIFIER
    ::= { sonusMicroServiceMIBNotifications 1 }

sonusMicroServiceName OBJECT-TYPE
    SYNTAX          DisplayString
    MAX-ACCESS      read-only
    STATUS          current
    DESCRIPTION     
            "Name of the micro-service."
    ::= { sonusMicroServiceMIBNotificationsObjects 1 }

sonusBfdMIBNotifications OBJECT IDENTIFIER
    ::= { sonusSbxTraps 34 }

sonusBfdMIBNotificationsPrefix OBJECT IDENTIFIER
    ::= { sonusBfdMIBNotifications 0 }

sonusBfdMIBNotificationsObjects OBJECT IDENTIFIER
    ::= { sonusBfdMIBNotifications 1 }

sonusBfdLinkId OBJECT-TYPE
    SYNTAX          Integer32 (0..65535)
    MAX-ACCESS      read-only
    STATUS          current
    DESCRIPTION     
            "link ID to identify bfd session."
    ::= { sonusBfdMIBNotificationsObjects 1 }

sonusH248NoRtpMIBNotifications OBJECT IDENTIFIER
    ::= { sonusSbxTraps 35 }

sonusH248NoRtpMIBNotificationsPrefix OBJECT IDENTIFIER
    ::= { sonusH248NoRtpMIBNotifications 0 }

sonusH248NoRtpMIBNotificationsObjects OBJECT IDENTIFIER
    ::= { sonusH248NoRtpMIBNotifications 1 }

sonusH248VmgName OBJECT-TYPE
    SYNTAX          DisplayString (SIZE(1..24))
    MAX-ACCESS      read-only
    STATUS          current
    DESCRIPTION     
            "The name of the VMG."
    ::= { sonusH248NoRtpMIBNotificationsObjects 1 }

sonusH248TermThreshold OBJECT-TYPE
    SYNTAX          Unsigned32
    MAX-ACCESS      read-only
    STATUS          current
    DESCRIPTION     
            "No RTP Alarm Set Threshold"
    ::= { sonusH248NoRtpMIBNotificationsObjects 2 }

sonusH248NoRtpTerminations OBJECT-TYPE
    SYNTAX          Unsigned32
    MAX-ACCESS      read-only
    STATUS          current
    DESCRIPTION     
            "Total Number of No RTP Terminations"
    ::= { sonusH248NoRtpMIBNotificationsObjects 3 }

sonusH248ClearThreshold OBJECT-TYPE
    SYNTAX          Unsigned32
    MAX-ACCESS      read-only
    STATUS          current
    DESCRIPTION     
            "No RTP Alarm Clear Threshold"
    ::= { sonusH248NoRtpMIBNotificationsObjects 4 }

sonusH248MinimumRtpTerminations OBJECT-TYPE
    SYNTAX          Unsigned32
    MAX-ACCESS      read-only
    STATUS          current
    DESCRIPTION     
            "Minimum Number of RTP Terminations Required"
    ::= { sonusH248NoRtpMIBNotificationsObjects 5 }

sonusH248TotalRtpTerminations OBJECT-TYPE
    SYNTAX          Unsigned32
    MAX-ACCESS      read-only
    STATUS          current
    DESCRIPTION     
            "Total RTP Terminations on VMG"
    ::= { sonusH248NoRtpMIBNotificationsObjects 6 }

sonusPortMIBNotifications OBJECT IDENTIFIER
    ::= { sonusSbxTraps 36 }

sonusPortMIBNotificationsPrefix OBJECT IDENTIFIER
    ::= { sonusPortMIBNotifications 0 }

sonusPortMIBNotificationsObjects OBJECT IDENTIFIER
    ::= { sonusPortMIBNotifications 1 }

sonusEthernetPortName OBJECT-TYPE
    SYNTAX          DisplayString (SIZE(1..24))
    MAX-ACCESS      read-only
    STATUS          current
    DESCRIPTION     
            "The name of the port."
    ::= { sonusPortMIBNotificationsObjects 1 }

sonusEthernetPortBwUsageThreshold OBJECT-TYPE
    SYNTAX          Unsigned32
    MAX-ACCESS      read-only
    STATUS          current
    DESCRIPTION     
            "Packet Port BW Usage Set Threshold"
    ::= { sonusPortMIBNotificationsObjects 2 }

sonusEthernetPortBwUsage OBJECT-TYPE
    SYNTAX          Unsigned32
    MAX-ACCESS      read-only
    STATUS          current
    DESCRIPTION     
            "BW Usage on Packet Port"
    ::= { sonusPortMIBNotificationsObjects 3 }

sonusEthernetPortBwUsageClearThreshold OBJECT-TYPE
    SYNTAX          Unsigned32
    MAX-ACCESS      read-only
    STATUS          current
    DESCRIPTION     
            "Packet Port BW Usage Clear Threshold"
    ::= { sonusPortMIBNotificationsObjects 4 }

sonusSbxSipCallSigPortOpenNotification NOTIFICATION-TYPE
    OBJECTS         { sonusAlarmNodeID, sonusAlarmLevel, 
                      sonusAlarmSequenceId, sonusAlarmTime, 
                      sonusAlarmDescription, sonusSipSigPortIpAddress, 
                      sonusSipSigPortNum, sonusSipSigProto }
    STATUS          current
    DESCRIPTION     
            "This trap indicates that a call signaling port is opened."
    ::= { sonusSipSignallingMIBNotificationsPrefix 1 }

sonusSbxSipCallSigPortCloseNotification NOTIFICATION-TYPE
    OBJECTS         { sonusAlarmNodeID, sonusAlarmLevel, 
                      sonusAlarmSequenceId, sonusAlarmTime, 
                      sonusAlarmDescription, sonusSipSigPortIpAddress, 
                      sonusSipSigPortNum, sonusSipSigProto }
    STATUS          current
    DESCRIPTION     
            "This trap indicates that a call signaling port is closed."
    ::= { sonusSipSignallingMIBNotificationsPrefix 2 }

sonusSbxSipTrunkGroupInServiceNotification NOTIFICATION-TYPE
    OBJECTS         { sonusAlarmNodeID, sonusAlarmLevel, 
                      sonusAlarmSequenceId, sonusAlarmTime, 
                      sonusAlarmDescription, sonusSipTgName }
    STATUS          current
    DESCRIPTION     
            "This trap indicates that the SIP Trunk Group was put
             into service by maintenance staff."
    ::= { sonusSipSignallingMIBNotificationsPrefix 3 }

sonusSbxSipTrunkGroupOutOfServiceNotification NOTIFICATION-TYPE
    OBJECTS         { sonusAlarmNodeID, sonusAlarmLevel, 
                      sonusAlarmSequenceId, sonusAlarmTime, 
                      sonusAlarmDescription, sonusSipTgName }
    STATUS          current
    DESCRIPTION     
            "This trap indicates that the SIP Trunk Group was taken
             out of service by maintenance staff."
    ::= { sonusSipSignallingMIBNotificationsPrefix 4 }

sonusSbxSipRegistrantPortChangeNotification NOTIFICATION-TYPE
    OBJECTS         { sonusAlarmNodeID, sonusAlarmLevel, 
                      sonusAlarmSequenceId, sonusAlarmTime, 
                      sonusAlarmDescription }
    STATUS          current
    DESCRIPTION     
            "This trap indicates that at least one SIP registrant
             has a source port number that changed over two or more
             consecutive REGISTER refreshes, possibly indicating that
             the registrant was unreachable from the SBC for a time."
    ::= { sonusSipSignallingMIBNotificationsPrefix 5 }

sonusSbxArsEndPointBlacklistedNotification NOTIFICATION-TYPE
    OBJECTS         { sonusAlarmNodeID, sonusAlarmLevel, 
                      sonusAlarmSequenceId, sonusAlarmTime, 
                      sonusAlarmDescription, 
                      sonusSipArsStatEndpointIpAddress, 
                      sonusSipArsStatEndpointIpPortNum, 
                      sonusSipArsStatSigZoneId, 
                      sonusSipArsStatSigPortNum, 
                      sonusSipArsStatEndpointOwnerId }
    STATUS          deprecated
    DESCRIPTION     
            "This trap is replaced by sonusSbxArsEndPointBlacklistedNotification2"
    ::= { sonusSipSignallingMIBNotificationsPrefix 6 }

sonusSbxArsEndPointRecoveredNotification NOTIFICATION-TYPE
    OBJECTS         { sonusAlarmNodeID, sonusAlarmLevel, 
                      sonusAlarmSequenceId, sonusAlarmTime, 
                      sonusAlarmDescription, 
                      sonusSipArsStatEndpointIpAddress, 
                      sonusSipArsStatEndpointIpPortNum, 
                      sonusSipArsStatSigZoneId, 
                      sonusSipArsStatSigPortNum, 
                      sonusSipArsStatEndpointOwnerId }
    STATUS          deprecated
    DESCRIPTION     
            "This trap is replaced by sonusSbxArsEndPointRecoveredNotification2"
    ::= { sonusSipSignallingMIBNotificationsPrefix 7 }

sonusSbxArsEndPointsRecoveredNotification NOTIFICATION-TYPE
    OBJECTS         { sonusAlarmNodeID, sonusAlarmLevel, 
                      sonusAlarmSequenceId, sonusAlarmTime, 
                      sonusAlarmDescription, sonusSipArsStatSigZoneId, 
                      sonusSipArsEndpointRecoveryAll }
    STATUS          deprecated
    DESCRIPTION     
            "This trap is replaced by sonusSbxArsEndPointsRecoveredNotification2"
    ::= { sonusSipSignallingMIBNotificationsPrefix 8 }

sonusSbxSipTgRegLimitReachedNotification NOTIFICATION-TYPE
    OBJECTS         { sonusAlarmNodeID, sonusAlarmLevel, 
                      sonusAlarmSequenceId, sonusAlarmTime, 
                      sonusAlarmDescription, sonusSipTgName }
    STATUS          current
    DESCRIPTION     
            "This trap indicates that a Trunk Group's max registration limit
             has reached due to received registrations on ingress OR implicit or child registrations."
    ::= { sonusSipSignallingMIBNotificationsPrefix 9 }

sonusSbxPathCheckPingStateUpNotification NOTIFICATION-TYPE
    OBJECTS         { sonusAlarmNodeID, sonusAlarmLevel, 
                      sonusAlarmSequenceId, sonusAlarmTime, 
                      sonusAlarmDescription, sonusPingPeerIpAddress, 
                      sonusPingPeerPortNum, sonusPingPeerZoneId }
    STATUS          deprecated
    DESCRIPTION     
            "This trap is replaced by sonusSbxPathCheckPingStateUpNotification2"
    ::= { sonusSipSignallingMIBNotificationsPrefix 10 }

sonusSbxPathCheckPingStateDownNotification NOTIFICATION-TYPE
    OBJECTS         { sonusAlarmNodeID, sonusAlarmLevel, 
                      sonusAlarmSequenceId, sonusAlarmTime, 
                      sonusAlarmDescription, sonusPingPeerIpAddress, 
                      sonusPingPeerPortNum, sonusPingPeerZoneId }
    STATUS          deprecated
    DESCRIPTION     
            "This trap is replaced by sonusSbxPathCheckPingStateDownNotification2"
    ::= { sonusSipSignallingMIBNotificationsPrefix 11 }

sonusSbxPathCheckRemoteAdminStateUpNotification NOTIFICATION-TYPE
    OBJECTS         { sonusAlarmNodeID, sonusAlarmLevel, 
                      sonusAlarmSequenceId, sonusAlarmTime, 
                      sonusAlarmDescription, sonusPingPeerIpAddress, 
                      sonusPingPeerPortNum, sonusPingPeerZoneId }
    STATUS          deprecated
    DESCRIPTION     
            "This trap is replaced by sonusSbxPathCheckRemoteAdminStateUpNotification2"
    ::= { sonusSipSignallingMIBNotificationsPrefix 12 }

sonusSbxPathCheckRemoteAdminStateDownNotification NOTIFICATION-TYPE
    OBJECTS         { sonusAlarmNodeID, sonusAlarmLevel, 
                      sonusAlarmSequenceId, sonusAlarmTime, 
                      sonusAlarmDescription, sonusPingPeerIpAddress, 
                      sonusPingPeerPortNum, sonusPingPeerZoneId }
    STATUS          deprecated
    DESCRIPTION     
            "This trap is replaced by sonusSbxPathCheckRemoteAdminStateDownNotification2"
    ::= { sonusSipSignallingMIBNotificationsPrefix 13 }

sonusSbxPathCheckLocalAdminStateUpNotification NOTIFICATION-TYPE
    OBJECTS         { sonusAlarmNodeID, sonusAlarmLevel, 
                      sonusAlarmSequenceId, sonusAlarmTime, 
                      sonusAlarmDescription, sonusPingPeerIpAddress, 
                      sonusPingPeerPortNum, sonusPingPeerZoneId }
    STATUS          deprecated
    DESCRIPTION     
            "This trap is replaced by sonusSbxPathCheckLocalAdminStateUpNotification2"
    ::= { sonusSipSignallingMIBNotificationsPrefix 14 }

sonusSbxPathCheckLocalAdminStateDownNotification NOTIFICATION-TYPE
    OBJECTS         { sonusAlarmNodeID, sonusAlarmLevel, 
                      sonusAlarmSequenceId, sonusAlarmTime, 
                      sonusAlarmDescription, sonusPingPeerIpAddress, 
                      sonusPingPeerPortNum, sonusPingPeerZoneId }
    STATUS          deprecated
    DESCRIPTION     
            "The trap is replaced by sonusSbxPathCheckLocalAdminStateDownNotification2"
    ::= { sonusSipSignallingMIBNotificationsPrefix 15 }

sonusSbxSipMultipleContactsPerAorSigPortExhaustedNotification NOTIFICATION-TYPE
    OBJECTS         { sonusAlarmNodeID, sonusAlarmLevel, 
                      sonusAlarmSequenceId, sonusAlarmTime, 
                      sonusAlarmDescription, sonusSipAorSigZoneId }
    STATUS          current
    DESCRIPTION     
            "This trap indicates that  an AOR registering from multiple
             contact address is reusing a signlaing port on trunk group the towards the 
             registrar. This trap is generated once per zone"
    ::= { sonusSipSignallingMIBNotificationsPrefix 16 }

sonusSbxSurrRegRegistrationSuccessNotification NOTIFICATION-TYPE
    OBJECTS         { sonusAlarmNodeID, sonusAlarmLevel, 
                      sonusAlarmSequenceId, sonusAlarmTime, 
                      sonusAlarmDescription, sonusSurrRegPeerIpAddress, 
                      sonusSurrRegPeerPortNum, sonusSurrRegPeerZoneId, 
                      sonusSurrRegUserPart }
    STATUS          current
    DESCRIPTION     
            "This trap indicates that the surrogate registration for the AOR succeeded"
    ::= { sonusSipSignallingMIBNotificationsPrefix 17 }

sonusSbxSurrRegRegistrationFailedNotification NOTIFICATION-TYPE
    OBJECTS         { sonusAlarmNodeID, sonusAlarmLevel, 
                      sonusAlarmSequenceId, sonusAlarmTime, 
                      sonusAlarmDescription, sonusSurrRegPeerIpAddress, 
                      sonusSurrRegPeerPortNum, sonusSurrRegPeerZoneId, 
                      sonusSurrRegUserPart }
    STATUS          current
    DESCRIPTION     
            "This trap indicates that the surrogate registration for the AOR failed"
    ::= { sonusSipSignallingMIBNotificationsPrefix 18 }

sonusSbxArsEndPointBlacklistedNotificationV6 NOTIFICATION-TYPE
    OBJECTS         { sonusAlarmNodeID, sonusAlarmLevel, 
                      sonusAlarmSequenceId, sonusAlarmTime, 
                      sonusAlarmDescription, 
                      sonusSipArsStatEndpointIpAddressV6, 
                      sonusSipArsStatEndpointIpPortNum, 
                      sonusSipArsStatSigZoneId, 
                      sonusSipArsStatSigPortNum, 
                      sonusSipArsStatEndpointOwnerId }
    STATUS          deprecated
    DESCRIPTION     
            "This trap is replaced by sonusSbxArsEndPointBlacklistedNotification2V6"
    ::= { sonusSipSignallingMIBNotificationsPrefix 19 }

sonusSbxArsEndPointRecoveredNotificationV6 NOTIFICATION-TYPE
    OBJECTS         { sonusAlarmNodeID, sonusAlarmLevel, 
                      sonusAlarmSequenceId, sonusAlarmTime, 
                      sonusAlarmDescription, 
                      sonusSipArsStatEndpointIpAddressV6, 
                      sonusSipArsStatEndpointIpPortNum, 
                      sonusSipArsStatSigZoneId, 
                      sonusSipArsStatSigPortNum, 
                      sonusSipArsStatEndpointOwnerId }
    STATUS          deprecated
    DESCRIPTION     
            "This trap is replaced by sonusSbxArsEndPointRecoveredNotification2V6"
    ::= { sonusSipSignallingMIBNotificationsPrefix 20 }

sonusSbxSipCallSigPortOpenNotificationV6 NOTIFICATION-TYPE
    OBJECTS         { sonusAlarmNodeID, sonusAlarmLevel, 
                      sonusAlarmSequenceId, sonusAlarmTime, 
                      sonusAlarmDescription, sonusSipSigPortIpAddressV6, 
                      sonusSipSigPortNum, sonusSipSigProto }
    STATUS          current
    DESCRIPTION     
            "This trap indicates that a call signaling port is opened."
    ::= { sonusSipSignallingMIBNotificationsPrefix 21 }

sonusSbxPathCheckLocalAdminStateUpNotificationV6 NOTIFICATION-TYPE
    OBJECTS         { sonusAlarmNodeID, sonusAlarmLevel, 
                      sonusAlarmSequenceId, sonusAlarmTime, 
                      sonusAlarmDescription, sonusPingPeerIpAddressV6, 
                      sonusPingPeerPortNum, sonusPingPeerZoneId }
    STATUS          deprecated
    DESCRIPTION     
            "This trap is replaced by sonusSbxPathCheckLocalAdminStateUpNotification2V6"
    ::= { sonusSipSignallingMIBNotificationsPrefix 22 }

sonusSbxPathCheckLocalAdminStateDownNotificationV6 NOTIFICATION-TYPE
    OBJECTS         { sonusAlarmNodeID, sonusAlarmLevel, 
                      sonusAlarmSequenceId, sonusAlarmTime, 
                      sonusAlarmDescription, sonusPingPeerIpAddressV6, 
                      sonusPingPeerPortNum, sonusPingPeerZoneId }
    STATUS          deprecated
    DESCRIPTION     
            "This trap is replaced by sonusSbxPathCheckLocalAdminStateDownNotification2V6"
    ::= { sonusSipSignallingMIBNotificationsPrefix 23 }

sonusSbxPathCheckPingStateUpNotificationV6 NOTIFICATION-TYPE
    OBJECTS         { sonusAlarmNodeID, sonusAlarmLevel, 
                      sonusAlarmSequenceId, sonusAlarmTime, 
                      sonusAlarmDescription, sonusPingPeerIpAddressV6, 
                      sonusPingPeerPortNum, sonusPingPeerZoneId }
    STATUS          deprecated
    DESCRIPTION     
            "This trap is replaced by sonusSbxPathCheckPingStateUpNotification2V6"
    ::= { sonusSipSignallingMIBNotificationsPrefix 24 }

sonusSbxPathCheckPingStateDownNotificationV6 NOTIFICATION-TYPE
    OBJECTS         { sonusAlarmNodeID, sonusAlarmLevel, 
                      sonusAlarmSequenceId, sonusAlarmTime, 
                      sonusAlarmDescription, sonusPingPeerIpAddressV6, 
                      sonusPingPeerPortNum, sonusPingPeerZoneId }
    STATUS          deprecated
    DESCRIPTION     
            "This trap is replaced by sonusSbxPathCheckPingStateDownNotification2V6"
    ::= { sonusSipSignallingMIBNotificationsPrefix 25 }

sonusSbxSipCallSigPortCloseNotificationV6 NOTIFICATION-TYPE
    OBJECTS         { sonusAlarmNodeID, sonusAlarmLevel, 
                      sonusAlarmSequenceId, sonusAlarmTime, 
                      sonusAlarmDescription, sonusSipSigPortIpAddressV6, 
                      sonusSipSigPortNum, sonusSipSigProto }
    STATUS          current
    DESCRIPTION     
            "This trap indicates that a call signaling port is closed."
    ::= { sonusSipSignallingMIBNotificationsPrefix 26 }

sonusSbxPathCheckRemoteAdminStateUpNotificationV6 NOTIFICATION-TYPE
    OBJECTS         { sonusAlarmNodeID, sonusAlarmLevel, 
                      sonusAlarmSequenceId, sonusAlarmTime, 
                      sonusAlarmDescription, sonusPingPeerIpAddressV6, 
                      sonusPingPeerPortNum, sonusPingPeerZoneId }
    STATUS          deprecated
    DESCRIPTION     
            "This trap is replaced by sonusSbxPathCheckRemoteAdminStateUpNotification2V6"
    ::= { sonusSipSignallingMIBNotificationsPrefix 27 }

sonusSbxPathCheckRemoteAdminStateDownNotificationV6 NOTIFICATION-TYPE
    OBJECTS         { sonusAlarmNodeID, sonusAlarmLevel, 
                      sonusAlarmSequenceId, sonusAlarmTime, 
                      sonusAlarmDescription, sonusPingPeerIpAddressV6, 
                      sonusPingPeerPortNum, sonusPingPeerZoneId }
    STATUS          deprecated
    DESCRIPTION     
            "This trap is replaced by sonusSbxPathCheckRemoteAdminStateDownNotification2V6"
    ::= { sonusSipSignallingMIBNotificationsPrefix 28 }

sonusSbxSurrRegRegistrationSuccessNotificationV6 NOTIFICATION-TYPE
    OBJECTS         { sonusAlarmNodeID, sonusAlarmLevel, 
                      sonusAlarmSequenceId, sonusAlarmTime, 
                      sonusAlarmDescription, sonusSurrRegPeerIpAddressV6, 
                      sonusSurrRegPeerPortNum, sonusSurrRegPeerZoneId }
    STATUS          current
    DESCRIPTION     
            "This trap indicates that the surrogate registration for the peer succeeded"
    ::= { sonusSipSignallingMIBNotificationsPrefix 29 }

sonusSbxSurrRegRegistrationFailedNotificationV6 NOTIFICATION-TYPE
    OBJECTS         { sonusAlarmNodeID, sonusAlarmLevel, 
                      sonusAlarmSequenceId, sonusAlarmTime, 
                      sonusAlarmDescription, sonusSurrRegPeerIpAddressV6, 
                      sonusSurrRegPeerPortNum, sonusSurrRegPeerZoneId }
    STATUS          current
    DESCRIPTION     
            "This trap indicates that the surrogate registration for the peer failed"
    ::= { sonusSipSignallingMIBNotificationsPrefix 30 }

sonusSbxPathCheckFqdnPeerUpNotification NOTIFICATION-TYPE
    OBJECTS         { sonusAlarmNodeID, sonusAlarmLevel, 
                      sonusAlarmSequenceId, sonusAlarmTime, 
                      sonusAlarmDescription, sonusPingPeerFqdn, 
                      sonusPingPeerPortNum, sonusPingPeerZoneId }
    STATUS          deprecated
    DESCRIPTION     
            "This trap is replaced by sonusSbxPathCheckFqdnPeerUpNotification2"
    ::= { sonusSipSignallingMIBNotificationsPrefix 31 }

sonusSbxPathCheckFqdnPeerDownNotification NOTIFICATION-TYPE
    OBJECTS         { sonusAlarmNodeID, sonusAlarmLevel, 
                      sonusAlarmSequenceId, sonusAlarmTime, 
                      sonusAlarmDescription, sonusPingPeerFqdn, 
                      sonusPingPeerPortNum, sonusPingPeerZoneId }
    STATUS          deprecated
    DESCRIPTION     
            "This trap is replaced by sonusSbxPathCheckFqdnPeerDownNotification2"
    ::= { sonusSipSignallingMIBNotificationsPrefix 32 }

sonusSbxPathCheckFqdnPeerIpEndpointUpNotification NOTIFICATION-TYPE
    OBJECTS         { sonusAlarmNodeID, sonusAlarmLevel, 
                      sonusAlarmSequenceId, sonusAlarmTime, 
                      sonusAlarmDescription, sonusPingPeerIpAddress, 
                      sonusPingPeerPortNum, sonusPingPeerFqdn, 
                      sonusPingPeerZoneId }
    STATUS          deprecated
    DESCRIPTION     
            "This trap is replaced by sonusSbxPathCheckFqdnPeerIpEndpointUpNotification2"
    ::= { sonusSipSignallingMIBNotificationsPrefix 33 }

sonusSbxPathCheckFqdnPeerIpEndpointDownNotification NOTIFICATION-TYPE
    OBJECTS         { sonusAlarmNodeID, sonusAlarmLevel, 
                      sonusAlarmSequenceId, sonusAlarmTime, 
                      sonusAlarmDescription, sonusPingPeerIpAddress, 
                      sonusPingPeerPortNum, sonusPingPeerFqdn, 
                      sonusPingPeerZoneId }
    STATUS          deprecated
    DESCRIPTION     
            "This trap is replaced by sonusSbxPathCheckFqdnPeerIpEndpointDownNotification2"
    ::= { sonusSipSignallingMIBNotificationsPrefix 34 }

sonusSbxFailedCertificateReCheck NOTIFICATION-TYPE
    OBJECTS         { sonusAlarmNodeID, sonusAlarmLevel, 
                      sonusAlarmSequenceId, sonusAlarmTime, 
                      sonusAlarmDescription, sonusCertReCheckSocketId, 
                      sonusCertReCheckName }
    STATUS          current
    DESCRIPTION     
            "This trap indicates that certificate recheck for long lived session failed."
    ::= { sonusSipSignallingMIBNotificationsPrefix 36 }

sonusSbxSurrRegAuthenticationFailedNotification NOTIFICATION-TYPE
    OBJECTS         { sonusAlarmNodeID, sonusAlarmLevel, 
                      sonusAlarmSequenceId, sonusAlarmTime, 
                      sonusAlarmDescription, sonusSurrRegMethodName, 
                      sonusSurrRegPeerName, sonusSurrRegUserPart, 
                      sonusSurrRegPeerIpAddress, sonusSurrRegPeerPortNum, 
                      sonusSurrRegPeerZoneId }
    STATUS          current
    DESCRIPTION     
            "This alarm indicates that the authentication failed for surrogate endpoint"
    ::= { sonusSipSignallingMIBNotificationsPrefix 37 }

sonusSbxSurrRegAuthenticationClearNotification NOTIFICATION-TYPE
    OBJECTS         { sonusAlarmNodeID, sonusAlarmLevel, 
                      sonusAlarmSequenceId, sonusAlarmTime, 
                      sonusAlarmDescription, sonusSurrRegPeerName, 
                      sonusSurrRegUserPart, sonusSurrRegPeerIpAddress, 
                      sonusSurrRegPeerPortNum, sonusSurrRegPeerZoneId }
    STATUS          current
    DESCRIPTION     
            "This trap indicates that the surrogate registration for the peer succeeded"
    ::= { sonusSipSignallingMIBNotificationsPrefix 38 }

sonusSbxPathCheckFqdnPeerIpV6EndpointUpNotification NOTIFICATION-TYPE
    OBJECTS         { sonusAlarmNodeID, sonusAlarmLevel, 
                      sonusAlarmSequenceId, sonusAlarmTime, 
                      sonusAlarmDescription, sonusPingPeerIpAddressV6, 
                      sonusPingPeerPortNum, sonusPingPeerFqdn, 
                      sonusPingPeerZoneId }
    STATUS          deprecated
    DESCRIPTION     
            "This trap is replaced by sonusSbxPathCheckFqdnPeerIpV6EndpointUpNotification2"
    ::= { sonusSipSignallingMIBNotificationsPrefix 39 }

sonusSbxPathCheckFqdnPeerIpV6EndpointDownNotification NOTIFICATION-TYPE
    OBJECTS         { sonusAlarmNodeID, sonusAlarmLevel, 
                      sonusAlarmSequenceId, sonusAlarmTime, 
                      sonusAlarmDescription, sonusPingPeerIpAddressV6, 
                      sonusPingPeerPortNum, sonusPingPeerFqdn, 
                      sonusPingPeerZoneId }
    STATUS          deprecated
    DESCRIPTION     
            "This trap is replaced by sonusSbxPathCheckFqdnPeerIpV6EndpointDownNotification2"
    ::= { sonusSipSignallingMIBNotificationsPrefix 40 }

sonusSbxSipRecRecordingFailedNotification NOTIFICATION-TYPE
    OBJECTS         { sonusAlarmNodeID, sonusAlarmLevel, 
                      sonusAlarmSequenceId, sonusAlarmTime, 
                      sonusAlarmDescription, sonusRecorderIpAddress, 
                      sonusRecorderPortNum, sonusRecCallGCID, 
                      sonusRecorderTrunkName, sonusRecordingCallLeg }
    STATUS          current
    DESCRIPTION     
            "This trap indicates that SIPRec recording failed"
    ::= { sonusSipSignallingMIBNotificationsPrefix 41 }

sonusSbxSipRecRecordingFailedNotificationV6 NOTIFICATION-TYPE
    OBJECTS         { sonusAlarmNodeID, sonusAlarmLevel, 
                      sonusAlarmSequenceId, sonusAlarmTime, 
                      sonusAlarmDescription, sonusRecorderIpAddressV6, 
                      sonusRecorderPortNum, sonusRecCallGCID, 
                      sonusRecorderTrunkName, sonusRecordingCallLeg }
    STATUS          current
    DESCRIPTION     
            "This trap indicates that SIPRec recording failed"
    ::= { sonusSipSignallingMIBNotificationsPrefix 42 }

sonusSbxSipSignallingRecordingRejectedServerUnavailable NOTIFICATION-TYPE
    OBJECTS         { sonusAlarmNodeID, sonusAlarmLevel, 
                      sonusAlarmSequenceId, sonusAlarmTime, 
                      sonusAlarmDescription, sonusRecorderIpAddress, 
                      sonusRecorderPortNum, sonusRecCallGCID, 
                      sonusRecorderTrunkName, sonusRecordingCallLeg }
    STATUS          current
    DESCRIPTION     
            "This trap indicates that recording request is rejected due to the unavailability of the recording server"
    ::= { sonusSipSignallingMIBNotificationsPrefix 43 }

sonusSbxSipSignallingRecordingRejectedServerUnavailableV6 NOTIFICATION-TYPE
    OBJECTS         { sonusAlarmNodeID, sonusAlarmLevel, 
                      sonusAlarmSequenceId, sonusAlarmTime, 
                      sonusAlarmDescription, sonusRecorderIpAddressV6, 
                      sonusRecorderPortNum, sonusRecCallGCID, 
                      sonusRecorderTrunkName, sonusRecordingCallLeg }
    STATUS          current
    DESCRIPTION     
            "This trap indicates that recording request is rejected due to the unavailability of the recording server"
    ::= { sonusSipSignallingMIBNotificationsPrefix 44 }

sonusSbxSIPRecLicenseNotAvailable NOTIFICATION-TYPE
    OBJECTS         { sonusAlarmNodeID, sonusAlarmLevel, 
                      sonusAlarmSequenceId, sonusAlarmTime, 
                      sonusAlarmDescription }
    STATUS          current
    DESCRIPTION     
            "The License is not enabled for SIPRec Feature"
    ::= { sonusSipSignallingMIBNotificationsPrefix 45 }

sonusSbxSuppressNonRouteInviteResponseNotification NOTIFICATION-TYPE
    OBJECTS         { sonusAlarmNodeID, sonusAlarmLevel, 
                      sonusAlarmSequenceId, sonusAlarmTime, 
                      sonusAlarmDescription, 
                      sonusNonRouteInviteRequestUri, 
                      sonusNonRouteInviteSourceIpAddress, 
                      sonusNonRouteInviteSourceIpPortNum }
    STATUS          current
    DESCRIPTION     
            "Non-routed incoming invite has been silently dropped."
    ::= { sonusSipSignallingMIBNotificationsPrefix 46 }

sonusSbxTgAuthenticationClearNotification NOTIFICATION-TYPE
    OBJECTS         { sonusAlarmNodeID, sonusAlarmLevel, 
                      sonusAlarmSequenceId, sonusAlarmTime, 
                      sonusAlarmDescription, sonusTgTrunkGroupName }
    STATUS          current
    DESCRIPTION     
            "This trap indicates that IPTG authentication on the trunkgroup succeeded"
    ::= { sonusSipSignallingMIBNotificationsPrefix 47 }

sonusSbxTgAuthenticationFailedNotification NOTIFICATION-TYPE
    OBJECTS         { sonusAlarmNodeID, sonusAlarmLevel, 
                      sonusAlarmSequenceId, sonusAlarmTime, 
                      sonusAlarmDescription, sonusTgTrunkGroupName }
    STATUS          current
    DESCRIPTION     
            "This trap indicates that authentication on the trunkgroup failed"
    ::= { sonusSipSignallingMIBNotificationsPrefix 48 }

sonusSbxDropSipMessageFromUnknownSourceNotification NOTIFICATION-TYPE
    OBJECTS         { sonusAlarmNodeID, sonusAlarmLevel, 
                      sonusAlarmSequenceId, sonusAlarmTime, 
                      sonusAlarmDescription, 
                      sonusDropSipMsgFromUnknowSrcAddress, 
                      sonusDropSipMsgFromUnknowSrcMsgType }
    STATUS          current
    DESCRIPTION     
            "SIP message from unknown source has been silently dropped."
    ::= { sonusSipSignallingMIBNotificationsPrefix 49 }

sonusSbxSipSignalingPortRangeRegistrationFailedNotification NOTIFICATION-TYPE
    OBJECTS         { sonusAlarmNodeID, sonusAlarmLevel, 
                      sonusAlarmSequenceId, sonusAlarmTime, 
                      sonusAlarmDescription, sonusAddressContextName, 
                      sonusZoneName, sonusRecorderTrunkName }
    STATUS          current
    DESCRIPTION     
            "This trap indicates that registration is rejected due to the unavailability of the ports."
    ::= { sonusSipSignallingMIBNotificationsPrefix 50 }

sonusSbxIceStunMsgValidationFailNotification NOTIFICATION-TYPE
    OBJECTS         { sonusAlarmNodeID, sonusAlarmLevel, 
                      sonusAlarmSequenceId, sonusAlarmTime, 
                      sonusAlarmDescription, sonusSipIceGcid, 
                      sonusSipIceRemoteIpAddress, sonusSipIceRemotePort, 
                      sonusSipIceLocalIpAddress, sonusSipIceLocalPort, 
                      sonusSipIceFailReason }
    STATUS          current
    DESCRIPTION     
            "This trap indicates that validation has failed for the first
             STUN messages for that call leg, indicating failure reason"
    ::= { sonusSipSignallingMIBNotificationsPrefix 51 }

sonusSbxDialogTransparencyMisConfiguredNotification NOTIFICATION-TYPE
    OBJECTS         { sonusAlarmNodeID, sonusAlarmLevel, 
                      sonusAlarmSequenceId, sonusAlarmTime, 
                      sonusAlarmDescription, sonusZoneName }
    STATUS          current
    DESCRIPTION     
            "This Trap is generated when one of ingress or egress dialog transparency flag is enabled and not both."
    ::= { sonusSipSignallingMIBNotificationsPrefix 52 }

sonusSbxSubscriptionToRegEventPackageFailedNotification NOTIFICATION-TYPE
    OBJECTS         { sonusAlarmNodeID, sonusAlarmLevel, 
                      sonusAlarmSequenceId, sonusAlarmTime, 
                      sonusAlarmDescription, sonusSubscriptionId }
    STATUS          current
    DESCRIPTION     
            "This trap indicates that the subscription to reg-event package failed"
    ::= { sonusSipSignallingMIBNotificationsPrefix 53 }

sonusEmergencyMessageRejectedNotification NOTIFICATION-TYPE
    OBJECTS         { sonusAlarmNodeID, sonusAlarmLevel, 
                      sonusAlarmSequenceId, sonusAlarmTime, 
                      sonusAlarmDescription, 
                      sonusEmergencyMessageRejected, sonusRPHNamespace, 
                      sonusRPHPriority, sonusPrefixedNumber, 
                      sonusZoneIdName, sonusTrunkGroupName, 
                      sonusPolicerName }
    STATUS          obsolete
    DESCRIPTION     
            "This trap indicates that Non-Invite OOD emergency message is rejected"
    ::= { sonusSipSignallingMIBNotificationsPrefix 54 }

sonusSbxIceTimerExpiryNotification NOTIFICATION-TYPE
    OBJECTS         { sonusAlarmNodeID, sonusAlarmLevel, 
                      sonusAlarmSequenceId, sonusAlarmTime, 
                      sonusAlarmDescription, sonusSipIceGcid, 
                      sonusSipIceLocalIpAddress, sonusSipIceLocalPort, 
                      sonusSipIceFailReason }
    STATUS          current
    DESCRIPTION     
            "This trap indicates that timer expired for waiting stun request/response
             for that call leg, indicating failure reason"
    ::= { sonusSipSignallingMIBNotificationsPrefix 55 }

sonusSbxIceStunMsgValidationFailNotificationV6 NOTIFICATION-TYPE
    OBJECTS         { sonusAlarmNodeID, sonusAlarmLevel, 
                      sonusAlarmSequenceId, sonusAlarmTime, 
                      sonusAlarmDescription, sonusSipIceGcid, 
                      sonusSipIceRemoteIpV6Address, 
                      sonusSipIceRemotePort, sonusSipIceLocalIpV6Address, 
                      sonusSipIceLocalPort, sonusSipIceFailReason }
    STATUS          current
    DESCRIPTION     
            "This trap indicates that validation has failed for the first
             STUN messages for that call leg, indicating failure reason"
    ::= { sonusSipSignallingMIBNotificationsPrefix 56 }

sonusSbxIceTimerExpiryNotificationV6 NOTIFICATION-TYPE
    OBJECTS         { sonusAlarmNodeID, sonusAlarmLevel, 
                      sonusAlarmSequenceId, sonusAlarmTime, 
                      sonusAlarmDescription, sonusSipIceGcid, 
                      sonusSipIceLocalIpV6Address, sonusSipIceLocalPort, 
                      sonusSipIceFailReason }
    STATUS          current
    DESCRIPTION     
            "This trap indicates that timer expired for waiting stun request/response
             for that call leg, indicating failure reason"
    ::= { sonusSipSignallingMIBNotificationsPrefix 57 }

sonusEmergencyMessageRejectNotification NOTIFICATION-TYPE
    OBJECTS         { sonusAlarmNodeID, sonusAlarmLevel, 
                      sonusAlarmSequenceId, sonusAlarmTime, 
                      sonusAlarmDescription, 
                      sonusEmergencyMessageRejected, sonusRPHNamespace, 
                      sonusRPHPriority, sonusPrefixedNumber, 
                      sonusZoneIdName, sonusTrunkGroupName, 
                      sonusPolicerName }
    STATUS          current
    DESCRIPTION     
            "This trap indicates that Non-Invite OOD emergency message is rejected"
    ::= { sonusSipSignallingMIBNotificationsPrefix 58 }

sonusSbxSipRecSrsSelectionFailedNotification NOTIFICATION-TYPE
    OBJECTS         { sonusAlarmNodeID, sonusAlarmLevel, 
                      sonusAlarmSequenceId, sonusAlarmTime, 
                      sonusAlarmDescription, sonusRecCallGCID, 
                      sonusRecorderTrunkName, sonusRecordingCallLeg, 
                      sonusRecNumStreamsConfigured, 
                      sonusRecInitFailureReason }
    STATUS          current
    DESCRIPTION     
            "This trap indicates that SIPRec recording initiation failed"
    ::= { sonusSipSignallingMIBNotificationsPrefix 59 }

sonusSbxSiprecLicenseUnavailableNotification NOTIFICATION-TYPE
    OBJECTS         { sonusAlarmNodeID, sonusAlarmLevel, 
                      sonusAlarmSequenceId, sonusAlarmTime, 
                      sonusAlarmDescription, sonusRecorderIpAddress, 
                      sonusRecorderPortNum, sonusRecCallGCID, 
                      sonusRecorderTrunkName, sonusRecordingCallLeg }
    STATUS          current
    DESCRIPTION     
            "This trap indicates that SIPRec recording failed due to lack of license"
    ::= { sonusSipSignallingMIBNotificationsPrefix 60 }

sonusSbxPDCSLicenseUnavailableNotification NOTIFICATION-TYPE
    OBJECTS         { sonusAlarmNodeID, sonusAlarmLevel, 
                      sonusAlarmSequenceId, sonusAlarmTime, 
                      sonusAlarmDescription, sonusRecCallGCID }
    STATUS          current
    DESCRIPTION     
            "This trap indicates that PDCS header interception failed due to lack of license"
    ::= { sonusSipSignallingMIBNotificationsPrefix 61 }

sonusSbxSipSmMonServerTcpConnFailureNotification NOTIFICATION-TYPE
    OBJECTS         { sonusAlarmNodeID, sonusAlarmLevel, 
                      sonusAlarmSequenceId, sonusAlarmTime, 
                      sonusAlarmDescription, sonusMonIpAddress, 
                      sonusMonPortNum }
    STATUS          current
    DESCRIPTION     
            "This trap indicates that TCP connection towards monitoring server failed"
    ::= { sonusSipSignallingMIBNotificationsPrefix 62 }

sonusSbxSipSmMonServerTcpConnFailureNotificationV6 NOTIFICATION-TYPE
    OBJECTS         { sonusAlarmNodeID, sonusAlarmLevel, 
                      sonusAlarmSequenceId, sonusAlarmTime, 
                      sonusAlarmDescription, sonusMonIpAddressV6, 
                      sonusMonPortNum }
    STATUS          current
    DESCRIPTION     
            "This trap indicates that TCP connection towards monitoring server failed"
    ::= { sonusSipSignallingMIBNotificationsPrefix 63 }

sonusSbxLocalSurvivabilityModeActiveNotification NOTIFICATION-TYPE
    OBJECTS         { sonusAlarmNodeID, sonusAlarmLevel, 
                      sonusAlarmSequenceId, sonusAlarmTime, 
                      sonusAlarmDescription, 
                      sonusSipArsStatEndpointIpAddress, 
                      sonusSipArsStatEndpointIpPortNum, 
                      sonusSipArsStatSigZoneId, 
                      sonusSipArsStatSigPortNum }
    STATUS          current
    DESCRIPTION     
            "This trap indicates that local survivability mode is active for a SIP server 
             of the specified ip address, port, sig zone"
    ::= { sonusSipSignallingMIBNotificationsPrefix 64 }

sonusSbxLocalSurvivabilityModeActiveNotificationV6 NOTIFICATION-TYPE
    OBJECTS         { sonusAlarmNodeID, sonusAlarmLevel, 
                      sonusAlarmSequenceId, sonusAlarmTime, 
                      sonusAlarmDescription, 
                      sonusSipArsStatEndpointIpAddressV6, 
                      sonusSipArsStatEndpointIpPortNum, 
                      sonusSipArsStatSigZoneId, 
                      sonusSipArsStatSigPortNum }
    STATUS          current
    DESCRIPTION     
            "This trap indicates that local survivability mode is active for a SIP server 
             of the specified V6 ip address, port, sig zone"
    ::= { sonusSipSignallingMIBNotificationsPrefix 65 }

sonusSbxLocalSurvivabilityModeClearNotification NOTIFICATION-TYPE
    OBJECTS         { sonusAlarmNodeID, sonusAlarmLevel, 
                      sonusAlarmSequenceId, sonusAlarmTime, 
                      sonusAlarmDescription, 
                      sonusSipArsStatEndpointIpAddress, 
                      sonusSipArsStatEndpointIpPortNum, 
                      sonusSipArsStatSigZoneId, 
                      sonusSipArsStatSigPortNum }
    STATUS          current
    DESCRIPTION     
            "This trap indicates that local survivability mode is cleared for a SIP server 
             of the specified ip address, port, sig zone"
    ::= { sonusSipSignallingMIBNotificationsPrefix 66 }

sonusSbxLocalSurvivabilityModeClearNotificationV6 NOTIFICATION-TYPE
    OBJECTS         { sonusAlarmNodeID, sonusAlarmLevel, 
                      sonusAlarmSequenceId, sonusAlarmTime, 
                      sonusAlarmDescription, 
                      sonusSipArsStatEndpointIpAddressV6, 
                      sonusSipArsStatEndpointIpPortNum, 
                      sonusSipArsStatSigZoneId, 
                      sonusSipArsStatSigPortNum }
    STATUS          current
    DESCRIPTION     
            "This trap indicates that local survivability mode is cleared for a SIP server 
             of the specified V6 ip address, port, sig zone"
    ::= { sonusSipSignallingMIBNotificationsPrefix 67 }

sonusSbxSipSmDropLargeSipPduOverUdpNotification NOTIFICATION-TYPE
    OBJECTS         { sonusAlarmNodeID, sonusAlarmLevel, 
                      sonusAlarmSequenceId, sonusAlarmTime, 
                      sonusAlarmDescription, sonusMonIpAddress, 
                      sonusMonPortNum }
    STATUS          current
    DESCRIPTION     
            "This trap indicates that we drop large sip pdu over UDP."
    ::= { sonusSipSignallingMIBNotificationsPrefix 68 }

sonusSbxSipSmDropLargeSipPduOverUdpNotificationV6 NOTIFICATION-TYPE
    OBJECTS         { sonusAlarmNodeID, sonusAlarmLevel, 
                      sonusAlarmSequenceId, sonusAlarmTime, 
                      sonusAlarmDescription, sonusMonIpAddressV6, 
                      sonusMonPortNum }
    STATUS          current
    DESCRIPTION     
            "This trap indicates that we drop large sip pdu over UDP."
    ::= { sonusSipSignallingMIBNotificationsPrefix 69 }

sonusSbxLbsLocalNodeIsLeaderLackOfCommuncationNotification NOTIFICATION-TYPE
    OBJECTS         { sonusAlarmNodeID, sonusAlarmLevel, 
                      sonusAlarmSequenceId, sonusAlarmTime, 
                      sonusAlarmDescription, sonusMsbcIpAddress }
    STATUS          current
    DESCRIPTION     
            "This trap indicates that Local Node Elected as Leader due to lack of communication with other instances in a cluster."
    ::= { sonusSipSignallingMIBNotificationsPrefix 70 }

sonusSbxLbsLocalNodeIsLeaderLackOfCommuncationNotificationV6 NOTIFICATION-TYPE
    OBJECTS         { sonusAlarmNodeID, sonusAlarmLevel, 
                      sonusAlarmSequenceId, sonusAlarmTime, 
                      sonusAlarmDescription, sonusMsbcIpAddressV6 }
    STATUS          current
    DESCRIPTION     
            "This trap indicates that Local Node Elected as Leader due to lack of communication with other instances in a cluster."
    ::= { sonusSipSignallingMIBNotificationsPrefix 71 }

sonusSbxArsEndPointBlacklistedNotification2 NOTIFICATION-TYPE
    OBJECTS         { sonusAlarmNodeID, sonusAlarmLevel, 
                      sonusAlarmSequenceId, sonusAlarmTime, 
                      sonusAlarmDescription, 
                      sonusSipArsStatEndpointIpAddress, 
                      sonusSipArsStatEndpointIpPortNum, 
                      sonusSipArsStatSigZoneId, 
                      sonusSipArsStatSigPortNum, 
                      sonusSipArsStatEndpointOwnerId, 
                      sonusSipArsStatSigZoneName }
    STATUS          current
    DESCRIPTION     
            "This trap indicates that  one SIP endpoint of the
             specified ip address, port, sig zone has been blacklisted
             by the ARS service. This indicates the endpoint is unreachable"
    ::= { sonusSipSignallingMIBNotificationsPrefix 72 }

sonusSbxArsEndPointRecoveredNotification2 NOTIFICATION-TYPE
    OBJECTS         { sonusAlarmNodeID, sonusAlarmLevel, 
                      sonusAlarmSequenceId, sonusAlarmTime, 
                      sonusAlarmDescription, 
                      sonusSipArsStatEndpointIpAddress, 
                      sonusSipArsStatEndpointIpPortNum, 
                      sonusSipArsStatSigZoneId, 
                      sonusSipArsStatSigPortNum, 
                      sonusSipArsStatEndpointOwnerId, 
                      sonusSipArsStatSigZoneName }
    STATUS          current
    DESCRIPTION     
            "This trap indicates that  one SIP endpoint of the specified ip address,
             port, sig zone has been recovered from  blacklisting by the ARS service.
             This indicates the endpoint is now reachable"
    ::= { sonusSipSignallingMIBNotificationsPrefix 73 }

sonusSbxArsEndPointsRecoveredNotification2 NOTIFICATION-TYPE
    OBJECTS         { sonusAlarmNodeID, sonusAlarmLevel, 
                      sonusAlarmSequenceId, sonusAlarmTime, 
                      sonusAlarmDescription, sonusSipArsStatSigZoneId, 
                      sonusSipArsEndpointRecoveryAll, 
                      sonusSipArsStatSigZoneName }
    STATUS          current
    DESCRIPTION     
            "This trap indicates that  all SIP endpoints in the specified zone,
             OR all the zones has been recovered from  blacklisting by the ARS service.
             This indicates these endpoints are  now reachable"
    ::= { sonusSipSignallingMIBNotificationsPrefix 74 }

sonusSbxArsEndPointBlacklistedNotification2V6 NOTIFICATION-TYPE
    OBJECTS         { sonusAlarmNodeID, sonusAlarmLevel, 
                      sonusAlarmSequenceId, sonusAlarmTime, 
                      sonusAlarmDescription, 
                      sonusSipArsStatEndpointIpAddressV6, 
                      sonusSipArsStatEndpointIpPortNum, 
                      sonusSipArsStatSigZoneId, 
                      sonusSipArsStatSigPortNum, 
                      sonusSipArsStatEndpointOwnerId, 
                      sonusSipArsStatSigZoneName }
    STATUS          current
    DESCRIPTION     
            "This trap indicates that  one SIP endpoint of the
             specified ip address, port, sig zone has been blacklisted
             by the ARS service. This indicates the endpoint is unreachable"
    ::= { sonusSipSignallingMIBNotificationsPrefix 75 }

sonusSbxArsEndPointRecoveredNotification2V6 NOTIFICATION-TYPE
    OBJECTS         { sonusAlarmNodeID, sonusAlarmLevel, 
                      sonusAlarmSequenceId, sonusAlarmTime, 
                      sonusAlarmDescription, 
                      sonusSipArsStatEndpointIpAddressV6, 
                      sonusSipArsStatEndpointIpPortNum, 
                      sonusSipArsStatSigZoneId, 
                      sonusSipArsStatSigPortNum, 
                      sonusSipArsStatEndpointOwnerId, 
                      sonusSipArsStatSigZoneName }
    STATUS          current
    DESCRIPTION     
            "This trap indicates that  one SIP endpoint of the specified ip address,
             port, sig zone has been recovered from  blacklisting by the ARS service.
             This indicates the endpoint is now reachable"
    ::= { sonusSipSignallingMIBNotificationsPrefix 76 }

sonusSbxPathCheckPingStateUpNotification2 NOTIFICATION-TYPE
    OBJECTS         { sonusAlarmNodeID, sonusAlarmLevel, 
                      sonusAlarmSequenceId, sonusAlarmTime, 
                      sonusAlarmDescription, sonusPingPeerIpAddress, 
                      sonusPingPeerPortNum, sonusPingPeerZoneId, 
                      sonusPingPeerZoneName, sonusPingPeerName }
    STATUS          current
    DESCRIPTION     
            "This trap indicates that the peer's ping state is up."
    ::= { sonusSipSignallingMIBNotificationsPrefix 77 }

sonusSbxPathCheckPingStateDownNotification2 NOTIFICATION-TYPE
    OBJECTS         { sonusAlarmNodeID, sonusAlarmLevel, 
                      sonusAlarmSequenceId, sonusAlarmTime, 
                      sonusAlarmDescription, sonusPingPeerIpAddress, 
                      sonusPingPeerPortNum, sonusPingPeerZoneId, 
                      sonusPingPeerZoneName, sonusPingPeerName }
    STATUS          current
    DESCRIPTION     
            "This trap indicates that the peer's ping state is down."
    ::= { sonusSipSignallingMIBNotificationsPrefix 78 }

sonusSbxPathCheckRemoteAdminStateUpNotification2 NOTIFICATION-TYPE
    OBJECTS         { sonusAlarmNodeID, sonusAlarmLevel, 
                      sonusAlarmSequenceId, sonusAlarmTime, 
                      sonusAlarmDescription, sonusPingPeerIpAddress, 
                      sonusPingPeerPortNum, sonusPingPeerZoneId, 
                      sonusPingPeerZoneName, sonusPingPeerName }
    STATUS          current
    DESCRIPTION     
            "This trap indicates that the peer's remote admin state is up."
    ::= { sonusSipSignallingMIBNotificationsPrefix 79 }

sonusSbxPathCheckRemoteAdminStateDownNotification2 NOTIFICATION-TYPE
    OBJECTS         { sonusAlarmNodeID, sonusAlarmLevel, 
                      sonusAlarmSequenceId, sonusAlarmTime, 
                      sonusAlarmDescription, sonusPingPeerIpAddress, 
                      sonusPingPeerPortNum, sonusPingPeerZoneId, 
                      sonusPingPeerZoneName, sonusPingPeerName }
    STATUS          current
    DESCRIPTION     
            "This trap indicates that the peer's remote admin state is down."
    ::= { sonusSipSignallingMIBNotificationsPrefix 80 }

sonusSbxPathCheckLocalAdminStateUpNotification2 NOTIFICATION-TYPE
    OBJECTS         { sonusAlarmNodeID, sonusAlarmLevel, 
                      sonusAlarmSequenceId, sonusAlarmTime, 
                      sonusAlarmDescription, sonusPingPeerIpAddress, 
                      sonusPingPeerPortNum, sonusPingPeerZoneId, 
                      sonusPingPeerZoneName, sonusPingPeerName }
    STATUS          current
    DESCRIPTION     
            "This trap indicates that the peer's local admin state is up."
    ::= { sonusSipSignallingMIBNotificationsPrefix 81 }

sonusSbxPathCheckLocalAdminStateDownNotification2 NOTIFICATION-TYPE
    OBJECTS         { sonusAlarmNodeID, sonusAlarmLevel, 
                      sonusAlarmSequenceId, sonusAlarmTime, 
                      sonusAlarmDescription, sonusPingPeerIpAddress, 
                      sonusPingPeerPortNum, sonusPingPeerZoneId, 
                      sonusPingPeerZoneName, sonusPingPeerName }
    STATUS          current
    DESCRIPTION     
            "This trap indicates that the peer's local admin state is down."
    ::= { sonusSipSignallingMIBNotificationsPrefix 82 }

sonusSbxPathCheckLocalAdminStateUpNotification2V6 NOTIFICATION-TYPE
    OBJECTS         { sonusAlarmNodeID, sonusAlarmLevel, 
                      sonusAlarmSequenceId, sonusAlarmTime, 
                      sonusAlarmDescription, sonusPingPeerIpAddressV6, 
                      sonusPingPeerPortNum, sonusPingPeerZoneId, 
                      sonusPingPeerZoneName, sonusPingPeerName }
    STATUS          current
    DESCRIPTION     
            "This trap indicates that the peer's local admin state is up."
    ::= { sonusSipSignallingMIBNotificationsPrefix 83 }

sonusSbxPathCheckLocalAdminStateDownNotification2V6 NOTIFICATION-TYPE
    OBJECTS         { sonusAlarmNodeID, sonusAlarmLevel, 
                      sonusAlarmSequenceId, sonusAlarmTime, 
                      sonusAlarmDescription, sonusPingPeerIpAddressV6, 
                      sonusPingPeerPortNum, sonusPingPeerZoneId, 
                      sonusPingPeerZoneName, sonusPingPeerName }
    STATUS          current
    DESCRIPTION     
            "This trap indicates that the peer's local admin state is down."
    ::= { sonusSipSignallingMIBNotificationsPrefix 84 }

sonusSbxPathCheckPingStateUpNotification2V6 NOTIFICATION-TYPE
    OBJECTS         { sonusAlarmNodeID, sonusAlarmLevel, 
                      sonusAlarmSequenceId, sonusAlarmTime, 
                      sonusAlarmDescription, sonusPingPeerIpAddressV6, 
                      sonusPingPeerPortNum, sonusPingPeerZoneId, 
                      sonusPingPeerZoneName, sonusPingPeerName }
    STATUS          current
    DESCRIPTION     
            "This trap indicates that the peer's ping state is up."
    ::= { sonusSipSignallingMIBNotificationsPrefix 85 }

sonusSbxPathCheckPingStateDownNotification2V6 NOTIFICATION-TYPE
    OBJECTS         { sonusAlarmNodeID, sonusAlarmLevel, 
                      sonusAlarmSequenceId, sonusAlarmTime, 
                      sonusAlarmDescription, sonusPingPeerIpAddressV6, 
                      sonusPingPeerPortNum, sonusPingPeerZoneId, 
                      sonusPingPeerZoneName, sonusPingPeerName }
    STATUS          current
    DESCRIPTION     
            "This trap indicates that the peer's ping state is down."
    ::= { sonusSipSignallingMIBNotificationsPrefix 86 }

sonusSbxPathCheckRemoteAdminStateUpNotification2V6 NOTIFICATION-TYPE
    OBJECTS         { sonusAlarmNodeID, sonusAlarmLevel, 
                      sonusAlarmSequenceId, sonusAlarmTime, 
                      sonusAlarmDescription, sonusPingPeerIpAddressV6, 
                      sonusPingPeerPortNum, sonusPingPeerZoneId, 
                      sonusPingPeerZoneName, sonusPingPeerName }
    STATUS          current
    DESCRIPTION     
            "This trap indicates that the peer's remote admin state is up."
    ::= { sonusSipSignallingMIBNotificationsPrefix 87 }

sonusSbxPathCheckRemoteAdminStateDownNotification2V6 NOTIFICATION-TYPE
    OBJECTS         { sonusAlarmNodeID, sonusAlarmLevel, 
                      sonusAlarmSequenceId, sonusAlarmTime, 
                      sonusAlarmDescription, sonusPingPeerIpAddressV6, 
                      sonusPingPeerPortNum, sonusPingPeerZoneId, 
                      sonusPingPeerZoneName, sonusPingPeerName }
    STATUS          current
    DESCRIPTION     
            "This trap indicates that the peer's remote admin state is down."
    ::= { sonusSipSignallingMIBNotificationsPrefix 88 }

sonusSbxPathCheckFqdnPeerUpNotification2 NOTIFICATION-TYPE
    OBJECTS         { sonusAlarmNodeID, sonusAlarmLevel, 
                      sonusAlarmSequenceId, sonusAlarmTime, 
                      sonusAlarmDescription, sonusPingPeerFqdn, 
                      sonusPingPeerPortNum, sonusPingPeerZoneId, 
                      sonusPingPeerZoneName, sonusPingPeerName }
    STATUS          current
    DESCRIPTION     
            "This trap indicates that the specified SIP peer is available to receive calls."
    ::= { sonusSipSignallingMIBNotificationsPrefix 89 }

sonusSbxPathCheckFqdnPeerDownNotification2 NOTIFICATION-TYPE
    OBJECTS         { sonusAlarmNodeID, sonusAlarmLevel, 
                      sonusAlarmSequenceId, sonusAlarmTime, 
                      sonusAlarmDescription, sonusPingPeerFqdn, 
                      sonusPingPeerPortNum, sonusPingPeerZoneId, 
                      sonusPingPeerZoneName, sonusPingPeerName }
    STATUS          current
    DESCRIPTION     
            "This trap indicates that the specified SIP peer is unavailable to receive calls."
    ::= { sonusSipSignallingMIBNotificationsPrefix 90 }

sonusSbxPathCheckFqdnPeerIpEndpointUpNotification2 NOTIFICATION-TYPE
    OBJECTS         { sonusAlarmNodeID, sonusAlarmLevel, 
                      sonusAlarmSequenceId, sonusAlarmTime, 
                      sonusAlarmDescription, sonusPingPeerIpAddress, 
                      sonusPingPeerPortNum, sonusPingPeerFqdn, 
                      sonusPingPeerZoneId, sonusPingPeerZoneName, 
                      sonusPingPeerName }
    STATUS          current
    DESCRIPTION     
            "This trap indicates that the specified IP end-point belonging to the SIP Peer is 
             available to receive calls."
    ::= { sonusSipSignallingMIBNotificationsPrefix 91 }

sonusSbxPathCheckFqdnPeerIpEndpointDownNotification2 NOTIFICATION-TYPE
    OBJECTS         { sonusAlarmNodeID, sonusAlarmLevel, 
                      sonusAlarmSequenceId, sonusAlarmTime, 
                      sonusAlarmDescription, sonusPingPeerIpAddress, 
                      sonusPingPeerPortNum, sonusPingPeerFqdn, 
                      sonusPingPeerZoneId, sonusPingPeerZoneName, 
                      sonusPingPeerName }
    STATUS          current
    DESCRIPTION     
            "This trap indicates that the specified IP end-point belonging to the SIP Peer is 
             unavailable to receive calls."
    ::= { sonusSipSignallingMIBNotificationsPrefix 92 }

sonusSbxPathCheckFqdnPeerIpV6EndpointUpNotification2 NOTIFICATION-TYPE
    OBJECTS         { sonusAlarmNodeID, sonusAlarmLevel, 
                      sonusAlarmSequenceId, sonusAlarmTime, 
                      sonusAlarmDescription, sonusPingPeerIpAddressV6, 
                      sonusPingPeerPortNum, sonusPingPeerFqdn, 
                      sonusPingPeerZoneId, sonusPingPeerZoneName, 
                      sonusPingPeerName }
    STATUS          current
    DESCRIPTION     
            "This trap indicates that the specified IPV6 end-point belonging to the SIP Peer is 
             available to receive calls."
    ::= { sonusSipSignallingMIBNotificationsPrefix 93 }

sonusSbxPathCheckFqdnPeerIpV6EndpointDownNotification2 NOTIFICATION-TYPE
    OBJECTS         { sonusAlarmNodeID, sonusAlarmLevel, 
                      sonusAlarmSequenceId, sonusAlarmTime, 
                      sonusAlarmDescription, sonusPingPeerIpAddressV6, 
                      sonusPingPeerPortNum, sonusPingPeerFqdn, 
                      sonusPingPeerZoneId, sonusPingPeerZoneName, 
                      sonusPingPeerName }
    STATUS          current
    DESCRIPTION     
            "This trap indicates that the specified IPV6 end-point belonging to the SIP Peer is 
             unavailable to receive calls."
    ::= { sonusSipSignallingMIBNotificationsPrefix 94 }

sonusSbxH323TrunkGroupInServiceNotification NOTIFICATION-TYPE
    OBJECTS         { sonusAlarmNodeID, sonusAlarmLevel, 
                      sonusAlarmSequenceId, sonusAlarmTime, 
                      sonusAlarmDescription, sonusH323TrunkGrpName }
    STATUS          current
    DESCRIPTION     
            "This trap indicates that the H323 Trunk Group was put
             into service by maintenance staff."
    ::= { sonusH323SignallingMIBNotificationsPrefix 1 }

sonusSbxH323TrunkGroupOutOfServiceNotification NOTIFICATION-TYPE
    OBJECTS         { sonusAlarmNodeID, sonusAlarmLevel, 
                      sonusAlarmSequenceId, sonusAlarmTime, 
                      sonusAlarmDescription, sonusH323TrunkGrpName }
    STATUS          current
    DESCRIPTION     
            "This trap indicates that the H323 Trunk Group was taken
             out of service by maintenance staff."
    ::= { sonusH323SignallingMIBNotificationsPrefix 2 }

sonusSbxSscsRouteFailureWithoutGapNotification NOTIFICATION-TYPE
    OBJECTS         { sonusAlarmNodeID, sonusAlarmLevel, 
                      sonusAlarmSequenceId, sonusAlarmTime, 
                      sonusAlarmDescription, sonusH323TrunkGrpName, 
                      sonusPscsPolicyServerName, 
                      sonusPscsRouteFailureReason, sonusPscsCalledNumber, 
                      sonusPscsCallingNumber, sonusPscsCarrierCode }
    STATUS          deprecated
    DESCRIPTION     
            "This trap has been replaced by sonusSbxSscsRouteFailureWithoutGapNotification2."
    ::= { sonusSoftswitchClientServicesMIBNotificationsPrefix 1 }

sonusSbxSscsRouteFailureNotification NOTIFICATION-TYPE
    OBJECTS         { sonusAlarmNodeID, sonusAlarmLevel, 
                      sonusAlarmSequenceId, sonusAlarmTime, 
                      sonusAlarmDescription, sonusPscsPolicyServerName, 
                      sonusPscsRouteFailureReason, sonusPscsCalledNumber, 
                      sonusPscsCallingNumber, sonusPscsCarrierCode, 
                      sonusPscsGapNumber }
    STATUS          current
    DESCRIPTION     
            "This trap indicates a route look up has failed."
    ::= { sonusSoftswitchClientServicesMIBNotificationsPrefix 2 }

sonusSbxSscsTransErrorNotification NOTIFICATION-TYPE
    OBJECTS         { sonusAlarmNodeID, sonusAlarmLevel, 
                      sonusAlarmSequenceId, sonusAlarmTime, 
                      sonusAlarmDescription, sonusPscsPolicyServerName, 
                      sonusPscsTranErrorReason }
    STATUS          current
    DESCRIPTION     
            "This trap indicates a softswitch has a transaction error."
    ::= { sonusSoftswitchClientServicesMIBNotificationsPrefix 3 }

sonusSbxSscsRejectIndNotification NOTIFICATION-TYPE
    OBJECTS         { sonusAlarmNodeID, sonusAlarmLevel, 
                      sonusAlarmSequenceId, sonusAlarmTime, 
                      sonusAlarmDescription, sonusPscsPolicyServerName, 
                      sonusPscsRejectIndReason }
    STATUS          current
    DESCRIPTION     
            "This trap indicates a reject indication has been received."
    ::= { sonusSoftswitchClientServicesMIBNotificationsPrefix 4 }

sonusSbxSscsOutOfServiceNotification NOTIFICATION-TYPE
    OBJECTS         { sonusAlarmNodeID, sonusAlarmLevel, 
                      sonusAlarmSequenceId, sonusAlarmTime, 
                      sonusAlarmDescription, sonusPscsPolicyServerName, 
                      sonusPscsOutOfServiceReason }
    STATUS          current
    DESCRIPTION     
            "This trap indicates a softswitch is now out of service."
    ::= { sonusSoftswitchClientServicesMIBNotificationsPrefix 5 }

sonusSbxSscsInServiceNotification NOTIFICATION-TYPE
    OBJECTS         { sonusAlarmNodeID, sonusAlarmLevel, 
                      sonusAlarmSequenceId, sonusAlarmTime, 
                      sonusAlarmDescription, sonusPscsPolicyServerName, 
                      sonusPscsOperState, sonusPscsInServiceReason }
    STATUS          current
    DESCRIPTION     
            "This trap indicates a softswitch is now in service"
    ::= { sonusSoftswitchClientServicesMIBNotificationsPrefix 6 }

sonusSbxSscsRouteFailureWithoutGapNotification2 NOTIFICATION-TYPE
    OBJECTS         { sonusAlarmNodeID, sonusAlarmLevel, 
                      sonusAlarmSequenceId, sonusAlarmTime, 
                      sonusAlarmDescription, sonusPscsPolicyServerName, 
                      sonusPscsRouteFailureReason, sonusPscsCalledNumber, 
                      sonusPscsCallingNumber, sonusPscsCarrierCode }
    STATUS          current
    DESCRIPTION     
            "This trap indicates a route look up has failed with out GAP."
    ::= { sonusSoftswitchClientServicesMIBNotificationsPrefix 7 }

sonusSbxNodeResourcesCallAdmissionSuspendedNotification NOTIFICATION-TYPE
    OBJECTS         { sonusAlarmNodeID, sonusAlarmLevel, 
                      sonusAlarmSequenceId, sonusAlarmTime, 
                      sonusAlarmDescription, 
                      sonusCallAdmissionChangeReason }
    STATUS          current
    DESCRIPTION     
            "This trap indicates that call admission into the SBC has been
             suspended. Information provided by this trap includes the reason
             why call admission has been suspended."
    ::= { sonusNodeResourcesMIBNotificationsPrefix 1 }

sonusSbxNodeResourcesCallAdmissionEnabledNotification NOTIFICATION-TYPE
    OBJECTS         { sonusAlarmNodeID, sonusAlarmLevel, 
                      sonusAlarmSequenceId, sonusAlarmTime, 
                      sonusAlarmDescription, 
                      sonusCallAdmissionChangeReason }
    STATUS          current
    DESCRIPTION     
            "This trap indicates that call admission into the SBC has been
             enabled. Information provided by this trap includes the reason
             why call admission has been enabled."
    ::= { sonusNodeResourcesMIBNotificationsPrefix 2 }

sonusSbxNodeResourcesCallTraceHitNotification NOTIFICATION-TYPE
    OBJECTS         { sonusAlarmNodeID, sonusAlarmLevel, 
                      sonusAlarmSequenceId, sonusAlarmTime, 
                      sonusAlarmDescription, sonusCallTraceCalledNumber, 
                      sonusCallTraceCallingNumber }
    STATUS          current
    DESCRIPTION     
            "This trap indicates that call trace filter had a hit.
             Information provided by this trap includes the called number
             and the calling number."
    ::= { sonusNodeResourcesMIBNotificationsPrefix 3 }

sonusSbxNodeResourcesCallTraceHitGAPNotification NOTIFICATION-TYPE
    OBJECTS         { sonusAlarmNodeID, sonusAlarmLevel, 
                      sonusAlarmSequenceId, sonusAlarmTime, 
                      sonusAlarmDescription, sonusCallTraceCalledNumber, 
                      sonusCallTraceCallingNumber, 
                      sonusActiveCallOrigCalledNum }
    STATUS          current
    DESCRIPTION     
            "This trap indicates that call trace filter had a hit.
             Information provided by this trap includes the called number,
             the calling number, and the original called number (in GAP)."
    ::= { sonusNodeResourcesMIBNotificationsPrefix 4 }

sonusSbxNodeResEmerCallNoRouteNotification NOTIFICATION-TYPE
    OBJECTS         { sonusAlarmNodeID, sonusAlarmLevel, 
                      sonusAlarmSequenceId, sonusAlarmTime, 
                      sonusAlarmDescription, 
                      sonusActiveCallIngressPstnTrunk, 
                      sonusNodeResourceIsupCircuit, 
                      sonusActiveCallCallingNum, 
                      sonusActiveCallCalledNum, 
                      sonusActiveCallOrigCalledNum }
    STATUS          current
    DESCRIPTION     
            "This trap indicates that an emergency call was placed
             that failed to route."
    ::= { sonusNodeResourcesMIBNotificationsPrefix 5 }

sonusSbxNodeResourcesMaxIpCallLimitSetNotification NOTIFICATION-TYPE
    OBJECTS         { sonusAlarmNodeID, sonusAlarmLevel, 
                      sonusAlarmSequenceId, sonusAlarmTime, 
                      sonusAlarmDescription }
    STATUS          current
    DESCRIPTION     
            "This trap indicates that MAX IP call Limit set."
    ::= { sonusNodeResourcesMIBNotificationsPrefix 6 }

sonusSbxNodeResourcesMaxIpCallLimitClearNotification NOTIFICATION-TYPE
    OBJECTS         { sonusAlarmNodeID, sonusAlarmLevel, 
                      sonusAlarmSequenceId, sonusAlarmTime, 
                      sonusAlarmDescription }
    STATUS          current
    DESCRIPTION     
            "This trap indicates that MAX IP call Limit cleared."
    ::= { sonusNodeResourcesMIBNotificationsPrefix 7 }

sonusSbxNodeResourcesMaxSysCallLimitSetNotification NOTIFICATION-TYPE
    OBJECTS         { sonusAlarmNodeID, sonusAlarmLevel, 
                      sonusAlarmSequenceId, sonusAlarmTime, 
                      sonusAlarmDescription }
    STATUS          current
    DESCRIPTION     
            "This trap indicates that MAX System call limit set."
    ::= { sonusNodeResourcesMIBNotificationsPrefix 8 }

sonusSbxNodeResourcesMaxSysCallLimitClearNotification NOTIFICATION-TYPE
    OBJECTS         { sonusAlarmNodeID, sonusAlarmLevel, 
                      sonusAlarmSequenceId, sonusAlarmTime, 
                      sonusAlarmDescription }
    STATUS          current
    DESCRIPTION     
            "This trap indicates that MAX system call limit cleared."
    ::= { sonusNodeResourcesMIBNotificationsPrefix 9 }

sonusSbxNodeResourcesFeatureKeyStateChangeNotification NOTIFICATION-TYPE
    OBJECTS         { sonusAlarmNodeID, sonusAlarmLevel, 
                      sonusAlarmSequenceId, sonusAlarmTime, 
                      sonusAlarmDescription, sonusFeatureName, 
                      sonusFeatureState }
    STATUS          current
    DESCRIPTION     
            "This trap indicates that there is change in feature key state."
    ::= { sonusNodeResourcesMIBNotificationsPrefix 10 }

sonusSbxCallFailureNoDspExceedThresholdNotification NOTIFICATION-TYPE
    OBJECTS         { sonusAlarmNodeID, sonusAlarmLevel, 
                      sonusAlarmSequenceId, sonusAlarmTime, 
                      sonusAlarmDescription, 
                      sonusNumCallFailureNoDspExceedThreshold }
    STATUS          current
    DESCRIPTION     
            "This trap indicates that number of call failure due to lack of DSP resource exceed the threshold."
    ::= { sonusNodeResourcesMIBNotificationsPrefix 11 }

sonusSbxDspAvailG729OnSetCrossThresholdNotification NOTIFICATION-TYPE
    OBJECTS         { sonusAlarmNodeID, sonusAlarmLevel, 
                      sonusAlarmSequenceId, sonusAlarmTime, 
                      sonusAlarmDescription, 
                      sonusNumDspAvailabilityG729CrossThreshold }
    STATUS          current
    DESCRIPTION     
            "This trap indicates that the Availability of type G729 DSP Cross the threshold downward."
    ::= { sonusNodeResourcesMIBNotificationsPrefix 12 }

sonusSbxDspAvailG726OnSetCrossThresholdNotification NOTIFICATION-TYPE
    OBJECTS         { sonusAlarmNodeID, sonusAlarmLevel, 
                      sonusAlarmSequenceId, sonusAlarmTime, 
                      sonusAlarmDescription, 
                      sonusNumDspAvailabilityG726CrossThreshold }
    STATUS          current
    DESCRIPTION     
            "This trap indicates that the Availability of type G726 DSP Cross the threshold downward."
    ::= { sonusNodeResourcesMIBNotificationsPrefix 13 }

sonusSbxDspAvailG711OnSetCrossThresholdNotification NOTIFICATION-TYPE
    OBJECTS         { sonusAlarmNodeID, sonusAlarmLevel, 
                      sonusAlarmSequenceId, sonusAlarmTime, 
                      sonusAlarmDescription, 
                      sonusNumDspAvailabilityG711PacketCrossThreshold }
    STATUS          current
    DESCRIPTION     
            "This trap indicates that the Availability of type G711 Packet DSP Cross the threshold downward."
    ::= { sonusNodeResourcesMIBNotificationsPrefix 14 }

sonusSbxDspAvailG729AbateCrossThresholdNotification NOTIFICATION-TYPE
    OBJECTS         { sonusAlarmNodeID, sonusAlarmLevel, 
                      sonusAlarmSequenceId, sonusAlarmTime, 
                      sonusAlarmDescription, 
                      sonusNumDspAvailabilityG729CrossThreshold }
    STATUS          current
    DESCRIPTION     
            "This trap indicates that the Availability of type G729 DSP Cross the threshold downward."
    ::= { sonusNodeResourcesMIBNotificationsPrefix 15 }

sonusSbxDspAvailG726AbateCrossThresholdNotification NOTIFICATION-TYPE
    OBJECTS         { sonusAlarmNodeID, sonusAlarmLevel, 
                      sonusAlarmSequenceId, sonusAlarmTime, 
                      sonusAlarmDescription, 
                      sonusNumDspAvailabilityG726CrossThreshold }
    STATUS          current
    DESCRIPTION     
            "This trap indicates that the Availability of type G726 DSP Cross the threshold downward."
    ::= { sonusNodeResourcesMIBNotificationsPrefix 16 }

sonusSbxDspAvailG711PacketAbateCrossThresholdNotification NOTIFICATION-TYPE
    OBJECTS         { sonusAlarmNodeID, sonusAlarmLevel, 
                      sonusAlarmSequenceId, sonusAlarmTime, 
                      sonusAlarmDescription, 
                      sonusNumDspAvailabilityG711PacketCrossThreshold }
    STATUS          current
    DESCRIPTION     
            "This trap indicates that the Availability of type G711 DSP Cross the threshold downward."
    ::= { sonusNodeResourcesMIBNotificationsPrefix 17 }

sonusSbxNodeResourcesPacketLossThresholdExceededNotification NOTIFICATION-TYPE
    OBJECTS         { sonusAlarmNodeID, sonusAlarmLevel, 
                      sonusAlarmSequenceId, sonusAlarmTime, 
                      sonusAlarmDescription, sonusNrmaCallGcid }
    STATUS          current
    DESCRIPTION     
            "This trap indicates that the packet loss has exceeded the threshold level."
    ::= { sonusNodeResourcesMIBNotificationsPrefix 18 }

sonusSbxNodeResourcesPacketLossThresholdClearNotification NOTIFICATION-TYPE
    OBJECTS         { sonusAlarmNodeID, sonusAlarmLevel, 
                      sonusAlarmSequenceId, sonusAlarmTime, 
                      sonusAlarmDescription, sonusNrmaCallGcid }
    STATUS          current
    DESCRIPTION     
            "This trap indicates that the packet loss is below the threshold level."
    ::= { sonusNodeResourcesMIBNotificationsPrefix 19 }

sonusSbxNodeResourcesNoPacketsReceivedNotification NOTIFICATION-TYPE
    OBJECTS         { sonusAlarmNodeID, sonusAlarmLevel, 
                      sonusAlarmSequenceId, sonusAlarmTime, 
                      sonusAlarmDescription, sonusNrmaCallGcid }
    STATUS          current
    DESCRIPTION     
            "This trap indicates that no RTP or RTCP packets were received from peer."
    ::= { sonusNodeResourcesMIBNotificationsPrefix 20 }

sonusSbxNodeResourcesNoPacketsReceivedClearNotification NOTIFICATION-TYPE
    OBJECTS         { sonusAlarmNodeID, sonusAlarmLevel, 
                      sonusAlarmSequenceId, sonusAlarmTime, 
                      sonusAlarmDescription, sonusNrmaCallGcid }
    STATUS          current
    DESCRIPTION     
            "This trap indicates that the peer has resumed sending RTP or RTCP packets."
    ::= { sonusNodeResourcesMIBNotificationsPrefix 21 }

sonusSbxPadThresholdNotification NOTIFICATION-TYPE
    OBJECTS         { sonusAlarmNodeID, sonusAlarmLevel, 
                      sonusAlarmSequenceId, sonusAlarmTime, 
                      sonusAlarmDescription }
    STATUS          current
    DESCRIPTION     
            "This trap indicates that the compression DSP resource usage has crossed the threshold value."
    ::= { sonusNodeResourcesMIBNotificationsPrefix 22 }

sonusSbxPadThresholdNotificationClear NOTIFICATION-TYPE
    OBJECTS         { sonusAlarmNodeID, sonusAlarmLevel, 
                      sonusAlarmSequenceId, sonusAlarmTime, 
                      sonusAlarmDescription }
    STATUS          current
    DESCRIPTION     
            "This trap indicates that the compression DSP resource usage has dropped below the threshold value."
    ::= { sonusNodeResourcesMIBNotificationsPrefix 23 }

sonusSbxMediaProfileDspReconfigurationNotification NOTIFICATION-TYPE
    OBJECTS         { sonusAlarmNodeID, sonusAlarmLevel, 
                      sonusAlarmSequenceId, sonusAlarmTime, 
                      sonusAlarmDescription }
    STATUS          current
    DESCRIPTION     
            "This trap indicates that the mediaProfile config has been modified and DSP reconfiguration initiated and in progress."
    ::= { sonusNodeResourcesMIBNotificationsPrefix 24 }

sonusSbxMediaProfileDspReconfigurationNotificationClear NOTIFICATION-TYPE
    OBJECTS         { sonusAlarmNodeID, sonusAlarmLevel, 
                      sonusAlarmSequenceId, sonusAlarmTime, 
                      sonusAlarmDescription }
    STATUS          current
    DESCRIPTION     
            "This trap indicates that the mediaProfile and DSP reconfiguration is complete."
    ::= { sonusNodeResourcesMIBNotificationsPrefix 25 }

sonusJsrcServerStateUpNotification NOTIFICATION-TYPE
    OBJECTS         { sonusAlarmNodeID, sonusAlarmLevel, 
                      sonusAlarmSequenceId, sonusAlarmTime, 
                      sonusAlarmDescription, sonusJSrcServerName }
    STATUS          current
    DESCRIPTION     
            "This trap indicates that the JSRC Server is up."
    ::= { sonusNodeResourcesMIBNotificationsPrefix 26 }

sonusJsrcServerStateDownNotification NOTIFICATION-TYPE
    OBJECTS         { sonusAlarmNodeID, sonusAlarmLevel, 
                      sonusAlarmSequenceId, sonusAlarmTime, 
                      sonusAlarmDescription, sonusJSrcServerName }
    STATUS          current
    DESCRIPTION     
            "This trap indicates that the JSRC Server is down."
    ::= { sonusNodeResourcesMIBNotificationsPrefix 27 }

sonusSbxNodeMachineCongestionNotification NOTIFICATION-TYPE
    OBJECTS         { sonusAlarmNodeID, sonusAlarmLevel, 
                      sonusAlarmSequenceId, sonusAlarmTime, 
                      sonusAlarmDescription, sonusOverloadLevel }
    STATUS          current
    DESCRIPTION     
            "The sonusSbxNodeMachineCongestionNotification indicates
             SBX Machine congestion level changes."
    ::= { sonusNodeResourcesMIBNotificationsPrefix 28 }

sonusSbxNodeResourceCallTraceDisabledNotification NOTIFICATION-TYPE
    OBJECTS         { sonusAlarmNodeID, sonusAlarmLevel, 
                      sonusAlarmSequenceId, sonusAlarmTime, 
                      sonusAlarmDescription, sonusCallTraceDisableReason }
    STATUS          current
    DESCRIPTION     
            "This trap indicates that call trace is disabled/inactive."
    ::= { sonusNodeResourcesMIBNotificationsPrefix 29 }

sonusSbxNodeResourceCallTraceActiveNotification NOTIFICATION-TYPE
    OBJECTS         { sonusAlarmNodeID, sonusAlarmLevel, 
                      sonusAlarmSequenceId, sonusAlarmTime, 
                      sonusAlarmDescription }
    STATUS          current
    DESCRIPTION     
            "This trap indicates that call trace started."
    ::= { sonusNodeResourcesMIBNotificationsPrefix 30 }

sonusSbxNodeResourcesMaxTcpMediaSessLimitSetNotification NOTIFICATION-TYPE
    OBJECTS         { sonusAlarmNodeID, sonusAlarmLevel, 
                      sonusAlarmSequenceId, sonusAlarmTime, 
                      sonusAlarmDescription }
    STATUS          current
    DESCRIPTION     
            "This trap indicates that TCP media sessions has reached higher threshold."
    ::= { sonusNodeResourcesMIBNotificationsPrefix 31 }

sonusSbxNodeResourcesMaxTcpMediaSessLimitClearNotification NOTIFICATION-TYPE
    OBJECTS         { sonusAlarmNodeID, sonusAlarmLevel, 
                      sonusAlarmSequenceId, sonusAlarmTime, 
                      sonusAlarmDescription }
    STATUS          current
    DESCRIPTION     
            "This trap indicates that the TCP media sessions has dropped below lower threshold."
    ::= { sonusNodeResourcesMIBNotificationsPrefix 32 }

sonusSbxNodeResourcesSysACLLimitNotification NOTIFICATION-TYPE
    OBJECTS         { sonusAlarmNodeID, sonusAlarmLevel, 
                      sonusAlarmSequenceId, sonusAlarmTime, 
                      sonusAlarmDescription }
    STATUS          current
    DESCRIPTION     
            "This trap indicates that there was an error creating system ACL for TCP media session possibly due to reaching maximum ACL limits."
    ::= { sonusNodeResourcesMIBNotificationsPrefix 33 }

sonusSbxNodeResourcesMediaPortRangeExhaustionNotification NOTIFICATION-TYPE
    OBJECTS         { sonusAlarmNodeID, sonusAlarmLevel, 
                      sonusAlarmSequenceId, sonusAlarmTime, 
                      sonusAlarmDescription, sonusTgName }
    STATUS          current
    DESCRIPTION     
            "The media port range has been exhausted."
    ::= { sonusNodeResourcesMIBNotificationsPrefix 34 }

sonusSbxNodeResourcesMediaPortRangeExhaustionClearedNotfication NOTIFICATION-TYPE
    OBJECTS         { sonusAlarmNodeID, sonusAlarmLevel, 
                      sonusAlarmSequenceId, sonusAlarmTime, 
                      sonusAlarmDescription, sonusTgName }
    STATUS          current
    DESCRIPTION     
            "The media port range is no longer exhausted."
    ::= { sonusNodeResourcesMIBNotificationsPrefix 35 }

sonusSbxNodeResourcesTcpPortRangeExhaustionNotification NOTIFICATION-TYPE
    OBJECTS         { sonusAlarmNodeID, sonusAlarmLevel, 
                      sonusAlarmSequenceId, sonusAlarmTime, 
                      sonusAlarmDescription, sonusTgName }
    STATUS          current
    DESCRIPTION     
            "The TCP port range has been exhausted."
    ::= { sonusNodeResourcesMIBNotificationsPrefix 36 }

sonusSbxNodeResourcesTcpPortRangeExhaustionClearedNotification NOTIFICATION-TYPE
    OBJECTS         { sonusAlarmNodeID, sonusAlarmLevel, 
                      sonusAlarmSequenceId, sonusAlarmTime, 
                      sonusAlarmDescription, sonusTgName }
    STATUS          current
    DESCRIPTION     
            "The TCP port range is no longer exhausted."
    ::= { sonusNodeResourcesMIBNotificationsPrefix 37 }

sonusSbxSingleDspReloadAndCoreDumpNotification NOTIFICATION-TYPE
    OBJECTS         { sonusAlarmNodeID, sonusAlarmLevel, 
                      sonusAlarmSequenceId, sonusAlarmTime, 
                      sonusAlarmDescription }
    STATUS          current
    DESCRIPTION     
            "This trap indicates completion of single Dsp Reload and Core-Dump process."
    ::= { sonusNodeResourcesMIBNotificationsPrefix 38 }

sonusSbxNodeMemoryCongestionNotification NOTIFICATION-TYPE
    OBJECTS         { sonusAlarmNodeID, sonusAlarmLevel, 
                      sonusAlarmSequenceId, sonusAlarmTime, 
                      sonusAlarmDescription, sonusCallCount, 
                      sonusRegCount, sonusRelayCount }
    STATUS          current
    DESCRIPTION     
            "This trap indicates that the machine's memory is congested."
    ::= { sonusNodeResourcesMIBNotificationsPrefix 39 }

sonusSbxNodeMemoryCongestionClearNotification NOTIFICATION-TYPE
    OBJECTS         { sonusAlarmNodeID, sonusAlarmLevel, 
                      sonusAlarmSequenceId, sonusAlarmTime, 
                      sonusAlarmDescription, sonusCallCount, 
                      sonusRegCount, sonusRelayCount }
    STATUS          current
    DESCRIPTION     
            "This trap indicates that the machine's memory is no longer congested."
    ::= { sonusNodeResourcesMIBNotificationsPrefix 40 }

sonusSbxNodeResourceCallTraceSignalingDisabledNotification NOTIFICATION-TYPE
    OBJECTS         { sonusAlarmNodeID, sonusAlarmLevel, 
                      sonusAlarmSequenceId, sonusAlarmTime, 
                      sonusAlarmDescription, sonusCallTraceDisableReason }
    STATUS          current
    DESCRIPTION     
            "This trap indicates that signaling packet capture is disabled/inactive."
    ::= { sonusNodeResourcesMIBNotificationsPrefix 41 }

sonusSbxNodeResourceCallTraceSignalingEnabledNotification NOTIFICATION-TYPE
    OBJECTS         { sonusAlarmNodeID, sonusAlarmLevel, 
                      sonusAlarmSequenceId, sonusAlarmTime, 
                      sonusAlarmDescription }
    STATUS          current
    DESCRIPTION     
            "This trap indicates that signaling packet capture started."
    ::= { sonusNodeResourcesMIBNotificationsPrefix 42 }

sonusSbxDspFpgaVersionCheckFailureNotification NOTIFICATION-TYPE
    OBJECTS         { sonusAlarmNodeID, sonusAlarmLevel, 
                      sonusAlarmSequenceId, sonusAlarmTime, 
                      sonusAlarmDescription }
    STATUS          current
    DESCRIPTION     
            "This trap indicates DSP FPGA version check failure."
    ::= { sonusNodeResourcesMIBNotificationsPrefix 43 }

sonusSbxNodeOutOfServiceNotification NOTIFICATION-TYPE
    OBJECTS         { sonusAlarmNodeID, sonusAlarmLevel, 
                      sonusAlarmSequenceId, sonusAlarmTime, 
                      sonusAlarmDescription }
    STATUS          current
    DESCRIPTION     
            "This trap indicates that this node has been administratively removed from processing calls."
    ::= { sonusNodeResourcesMIBNotificationsPrefix 44 }

sonusSbxToneAnnouncementFailedNotification NOTIFICATION-TYPE
    OBJECTS         { sonusAlarmNodeID, sonusAlarmLevel, 
                      sonusAlarmSequenceId, sonusAlarmTime, 
                      sonusAlarmDescription, sonusNrmaToneType, 
                      sonusNrmaCodecType, sonusNrmaCodecAttr }
    STATUS          current
    DESCRIPTION     
            "This trap indicates that tone playing failed when we are playing compressed tone using file."
    ::= { sonusNodeResourcesMIBNotificationsPrefix 45 }

sonusLiCryptoFailureNotification NOTIFICATION-TYPE
    OBJECTS         { sonusAlarmNodeID, sonusAlarmLevel, 
                      sonusAlarmSequenceId, sonusAlarmTime, 
                      sonusAlarmDescription, sonusScmInstanceId, 
                      sonusDecryptModuleId }
    STATUS          current
    DESCRIPTION     
            "Decryption failed"
    ::= { sonusNodeResourcesMIBNotificationsPrefix 46 }

sonusLiCryptoSuccessNotification NOTIFICATION-TYPE
    OBJECTS         { sonusAlarmNodeID, sonusAlarmLevel, 
                      sonusAlarmSequenceId, sonusAlarmTime, 
                      sonusAlarmDescription, sonusScmInstanceId, 
                      sonusDecryptModuleId }
    STATUS          current
    DESCRIPTION     
            "Decryption successful"
    ::= { sonusNodeResourcesMIBNotificationsPrefix 47 }

sonusSbxNodeInServiceNotification NOTIFICATION-TYPE
    OBJECTS         { sonusAlarmNodeID, sonusAlarmLevel, 
                      sonusAlarmSequenceId, sonusAlarmTime, 
                      sonusAlarmDescription }
    STATUS          current
    DESCRIPTION     
            "This trap indicates that this node has been administratively placed in service for processing calls."
    ::= { sonusNodeResourcesMIBNotificationsPrefix 48 }

sonusSbxDspCardOrDeviceFailureNotification NOTIFICATION-TYPE
    OBJECTS         { sonusAlarmNodeID, sonusAlarmLevel, 
                      sonusAlarmSequenceId, sonusAlarmTime, 
                      sonusAlarmDescription }
    STATUS          current
    DESCRIPTION     
            "This trap indicates and identifies a fatal DSP device or card failure."
    ::= { sonusNodeResourcesMIBNotificationsPrefix 49 }

sonusSbxDspCardOrDeviceFailureNotificationClear NOTIFICATION-TYPE
    OBJECTS         { sonusAlarmNodeID, sonusAlarmLevel, 
                      sonusAlarmSequenceId, sonusAlarmTime, 
                      sonusAlarmDescription }
    STATUS          current
    DESCRIPTION     
            "This trap indicates that a DSP device or card failure has cleared."
    ::= { sonusNodeResourcesMIBNotificationsPrefix 50 }

sonusSbxGpuCodecThresholdNotification NOTIFICATION-TYPE
    OBJECTS         { sonusAlarmNodeID, sonusAlarmLevel, 
                      sonusAlarmSequenceId, sonusAlarmTime, 
                      sonusAlarmDescription, sonusThresholdCrossingCodec }
    STATUS          current
    DESCRIPTION     
            "This trap indicates that the compression DSP resource usage for certain GPU supported codecs has crossed the threshold value."
    ::= { sonusNodeResourcesMIBNotificationsPrefix 51 }

sonusSbxGpuCodecThresholdNotificationClear NOTIFICATION-TYPE
    OBJECTS         { sonusAlarmNodeID, sonusAlarmLevel, 
                      sonusAlarmSequenceId, sonusAlarmTime, 
                      sonusAlarmDescription, sonusThresholdCrossingCodec }
    STATUS          current
    DESCRIPTION     
            "This trap indicates that the compression DSP resource usage for GPU supported codec has dropped below the threshold value."
    ::= { sonusNodeResourcesMIBNotificationsPrefix 52 }

sonusSbxMediaOverFlowPacketsNotification NOTIFICATION-TYPE
    OBJECTS         { sonusAlarmNodeID, sonusAlarmLevel, 
                      sonusAlarmSequenceId, sonusAlarmTime, 
                      sonusAlarmDescription }
    STATUS          current
    DESCRIPTION     
            "This trap indicates that over flow packets or Non-Confirming packets were found for one or more calls during X interval defined in system policing."
    ::= { sonusNodeResourcesMIBNotificationsPrefix 53 }

sonusSbxMediaOverFlowPacketsCleared NOTIFICATION-TYPE
    OBJECTS         { sonusAlarmNodeID, sonusAlarmLevel, 
                      sonusAlarmSequenceId, sonusAlarmTime, 
                      sonusAlarmDescription }
    STATUS          current
    DESCRIPTION     
            "This trap indicates that there are no more over flow packets or Non-Confirming packets for calls during X interval defined in system policing."
    ::= { sonusNodeResourcesMIBNotificationsPrefix 54 }

sonusTrafficProfileActivationNotification NOTIFICATION-TYPE
    OBJECTS         { sonusAlarmNodeID, sonusAlarmLevel, 
                      sonusAlarmSequenceId, sonusAlarmTime, 
                      sonusAlarmDescription, 
                      sonusTrafficProfileActivationMsg, 
                      sonusTrafficProfileActivationStatus }
    STATUS          current
    DESCRIPTION     
            "This trap indicates that there was an attempt to activate a traffic profile on a SWe/Cloud instance from OAM."
    ::= { sonusNodeResourcesMIBNotificationsPrefix 55 }

sonusConfigProfileActivationNotification NOTIFICATION-TYPE
    OBJECTS         { sonusAlarmNodeID, sonusAlarmLevel, 
                      sonusAlarmSequenceId, sonusAlarmTime, 
                      sonusAlarmDescription, 
                      sonusConfigProfileActivationMsg, 
                      sonusConfigProfileActivationStatus }
    STATUS          current
    DESCRIPTION     
            "This trap indicates that there was an attempt to activate a Config profile on a SWe/Cloud instance from OAM."
    ::= { sonusNodeResourcesMIBNotificationsPrefix 56 }

sonusMrfpRealmMediaPortRangeThresholdExceededNotification NOTIFICATION-TYPE
    OBJECTS         { sonusAlarmNodeID, sonusAlarmLevel, 
                      sonusAlarmSequenceId, sonusAlarmTime, 
                      sonusAlarmDescription, sonusMrfpRealmId }
    STATUS          current
    DESCRIPTION     
            "The realm media port usage has exceeded threshold."
    ::= { sonusNodeResourcesMIBNotificationsPrefix 57 }

sonusMrfpRealmMediaPortRangeThresholdExceededClearedNotfication NOTIFICATION-TYPE
    OBJECTS         { sonusAlarmNodeID, sonusAlarmLevel, 
                      sonusAlarmSequenceId, sonusAlarmTime, 
                      sonusAlarmDescription, sonusMrfpRealmId }
    STATUS          current
    DESCRIPTION     
            "The realm media port range is back under threshold."
    ::= { sonusNodeResourcesMIBNotificationsPrefix 58 }

sonusSbxTrunkGroupTrafficControlConfChanged NOTIFICATION-TYPE
    OBJECTS         { sonusAlarmNodeID, sonusAlarmLevel, 
                      sonusAlarmSequenceId, sonusAlarmTime, 
                      sonusAlarmDescription, sonusTgName, 
                      sonusTrunkGroupTCObject, sonusTgAdditionalData }
    STATUS          deprecated
    DESCRIPTION     
            "This trap has been replaced by sonusSbxTrunkGroupTrafficControlConfChanged2."
    ::= { sonusTrunkGroupResourcesMIBNotificationsPrefix 1 }

sonusSbxTrunkGroupManualControlActive NOTIFICATION-TYPE
    OBJECTS         { sonusAlarmNodeID, sonusAlarmLevel, 
                      sonusAlarmSequenceId, sonusAlarmTime, 
                      sonusAlarmDescription, sonusTgName, 
                      sonusTrunkGroupManCon, sonusTgAdditionalData }
    STATUS          deprecated
    DESCRIPTION     
            "This trap has been replaced by sonusSbxTrunkGroupManualControlActive2."
    ::= { sonusTrunkGroupResourcesMIBNotificationsPrefix 2 }

sonusSbxTrunkGroupAutomaticControlActive NOTIFICATION-TYPE
    OBJECTS         { sonusAlarmNodeID, sonusAlarmLevel, 
                      sonusAlarmSequenceId, sonusAlarmTime, 
                      sonusAlarmDescription, sonusTgName, 
                      sonusTrunkGroupAutoCon, sonusTgAdditionalData }
    STATUS          deprecated
    DESCRIPTION     
            "This trap has been replaced by sonusSbxTrunkGroupAutomaticControlActive2."
    ::= { sonusTrunkGroupResourcesMIBNotificationsPrefix 3 }

sonusSbxTrunkGroupOutOfResourcesNotification NOTIFICATION-TYPE
    OBJECTS         { sonusAlarmNodeID, sonusAlarmLevel, 
                      sonusAlarmSequenceId, sonusAlarmTime, 
                      sonusAlarmDescription, sonusTgName, 
                      sonusCacLimitType, sonusTgAdditionalData }
    STATUS          deprecated
    DESCRIPTION     
            "This trap has been replaced by sonusSbxTrunkGroupOutOfResourcesNotification2."
    ::= { sonusTrunkGroupResourcesMIBNotificationsPrefix 4 }

sonusSbxTrunkGroupKpiClearedThresholdNotification NOTIFICATION-TYPE
    OBJECTS         { sonusAlarmNodeID, sonusAlarmLevel, 
                      sonusAlarmSequenceId, sonusAlarmTime, 
                      sonusAlarmDescription, sonusTgName, 
                      sonusAddressContextName, sonusZoneName, sonusKpi, 
                      sonusCurrentKpiValue }
    STATUS          current
    DESCRIPTION     
            "This trap indicates that bad QOS KPI condition in the trunk
             group got cleared."
    ::= { sonusTrunkGroupResourcesMIBNotificationsPrefix 5 }

sonusSbxTrunkGroupKpiMajorThresholdNotification NOTIFICATION-TYPE
    OBJECTS         { sonusAlarmNodeID, sonusAlarmLevel, 
                      sonusAlarmSequenceId, sonusAlarmTime, 
                      sonusAlarmDescription, sonusTgName, 
                      sonusAddressContextName, sonusZoneName, sonusKpi, 
                      sonusCurrentKpiValue }
    STATUS          current
    DESCRIPTION     
            "This trap indicates that major QOS KPI condition in the trunk"
    ::= { sonusTrunkGroupResourcesMIBNotificationsPrefix 6 }

sonusSbxTrunkGroupKpiCriticalThresholdNotification NOTIFICATION-TYPE
    OBJECTS         { sonusAlarmNodeID, sonusAlarmLevel, 
                      sonusAlarmSequenceId, sonusAlarmTime, 
                      sonusAlarmDescription, sonusTgName, 
                      sonusAddressContextName, sonusZoneName, sonusKpi, 
                      sonusCurrentKpiValue }
    STATUS          current
    DESCRIPTION     
            "This trap indicates that critical QOS KPI condition in the TG"
    ::= { sonusTrunkGroupResourcesMIBNotificationsPrefix 7 }

sonusSbxTrunkGroupKpiCriticalThresholdClearedNotification NOTIFICATION-TYPE
    OBJECTS         { sonusAlarmNodeID, sonusAlarmLevel, 
                      sonusAlarmSequenceId, sonusAlarmTime, 
                      sonusAlarmDescription, sonusTgName, 
                      sonusAddressContextName, sonusZoneName, sonusKpi, 
                      sonusCurrentKpiValue }
    STATUS          current
    DESCRIPTION     
            "This trap indicates that critical QOS KPI condition in the TG got cleared"
    ::= { sonusTrunkGroupResourcesMIBNotificationsPrefix 8 }

sonusSbxTrunkGroupTrafficControlConfChanged2 NOTIFICATION-TYPE
    OBJECTS         { sonusAlarmNodeID, sonusAlarmLevel, 
                      sonusAlarmSequenceId, sonusAlarmTime, 
                      sonusAlarmDescription, sonusTgName, 
                      sonusTrunkGroupTCObject }
    STATUS          current
    DESCRIPTION     
            "This trap indicates that a traffic control
             configuration object in 
             the trunk group table has changed.  The 
             sonusTrunkGroupTCObject parameter indicates what 
             object or objects have changed."
    ::= { sonusTrunkGroupResourcesMIBNotificationsPrefix 9 }

sonusSbxTrunkGroupManualControlActive2 NOTIFICATION-TYPE
    OBJECTS         { sonusAlarmNodeID, sonusAlarmLevel, 
                      sonusAlarmSequenceId, sonusAlarmTime, 
                      sonusAlarmDescription, sonusTgName, 
                      sonusTrunkGroupManCon }
    STATUS          deprecated
    DESCRIPTION     
            "This trap has been replaced by sonusSbxTrunkGroupManualControlActive3."
    ::= { sonusTrunkGroupResourcesMIBNotificationsPrefix 10 }

sonusSbxTrunkGroupAutomaticControlActive2 NOTIFICATION-TYPE
    OBJECTS         { sonusAlarmNodeID, sonusAlarmLevel, 
                      sonusAlarmSequenceId, sonusAlarmTime, 
                      sonusAlarmDescription, sonusTgName, 
                      sonusTrunkGroupAutoCon }
    STATUS          deprecated
    DESCRIPTION     
            "This trap has been replaced by sonusSbxTrunkGroupManualControlActive3."
    ::= { sonusTrunkGroupResourcesMIBNotificationsPrefix 11 }

sonusSbxTrunkGroupOutOfResourcesNotification2 NOTIFICATION-TYPE
    OBJECTS         { sonusAlarmNodeID, sonusAlarmLevel, 
                      sonusAlarmSequenceId, sonusAlarmTime, 
                      sonusAlarmDescription, sonusTgName, 
                      sonusCacLimitType }
    STATUS          current
    DESCRIPTION     
            "This trap indicates a Trunk Group is out of resources."
    ::= { sonusTrunkGroupResourcesMIBNotificationsPrefix 12 }

sonusSbxTrunkGroupManualControlActive3 NOTIFICATION-TYPE
    OBJECTS         { sonusAlarmNodeID, sonusAlarmLevel, 
                      sonusAlarmSequenceId, sonusAlarmTime, 
                      sonusAlarmDescription, sonusTgName, 
                      sonusTrunkGroupManCon3 }
    STATUS          current
    DESCRIPTION     
            "This trap indicates that a manual traffic control 
             was active within the last 30 seconds.  The 
             sonusTrunkGroupManualControl parameter indicates what 
             manual control was active."
    ::= { sonusTrunkGroupResourcesMIBNotificationsPrefix 13 }

sonusSbxTrunkGroupAutomaticControlActive3 NOTIFICATION-TYPE
    OBJECTS         { sonusAlarmNodeID, sonusAlarmLevel, 
                      sonusAlarmSequenceId, sonusAlarmTime, 
                      sonusAlarmDescription, sonusTgName, 
                      sonusTrunkGroupAutoCon3 }
    STATUS          current
    DESCRIPTION     
            "This trap indicates that an automatic traffic control 
             was active within the last 30 seconds.  The 
             sonusTrunkGroupAutomaticControl parameter indicates 
             what automatic control was active."
    ::= { sonusTrunkGroupResourcesMIBNotificationsPrefix 14 }

sonusSbxCallAccountingInServiceNotification NOTIFICATION-TYPE
    OBJECTS         { sonusAlarmNodeID, sonusAlarmLevel, 
                      sonusAlarmSequenceId, sonusAlarmTime, 
                      sonusAlarmDescription, sonusAcctGenerationMode, 
                      sonusAcctLogDestination, sonusAcctIntAcctState, 
                      sonusAcctIntAcctInterval, sonusAcctIntAcctMode, 
                      sonusAcctIntLongDurGenTime }
    STATUS          current
    DESCRIPTION     
            "This Trap is Generated when a change is made to the Accounting 
             Configuration for the Node, and the resultant configuration
             state of accounting for the node is that it is enabled/in-service"
    ::= { sonusAccountingMIBNotificationsPrefix 1 }

sonusSbxCallAccountingOutOfServiceNotification NOTIFICATION-TYPE
    OBJECTS         { sonusAlarmNodeID, sonusAlarmLevel, 
                      sonusAlarmSequenceId, sonusAlarmTime, 
                      sonusAlarmDescription, sonusAcctOutOfServiceReason }
    STATUS          current
    DESCRIPTION     
            "This Trap is Generated when Accounting Records are no
             longer being generated on the Node. It could be either
             because of a change to the Accounting Configuration
             or because of errors in the logging mechanism such as file logging
             errors. When the reason specified for accounting outofservice
             is event logging error, then the SYS event logs on the Node
             should be examined to obtain further information about the
             event logging failure"
    ::= { sonusAccountingMIBNotificationsPrefix 2 }

sonusSbxAccountingIntermediateRecordNotification NOTIFICATION-TYPE
    OBJECTS         { sonusAlarmNodeID, sonusAlarmLevel, 
                      sonusAlarmSequenceId, sonusAlarmTime, 
                      sonusAlarmDescription, sonusAcctGcid, 
                      sonusAcctOrigTrunkgroupType, sonusAcctIngressCep, 
                      sonusAcctTermTrunkgroupType, sonusAcctEgressCep, 
                      sonusAcctCallingPartyNumber, 
                      sonusAcctCalledPartyNumber }
    STATUS          current
    DESCRIPTION     
            "This Trap is Generated when an INTERMEDIATE accounting
             record is generated."
    ::= { sonusAccountingMIBNotificationsPrefix 3 }

sonusSbxSelCdrConfUpdateNotification NOTIFICATION-TYPE
    OBJECTS         { sonusAlarmNodeID, sonusAlarmLevel, 
                      sonusAlarmSequenceId, sonusAlarmTime, 
                      sonusAlarmDescription, sonusSelCdrSequenceNumber, 
                      sonusSelCdrUpdateStatus }
    STATUS          deprecated
    DESCRIPTION     
            "This Trap indicates that SBC receives
             selectable CDR configuration from DSI
             stream server. The variable sonusSelCdrConfSeqNum
             indicates the new sequence number of selectable CDR
             configuration received. The variable
             sonusSelCdrConfUpdateStatus indicates
             the accept status of the configuration updates."
    ::= { sonusAccountingMIBNotificationsPrefix 4 }

sonusSbxSelCdrConfigReqRspTimeoutNotification NOTIFICATION-TYPE
    OBJECTS         { sonusAlarmNodeID, sonusAlarmLevel, 
                      sonusAlarmSequenceId, sonusAlarmTime, 
                      sonusAlarmDescription, sonusSelCdrReqRspTimeout, 
                      sonusSelCdrSequenceNumber }
    STATUS          deprecated
    DESCRIPTION     
            "This trap indicates that SBC requests DSI for current selectable
             CDR configuration due to previous CDR streaming link outage or LSWU,
             but didn\222t receive the configuration updates from DSI after three 
             	    retries.
             
             The variable sonusSelCdrConfSeqNum indicates the last selectable CDR
             Configuration received, the variable sonusSelCdrReqRspTimeout
             indicates the duration of three retries."
    ::= { sonusAccountingMIBNotificationsPrefix 5 }

sonusSbxCallProcAnswerSupervisionTimeout NOTIFICATION-TYPE
    OBJECTS         { sonusAlarmNodeID, sonusAlarmLevel, 
                      sonusAlarmSequenceId, sonusAlarmTime, 
                      sonusAlarmDescription, sonusIngressTgName, 
                      sonusIngressCep, sonusEgressTgName, sonusEgressCep, 
                      sonusCalledNumber, sonusCallingNumber }
    STATUS          current
    DESCRIPTION     
            "The answer supervision timer has expired, indicating that 
             answer message has not been received from the called party.
             This trap is used to inform maintenance personnel of the
             situation so they can decide whether executive action is 
             required to tear the call down."
    ::= { sonusCommonCallProcessMIBNotificationsPrefix 1 }

sonusSbxCallProcLongDurationCallTimeout NOTIFICATION-TYPE
    OBJECTS         { sonusAlarmNodeID, sonusAlarmLevel, 
                      sonusAlarmSequenceId, sonusAlarmTime, 
                      sonusAlarmDescription, sonusTgName, sonusCep, 
                      sonusStaticCallGcid, sonusCalledNumber, 
                      sonusCallingNumber, sonusLdcStatus }
    STATUS          current
    DESCRIPTION     
            "This trap is used to inform that the long duration call 
             timer has expired. The call has been active for the 
             configured timeout period and the appropriate
             action has been taken."
    ::= { sonusCommonCallProcessMIBNotificationsPrefix 2 }

sonusSbxNetMgmtClientInformReqQueueFlushedNotification NOTIFICATION-TYPE
    OBJECTS         { sonusAlarmNodeID, sonusAlarmLevel, 
                      sonusAlarmSequenceId, sonusAlarmTime, 
                      sonusAlarmDescription, sonusNetMgmtClientName, 
                      sonusNetMgmtInformReqDiscards }
    STATUS          current
    DESCRIPTION     
            "The specified number of InformRequest PDUs destined to
             the specified Management Client were flushed from the
             InformRequest PDU queue because no Response PDUs were
             were received from the Management Client.
             
             This situtation could occur if the Management Client
             cannot quickly process and respond to InformRequest PDUs
             that it receives, or if communications is lost with the
             Management Client.
             
             If this situation occurs occasionally, it is recommended
             to increase the InformRequest PDU timeout and/or retry
             values (see sonusNetMgmtClientInformReqRspTimeout and
             sonusNetMgmtClientInformReqRetries.)
             
             If this situation occurs repeatedly, it is an indication
             that communications is lost with the Management Client,
             either because of network problems, or because the
             Management Client is no longer operational.
             
             It is recommended that this device be configured to
             send a Trap PDU, not an InformRequest PDU, for this
             Notification to all Management Clients, thus bypassing
             a problematic InformRequest PDU queue and allowing the
             situation to be quickly identified and resolved."
    ::= { sonusCommonMIBNotificationsPrefix 1 }

sonusSbxNetMgmtClientInformReqQueueFullNotification NOTIFICATION-TYPE
    OBJECTS         { sonusAlarmNodeID, sonusAlarmLevel, 
                      sonusAlarmSequenceId, sonusAlarmTime, 
                      sonusAlarmDescription, sonusNetMgmtClientName, 
                      sonusNetMgmtInformReqDiscards }
    STATUS          current
    DESCRIPTION     
            "The specified number of InformRequest PDUs destined to
             the specified Management Client were discard because its
             InformRequest PDU queue was full.
             
             This situtation could occur if the Management Client
             cannot quickly process and respond to InformRequest PDUs
             that it receives, or if communications is lost with the
             Management Client.
             
             If this situation occurs occasionally, it is recommended
             to increase the InformRequest PDU queue size (see
             sonusNetMgmtClientInformReqMaxQueue.)
             
             If this situation occurs repeatedly, it is an indication
             that communications is lost with the Management Client,
             either because of network problems, or because the
             Management Client is no longer operational.
             
             It is recommended that this device be configured to
             send a Trap PDU, not an InformRequest PDU, for this
             Notification to all Management Clients, thus bypassing
             a problematic InformRequest PDU queue and allowing the
             situation to be quickly identified and resolved."
    ::= { sonusCommonMIBNotificationsPrefix 2 }

sonusSbxNodePolicerMinorAlarmNotification NOTIFICATION-TYPE
    OBJECTS         { sonusAlarmNodeID, sonusAlarmLevel, 
                      sonusAlarmSequenceId, sonusAlarmTime, 
                      sonusAlarmDescription, sonusPolicerTypeStr, 
                      sonusPolicerLevelStr }
    STATUS          current
    DESCRIPTION     
            "The sonusNodePolicerMinorAlarmNotification indicates
             a system policer minor level alarm."
    ::= { sonusIpmMIBNotificationsPrefix 1 }

sonusSbxNodePolicerMajorAlarmNotification NOTIFICATION-TYPE
    OBJECTS         { sonusAlarmNodeID, sonusAlarmLevel, 
                      sonusAlarmSequenceId, sonusAlarmTime, 
                      sonusAlarmDescription, sonusPolicerTypeStr, 
                      sonusPolicerLevelStr }
    STATUS          current
    DESCRIPTION     
            "The sonusNodePolicerMajorAlarmNotification indicates
             a system policer major level alarm."
    ::= { sonusIpmMIBNotificationsPrefix 2 }

sonusSbxNodePolicerClearAlarmNotification NOTIFICATION-TYPE
    OBJECTS         { sonusAlarmNodeID, sonusAlarmLevel, 
                      sonusAlarmSequenceId, sonusAlarmTime, 
                      sonusAlarmDescription, sonusPolicerTypeStr }
    STATUS          current
    DESCRIPTION     
            "The sonusNodePolicerClearAlarmNotification indicates
             a system policer alarm clear."
    ::= { sonusIpmMIBNotificationsPrefix 3 }

sonusSbxDBLActionMajorNotification NOTIFICATION-TYPE
    OBJECTS         { sonusAlarmNodeID, sonusAlarmLevel, 
                      sonusAlarmSequenceId, sonusAlarmTime, 
                      sonusAlarmDescription, sonusDBLAddressContextName }
    STATUS          current
    DESCRIPTION     
            "The sonusSbxDBLActionMajorNotification indicates
             there are one or more DBL entries in the system"
    ::= { sonusIpmMIBNotificationsPrefix 4 }

sonusSbxDBLClearActionMajorNotification NOTIFICATION-TYPE
    OBJECTS         { sonusAlarmNodeID, sonusAlarmLevel, 
                      sonusAlarmSequenceId, sonusAlarmTime, 
                      sonusAlarmDescription, sonusDBLAddressContextName }
    STATUS          current
    DESCRIPTION     
            "The sonusSbxDBLClearActionMajorNotification notifies 
             that there are no DBL entries in the system"
    ::= { sonusIpmMIBNotificationsPrefix 5 }

sonusSbxDBLEnhActionSetNotification NOTIFICATION-TYPE
    OBJECTS         { sonusAlarmNodeID, sonusAlarmLevel, 
                      sonusAlarmSequenceId, sonusAlarmTime, 
                      sonusAlarmDescription, sonusDBLAddressContextName, 
                      sonusDBLEndPointInfo, sonusDBLAction, 
                      sonusDBLDuration, sonusDBLCriteria, 
                      sonusDBLProfileRuleInfo }
    STATUS          current
    DESCRIPTION     
            "The sonusSbxDBLEnhActionSetNotification indicates
             that action has been taken on the endpoint due to
             enhanced DBL enforcements"
    ::= { sonusIpmMIBNotificationsPrefix 6 }

sonusSbxDBLEnhActionClearNotification NOTIFICATION-TYPE
    OBJECTS         { sonusAlarmNodeID, sonusAlarmLevel, 
                      sonusAlarmSequenceId, sonusAlarmTime, 
                      sonusAlarmDescription, sonusDBLAddressContextName, 
                      sonusDBLEndPointInfo, sonusDBLAction, 
                      sonusDBLDuration, sonusDBLCriteria, 
                      sonusDBLProfileRuleInfo }
    STATUS          current
    DESCRIPTION     
            "The sonusSbxDBLEnhActionClearNotification notifies 
             that action which had been taken on the endpoint is now
             cleared"
    ::= { sonusIpmMIBNotificationsPrefix 7 }

sonusSbxDBLActionEndpointInfoNotification NOTIFICATION-TYPE
    OBJECTS         { sonusAlarmNodeID, sonusAlarmLevel, 
                      sonusAlarmSequenceId, sonusAlarmTime, 
                      sonusAlarmDescription, sonusDBLAddressContextName, 
                      sonusDBLEndPointInfo, sonusDBLEventName, 
                      sonusDBLAction, sonusDBLDuration, 
                      sonusDBLProfileRuleInfo }
    STATUS          current
    DESCRIPTION     
            "The sonusSbxDBLActionEndpointInfoNotification indicates 
             that action has been taken on the endpoint due to 
             the DBL enforcements."
    ::= { sonusIpmMIBNotificationsPrefix 8 }

sonusSbxDBLClearActionEndpointInfoNotification NOTIFICATION-TYPE
    OBJECTS         { sonusAlarmNodeID, sonusAlarmLevel, 
                      sonusAlarmSequenceId, sonusAlarmTime, 
                      sonusAlarmDescription, sonusDBLAddressContextName, 
                      sonusDBLEndPointInfo, sonusDBLEventName, 
                      sonusDBLAction, sonusDBLDuration, 
                      sonusDBLProfileRuleInfo }
    STATUS          current
    DESCRIPTION     
            "The sonusSbxDBLClearActionEndpointInfoNotification notifies 
             that action which had been taken on the endpoint is now cleared"
    ::= { sonusIpmMIBNotificationsPrefix 9 }

sonusSbxNrsIpInterfaceOOSNotification NOTIFICATION-TYPE
    OBJECTS         { sonusAlarmNodeID, sonusAlarmLevel, 
                      sonusAlarmSequenceId, sonusAlarmTime, 
                      sonusAlarmDescription, sonusNrsAddressContextName, 
                      sonusNrsIpInterfaceGroupName, 
                      sonusNrsIpInterfaceName }
    STATUS          current
    DESCRIPTION     
            "The IP Interface is out of service."
    ::= { sonusNrsMIBNotificationsPrefix 1 }

sonusSbxNrsIpInterfaceISNotification NOTIFICATION-TYPE
    OBJECTS         { sonusAlarmNodeID, sonusAlarmLevel, 
                      sonusAlarmSequenceId, sonusAlarmTime, 
                      sonusAlarmDescription, sonusNrsAddressContextName, 
                      sonusNrsIpInterfaceGroupName, 
                      sonusNrsIpInterfaceName }
    STATUS          current
    DESCRIPTION     
            "The IP Interface is in service."
    ::= { sonusNrsMIBNotificationsPrefix 2 }

sonusSbxNrsIpInterfaceAdminDisabledNotification NOTIFICATION-TYPE
    OBJECTS         { sonusAlarmNodeID, sonusAlarmLevel, 
                      sonusAlarmSequenceId, sonusAlarmTime, 
                      sonusAlarmDescription, sonusNrsAddressContextName, 
                      sonusNrsIpInterfaceGroupName, 
                      sonusNrsIpInterfaceName }
    STATUS          current
    DESCRIPTION     
            "The IP Interface was administratively disabled."
    ::= { sonusNrsMIBNotificationsPrefix 3 }

sonusSbxNrsIpInterfaceAdminEnabledNotification NOTIFICATION-TYPE
    OBJECTS         { sonusAlarmNodeID, sonusAlarmLevel, 
                      sonusAlarmSequenceId, sonusAlarmTime, 
                      sonusAlarmDescription, sonusNrsAddressContextName, 
                      sonusNrsIpInterfaceGroupName, 
                      sonusNrsIpInterfaceName }
    STATUS          current
    DESCRIPTION     
            "The IP Interface was administratively enabled"
    ::= { sonusNrsMIBNotificationsPrefix 4 }

sonusSbxNrsIpInterfaceAdminOOSNotification NOTIFICATION-TYPE
    OBJECTS         { sonusAlarmNodeID, sonusAlarmLevel, 
                      sonusAlarmSequenceId, sonusAlarmTime, 
                      sonusAlarmDescription, sonusNrsAddressContextName, 
                      sonusNrsIpInterfaceGroupName, 
                      sonusNrsIpInterfaceName }
    STATUS          current
    DESCRIPTION     
            "The IP Interface was administratively placed out of service."
    ::= { sonusNrsMIBNotificationsPrefix 5 }

sonusSbxNrsIpInterfaceAdminISNotification NOTIFICATION-TYPE
    OBJECTS         { sonusAlarmNodeID, sonusAlarmLevel, 
                      sonusAlarmSequenceId, sonusAlarmTime, 
                      sonusAlarmDescription, sonusNrsAddressContextName, 
                      sonusNrsIpInterfaceGroupName, 
                      sonusNrsIpInterfaceName }
    STATUS          current
    DESCRIPTION     
            "The IP Interface was administratively placed in service."
    ::= { sonusNrsMIBNotificationsPrefix 6 }

sonusSbxNrsIpInterfaceAdminDeletedNotification NOTIFICATION-TYPE
    OBJECTS         { sonusAlarmNodeID, sonusAlarmLevel, 
                      sonusAlarmSequenceId, sonusAlarmTime, 
                      sonusAlarmDescription, sonusNrsAddressContextName, 
                      sonusNrsIpInterfaceGroupName, 
                      sonusNrsIpInterfaceName }
    STATUS          obsolete
    DESCRIPTION     
            "The IP Interface was administratively deleted"
    ::= { sonusNrsMIBNotificationsPrefix 7 }

sonusSbxNrsMgmtIpInterfaceAdminDisabledNotification NOTIFICATION-TYPE
    OBJECTS         { sonusAlarmNodeID, sonusAlarmLevel, 
                      sonusAlarmSequenceId, sonusAlarmTime, 
                      sonusAlarmDescription, sonusNrsAddressContextName, 
                      sonusNrsIpInterfaceGroupName, 
                      sonusNrsIpInterfaceName }
    STATUS          current
    DESCRIPTION     
            "The Management IP Interface was administratively disabled."
    ::= { sonusNrsMIBNotificationsPrefix 8 }

sonusSbxNrsMgmtIpInterfaceAdminEnabledNotification NOTIFICATION-TYPE
    OBJECTS         { sonusAlarmNodeID, sonusAlarmLevel, 
                      sonusAlarmSequenceId, sonusAlarmTime, 
                      sonusAlarmDescription, sonusNrsAddressContextName, 
                      sonusNrsIpInterfaceGroupName, 
                      sonusNrsIpInterfaceName }
    STATUS          current
    DESCRIPTION     
            "The Management IP Interface was administratively enabled."
    ::= { sonusNrsMIBNotificationsPrefix 9 }

sonusSbxNrsMgmtPortAdminDisabledNotification NOTIFICATION-TYPE
    OBJECTS         { sonusAlarmNodeID, sonusAlarmLevel, 
                      sonusAlarmSequenceId, sonusAlarmTime, 
                      sonusAlarmDescription, sonusNrsCeName, 
                      sonusNrsPortName }
    STATUS          current
    DESCRIPTION     
            "The Management Port was administratively disabled."
    ::= { sonusNrsMIBNotificationsPrefix 10 }

sonusSbxNrsMgmtPortAdminEnabledNotification NOTIFICATION-TYPE
    OBJECTS         { sonusAlarmNodeID, sonusAlarmLevel, 
                      sonusAlarmSequenceId, sonusAlarmTime, 
                      sonusAlarmDescription, sonusNrsCeName, 
                      sonusNrsPortName }
    STATUS          current
    DESCRIPTION     
            "The Management Port was administratively enabled."
    ::= { sonusNrsMIBNotificationsPrefix 11 }

sonusSbxNrsMgmtPortIpInterfaceDeletedNotification NOTIFICATION-TYPE
    OBJECTS         { sonusAlarmNodeID, sonusAlarmLevel, 
                      sonusAlarmSequenceId, sonusAlarmTime, 
                      sonusAlarmDescription, sonusNrsAddressContextName, 
                      sonusNrsIpInterfaceGroupName, 
                      sonusNrsIpInterfaceName }
    STATUS          obsolete
    DESCRIPTION     
            "The Management Port was administratively deleted."
    ::= { sonusNrsMIBNotificationsPrefix 12 }

sonusSbxNrsPacketPortDownNotification NOTIFICATION-TYPE
    OBJECTS         { sonusAlarmNodeID, sonusAlarmLevel, 
                      sonusAlarmSequenceId, sonusAlarmTime, 
                      sonusAlarmDescription, sonusNrsCeName, 
                      sonusNrsPortName }
    STATUS          current
    DESCRIPTION     
            "The packet port is down."
    ::= { sonusNrsMIBNotificationsPrefix 13 }

sonusSbxNrsPacketPortUpNotification NOTIFICATION-TYPE
    OBJECTS         { sonusAlarmNodeID, sonusAlarmLevel, 
                      sonusAlarmSequenceId, sonusAlarmTime, 
                      sonusAlarmDescription, sonusNrsCeName, 
                      sonusNrsPortName }
    STATUS          current
    DESCRIPTION     
            "The packet port is up."
    ::= { sonusNrsMIBNotificationsPrefix 14 }

sonusSbxNrsMgmtPortDownNotification NOTIFICATION-TYPE
    OBJECTS         { sonusAlarmNodeID, sonusAlarmLevel, 
                      sonusAlarmSequenceId, sonusAlarmTime, 
                      sonusAlarmDescription, sonusNrsCeName, 
                      sonusNrsPortName }
    STATUS          current
    DESCRIPTION     
            "The Management IP Interface is down."
    ::= { sonusNrsMIBNotificationsPrefix 15 }

sonusSbxNrsMgmtPortUpNotification NOTIFICATION-TYPE
    OBJECTS         { sonusAlarmNodeID, sonusAlarmLevel, 
                      sonusAlarmSequenceId, sonusAlarmTime, 
                      sonusAlarmDescription, sonusNrsCeName, 
                      sonusNrsPortName }
    STATUS          current
    DESCRIPTION     
            "The Management IP Interface is up"
    ::= { sonusNrsMIBNotificationsPrefix 16 }

sonusSbxNrsIpInterfaceLinkMonitorDownNotification NOTIFICATION-TYPE
    OBJECTS         { sonusAlarmNodeID, sonusAlarmLevel, 
                      sonusAlarmSequenceId, sonusAlarmTime, 
                      sonusAlarmDescription, sonusNrsAddressContextName, 
                      sonusNrsIpInterfaceName, sonusNrsIpAddress }
    STATUS          current
    DESCRIPTION     
            "The destination IP Interface is down."
    ::= { sonusNrsMIBNotificationsPrefix 17 }

sonusSbxNrsIpInterfaceLinkMonitorUpNotification NOTIFICATION-TYPE
    OBJECTS         { sonusAlarmNodeID, sonusAlarmLevel, 
                      sonusAlarmSequenceId, sonusAlarmTime, 
                      sonusAlarmDescription, sonusNrsAddressContextName, 
                      sonusNrsIpInterfaceName, sonusNrsIpAddress }
    STATUS          current
    DESCRIPTION     
            "The destination IP Interface is up."
    ::= { sonusNrsMIBNotificationsPrefix 18 }

sonusSbxNrsLogMgmtIpInterfaceAdminEnabledNotification NOTIFICATION-TYPE
    OBJECTS         { sonusAlarmNodeID, sonusAlarmLevel, 
                      sonusAlarmSequenceId, sonusAlarmTime, 
                      sonusAlarmDescription, sonusNrsIpInterfaceName }
    STATUS          current
    DESCRIPTION     
            "The Logical Management IP Interface was administratively enabled."
    ::= { sonusNrsMIBNotificationsPrefix 19 }

sonusSbxNrsLogMgmtIpInterfaceAdminDisabledNotification NOTIFICATION-TYPE
    OBJECTS         { sonusAlarmNodeID, sonusAlarmLevel, 
                      sonusAlarmSequenceId, sonusAlarmTime, 
                      sonusAlarmDescription, sonusNrsIpInterfaceName }
    STATUS          current
    DESCRIPTION     
            "The Logical Management Port was administratively disabled."
    ::= { sonusNrsMIBNotificationsPrefix 20 }

sonusSbxNrsIpInterfaceLinkMonitorDownNotificationV6 NOTIFICATION-TYPE
    OBJECTS         { sonusAlarmNodeID, sonusAlarmLevel, 
                      sonusAlarmSequenceId, sonusAlarmTime, 
                      sonusAlarmDescription, sonusNrsAddressContextName, 
                      sonusNrsIpInterfaceName, sonusNrsIpAddressV6 }
    STATUS          current
    DESCRIPTION     
            "The destination IP Interface is down."
    ::= { sonusNrsMIBNotificationsPrefix 21 }

sonusSbxNrsIpInterfaceLinkMonitorUpNotificationV6 NOTIFICATION-TYPE
    OBJECTS         { sonusAlarmNodeID, sonusAlarmLevel, 
                      sonusAlarmSequenceId, sonusAlarmTime, 
                      sonusAlarmDescription, sonusNrsAddressContextName, 
                      sonusNrsIpInterfaceName, sonusNrsIpAddressV6 }
    STATUS          current
    DESCRIPTION     
            "The destination IP Interface is up."
    ::= { sonusNrsMIBNotificationsPrefix 22 }

sonusSbxNrsMediaPortDownNoLicenseNotification NOTIFICATION-TYPE
    OBJECTS         { sonusAlarmNodeID, sonusAlarmLevel, 
                      sonusAlarmSequenceId, sonusAlarmTime, 
                      sonusAlarmDescription, sonusNrsCeName, 
                      sonusNrsPortName }
    STATUS          current
    DESCRIPTION     
            "The media port is down due to no license present."
    ::= { sonusNrsMIBNotificationsPrefix 23 }

sonusSbxNrsMediaPortDownNoLicenseClearedNotification NOTIFICATION-TYPE
    OBJECTS         { sonusAlarmNodeID, sonusAlarmLevel, 
                      sonusAlarmSequenceId, sonusAlarmTime, 
                      sonusAlarmDescription, sonusNrsCeName, 
                      sonusNrsPortName }
    STATUS          current
    DESCRIPTION     
            "The media port is no longer down due to no license present."
    ::= { sonusNrsMIBNotificationsPrefix 24 }

sonusSbxNrsMediaPortInvalidSfpNotification NOTIFICATION-TYPE
    OBJECTS         { sonusAlarmNodeID, sonusAlarmLevel, 
                      sonusAlarmSequenceId, sonusAlarmTime, 
                      sonusAlarmDescription, sonusNrsCeName, 
                      sonusNrsPortName, sonusNrsInvalidSfpReason }
    STATUS          current
    DESCRIPTION     
            "An invalid SFP is plugged in to the port."
    ::= { sonusNrsMIBNotificationsPrefix 25 }

sonusSbxNrsMediaPortInvalidSfpClearedNotification NOTIFICATION-TYPE
    OBJECTS         { sonusAlarmNodeID, sonusAlarmLevel, 
                      sonusAlarmSequenceId, sonusAlarmTime, 
                      sonusAlarmDescription, sonusNrsCeName, 
                      sonusNrsPortName, sonusNrsInvalidSfpReason }
    STATUS          current
    DESCRIPTION     
            "An invalid SFP is no longer plugged into the port."
    ::= { sonusNrsMIBNotificationsPrefix 26 }

sonusNrsNifHighWatermarkNotification NOTIFICATION-TYPE
    OBJECTS         { sonusAlarmNodeID, sonusAlarmLevel, 
                      sonusAlarmSequenceId, sonusAlarmTime, 
                      sonusAlarmDescription, sonusNifPort, sonusNifIndex, 
                      sonusNrsPortName }
    STATUS          current
    DESCRIPTION     
            "This trap indicates that a NIF's high watermark has been reached 
             the first time since the NIF's low watermark has beend reached."
    ::= { sonusNrsMIBNotificationsPrefix 27 }

sonusNrsNifLowWatermarkNotification NOTIFICATION-TYPE
    OBJECTS         { sonusAlarmNodeID, sonusAlarmLevel, 
                      sonusAlarmSequenceId, sonusAlarmTime, 
                      sonusAlarmDescription, sonusNifPort, sonusNifIndex, 
                      sonusNrsPortName }
    STATUS          current
    DESCRIPTION     
            "This trap indicates that a NIF's low watermark has been reached
             the first time since the NIF's high watermark has been reached."
    ::= { sonusNrsMIBNotificationsPrefix 28 }

sonusH248ScDisconnectedTxNotification NOTIFICATION-TYPE
    OBJECTS         { sonusAlarmNodeID, sonusAlarmLevel, 
                      sonusAlarmSequenceId, sonusAlarmTime, 
                      sonusAlarmDescription, sonusH248SigRemoteIpAddr, 
                      sonusH248SigLocalIpAddr, sonusH248SigScMethod, 
                      sonusH248SigMid }
    STATUS          current
    DESCRIPTION     
            "This trap indicates the Service change Disconnected is
             transmitted."
    ::= { sonusBgfMIBNotificationsPrefix 1 }

sonusH248ScHandoffTxNotification NOTIFICATION-TYPE
    OBJECTS         { sonusAlarmNodeID, sonusAlarmLevel, 
                      sonusAlarmSequenceId, sonusAlarmTime, 
                      sonusAlarmDescription, sonusH248SigRemoteIpAddr, 
                      sonusH248SigLocalIpAddr, sonusH248SigScMethod, 
                      sonusH248SigMid }
    STATUS          deprecated
    DESCRIPTION     
            "This trap indicates the Service change Handoff is
             transmitted."
    ::= { sonusBgfMIBNotificationsPrefix 2 }

sonusH248ScFailoverTxStatusNotification NOTIFICATION-TYPE
    OBJECTS         { sonusAlarmNodeID, sonusAlarmLevel, 
                      sonusAlarmSequenceId, sonusAlarmTime, 
                      sonusAlarmDescription, sonusH248SigRemoteIpAddr, 
                      sonusH248SigLocalIpAddr, sonusH248SigScMethod, 
                      sonusH248SigMid, sonusH248SigStatus }
    STATUS          current
    DESCRIPTION     
            "This trap indicates the Service change Failover 
             transmitted status."
    ::= { sonusBgfMIBNotificationsPrefix 3 }

sonusH248ScFailoverTxNotification NOTIFICATION-TYPE
    OBJECTS         { sonusAlarmNodeID, sonusAlarmLevel, 
                      sonusAlarmSequenceId, sonusAlarmTime, 
                      sonusAlarmDescription, sonusH248SigRemoteIpAddr, 
                      sonusH248SigLocalIpAddr, sonusH248SigScMethod, 
                      sonusH248SigMid }
    STATUS          current
    DESCRIPTION     
            "This trap indicates the Service change Failover is
             transmitted. "
    ::= { sonusBgfMIBNotificationsPrefix 4 }

sonusH248ScHandoffRxNotification NOTIFICATION-TYPE
    OBJECTS         { sonusAlarmNodeID, sonusAlarmLevel, 
                      sonusAlarmSequenceId, sonusAlarmTime, 
                      sonusAlarmDescription, sonusH248SigLocalIpAddr, 
                      sonusH248SigScMethod, sonusH248SigMid, 
                      sonusH248SigMid }
    STATUS          current
    DESCRIPTION     
            "This trap indicates the Service change Handoff 
             is received. "
    ::= { sonusBgfMIBNotificationsPrefix 5 }

sonusH248ScRestartRxNotification NOTIFICATION-TYPE
    OBJECTS         { sonusAlarmNodeID, sonusAlarmLevel, 
                      sonusAlarmSequenceId, sonusAlarmTime, 
                      sonusAlarmDescription, sonusH248SigLocalIpAddr, 
                      sonusH248SigScMethod, sonusH248SigMid }
    STATUS          deprecated
    DESCRIPTION     
            "This trap indicates the Service change Restart 
             is received. "
    ::= { sonusBgfMIBNotificationsPrefix 6 }

sonusH248ScVerNotSupportedNotification NOTIFICATION-TYPE
    OBJECTS         { sonusAlarmNodeID, sonusAlarmLevel, 
                      sonusAlarmSequenceId, sonusAlarmTime, 
                      sonusAlarmDescription, sonusH248SigRemoteIpAddr, 
                      sonusH248SigLocalIpAddr, sonusH248SigMid, 
                      sonusH248SpdfName, sonusH248Version }
    STATUS          deprecated
    DESCRIPTION     
            "This trap indicates the unsuccessful version
             negotiation. "
    ::= { sonusBgfMIBNotificationsPrefix 7 }

sonusH248ScVerNegotiatedNotification NOTIFICATION-TYPE
    OBJECTS         { sonusAlarmNodeID, sonusAlarmLevel, 
                      sonusAlarmSequenceId, sonusAlarmTime, 
                      sonusAlarmDescription, sonusH248SigRemoteIpAddr, 
                      sonusH248SigLocalIpAddr, sonusH248SigMid, 
                      sonusH248SpdfName, sonusH248Version }
    STATUS          deprecated
    DESCRIPTION     
            "This trap indicates the successful version
             negotiation. "
    ::= { sonusBgfMIBNotificationsPrefix 8 }

sonusH248FeatureLicenseExpiryNotification NOTIFICATION-TYPE
    OBJECTS         { sonusAlarmNodeID, sonusAlarmLevel, 
                      sonusAlarmSequenceId, sonusAlarmTime, 
                      sonusAlarmDescription, sonusH248FeatureName }
    STATUS          deprecated
    DESCRIPTION     
            "This trap indicates License expiry 
             notification. "
    ::= { sonusBgfMIBNotificationsPrefix 9 }

sonusH248FeatureLicenseLimitNotification NOTIFICATION-TYPE
    OBJECTS         { sonusAlarmNodeID, sonusAlarmLevel, 
                      sonusAlarmSequenceId, sonusAlarmTime, 
                      sonusAlarmDescription, sonusH248FeatureName }
    STATUS          deprecated
    DESCRIPTION     
            "This trap indicates License Limit is reached
             notification. "
    ::= { sonusBgfMIBNotificationsPrefix 10 }

sonusH248FeatureDisabledNotification NOTIFICATION-TYPE
    OBJECTS         { sonusAlarmNodeID, sonusAlarmLevel, 
                      sonusAlarmSequenceId, sonusAlarmTime, 
                      sonusAlarmDescription, sonusH248FeatureName }
    STATUS          deprecated
    DESCRIPTION     
            "This trap indicates License is Disabled for Feature. "
    ::= { sonusBgfMIBNotificationsPrefix 11 }

sonusH248FeatureEnableNotification NOTIFICATION-TYPE
    OBJECTS         { sonusAlarmNodeID, sonusAlarmLevel, 
                      sonusAlarmSequenceId, sonusAlarmTime, 
                      sonusAlarmDescription, sonusH248FeatureName }
    STATUS          deprecated
    DESCRIPTION     
            "This trap indicates License is Enabled for Feature. "
    ::= { sonusBgfMIBNotificationsPrefix 12 }

sonusH248SigPortOpenNotification NOTIFICATION-TYPE
    OBJECTS         { sonusAlarmNodeID, sonusAlarmLevel, 
                      sonusAlarmSequenceId, sonusAlarmTime, 
                      sonusAlarmDescription, sonusH248SigPortIpAddress, 
                      sonusH248SigPortNum, sonusH248SigProto }
    STATUS          current
    DESCRIPTION     
            "This trap indicates that a H248 signaling port is opened."
    ::= { sonusBgfMIBNotificationsPrefix 13 }

sonusH248SigPortCloseNotification NOTIFICATION-TYPE
    OBJECTS         { sonusAlarmNodeID, sonusAlarmLevel, 
                      sonusAlarmSequenceId, sonusAlarmTime, 
                      sonusAlarmDescription, sonusH248SigPortIpAddress, 
                      sonusH248SigPortNum, sonusH248SigProto }
    STATUS          current
    DESCRIPTION     
            "This trap indicates that a call signaling port is closed."
    ::= { sonusBgfMIBNotificationsPrefix 14 }

sonusH248ScNotificationClear NOTIFICATION-TYPE
    OBJECTS         { sonusAlarmNodeID, sonusAlarmLevel, 
                      sonusAlarmSequenceId, sonusAlarmTime, 
                      sonusAlarmDescription, sonusH248SigRemoteIpAddr, 
                      sonusH248SigLocalIpAddr, sonusH248SigScMethod, 
                      sonusH248SigMid }
    STATUS          current
    DESCRIPTION     
            "This trap indicates the Service change is cleared."
    ::= { sonusBgfMIBNotificationsPrefix 15 }

sonusSbxGwSigChanOpenNotification NOTIFICATION-TYPE
    OBJECTS         { sonusAlarmNodeID, sonusAlarmLevel, 
                      sonusAlarmSequenceId, sonusAlarmTime, 
                      sonusAlarmDescription, sonusGwRemoteGwAddr }
    STATUS          current
    DESCRIPTION     
            "This trap indicates that a Call Signaling Link to a Remote Gateway has been sucessfully opened."
    ::= { sonusGatewaySignallingMIBNotificationsPrefix 1 }

sonusSbxGwSigChanCloseNotification NOTIFICATION-TYPE
    OBJECTS         { sonusAlarmNodeID, sonusAlarmLevel, 
                      sonusAlarmSequenceId, sonusAlarmTime, 
                      sonusAlarmDescription, sonusGwRemoteGwAddr, 
                      sonusGwCloseReasonCode }
    STATUS          current
    DESCRIPTION     
            "This trap indicates that a Call Signaling Link to a Remote Gateway has been closed."
    ::= { sonusGatewaySignallingMIBNotificationsPrefix 2 }

sonusSbxGwSigChanOpenAttemptNotification NOTIFICATION-TYPE
    OBJECTS         { sonusAlarmNodeID, sonusAlarmLevel, 
                      sonusAlarmSequenceId, sonusAlarmTime, 
                      sonusAlarmDescription, sonusGwRemoteGwAddr }
    STATUS          current
    DESCRIPTION     
            "This trap indicates that a request to Open a Call Signaling Link has been sent to a Remote Gateway."
    ::= { sonusGatewaySignallingMIBNotificationsPrefix 3 }

sonusSbxGwSigChanRetryTimerExpiredNotification NOTIFICATION-TYPE
    OBJECTS         { sonusAlarmNodeID, sonusAlarmLevel, 
                      sonusAlarmSequenceId, sonusAlarmTime, 
                      sonusAlarmDescription, sonusGwRemoteGwAddr }
    STATUS          current
    DESCRIPTION     
            "This trap indicates that attempts to recover a Call Signaling Link to a Remote GW have failed."
    ::= { sonusGatewaySignallingMIBNotificationsPrefix 4 }

sonusSbxGwTrunkGroupInServiceNotification NOTIFICATION-TYPE
    OBJECTS         { sonusAlarmNodeID, sonusAlarmLevel, 
                      sonusAlarmSequenceId, sonusAlarmTime, 
                      sonusAlarmDescription, sonusGwSigTgName }
    STATUS          current
    DESCRIPTION     
            "This trap indicates that the Gateway Trunk Group was put
             into service by maintenance staff."
    ::= { sonusGatewaySignallingMIBNotificationsPrefix 5 }

sonusSbxGwSigTrunkGroupOutOfServiceNotification NOTIFICATION-TYPE
    OBJECTS         { sonusAlarmNodeID, sonusAlarmLevel, 
                      sonusAlarmSequenceId, sonusAlarmTime, 
                      sonusAlarmDescription, sonusGwSigTgName }
    STATUS          current
    DESCRIPTION     
            "This trap indicates that the Gateway Trunk Group was taken
             out of service by maintenance staff."
    ::= { sonusGatewaySignallingMIBNotificationsPrefix 6 }

sonusSbxGwSigChanOpenNotificationV6 NOTIFICATION-TYPE
    OBJECTS         { sonusAlarmNodeID, sonusAlarmLevel, 
                      sonusAlarmSequenceId, sonusAlarmTime, 
                      sonusAlarmDescription, sonusGwRemoteGw6Addr }
    STATUS          current
    DESCRIPTION     
            "This trap indicates that a Call Signaling IPV6 Link to a Remote Gateway has been sucessfully opened."
    ::= { sonusGatewaySignallingMIBNotificationsPrefix 7 }

sonusSbxGwSigChanOpenAttemptNotificationV6 NOTIFICATION-TYPE
    OBJECTS         { sonusAlarmNodeID, sonusAlarmLevel, 
                      sonusAlarmSequenceId, sonusAlarmTime, 
                      sonusAlarmDescription, sonusGwRemoteGw6Addr }
    STATUS          current
    DESCRIPTION     
            "This trap indicates that a request to Open a Call Signaling IPV6 Link has been sent to a Remote Gateway."
    ::= { sonusGatewaySignallingMIBNotificationsPrefix 8 }

sonusSbxGwSigChanRetryTimerExpiredNotificationV6 NOTIFICATION-TYPE
    OBJECTS         { sonusAlarmNodeID, sonusAlarmLevel, 
                      sonusAlarmSequenceId, sonusAlarmTime, 
                      sonusAlarmDescription, sonusGwRemoteGw6Addr }
    STATUS          current
    DESCRIPTION     
            "This trap indicates that attempts to recover a Call Signaling IPV6 Link to a Remote GW have failed."
    ::= { sonusGatewaySignallingMIBNotificationsPrefix 9 }

sonusSbxGwSigChanCloseNotificationV6 NOTIFICATION-TYPE
    OBJECTS         { sonusAlarmNodeID, sonusAlarmLevel, 
                      sonusAlarmSequenceId, sonusAlarmTime, 
                      sonusAlarmDescription, sonusGwRemoteGw6Addr, 
                      sonusGwCloseReasonCode }
    STATUS          current
    DESCRIPTION     
            "This trap indicates that a IPV6 Call Signaling Link to a Remote Gateway has been closed."
    ::= { sonusGatewaySignallingMIBNotificationsPrefix 10 }

sonusSbxCallRejectsDueToSessionLicenseNotification NOTIFICATION-TYPE
    OBJECTS         { sonusAlarmNodeID, sonusAlarmLevel, 
                      sonusAlarmSequenceId, sonusAlarmTime, 
                      sonusAlarmDescription, sonusSessLicenseLimit }
    STATUS          current
    DESCRIPTION     
            "This Trap is generated when either pass-through or
             transcoded sessions fail to setup due to the lack of a 
             valid session license or if the total number of active 
             sessions has reached the session license limits thereby 
             unable to complete newer calls."
    ::= { sonusOrcaLicenseMIBNotificationsPrefix 1 }

sonusSbxCallRejectsDueToSessionLicenseClearNotification NOTIFICATION-TYPE
    OBJECTS         { sonusAlarmNodeID, sonusAlarmLevel, 
                      sonusAlarmSequenceId, sonusAlarmTime, 
                      sonusAlarmDescription, sonusSessLicenseLimit }
    STATUS          current
    DESCRIPTION     
            "This Trap is not actually raised, but used to fool the alarm framework.
             If an application raises this trap, the comment has to be revisited"
    ::= { sonusOrcaLicenseMIBNotificationsPrefix 2 }

sonusSbxLicensedSessionsThresholdReachedNotification NOTIFICATION-TYPE
    OBJECTS         { sonusAlarmNodeID, sonusAlarmLevel, 
                      sonusAlarmSequenceId, sonusAlarmTime, 
                      sonusAlarmDescription, sonusConcurrentCalls, 
                      sonusSessLicenseLimit, sonusSessionsThreshold }
    STATUS          current
    DESCRIPTION     
            "This trap indicates the licensed sessions notification threshold has been reached or exceeded."
    ::= { sonusOrcaLicenseMIBNotificationsPrefix 3 }

sonusSbxCallRejectsDueToNotAbleToAcquireAdvancedERELicense NOTIFICATION-TYPE
    OBJECTS         { sonusAlarmNodeID, sonusAlarmLevel, 
                      sonusAlarmSequenceId, sonusAlarmTime, 
                      sonusAlarmDescription, sonusAlarmName, 
                      sonusAlarmReason }
    STATUS          deprecated
    DESCRIPTION     
            "This Trap is generated when the system is unable to proceed to call 
             processing due to the inability to acquire an Advanced ERE license.
             ."
    ::= { sonusOrcaLicenseMIBNotificationsPrefix 4 }

sonusSbxAcquiredAdvancedERELicenseNotification NOTIFICATION-TYPE
    OBJECTS         { sonusAlarmNodeID, sonusAlarmLevel, 
                      sonusAlarmSequenceId, sonusAlarmTime, 
                      sonusAlarmDescription, sonusAlarmName, 
                      sonusAlarmReason }
    STATUS          deprecated
    DESCRIPTION     
            "This is clearing as SBX aquired an Advanced ERE license."
    ::= { sonusOrcaLicenseMIBNotificationsPrefix 5 }

sonusSbxMinimumLicenseCountThresholdNotReached NOTIFICATION-TYPE
    OBJECTS         { sonusAlarmNodeID, sonusAlarmLevel, 
                      sonusAlarmSequenceId, sonusAlarmTime, 
                      sonusAlarmDescription, sonusAlarmName, 
                      sonusSessionsThreshold, sonusSessLicenseLimit }
    STATUS          current
    DESCRIPTION     
            "This Trap is generated when when the SBC-POL-RTU license is configured with a 
             minimum threshold (this will match the SBC-RTU minimum license count) that cannot 
             be returned by the site license server."
    ::= { sonusOrcaLicenseMIBNotificationsPrefix 6 }

sonusSbxClearMinimumLicenseCountThresholdNotReached NOTIFICATION-TYPE
    OBJECTS         { sonusAlarmNodeID, sonusAlarmLevel, 
                      sonusAlarmSequenceId, sonusAlarmTime, 
                      sonusAlarmDescription, sonusAlarmName, 
                      sonusSessionsThreshold, sonusSessLicenseLimit }
    STATUS          current
    DESCRIPTION     
            "Clear the trap ."
    ::= { sonusOrcaLicenseMIBNotificationsPrefix 7 }

sonusSbxMaximumLicenseCountThresholdExceeded NOTIFICATION-TYPE
    OBJECTS         { sonusAlarmNodeID, sonusAlarmLevel, 
                      sonusAlarmSequenceId, sonusAlarmTime, 
                      sonusAlarmDescription, sonusAlarmName, 
                      sonusSessionsThreshold, sonusSessLicenseLimit }
    STATUS          current
    DESCRIPTION     
            "This Trap is generated when when the SBC-POL-RTU license is configured with a maximum 
             threshold (this will match the SBC-RTU maximum license count) that is lower than the 
             current license count returned by the site license server.when the SBC-POL-RTU license 
             is configured with a maximum threshold (this will match the SBC-RTU maximum license count) 
             that is lower than the current license count returned by the site license server."
    ::= { sonusOrcaLicenseMIBNotificationsPrefix 8 }

sonusSbxClearMaximumLicenseCountThresholdExceeded NOTIFICATION-TYPE
    OBJECTS         { sonusAlarmNodeID, sonusAlarmLevel, 
                      sonusAlarmSequenceId, sonusAlarmTime, 
                      sonusAlarmDescription, sonusAlarmName, 
                      sonusSessionsThreshold, sonusSessLicenseLimit }
    STATUS          current
    DESCRIPTION     
            "Clear the trap ."
    ::= { sonusOrcaLicenseMIBNotificationsPrefix 9 }

sonusSbxLicensedEncryptSessionsThresholdReachedNotification NOTIFICATION-TYPE
    OBJECTS         { sonusAlarmNodeID, sonusAlarmLevel, 
                      sonusAlarmSequenceId, sonusAlarmTime, 
                      sonusAlarmDescription, sonusSessionsThreshold, 
                      sonusActiveSessionCount, sonusSessLicenseLimit }
    STATUS          deprecated
    DESCRIPTION     
            "This trap is only applicable when the SBC is using local licenses.
             configured threshold is reached for ENCRYPT sessions."
    ::= { sonusOrcaLicenseMIBNotificationsPrefix 10 }

sonusSbxServiceDeniedDueToUnavailableLicenseNotification NOTIFICATION-TYPE
    OBJECTS         { sonusAlarmNodeID, sonusAlarmLevel, 
                      sonusAlarmSequenceId, sonusAlarmTime, 
                      sonusAlarmDescription, sonusAlarmName, 
                      sonusActiveSessionCount }
    STATUS          deprecated
    DESCRIPTION     
            "A licensed service has been denied due to lack of licenses.
             This trap is only applicable when the SBC is using Local/Network licenses."
    ::= { sonusOrcaLicenseMIBNotificationsPrefix 11 }

sonusSbxLicensedSrtpSessionsThresholdReachedNotification NOTIFICATION-TYPE
    OBJECTS         { sonusAlarmNodeID, sonusAlarmLevel, 
                      sonusAlarmSequenceId, sonusAlarmTime, 
                      sonusAlarmDescription, sonusSessionsThreshold, 
                      sonusActiveSessionCount, sonusSessLicenseLimit }
    STATUS          deprecated
    DESCRIPTION     
            "This trap is fired when configured threshold is reached for SRTP session
             only in LOCAL mode."
    ::= { sonusOrcaLicenseMIBNotificationsPrefix 12 }

sonusSbxLicensedVideoSessionsThresholdReachedNotification NOTIFICATION-TYPE
    OBJECTS         { sonusAlarmNodeID, sonusAlarmLevel, 
                      sonusAlarmSequenceId, sonusAlarmTime, 
                      sonusAlarmDescription, sonusSessionsThreshold, 
                      sonusActiveSessionCount, sonusSessLicenseLimit }
    STATUS          deprecated
    DESCRIPTION     
            "This trap is fired when configured threshold is reached for VIDEO session
             only in LOCAL mode."
    ::= { sonusOrcaLicenseMIBNotificationsPrefix 13 }

sonusSbxLicensedAmrNbSessionsThresholdReachedNotification NOTIFICATION-TYPE
    OBJECTS         { sonusAlarmNodeID, sonusAlarmLevel, 
                      sonusAlarmSequenceId, sonusAlarmTime, 
                      sonusAlarmDescription, sonusSessionsThreshold, 
                      sonusActiveSessionCount, sonusSessLicenseLimit }
    STATUS          current
    DESCRIPTION     
            "This trap is only applicable when the SBC is using local licenses and
             configured threshold is reached for AMRNB sessions."
    ::= { sonusOrcaLicenseMIBNotificationsPrefix 14 }

sonusSbxLicensedAmrWbSessionsThresholdReachedNotification NOTIFICATION-TYPE
    OBJECTS         { sonusAlarmNodeID, sonusAlarmLevel, 
                      sonusAlarmSequenceId, sonusAlarmTime, 
                      sonusAlarmDescription, sonusSessionsThreshold, 
                      sonusActiveSessionCount, sonusSessLicenseLimit }
    STATUS          current
    DESCRIPTION     
            "This trap is only applicable when the SBC is using local licenses and
             configured threshold is reached for AMRWB sessions."
    ::= { sonusOrcaLicenseMIBNotificationsPrefix 15 }

sonusSbxLicensedEvrcSessionsThresholdReachedNotification NOTIFICATION-TYPE
    OBJECTS         { sonusAlarmNodeID, sonusAlarmLevel, 
                      sonusAlarmSequenceId, sonusAlarmTime, 
                      sonusAlarmDescription, sonusSessionsThreshold, 
                      sonusActiveSessionCount, sonusSessLicenseLimit }
    STATUS          current
    DESCRIPTION     
            "This trap is only applicable when the SBC is using local licenses and
             configured threshold is reached for EVRC sessions."
    ::= { sonusOrcaLicenseMIBNotificationsPrefix 16 }

sonusSbxLicensedNiceRecThresholdReachedNotification NOTIFICATION-TYPE
    OBJECTS         { sonusAlarmNodeID, sonusAlarmLevel, 
                      sonusAlarmSequenceId, sonusAlarmTime, 
                      sonusAlarmDescription, sonusSessionsThreshold, 
                      sonusActiveSessionCount, sonusSessLicenseLimit }
    STATUS          deprecated
    DESCRIPTION     
            "This trap is only applicable when the SBC is using local licenses and
             configured threshold is reached for Nice Rec  sessions."
    ::= { sonusOrcaLicenseMIBNotificationsPrefix 17 }

sonusSbxLicensedSipRecThresholdReachedNotification NOTIFICATION-TYPE
    OBJECTS         { sonusAlarmNodeID, sonusAlarmLevel, 
                      sonusAlarmSequenceId, sonusAlarmTime, 
                      sonusAlarmDescription, sonusSessionsThreshold, 
                      sonusActiveSessionCount, sonusSessLicenseLimit }
    STATUS          deprecated
    DESCRIPTION     
            "This trap is only applicable when the SBC is using local licenses and
             configured threshold is reached for SIPREC sessions."
    ::= { sonusOrcaLicenseMIBNotificationsPrefix 18 }

sonusSbxLicensedVdspThresholdReachedNotification NOTIFICATION-TYPE
    OBJECTS         { sonusAlarmNodeID, sonusAlarmLevel, 
                      sonusAlarmSequenceId, sonusAlarmTime, 
                      sonusAlarmDescription, sonusSessionsThreshold, 
                      sonusActiveSessionCount, sonusSessLicenseLimit }
    STATUS          current
    DESCRIPTION     
            "This trap is only applicable when the SBC is using local licenses and
             configured threshold is reached for VDSP sessions."
    ::= { sonusOrcaLicenseMIBNotificationsPrefix 19 }

sonusSbxLicensedMrfSessionsThresholdReachedNotification NOTIFICATION-TYPE
    OBJECTS         { sonusAlarmNodeID, sonusAlarmLevel, 
                      sonusAlarmSequenceId, sonusAlarmTime, 
                      sonusAlarmDescription, sonusSessionsThreshold, 
                      sonusActiveSessionCount, sonusSessLicenseLimit }
    STATUS          deprecated
    DESCRIPTION     
            "This trap is only applicable when the SBC is using local licenses and
             configured threshold is reached for MRF sessions."
    ::= { sonusOrcaLicenseMIBNotificationsPrefix 20 }

sonusSbxMandatoryLicenseUnavailable NOTIFICATION-TYPE
    OBJECTS         { sonusAlarmNodeID, sonusAlarmLevel, 
                      sonusAlarmSequenceId, sonusAlarmTime, 
                      sonusAlarmDescription, sonusAlarmName }
    STATUS          current
    DESCRIPTION     
            "This Alarm is generated when Mandatory licenses are specified in the RLT but 
             the SLS was unable to return at least 1 license of each mandatory license specified.
             Mandatory Licenses : SBC-RTU, SWE-INSTANCE,SBC-PSX-RTU,SBC-POL-RTU.
             ."
    ::= { sonusOrcaLicenseMIBNotificationsPrefix 21 }

sonusSbxMandatoryLicenseAvailable NOTIFICATION-TYPE
    OBJECTS         { sonusAlarmNodeID, sonusAlarmLevel, 
                      sonusAlarmSequenceId, sonusAlarmTime, 
                      sonusAlarmDescription, sonusAlarmName }
    STATUS          current
    DESCRIPTION     
            "Mandatory license successfully retrieved from the license server.
             Mandatory Licenses : SBC-RTU, SWE-INSTANCE,SBC-PSX-RTU,SBC-POL-RTU."
    ::= { sonusOrcaLicenseMIBNotificationsPrefix 22 }

sonusSbxServiceLicenseUnavailable NOTIFICATION-TYPE
    OBJECTS         { sonusAlarmNodeID, sonusAlarmLevel, 
                      sonusAlarmSequenceId, sonusAlarmTime, 
                      sonusAlarmDescription, sonusAlarmName }
    STATUS          current
    DESCRIPTION     
            "This Alarm is generated when Service licenses are specified in the RLT but 
             the SLS was unable to return at least 1 license of each mandatory license specified.
             ."
    ::= { sonusOrcaLicenseMIBNotificationsPrefix 23 }

sonusSbxServiceLicenseAvailable NOTIFICATION-TYPE
    OBJECTS         { sonusAlarmNodeID, sonusAlarmLevel, 
                      sonusAlarmSequenceId, sonusAlarmTime, 
                      sonusAlarmDescription, sonusAlarmName }
    STATUS          current
    DESCRIPTION     
            "The licensed service functionality will be Allowed."
    ::= { sonusOrcaLicenseMIBNotificationsPrefix 24 }

sonusSbxLicensedServiceDeniedDueToLicenseLimit NOTIFICATION-TYPE
    OBJECTS         { sonusAlarmNodeID, sonusAlarmLevel, 
                      sonusAlarmSequenceId, sonusAlarmTime, 
                      sonusAlarmDescription, sonusAlarmName, 
                      sonusActiveSessionCount }
    STATUS          current
    DESCRIPTION     
            "A licensed service has been denied due to lack of licenses.
             This trap is only applicable when the SBC is using Local/Network licenses."
    ::= { sonusOrcaLicenseMIBNotificationsPrefix 25 }

sonusSbxLicensedEvsSessionsThresholdReachedNotification NOTIFICATION-TYPE
    OBJECTS         { sonusAlarmNodeID, sonusAlarmLevel, 
                      sonusAlarmSequenceId, sonusAlarmTime, 
                      sonusAlarmDescription, sonusSessionsThreshold, 
                      sonusActiveSessionCount, sonusSessLicenseLimit }
    STATUS          current
    DESCRIPTION     
            "This trap is only applicable when the SBC is using local licenses and
             configured threshold is reached for EVS sessions."
    ::= { sonusOrcaLicenseMIBNotificationsPrefix 28 }

sonusSbxCallRejectsDueToSlbSessionLicenseNotification NOTIFICATION-TYPE
    OBJECTS         { sonusAlarmNodeID, sonusAlarmLevel, 
                      sonusAlarmSequenceId, sonusAlarmTime, 
                      sonusAlarmDescription, sonusSessLicenseLimit }
    STATUS          current
    DESCRIPTION     
            "This Trap is generated when either pass-through or
             transcoded sessions fail to setup due to the lack of a 
             valid slb session license or if the total number of active 
             slb sessions has reached the slb session license limits thereby 
             unable to complete newer calls."
    ::= { sonusOrcaLicenseMIBNotificationsPrefix 29 }

sonusSbxLicensedSlbSessionsThresholdReachedNotification NOTIFICATION-TYPE
    OBJECTS         { sonusAlarmNodeID, sonusAlarmLevel, 
                      sonusAlarmSequenceId, sonusAlarmTime, 
                      sonusAlarmDescription, sonusConcurrentCalls, 
                      sonusSessLicenseLimit, sonusSessionsThreshold }
    STATUS          current
    DESCRIPTION     
            "This trap indicates the licensed slb sessions notification threshold has been reached or exceeded."
    ::= { sonusOrcaLicenseMIBNotificationsPrefix 30 }

sonusSbxFeatureLicenseUnavailable NOTIFICATION-TYPE
    OBJECTS         { sonusAlarmNodeID, sonusAlarmLevel, 
                      sonusAlarmSequenceId, sonusAlarmTime, 
                      sonusAlarmDescription, sonusAlarmName }
    STATUS          current
    DESCRIPTION     
            "This alarm is generated when the mandatory feature license is not available.
             ."
    ::= { sonusOrcaLicenseMIBNotificationsPrefix 31 }

sonusSbxFeatureLicenseAvailable NOTIFICATION-TYPE
    OBJECTS         { sonusAlarmNodeID, sonusAlarmLevel, 
                      sonusAlarmSequenceId, sonusAlarmTime, 
                      sonusAlarmDescription, sonusAlarmName }
    STATUS          current
    DESCRIPTION     
            "This alarm is generated when the feature license becomes available."
    ::= { sonusOrcaLicenseMIBNotificationsPrefix 32 }

sonusDatabaseConfigPolicyDataOutOfSyncNotification NOTIFICATION-TYPE
    OBJECTS         { sonusAlarmNodeID, sonusAlarmLevel, 
                      sonusAlarmSequenceId, sonusAlarmTime, 
                      sonusAlarmDescription, sonusSbxSystemName, 
                      sonusSbxServerName, sonusSbxRedundencyRole }
    STATUS          current
    DESCRIPTION     
            "This trap indicates that the config policy databases on the active are out of sync and manual action is required."
    ::= { sonusDatabaseMIBNotificationsPrefix 1 }

sonusDatabaseConfigPolicyDataInSyncNotification NOTIFICATION-TYPE
    OBJECTS         { sonusAlarmNodeID, sonusAlarmLevel, 
                      sonusAlarmSequenceId, sonusAlarmTime, 
                      sonusAlarmDescription, sonusSbxSystemName, 
                      sonusSbxServerName, sonusSbxRedundencyRole }
    STATUS          current
    DESCRIPTION     
            "This trap indicates that the config policy databases on the active are in sync."
    ::= { sonusDatabaseMIBNotificationsPrefix 2 }

sonusDatabasePolicyDataOutOfSyncNotification NOTIFICATION-TYPE
    OBJECTS         { sonusAlarmNodeID, sonusAlarmLevel, 
                      sonusAlarmSequenceId, sonusAlarmTime, 
                      sonusAlarmDescription, sonusSbxSystemName, 
                      sonusSbxServerName, sonusSbxPeerServerName }
    STATUS          current
    DESCRIPTION     
            "This trap indicates that the policy databases on active and standby are out of sync and manual action is required."
    ::= { sonusDatabaseMIBNotificationsPrefix 3 }

sonusDatabasePolicyDataInSyncNotification NOTIFICATION-TYPE
    OBJECTS         { sonusAlarmNodeID, sonusAlarmLevel, 
                      sonusAlarmSequenceId, sonusAlarmTime, 
                      sonusAlarmDescription, sonusSbxSystemName, 
                      sonusSbxServerName, sonusSbxPeerServerName }
    STATUS          current
    DESCRIPTION     
            "This trap indicates that the policy databases on active and standby are in sync."
    ::= { sonusDatabaseMIBNotificationsPrefix 4 }

sonusSbxResourceThresholdReachedNotification NOTIFICATION-TYPE
    OBJECTS         { sonusAlarmNodeID, sonusAlarmLevel, 
                      sonusAlarmSequenceId, sonusAlarmTime, 
                      sonusAlarmDescription, sonusResource, 
                      sonusEntityType, sonusEntityName, 
                      sonusSharedCacLimitPoolProfileId, 
                      sonusResourceUsage, sonusResourceLimit, 
                      sonusResourceThreshold }
    STATUS          current
    DESCRIPTION     
            "This trap indicates the resource usage notification threshold has been reached or exceeded."
    ::= { sonusResourceMIBNotificationsPrefix 1 }

sonusSbxIpPeerKpiCriticalThresholdNotification NOTIFICATION-TYPE
    OBJECTS         { sonusAlarmNodeID, sonusAlarmLevel, 
                      sonusAlarmSequenceId, sonusAlarmTime, 
                      sonusAlarmDescription, sonusPeerName, 
                      sonusZoneName, sonusKpi, sonusCurrentKpiValue }
    STATUS          current
    DESCRIPTION     
            "This IP peer has been put to Temporary OOS and shall not be chosen for Routing"
    ::= { sonusPeerResourcesMIBNotificationsPrefix 1 }

sonusSbxIpPeerKpiCriticalThresholdClearedNotification NOTIFICATION-TYPE
    OBJECTS         { sonusAlarmNodeID, sonusAlarmLevel, 
                      sonusAlarmSequenceId, sonusAlarmTime, 
                      sonusAlarmDescription, sonusPeerName, 
                      sonusZoneName, sonusKpi, sonusCurrentKpiValue }
    STATUS          current
    DESCRIPTION     
            "This trap indicates that critical QOS KPI condition in the IP PEER got cleared"
    ::= { sonusPeerResourcesMIBNotificationsPrefix 2 }

sonusSbxImPriOperStateChange NOTIFICATION-TYPE
    OBJECTS         { sonusAlarmNodeID, sonusAlarmLevel, 
                      sonusAlarmSequenceId, sonusAlarmTime, 
                      sonusAlarmDescription, sonusImStatusPriOperState }
    STATUS          current
    DESCRIPTION     
            "This trap indicates the intercept manager primary operational state has changed."
    ::= { sonusInterceptManagerMIBNotificationsPrefix 1 }

sonusSbxImSecOperStateChange NOTIFICATION-TYPE
    OBJECTS         { sonusAlarmNodeID, sonusAlarmLevel, 
                      sonusAlarmSequenceId, sonusAlarmTime, 
                      sonusAlarmDescription, sonusImStatusSecOperState }
    STATUS          current
    DESCRIPTION     
            "This trap indicates the intercept manager secondary operational state has changed."
    ::= { sonusInterceptManagerMIBNotificationsPrefix 2 }

sonusSbxImMediationServerTcpLinkDown NOTIFICATION-TYPE
    OBJECTS         { sonusAlarmNodeID, sonusAlarmLevel, 
                      sonusAlarmSequenceId, sonusAlarmTime, 
                      sonusAlarmDescription, sonusImMediationServerName, 
                      sonusImMediationServerState, 
                      sonusImMediationServerInterceptMediaType }
    STATUS          current
    DESCRIPTION     
            "TCP link towards Mediation Server is down"
    ::= { sonusInterceptManagerMIBNotificationsPrefix 3 }

sonusSbxImMediationServerTcpLinkUp NOTIFICATION-TYPE
    OBJECTS         { sonusAlarmNodeID, sonusAlarmLevel, 
                      sonusAlarmSequenceId, sonusAlarmTime, 
                      sonusAlarmDescription, sonusImMediationServerName, 
                      sonusImMediationServerState, 
                      sonusImMediationServerInterceptMediaType }
    STATUS          current
    DESCRIPTION     
            "TCP link towards Mediation Server is established."
    ::= { sonusInterceptManagerMIBNotificationsPrefix 4 }

sonusSbxImMediationServerX2MsgBufferFull NOTIFICATION-TYPE
    OBJECTS         { sonusAlarmNodeID, sonusAlarmLevel, 
                      sonusAlarmSequenceId, sonusAlarmTime, 
                      sonusAlarmDescription, sonusImMediationServerName }
    STATUS          current
    DESCRIPTION     
            "Mediation server or diameter realm X2 Message Buffer is Full"
    ::= { sonusInterceptManagerMIBNotificationsPrefix 5 }

sonusSbxImMediationServerX2MsgBufferAvailable NOTIFICATION-TYPE
    OBJECTS         { sonusAlarmNodeID, sonusAlarmLevel, 
                      sonusAlarmSequenceId, sonusAlarmTime, 
                      sonusAlarmDescription, sonusImMediationServerName }
    STATUS          current
    DESCRIPTION     
            "Mediation server or diameter realm X2 Message Buffer is available"
    ::= { sonusInterceptManagerMIBNotificationsPrefix 6 }

sonusSbxMtrmPortAvailNotification NOTIFICATION-TYPE
    OBJECTS         { sonusAlarmNodeID, sonusAlarmLevel, 
                      sonusAlarmSequenceId, sonusAlarmTime, 
                      sonusAlarmDescription, sonusMtrmPortIndex }
    STATUS          current
    DESCRIPTION     
            "This trap indicates that MTRM peer connection is available."
    ::= { sonusMtrmMIBNotificationsPrefix 1 }

sonusSbxMtrmPortUnAvailNotification NOTIFICATION-TYPE
    OBJECTS         { sonusAlarmNodeID, sonusAlarmLevel, 
                      sonusAlarmSequenceId, sonusAlarmTime, 
                      sonusAlarmDescription, sonusMtrmPortIndex }
    STATUS          current
    DESCRIPTION     
            "This trap indicates that MTRM peer connection is unavailable."
    ::= { sonusMtrmMIBNotificationsPrefix 2 }

sonusSbxMtrmPortSwitchoverNotification NOTIFICATION-TYPE
    OBJECTS         { sonusAlarmNodeID, sonusAlarmLevel, 
                      sonusAlarmSequenceId, sonusAlarmTime, 
                      sonusAlarmDescription, sonusMtrmPortIndex }
    STATUS          current
    DESCRIPTION     
            "This trap indicates that MTRM client connection is now switched to secondary server."
    ::= { sonusMtrmMIBNotificationsPrefix 3 }

sonusOcspConnectionFailed NOTIFICATION-TYPE
    OBJECTS         { sonusAlarmNodeID, sonusAlarmLevel, 
                      sonusAlarmSequenceId, sonusAlarmTime, 
                      sonusAlarmDescription, sonusSecurityOcspUrlName }
    STATUS          current
    DESCRIPTION     
            "TCP connection to a OCSP Responder cannot be established."
    ::= { sonusSecurityMIBNotificationsPrefix 1 }

sonusInvalidOcspResponseReceived NOTIFICATION-TYPE
    OBJECTS         { sonusAlarmNodeID, sonusAlarmLevel, 
                      sonusAlarmSequenceId, sonusAlarmTime, 
                      sonusAlarmDescription, sonusSecurityOcspUrlName }
    STATUS          current
    DESCRIPTION     
            "An invalid OCSP response was received."
    ::= { sonusSecurityMIBNotificationsPrefix 2 }

sonusNoValidOcspResponseReceived NOTIFICATION-TYPE
    OBJECTS         { sonusAlarmNodeID, sonusAlarmLevel, 
                      sonusAlarmSequenceId, sonusAlarmTime, 
                      sonusAlarmDescription, sonusSecurityOcspUrlName }
    STATUS          current
    DESCRIPTION     
            "No Valid OCSP response was received upon the expiry of the OCSP response timer."
    ::= { sonusSecurityMIBNotificationsPrefix 3 }

sonusOcspResponseUnknown NOTIFICATION-TYPE
    OBJECTS         { sonusAlarmNodeID, sonusAlarmLevel, 
                      sonusAlarmSequenceId, sonusAlarmTime, 
                      sonusAlarmDescription, sonusSecurityOcspUrlName, 
                      sonusSecurityOcspResponseStatus }
    STATUS          current
    DESCRIPTION     
            "A valid OCSP response was received with certificate status unknown."
    ::= { sonusSecurityMIBNotificationsPrefix 4 }

sonusOcspExceptionResponse NOTIFICATION-TYPE
    OBJECTS         { sonusAlarmNodeID, sonusAlarmLevel, 
                      sonusAlarmSequenceId, sonusAlarmTime, 
                      sonusAlarmDescription, sonusSecurityOcspUrlName, 
                      sonusSecurityOcspResponseStatus }
    STATUS          current
    DESCRIPTION     
            "An exception OCSP response was received from OCSP responder - malformedRequest, internalError, tryLater, sigRequired, unauthorized"
    ::= { sonusSecurityMIBNotificationsPrefix 5 }

sonusVnfmConnectionFailed NOTIFICATION-TYPE
    OBJECTS         { sonusAlarmNodeID, sonusAlarmLevel, 
                      sonusAlarmSequenceId, sonusAlarmTime, 
                      sonusAlarmDescription, sonusVnfmUrlName }
    STATUS          current
    DESCRIPTION     
            "SBC connection to VNFM cannot be established."
    ::= { sonusSecurityMIBNotificationsPrefix 6 }

sonusVnfmConnectionSucceeded NOTIFICATION-TYPE
    OBJECTS         { sonusAlarmNodeID, sonusAlarmLevel, 
                      sonusAlarmSequenceId, sonusAlarmTime, 
                      sonusAlarmDescription, sonusVnfmUrlName }
    STATUS          current
    DESCRIPTION     
            "SBC connection to VNFM is recovered."
    ::= { sonusSecurityMIBNotificationsPrefix 7 }

sonusSbxLvmPhyPacketPortDownNotification NOTIFICATION-TYPE
    OBJECTS         { sonusAlarmNodeID, sonusAlarmLevel, 
                      sonusAlarmSequenceId, sonusAlarmTime, 
                      sonusAlarmDescription, sonusNrsCeName, 
                      sonusNrsPortName }
    STATUS          current
    DESCRIPTION     
            "The physical packet port is down."
    ::= { sonusLvmMIBNotificationsPrefix 1 }

sonusSbxLvmPhyPacketPortUpNotification NOTIFICATION-TYPE
    OBJECTS         { sonusAlarmNodeID, sonusAlarmLevel, 
                      sonusAlarmSequenceId, sonusAlarmTime, 
                      sonusAlarmDescription, sonusNrsCeName, 
                      sonusNrsPortName }
    STATUS          current
    DESCRIPTION     
            "The physical packet port is up."
    ::= { sonusLvmMIBNotificationsPrefix 2 }

sonusSbxLvmPrimaryPhyPacketPortActiveNotification NOTIFICATION-TYPE
    OBJECTS         { sonusAlarmNodeID, sonusAlarmLevel, 
                      sonusAlarmSequenceId, sonusAlarmTime, 
                      sonusAlarmDescription, sonusNrsCeName, 
                      sonusNrsPortName, sonusLvmPortSwitchReason }
    STATUS          current
    DESCRIPTION     
            "The primary physical packet port is made ACTIVE."
    ::= { sonusLvmMIBNotificationsPrefix 3 }

sonusSbxLvmSecondaryPhyPacketPortActiveNotification NOTIFICATION-TYPE
    OBJECTS         { sonusAlarmNodeID, sonusAlarmLevel, 
                      sonusAlarmSequenceId, sonusAlarmTime, 
                      sonusAlarmDescription, sonusNrsCeName, 
                      sonusNrsPortName, sonusLvmPortSwitchReason }
    STATUS          current
    DESCRIPTION     
            "The secondary physical packet port is made ACTIVE."
    ::= { sonusLvmMIBNotificationsPrefix 4 }

sonusSbxLvmLinkDetectionGroupFailedNotification NOTIFICATION-TYPE
    OBJECTS         { sonusAlarmNodeID, sonusAlarmLevel, 
                      sonusAlarmSequenceId, sonusAlarmTime, 
                      sonusAlarmDescription, sonusNrsCeName, 
                      sonusNrsAddressContextName, 
                      sonusLvmLinkDetectionGroupName }
    STATUS          current
    DESCRIPTION     
            "The link detection group has failed."
    ::= { sonusLvmMIBNotificationsPrefix 5 }

sonusSbxLvmLinkDetectionGroupRestoredNotification NOTIFICATION-TYPE
    OBJECTS         { sonusAlarmNodeID, sonusAlarmLevel, 
                      sonusAlarmSequenceId, sonusAlarmTime, 
                      sonusAlarmDescription, sonusNrsCeName, 
                      sonusNrsAddressContextName, 
                      sonusLvmLinkDetectionGroupName }
    STATUS          current
    DESCRIPTION     
            "The link detection group has been restored."
    ::= { sonusLvmMIBNotificationsPrefix 6 }

sonusSbxLvmLinkDetectionGroupSwitchoverNotification NOTIFICATION-TYPE
    OBJECTS         { sonusAlarmNodeID, sonusAlarmLevel, 
                      sonusAlarmSequenceId, sonusAlarmTime, 
                      sonusAlarmDescription, sonusNrsCeName, 
                      sonusNrsAddressContextName, 
                      sonusLvmLinkDetectionGroupName }
    STATUS          current
    DESCRIPTION     
            "The link detection group has triggered a CE switchover."
    ::= { sonusLvmMIBNotificationsPrefix 7 }

sonusSbxLvmPrgLinkFailureToggleNotification NOTIFICATION-TYPE
    OBJECTS         { sonusAlarmNodeID, sonusAlarmLevel, 
                      sonusAlarmSequenceId, sonusAlarmTime, 
                      sonusAlarmDescription, sonusNrsCeName, 
                      sonusLvmPortRedundancyGroupName }
    STATUS          current
    DESCRIPTION     
            "Port Redundancy Group detected link failure toggling."
    ::= { sonusLvmMIBNotificationsPrefix 8 }

sonusSbxLvmPrgLinkFailureToggleClearedNotification NOTIFICATION-TYPE
    OBJECTS         { sonusAlarmNodeID, sonusAlarmLevel, 
                      sonusAlarmSequenceId, sonusAlarmTime, 
                      sonusAlarmDescription, sonusNrsCeName, 
                      sonusLvmPortRedundancyGroupName }
    STATUS          current
    DESCRIPTION     
            "Port Redundancy Group cleared link failure toggling."
    ::= { sonusLvmMIBNotificationsPrefix 9 }

sonusSbxLvmPrgSwitchoverToRecoverLinksNotification NOTIFICATION-TYPE
    OBJECTS         { sonusAlarmNodeID, sonusAlarmLevel, 
                      sonusAlarmSequenceId, sonusAlarmTime, 
                      sonusAlarmDescription }
    STATUS          current
    DESCRIPTION     
            "Initiating CE switchover as the system is unable to recover from port toggling."
    ::= { sonusLvmMIBNotificationsPrefix 10 }

sonusSbxDiamConnectionToRfAccountingServerGoesDown NOTIFICATION-TYPE
    OBJECTS         { sonusAlarmNodeID, sonusAlarmLevel, 
                      sonusAlarmSequenceId, sonusAlarmTime, 
                      sonusAlarmDescription, sonusRfAccountingServerName }
    STATUS          deprecated
    DESCRIPTION     
            "This trap has been replaced by sonusSbxDiamPeerConnectionDown."
    ::= { sonusDiamMIBNotificationsPrefix 1 }

sonusSbxDiamConnectionToRfAccountingServerGoesUp NOTIFICATION-TYPE
    OBJECTS         { sonusAlarmNodeID, sonusAlarmLevel, 
                      sonusAlarmSequenceId, sonusAlarmTime, 
                      sonusAlarmDescription, sonusRfAccountingServerName }
    STATUS          deprecated
    DESCRIPTION     
            "This trap has been replaced by sonusSbxDiamPeerConnectionUp"
    ::= { sonusDiamMIBNotificationsPrefix 2 }

sonusSbxDiamPeerConnectionDown NOTIFICATION-TYPE
    OBJECTS         { sonusAlarmNodeID, sonusAlarmLevel, 
                      sonusAlarmSequenceId, sonusAlarmTime, 
                      sonusAlarmDescription, sonusDiamPeerName, 
                      sonusDiamPeerIpAddress }
    STATUS          current
    DESCRIPTION     
            "Diameter Peer Connection is detected as lost or broken."
    ::= { sonusDiamMIBNotificationsPrefix 3 }

sonusSbxDiamPeerConnectionUp NOTIFICATION-TYPE
    OBJECTS         { sonusAlarmNodeID, sonusAlarmLevel, 
                      sonusAlarmSequenceId, sonusAlarmTime, 
                      sonusAlarmDescription, sonusDiamPeerName, 
                      sonusDiamPeerIpAddress }
    STATUS          current
    DESCRIPTION     
            "Diameter Peer Connection is established."
    ::= { sonusDiamMIBNotificationsPrefix 4 }

sonusSbxDnsServerBlacklistedNotification NOTIFICATION-TYPE
    OBJECTS         { sonusAlarmNodeID, sonusAlarmLevel, 
                      sonusAlarmSequenceId, sonusAlarmTime, 
                      sonusAlarmDescription, sonusDnsServerIp, 
                      sonusDnsServerPortNum, sonusDnsServerTransport }
    STATUS          current
    DESCRIPTION     
            "This alarms is raised when dns server consistently failed to send response 
             to sbx dns request . Dns Server will be moved to Blacklisting state "
    ::= { sonusDnsMIBNotificationsPrefix 1 }

sonusSbxDnsServerRecoveredNotification NOTIFICATION-TYPE
    OBJECTS         { sonusAlarmNodeID, sonusAlarmLevel, 
                      sonusAlarmSequenceId, sonusAlarmTime, 
                      sonusAlarmDescription, sonusDnsServerIp, 
                      sonusDnsServerPortNum, sonusDnsServerTransport }
    STATUS          current
    DESCRIPTION     
            "This alarms is raised when sbx  recoverd from blacklisted state "
    ::= { sonusDnsMIBNotificationsPrefix 2 }

sonusSbxRcodeErrorOnDnsQuery NOTIFICATION-TYPE
    OBJECTS         { sonusAlarmNodeID, sonusAlarmLevel, 
                      sonusAlarmSequenceId, sonusAlarmTime, 
                      sonusAlarmDescription, sonusDnsServerZoneId, 
                      sonusDnsIpAddr, sonusRcodeError, 
                      sonusDnsServerType }
    STATUS          current
    DESCRIPTION     
            "The DNS Server has encountered an RCODE error"
    ::= { sonusDnsMIBNotificationsPrefix 3 }

sonusSbxRcodeErrorClearNotification NOTIFICATION-TYPE
    OBJECTS         { sonusAlarmNodeID, sonusAlarmLevel, 
                      sonusAlarmSequenceId, sonusAlarmTime, 
                      sonusAlarmDescription, sonusDnsIpAddr }
    STATUS          current
    DESCRIPTION     
            "RCODE Alarm Monitor interval expired for DNS server "
    ::= { sonusDnsMIBNotificationsPrefix 4 }

sonusSbxRcodeErrorOnDnsQueryV6 NOTIFICATION-TYPE
    OBJECTS         { sonusAlarmNodeID, sonusAlarmLevel, 
                      sonusAlarmSequenceId, sonusAlarmTime, 
                      sonusAlarmDescription, sonusDnsServerZoneId, 
                      sonusDnsIpV6Addr, sonusRcodeError, 
                      sonusDnsServerType }
    STATUS          current
    DESCRIPTION     
            "The DNS Server has encountered an RCODE error"
    ::= { sonusDnsMIBNotificationsPrefix 5 }

sonusSbxRcodeErrorClearNotificationV6 NOTIFICATION-TYPE
    OBJECTS         { sonusAlarmNodeID, sonusAlarmLevel, 
                      sonusAlarmSequenceId, sonusAlarmTime, 
                      sonusAlarmDescription, sonusDnsIpV6Addr }
    STATUS          current
    DESCRIPTION     
            "RCODE Alarm Monitor interval expired for DNS server "
    ::= { sonusDnsMIBNotificationsPrefix 6 }

sonusSbxDnsServerEdnsFailureNotification NOTIFICATION-TYPE
    OBJECTS         { sonusAlarmNodeID, sonusAlarmLevel, 
                      sonusAlarmSequenceId, sonusAlarmTime, 
                      sonusAlarmDescription, sonusEdnsServerIp }
    STATUS          current
    DESCRIPTION     
            "This alarms is raised when dns server consistently sends negative response
             to sbx edns request . Dns Server will be moved to the edns unsupported state "
    ::= { sonusEdnsMIBNotificationsPrefix 1 }

sonusSbxDsbcControlChanOpenNotification NOTIFICATION-TYPE
    OBJECTS         { sonusAlarmNodeID, sonusAlarmLevel, 
                      sonusAlarmSequenceId, sonusAlarmTime, 
                      sonusAlarmDescription, sonusDsbcRemoteDsbcAddr }
    STATUS          current
    DESCRIPTION     
            "This trap indicates that a Control Channel Link to a Remote DSBC node has been sucessfully opened."
    ::= { sonusDsbcSignallingMIBNotificationsPrefix 1 }

sonusSbxDsbcControlChanCloseNotification NOTIFICATION-TYPE
    OBJECTS         { sonusAlarmNodeID, sonusAlarmLevel, 
                      sonusAlarmSequenceId, sonusAlarmTime, 
                      sonusAlarmDescription, sonusDsbcRemoteDsbcAddr, 
                      sonusDsbcCloseReasonCode }
    STATUS          current
    DESCRIPTION     
            "This trap indicates that a Control Channel Link to a Remote DSBC node has been closed."
    ::= { sonusDsbcSignallingMIBNotificationsPrefix 2 }

sonusSbxDsbcControlChanOpenAttemptNotification NOTIFICATION-TYPE
    OBJECTS         { sonusAlarmNodeID, sonusAlarmLevel, 
                      sonusAlarmSequenceId, sonusAlarmTime, 
                      sonusAlarmDescription, sonusDsbcRemoteDsbcAddr }
    STATUS          current
    DESCRIPTION     
            "This trap indicates that a request to Open a Control Channel Link has been sent to a Remote Dsbc."
    ::= { sonusDsbcSignallingMIBNotificationsPrefix 3 }

sonusSbxDsbcControlChanRetryTimerExpiredNotification NOTIFICATION-TYPE
    OBJECTS         { sonusAlarmNodeID, sonusAlarmLevel, 
                      sonusAlarmSequenceId, sonusAlarmTime, 
                      sonusAlarmDescription, sonusDsbcRemoteDsbcAddr }
    STATUS          current
    DESCRIPTION     
            "This trap indicates that attempts to recover a Control Channel Link to a Remote DSBC node have failed."
    ::= { sonusDsbcSignallingMIBNotificationsPrefix 4 }

sonusSbxDsbcControlChanOpenNotificationV6 NOTIFICATION-TYPE
    OBJECTS         { sonusAlarmNodeID, sonusAlarmLevel, 
                      sonusAlarmSequenceId, sonusAlarmTime, 
                      sonusAlarmDescription, sonusDsbcRemoteDsbc6Addr }
    STATUS          current
    DESCRIPTION     
            "This trap indicates that a Call Signaling IPV6 Link to a Remote DSBC node has been sucessfully opened."
    ::= { sonusDsbcSignallingMIBNotificationsPrefix 5 }

sonusSbxDsbcControlChanOpenAttemptNotificationV6 NOTIFICATION-TYPE
    OBJECTS         { sonusAlarmNodeID, sonusAlarmLevel, 
                      sonusAlarmSequenceId, sonusAlarmTime, 
                      sonusAlarmDescription, sonusDsbcRemoteDsbc6Addr }
    STATUS          current
    DESCRIPTION     
            "This trap indicates that a request to Open a Call Signaling IPV6 Link has been sent to a Remote Dsbc."
    ::= { sonusDsbcSignallingMIBNotificationsPrefix 6 }

sonusSbxDsbcControlChanRetryTimerExpiredNotificationV6 NOTIFICATION-TYPE
    OBJECTS         { sonusAlarmNodeID, sonusAlarmLevel, 
                      sonusAlarmSequenceId, sonusAlarmTime, 
                      sonusAlarmDescription, sonusDsbcRemoteDsbc6Addr }
    STATUS          current
    DESCRIPTION     
            "This trap indicates that attempts to recover a Call Signaling IPV6 Link to a Remote DSBC node have failed."
    ::= { sonusDsbcSignallingMIBNotificationsPrefix 7 }

sonusSbxDsbcControlChanCloseNotificationV6 NOTIFICATION-TYPE
    OBJECTS         { sonusAlarmNodeID, sonusAlarmLevel, 
                      sonusAlarmSequenceId, sonusAlarmTime, 
                      sonusAlarmDescription, sonusDsbcRemoteDsbc6Addr, 
                      sonusDsbcCloseReasonCode }
    STATUS          current
    DESCRIPTION     
            "This trap indicates that a IPV6 Control Channel Link to a Remote DSBC node has been closed."
    ::= { sonusDsbcSignallingMIBNotificationsPrefix 8 }

sonusSbxDsbcClusterFqdnResolutionFailure NOTIFICATION-TYPE
    OBJECTS         { sonusAlarmNodeID, sonusAlarmLevel, 
                      sonusAlarmSequenceId, sonusAlarmTime, 
                      sonusAlarmDescription, sonusDsbcClusterFqdn, 
                      sonusDsbcClusterType }
    STATUS          current
    DESCRIPTION     
            "This trap indicates that all FQDN resolution attempts have failed for this cluster."
    ::= { sonusDsbcSignallingMIBNotificationsPrefix 9 }

sonusSbxDsbcClusterFqdnResolutionSuccess NOTIFICATION-TYPE
    OBJECTS         { sonusAlarmNodeID, sonusAlarmLevel, 
                      sonusAlarmSequenceId, sonusAlarmTime, 
                      sonusAlarmDescription, sonusDsbcClusterFqdn, 
                      sonusDsbcClusterType }
    STATUS          current
    DESCRIPTION     
            "This trap indicates that FQDN resolution has succeeded for this cluster."
    ::= { sonusDsbcSignallingMIBNotificationsPrefix 10 }

sonusSbxDsbcClusterAllSeedNodesUnreachable NOTIFICATION-TYPE
    OBJECTS         { sonusAlarmNodeID, sonusAlarmLevel, 
                      sonusAlarmSequenceId, sonusAlarmTime, 
                      sonusAlarmDescription, sonusDsbcClusterFqdn, 
                      sonusDsbcClusterType }
    STATUS          current
    DESCRIPTION     
            "This trap indicates that all seed nodes for this cluster FQDN are unreachable."
    ::= { sonusDsbcSignallingMIBNotificationsPrefix 11 }

sonusSbxDsbcClusterLeaderDiscoveryInProgress NOTIFICATION-TYPE
    OBJECTS         { sonusAlarmNodeID, sonusAlarmLevel, 
                      sonusAlarmSequenceId, sonusAlarmTime, 
                      sonusAlarmDescription, sonusDsbcClusterFqdn, 
                      sonusDsbcClusterType, sonusDsbcRemoteDsbcAddr }
    STATUS          current
    DESCRIPTION     
            "This trap indicates that a seed node for this cluster has been reached and leader discovery is in progress."
    ::= { sonusDsbcSignallingMIBNotificationsPrefix 12 }

sonusSbxDsbcClusterLeaderDiscoveryInProgressV6 NOTIFICATION-TYPE
    OBJECTS         { sonusAlarmNodeID, sonusAlarmLevel, 
                      sonusAlarmSequenceId, sonusAlarmTime, 
                      sonusAlarmDescription, sonusDsbcClusterFqdn, 
                      sonusDsbcClusterType, sonusDsbcRemoteDsbc6Addr }
    STATUS          current
    DESCRIPTION     
            "This trap indicates that a seed node for this cluster has been reached and leader discovery is in progress."
    ::= { sonusDsbcSignallingMIBNotificationsPrefix 13 }

sonusSbxDsbcClusterLeaderRetrievalCompleted NOTIFICATION-TYPE
    OBJECTS         { sonusAlarmNodeID, sonusAlarmLevel, 
                      sonusAlarmSequenceId, sonusAlarmTime, 
                      sonusAlarmDescription, sonusDsbcClusterFqdn, 
                      sonusDsbcClusterType, sonusDsbcRemoteDsbcAddr }
    STATUS          current
    DESCRIPTION     
            "This trap indicates that a seed node for this cluster has been reached and leader retrieval is completed."
    ::= { sonusDsbcSignallingMIBNotificationsPrefix 14 }

sonusSbxDsbcClusterLeaderRetrievalCompletedV6 NOTIFICATION-TYPE
    OBJECTS         { sonusAlarmNodeID, sonusAlarmLevel, 
                      sonusAlarmSequenceId, sonusAlarmTime, 
                      sonusAlarmDescription, sonusDsbcClusterFqdn, 
                      sonusDsbcClusterType, sonusDsbcRemoteDsbc6Addr }
    STATUS          current
    DESCRIPTION     
            "This trap indicates that a seed node for this cluster has been reached and leader retrieval is completed."
    ::= { sonusDsbcSignallingMIBNotificationsPrefix 15 }

sonusSbxDsbcFaultCallsReleased NOTIFICATION-TYPE
    OBJECTS         { sonusAlarmNodeID, sonusAlarmLevel, 
                      sonusAlarmSequenceId, sonusAlarmTime, 
                      sonusAlarmDescription, 
                      sonusDsbcCallsReleasedReasonCode, 
                      sonusDsbcCallsReleasedCount, 
                      sonusDsbcRemoteDsbcAddr }
    STATUS          current
    DESCRIPTION     
            "This trap indicates that a D-SBC network fault has resulted in calls being dropped."
    ::= { sonusDsbcSignallingMIBNotificationsPrefix 16 }

sonusSbxDsbcFaultCallsReleasedClear NOTIFICATION-TYPE
    OBJECTS         { sonusAlarmNodeID, sonusAlarmLevel, 
                      sonusAlarmSequenceId, sonusAlarmTime, 
                      sonusAlarmDescription, 
                      sonusDsbcCallsReleasedReasonCode, 
                      sonusDsbcRemoteDsbcAddr }
    STATUS          current
    DESCRIPTION     
            "This trap clears the D-SBC network fault call drop trap."
    ::= { sonusDsbcSignallingMIBNotificationsPrefix 17 }

sonusSbxDsbcFaultCallsReleasedV6 NOTIFICATION-TYPE
    OBJECTS         { sonusAlarmNodeID, sonusAlarmLevel, 
                      sonusAlarmSequenceId, sonusAlarmTime, 
                      sonusAlarmDescription, 
                      sonusDsbcCallsReleasedReasonCode, 
                      sonusDsbcCallsReleasedCount, 
                      sonusDsbcRemoteDsbc6Addr }
    STATUS          current
    DESCRIPTION     
            "This trap indicates that a D-SBC network fault has resulted in calls being dropped."
    ::= { sonusDsbcSignallingMIBNotificationsPrefix 18 }

sonusSbxDsbcFaultCallsReleasedClearV6 NOTIFICATION-TYPE
    OBJECTS         { sonusAlarmNodeID, sonusAlarmLevel, 
                      sonusAlarmSequenceId, sonusAlarmTime, 
                      sonusAlarmDescription, 
                      sonusDsbcCallsReleasedReasonCode, 
                      sonusDsbcRemoteDsbc6Addr }
    STATUS          current
    DESCRIPTION     
            "This trap clears the D-SBC network fault call drop trap."
    ::= { sonusDsbcSignallingMIBNotificationsPrefix 19 }

sonusSbxDsbcNodeCongested NOTIFICATION-TYPE
    OBJECTS         { sonusAlarmNodeID, sonusAlarmLevel, 
                      sonusAlarmSequenceId, sonusAlarmTime, 
                      sonusAlarmDescription, sonusDsbcRemoteDsbcAddr }
    STATUS          current
    DESCRIPTION     
            "This trap indicates that the D-SBC node has reported congestion failure."
    ::= { sonusDsbcSignallingMIBNotificationsPrefix 20 }

sonusSbxDsbcNodeCongestedClear NOTIFICATION-TYPE
    OBJECTS         { sonusAlarmNodeID, sonusAlarmLevel, 
                      sonusAlarmSequenceId, sonusAlarmTime, 
                      sonusAlarmDescription, sonusDsbcRemoteDsbcAddr }
    STATUS          current
    DESCRIPTION     
            "This trap indicates that the D-SBC node congestion condition has been cleared."
    ::= { sonusDsbcSignallingMIBNotificationsPrefix 21 }

sonusSbxDsbcNodeCongestedV6 NOTIFICATION-TYPE
    OBJECTS         { sonusAlarmNodeID, sonusAlarmLevel, 
                      sonusAlarmSequenceId, sonusAlarmTime, 
                      sonusAlarmDescription, sonusDsbcRemoteDsbc6Addr }
    STATUS          current
    DESCRIPTION     
            "This trap indicates that a D-SBC node has reported congestion failure."
    ::= { sonusDsbcSignallingMIBNotificationsPrefix 22 }

sonusSbxDsbcNodeCongestedClearV6 NOTIFICATION-TYPE
    OBJECTS         { sonusAlarmNodeID, sonusAlarmLevel, 
                      sonusAlarmSequenceId, sonusAlarmTime, 
                      sonusAlarmDescription, sonusDsbcRemoteDsbc6Addr }
    STATUS          current
    DESCRIPTION     
            "This trap indicates that the D-SBC node congestion condition has been cleared."
    ::= { sonusDsbcSignallingMIBNotificationsPrefix 23 }

sonusSbxDsbcNodeAllocationFailure NOTIFICATION-TYPE
    OBJECTS         { sonusAlarmNodeID, sonusAlarmLevel, 
                      sonusAlarmSequenceId, sonusAlarmTime, 
                      sonusAlarmDescription, sonusDsbcAllocFailuresCount, 
                      sonusDsbcRemoteDsbcAddr }
    STATUS          current
    DESCRIPTION     
            "This trap indicates that the M-SBC node has reported allocation failure(s)."
    ::= { sonusDsbcSignallingMIBNotificationsPrefix 24 }

sonusSbxDsbcNodeAllocationFailureClear NOTIFICATION-TYPE
    OBJECTS         { sonusAlarmNodeID, sonusAlarmLevel, 
                      sonusAlarmSequenceId, sonusAlarmTime, 
                      sonusAlarmDescription, sonusDsbcAllocFailuresCount, 
                      sonusDsbcRemoteDsbcAddr }
    STATUS          current
    DESCRIPTION     
            "This trap indicates that the M-SBC node allocation failure condition has been cleared."
    ::= { sonusDsbcSignallingMIBNotificationsPrefix 25 }

sonusSbxDsbcNodeAllocationFailureV6 NOTIFICATION-TYPE
    OBJECTS         { sonusAlarmNodeID, sonusAlarmLevel, 
                      sonusAlarmSequenceId, sonusAlarmTime, 
                      sonusAlarmDescription, sonusDsbcAllocFailuresCount, 
                      sonusDsbcRemoteDsbc6Addr }
    STATUS          current
    DESCRIPTION     
            "This trap indicates that the M-SBC node has reported allocation failure(s)."
    ::= { sonusDsbcSignallingMIBNotificationsPrefix 26 }

sonusSbxDsbcNodeAllocationFailureClearV6 NOTIFICATION-TYPE
    OBJECTS         { sonusAlarmNodeID, sonusAlarmLevel, 
                      sonusAlarmSequenceId, sonusAlarmTime, 
                      sonusAlarmDescription, sonusDsbcAllocFailuresCount, 
                      sonusDsbcRemoteDsbc6Addr }
    STATUS          current
    DESCRIPTION     
            "This trap indicates that the M-SBC node allocation failure condition has been cleared."
    ::= { sonusDsbcSignallingMIBNotificationsPrefix 27 }

sonusSbxCallRejectedDueToNonRegCacMaxLimitReachedNotification NOTIFICATION-TYPE
    OBJECTS         { sonusAlarmNodeID, sonusAlarmLevel, 
                      sonusAlarmSequenceId, sonusAlarmTime, 
                      sonusAlarmDescription, sonusCacSrcIp }
    STATUS          current
    DESCRIPTION     
            "This alarms is raised when call gets rejected due to maximum cac limit is
             reached and all CACs have active sessions."
    ::= { sonusCacMIBNotificationsPrefix 1 }

sonusSbxCcsClusterDownNotification NOTIFICATION-TYPE
    OBJECTS         { sonusAlarmNodeID, sonusAlarmLevel, 
                      sonusAlarmSequenceId, sonusAlarmTime, 
                      sonusAlarmDescription, sonusNrsCeName }
    STATUS          current
    DESCRIPTION     
            "The cluster is down."
    ::= { sonusCcsMIBNotificationsPrefix 1 }

sonusSbxCcsClusterUpNotification NOTIFICATION-TYPE
    OBJECTS         { sonusAlarmNodeID, sonusAlarmLevel, 
                      sonusAlarmSequenceId, sonusAlarmTime, 
                      sonusAlarmDescription, sonusNrsCeName }
    STATUS          current
    DESCRIPTION     
            "The cluster is up."
    ::= { sonusCcsMIBNotificationsPrefix 2 }

sonusSbxLicensedOodRateLimitReachedNotification NOTIFICATION-TYPE
    OBJECTS         { sonusAlarmNodeID, sonusAlarmLevel, 
                      sonusAlarmSequenceId, sonusAlarmTime, 
                      sonusAlarmDescription, sonusAlarmName, 
                      sonusActiveOodRate, sonusOodRateLimit }
    STATUS          current
    DESCRIPTION     
            "This trap indicates the licensed sessions notification threshold has been reached or exceeded."
    ::= { sonusOodMIBNotificationsPrefix 1 }

sonusSbxLicensedOodRateLimitClearNotification NOTIFICATION-TYPE
    OBJECTS         { sonusAlarmNodeID, sonusAlarmLevel, 
                      sonusAlarmSequenceId, sonusAlarmTime, 
                      sonusAlarmDescription, sonusAlarmName, 
                      sonusActiveOodRate, sonusOodRateLimit }
    STATUS          current
    DESCRIPTION     
            "This trap indicates the licensed sessions notification threshold has been cleared under 90% limit."
    ::= { sonusOodMIBNotificationsPrefix 2 }

sonusSbxManagedNodeUnableToReceiveConfigUpdates NOTIFICATION-TYPE
    OBJECTS         { sonusAlarmNodeID, sonusAlarmLevel, 
                      sonusAlarmSequenceId, sonusAlarmTime, 
                      sonusAlarmDescription, sonusManagedNodeCeName }
    STATUS          current
    DESCRIPTION     
            "Managed node is unable to receive config update/revert requests (i.e., managed node is unable to access config update/revert requests on OAM node)."
    ::= { sonusOamMIBNotificationsPrefix 1 }

sonusSbxManagedNodeAbleToReceiveConfigUpdates NOTIFICATION-TYPE
    OBJECTS         { sonusAlarmNodeID, sonusAlarmLevel, 
                      sonusAlarmSequenceId, sonusAlarmTime, 
                      sonusAlarmDescription, sonusManagedNodeCeName }
    STATUS          current
    DESCRIPTION     
            "Managed node is able to receive config update/revert requests (i.e., managed node is able to access config update/revert requests on OAM node)."
    ::= { sonusOamMIBNotificationsPrefix 2 }

sonusSbxManagedNodeConfigChangeListApplyFailed NOTIFICATION-TYPE
    OBJECTS         { sonusAlarmNodeID, sonusAlarmLevel, 
                      sonusAlarmSequenceId, sonusAlarmTime, 
                      sonusAlarmDescription, sonusManagedNodeCeName }
    STATUS          current
    DESCRIPTION     
            "Managed node failed to apply the config changes by replaying the config change list."
    ::= { sonusOamMIBNotificationsPrefix 3 }

sonusSbxManagedNodeConfigChangeListApplySucceeded NOTIFICATION-TYPE
    OBJECTS         { sonusAlarmNodeID, sonusAlarmLevel, 
                      sonusAlarmSequenceId, sonusAlarmTime, 
                      sonusAlarmDescription, sonusManagedNodeCeName }
    STATUS          current
    DESCRIPTION     
            "Managed node successfully  applied the config changes by replaying the config change list."
    ::= { sonusOamMIBNotificationsPrefix 4 }

sonusHpcLimitHighIngressCallRateNotification NOTIFICATION-TYPE
    OBJECTS         { sonusAlarmNodeID, sonusAlarmLevel, 
                      sonusAlarmSequenceId, sonusAlarmTime, 
                      sonusAlarmDescription, sonusHpcCallLimitEntityName, 
                      sonusHpcCallLimitDeniedAttempts }
    STATUS          current
    DESCRIPTION     
            "This trap indicates a HPC Call Rate Limit has been exceeded and reports the number of denied attempts."
    ::= { sonusHpcCallLimitMIBNotificationsPrefix 1 }

sonusHpcLimitHighSimultaneousCallsNotification NOTIFICATION-TYPE
    OBJECTS         { sonusAlarmNodeID, sonusAlarmLevel, 
                      sonusAlarmSequenceId, sonusAlarmTime, 
                      sonusAlarmDescription, sonusHpcCallLimitEntityName, 
                      sonusHpcCallLimitDeniedAttempts }
    STATUS          current
    DESCRIPTION     
            "This trap indicates a HPC Simultaneous Call Limit has been exceeded and reports the number of denied attempts."
    ::= { sonusHpcCallLimitMIBNotificationsPrefix 2 }

sonusHpcCallNoLicenseNotification NOTIFICATION-TYPE
    OBJECTS         { sonusAlarmNodeID, sonusAlarmLevel, 
                      sonusAlarmSequenceId, sonusAlarmTime, 
                      sonusAlarmDescription }
    STATUS          current
    DESCRIPTION     
            "This trap indicates a HPC Call occurred without a valid license"
    ::= { sonusHpcCallNoLicenseMIBNotificationsPrefix 1 }

sonusSlbSbcRegistrationNotification NOTIFICATION-TYPE
    OBJECTS         { sonusAlarmNodeID, sonusAlarmLevel, 
                      sonusAlarmSequenceId, sonusAlarmTime, 
                      sonusAlarmDescription, sonusVnfId, 
                      sonusVnfcInstanceId }
    STATUS          current
    DESCRIPTION     
            "An SBC has registered with the SLB."
    ::= { sonusSlbMIBNotificationsPrefix 1 }

sonusSlbSbcConnectionUpNotification NOTIFICATION-TYPE
    OBJECTS         { sonusAlarmNodeID, sonusAlarmLevel, 
                      sonusAlarmSequenceId, sonusAlarmTime, 
                      sonusAlarmDescription, sonusVnfId, 
                      sonusVnfcInstanceId }
    STATUS          current
    DESCRIPTION     
            "The control channel connection between the SLB and a registered SBC is up."
    ::= { sonusSlbMIBNotificationsPrefix 2 }

sonusSlbSbcConnectionDownNotification NOTIFICATION-TYPE
    OBJECTS         { sonusAlarmNodeID, sonusAlarmLevel, 
                      sonusAlarmSequenceId, sonusAlarmTime, 
                      sonusAlarmDescription, sonusVnfId, 
                      sonusVnfcInstanceId }
    STATUS          current
    DESCRIPTION     
            "The control channel connection between the SLB and a registered SBC is down."
    ::= { sonusSlbMIBNotificationsPrefix 3 }

sonusSlbSbcsUnreachableNotification NOTIFICATION-TYPE
    OBJECTS         { sonusAlarmNodeID, sonusAlarmLevel, 
                      sonusAlarmSequenceId, sonusAlarmTime, 
                      sonusAlarmDescription, sonusSipSigPortNum }
    STATUS          current
    DESCRIPTION     
            "The SLB is unable to forward a SIP message because all registered SBCs that could process that message are unreachable."
    ::= { sonusSlbMIBNotificationsPrefix 4 }

sonusSbxSlbConnectionUpNotification NOTIFICATION-TYPE
    OBJECTS         { sonusAlarmNodeID, sonusAlarmLevel, 
                      sonusAlarmSequenceId, sonusAlarmTime, 
                      sonusAlarmDescription, sonusSlbIpAddress }
    STATUS          current
    DESCRIPTION     
            "The SBC has successfully connected and registered with the SLB."
    ::= { sonusSlbMIBNotificationsPrefix 5 }

sonusSbxSlbConnectionDownNotification NOTIFICATION-TYPE
    OBJECTS         { sonusAlarmNodeID, sonusAlarmLevel, 
                      sonusAlarmSequenceId, sonusAlarmTime, 
                      sonusAlarmDescription, sonusSlbIpAddress }
    STATUS          current
    DESCRIPTION     
            "The SBC's control channel connection with the SLB has gone down."
    ::= { sonusSlbMIBNotificationsPrefix 6 }

sonusSbxSlbConnectionUpNotificationV6 NOTIFICATION-TYPE
    OBJECTS         { sonusAlarmNodeID, sonusAlarmLevel, 
                      sonusAlarmSequenceId, sonusAlarmTime, 
                      sonusAlarmDescription, sonusSlbIpv6Address }
    STATUS          current
    DESCRIPTION     
            "The SBC has successfully connected and registered with the SLB."
    ::= { sonusSlbMIBNotificationsPrefix 7 }

sonusSbxSlbConnectionDownNotificationV6 NOTIFICATION-TYPE
    OBJECTS         { sonusAlarmNodeID, sonusAlarmLevel, 
                      sonusAlarmSequenceId, sonusAlarmTime, 
                      sonusAlarmDescription, sonusSlbIpv6Address }
    STATUS          current
    DESCRIPTION     
            "The SBC's control channel connection with the SLB has gone down."
    ::= { sonusSlbMIBNotificationsPrefix 8 }

sonusSbxSlbGlobalLossRatioThresholdReachedNotification NOTIFICATION-TYPE
    OBJECTS         { sonusAlarmNodeID, sonusAlarmLevel, 
                      sonusAlarmSequenceId, sonusAlarmTime, 
                      sonusAlarmDescription, sonusCurrentGlobalLossRatio, 
                      sonusGlobalLossRatioLimit }
    STATUS          current
    DESCRIPTION     
            "This trap indicates the global loss ratio threshold for SLB has been reached or exceeded."
    ::= { sonusSlbMIBNotificationsPrefix 9 }

sonusSbcSlbConnectionEstablishedNotification NOTIFICATION-TYPE
    OBJECTS         { sonusAlarmNodeID, sonusAlarmLevel, 
                      sonusAlarmSequenceId, sonusAlarmTime, 
                      sonusAlarmDescription, sonusSlbName, 
                      sonusSlbIpAddress }
    STATUS          current
    DESCRIPTION     
            "The connection between SBC and SLB is established."
    ::= { sonusSlbMIBNotificationsPrefix 10 }

sonusSbcSlbConnectionNotEstablishedNotification NOTIFICATION-TYPE
    OBJECTS         { sonusAlarmNodeID, sonusAlarmLevel, 
                      sonusAlarmSequenceId, sonusAlarmTime, 
                      sonusAlarmDescription, sonusSlbName, 
                      sonusSlbIpAddress }
    STATUS          current
    DESCRIPTION     
            "The connection establishment between SBC and SLB failed"
    ::= { sonusSlbMIBNotificationsPrefix 11 }

sonusSbxSlbGlobalLossRatioThresoldClearNotification NOTIFICATION-TYPE
    OBJECTS         { sonusAlarmNodeID, sonusAlarmLevel, 
                      sonusAlarmSequenceId, sonusAlarmTime, 
                      sonusAlarmDescription, sonusCurrentGlobalLossRatio, 
                      sonusGlobalLossRatioLimit }
    STATUS          current
    DESCRIPTION     
            "This trap indicates the global loss ratio threshold has been cleared."
    ::= { sonusSlbMIBNotificationsPrefix 12 }

sonusSbxSlbGlobalUtilizationThresholdReachedNotification NOTIFICATION-TYPE
    OBJECTS         { sonusAlarmNodeID, sonusAlarmLevel, 
                      sonusAlarmSequenceId, sonusAlarmTime, 
                      sonusAlarmDescription, 
                      sonusCurrentGlobalUtilization, 
                      sonusGlobalUtilizationLimit }
    STATUS          current
    DESCRIPTION     
            "This trap indicates the global utilization threshold for SLB has been reached or exceeded."
    ::= { sonusSlbMIBNotificationsPrefix 13 }

sonusSbxSlbGlobalUtilizationThresholdClearNotification NOTIFICATION-TYPE
    OBJECTS         { sonusAlarmNodeID, sonusAlarmLevel, 
                      sonusAlarmSequenceId, sonusAlarmTime, 
                      sonusAlarmDescription, 
                      sonusCurrentGlobalUtilization, 
                      sonusGlobalUtilizationLimit }
    STATUS          current
    DESCRIPTION     
            "This trap indicates the global utilization threshold has been cleared."
    ::= { sonusSlbMIBNotificationsPrefix 14 }

sonusMicroServiceConnectionFailed NOTIFICATION-TYPE
    OBJECTS         { sonusAlarmNodeID, sonusAlarmLevel, 
                      sonusAlarmSequenceId, sonusAlarmTime, 
                      sonusAlarmDescription, sonusMicroServiceName }
    STATUS          current
    DESCRIPTION     
            "The connection to the specified micro-service is lost."
    ::= { sonusMicroServiceMIBNotificationsPrefix 1 }

sonusMicroServiceConnectionSucceeded NOTIFICATION-TYPE
    OBJECTS         { sonusAlarmNodeID, sonusAlarmLevel, 
                      sonusAlarmSequenceId, sonusAlarmTime, 
                      sonusAlarmDescription, sonusMicroServiceName }
    STATUS          current
    DESCRIPTION     
            "The connection to the specified micro-service is restored."
    ::= { sonusMicroServiceMIBNotificationsPrefix 2 }

sonusBfdSessionDown NOTIFICATION-TYPE
    OBJECTS         { sonusAlarmNodeID, sonusAlarmLevel, 
                      sonusAlarmSequenceId, sonusAlarmTime, 
                      sonusAlarmDescription, sonusBfdLinkId }
    STATUS          current
    DESCRIPTION     
            "BFD session for the specified linkId is DOWN"
    ::= { sonusBfdMIBNotificationsPrefix 1 }

sonusBfdSessionUp NOTIFICATION-TYPE
    OBJECTS         { sonusAlarmNodeID, sonusAlarmLevel, 
                      sonusAlarmSequenceId, sonusAlarmTime, 
                      sonusAlarmDescription, sonusBfdLinkId }
    STATUS          current
    DESCRIPTION     
            "BFD session for the specified linkId is UP"
    ::= { sonusBfdMIBNotificationsPrefix 2 }

sonusBfdSessionDelete NOTIFICATION-TYPE
    OBJECTS         { sonusAlarmNodeID, sonusAlarmLevel, 
                      sonusAlarmSequenceId, sonusAlarmTime, 
                      sonusAlarmDescription, sonusBfdLinkId }
    STATUS          current
    DESCRIPTION     
            "BFD session for the specified linkId is DELETED"
    ::= { sonusBfdMIBNotificationsPrefix 3 }

sonusH248VMGtermNoRTPRcvdThresholdExceeded NOTIFICATION-TYPE
    OBJECTS         { sonusAlarmNodeID, sonusAlarmLevel, 
                      sonusAlarmSequenceId, sonusAlarmTime, 
                      sonusAlarmDescription, sonusH248VmgName, 
                      sonusH248TermThreshold, sonusH248NoRtpTerminations }
    STATUS          current
    DESCRIPTION     
            "This alarm is generated when the VMG is configured with a maximum threshold 
             specifying percentage of the total number of Terminations that never received 
             any RTP/RTCP during their session in the latest bin period, and that threshold 
             is exceeded"
    ::= { sonusH248NoRtpMIBNotificationsPrefix 1 }

sonusH248ClearVMGtermNoRTPRcvdThresholdExceeded NOTIFICATION-TYPE
    OBJECTS         { sonusAlarmNodeID, sonusAlarmLevel, 
                      sonusAlarmSequenceId, sonusAlarmTime, 
                      sonusAlarmDescription, sonusH248VmgName, 
                      sonusH248ClearThreshold, 
                      sonusH248NoRtpTerminations, 
                      sonusH248MinimumRtpTerminations, 
                      sonusH248TotalRtpTerminations }
    STATUS          current
    DESCRIPTION     
            "This alarm is generated when the VMG is configured with a clear threshold 
             specifying percentage of the total number of Terminations that never received 
             any RTP/RTCP during their session in the latest bin period, and the latest 
             value goes under this threshold"
    ::= { sonusH248NoRtpMIBNotificationsPrefix 2 }

sonusPacketPortBWusageThresholdExceeded NOTIFICATION-TYPE
    OBJECTS         { sonusAlarmNodeID, sonusAlarmLevel, 
                      sonusAlarmSequenceId, sonusAlarmTime, 
                      sonusAlarmDescription, sonusEthernetPortName, 
                      sonusEthernetPortBwUsageThreshold, 
                      sonusEthernetPortBwUsage }
    STATUS          current
    DESCRIPTION     
            "This alarm is generated when the Bandwidth Usage exceeds a maximum threshold of 95%"
    ::= { sonusPortMIBNotificationsPrefix 1 }

sonusClearPacketPortclearThresholdExceeded NOTIFICATION-TYPE
    OBJECTS         { sonusAlarmNodeID, sonusAlarmLevel, 
                      sonusAlarmSequenceId, sonusAlarmTime, 
                      sonusAlarmDescription, sonusEthernetPortName, 
                      sonusEthernetPortBwUsageClearThreshold, 
                      sonusEthernetPortBwUsage }
    STATUS          current
    DESCRIPTION     
            "This alarm is generated when the Bandwidth Usage returns back under a threshold of 90%"
    ::= { sonusPortMIBNotificationsPrefix 2 }

END -- end of module SONUS-SBX-TRAP-MIB.
