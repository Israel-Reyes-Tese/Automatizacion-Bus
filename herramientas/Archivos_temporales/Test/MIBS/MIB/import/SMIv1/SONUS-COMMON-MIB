--
-- This SMIv1 module has been generated by smidump 0.2-cvs. Do not edit.
--

SONUS-COMMON-MIB DEFINITIONS ::= BEGIN

IMPORTS
    Ipv6Address
        FROM IPV6-TC
    OBJECT-TYPE
        FROM RFC-1212
    TRAP-TYPE
        FROM RFC-1215
    Counter, IpAddress
        FROM RFC1155-SMI
    DateAndTime, RowStatus
        FROM SNMPv2-TC
    sonusSystemMIBs
        FROM SONUS-SMI
    SonusAccessLevel, SonusAdminState, SonusEventClass, SonusEventLevel, 
    SonusEventString, SonusExtendedName, SonusName, SonusNameReference, 
    SonusPimIndex, SonusSfpIndex, SonusShelfIndex, SonusSlotIndex, 
    SonusTrapType
        FROM SONUS-TC;

sonusCommonMIB OBJECT IDENTIFIER
    ::= { sonusSystemMIBs 5 }

-- sonusCommonMIB MODULE-IDENTITY
--     LAST-UPDATED    "201108010000Z"
--     ORGANIZATION    
--             "Sonus Networks, Inc."
--     CONTACT-INFO    
--             "   Customer Support    
--              Sonus Networks, Inc.
--              7 Technology Park Drive
--              Westford, MA 01886
--              USA
--              
--              Tel: 978-614-8100
--              Fax: 978-614-8609"
--     DESCRIPTION     
--             "The MIB Module for common management of all Sonus devices."
--     ::= { sonusSystemMIBs 5 }


sonusCommonMIBObjects OBJECT IDENTIFIER
    ::= { sonusCommonMIB 1 }

sonusNetMgmt OBJECT IDENTIFIER
    ::= { sonusCommonMIBObjects 1 }

sonusNetMgmtClient OBJECT IDENTIFIER
    ::= { sonusNetMgmt 1 }

sonusNetMgmtClientNextIndex OBJECT-TYPE
    SYNTAX          INTEGER (0..65535)
    ACCESS          read-only
    STATUS          mandatory
    DESCRIPTION     
            "The next valid index to use when creating an entry in
             the sonusNetMgmtClientTable."
    ::= { sonusNetMgmtClient 1 }

sonusNetMgmtClientTable OBJECT-TYPE
    SYNTAX          SEQUENCE OF SonusNetMgmtClientEntry
    ACCESS          not-accessible
    STATUS          mandatory
    DESCRIPTION     
            "The sonusNetMgmtClientTable specifies the management entities
             (i.e. clients) that are capable of configurating the node.
             Each management client is identified by its IP address."
    ::= { sonusNetMgmtClient 2 }

sonusNetMgmtClientEntry OBJECT-TYPE
    SYNTAX          SonusNetMgmtClientEntry
    ACCESS          not-accessible
    STATUS          mandatory
    DESCRIPTION     
            "An entry in the sonusNetMgmtClientTable."
    INDEX           { sonusNetMgmtClientIndex }
    ::= { sonusNetMgmtClientTable 1 }

SonusNetMgmtClientEntry ::=
    SEQUENCE {
        sonusNetMgmtClientIndex         INTEGER,
        sonusNetMgmtClientName          SonusExtendedName,
        sonusNetMgmtClientState         SonusAdminState,
        sonusNetMgmtClientIpAddr        IpAddress,
        sonusNetMgmtClientAccess        SonusAccessLevel,
        sonusNetMgmtClientSnmpCommunityGet  DisplayString,
        sonusNetMgmtClientSnmpCommunitySet  DisplayString,
        sonusNetMgmtClientSnmpCommunityTrap   DisplayString,
        sonusNetMgmtClientTrapState     SonusAdminState,
        sonusNetMgmtClientRowStatus     RowStatus,
        sonusNetMgmtClientTrapPort      INTEGER,
        sonusNetMgmtClientAllTraps      SonusTrapType,
        sonusNetMgmtClientInformReqTimeout  INTEGER,
        sonusNetMgmtClientInformReqRetries  INTEGER,
        sonusNetMgmtClientInformReqMaxQueue   INTEGER,
        sonusNetMgmtClientInformReqRspTimeout     INTEGER,
        sonusNetMgmtClientIp6Addr       Ipv6Address,
        sonusNetMgmtClientIpVersion     INTEGER
    }

sonusNetMgmtClientIndex OBJECT-TYPE
    SYNTAX          INTEGER (1..8)
    ACCESS          read-only
    STATUS          mandatory
    DESCRIPTION     
            "The tabular index of this administrative management client."
    DEFVAL          { 1 }
    ::= { sonusNetMgmtClientEntry 1 }

sonusNetMgmtClientName OBJECT-TYPE
    SYNTAX          SonusExtendedName
    ACCESS          read-write
    STATUS          mandatory
    DESCRIPTION     
            "The name of this administrative management client."
    ::= { sonusNetMgmtClientEntry 2 }

sonusNetMgmtClientState OBJECT-TYPE
    SYNTAX          SonusAdminState
    ACCESS          read-write
    STATUS          mandatory
    DESCRIPTION     
            "The administrative state of this management client."
    DEFVAL          { disabled }
    ::= { sonusNetMgmtClientEntry 3 }

sonusNetMgmtClientIpAddr OBJECT-TYPE
    SYNTAX          IpAddress
    ACCESS          read-write
    STATUS          mandatory
    DESCRIPTION     
            "The IP address of this management client."
    DEFVAL          { '01010101'H }
    ::= { sonusNetMgmtClientEntry 4 }

sonusNetMgmtClientAccess OBJECT-TYPE
    SYNTAX          SonusAccessLevel
    ACCESS          read-write
    STATUS          mandatory
    DESCRIPTION     
            "The level of management that is granted to this management client."
    DEFVAL          { readOnly }
    ::= { sonusNetMgmtClientEntry 5 }

sonusNetMgmtClientSnmpCommunityGet OBJECT-TYPE
    SYNTAX          DisplayString (SIZE(0..23))
    ACCESS          read-write
    STATUS          mandatory
    DESCRIPTION     
            "The SNMP read-only community string."
    DEFVAL          { "public" }
    ::= { sonusNetMgmtClientEntry 6 }

sonusNetMgmtClientSnmpCommunitySet OBJECT-TYPE
    SYNTAX          DisplayString (SIZE(0..23))
    ACCESS          read-write
    STATUS          mandatory
    DESCRIPTION     
            "The SNMP read-write community string."
    DEFVAL          { "private" }
    ::= { sonusNetMgmtClientEntry 7 }

sonusNetMgmtClientSnmpCommunityTrap OBJECT-TYPE
    SYNTAX          DisplayString (SIZE(0..23))
    ACCESS          read-write
    STATUS          mandatory
    DESCRIPTION     
            "The SNMP trap community string."
    DEFVAL          { "public" }
    ::= { sonusNetMgmtClientEntry 8 }

sonusNetMgmtClientTrapState OBJECT-TYPE
    SYNTAX          SonusAdminState
    ACCESS          read-write
    STATUS          mandatory
    DESCRIPTION     
            "Determines whether SNMP traps are transmitted to this
             management client."
    DEFVAL          { disabled }
    ::= { sonusNetMgmtClientEntry 9 }

sonusNetMgmtClientRowStatus OBJECT-TYPE
    SYNTAX          RowStatus
    ACCESS          read-write
    STATUS          mandatory
    DESCRIPTION     
            "This object is used to create and delete rows in the
             sonusNetMgmtClientTable."
    ::= { sonusNetMgmtClientEntry 10 }

sonusNetMgmtClientTrapPort OBJECT-TYPE
    SYNTAX          INTEGER (0..65535)
    ACCESS          read-write
    STATUS          mandatory
    DESCRIPTION     
            "The port number of the management client where trap/notification
             PDUs are to be sent to."
    DEFVAL          { 162 }
    ::= { sonusNetMgmtClientEntry 11 }

sonusNetMgmtClientAllTraps OBJECT-TYPE
    SYNTAX          SonusTrapType
    ACCESS          read-write
    STATUS          mandatory
    DESCRIPTION     
            "Indicates if all traps are to be sent to this management client,
             and defines their trap type."
    DEFVAL          { trapv2 }
    ::= { sonusNetMgmtClientEntry 12 }

sonusNetMgmtClientInformReqTimeout OBJECT-TYPE
    SYNTAX          INTEGER (1..120)
    ACCESS          read-write
    STATUS          deprecated
    DESCRIPTION     
            "This object had been replaced with sonusNetMgmtClientInformReqRspTimeout
             in V05.00.00 "
    DEFVAL          { 5 }
    ::= { sonusNetMgmtClientEntry 13 }

sonusNetMgmtClientInformReqRetries OBJECT-TYPE
    SYNTAX          INTEGER (0..10)
    ACCESS          read-write
    STATUS          mandatory
    DESCRIPTION     
            "The number of retries that are to be made when sending an
             InformRequest PDU to this Management Client.  The maximum
             number of attempts to send an InformRequest PDU to a
             Management Client will be one, for the initial attempt,
             plus the number of retries.  This MIB object does not apply
             to SNMPv1 or SNMPv2 Trap PDUs.
             
             Refer to sonusNetMgmtClientInformRequestTimeout for related
             information."
    DEFVAL          { 3 }
    ::= { sonusNetMgmtClientEntry 14 }

sonusNetMgmtClientInformReqMaxQueue OBJECT-TYPE
    SYNTAX          INTEGER (1..150)
    ACCESS          read-write
    STATUS          mandatory
    DESCRIPTION     
            "The maximum of InformRequest PDUs that will be outstanding,
             awaiting for Response PDUs from this Management Client.
             When the maximum number has been reached, consectutive
             InformRequest PDUs will be discarded (i.e. not sent.)
             Increasing this number will increase the memory consumed
             by the GSX software and the CPU time required to process
             the InformRequest PDUs.  This MIB object does not apply to
             SNMPv1 or SNMPv2 Trap PDUs."
    DEFVAL          { 100 }
    ::= { sonusNetMgmtClientEntry 15 }

sonusNetMgmtClientInformReqRspTimeout OBJECT-TYPE
    SYNTAX          INTEGER (1..30)
    ACCESS          read-write
    STATUS          mandatory
    DESCRIPTION     
            "The time in seconds that an InformRequest PDU that is sent to
             this Management Client will timeout if no Response PDU is received.
             This MIB object does not apply to SNMPv1 or SNMPv2 Trap PDUs.
             
             Refer to sonusNetMgmtClientInformRequestRetries for related
             information."
    DEFVAL          { 6 }
    ::= { sonusNetMgmtClientEntry 16 }

sonusNetMgmtClientIp6Addr OBJECT-TYPE
    SYNTAX          Ipv6Address
    ACCESS          read-write
    STATUS          mandatory
    DESCRIPTION     
            "The IPv6 address of this management client."
    ::= { sonusNetMgmtClientEntry 18 }

sonusNetMgmtClientIpVersion OBJECT-TYPE
    SYNTAX          INTEGER { afInet(2), afInet6(24) }
    ACCESS          read-only
    STATUS          mandatory
    DESCRIPTION     
            "The IP address type  of this management client."
    ::= { sonusNetMgmtClientEntry 19 }

sonusNetMgmtClientStatusTable OBJECT-TYPE
    SYNTAX          SEQUENCE OF SonusNetMgmtClientStatusEntry
    ACCESS          not-accessible
    STATUS          mandatory
    DESCRIPTION     
            "The sonusNetMgmtClientStatusTable specifies the status of the
             management entities (i.e. clients)."
    ::= { sonusNetMgmtClient 3 }

sonusNetMgmtClientStatusEntry OBJECT-TYPE
    SYNTAX          SonusNetMgmtClientStatusEntry
    ACCESS          not-accessible
    STATUS          mandatory
    DESCRIPTION     
            "An entry in the sonusNetMgmtClientStatusTable."
    INDEX           { sonusNetMgmtClientStatusIndex }
    ::= { sonusNetMgmtClientStatusTable 1 }

SonusNetMgmtClientStatusEntry ::=
    SEQUENCE {
        sonusNetMgmtClientStatusIndex   INTEGER,
        sonusNetMgmtClientStatusLastConfigChange        DateAndTime,
        sonusNetMgmtClientStatusLastTrapSequenceId          INTEGER,
        sonusNetMgmtClientStatusLastTrapSequenceEpoch             INTEGER,
        sonusNetMgmtClientStatusName    DisplayString
    }

sonusNetMgmtClientStatusIndex OBJECT-TYPE
    SYNTAX          INTEGER (1..8)
    ACCESS          not-accessible
    STATUS          mandatory
    DESCRIPTION     
            "The tabular index of this status management client."
    ::= { sonusNetMgmtClientStatusEntry 1 }

sonusNetMgmtClientStatusLastConfigChange OBJECT-TYPE
    SYNTAX          DateAndTime
    ACCESS          read-only
    STATUS          mandatory
    DESCRIPTION     
            "Octet string that identifies the GMT timestamp of last
             successful SET PDU from this management client.
             
             field  octects  contents      range
             -----  -------  --------      -----
               1      1-2      year         0..65536
               2       3       month        1..12
               3       4       day          1..31
               4       5       hour         0..23
               5       6       minutes      0..59
               6       7       seconds      0..59
               7       8       deci-sec     0..9
             
               * Notes:
               - the value of year is in network-byte order "
    ::= { sonusNetMgmtClientStatusEntry 2 }

sonusNetMgmtClientStatusLastTrapSequenceId OBJECT-TYPE
    SYNTAX          INTEGER
    ACCESS          read-only
    STATUS          mandatory
    DESCRIPTION     
            "Sequence number included in last trap sent to mgmt client."
    ::= { sonusNetMgmtClientStatusEntry 3 }

sonusNetMgmtClientStatusLastTrapSequenceEpoch OBJECT-TYPE
    SYNTAX          INTEGER
    ACCESS          read-only
    STATUS          mandatory
    DESCRIPTION     
            "Sequence Epoch included in last trap sent to mgmt client."
    ::= { sonusNetMgmtClientStatusEntry 4 }

sonusNetMgmtClientStatusName OBJECT-TYPE
    SYNTAX          DisplayString (SIZE(0..23))
    ACCESS          read-write
    STATUS          mandatory
    DESCRIPTION     
            "The name of the management client."
    ::= { sonusNetMgmtClientStatusEntry 5 }

sonusNetMgmtTrap OBJECT IDENTIFIER
    ::= { sonusNetMgmt 2 }

sonusNetMgmtTrapNextIndex OBJECT IDENTIFIER
    ::= { sonusNetMgmtTrap 1 }

sonusNetMgmtTrapTable OBJECT-TYPE
    SYNTAX          SEQUENCE OF SonusNetMgmtTrapEntry
    ACCESS          not-accessible
    STATUS          mandatory
    DESCRIPTION     
            "The sonusNetMgmtTrapTable identifies the SNMP Traps
             that this node supports."
    ::= { sonusNetMgmtTrap 2 }

sonusNetMgmtTrapEntry OBJECT-TYPE
    SYNTAX          SonusNetMgmtTrapEntry
    ACCESS          not-accessible
    STATUS          mandatory
    DESCRIPTION     
            "An entry in the sonusNetMgmtTrapTable."
    INDEX           { sonusNetMgmtTrapIndex }
    ::= { sonusNetMgmtTrapTable 1 }

SonusNetMgmtTrapEntry ::=
    SEQUENCE {
        sonusNetMgmtTrapIndex           INTEGER,
        sonusNetMgmtTrapName            SonusName,
        sonusNetMgmtTrapMIBName         DisplayString,
        sonusNetMgmtTrapOID             OBJECT IDENTIFIER,
        sonusNetMgmtTrapClass           SonusEventClass,
        sonusNetMgmtTrapLevel           SonusEventLevel,
        sonusNetMgmtTrapState           SonusAdminState
    }

sonusNetMgmtTrapIndex OBJECT-TYPE
    SYNTAX          INTEGER (1..65535)
    ACCESS          not-accessible
    STATUS          mandatory
    DESCRIPTION     
            "The tabular index of this trap."
    DEFVAL          { 1 }
    ::= { sonusNetMgmtTrapEntry 1 }

sonusNetMgmtTrapName OBJECT-TYPE
    SYNTAX          SonusName
    ACCESS          read-only
    STATUS          mandatory
    DESCRIPTION     
            "The name of this trap."
    ::= { sonusNetMgmtTrapEntry 2 }

sonusNetMgmtTrapMIBName OBJECT-TYPE
    SYNTAX          DisplayString (SIZE(0..63))
    ACCESS          read-only
    STATUS          obsolete
    DESCRIPTION     
            "The full MIB name of this trap."
    DEFVAL          { "" }
    ::= { sonusNetMgmtTrapEntry 3 }

sonusNetMgmtTrapOID OBJECT-TYPE
    SYNTAX          OBJECT IDENTIFIER
    ACCESS          read-only
    STATUS          mandatory
    DESCRIPTION     
            "The MIB OID of this trap."
    ::= { sonusNetMgmtTrapEntry 4 }

sonusNetMgmtTrapClass OBJECT-TYPE
    SYNTAX          SonusEventClass
    ACCESS          read-only
    STATUS          mandatory
    DESCRIPTION     
            "The classification of the event that corresponds
             to this trap."
    DEFVAL          { sysmgmt }
    ::= { sonusNetMgmtTrapEntry 5 }

sonusNetMgmtTrapLevel OBJECT-TYPE
    SYNTAX          SonusEventLevel
    ACCESS          read-only
    STATUS          mandatory
    DESCRIPTION     
            "The severity level of the event that corresponds
             to this trap."
    DEFVAL          { info }
    ::= { sonusNetMgmtTrapEntry 6 }

sonusNetMgmtTrapState OBJECT-TYPE
    SYNTAX          SonusAdminState
    ACCESS          read-write
    STATUS          mandatory
    DESCRIPTION     
            "Determines if this SNMP trap is transmitted to any
             management client."
    DEFVAL          { enabled }
    ::= { sonusNetMgmtTrapEntry 7 }

sonusNetMgmtNotify OBJECT IDENTIFIER
    ::= { sonusNetMgmt 3 }

sonusNetMgmtNotifyNextIndex OBJECT-TYPE
    SYNTAX          INTEGER (0..65535)
    ACCESS          read-only
    STATUS          mandatory
    DESCRIPTION     
            "The next valid index to use when creating an entry in
             the sonusNetMgmtNotifyTable."
    ::= { sonusNetMgmtNotify 1 }

sonusNetMgmtNotifyTable OBJECT-TYPE
    SYNTAX          SEQUENCE OF SonusNetMgmtNotifyEntry
    ACCESS          not-accessible
    STATUS          mandatory
    DESCRIPTION     
            "The sonusNetMgmtNotifyTable identifies which management
             clients are to be notified by which SNMP Traps."
    ::= { sonusNetMgmtNotify 2 }

sonusNetMgmtNotifyEntry OBJECT-TYPE
    SYNTAX          SonusNetMgmtNotifyEntry
    ACCESS          not-accessible
    STATUS          mandatory
    DESCRIPTION     
            "An entry in the sonusNetMgmtNotifyTable."
    INDEX           { sonusNetMgmtNotifyIndex }
    ::= { sonusNetMgmtNotifyTable 1 }

SonusNetMgmtNotifyEntry ::=
    SEQUENCE {
        sonusNetMgmtNotifyIndex         INTEGER,
        sonusNetMgmtNotifyName          SonusName,
        sonusNetMgmtNotifyMgmtName      SonusNameReference,
        sonusNetMgmtNotifyTrapName      SonusNameReference,
        sonusNetMgmtNotifyTrapType      SonusTrapType,
        sonusNetMgmtNotifyRowStatus     RowStatus
    }

sonusNetMgmtNotifyIndex OBJECT-TYPE
    SYNTAX          INTEGER (1..65535)
    ACCESS          not-accessible
    STATUS          mandatory
    DESCRIPTION     
            "The table index of notify entries."
    DEFVAL          { 1 }
    ::= { sonusNetMgmtNotifyEntry 1 }

sonusNetMgmtNotifyName OBJECT-TYPE
    SYNTAX          SonusName
    ACCESS          read-write
    STATUS          mandatory
    DESCRIPTION     
            "The name of the notification entry."
    ::= { sonusNetMgmtNotifyEntry 2 }

sonusNetMgmtNotifyMgmtName OBJECT-TYPE
    SYNTAX          SonusNameReference
    ACCESS          read-write
    STATUS          mandatory
    DESCRIPTION     
            "The name of the management client that is to be 
             notified of the trap identified by this entry.  The
             value must match an existing sonusNetMgmtClientName 
             in the sonusNetMgmtClientTable."
    DEFVAL          { "" }
    ::= { sonusNetMgmtNotifyEntry 3 }

sonusNetMgmtNotifyTrapName OBJECT-TYPE
    SYNTAX          SonusNameReference
    ACCESS          read-write
    STATUS          mandatory
    DESCRIPTION     
            "The name of the trap that is to be sent to the 
             management client identified by this entry.  The
             value must match an existing sonusNetMgmtTrapName in
             the sonusNetMgmtTrapTable."
    DEFVAL          { "" }
    ::= { sonusNetMgmtNotifyEntry 4 }

sonusNetMgmtNotifyTrapType OBJECT-TYPE
    SYNTAX          SonusTrapType
    ACCESS          read-write
    STATUS          mandatory
    DESCRIPTION     
            "Identify whether no PDU, a SNMPv1 Trap PDU, SNMPv2 Trap PDU,
             or SNMPv2 Inform PDU is to be transmitted to this
             management client."
    DEFVAL          { trapv2 }
    ::= { sonusNetMgmtNotifyEntry 5 }

sonusNetMgmtNotifyRowStatus OBJECT-TYPE
    SYNTAX          RowStatus
    ACCESS          read-write
    STATUS          mandatory
    DESCRIPTION     
            "This object is used to create and delete rows in the
             sonusNetMgmtNotifyTable."
    ::= { sonusNetMgmtNotifyEntry 6 }

sonusSnmpStat OBJECT IDENTIFIER
    ::= { sonusCommonMIBObjects 2 }

sonusSnmpInUnauthorizedClients OBJECT-TYPE
    SYNTAX          Counter
    ACCESS          read-only
    STATUS          mandatory
    DESCRIPTION     
            "The total number of SNMP messages delivered to the SNMP
             entity from unauthorized clients."
    ::= { sonusSnmpStat 1 }

sonusSnmpInLswuDrops OBJECT-TYPE
    SYNTAX          Counter
    ACCESS          read-only
    STATUS          mandatory
    DESCRIPTION     
            "The total SNMP messages received during Live Software Upgrade 
             from external entity. All the snmp requests received from 
             external entity are dropped during Live Software Upgrade."
    ::= { sonusSnmpStat 2 }

sonusSnmpInDrops OBJECT-TYPE
    SYNTAX          Counter
    ACCESS          read-only
    STATUS          mandatory
    DESCRIPTION     
            "The total number of snmp request PDU's silently dropped due to
             snmp request waiting to be processeed reached the maximum limit."
    ::= { sonusSnmpStat 3 }

sonusCommonMIBNotifications OBJECT IDENTIFIER
    ::= { sonusCommonMIB 2 }

sonusCommonMIBNotificationsPrefix OBJECT IDENTIFIER
    ::= { sonusCommonMIBNotifications 0 }

sonusCommonMIBNotificationsObjects OBJECT IDENTIFIER
    ::= { sonusCommonMIBNotifications 1 }

sonusShelfIndex OBJECT-TYPE
    SYNTAX          SonusShelfIndex
    ACCESS          read-only
    STATUS          mandatory
    DESCRIPTION     
            "The shelf index of the event that generated the trap."
    ::= { sonusCommonMIBNotificationsObjects 1 }

sonusSlotIndex OBJECT-TYPE
    SYNTAX          SonusSlotIndex
    ACCESS          read-only
    STATUS          mandatory
    DESCRIPTION     
            "The slot index of the event that generated the trap."
    ::= { sonusCommonMIBNotificationsObjects 2 }

sonusPortIndex OBJECT-TYPE
    SYNTAX          INTEGER (0..65535)
    ACCESS          read-only
    STATUS          mandatory
    DESCRIPTION     
            "The port index of the event that generated the trap."
    ::= { sonusCommonMIBNotificationsObjects 3 }

sonusDs3Index OBJECT-TYPE
    SYNTAX          INTEGER (0..65535)
    ACCESS          read-only
    STATUS          mandatory
    DESCRIPTION     
            "The DS3 index of the event that generated the trap."
    ::= { sonusCommonMIBNotificationsObjects 4 }

sonusDs1Index OBJECT-TYPE
    SYNTAX          INTEGER (0..65535)
    ACCESS          read-only
    STATUS          mandatory
    DESCRIPTION     
            "The DS1 index of the event that generated the trap."
    ::= { sonusCommonMIBNotificationsObjects 5 }

sonusEventDescription OBJECT-TYPE
    SYNTAX          SonusEventString
    ACCESS          read-only
    STATUS          mandatory
    DESCRIPTION     
            "A description of the event that generated the trap."
    ::= { sonusCommonMIBNotificationsObjects 6 }

sonusEventClass OBJECT-TYPE
    SYNTAX          SonusEventClass
    ACCESS          read-only
    STATUS          mandatory
    DESCRIPTION     
            "The category of the event that generated the trap."
    ::= { sonusCommonMIBNotificationsObjects 7 }

sonusEventLevel OBJECT-TYPE
    SYNTAX          SonusEventLevel
    ACCESS          read-only
    STATUS          mandatory
    DESCRIPTION     
            "The severity level of the event that generated the trap."
    ::= { sonusCommonMIBNotificationsObjects 8 }

sonusSequenceId OBJECT-TYPE
    SYNTAX          Gauge
    ACCESS          read-only
    STATUS          mandatory
    DESCRIPTION     
            "A consecutive number assigned to each trap in a
             sequence of traps that are sent to one management client.
             Each management client has its own set of sequence IDs."
    ::= { sonusCommonMIBNotificationsObjects 9 }

sonusEventTime OBJECT-TYPE
    SYNTAX          DateAndTime
    ACCESS          read-only
    STATUS          mandatory
    DESCRIPTION     
            "The date and time of the event that generated the trap."
    ::= { sonusCommonMIBNotificationsObjects 10 }

sonusNetMgmtInformReqDiscards OBJECT-TYPE
    SYNTAX          INTEGER (0..100)
    ACCESS          read-only
    STATUS          mandatory
    DESCRIPTION     
            "The number of InformRequest PDUs that were discarded
             for a Management Client."
    ::= { sonusCommonMIBNotificationsObjects 11 }

sonusPimIndex OBJECT-TYPE
    SYNTAX          SonusPimIndex
    ACCESS          read-only
    STATUS          mandatory
    DESCRIPTION     
            "The pim index of the event that generated the trap."
    ::= { sonusCommonMIBNotificationsObjects 12 }

sonusSfpIndex OBJECT-TYPE
    SYNTAX          SonusSfpIndex
    ACCESS          read-only
    STATUS          mandatory
    DESCRIPTION     
            "The sfp index of the event that generated the trap."
    ::= { sonusCommonMIBNotificationsObjects 13 }

sonusSequenceEpoch OBJECT-TYPE
    SYNTAX          Gauge
    ACCESS          read-only
    STATUS          mandatory
    DESCRIPTION     
            "A consecutive number assigned to each instance of a GSX
             reboot or MNS switchover, indicating a new epoch for the
             sonusSequenceId of traps that are sent to a management client."
    ::= { sonusCommonMIBNotificationsObjects 14 }

sonusNetMgmtClientInformReqQueueFlushedNotification TRAP-TYPE
    ENTERPRISE      sonusCommonMIBNotifications
    VARIABLES       { sonusNetMgmtClientName, 
                      sonusNetMgmtInformReqDiscards, 
                      sonusEventDescription, sonusEventClass, 
                      sonusEventLevel, sonusSequenceId, sonusEventTime }
--     STATUS          mandatory
    DESCRIPTION     
            "The specified number of InformRequest PDUs destined to
             the specified Management Client were flushed from the
             InformRequest PDU queue because no Response PDUs were
             were received from the Management Client.
             
             This situtation could occur if the Management Client
             cannot quickly process and respond to InformRequest PDUs
             that it receives, or if communications is lost with the
             Management Client.
             
             If this situation occurs occasionally, it is recommended
             to increase the InformRequest PDU timeout and/or retry
             values (see sonusNetMgmtClientInformReqRspTimeout and
             sonusNetMgmtClientInformReqRetries.)
             
             If this situation occurs repeatedly, it is an indication
             that communications is lost with the Management Client,
             either because of network problems, or because the
             Management Client is no longer operational.
             
             It is recommended that this device be configured to
             send a Trap PDU, not an InformRequest PDU, for this
             Notification to all Management Clients, thus bypassing
             a problematic InformRequest PDU queue and allowing the
             situation to be quickly identified and resolved."
    ::= 1

sonusNetMgmtClientInformReqQueueFullNotification TRAP-TYPE
    ENTERPRISE      sonusCommonMIBNotifications
    VARIABLES       { sonusNetMgmtClientName, 
                      sonusNetMgmtInformReqDiscards, 
                      sonusEventDescription, sonusEventClass, 
                      sonusEventLevel, sonusSequenceId, sonusEventTime }
--     STATUS          mandatory
    DESCRIPTION     
            "The specified number of InformRequest PDUs destined to
             the specified Management Client were discard because its
             InformRequest PDU queue was full.
             
             This situtation could occur if the Management Client
             cannot quickly process and respond to InformRequest PDUs
             that it receives, or if communications is lost with the
             Management Client.
             
             If this situation occurs occasionally, it is recommended
             to increase the InformRequest PDU queue size (see
             sonusNetMgmtClientInformReqMaxQueue.)
             
             If this situation occurs repeatedly, it is an indication
             that communications is lost with the Management Client,
             either because of network problems, or because the
             Management Client is no longer operational.
             
             It is recommended that this device be configured to
             send a Trap PDU, not an InformRequest PDU, for this
             Notification to all Management Clients, thus bypassing
             a problematic InformRequest PDU queue and allowing the
             situation to be quickly identified and resolved."
    ::= 2

sonusIpCacPlusLimitSetNotification TRAP-TYPE
    ENTERPRISE      sonusCommonMIBNotifications
    VARIABLES       { sonusEventDescription, sonusEventClass, 
                      sonusEventLevel, sonusSequenceId, sonusEventTime }
--     STATUS          mandatory
    DESCRIPTION     
            "This trap indicates that IP CAC Limit is set."
    ::= 3

sonusIpCacPlusLimitClearNotification TRAP-TYPE
    ENTERPRISE      sonusCommonMIBNotifications
    VARIABLES       { sonusEventDescription, sonusEventClass, 
                      sonusEventLevel, sonusSequenceId, sonusEventTime }
--     STATUS          mandatory
    DESCRIPTION     
            "This trap indicates that IP CAC Limit is cleared."
    ::= 4

END -- end of module SONUS-COMMON-MIB.
