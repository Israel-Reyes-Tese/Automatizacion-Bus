--
-- This SMIv1 module has been generated by smidump 0.2-cvs. Do not edit.
--

SONUS-SOFTSWITCH-UTIL-MIB DEFINITIONS ::= BEGIN

IMPORTS
    TRAP-TYPE
        FROM RFC-1215
    sonusEventClass, sonusEventDescription, sonusEventLevel, 
    sonusEventTime
        FROM SONUS-COMMON-MIB
    sonusServicesMIBs
        FROM SONUS-SMI;

sonusSoftSwitchUtilMIB OBJECT IDENTIFIER
    ::= { sonusServicesMIBs 41 }

-- sonusSoftSwitchUtilMIB MODULE-IDENTITY
--     LAST-UPDATED    "200205030000Z"
--     ORGANIZATION    
--             "Sonus Networks, Inc."
--     CONTACT-INFO    
--             "   Customer Support    
--              Sonus Networks, Inc.
--              4 Technology Park Drive 
--              Westford, MA 01886
--              USA
--              
--              Tel: 978-614-8100
--              Fax: 978-614-8609"
--     DESCRIPTION     
--             "The MIB Module for SoftSwitch Database Replication Management."
--     ::= { sonusServicesMIBs 41 }


sonusSoftSwitchUtilMIBObjects OBJECT IDENTIFIER
    ::= { sonusSoftSwitchUtilMIB 1 }

sonusSoftSwitchUtilMIBNotifications OBJECT IDENTIFIER
    ::= { sonusSoftSwitchUtilMIB 2 }

sonusSoftSwitchUtilMIBNotificationsPrefix OBJECT IDENTIFIER
    ::= { sonusSoftSwitchUtilMIBNotifications 0 }

sonusSoftSwitchUtilMIBNotificationsObjects OBJECT IDENTIFIER
    ::= { sonusSoftSwitchUtilMIBNotifications 1 }

sonusSoftSwitchUtilBDDLoadFailedNotification TRAP-TYPE
    ENTERPRISE      sonusSoftSwitchUtilMIBNotifications
    VARIABLES       { sonusEventDescription, sonusEventClass, 
                      sonusEventLevel, sonusEventTime }
--     STATUS          mandatory
    DESCRIPTION     
            "The BDD loader tool encounters an error while loading."
    ::= 1

END -- end of module SONUS-SOFTSWITCH-UTIL-MIB.
