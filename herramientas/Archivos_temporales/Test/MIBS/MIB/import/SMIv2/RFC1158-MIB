--
-- This SMIv2 module has been generated by smidump 0.2-cvs. Do not edit.
--

RFC1158-MIB DEFINITIONS ::= BEGIN

IMPORTS
    NetworkAddress
        FROM RFC1155-SMI
    Counter32, Gauge32, Integer32, IpAddress, OBJECT-TYPE, TimeTicks, 
    mgmt
        FROM SNMPv2-SMI;

DisplayString ::=
    OCTET STRING

nullSpecific OBJECT IDENTIFIER
    ::= { 0 0 }

mib-2 OBJECT IDENTIFIER
    ::= { mgmt 1 }

system OBJECT IDENTIFIER
    ::= { mib-2 1 }

sysDescr OBJECT-TYPE
    SYNTAX          DisplayString (SIZE(0..255))
    MAX-ACCESS      read-only
    STATUS          current
    DESCRIPTION     
            "..."
    ::= { system 1 }

sysObjectID OBJECT-TYPE
    SYNTAX          OBJECT IDENTIFIER
    MAX-ACCESS      read-only
    STATUS          current
    DESCRIPTION     
            "..."
    ::= { system 2 }

sysUpTime OBJECT-TYPE
    SYNTAX          TimeTicks
    MAX-ACCESS      read-only
    STATUS          current
    DESCRIPTION     
            "..."
    ::= { system 3 }

sysContact OBJECT-TYPE
    SYNTAX          DisplayString (SIZE(0..255))
    MAX-ACCESS      read-write
    STATUS          current
    DESCRIPTION     
            "..."
    ::= { system 4 }

sysName OBJECT-TYPE
    SYNTAX          DisplayString (SIZE(0..255))
    MAX-ACCESS      read-write
    STATUS          current
    DESCRIPTION     
            "..."
    ::= { system 5 }

sysLocation OBJECT-TYPE
    SYNTAX          DisplayString (SIZE(0..255))
    MAX-ACCESS      read-only
    STATUS          current
    DESCRIPTION     
            "..."
    ::= { system 6 }

sysServices OBJECT-TYPE
    SYNTAX          Integer32 (0..127)
    MAX-ACCESS      read-only
    STATUS          current
    DESCRIPTION     
            "..."
    ::= { system 7 }

interfaces OBJECT IDENTIFIER
    ::= { mib-2 2 }

ifNumber OBJECT-TYPE
    SYNTAX          Integer32
    MAX-ACCESS      read-only
    STATUS          current
    DESCRIPTION     
            "..."
    ::= { interfaces 1 }

ifTable OBJECT-TYPE
    SYNTAX          SEQUENCE OF IfEntry
    MAX-ACCESS      read-only
    STATUS          current
    DESCRIPTION     
            "..."
    ::= { interfaces 2 }

ifEntry OBJECT-TYPE
    SYNTAX          IfEntry
    MAX-ACCESS      read-only
    STATUS          current
    DESCRIPTION     
            "..."
    ::= { ifTable 1 }

IfEntry ::=
    SEQUENCE {
        ifIndex                         Integer32,
        ifDescr                         DisplayString,
        ifType                          INTEGER,
        ifMtu                           Integer32,
        ifSpeed                         Gauge32,
        ifPhysAddress                   OCTET STRING,
        ifAdminStatus                   INTEGER,
        ifOperStatus                    INTEGER,
        ifLastChange                    TimeTicks,
        ifInOctets                      Counter32,
        ifInUcastPkts                   Counter32,
        ifInNUcastPkts                  Counter32,
        ifInDiscards                    Counter32,
        ifInErrors                      Counter32,
        ifInUnknownProtos               Counter32,
        ifOutOctets                     Counter32,
        ifOutUcastPkts                  Counter32,
        ifOutNUcastPkts                 Counter32,
        ifOutDiscards                   Counter32,
        ifOutErrors                     Counter32,
        ifOutQLen                       Gauge32,
        ifSpecific                      OBJECT IDENTIFIER
    }

ifIndex OBJECT-TYPE
    SYNTAX          Integer32
    MAX-ACCESS      read-only
    STATUS          current
    DESCRIPTION     
            "..."
    ::= { ifEntry 1 }

ifDescr OBJECT-TYPE
    SYNTAX          DisplayString (SIZE(0..255))
    MAX-ACCESS      read-only
    STATUS          current
    DESCRIPTION     
            "..."
    ::= { ifEntry 2 }

ifType OBJECT-TYPE
    SYNTAX          INTEGER { other(1), regular1822(2), hdh1822(3), 
                        ddn-x25(4), rfc877-x25(5), ethernet-csmacd(6), 
                        iso88023-csmacd(7), iso88024-tokenBus(8), 
                        iso88025-tokenRing(9), iso88026-man(10), 
                        starLan(11), proteon-10Mbit(12), 
                        proteon-80Mbit(13), hyperchannel(14), fddi(15), 
                        lapb(16), sdlc(17), t1-carrier(18), cept(19), 
                        basicISDN(20), primaryISDN(21), 
                        propPointToPointSerial(22), 
                        terminalServer-asyncPort(23), 
                        softwareLoopback(24), eon(25), 
                        ethernet-3Mbit(26), nsip(27), slip(28) }
    MAX-ACCESS      read-only
    STATUS          current
    DESCRIPTION     
            "..."
    ::= { ifEntry 3 }

ifMtu OBJECT-TYPE
    SYNTAX          Integer32
    MAX-ACCESS      read-only
    STATUS          current
    DESCRIPTION     
            "..."
    ::= { ifEntry 4 }

ifSpeed OBJECT-TYPE
    SYNTAX          Gauge32
    MAX-ACCESS      read-only
    STATUS          current
    DESCRIPTION     
            "..."
    ::= { ifEntry 5 }

ifPhysAddress OBJECT-TYPE
    SYNTAX          OCTET STRING
    MAX-ACCESS      read-only
    STATUS          current
    DESCRIPTION     
            "..."
    ::= { ifEntry 6 }

ifAdminStatus OBJECT-TYPE
    SYNTAX          INTEGER { up(1), down(2), testing(3) }
    MAX-ACCESS      read-write
    STATUS          current
    DESCRIPTION     
            "..."
    ::= { ifEntry 7 }

ifOperStatus OBJECT-TYPE
    SYNTAX          INTEGER { up(1), down(2), testing(3) }
    MAX-ACCESS      read-only
    STATUS          current
    DESCRIPTION     
            "..."
    ::= { ifEntry 8 }

ifLastChange OBJECT-TYPE
    SYNTAX          TimeTicks
    MAX-ACCESS      read-only
    STATUS          current
    DESCRIPTION     
            "..."
    ::= { ifEntry 9 }

ifInOctets OBJECT-TYPE
    SYNTAX          Counter32
    MAX-ACCESS      read-only
    STATUS          current
    DESCRIPTION     
            "..."
    ::= { ifEntry 10 }

ifInUcastPkts OBJECT-TYPE
    SYNTAX          Counter32
    MAX-ACCESS      read-only
    STATUS          current
    DESCRIPTION     
            "..."
    ::= { ifEntry 11 }

ifInNUcastPkts OBJECT-TYPE
    SYNTAX          Counter32
    MAX-ACCESS      read-only
    STATUS          current
    DESCRIPTION     
            "..."
    ::= { ifEntry 12 }

ifInDiscards OBJECT-TYPE
    SYNTAX          Counter32
    MAX-ACCESS      read-only
    STATUS          current
    DESCRIPTION     
            "..."
    ::= { ifEntry 13 }

ifInErrors OBJECT-TYPE
    SYNTAX          Counter32
    MAX-ACCESS      read-only
    STATUS          current
    DESCRIPTION     
            "..."
    ::= { ifEntry 14 }

ifInUnknownProtos OBJECT-TYPE
    SYNTAX          Counter32
    MAX-ACCESS      read-only
    STATUS          current
    DESCRIPTION     
            "..."
    ::= { ifEntry 15 }

ifOutOctets OBJECT-TYPE
    SYNTAX          Counter32
    MAX-ACCESS      read-only
    STATUS          current
    DESCRIPTION     
            "..."
    ::= { ifEntry 16 }

ifOutUcastPkts OBJECT-TYPE
    SYNTAX          Counter32
    MAX-ACCESS      read-only
    STATUS          current
    DESCRIPTION     
            "..."
    ::= { ifEntry 17 }

ifOutNUcastPkts OBJECT-TYPE
    SYNTAX          Counter32
    MAX-ACCESS      read-only
    STATUS          current
    DESCRIPTION     
            "..."
    ::= { ifEntry 18 }

ifOutDiscards OBJECT-TYPE
    SYNTAX          Counter32
    MAX-ACCESS      read-only
    STATUS          current
    DESCRIPTION     
            "..."
    ::= { ifEntry 19 }

ifOutErrors OBJECT-TYPE
    SYNTAX          Counter32
    MAX-ACCESS      read-only
    STATUS          current
    DESCRIPTION     
            "..."
    ::= { ifEntry 20 }

ifOutQLen OBJECT-TYPE
    SYNTAX          Gauge32
    MAX-ACCESS      read-only
    STATUS          current
    DESCRIPTION     
            "..."
    ::= { ifEntry 21 }

ifSpecific OBJECT-TYPE
    SYNTAX          OBJECT IDENTIFIER
    MAX-ACCESS      read-only
    STATUS          current
    DESCRIPTION     
            "..."
    ::= { ifEntry 22 }

at OBJECT IDENTIFIER
    ::= { mib-2 3 }

atTable OBJECT-TYPE
    SYNTAX          SEQUENCE OF AtEntry
    MAX-ACCESS      read-write
    STATUS          obsolete
    DESCRIPTION     
            "..."
    ::= { at 1 }

atEntry OBJECT-TYPE
    SYNTAX          AtEntry
    MAX-ACCESS      read-write
    STATUS          obsolete
    DESCRIPTION     
            "..."
    ::= { atTable 1 }

AtEntry ::=
    SEQUENCE {
        atIfIndex                       Integer32,
        atPhysAddress                   OCTET STRING,
        atNetAddress                    NetworkAddress
    }

atIfIndex OBJECT-TYPE
    SYNTAX          Integer32
    MAX-ACCESS      read-write
    STATUS          obsolete
    DESCRIPTION     
            "..."
    ::= { atEntry 1 }

atPhysAddress OBJECT-TYPE
    SYNTAX          OCTET STRING
    MAX-ACCESS      read-write
    STATUS          obsolete
    DESCRIPTION     
            "..."
    ::= { atEntry 2 }

atNetAddress OBJECT-TYPE
    SYNTAX          NetworkAddress
    MAX-ACCESS      read-write
    STATUS          obsolete
    DESCRIPTION     
            "..."
    ::= { atEntry 3 }

ip OBJECT IDENTIFIER
    ::= { mib-2 4 }

ipForwarding OBJECT-TYPE
    SYNTAX          INTEGER { gateway(1), host(2) }
    MAX-ACCESS      read-write
    STATUS          current
    DESCRIPTION     
            "..."
    ::= { ip 1 }

ipDefaultTTL OBJECT-TYPE
    SYNTAX          Integer32
    MAX-ACCESS      read-write
    STATUS          current
    DESCRIPTION     
            "..."
    ::= { ip 2 }

ipInReceives OBJECT-TYPE
    SYNTAX          Counter32
    MAX-ACCESS      read-only
    STATUS          current
    DESCRIPTION     
            "..."
    ::= { ip 3 }

ipInHdrErrors OBJECT-TYPE
    SYNTAX          Counter32
    MAX-ACCESS      read-only
    STATUS          current
    DESCRIPTION     
            "..."
    ::= { ip 4 }

ipInAddrErrors OBJECT-TYPE
    SYNTAX          Counter32
    MAX-ACCESS      read-only
    STATUS          current
    DESCRIPTION     
            "..."
    ::= { ip 5 }

ipForwDatagrams OBJECT-TYPE
    SYNTAX          Counter32
    MAX-ACCESS      read-only
    STATUS          current
    DESCRIPTION     
            "..."
    ::= { ip 6 }

ipInUnknownProtos OBJECT-TYPE
    SYNTAX          Counter32
    MAX-ACCESS      read-only
    STATUS          current
    DESCRIPTION     
            "..."
    ::= { ip 7 }

ipInDiscards OBJECT-TYPE
    SYNTAX          Counter32
    MAX-ACCESS      read-only
    STATUS          current
    DESCRIPTION     
            "..."
    ::= { ip 8 }

ipInDelivers OBJECT-TYPE
    SYNTAX          Counter32
    MAX-ACCESS      read-only
    STATUS          current
    DESCRIPTION     
            "..."
    ::= { ip 9 }

ipOutRequests OBJECT-TYPE
    SYNTAX          Counter32
    MAX-ACCESS      read-only
    STATUS          current
    DESCRIPTION     
            "..."
    ::= { ip 10 }

ipOutDiscards OBJECT-TYPE
    SYNTAX          Counter32
    MAX-ACCESS      read-only
    STATUS          current
    DESCRIPTION     
            "..."
    ::= { ip 11 }

ipOutNoRoutes OBJECT-TYPE
    SYNTAX          Counter32
    MAX-ACCESS      read-only
    STATUS          current
    DESCRIPTION     
            "..."
    ::= { ip 12 }

ipReasmTimeout OBJECT-TYPE
    SYNTAX          Integer32
    MAX-ACCESS      read-only
    STATUS          current
    DESCRIPTION     
            "..."
    ::= { ip 13 }

ipReasmReqds OBJECT-TYPE
    SYNTAX          Counter32
    MAX-ACCESS      read-only
    STATUS          current
    DESCRIPTION     
            "..."
    ::= { ip 14 }

ipReasmOKs OBJECT-TYPE
    SYNTAX          Counter32
    MAX-ACCESS      read-only
    STATUS          current
    DESCRIPTION     
            "..."
    ::= { ip 15 }

ipReasmFails OBJECT-TYPE
    SYNTAX          Counter32
    MAX-ACCESS      read-only
    STATUS          current
    DESCRIPTION     
            "..."
    ::= { ip 16 }

ipFragOKs OBJECT-TYPE
    SYNTAX          Counter32
    MAX-ACCESS      read-only
    STATUS          current
    DESCRIPTION     
            "..."
    ::= { ip 17 }

ipFragFails OBJECT-TYPE
    SYNTAX          Counter32
    MAX-ACCESS      read-only
    STATUS          current
    DESCRIPTION     
            "..."
    ::= { ip 18 }

ipFragCreates OBJECT-TYPE
    SYNTAX          Counter32
    MAX-ACCESS      read-only
    STATUS          current
    DESCRIPTION     
            "..."
    ::= { ip 19 }

ipAddrTable OBJECT-TYPE
    SYNTAX          SEQUENCE OF IpAddrEntry
    MAX-ACCESS      read-only
    STATUS          current
    DESCRIPTION     
            "..."
    ::= { ip 20 }

ipAddrEntry OBJECT-TYPE
    SYNTAX          IpAddrEntry
    MAX-ACCESS      read-only
    STATUS          current
    DESCRIPTION     
            "..."
    ::= { ipAddrTable 1 }

IpAddrEntry ::=
    SEQUENCE {
        ipAdEntAddr                     IpAddress,
        ipAdEntIfIndex                  Integer32,
        ipAdEntNetMask                  IpAddress,
        ipAdEntBcastAddr                Integer32,
        ipAdEntReasmMaxSize             Integer32
    }

ipAdEntAddr OBJECT-TYPE
    SYNTAX          IpAddress
    MAX-ACCESS      read-only
    STATUS          current
    DESCRIPTION     
            "..."
    ::= { ipAddrEntry 1 }

ipAdEntIfIndex OBJECT-TYPE
    SYNTAX          Integer32
    MAX-ACCESS      read-only
    STATUS          current
    DESCRIPTION     
            "..."
    ::= { ipAddrEntry 2 }

ipAdEntNetMask OBJECT-TYPE
    SYNTAX          IpAddress
    MAX-ACCESS      read-only
    STATUS          current
    DESCRIPTION     
            "..."
    ::= { ipAddrEntry 3 }

ipAdEntBcastAddr OBJECT-TYPE
    SYNTAX          Integer32
    MAX-ACCESS      read-only
    STATUS          current
    DESCRIPTION     
            "..."
    ::= { ipAddrEntry 4 }

ipAdEntReasmMaxSize OBJECT-TYPE
    SYNTAX          Integer32 (0..65535)
    MAX-ACCESS      read-only
    STATUS          current
    DESCRIPTION     
            "..."
    ::= { ipAddrEntry 5 }

ipRoutingTable OBJECT-TYPE
    SYNTAX          SEQUENCE OF IpRouteEntry
    MAX-ACCESS      read-write
    STATUS          current
    DESCRIPTION     
            "..."
    ::= { ip 21 }

ipRouteEntry OBJECT-TYPE
    SYNTAX          IpRouteEntry
    MAX-ACCESS      read-write
    STATUS          current
    DESCRIPTION     
            "..."
    ::= { ipRoutingTable 1 }

IpRouteEntry ::=
    SEQUENCE {
        ipRouteDest                     IpAddress,
        ipRouteIfIndex                  Integer32,
        ipRouteMetric1                  Integer32,
        ipRouteMetric2                  Integer32,
        ipRouteMetric3                  Integer32,
        ipRouteMetric4                  Integer32,
        ipRouteNextHop                  IpAddress,
        ipRouteType                     INTEGER,
        ipRouteProto                    INTEGER,
        ipRouteAge                      Integer32,
        ipRouteMask                     IpAddress
    }

ipRouteDest OBJECT-TYPE
    SYNTAX          IpAddress
    MAX-ACCESS      read-write
    STATUS          current
    DESCRIPTION     
            "..."
    ::= { ipRouteEntry 1 }

ipRouteIfIndex OBJECT-TYPE
    SYNTAX          Integer32
    MAX-ACCESS      read-write
    STATUS          current
    DESCRIPTION     
            "..."
    ::= { ipRouteEntry 2 }

ipRouteMetric1 OBJECT-TYPE
    SYNTAX          Integer32
    MAX-ACCESS      read-write
    STATUS          current
    DESCRIPTION     
            "..."
    ::= { ipRouteEntry 3 }

ipRouteMetric2 OBJECT-TYPE
    SYNTAX          Integer32
    MAX-ACCESS      read-write
    STATUS          current
    DESCRIPTION     
            "..."
    ::= { ipRouteEntry 4 }

ipRouteMetric3 OBJECT-TYPE
    SYNTAX          Integer32
    MAX-ACCESS      read-write
    STATUS          current
    DESCRIPTION     
            "..."
    ::= { ipRouteEntry 5 }

ipRouteMetric4 OBJECT-TYPE
    SYNTAX          Integer32
    MAX-ACCESS      read-write
    STATUS          current
    DESCRIPTION     
            "..."
    ::= { ipRouteEntry 6 }

ipRouteNextHop OBJECT-TYPE
    SYNTAX          IpAddress
    MAX-ACCESS      read-write
    STATUS          current
    DESCRIPTION     
            "..."
    ::= { ipRouteEntry 7 }

ipRouteType OBJECT-TYPE
    SYNTAX          INTEGER { other(1), invalid(2), direct(3), remote(4) }
    MAX-ACCESS      read-write
    STATUS          current
    DESCRIPTION     
            "..."
    ::= { ipRouteEntry 8 }

ipRouteProto OBJECT-TYPE
    SYNTAX          INTEGER { other(1), local(2), netmgmt(3), icmp(4), 
                        egp(5), ggp(6), hello(7), rip(8), is-is(9), 
                        es-is(10), ciscoIgrp(11), bbnSpfIgp(12), 
                        ospf(13), bgp(14) }
    MAX-ACCESS      read-only
    STATUS          current
    DESCRIPTION     
            "..."
    ::= { ipRouteEntry 9 }

ipRouteAge OBJECT-TYPE
    SYNTAX          Integer32
    MAX-ACCESS      read-write
    STATUS          current
    DESCRIPTION     
            "..."
    ::= { ipRouteEntry 10 }

ipRouteMask OBJECT-TYPE
    SYNTAX          IpAddress
    MAX-ACCESS      read-write
    STATUS          current
    DESCRIPTION     
            "..."
    ::= { ipRouteEntry 11 }

ipNetToMediaTable OBJECT-TYPE
    SYNTAX          SEQUENCE OF IpNetToMediaEntry
    MAX-ACCESS      read-write
    STATUS          current
    DESCRIPTION     
            "..."
    ::= { ip 22 }

ipNetToMediaEntry OBJECT-TYPE
    SYNTAX          IpNetToMediaEntry
    MAX-ACCESS      read-write
    STATUS          current
    DESCRIPTION     
            "..."
    ::= { ipNetToMediaTable 1 }

IpNetToMediaEntry ::=
    SEQUENCE {
        ipNetToMediaIfIndex             Integer32,
        ipNetToMediaPhysAddress         OCTET STRING,
        ipNetToMediaNetAddress          IpAddress,
        ipNetToMediaType                INTEGER
    }

ipNetToMediaIfIndex OBJECT-TYPE
    SYNTAX          Integer32
    MAX-ACCESS      read-write
    STATUS          current
    DESCRIPTION     
            "..."
    ::= { ipNetToMediaEntry 1 }

ipNetToMediaPhysAddress OBJECT-TYPE
    SYNTAX          OCTET STRING
    MAX-ACCESS      read-write
    STATUS          current
    DESCRIPTION     
            "..."
    ::= { ipNetToMediaEntry 2 }

ipNetToMediaNetAddress OBJECT-TYPE
    SYNTAX          IpAddress
    MAX-ACCESS      read-write
    STATUS          current
    DESCRIPTION     
            "..."
    ::= { ipNetToMediaEntry 3 }

ipNetToMediaType OBJECT-TYPE
    SYNTAX          INTEGER { other(1), invalid(2), dynamic(3), 
                        static(4) }
    MAX-ACCESS      read-write
    STATUS          current
    DESCRIPTION     
            "..."
    ::= { ipNetToMediaEntry 4 }

icmp OBJECT IDENTIFIER
    ::= { mib-2 5 }

icmpInMsgs OBJECT-TYPE
    SYNTAX          Counter32
    MAX-ACCESS      read-only
    STATUS          current
    DESCRIPTION     
            "..."
    ::= { icmp 1 }

icmpInErrors OBJECT-TYPE
    SYNTAX          Counter32
    MAX-ACCESS      read-only
    STATUS          current
    DESCRIPTION     
            "..."
    ::= { icmp 2 }

icmpInDestUnreachs OBJECT-TYPE
    SYNTAX          Counter32
    MAX-ACCESS      read-only
    STATUS          current
    DESCRIPTION     
            "..."
    ::= { icmp 3 }

icmpInTimeExcds OBJECT-TYPE
    SYNTAX          Counter32
    MAX-ACCESS      read-only
    STATUS          current
    DESCRIPTION     
            "..."
    ::= { icmp 4 }

icmpInParmProbs OBJECT-TYPE
    SYNTAX          Counter32
    MAX-ACCESS      read-only
    STATUS          current
    DESCRIPTION     
            "..."
    ::= { icmp 5 }

icmpInSrcQuenchs OBJECT-TYPE
    SYNTAX          Counter32
    MAX-ACCESS      read-only
    STATUS          current
    DESCRIPTION     
            "..."
    ::= { icmp 6 }

icmpInRedirects OBJECT-TYPE
    SYNTAX          Counter32
    MAX-ACCESS      read-only
    STATUS          current
    DESCRIPTION     
            "..."
    ::= { icmp 7 }

icmpInEchos OBJECT-TYPE
    SYNTAX          Counter32
    MAX-ACCESS      read-only
    STATUS          current
    DESCRIPTION     
            "..."
    ::= { icmp 8 }

icmpInEchoReps OBJECT-TYPE
    SYNTAX          Counter32
    MAX-ACCESS      read-only
    STATUS          current
    DESCRIPTION     
            "..."
    ::= { icmp 9 }

icmpInTimestamps OBJECT-TYPE
    SYNTAX          Counter32
    MAX-ACCESS      read-only
    STATUS          current
    DESCRIPTION     
            "..."
    ::= { icmp 10 }

icmpInTimestampReps OBJECT-TYPE
    SYNTAX          Counter32
    MAX-ACCESS      read-only
    STATUS          current
    DESCRIPTION     
            "..."
    ::= { icmp 11 }

icmpInAddrMasks OBJECT-TYPE
    SYNTAX          Counter32
    MAX-ACCESS      read-only
    STATUS          current
    DESCRIPTION     
            "..."
    ::= { icmp 12 }

icmpInAddrMaskReps OBJECT-TYPE
    SYNTAX          Counter32
    MAX-ACCESS      read-only
    STATUS          current
    DESCRIPTION     
            "..."
    ::= { icmp 13 }

icmpOutMsgs OBJECT-TYPE
    SYNTAX          Counter32
    MAX-ACCESS      read-only
    STATUS          current
    DESCRIPTION     
            "..."
    ::= { icmp 14 }

icmpOutErrors OBJECT-TYPE
    SYNTAX          Counter32
    MAX-ACCESS      read-only
    STATUS          current
    DESCRIPTION     
            "..."
    ::= { icmp 15 }

icmpOutDestUnreachs OBJECT-TYPE
    SYNTAX          Counter32
    MAX-ACCESS      read-only
    STATUS          current
    DESCRIPTION     
            "..."
    ::= { icmp 16 }

icmpOutTimeExcds OBJECT-TYPE
    SYNTAX          Counter32
    MAX-ACCESS      read-only
    STATUS          current
    DESCRIPTION     
            "..."
    ::= { icmp 17 }

icmpOutParmProbs OBJECT-TYPE
    SYNTAX          Counter32
    MAX-ACCESS      read-only
    STATUS          current
    DESCRIPTION     
            "..."
    ::= { icmp 18 }

icmpOutSrcQuenchs OBJECT-TYPE
    SYNTAX          Counter32
    MAX-ACCESS      read-only
    STATUS          current
    DESCRIPTION     
            "..."
    ::= { icmp 19 }

icmpOutRedirects OBJECT-TYPE
    SYNTAX          Counter32
    MAX-ACCESS      read-only
    STATUS          current
    DESCRIPTION     
            "..."
    ::= { icmp 20 }

icmpOutEchos OBJECT-TYPE
    SYNTAX          Counter32
    MAX-ACCESS      read-only
    STATUS          current
    DESCRIPTION     
            "..."
    ::= { icmp 21 }

icmpOutEchoReps OBJECT-TYPE
    SYNTAX          Counter32
    MAX-ACCESS      read-only
    STATUS          current
    DESCRIPTION     
            "..."
    ::= { icmp 22 }

icmpOutTimestamps OBJECT-TYPE
    SYNTAX          Counter32
    MAX-ACCESS      read-only
    STATUS          current
    DESCRIPTION     
            "..."
    ::= { icmp 23 }

icmpOutTimestampReps OBJECT-TYPE
    SYNTAX          Counter32
    MAX-ACCESS      read-only
    STATUS          current
    DESCRIPTION     
            "..."
    ::= { icmp 24 }

icmpOutAddrMasks OBJECT-TYPE
    SYNTAX          Counter32
    MAX-ACCESS      read-only
    STATUS          current
    DESCRIPTION     
            "..."
    ::= { icmp 25 }

icmpOutAddrMaskReps OBJECT-TYPE
    SYNTAX          Counter32
    MAX-ACCESS      read-only
    STATUS          current
    DESCRIPTION     
            "..."
    ::= { icmp 26 }

tcp OBJECT IDENTIFIER
    ::= { mib-2 6 }

tcpRtoAlgorithm OBJECT-TYPE
    SYNTAX          INTEGER { other(1), constant(2), rsre(3), vanj(4) }
    MAX-ACCESS      read-only
    STATUS          current
    DESCRIPTION     
            "..."
    ::= { tcp 1 }

tcpRtoMin OBJECT-TYPE
    SYNTAX          Integer32
    MAX-ACCESS      read-only
    STATUS          current
    DESCRIPTION     
            "..."
    ::= { tcp 2 }

tcpRtoMax OBJECT-TYPE
    SYNTAX          Integer32
    MAX-ACCESS      read-only
    STATUS          current
    DESCRIPTION     
            "..."
    ::= { tcp 3 }

tcpMaxConn OBJECT-TYPE
    SYNTAX          Integer32
    MAX-ACCESS      read-only
    STATUS          current
    DESCRIPTION     
            "..."
    ::= { tcp 4 }

tcpActiveOpens OBJECT-TYPE
    SYNTAX          Counter32
    MAX-ACCESS      read-only
    STATUS          current
    DESCRIPTION     
            "..."
    ::= { tcp 5 }

tcpPassiveOpens OBJECT-TYPE
    SYNTAX          Counter32
    MAX-ACCESS      read-only
    STATUS          current
    DESCRIPTION     
            "..."
    ::= { tcp 6 }

tcpAttemptFails OBJECT-TYPE
    SYNTAX          Counter32
    MAX-ACCESS      read-only
    STATUS          current
    DESCRIPTION     
            "..."
    ::= { tcp 7 }

tcpEstabResets OBJECT-TYPE
    SYNTAX          Counter32
    MAX-ACCESS      read-only
    STATUS          current
    DESCRIPTION     
            "..."
    ::= { tcp 8 }

tcpCurrEstab OBJECT-TYPE
    SYNTAX          Gauge32
    MAX-ACCESS      read-only
    STATUS          current
    DESCRIPTION     
            "..."
    ::= { tcp 9 }

tcpInSegs OBJECT-TYPE
    SYNTAX          Counter32
    MAX-ACCESS      read-only
    STATUS          current
    DESCRIPTION     
            "..."
    ::= { tcp 10 }

tcpOutSegs OBJECT-TYPE
    SYNTAX          Counter32
    MAX-ACCESS      read-only
    STATUS          current
    DESCRIPTION     
            "..."
    ::= { tcp 11 }

tcpRetransSegs OBJECT-TYPE
    SYNTAX          Counter32
    MAX-ACCESS      read-only
    STATUS          current
    DESCRIPTION     
            "..."
    ::= { tcp 12 }

tcpConnTable OBJECT-TYPE
    SYNTAX          SEQUENCE OF TcpConnEntry
    MAX-ACCESS      read-only
    STATUS          current
    DESCRIPTION     
            "..."
    ::= { tcp 13 }

tcpConnEntry OBJECT-TYPE
    SYNTAX          TcpConnEntry
    MAX-ACCESS      read-only
    STATUS          current
    DESCRIPTION     
            "..."
    ::= { tcpConnTable 1 }

TcpConnEntry ::=
    SEQUENCE {
        tcpConnState                    INTEGER,
        tcpConnLocalAddress             IpAddress,
        tcpConnLocalPort                Integer32,
        tcpConnRemAddress               IpAddress,
        tcpConnRemPort                  Integer32
    }

tcpConnState OBJECT-TYPE
    SYNTAX          INTEGER { closed(1), listen(2), synSent(3), 
                        synReceived(4), established(5), finWait1(6), 
                        finWait2(7), closeWait(8), lastAck(9), 
                        closing(10), timeWait(11) }
    MAX-ACCESS      read-only
    STATUS          current
    DESCRIPTION     
            "..."
    ::= { tcpConnEntry 1 }

tcpConnLocalAddress OBJECT-TYPE
    SYNTAX          IpAddress
    MAX-ACCESS      read-only
    STATUS          current
    DESCRIPTION     
            "..."
    ::= { tcpConnEntry 2 }

tcpConnLocalPort OBJECT-TYPE
    SYNTAX          Integer32 (0..65535)
    MAX-ACCESS      read-only
    STATUS          current
    DESCRIPTION     
            "..."
    ::= { tcpConnEntry 3 }

tcpConnRemAddress OBJECT-TYPE
    SYNTAX          IpAddress
    MAX-ACCESS      read-only
    STATUS          current
    DESCRIPTION     
            "..."
    ::= { tcpConnEntry 4 }

tcpConnRemPort OBJECT-TYPE
    SYNTAX          Integer32 (0..65535)
    MAX-ACCESS      read-only
    STATUS          current
    DESCRIPTION     
            "..."
    ::= { tcpConnEntry 5 }

tcpInErrs OBJECT-TYPE
    SYNTAX          Counter32
    MAX-ACCESS      read-only
    STATUS          current
    DESCRIPTION     
            "..."
    ::= { tcp 14 }

tcpOutRsts OBJECT-TYPE
    SYNTAX          Counter32
    MAX-ACCESS      read-only
    STATUS          current
    DESCRIPTION     
            "..."
    ::= { tcp 15 }

udp OBJECT IDENTIFIER
    ::= { mib-2 7 }

udpInDatagrams OBJECT-TYPE
    SYNTAX          Counter32
    MAX-ACCESS      read-only
    STATUS          current
    DESCRIPTION     
            "..."
    ::= { udp 1 }

udpNoPorts OBJECT-TYPE
    SYNTAX          Counter32
    MAX-ACCESS      read-only
    STATUS          current
    DESCRIPTION     
            "..."
    ::= { udp 2 }

udpInErrors OBJECT-TYPE
    SYNTAX          Counter32
    MAX-ACCESS      read-only
    STATUS          current
    DESCRIPTION     
            "..."
    ::= { udp 3 }

udpOutDatagrams OBJECT-TYPE
    SYNTAX          Counter32
    MAX-ACCESS      read-only
    STATUS          current
    DESCRIPTION     
            "..."
    ::= { udp 4 }

udpTable OBJECT-TYPE
    SYNTAX          SEQUENCE OF UdpEntry
    MAX-ACCESS      read-only
    STATUS          current
    DESCRIPTION     
            "..."
    ::= { udp 5 }

udpEntry OBJECT-TYPE
    SYNTAX          UdpEntry
    MAX-ACCESS      read-only
    STATUS          current
    DESCRIPTION     
            "..."
    ::= { udpTable 1 }

UdpEntry ::=
    SEQUENCE {
        udpLocalAddress                 IpAddress,
        udpLocalPort                    Integer32
    }

udpLocalAddress OBJECT-TYPE
    SYNTAX          IpAddress
    MAX-ACCESS      read-only
    STATUS          current
    DESCRIPTION     
            "..."
    ::= { udpEntry 1 }

udpLocalPort OBJECT-TYPE
    SYNTAX          Integer32 (0..65535)
    MAX-ACCESS      read-only
    STATUS          current
    DESCRIPTION     
            "..."
    ::= { udpEntry 2 }

egp OBJECT IDENTIFIER
    ::= { mib-2 8 }

egpInMsgs OBJECT-TYPE
    SYNTAX          Counter32
    MAX-ACCESS      read-only
    STATUS          current
    DESCRIPTION     
            "..."
    ::= { egp 1 }

egpInErrors OBJECT-TYPE
    SYNTAX          Counter32
    MAX-ACCESS      read-only
    STATUS          current
    DESCRIPTION     
            "..."
    ::= { egp 2 }

egpOutMsgs OBJECT-TYPE
    SYNTAX          Counter32
    MAX-ACCESS      read-only
    STATUS          current
    DESCRIPTION     
            "..."
    ::= { egp 3 }

egpOutErrors OBJECT-TYPE
    SYNTAX          Counter32
    MAX-ACCESS      read-only
    STATUS          current
    DESCRIPTION     
            "..."
    ::= { egp 4 }

egpNeighTable OBJECT-TYPE
    SYNTAX          SEQUENCE OF EgpNeighEntry
    MAX-ACCESS      read-only
    STATUS          current
    DESCRIPTION     
            "..."
    ::= { egp 5 }

egpNeighEntry OBJECT-TYPE
    SYNTAX          EgpNeighEntry
    MAX-ACCESS      read-only
    STATUS          current
    DESCRIPTION     
            "..."
    ::= { egpNeighTable 1 }

EgpNeighEntry ::=
    SEQUENCE {
        egpNeighState                   INTEGER,
        egpNeighAddr                    IpAddress,
        egpNeighAs                      Integer32,
        egpNeighInMsgs                  Counter32,
        egpNeighInErrs                  Counter32,
        egpNeighOutMsgs                 Counter32,
        egpNeighOutErrs                 Counter32,
        egpNeighInErrMsgs               Counter32,
        egpNeighOutErrMsgs              Counter32,
        egpNeighStateUps                Counter32,
        egpNeighStateDowns              Counter32,
        egpNeighIntervalHello           Integer32,
        egpNeighIntervalPoll            Integer32,
        egpNeighMode                    INTEGER,
        egpNeighEventTrigger            INTEGER
    }

egpNeighState OBJECT-TYPE
    SYNTAX          INTEGER { idle(1), acquisition(2), down(3), up(4), 
                        cease(5) }
    MAX-ACCESS      read-only
    STATUS          current
    DESCRIPTION     
            "..."
    ::= { egpNeighEntry 1 }

egpNeighAddr OBJECT-TYPE
    SYNTAX          IpAddress
    MAX-ACCESS      read-only
    STATUS          current
    DESCRIPTION     
            "..."
    ::= { egpNeighEntry 2 }

egpNeighAs OBJECT-TYPE
    SYNTAX          Integer32
    MAX-ACCESS      read-only
    STATUS          current
    DESCRIPTION     
            "..."
    ::= { egpNeighEntry 3 }

egpNeighInMsgs OBJECT-TYPE
    SYNTAX          Counter32
    MAX-ACCESS      read-only
    STATUS          current
    DESCRIPTION     
            "..."
    ::= { egpNeighEntry 4 }

egpNeighInErrs OBJECT-TYPE
    SYNTAX          Counter32
    MAX-ACCESS      read-only
    STATUS          current
    DESCRIPTION     
            "..."
    ::= { egpNeighEntry 5 }

egpNeighOutMsgs OBJECT-TYPE
    SYNTAX          Counter32
    MAX-ACCESS      read-only
    STATUS          current
    DESCRIPTION     
            "..."
    ::= { egpNeighEntry 6 }

egpNeighOutErrs OBJECT-TYPE
    SYNTAX          Counter32
    MAX-ACCESS      read-only
    STATUS          current
    DESCRIPTION     
            "..."
    ::= { egpNeighEntry 7 }

egpNeighInErrMsgs OBJECT-TYPE
    SYNTAX          Counter32
    MAX-ACCESS      read-only
    STATUS          current
    DESCRIPTION     
            "..."
    ::= { egpNeighEntry 8 }

egpNeighOutErrMsgs OBJECT-TYPE
    SYNTAX          Counter32
    MAX-ACCESS      read-only
    STATUS          current
    DESCRIPTION     
            "..."
    ::= { egpNeighEntry 9 }

egpNeighStateUps OBJECT-TYPE
    SYNTAX          Counter32
    MAX-ACCESS      read-only
    STATUS          current
    DESCRIPTION     
            "..."
    ::= { egpNeighEntry 10 }

egpNeighStateDowns OBJECT-TYPE
    SYNTAX          Counter32
    MAX-ACCESS      read-only
    STATUS          current
    DESCRIPTION     
            "..."
    ::= { egpNeighEntry 11 }

egpNeighIntervalHello OBJECT-TYPE
    SYNTAX          Integer32
    MAX-ACCESS      read-only
    STATUS          current
    DESCRIPTION     
            "..."
    ::= { egpNeighEntry 12 }

egpNeighIntervalPoll OBJECT-TYPE
    SYNTAX          Integer32
    MAX-ACCESS      read-only
    STATUS          current
    DESCRIPTION     
            "..."
    ::= { egpNeighEntry 13 }

egpNeighMode OBJECT-TYPE
    SYNTAX          INTEGER { active(1), passive(2) }
    MAX-ACCESS      read-only
    STATUS          current
    DESCRIPTION     
            "..."
    ::= { egpNeighEntry 14 }

egpNeighEventTrigger OBJECT-TYPE
    SYNTAX          INTEGER { start(1), stop(2) }
    MAX-ACCESS      read-write
    STATUS          current
    DESCRIPTION     
            "..."
    ::= { egpNeighEntry 15 }

egpAs OBJECT-TYPE
    SYNTAX          Integer32
    MAX-ACCESS      read-only
    STATUS          current
    DESCRIPTION     
            "..."
    ::= { egp 6 }

transmission OBJECT IDENTIFIER
    ::= { mib-2 10 }

snmp OBJECT IDENTIFIER
    ::= { mib-2 11 }

snmpInPkts OBJECT-TYPE
    SYNTAX          Counter32
    MAX-ACCESS      read-only
    STATUS          current
    DESCRIPTION     
            "..."
    ::= { snmp 1 }

snmpOutPkts OBJECT-TYPE
    SYNTAX          Counter32
    MAX-ACCESS      read-only
    STATUS          current
    DESCRIPTION     
            "..."
    ::= { snmp 2 }

snmpInBadVersions OBJECT-TYPE
    SYNTAX          Counter32
    MAX-ACCESS      read-only
    STATUS          current
    DESCRIPTION     
            "..."
    ::= { snmp 3 }

snmpInBadCommunityNames OBJECT-TYPE
    SYNTAX          Counter32
    MAX-ACCESS      read-only
    STATUS          current
    DESCRIPTION     
            "..."
    ::= { snmp 4 }

snmpInBadCommunityUses OBJECT-TYPE
    SYNTAX          Counter32
    MAX-ACCESS      read-only
    STATUS          current
    DESCRIPTION     
            "..."
    ::= { snmp 5 }

snmpInASNParseErrs OBJECT-TYPE
    SYNTAX          Counter32
    MAX-ACCESS      read-only
    STATUS          current
    DESCRIPTION     
            "..."
    ::= { snmp 6 }

snmpInBadTypes OBJECT-TYPE
    SYNTAX          Counter32
    MAX-ACCESS      read-only
    STATUS          current
    DESCRIPTION     
            "..."
    ::= { snmp 7 }

snmpInTooBigs OBJECT-TYPE
    SYNTAX          Counter32
    MAX-ACCESS      read-only
    STATUS          current
    DESCRIPTION     
            "..."
    ::= { snmp 8 }

snmpInNoSuchNames OBJECT-TYPE
    SYNTAX          Counter32
    MAX-ACCESS      read-only
    STATUS          current
    DESCRIPTION     
            "..."
    ::= { snmp 9 }

snmpInBadValues OBJECT-TYPE
    SYNTAX          Counter32
    MAX-ACCESS      read-only
    STATUS          current
    DESCRIPTION     
            "..."
    ::= { snmp 10 }

snmpInReadOnlys OBJECT-TYPE
    SYNTAX          Counter32
    MAX-ACCESS      read-only
    STATUS          current
    DESCRIPTION     
            "..."
    ::= { snmp 11 }

snmpInGenErrs OBJECT-TYPE
    SYNTAX          Counter32
    MAX-ACCESS      read-only
    STATUS          current
    DESCRIPTION     
            "..."
    ::= { snmp 12 }

snmpInTotalReqVars OBJECT-TYPE
    SYNTAX          Counter32
    MAX-ACCESS      read-only
    STATUS          current
    DESCRIPTION     
            "..."
    ::= { snmp 13 }

snmpInTotalSetVars OBJECT-TYPE
    SYNTAX          Counter32
    MAX-ACCESS      read-only
    STATUS          current
    DESCRIPTION     
            "..."
    ::= { snmp 14 }

snmpInGetRequests OBJECT-TYPE
    SYNTAX          Counter32
    MAX-ACCESS      read-only
    STATUS          current
    DESCRIPTION     
            "..."
    ::= { snmp 15 }

snmpInGetNexts OBJECT-TYPE
    SYNTAX          Counter32
    MAX-ACCESS      read-only
    STATUS          current
    DESCRIPTION     
            "..."
    ::= { snmp 16 }

snmpInSetRequests OBJECT-TYPE
    SYNTAX          Counter32
    MAX-ACCESS      read-only
    STATUS          current
    DESCRIPTION     
            "..."
    ::= { snmp 17 }

snmpInGetResponses OBJECT-TYPE
    SYNTAX          Counter32
    MAX-ACCESS      read-only
    STATUS          current
    DESCRIPTION     
            "..."
    ::= { snmp 18 }

snmpInTraps OBJECT-TYPE
    SYNTAX          Counter32
    MAX-ACCESS      read-only
    STATUS          current
    DESCRIPTION     
            "..."
    ::= { snmp 19 }

snmpOutTooBigs OBJECT-TYPE
    SYNTAX          Counter32
    MAX-ACCESS      read-only
    STATUS          current
    DESCRIPTION     
            "..."
    ::= { snmp 20 }

snmpOutNoSuchNames OBJECT-TYPE
    SYNTAX          Counter32
    MAX-ACCESS      read-only
    STATUS          current
    DESCRIPTION     
            "..."
    ::= { snmp 21 }

snmpOutBadValues OBJECT-TYPE
    SYNTAX          Counter32
    MAX-ACCESS      read-only
    STATUS          current
    DESCRIPTION     
            "..."
    ::= { snmp 22 }

snmpOutReadOnlys OBJECT-TYPE
    SYNTAX          Counter32
    MAX-ACCESS      read-only
    STATUS          current
    DESCRIPTION     
            "..."
    ::= { snmp 23 }

snmpOutGenErrs OBJECT-TYPE
    SYNTAX          Counter32
    MAX-ACCESS      read-only
    STATUS          current
    DESCRIPTION     
            "..."
    ::= { snmp 24 }

snmpOutGetRequests OBJECT-TYPE
    SYNTAX          Counter32
    MAX-ACCESS      read-only
    STATUS          current
    DESCRIPTION     
            "..."
    ::= { snmp 25 }

snmpOutGetNexts OBJECT-TYPE
    SYNTAX          Counter32
    MAX-ACCESS      read-only
    STATUS          current
    DESCRIPTION     
            "..."
    ::= { snmp 26 }

snmpOutSetRequests OBJECT-TYPE
    SYNTAX          Counter32
    MAX-ACCESS      read-only
    STATUS          current
    DESCRIPTION     
            "..."
    ::= { snmp 27 }

snmpOutGetResponses OBJECT-TYPE
    SYNTAX          Counter32
    MAX-ACCESS      read-only
    STATUS          current
    DESCRIPTION     
            "..."
    ::= { snmp 28 }

snmpOutTraps OBJECT-TYPE
    SYNTAX          Counter32
    MAX-ACCESS      read-only
    STATUS          current
    DESCRIPTION     
            "..."
    ::= { snmp 29 }

snmpEnableAuthTraps OBJECT-TYPE
    SYNTAX          INTEGER { enabled(1), disabled(2) }
    MAX-ACCESS      read-write
    STATUS          current
    DESCRIPTION     
            "..."
    ::= { snmp 30 }

END -- end of module RFC1158-MIB.
