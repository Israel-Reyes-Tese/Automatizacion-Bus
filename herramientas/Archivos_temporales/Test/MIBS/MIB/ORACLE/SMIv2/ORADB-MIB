--
-- This SMIv2 module has been generated by smidump 0.2-cvs. Do not edit.
--

ORADB-MIB DEFINITIONS ::= BEGIN

IMPORTS
    applIndex
        FROM APPLICATION-MIB
    rdbmsDbIndex
        FROM RDBMS-MIB
    Counter32, Integer32, OBJECT-TYPE, enterprises, experimental
        FROM SNMPv2-SMI
    DisplayString
        FROM SNMPv2-TC;

DateAndTime ::=
    OCTET STRING (SIZE(8..11))

TruthValue ::=
    INTEGER { true(1), false(2) }

oracle OBJECT IDENTIFIER
    ::= { enterprises 111 }

oraDbMIB OBJECT IDENTIFIER
    ::= { oracle 4 }

oraDbObjects OBJECT IDENTIFIER
    ::= { oraDbMIB 1 }

oraDbSysTable OBJECT-TYPE
    SYNTAX          SEQUENCE OF OraDbSysEntry
    MAX-ACCESS      not-accessible
    STATUS          current
    DESCRIPTION     
            "Oracle-specific performance information global to a database."
    ::= { oraDbObjects 1 }

oraDbSysEntry OBJECT-TYPE
    SYNTAX          OraDbSysEntry
    MAX-ACCESS      not-accessible
    STATUS          current
    DESCRIPTION     
            "Selected info from the v$sysstat table on instance performance.
             Variables are included here
             because they have been found particularly useful in 
             tuning an Oracle instance.  In many cases, the variable should
             only be considered in conjunction with other variables, often
             as a ratio.  Frequently, hints on these are given in the 
             descriptions, but Oracle tuning documentation should always
             be consulted, particularly the Oracle University course on 
             tuning V7 applications."
    INDEX           { applIndex }
    ::= { oraDbSysTable 1 }

OraDbSysEntry ::=
    SEQUENCE {
        oraDbSysConsistentChanges       Counter32,
        oraDbSysConsistentGets          Counter32,
        oraDbSysDbBlockChanges          Counter32,
        oraDbSysDbBlockGets             Counter32,
        oraDbSysFreeBufferInspected     Counter32,
        oraDbSysFreeBufferRequested     Counter32,
        oraDbSysParseCount              Counter32,
        oraDbSysPhysReads               Counter32,
        oraDbSysPhysWrites              Counter32,
        oraDbSysRedoEntries             Counter32,
        oraDbSysRedoLogSpaceRequests    Counter32,
        oraDbSysRedoSyncWrites          Counter32,
        oraDbSysSortsDisk               Counter32,
        oraDbSysSortsMemory             Counter32,
        oraDbSysSortsRows               Counter32,
        oraDbSysTableFetchRowid         Counter32,
        oraDbSysTableFetchContinuedRow  Counter32,
        oraDbSysTableScanBlocks         Counter32,
        oraDbSysTableScanRows           Counter32,
        oraDbSysTableScansLong          Counter32,
        oraDbSysTableScansShort         Counter32,
        oraDbSysUserCalls               Counter32,
        oraDbSysUserCommits             Counter32,
        oraDbSysUserRollbacks           Counter32,
        oraDbSysWriteRequests           Counter32
    }

oraDbSysConsistentChanges OBJECT-TYPE
    SYNTAX          Counter32
    MAX-ACCESS      read-only
    STATUS          current
    DESCRIPTION     
            "the 'consistent changes' parameter from v$sysstat"
    ::= { oraDbSysEntry 1 }

oraDbSysConsistentGets OBJECT-TYPE
    SYNTAX          Counter32
    MAX-ACCESS      read-only
    STATUS          current
    DESCRIPTION     
            "the 'consistent gets' parameter from v$sysstat"
    ::= { oraDbSysEntry 2 }

oraDbSysDbBlockChanges OBJECT-TYPE
    SYNTAX          Counter32
    MAX-ACCESS      read-only
    STATUS          current
    DESCRIPTION     
            "the 'Db block changes' parameter from v$sysstat"
    ::= { oraDbSysEntry 3 }

oraDbSysDbBlockGets OBJECT-TYPE
    SYNTAX          Counter32
    MAX-ACCESS      read-only
    STATUS          current
    DESCRIPTION     
            "the 'db block gets' parameter from v$sysstat"
    ::= { oraDbSysEntry 4 }

oraDbSysFreeBufferInspected OBJECT-TYPE
    SYNTAX          Counter32
    MAX-ACCESS      read-only
    STATUS          current
    DESCRIPTION     
            "the 'free buffer inspected' parameter from v$sysstat"
    ::= { oraDbSysEntry 5 }

oraDbSysFreeBufferRequested OBJECT-TYPE
    SYNTAX          Counter32
    MAX-ACCESS      read-only
    STATUS          current
    DESCRIPTION     
            "the 'free buffer requested' parameter from v$sysstat"
    ::= { oraDbSysEntry 6 }

oraDbSysParseCount OBJECT-TYPE
    SYNTAX          Counter32
    MAX-ACCESS      read-only
    STATUS          current
    DESCRIPTION     
            "the 'parse count' parameter from v$sysstat"
    ::= { oraDbSysEntry 7 }

oraDbSysPhysReads OBJECT-TYPE
    SYNTAX          Counter32
    MAX-ACCESS      read-only
    STATUS          current
    DESCRIPTION     
            "the 'physical reads' parameter from v$sysstat"
    ::= { oraDbSysEntry 8 }

oraDbSysPhysWrites OBJECT-TYPE
    SYNTAX          Counter32
    MAX-ACCESS      read-only
    STATUS          current
    DESCRIPTION     
            "the 'physical writes' parameter from v$sysstat"
    ::= { oraDbSysEntry 9 }

oraDbSysRedoEntries OBJECT-TYPE
    SYNTAX          Counter32
    MAX-ACCESS      read-only
    STATUS          current
    DESCRIPTION     
            "the 'redo entries' parameter from v$sysstat"
    ::= { oraDbSysEntry 10 }

oraDbSysRedoLogSpaceRequests OBJECT-TYPE
    SYNTAX          Counter32
    MAX-ACCESS      read-only
    STATUS          current
    DESCRIPTION     
            "the 'redo log space requests' parameter from v$sysstat"
    ::= { oraDbSysEntry 11 }

oraDbSysRedoSyncWrites OBJECT-TYPE
    SYNTAX          Counter32
    MAX-ACCESS      read-only
    STATUS          current
    DESCRIPTION     
            "the 'redo synch writes' parameter from v$sysstat"
    ::= { oraDbSysEntry 12 }

oraDbSysSortsDisk OBJECT-TYPE
    SYNTAX          Counter32
    MAX-ACCESS      read-only
    STATUS          current
    DESCRIPTION     
            "the 'sorts (disk)' parameter from v$sysstat"
    ::= { oraDbSysEntry 13 }

oraDbSysSortsMemory OBJECT-TYPE
    SYNTAX          Counter32
    MAX-ACCESS      read-only
    STATUS          current
    DESCRIPTION     
            "the 'sorts (memory)' parameter from v$sysstat"
    ::= { oraDbSysEntry 14 }

oraDbSysSortsRows OBJECT-TYPE
    SYNTAX          Counter32
    MAX-ACCESS      read-only
    STATUS          current
    DESCRIPTION     
            "the 'sorts (rows)' parameter from v$sysstat"
    ::= { oraDbSysEntry 15 }

oraDbSysTableFetchRowid OBJECT-TYPE
    SYNTAX          Counter32
    MAX-ACCESS      read-only
    STATUS          current
    DESCRIPTION     
            "the 'table fetch by rowid' parameter from v$sysstat"
    ::= { oraDbSysEntry 16 }

oraDbSysTableFetchContinuedRow OBJECT-TYPE
    SYNTAX          Counter32
    MAX-ACCESS      read-only
    STATUS          current
    DESCRIPTION     
            "the 'table fetch continued row' parameter from v$sysstat"
    ::= { oraDbSysEntry 17 }

oraDbSysTableScanBlocks OBJECT-TYPE
    SYNTAX          Counter32
    MAX-ACCESS      read-only
    STATUS          current
    DESCRIPTION     
            "the 'table scan blocks gotten' parameter from v$sysstat"
    ::= { oraDbSysEntry 18 }

oraDbSysTableScanRows OBJECT-TYPE
    SYNTAX          Counter32
    MAX-ACCESS      read-only
    STATUS          current
    DESCRIPTION     
            "the 'table scan rows gotten' parameter from v$sysstat"
    ::= { oraDbSysEntry 19 }

oraDbSysTableScansLong OBJECT-TYPE
    SYNTAX          Counter32
    MAX-ACCESS      read-only
    STATUS          current
    DESCRIPTION     
            "the 'table scans (long tables)' parameter from v$sysstat"
    ::= { oraDbSysEntry 20 }

oraDbSysTableScansShort OBJECT-TYPE
    SYNTAX          Counter32
    MAX-ACCESS      read-only
    STATUS          current
    DESCRIPTION     
            "the 'table scans (short tables)' parameter from v$sysstat"
    ::= { oraDbSysEntry 21 }

oraDbSysUserCalls OBJECT-TYPE
    SYNTAX          Counter32
    MAX-ACCESS      read-only
    STATUS          current
    DESCRIPTION     
            "the 'user calls' parameter from v$sysstat"
    ::= { oraDbSysEntry 22 }

oraDbSysUserCommits OBJECT-TYPE
    SYNTAX          Counter32
    MAX-ACCESS      read-only
    STATUS          current
    DESCRIPTION     
            "the 'user commits' parameter from v$sysstat"
    ::= { oraDbSysEntry 23 }

oraDbSysUserRollbacks OBJECT-TYPE
    SYNTAX          Counter32
    MAX-ACCESS      read-only
    STATUS          current
    DESCRIPTION     
            "the 'user rollbacks' parameter from v$sysstat"
    ::= { oraDbSysEntry 24 }

oraDbSysWriteRequests OBJECT-TYPE
    SYNTAX          Counter32
    MAX-ACCESS      read-only
    STATUS          current
    DESCRIPTION     
            "the 'write requests' parameter from v$sysstat"
    ::= { oraDbSysEntry 25 }

oraDbTablespaceTable OBJECT-TYPE
    SYNTAX          SEQUENCE OF OraDbTablespaceEntry
    MAX-ACCESS      not-accessible
    STATUS          current
    DESCRIPTION     
            "Information on tablespaces within an Oracle database."
    ::= { oraDbObjects 2 }

oraDbTablespaceEntry OBJECT-TYPE
    SYNTAX          OraDbTablespaceEntry
    MAX-ACCESS      not-accessible
    STATUS          current
    DESCRIPTION     
            "Information for each tablespace within an Oracle database."
    INDEX           { rdbmsDbIndex, oraDbTablespaceIndex }
    ::= { oraDbTablespaceTable 1 }

OraDbTablespaceEntry ::=
    SEQUENCE {
        oraDbTablespaceIndex            Integer32,
        oraDbTablespaceName             DisplayString,
        oraDbTablespaceSizeAllocated    Integer32,
        oraDbTablespaceSizeUsed         Integer32,
        oraDbTablespaceState            INTEGER,
        oraDbTablespaceLargestAvailableChunk    Integer32
    }

oraDbTablespaceIndex OBJECT-TYPE
    SYNTAX          Integer32
    MAX-ACCESS      read-only
    STATUS          current
    DESCRIPTION     
            "A numeric index, unique among tablespaces within a single
             Oracle database."
    ::= { oraDbTablespaceEntry 1 }

oraDbTablespaceName OBJECT-TYPE
    SYNTAX          DisplayString
    MAX-ACCESS      read-only
    STATUS          current
    DESCRIPTION     
            "The name of this tablespace."
    ::= { oraDbTablespaceEntry 2 }

oraDbTablespaceSizeAllocated OBJECT-TYPE
    SYNTAX          Integer32 (-2147483648..2147483647)
    MAX-ACCESS      read-only
    STATUS          current
    DESCRIPTION     
            "The amount of disk space, in kilobytes, allocated for this
             tablespace.  This is the sum of the sizes of the data files
             associated with the tablespace."
    ::= { oraDbTablespaceEntry 3 }

oraDbTablespaceSizeUsed OBJECT-TYPE
    SYNTAX          Integer32 (-2147483648..2147483647)
    MAX-ACCESS      read-only
    STATUS          current
    DESCRIPTION     
            "The amount of disk space, in kilobytes, which is actually in
             use for storing data."
    ::= { oraDbTablespaceEntry 4 }

oraDbTablespaceState OBJECT-TYPE
    SYNTAX          INTEGER { online(1), offline(2), invalid(3) }
    MAX-ACCESS      read-only
    STATUS          current
    DESCRIPTION     
            "The current accessibility of this tablespace.  If a
             tablespace is offline(2), then SQL statements cannot
             reference objects contained in the tablespace.  An invalid(3)
             tablespace is one that has been dropped."
    ::= { oraDbTablespaceEntry 5 }

oraDbTablespaceLargestAvailableChunk OBJECT-TYPE
    SYNTAX          Integer32 (-2147483648..2147483647)
    MAX-ACCESS      read-only
    STATUS          current
    DESCRIPTION     
            "The size, in kilobytes, of the largest contiguous set of free
             data blocks in the tablespace."
    ::= { oraDbTablespaceEntry 6 }

oraDbDataFileTable OBJECT-TYPE
    SYNTAX          SEQUENCE OF OraDbDataFileEntry
    MAX-ACCESS      not-accessible
    STATUS          current
    DESCRIPTION     
            "Information on data files within an Oracle database."
    ::= { oraDbObjects 3 }

oraDbDataFileEntry OBJECT-TYPE
    SYNTAX          OraDbDataFileEntry
    MAX-ACCESS      not-accessible
    STATUS          current
    DESCRIPTION     
            "Information for each data file within an Oracle database."
    INDEX           { rdbmsDbIndex, oraDbDataFileIndex }
    ::= { oraDbDataFileTable 1 }

OraDbDataFileEntry ::=
    SEQUENCE {
        oraDbDataFileIndex              Integer32,
        oraDbDataFileName               DisplayString,
        oraDbDataFileSizeAllocated      Integer32,
        oraDbDataFileDiskReads          Counter32,
        oraDbDataFileDiskWrites         Counter32,
        oraDbDataFileDiskReadBlocks     Counter32,
        oraDbDataFileDiskWrittenBlocks  Counter32,
        oraDbDataFileDiskReadTimeTicks  Counter32,
        oraDbDataFileDiskWriteTimeTicks Counter32
    }

oraDbDataFileIndex OBJECT-TYPE
    SYNTAX          Integer32
    MAX-ACCESS      read-only
    STATUS          current
    DESCRIPTION     
            "A numeric index, unique among data files associated with a
             single tablespace."
    ::= { oraDbDataFileEntry 1 }

oraDbDataFileName OBJECT-TYPE
    SYNTAX          DisplayString
    MAX-ACCESS      read-only
    STATUS          current
    DESCRIPTION     
            "The fully-qualified name of this datafile."
    ::= { oraDbDataFileEntry 2 }

oraDbDataFileSizeAllocated OBJECT-TYPE
    SYNTAX          Integer32 (-2147483648..2147483647)
    MAX-ACCESS      read-only
    STATUS          current
    DESCRIPTION     
            "The allocated size, in kilobytes, of this data file."
    ::= { oraDbDataFileEntry 3 }

oraDbDataFileDiskReads OBJECT-TYPE
    SYNTAX          Counter32
    MAX-ACCESS      read-only
    STATUS          current
    DESCRIPTION     
            "The total number of reads issued against this data file since
             startup."
    ::= { oraDbDataFileEntry 4 }

oraDbDataFileDiskWrites OBJECT-TYPE
    SYNTAX          Counter32
    MAX-ACCESS      read-only
    STATUS          current
    DESCRIPTION     
            "The total number of writes issued against this data file since
             startup."
    ::= { oraDbDataFileEntry 5 }

oraDbDataFileDiskReadBlocks OBJECT-TYPE
    SYNTAX          Counter32
    MAX-ACCESS      read-only
    STATUS          current
    DESCRIPTION     
            "The total number of physical blocks read from this data file
             since startup."
    ::= { oraDbDataFileEntry 6 }

oraDbDataFileDiskWrittenBlocks OBJECT-TYPE
    SYNTAX          Counter32
    MAX-ACCESS      read-only
    STATUS          current
    DESCRIPTION     
            "The total number of physical blocks written to this data file
             since startup."
    ::= { oraDbDataFileEntry 7 }

oraDbDataFileDiskReadTimeTicks OBJECT-TYPE
    SYNTAX          Counter32
    MAX-ACCESS      read-only
    STATUS          current
    DESCRIPTION     
            "The time spent reading from this data file since startup IF
             the database parameter TIMED_STATISTICS is TRUE.  If
             TIMED_STATISTICS is FALSE, then the value will be zero."
    ::= { oraDbDataFileEntry 8 }

oraDbDataFileDiskWriteTimeTicks OBJECT-TYPE
    SYNTAX          Counter32
    MAX-ACCESS      read-only
    STATUS          current
    DESCRIPTION     
            "The time spent writing to this data file since startup IF
             the database parameter TIMED_STATISTICS is TRUE.  If
             TIMED_STATISTICS is FALSE, then the value will be zero."
    ::= { oraDbDataFileEntry 9 }

oraDbLibraryCacheTable OBJECT-TYPE
    SYNTAX          SEQUENCE OF OraDbLibraryCacheEntry
    MAX-ACCESS      not-accessible
    STATUS          current
    DESCRIPTION     
            "Information on libraryCache performance."
    ::= { oraDbObjects 4 }

oraDbLibraryCacheEntry OBJECT-TYPE
    SYNTAX          OraDbLibraryCacheEntry
    MAX-ACCESS      not-accessible
    STATUS          current
    DESCRIPTION     
            "LibraryCache information for each Oracle database."
    INDEX           { applIndex, oraDbLibraryCacheIndex }
    ::= { oraDbLibraryCacheTable 1 }

OraDbLibraryCacheEntry ::=
    SEQUENCE {
        oraDbLibraryCacheIndex          Integer32,
        oraDbLibraryCacheNameSpace      DisplayString,
        oraDbLibraryCacheGets           Counter32,
        oraDbLibraryCacheGetHits        Counter32,
        oraDbLibraryCachePins           Counter32,
        oraDbLibraryCachePinHits        Counter32,
        oraDbLibraryCacheReloads        Counter32,
        oraDbLibraryCacheInvalidations  Counter32
    }

oraDbLibraryCacheIndex OBJECT-TYPE
    SYNTAX          Integer32
    MAX-ACCESS      read-only
    STATUS          current
    DESCRIPTION     
            "A unique integer for each row of the table."
    ::= { oraDbLibraryCacheEntry 1 }

oraDbLibraryCacheNameSpace OBJECT-TYPE
    SYNTAX          DisplayString
    MAX-ACCESS      read-only
    STATUS          current
    DESCRIPTION     
            "The namespace of the v$librarycache table that this
             row relates to."
    ::= { oraDbLibraryCacheEntry 2 }

oraDbLibraryCacheGets OBJECT-TYPE
    SYNTAX          Counter32
    MAX-ACCESS      read-only
    STATUS          current
    DESCRIPTION     
            "Number of times the system requests handles to library
             objects in this namespace."
    ::= { oraDbLibraryCacheEntry 3 }

oraDbLibraryCacheGetHits OBJECT-TYPE
    SYNTAX          Counter32
    MAX-ACCESS      read-only
    STATUS          current
    DESCRIPTION     
            "Number of times the handles are already allocated in 
             the cache."
    ::= { oraDbLibraryCacheEntry 4 }

oraDbLibraryCachePins OBJECT-TYPE
    SYNTAX          Counter32
    MAX-ACCESS      read-only
    STATUS          current
    DESCRIPTION     
            "Number of times the system issues pin requests
             for objects in the cache in order to access them."
    ::= { oraDbLibraryCacheEntry 5 }

oraDbLibraryCachePinHits OBJECT-TYPE
    SYNTAX          Counter32
    MAX-ACCESS      read-only
    STATUS          current
    DESCRIPTION     
            "Number of times the objects the system is pinning
             are already allocated and initialized in the cache."
    ::= { oraDbLibraryCacheEntry 6 }

oraDbLibraryCacheReloads OBJECT-TYPE
    SYNTAX          Counter32
    MAX-ACCESS      read-only
    STATUS          current
    DESCRIPTION     
            "Number of times the library objects have to be reinitialized
             and reloaded with data because they have been aged out or
             invalidated"
    ::= { oraDbLibraryCacheEntry 7 }

oraDbLibraryCacheInvalidations OBJECT-TYPE
    SYNTAX          Counter32
    MAX-ACCESS      read-only
    STATUS          current
    DESCRIPTION     
            "Number of times that non-persistent library objects
             (like shared SQL areas) have been invalidated."
    ::= { oraDbLibraryCacheEntry 8 }

oraDbLibraryCacheSumTable OBJECT-TYPE
    SYNTAX          SEQUENCE OF OraDbLibraryCacheSumEntry
    MAX-ACCESS      not-accessible
    STATUS          current
    DESCRIPTION     
            "Information on library cache performance, summed over all
             library caches in a single database instance."
    ::= { oraDbObjects 5 }

oraDbLibraryCacheSumEntry OBJECT-TYPE
    SYNTAX          OraDbLibraryCacheSumEntry
    MAX-ACCESS      not-accessible
    STATUS          current
    DESCRIPTION     
            "LibraryCache information, summed over all library caches,
             for each Oracle database."
    INDEX           { applIndex }
    ::= { oraDbLibraryCacheSumTable 1 }

OraDbLibraryCacheSumEntry ::=
    SEQUENCE {
        oraDbLibraryCacheSumGets        Counter32,
        oraDbLibraryCacheSumGetHits     Counter32,
        oraDbLibraryCacheSumPins        Counter32,
        oraDbLibraryCacheSumPinHits     Counter32,
        oraDbLibraryCacheSumReloads     Counter32,
        oraDbLibraryCacheSumInvalidations Counter32
    }

oraDbLibraryCacheSumGets OBJECT-TYPE
    SYNTAX          Counter32
    MAX-ACCESS      read-only
    STATUS          current
    DESCRIPTION     
            "Number of times the system requests handles to library
             objects, summed over all library caches in the instance."
    ::= { oraDbLibraryCacheSumEntry 1 }

oraDbLibraryCacheSumGetHits OBJECT-TYPE
    SYNTAX          Counter32
    MAX-ACCESS      read-only
    STATUS          current
    DESCRIPTION     
            "Number of times the handles are already allocated in 
             the cache, summed over all library caches in the instance."
    ::= { oraDbLibraryCacheSumEntry 2 }

oraDbLibraryCacheSumPins OBJECT-TYPE
    SYNTAX          Counter32
    MAX-ACCESS      read-only
    STATUS          current
    DESCRIPTION     
            "Number of times the system issues pin requests
             for objects in a cache in order to access them,
             summed over all library caches in the instance."
    ::= { oraDbLibraryCacheSumEntry 3 }

oraDbLibraryCacheSumPinHits OBJECT-TYPE
    SYNTAX          Counter32
    MAX-ACCESS      read-only
    STATUS          current
    DESCRIPTION     
            "Number of times the objects the system is pinning
             are already allocated and initialized in a cache,
             summed over all library caches in the instance."
    ::= { oraDbLibraryCacheSumEntry 4 }

oraDbLibraryCacheSumReloads OBJECT-TYPE
    SYNTAX          Counter32
    MAX-ACCESS      read-only
    STATUS          current
    DESCRIPTION     
            "Number of times the library objects have to be reinitialized
             and reloaded with data because they have been aged out or
             invalidated, summed over all library caches in the instance."
    ::= { oraDbLibraryCacheSumEntry 5 }

oraDbLibraryCacheSumInvalidations OBJECT-TYPE
    SYNTAX          Counter32
    MAX-ACCESS      read-only
    STATUS          current
    DESCRIPTION     
            "Number of times that non-persistent library objects
             (like shared SQL areas) have been invalidated, summed over
             all library caches in the instance."
    ::= { oraDbLibraryCacheSumEntry 6 }

oraDbSGATable OBJECT-TYPE
    SYNTAX          SEQUENCE OF OraDbSGAEntry
    MAX-ACCESS      not-accessible
    STATUS          current
    DESCRIPTION     
            "Summary information on the System Global Area"
    ::= { oraDbObjects 6 }

oraDbSGAEntry OBJECT-TYPE
    SYNTAX          OraDbSGAEntry
    MAX-ACCESS      not-accessible
    STATUS          current
    DESCRIPTION     
            "A single entry from the v$sga table"
    INDEX           { applIndex }
    ::= { oraDbSGATable 1 }

OraDbSGAEntry ::=
    SEQUENCE {
        oraDbSGAFixedSize               Integer32,
        oraDbSGAVariableSize            Integer32,
        oraDbSGADatabaseBuffers         Integer32,
        oraDbSGARedoBuffers             Integer32
    }

oraDbSGAFixedSize OBJECT-TYPE
    SYNTAX          Integer32
    MAX-ACCESS      read-only
    STATUS          current
    DESCRIPTION     
            ""
    ::= { oraDbSGAEntry 1 }

oraDbSGAVariableSize OBJECT-TYPE
    SYNTAX          Integer32
    MAX-ACCESS      read-only
    STATUS          current
    DESCRIPTION     
            ""
    ::= { oraDbSGAEntry 2 }

oraDbSGADatabaseBuffers OBJECT-TYPE
    SYNTAX          Integer32
    MAX-ACCESS      read-only
    STATUS          current
    DESCRIPTION     
            ""
    ::= { oraDbSGAEntry 3 }

oraDbSGARedoBuffers OBJECT-TYPE
    SYNTAX          Integer32
    MAX-ACCESS      read-only
    STATUS          current
    DESCRIPTION     
            ""
    ::= { oraDbSGAEntry 4 }

oraDbConfigTable OBJECT-TYPE
    SYNTAX          SEQUENCE OF OraDbConfigEntry
    MAX-ACCESS      not-accessible
    STATUS          current
    DESCRIPTION     
            "Oracle-specific configuration information global to a database."
    ::= { oraDbObjects 7 }

oraDbConfigEntry OBJECT-TYPE
    SYNTAX          OraDbConfigEntry
    MAX-ACCESS      not-accessible
    STATUS          current
    DESCRIPTION     
            "Oracle-specific configuration information.  This table only
             lists a few init.ora parameters that are particularly
             relevant to the task of monitoring database performance.  By
             giving them easy-to-use, fixed object-ids, we make it easier
             to graph them along with the dynamic performance values that
             they affect.  A complete list of parameters can be found in
             the Internet standard MIB 'rdbmsSrvParam' objects."
    INDEX           { applIndex }
    ::= { oraDbConfigTable 1 }

OraDbConfigEntry ::=
    SEQUENCE {
        oraDbConfigDbBlockBuffers       Integer32,
        oraDbConfigDbBlockCkptBatch     Integer32,
        oraDbConfigDbBlockSize          Integer32,
        oraDbConfigDbFileSimWrites      Integer32,
        oraDbConfigDbMultiBlockReadCount Integer32,
        oraDbConfigDistLockTimeout      Integer32,
        oraDbConfigDistRecoveryConnectHold  Integer32,
        oraDbConfigDistTransactions     Integer32,
        oraDbConfigLogArchiveBufferSize Integer32,
        oraDbConfigLogArchiveBuffers    Integer32,
        oraDbConfigLogBuffer            Integer32,
        oraDbConfigLogCheckpointInterval Integer32,
        oraDbConfigLogCheckpointTimeout Integer32,
        oraDbConfigLogFiles             Integer32,
        oraDbConfigMaxRollbackSegments  Integer32,
        oraDbConfigMTSMaxDispatchers    Integer32,
        oraDbConfigMTSMaxServers        Integer32,
        oraDbConfigMTSServers           Integer32,
        oraDbConfigOpenCursors          Integer32,
        oraDbConfigOpenLinks            Integer32,
        oraDbConfigOptimizerMode        DisplayString,
        oraDbConfigProcesses            Integer32,
        oraDbConfigSerializable         TruthValue,
        oraDbConfigSessions             Integer32,
        oraDbConfigSharedPool           Integer32,
        oraDbConfigSortAreaSize         Integer32,
        oraDbConfigSortAreaRetainedSize Integer32,
        oraDbConfigTransactions         Integer32,
        oraDbConfigTransactionsPerRollback  Integer32
    }

oraDbConfigDbBlockBuffers OBJECT-TYPE
    SYNTAX          Integer32
    MAX-ACCESS      read-only
    STATUS          current
    DESCRIPTION     
            "The DB_BLOCK_BUFFERS parameter from the init.ora file "
    ::= { oraDbConfigEntry 1 }

oraDbConfigDbBlockCkptBatch OBJECT-TYPE
    SYNTAX          Integer32
    MAX-ACCESS      read-only
    STATUS          current
    DESCRIPTION     
            "The DB_BLOCK_CHECKPOINT_BATCH  parameter from the init.ora file "
    ::= { oraDbConfigEntry 2 }

oraDbConfigDbBlockSize OBJECT-TYPE
    SYNTAX          Integer32
    MAX-ACCESS      read-only
    STATUS          current
    DESCRIPTION     
            "The DB_BLOCK_SIZE parameter from the init.ora file "
    ::= { oraDbConfigEntry 3 }

oraDbConfigDbFileSimWrites OBJECT-TYPE
    SYNTAX          Integer32
    MAX-ACCESS      read-only
    STATUS          current
    DESCRIPTION     
            "The DB_FILE_SIMULTANEOUS_WRITES parameter from the init.ora file "
    ::= { oraDbConfigEntry 4 }

oraDbConfigDbMultiBlockReadCount OBJECT-TYPE
    SYNTAX          Integer32
    MAX-ACCESS      read-only
    STATUS          current
    DESCRIPTION     
            "The DB_MULTIBLOCK_READ_COUNT  parameter from the init.ora file "
    ::= { oraDbConfigEntry 5 }

oraDbConfigDistLockTimeout OBJECT-TYPE
    SYNTAX          Integer32
    MAX-ACCESS      read-only
    STATUS          current
    DESCRIPTION     
            "The DISTRIBUTED_LOCK_TIMEOUT parameter from the init.ora file "
    ::= { oraDbConfigEntry 6 }

oraDbConfigDistRecoveryConnectHold OBJECT-TYPE
    SYNTAX          Integer32
    MAX-ACCESS      read-only
    STATUS          current
    DESCRIPTION     
            "The DISTRIBUTED_RECOVERY_CONNECT_HOLD parameter from the
             init.ora file "
    ::= { oraDbConfigEntry 7 }

oraDbConfigDistTransactions OBJECT-TYPE
    SYNTAX          Integer32
    MAX-ACCESS      read-only
    STATUS          current
    DESCRIPTION     
            "The DISTRIBUTED_TRANSACTIONS  parameter from the init.ora file "
    ::= { oraDbConfigEntry 8 }

oraDbConfigLogArchiveBufferSize OBJECT-TYPE
    SYNTAX          Integer32
    MAX-ACCESS      read-only
    STATUS          current
    DESCRIPTION     
            "The LOG_ARCHIVE_BUFFER_SIZE parameter from the init.ora file "
    ::= { oraDbConfigEntry 9 }

oraDbConfigLogArchiveBuffers OBJECT-TYPE
    SYNTAX          Integer32
    MAX-ACCESS      read-only
    STATUS          current
    DESCRIPTION     
            "The LOG_ARCHIVE_BUFFERS parameter from the init.ora file "
    ::= { oraDbConfigEntry 10 }

oraDbConfigLogBuffer OBJECT-TYPE
    SYNTAX          Integer32
    MAX-ACCESS      read-only
    STATUS          current
    DESCRIPTION     
            "The LOG_BUFFER parameter from the init.ora file "
    ::= { oraDbConfigEntry 11 }

oraDbConfigLogCheckpointInterval OBJECT-TYPE
    SYNTAX          Integer32
    MAX-ACCESS      read-only
    STATUS          current
    DESCRIPTION     
            "The LOG_CHECKPOINT_INTERVAL parameter from the init.ora file "
    ::= { oraDbConfigEntry 12 }

oraDbConfigLogCheckpointTimeout OBJECT-TYPE
    SYNTAX          Integer32
    MAX-ACCESS      read-only
    STATUS          current
    DESCRIPTION     
            "The LOG_CHECKPOINT_TIMEOUT parameter from the init.ora file "
    ::= { oraDbConfigEntry 13 }

oraDbConfigLogFiles OBJECT-TYPE
    SYNTAX          Integer32
    MAX-ACCESS      read-only
    STATUS          current
    DESCRIPTION     
            "The LOG_FILES parameter from the init.ora file "
    ::= { oraDbConfigEntry 14 }

oraDbConfigMaxRollbackSegments OBJECT-TYPE
    SYNTAX          Integer32
    MAX-ACCESS      read-only
    STATUS          current
    DESCRIPTION     
            "The MAX_ROLLBACK_SEGMENTS parameter from the init.ora file "
    ::= { oraDbConfigEntry 15 }

oraDbConfigMTSMaxDispatchers OBJECT-TYPE
    SYNTAX          Integer32
    MAX-ACCESS      read-only
    STATUS          current
    DESCRIPTION     
            "The MTS_MAX_DISPATCHERS parameter from the init.ora file "
    ::= { oraDbConfigEntry 16 }

oraDbConfigMTSMaxServers OBJECT-TYPE
    SYNTAX          Integer32
    MAX-ACCESS      read-only
    STATUS          current
    DESCRIPTION     
            "The MTS_MAX_SERVERS  parameter from the init.ora file "
    ::= { oraDbConfigEntry 17 }

oraDbConfigMTSServers OBJECT-TYPE
    SYNTAX          Integer32
    MAX-ACCESS      read-only
    STATUS          current
    DESCRIPTION     
            "The MTS_SERVERS  parameter from the init.ora file "
    ::= { oraDbConfigEntry 18 }

oraDbConfigOpenCursors OBJECT-TYPE
    SYNTAX          Integer32
    MAX-ACCESS      read-only
    STATUS          current
    DESCRIPTION     
            "The OPEN_CURSORS parameter from the init.ora file "
    ::= { oraDbConfigEntry 19 }

oraDbConfigOpenLinks OBJECT-TYPE
    SYNTAX          Integer32
    MAX-ACCESS      read-only
    STATUS          current
    DESCRIPTION     
            "The OPEN_LINKS parameter from the init.ora file "
    ::= { oraDbConfigEntry 20 }

oraDbConfigOptimizerMode OBJECT-TYPE
    SYNTAX          DisplayString
    MAX-ACCESS      read-only
    STATUS          current
    DESCRIPTION     
            "The  OPTIMIZER_MODE parameter from the init.ora file "
    ::= { oraDbConfigEntry 21 }

oraDbConfigProcesses OBJECT-TYPE
    SYNTAX          Integer32
    MAX-ACCESS      read-only
    STATUS          current
    DESCRIPTION     
            "The PROCESSES parameter from the init.ora file "
    ::= { oraDbConfigEntry 22 }

oraDbConfigSerializable OBJECT-TYPE
    SYNTAX          TruthValue
    MAX-ACCESS      read-only
    STATUS          current
    DESCRIPTION     
            "The SERIALIZABLE parameter from the init.ora file "
    ::= { oraDbConfigEntry 23 }

oraDbConfigSessions OBJECT-TYPE
    SYNTAX          Integer32
    MAX-ACCESS      read-only
    STATUS          current
    DESCRIPTION     
            "The SESSIONS  parameter from the init.ora file "
    ::= { oraDbConfigEntry 24 }

oraDbConfigSharedPool OBJECT-TYPE
    SYNTAX          Integer32
    MAX-ACCESS      read-only
    STATUS          current
    DESCRIPTION     
            "The SHARED_POOL parameter from the init.ora file "
    ::= { oraDbConfigEntry 25 }

oraDbConfigSortAreaSize OBJECT-TYPE
    SYNTAX          Integer32
    MAX-ACCESS      read-only
    STATUS          current
    DESCRIPTION     
            "The SORT_AREA_SIZE parameter from the init.ora file "
    ::= { oraDbConfigEntry 26 }

oraDbConfigSortAreaRetainedSize OBJECT-TYPE
    SYNTAX          Integer32
    MAX-ACCESS      read-only
    STATUS          current
    DESCRIPTION     
            "The SORT_AREA_RETAINED_SIZE  parameter from the init.ora file "
    ::= { oraDbConfigEntry 27 }

oraDbConfigTransactions OBJECT-TYPE
    SYNTAX          Integer32
    MAX-ACCESS      read-only
    STATUS          current
    DESCRIPTION     
            "The TRANSACTIONS parameter from the init.ora file "
    ::= { oraDbConfigEntry 28 }

oraDbConfigTransactionsPerRollback OBJECT-TYPE
    SYNTAX          Integer32
    MAX-ACCESS      read-only
    STATUS          current
    DESCRIPTION     
            "The TRANSACTIONS_PER_ROLLBACK parameter from the init.ora file "
    ::= { oraDbConfigEntry 29 }

END -- end of module ORADB-MIB.
