--
-- This SMIv1 module has been generated by smidump 0.2-cvs. Do not edit.
--

SONUS-IP-ADDRESS-MIB DEFINITIONS ::= BEGIN

IMPORTS
    Ipv6Address
        FROM IPV6-TC
    OBJECT-TYPE
        FROM RFC-1212
    IpAddress
        FROM RFC1155-SMI
    PhysAddress
        FROM SNMPv2-TC
    sonusPacketMIBs
        FROM SONUS-SMI
    SonusShelfIndex, SonusSlotIndex
        FROM SONUS-TC;

sonusIpAddressMIB OBJECT IDENTIFIER
    ::= { sonusPacketMIBs 2 }

-- sonusIpAddressMIB MODULE-IDENTITY
--     LAST-UPDATED    "201008100000Z"
--     ORGANIZATION    
--             "Sonus Networks, Inc."
--     CONTACT-INFO    
--             "   Customer Support    
--              Sonus Networks, Inc.
--              7 Technology Park Drive
--              Westford, MA 01886
--              USA
--              
--              Tel: 978-614-8100
--              Fax: 978-614-8609"
--     DESCRIPTION     
--             "The MIB Module for IP Address Management."
--     ::= { sonusPacketMIBs 2 }


sonusIpAddrTable OBJECT-TYPE
    SYNTAX          SEQUENCE OF SonusIpAddrEntry
    ACCESS          not-accessible
    STATUS          mandatory
    DESCRIPTION     
            "The table of addressing information relevant to this
             entity's IP addresses."
    ::= { sonusIpAddressMIB 1 }

sonusIpAddrEntry OBJECT-TYPE
    SYNTAX          SonusIpAddrEntry
    ACCESS          not-accessible
    STATUS          mandatory
    DESCRIPTION     
            "The addressing information for one of this entity's IP
             addresses."
    INDEX           { sonusIpAdEntShelf, sonusIpAdEntSlot, 
                      sonusIpAdEntInstance, sonusIpAdEntAddr }
    ::= { sonusIpAddrTable 1 }

SonusIpAddrEntry ::=
    SEQUENCE {
        sonusIpAdEntAddr                IpAddress,
        sonusIpAdEntIfIndex             INTEGER,
        sonusIpAdEntNetMask             IpAddress,
        sonusIpAdEntBcastAddr           INTEGER,
        sonusIpAdEntReasmMaxSize        INTEGER,
        sonusIpAdEntShelf               SonusShelfIndex,
        sonusIpAdEntSlot                SonusSlotIndex,
        sonusIpAdEntInstance            INTEGER
    }

sonusIpAdEntAddr OBJECT-TYPE
    SYNTAX          IpAddress
    ACCESS          read-only
    STATUS          mandatory
    DESCRIPTION     
            "The IP address to which this entry's addressing information
             pertains."
    ::= { sonusIpAddrEntry 1 }

sonusIpAdEntIfIndex OBJECT-TYPE
    SYNTAX          INTEGER (1..2147483647)
    ACCESS          read-only
    STATUS          mandatory
    DESCRIPTION     
            "The index value which uniquely identifies the interface to
             which this entry is applicable.  The interface identified by
             a particular value of this index is the same interface as
             identified by the same value of RFC 1573's ifIndex."
    ::= { sonusIpAddrEntry 2 }

sonusIpAdEntNetMask OBJECT-TYPE
    SYNTAX          IpAddress
    ACCESS          read-only
    STATUS          mandatory
    DESCRIPTION     
            "The subnet mask associated with the IP address of this
             entry.  The value of the mask is an IP address with all the
             network bits set to 1 and all the hosts bits set to 0."
    ::= { sonusIpAddrEntry 3 }

sonusIpAdEntBcastAddr OBJECT-TYPE
    SYNTAX          INTEGER (0..1)
    ACCESS          read-only
    STATUS          mandatory
    DESCRIPTION     
            "The value of the least-significant bit in the IP broadcast
             address used for sending datagrams on the (logical)
             interface associated with the IP address of this entry.  For
             example, when the Internet standard all-ones broadcast
             address is used, the value will be 1.  This value applies to
             both the subnet and network broadcasts addresses used by the
             entity on this (logical) interface."
    ::= { sonusIpAddrEntry 4 }

sonusIpAdEntReasmMaxSize OBJECT-TYPE
    SYNTAX          INTEGER (0..65535)
    ACCESS          read-only
    STATUS          mandatory
    DESCRIPTION     
            "The size of the largest IP datagram which this entity can
             re-assemble from incoming IP fragmented datagrams received
             on this interface."
    ::= { sonusIpAddrEntry 5 }

sonusIpAdEntShelf OBJECT-TYPE
    SYNTAX          SonusShelfIndex
    ACCESS          read-only
    STATUS          mandatory
    DESCRIPTION     
            "A 32-bit integer identifying the shelf
             that the IP Addr table applies to"
    ::= { sonusIpAddrEntry 6 }

sonusIpAdEntSlot OBJECT-TYPE
    SYNTAX          SonusSlotIndex
    ACCESS          read-only
    STATUS          mandatory
    DESCRIPTION     
            "A 32-bit integer identifying the slot
             that the IP Addr table applies to"
    ::= { sonusIpAddrEntry 7 }

sonusIpAdEntInstance OBJECT-TYPE
    SYNTAX          INTEGER
    ACCESS          read-only
    STATUS          mandatory
    DESCRIPTION     
            "A 32-bit integer identifying the instance
             that the IP Addr table applies to"
    ::= { sonusIpAddrEntry 8 }

sonusIpNetToMediaTable OBJECT-TYPE
    SYNTAX          SEQUENCE OF SonusIpNetToMediaEntry
    ACCESS          not-accessible
    STATUS          mandatory
    DESCRIPTION     
            "The IP Address Translation table used for mapping from IP
             addresses to physical addresses."
    ::= { sonusIpAddressMIB 2 }

sonusIpNetToMediaEntry OBJECT-TYPE
    SYNTAX          SonusIpNetToMediaEntry
    ACCESS          not-accessible
    STATUS          mandatory
    DESCRIPTION     
            "Each entry contains one IpAddress to `physical' address
             equivalence."
    INDEX           { sonusIpNetToMediaIpVersion, sonusIpNetToMediaShelf, 
                      sonusIpNetToMediaSlot, sonusIpNetToMediaInstance, 
                      sonusIpNetToMediaIfIndex, 
                      sonusIpNetToMediaNetAddress, 
                      sonusIpNetToMediaNetAddress6 }
    ::= { sonusIpNetToMediaTable 1 }

SonusIpNetToMediaEntry ::=
    SEQUENCE {
        sonusIpNetToMediaIfIndex        INTEGER,
        sonusIpNetToMediaPhysAddress    PhysAddress,
        sonusIpNetToMediaNetAddress     IpAddress,
        sonusIpNetToMediaType           INTEGER,
        sonusIpNetToMediaShelf          SonusShelfIndex,
        sonusIpNetToMediaSlot           SonusSlotIndex,
        sonusIpNetToMediaInstance       INTEGER,
        sonusIpNetToMediaNetAddress6    Ipv6Address,
        sonusIpNetToMediaIpVersion      INTEGER
    }

sonusIpNetToMediaIfIndex OBJECT-TYPE
    SYNTAX          INTEGER (1..2147483647)
    ACCESS          read-only
    STATUS          mandatory
    DESCRIPTION     
            "The interface on which this entry's equivalence is
             effective.  The interface identified by a particular value
             of this index is the same interface as identified by the
             same value of RFC 1573's ifIndex."
    ::= { sonusIpNetToMediaEntry 1 }

sonusIpNetToMediaPhysAddress OBJECT-TYPE
    SYNTAX          PhysAddress
    ACCESS          read-write
    STATUS          mandatory
    DESCRIPTION     
            "The media-dependent `physical' address."
    ::= { sonusIpNetToMediaEntry 2 }

sonusIpNetToMediaNetAddress OBJECT-TYPE
    SYNTAX          IpAddress
    ACCESS          read-only
    STATUS          mandatory
    DESCRIPTION     
            "The IpAddress corresponding to the media-dependent
             `physical' address."
    ::= { sonusIpNetToMediaEntry 3 }

sonusIpNetToMediaType OBJECT-TYPE
    SYNTAX          INTEGER { other(1), invalid(2), dynamic(3), 
                        static(4) }
    ACCESS          read-write
    STATUS          mandatory
    DESCRIPTION     
            "The type of mapping.
             Setting this object to the value invalid(2) has the effect
             of invalidating the corresponding entry in the
             ipNetToMediaTable.  That is, it effectively disassociates
             the interface identified with said entry from the mapping
             identified with said entry.  It is an implementation-
             specific matter as to whether the agent removes an
             invalidated entry from the table.  Accordingly, management
             stations must be prepared to receive tabular information
             from agents that corresponds to entries not currently in
             use.  Proper interpretation of such entries requires
             examination of the relevant ipNetToMediaType object."
    ::= { sonusIpNetToMediaEntry 4 }

sonusIpNetToMediaShelf OBJECT-TYPE
    SYNTAX          SonusShelfIndex
    ACCESS          read-only
    STATUS          mandatory
    DESCRIPTION     
            "A 32-bit integer identifying the shelf
             that the IP Net to Media table applies to"
    ::= { sonusIpNetToMediaEntry 5 }

sonusIpNetToMediaSlot OBJECT-TYPE
    SYNTAX          SonusSlotIndex
    ACCESS          read-only
    STATUS          mandatory
    DESCRIPTION     
            "A 32-bit integer identifying the slot
             that the IP Net to Media table applies to"
    ::= { sonusIpNetToMediaEntry 6 }

sonusIpNetToMediaInstance OBJECT-TYPE
    SYNTAX          INTEGER
    ACCESS          read-only
    STATUS          mandatory
    DESCRIPTION     
            "A 32-bit integer identifying the instance
             that the IP Net to Media table applies to"
    ::= { sonusIpNetToMediaEntry 7 }

sonusIpNetToMediaNetAddress6 OBJECT-TYPE
    SYNTAX          Ipv6Address
    ACCESS          read-only
    STATUS          mandatory
    DESCRIPTION     
            "The IPv6 address corresponding to the media-dependent
             `physical' address."
    ::= { sonusIpNetToMediaEntry 8 }

sonusIpNetToMediaIpVersion OBJECT-TYPE
    SYNTAX          INTEGER { afInet(2), afInet6(24) }
    ACCESS          read-only
    STATUS          mandatory
    DESCRIPTION     
            "The local IP version for this UDP connection."
    ::= { sonusIpNetToMediaEntry 9 }

sonusPhyAddrTable OBJECT-TYPE
    SYNTAX          SEQUENCE OF SonusPhyAddrEntry
    ACCESS          not-accessible
    STATUS          mandatory
    DESCRIPTION     
            "The table of addressing information relevant to this
             entity's IP addresses."
    ::= { sonusIpAddressMIB 3 }

sonusPhyAddrEntry OBJECT-TYPE
    SYNTAX          SonusPhyAddrEntry
    ACCESS          not-accessible
    STATUS          mandatory
    DESCRIPTION     
            "The addressing information for one of this entity's
             physical addresses."
    INDEX           { sonusPhyAddrIfIndex, sonusPhyAddrIndex }
    ::= { sonusPhyAddrTable 1 }

SonusPhyAddrEntry ::=
    SEQUENCE {
        sonusPhyAddrIfIndex             INTEGER,
        sonusPhyAddrIndex               INTEGER,
        sonusPhyAddr                    PhysAddress
    }

sonusPhyAddrIfIndex OBJECT-TYPE
    SYNTAX          INTEGER (1..2147483647)
    ACCESS          read-only
    STATUS          mandatory
    DESCRIPTION     
            "The interface to which this physical address belongs.
             The interface identified by a particular value
             of this index is the same interface as identified by the
             same value of RFC 1573's ifIndex."
    ::= { sonusPhyAddrEntry 1 }

sonusPhyAddrIndex OBJECT-TYPE
    SYNTAX          INTEGER
    ACCESS          read-only
    STATUS          mandatory
    DESCRIPTION     
            "If more the interface identified by sonusPhyAddrIfIndex
             supports more than a single physical address this is an
             index of those supported physical addresses."
    ::= { sonusPhyAddrEntry 2 }

sonusPhyAddr OBJECT-TYPE
    SYNTAX          PhysAddress
    ACCESS          read-only
    STATUS          mandatory
    DESCRIPTION     
            "The media-dependent `physical' address."
    ::= { sonusPhyAddrEntry 3 }

END -- end of module SONUS-IP-ADDRESS-MIB.
