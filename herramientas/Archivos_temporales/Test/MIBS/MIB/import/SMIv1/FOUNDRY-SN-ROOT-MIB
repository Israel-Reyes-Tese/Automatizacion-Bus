--
-- This SMIv1 module has been generated by smidump 0.2-cvs. Do not edit.
--

FOUNDRY-SN-ROOT-MIB DEFINITIONS ::= BEGIN

IMPORTS
    enterprises
        FROM RFC1155-SMI;

foundry OBJECT IDENTIFIER
    ::= { enterprises 1991 }

products OBJECT IDENTIFIER
    ::= { foundry 1 }

switch OBJECT IDENTIFIER
    ::= { products 1 }

snChassis OBJECT IDENTIFIER
    ::= { switch 1 }

snAgentSys OBJECT IDENTIFIER
    ::= { switch 2 }

snSwitch OBJECT IDENTIFIER
    ::= { switch 3 }

snL4 OBJECT IDENTIFIER
    ::= { switch 4 }

snStack OBJECT IDENTIFIER
    ::= { switch 5 }

router OBJECT IDENTIFIER
    ::= { products 2 }

snIpx OBJECT IDENTIFIER
    ::= { router 1 }

snIp OBJECT IDENTIFIER
    ::= { router 2 }

snRip OBJECT IDENTIFIER
    ::= { router 3 }

snOspf OBJECT IDENTIFIER
    ::= { router 4 }

snDvmrp OBJECT IDENTIFIER
    ::= { router 5 }

snIgmp OBJECT IDENTIFIER
    ::= { router 6 }

snFsrp OBJECT IDENTIFIER
    ::= { router 7 }

snGblRt OBJECT IDENTIFIER
    ::= { router 8 }

snPim OBJECT IDENTIFIER
    ::= { router 9 }

snAppleTalk OBJECT IDENTIFIER
    ::= { router 10 }

snBgp4 OBJECT IDENTIFIER
    ::= { router 11 }

snVrrp OBJECT IDENTIFIER
    ::= { router 12 }

snLoopbackIf OBJECT IDENTIFIER
    ::= { router 13 }

snPOS OBJECT IDENTIFIER
    ::= { router 14 }

registration OBJECT IDENTIFIER
    ::= { products 3 }

snFastIron OBJECT IDENTIFIER
    ::= { registration 1 }

snFIWGSwitch OBJECT IDENTIFIER
    ::= { snFastIron 1 }

snFIBBSwitch OBJECT IDENTIFIER
    ::= { snFastIron 2 }

snNetIron OBJECT IDENTIFIER
    ::= { registration 2 }

snNIRouter OBJECT IDENTIFIER
    ::= { snNetIron 1 }

snServerIron OBJECT IDENTIFIER
    ::= { registration 3 }

snSI OBJECT IDENTIFIER
    ::= { snServerIron 1 }

snSIXL OBJECT IDENTIFIER
    ::= { snServerIron 2 }

snTurboIron OBJECT IDENTIFIER
    ::= { registration 4 }

snTISwitch OBJECT IDENTIFIER
    ::= { snTurboIron 1 }

snTIRouter OBJECT IDENTIFIER
    ::= { snTurboIron 2 }

snTurboIron8 OBJECT IDENTIFIER
    ::= { registration 5 }

snT8Switch OBJECT IDENTIFIER
    ::= { snTurboIron8 1 }

snT8Router OBJECT IDENTIFIER
    ::= { snTurboIron8 2 }

snT8SI OBJECT IDENTIFIER
    ::= { snTurboIron8 3 }

snT8SIXLG OBJECT IDENTIFIER
    ::= { snTurboIron8 4 }

snBigIron4000 OBJECT IDENTIFIER
    ::= { registration 6 }

snBI4000Switch OBJECT IDENTIFIER
    ::= { snBigIron4000 1 }

snBI4000Router OBJECT IDENTIFIER
    ::= { snBigIron4000 2 }

snBI4000SI OBJECT IDENTIFIER
    ::= { snBigIron4000 3 }

snBigIron8000 OBJECT IDENTIFIER
    ::= { registration 7 }

snBI8000Switch OBJECT IDENTIFIER
    ::= { snBigIron8000 1 }

snBI8000Router OBJECT IDENTIFIER
    ::= { snBigIron8000 2 }

snBI8000SI OBJECT IDENTIFIER
    ::= { snBigIron8000 3 }

snFastIron2 OBJECT IDENTIFIER
    ::= { registration 8 }

snFI2Switch OBJECT IDENTIFIER
    ::= { snFastIron2 1 }

snFI2Router OBJECT IDENTIFIER
    ::= { snFastIron2 2 }

snFastIron2Plus OBJECT IDENTIFIER
    ::= { registration 9 }

snFI2PlusSwitch OBJECT IDENTIFIER
    ::= { snFastIron2Plus 1 }

snFI2PlusRouter OBJECT IDENTIFIER
    ::= { snFastIron2Plus 2 }

snNetIron400 OBJECT IDENTIFIER
    ::= { registration 10 }

snNI400Router OBJECT IDENTIFIER
    ::= { snNetIron400 1 }

snNetIron800 OBJECT IDENTIFIER
    ::= { registration 11 }

snNI800Router OBJECT IDENTIFIER
    ::= { snNetIron800 1 }

snFastIron2GC OBJECT IDENTIFIER
    ::= { registration 12 }

snFI2GCSwitch OBJECT IDENTIFIER
    ::= { snFastIron2GC 1 }

snFI2GCRouter OBJECT IDENTIFIER
    ::= { snFastIron2GC 2 }

snFastIron2PlusGC OBJECT IDENTIFIER
    ::= { registration 13 }

snFI2PlusGCSwitch OBJECT IDENTIFIER
    ::= { snFastIron2PlusGC 1 }

snFI2PlusGCRouter OBJECT IDENTIFIER
    ::= { snFastIron2PlusGC 2 }

END -- end of module FOUNDRY-SN-ROOT-MIB.
