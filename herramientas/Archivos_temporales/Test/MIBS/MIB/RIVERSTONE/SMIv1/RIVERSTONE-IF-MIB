--
-- This SMIv1 module has been generated by smidump 0.2-cvs. Do not edit.
--

RIVERSTONE-IF-MIB DEFINITIONS ::= BEGIN

IMPORTS
    ifIndex
        FROM IF-MIB
    OBJECT-TYPE
        FROM RFC-1212
    Counter, Gauge
        FROM RFC1155-SMI
    riverstoneMibs
        FROM RIVERSTONE-SMI-MIB
    RsQueuePolicy
        FROM RIVERSTONE-TC-MIB
    TruthValue
        FROM SNMPv2-TC;

rsIfMIB OBJECT IDENTIFIER
    ::= { riverstoneMibs 60 }

-- rsIfMIB MODULE-IDENTITY
--     LAST-UPDATED    "200210170000Z"
--     ORGANIZATION    
--             "Riverstone Networks, Inc"
--     CONTACT-INFO    
--             "Riverstone Networks
--              Customer Service
--              
--              Postal:
--              Riverstone Networks, Inc
--              5200 Great America Parkway
--              Santa Clara CA 95054 USA
--              
--              PHONE:+1 408.878.6500
--              EMAIL: nms-eng@riverstonenet.com
--              WEB: http://www.riverstonenet.com"
--     DESCRIPTION     
--             "This MIB module extends the IF-MIB."
--     REVISION        "200210170000Z"
--     DESCRIPTION     
--             "Initial version."
--     ::= { riverstoneMibs 60 }


rsIfMIBObjects OBJECT IDENTIFIER
    ::= { rsIfMIB 1 }

rsIfStatsTable OBJECT-TYPE
    SYNTAX          SEQUENCE OF RsIfStatsEntry
    ACCESS          not-accessible
    STATUS          mandatory
    DESCRIPTION     
            "This table contains additional information for
             interfaces in the ifTable. An interface would
             be included in this table only if the value 
             of its ifConnectorPresent is true."
--     REFERENCE       
--             "RFC 2233 ifConnectorPresent, ifTable"
    ::= { rsIfMIBObjects 1 }

rsIfStatsEntry OBJECT-TYPE
    SYNTAX          RsIfStatsEntry
    ACCESS          not-accessible
    STATUS          mandatory
    DESCRIPTION     
            "This entry provides additional information for 
             the corresponding interface in the ifTable. 
             
             Discontinuities in the values of this row 
             can occur at re-initialization of the management
             system, and at other times as indicated by the
             value of ifCounterDiscontinuityTime.
             
             The objects in this entry complement other counters
             in IF-MIB, P/Q-BRIDGE-MIB, EtherLike-MIB. RMON-MIB"
--     REFERENCE       
--             "RFC 2233 ifIndex, ifCounterDiscontinuityTime,
--              IF-MIB. RFC 2819 RMON-MIB. 
--              RFC 2674 P/Q-BRIDGE-MIB. RFC 2665 EtherLike-MIB.
--              RS CLI Reference Manual 'statistics show port-stats'."
    INDEX           { ifIndex }
    ::= { rsIfStatsTable 1 }

RsIfStatsEntry ::=
    SEQUENCE {
        rsIfStatsCapability             OCTET STRING,
        rsIfQueuePolicy                 RsQueuePolicy,
        rsIfMru                         INTEGER,
        rsIfForceEtherIIState           TruthValue,
        rsIfTotalUpTime                 Counter,
        rsIfTotalDownTime               Counter,
        rsIfUpTransitions               Counter,
        rsIfDownTransitions             Counter,
        rsIfInCorrelatedLayer1Errors    Counter,
--         rsIfInBridgedOctets             Counter64,
--         rsIfInLocalFrames               Counter64,
--         rsIfInL2TableMisses             Counter64,
--         rsIfInRoutedOctets              Counter64,
--         rsIfInRoutedSwitchedPackets     Counter64,
--         rsIfInRoutedCpuPackets          Counter64,
--         rsIfInIpTableMisses             Counter64,
        rsIfInInvalidMacEncap           Counter,
        rsIfInVlanTableDiscards         Counter,
--         rsIfOutBridgedOctets            Counter64,
--         rsIfOutRoutedOctets             Counter64,
        rsIfOutVlanTableDiscards        Counter
    }

rsIfStatsCapability OBJECT-TYPE
    SYNTAX          OCTET STRING
--                       { ifTotalUpTime(0), ifTotalDownTime(1), 
--                         ifUpTransitions(2), ifDownTransitions(3), 
--                         ifInCorrelatedLayer1Errors(4), 
--                         ifInBridgedOctets(5), ifInLocalFrames(6), 
--                         ifInL2TableMisses(7), ifInRoutedOctets(8), 
--                         ifInRoutedSwitchedPackets(9), 
--                         ifInRoutedCpuPackets(10), 
--                         ifInIpTableMisses(11), 
--                         ifInInvalidMacEncap(12), 
--                         ifInVlanTableDiscards(13), 
--                         ifOutBridgedOctets(14), ifOutRoutedOctets(15), 
--                         ifOutVlanTableDiscards(16) }
    ACCESS          read-only
    STATUS          mandatory
    DESCRIPTION     
            "The validity of each counter in this table. Each bit
             refers to one counter. 
             
             This object indicates if each counter in the row is
             supported."
    ::= { rsIfStatsEntry 1 }

rsIfQueuePolicy OBJECT-TYPE
    SYNTAX          RsQueuePolicy
    ACCESS          read-only
    STATUS          mandatory
    DESCRIPTION     
            "The queuing policy used on this physical interface. 
             
             On the RS platform, the user can see the queue policy 
             by entering: 'qos show weighted-fair port <port>'
             in enabled mode."
--     REFERENCE       
--             "RS CLI Reference Manual 'qos show weighted-fair'"
    ::= { rsIfStatsEntry 2 }

rsIfMru OBJECT-TYPE
    SYNTAX          INTEGER
    ACCESS          read-only
    STATUS          mandatory
    DESCRIPTION     
            "The size of the largest frame which can be 
             received by this physical network interface for a
             specific media type. 
             
             Frames received that are larger than this size
             will be dropped and the generic ifInErrors 
             counter will be incremented. 
             
             Depending on the interface type, a specific 
             (too big) counter will be incremented such as
             dot3StatsFrameTooLongs.
             
             On the RS platform, the user can see the MRU 
             by entering: 'port show mtu <port>' in enabled 
             mode."
--     REFERENCE       
--             "RFC 2233 ifInErrors. RFC 2665 dot3StatsFrameTooLongs.
--              RS CLI Reference Manual 'port show mtu'"
    ::= { rsIfStatsEntry 3 }

rsIfForceEtherIIState OBJECT-TYPE
    SYNTAX          TruthValue
    ACCESS          read-only
    STATUS          mandatory
    DESCRIPTION     
            "The object indicates if the port is configured 
             to force input encapsulation to be interpreted 
             as 'Ethernet II'. 
             
             If the value is false, this means the port is not
             an Ethernet port or the Ethernet port is not forcing
             this input encapsulation.
             
             On the RS platform, the user can check for the line
             'port set <port> input-encapsulation forced-ethernet_ii'
             in config mode."
    ::= { rsIfStatsEntry 4 }

rsIfTotalUpTime OBJECT-TYPE
    SYNTAX          Counter
    ACCESS          read-only
    STATUS          mandatory
    DESCRIPTION     
            "The amount of time since the router boots up for which
             the interface is up.
             
             The sum of rsIfTotalUpTime and rsIfTotalDownTime is equal to
             sysUpTime."
    ::= { rsIfStatsEntry 5 }

rsIfTotalDownTime OBJECT-TYPE
    SYNTAX          Counter
    ACCESS          read-only
    STATUS          mandatory
    DESCRIPTION     
            "The amount of time since the router boots up for which
             the interface is down.
             
             The sum of rsIfTotalUpTime and rsIfTotalDownTime is equal to
             sysUpTime."
    ::= { rsIfStatsEntry 6 }

rsIfUpTransitions OBJECT-TYPE
    SYNTAX          Counter
    ACCESS          read-only
    STATUS          mandatory
    DESCRIPTION     
            "The number of times this interface has changed from 
             link-down to link-up."
    ::= { rsIfStatsEntry 7 }

rsIfDownTransitions OBJECT-TYPE
    SYNTAX          Counter
    ACCESS          read-only
    STATUS          mandatory
    DESCRIPTION     
            "The number of times this interface has changed from 
             link-up to link-down."
    ::= { rsIfStatsEntry 8 }

rsIfInCorrelatedLayer1Errors OBJECT-TYPE
    SYNTAX          Counter
    ACCESS          read-only
    STATUS          mandatory
    DESCRIPTION     
            "The number of frames in error due to physical signal 
             degradation. 
             
             This counter is a close approximation of the actual 
             number of frames dropped due to layer 1 errors. 
             
             An empirical experiment was done to correlate the 
             registers to the actual frames dropped in a controlled
             environment that simulates physical signal degradation. 
             
             On the RS platform, a number of hardware registers 
             were identified that approximate the actual number of
             frames dropped. The registers would be different for
             the different interfaces on the RS platform.
             
             Usually on WAN interface, this counter is not supported.
             Refer to the value of rsIfStatsCapability to determine
             if this interface supports this counter."
    ::= { rsIfStatsEntry 9 }

-- rsIfInBridgedOctets OBJECT-TYPE
--     SYNTAX          Counter64
--     ACCESS          read-only
--     STATUS          mandatory
--     DESCRIPTION     
--             "The number of bridged octets that are received by
--              this interface.
--              
--              The sum of rsIfInBridgedOctets and rsIfInRoutedOctets
--              is equal to ifInOctets.
--              
--              This object is similar to dot1dTpHCPortInFrames, but 
--              bytes are counted instead of frames."
--     REFERENCE       
--             "RFC 2674 dot1dTpHCPortInFrames."
--     ::= { rsIfStatsEntry 10 }

-- rsIfInLocalFrames OBJECT-TYPE
--     SYNTAX          Counter64
--     ACCESS          read-only
--     STATUS          mandatory
--     DESCRIPTION     
--             "The number of frames whose destination address is a 
--              local MAC address and whose etype is of L2 variety."
--     ::= { rsIfStatsEntry 11 }

-- rsIfInL2TableMisses OBJECT-TYPE
--     SYNTAX          Counter64
--     ACCESS          read-only
--     STATUS          mandatory
--     DESCRIPTION     
--             "The number of times that there is no entry in the 
--              Forwarding Database. As a result, this frame would
--              go to a CPU."
--     ::= { rsIfStatsEntry 12 }

-- rsIfInRoutedOctets OBJECT-TYPE
--     SYNTAX          Counter64
--     ACCESS          read-only
--     STATUS          mandatory
--     DESCRIPTION     
--             "The number of routed octets received by this interface.
--              
--              The sum of rsIfInBridgedOctets and rsIfInRoutedOctets
--              is equal to ifInOctets."
--     ::= { rsIfStatsEntry 13 }

-- rsIfInRoutedSwitchedPackets OBJECT-TYPE
--     SYNTAX          Counter64
--     ACCESS          read-only
--     STATUS          mandatory
--     DESCRIPTION     
--             "The number of IP packets that were switched through 
--              the fabric without going to the CPU. 
--              
--              On the RS platform with HRT disabled, when the L3 flow 
--              table does not have a flow entry for a packet, the first
--              packet for the flow would go to the CPU first to 
--              establish a flow entry."
--     ::= { rsIfStatsEntry 14 }

-- rsIfInRoutedCpuPackets OBJECT-TYPE
--     SYNTAX          Counter64
--     ACCESS          read-only
--     STATUS          mandatory
--     DESCRIPTION     
--             "The number of IP packets sent to the CPU. This 
--              counter would increase when a packet is destined
--              to the CPU and the L3 table has its flow entry."
--     ::= { rsIfStatsEntry 15 }

-- rsIfInIpTableMisses OBJECT-TYPE
--     SYNTAX          Counter64
--     ACCESS          read-only
--     STATUS          mandatory
--     DESCRIPTION     
--             "The number of times that an appropriate flow for
--              the packet is not found in the L3 flow table.
--              As a result, this packet goes to the CPU to
--              create a L3 flow entry.
--              
--              On the RS platform with HRT mode enabled, the packet
--              would not go to the CPU."
--     ::= { rsIfStatsEntry 16 }

rsIfInInvalidMacEncap OBJECT-TYPE
    SYNTAX          Counter
    ACCESS          read-only
    STATUS          mandatory
    DESCRIPTION     
            "The number of frames received by this interface that 
             used invalid MAC encapsulation."
    ::= { rsIfStatsEntry 17 }

rsIfInVlanTableDiscards OBJECT-TYPE
    SYNTAX          Counter
    ACCESS          read-only
    STATUS          mandatory
    DESCRIPTION     
            "The number of frames received by this interface that 
             were discarded due to VLAN related reasons.
             
             This object is similar to dot1qTpVlanPortInDiscards. 
             It would have the same value if this interface belongs
             to only one VLAN. 
             
             On some interfaces, this object is not valid. Refer to
             the value of rsIfStatsCapability to check its validity."
--     REFERENCE       
--             "RFC 2674 dot1qTpVlanPortInDiscards."
    ::= { rsIfStatsEntry 18 }

-- rsIfOutBridgedOctets OBJECT-TYPE
--     SYNTAX          Counter64
--     ACCESS          read-only
--     STATUS          mandatory
--     DESCRIPTION     
--             "The number of bridged octets that are transmitted by
--              this interface. 
--              
--              This object is similar to dot1dTpHCPortInFrames, but 
--              bytes are counted instead of frames."
--     REFERENCE       
--             "RFC 2674 dot1dTpHCPortOutFrames."
--     ::= { rsIfStatsEntry 19 }

-- rsIfOutRoutedOctets OBJECT-TYPE
--     SYNTAX          Counter64
--     ACCESS          read-only
--     STATUS          mandatory
--     DESCRIPTION     
--             "The number of routed octets transmitted by this interface.
--              
--              The sum of rsIfOutBridgedOctets and rsIfOutRoutedOctets
--              is equal to ifOutOctets."
--     ::= { rsIfStatsEntry 20 }

rsIfOutVlanTableDiscards OBJECT-TYPE
    SYNTAX          Counter
    ACCESS          read-only
    STATUS          mandatory
    DESCRIPTION     
            "The number of frames to be transmitted by this interface 
             but were discarded due to VLAN related reasons.
             
             This object is similar to dot1qTpVlanPortOutDiscards. 
             It would have the same value if this interface belongs
             to only one VLAN. 
             
             On some interfaces, this object is not valid. Refer to
             the value of rsIfStatsCapability to check its validity."
--     REFERENCE       
--             "RFC 2674 dot1qTpVlanPortOutDiscards."
    ::= { rsIfStatsEntry 21 }

rsIfGaugeTable OBJECT-TYPE
    SYNTAX          SEQUENCE OF RsIfGaugeEntry
    ACCESS          not-accessible
    STATUS          mandatory
    DESCRIPTION     
            "This table contains gauges for a port interface."
    ::= { rsIfMIBObjects 2 }

rsIfGaugeEntry OBJECT-TYPE
    SYNTAX          RsIfGaugeEntry
    ACCESS          not-accessible
    STATUS          mandatory
    DESCRIPTION     
            "This row contains gauges for a port interface.
             
             The number of updates done to caluculate the
             difference of a gauge in the one minute interval 
             may vary across different software versions.
             
             If the updates are infrequent for example every 30 
             seconds, the user would observe a constant value
             for that 30 seconds.
             
             Discontinuities in the values of this row can
             occur at re-initialization of the management
             system, and at other times as indicated by the
             value of ifCounterDiscontinuityTime."
--     REFERENCE       
--             "RFC 2233 ifIndex, ifCounterDiscontinuityTime. 
--              RS CLI Reference Manual 'statistics show port-stats.'"
    INDEX           { ifIndex }
    ::= { rsIfGaugeTable 1 }

RsIfGaugeEntry ::=
    SEQUENCE {
        rsIfGaugeCapability             OCTET STRING,
        rsIfInOneMinBitsPerSec          Gauge,
        rsIfInOneMinPktsDiscards        Gauge,
        rsIfInOneMinPktsErrors          Gauge,
        rsIfInOneMinUnicastPkts         Gauge,
        rsIfInOneMinMulticastPkts       Gauge,
        rsIfInOneMinBroadcastPkts       Gauge,
        rsIfOutOneMinBitsPerSec         Gauge,
        rsIfOutOneMinPktsDiscards       Gauge,
        rsIfOutOneMinPktsErrors         Gauge,
        rsIfOutOneMinUnicastPkts        Gauge,
        rsIfOutOneMinMulticastPkts      Gauge,
        rsIfOutOneMinBroadcastPkts      Gauge
    }

rsIfGaugeCapability OBJECT-TYPE
    SYNTAX          OCTET STRING
--                       { ifInOneMinBitsPerSec(0), 
--                         ifInOneMinPktsDiscards(1), 
--                         ifInOneMinPktsErrors(2), 
--                         ifInOneMinUnicastPkts(3), 
--                         ifInOneMinMulticastPkts(4), 
--                         ifInOneMinBroadcastPkts(5), 
--                         ifOutOneMinBitsPerSec(6), 
--                         ifOutOneMinPktsDiscards(7), 
--                         ifOutOneMinPktsErrors(8), 
--                         ifOutOneMinUnicastPkts(9), 
--                         ifOutOneMinMulticastPkts(10), 
--                         ifOutOneMinBroadcastPkts(11) }
    ACCESS          read-only
    STATUS          mandatory
    DESCRIPTION     
            "The validity of each object in this table. 
             Each bit refers to one object. 
             
             This object indicates if each counter in the row is
             supported."
    ::= { rsIfGaugeEntry 1 }

rsIfInOneMinBitsPerSec OBJECT-TYPE
    SYNTAX          Gauge
    ACCESS          read-only
    STATUS          mandatory
    DESCRIPTION     
            "The average receive rate across the one minute 
             interval before the update."
    ::= { rsIfGaugeEntry 2 }

rsIfInOneMinPktsDiscards OBJECT-TYPE
    SYNTAX          Gauge
    ACCESS          read-only
    STATUS          mandatory
    DESCRIPTION     
            "The number of packets received by this port that 
             were discarded in the one minute interval before
             the update.
             
             On the RS platform, a reason for discarding the
             packets would be buffer overflow."
    ::= { rsIfGaugeEntry 3 }

rsIfInOneMinPktsErrors OBJECT-TYPE
    SYNTAX          Gauge
    ACCESS          read-only
    STATUS          mandatory
    DESCRIPTION     
            "The number of packets with error received by 
             this port in the one minute interval before
             the update.
             
             On the RS platform, the number of received packets
             with 'error' is a sum of:
                  frames with invalid MAC encapsulation, 
                  oversize frames, 
                  jabbers, 
                  undersize frames, 
                  frames with bad alignment, 
                  frames with bad CRC,
                  internal frame error, 
                  input VLAN dropped frames,
                  carrier sense error frames."
--     REFERENCE       
--             "RFC 2665 dot3StatsFrameTooLongs, 
--              dot3StatsAlignmentErrors,
--              dot3StatsFCSErrors,
--              dot3StatsInternalMacReceiveErrors,
--              dot3StatsCarrierSenseErrors.
--              RFC 2819 etherStatsOversizePkts,
--              etherStatsJabbers, etherStatsUndersizePkts."
    ::= { rsIfGaugeEntry 4 }

rsIfInOneMinUnicastPkts OBJECT-TYPE
    SYNTAX          Gauge
    ACCESS          read-only
    STATUS          mandatory
    DESCRIPTION     
            "The number of unicast packets received by 
             this port in the one minute interval before 
             the update."
    ::= { rsIfGaugeEntry 5 }

rsIfInOneMinMulticastPkts OBJECT-TYPE
    SYNTAX          Gauge
    ACCESS          read-only
    STATUS          mandatory
    DESCRIPTION     
            "The number of multicast packets received by 
             this port in the one minute interval before the 
             update."
--     REFERENCE       
--             "RFC 2819 etherStatsMulticastPkts."
    ::= { rsIfGaugeEntry 6 }

rsIfInOneMinBroadcastPkts OBJECT-TYPE
    SYNTAX          Gauge
    ACCESS          read-only
    STATUS          mandatory
    DESCRIPTION     
            "The number of broadcast packets received by
             this port in the one minute interval before the 
             update."
--     REFERENCE       
--             "RFC 2819 etherStatsBroadcastPkts."
    ::= { rsIfGaugeEntry 7 }

rsIfOutOneMinBitsPerSec OBJECT-TYPE
    SYNTAX          Gauge
    ACCESS          read-only
    STATUS          mandatory
    DESCRIPTION     
            "The average transmit rate across the one minute.
             before the update."
    ::= { rsIfGaugeEntry 8 }

rsIfOutOneMinPktsDiscards OBJECT-TYPE
    SYNTAX          Gauge
    ACCESS          read-only
    STATUS          mandatory
    DESCRIPTION     
            "The number of packets to be transmitted that were
             discarded by the port interface in the minute
             before the update.
             
             On the RS platform, a reason for discarding the 
             packets would be buffer overflow."
    ::= { rsIfGaugeEntry 9 }

rsIfOutOneMinPktsErrors OBJECT-TYPE
    SYNTAX          Gauge
    ACCESS          read-only
    STATUS          mandatory
    DESCRIPTION     
            "The number of packets to be transmitted but may or
             may not have been discarded by the port interface 
             because of 'error' in the one minute interval before
             the update.
             
             On the RS platform, the number of packets 
             with 'error' is a sum of:
                  single collision frames, 
                  multiple collision frames,
                  frames dropped because of collisions, 
                  deferred transmissions, 
                  late collision frames,
                  underruns, 
                  internal transmit errors."
--     REFERENCE       
--             "RFC 2665 dot3StatsSingleCollisionFrames,
--              dot3StatsMultipleCollisionFrames, 
--              dot3StatsExcessiveCollisions,
--              dot3StatsDeferredTransmissions,
--              dot3StatsLateCollisions,
--              dot3StatsInternalMacTransmitErrors."
    ::= { rsIfGaugeEntry 10 }

rsIfOutOneMinUnicastPkts OBJECT-TYPE
    SYNTAX          Gauge
    ACCESS          read-only
    STATUS          mandatory
    DESCRIPTION     
            "The number of unicast packets transmitted in the
             one minute interval before the update."
    ::= { rsIfGaugeEntry 11 }

rsIfOutOneMinMulticastPkts OBJECT-TYPE
    SYNTAX          Gauge
    ACCESS          read-only
    STATUS          mandatory
    DESCRIPTION     
            "The number of multicast packets transmitted in the
             one minute interval before the update."
    ::= { rsIfGaugeEntry 12 }

rsIfOutOneMinBroadcastPkts OBJECT-TYPE
    SYNTAX          Gauge
    ACCESS          read-only
    STATUS          mandatory
    DESCRIPTION     
            "The number of broadcast packets transmitted in the
             one minute interval before the update."
    ::= { rsIfGaugeEntry 13 }

rsIfConformance OBJECT IDENTIFIER
    ::= { rsIfMIB 2 }

rsIfCompliances OBJECT IDENTIFIER
    ::= { rsIfConformance 1 }

rsIfGroups OBJECT IDENTIFIER
    ::= { rsIfConformance 2 }

rsIfStatsGroup OBJECT IDENTIFIER
    ::= { rsIfGroups 1 }

-- rsIfStatsGroup OBJECT-GROUP
--     OBJECTS         { rsIfStatsCapability, rsIfQueuePolicy, rsIfMru, 
--                       rsIfForceEtherIIState, rsIfTotalUpTime, 
--                       rsIfTotalDownTime, rsIfUpTransitions, 
--                       rsIfDownTransitions, 
--                       rsIfInCorrelatedLayer1Errors, rsIfInLocalFrames, 
--                       rsIfInRoutedSwitchedPackets, 
--                       rsIfInRoutedCpuPackets, rsIfInBridgedOctets, 
--                       rsIfInRoutedOctets, rsIfInL2TableMisses, 
--                       rsIfInIpTableMisses, rsIfInInvalidMacEncap, 
--                       rsIfInVlanTableDiscards, rsIfOutBridgedOctets, 
--                       rsIfOutRoutedOctets, rsIfOutVlanTableDiscards }
--     STATUS          mandatory
--     DESCRIPTION     
--             "The collection of objects representing additional port 
--              interface counters and state data."
--     ::= { rsIfGroups 1 }

rsIfGaugeGroup OBJECT IDENTIFIER
    ::= { rsIfGroups 2 }

-- rsIfGaugeGroup OBJECT-GROUP
--     OBJECTS         { rsIfGaugeCapability, rsIfInOneMinBitsPerSec, 
--                       rsIfInOneMinPktsDiscards, 
--                       rsIfInOneMinPktsErrors, rsIfInOneMinUnicastPkts, 
--                       rsIfInOneMinMulticastPkts, 
--                       rsIfInOneMinBroadcastPkts, 
--                       rsIfOutOneMinBitsPerSec, 
--                       rsIfOutOneMinPktsDiscards, 
--                       rsIfOutOneMinPktsErrors, 
--                       rsIfOutOneMinUnicastPkts, 
--                       rsIfOutOneMinMulticastPkts, 
--                       rsIfOutOneMinBroadcastPkts }
--     STATUS          mandatory
--     DESCRIPTION     
--             "The collection of objects representing port interface
--              gauges."
--     ::= { rsIfGroups 2 }

rsIfCompliance OBJECT IDENTIFIER
    ::= { rsIfCompliances 1 }

-- rsIfCompliance MODULE-COMPLIANCE
--     STATUS          mandatory
--     DESCRIPTION     
--             "The compliance statement for RIVERSTONE-STATS-MIB."

--     MODULE          -- -- this module

--         MANDATORY-GROUPS    { rsIfStatsGroup }

--     ::= { rsIfCompliances 1 }

END -- end of module RIVERSTONE-IF-MIB.
