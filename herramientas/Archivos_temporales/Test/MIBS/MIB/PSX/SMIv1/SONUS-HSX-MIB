--
-- This SMIv1 module has been generated by smidump 0.2-cvs. Do not edit.
--

SONUS-HSX-MIB DEFINITIONS ::= BEGIN

IMPORTS
    OBJECT-TYPE
        FROM RFC-1212
    TRAP-TYPE
        FROM RFC-1215
    Counter, Gauge, TimeTicks
        FROM RFC1155-SMI
    sonusEventClass, sonusEventDescription, sonusEventLevel, 
    sonusEventTime
        FROM SONUS-COMMON-MIB
    sonusServicesMIBs
        FROM SONUS-SMI;

sonusHomeSubscriberServerMIB OBJECT IDENTIFIER
    ::= { sonusServicesMIBs 29 }

-- sonusHomeSubscriberServerMIB MODULE-IDENTITY
--     LAST-UPDATED    "200603290000Z"
--     ORGANIZATION    
--             "Sonus Networks, Inc."
--     CONTACT-INFO    
--             "   Customer Support    
--              Sonus Networks, Inc.
--              250 Apollo Drive
--              Chelmsford, MA 01824
--              USA
--              
--              Tel: 978-614-8100
--              Fax: 978-614-8609"
--     DESCRIPTION     
--             "The MIB Module for Home Subscriber Server Management."
--     ::= { sonusServicesMIBs 29 }


sonusHomeSubscriberServerMIBObjects OBJECT IDENTIFIER
    ::= { sonusHomeSubscriberServerMIB 1 }

sonusHomeSubscriberServerStatistics OBJECT IDENTIFIER
    ::= { sonusHomeSubscriberServerMIBObjects 1 }

sonusHssCxCounters OBJECT IDENTIFIER
    ::= { sonusHomeSubscriberServerStatistics 1 }

sonusHssCxCountersIncomingSAR OBJECT-TYPE
    SYNTAX          Counter
    ACCESS          read-only
    STATUS          mandatory
    DESCRIPTION     
            "This counter keeps track of incoming Cx SAR requests."
    ::= { sonusHssCxCounters 1 }

sonusHssCxCountersIncomingMAR OBJECT-TYPE
    SYNTAX          Counter
    ACCESS          read-only
    STATUS          mandatory
    DESCRIPTION     
            "This counter keeps track of incoming Cx MAR requests."
    ::= { sonusHssCxCounters 2 }

sonusHssCxCountersIncomingUAR OBJECT-TYPE
    SYNTAX          Counter
    ACCESS          read-only
    STATUS          mandatory
    DESCRIPTION     
            "This counter keeps track of incoming Cx UAR requests."
    ::= { sonusHssCxCounters 3 }

sonusHssCxCountersIncomingLIR OBJECT-TYPE
    SYNTAX          Counter
    ACCESS          read-only
    STATUS          mandatory
    DESCRIPTION     
            "This counter keeps track of incoming Cx LIR requests."
    ::= { sonusHssCxCounters 4 }

sonusHssCxCountersOutgoingRTR OBJECT-TYPE
    SYNTAX          Counter
    ACCESS          read-only
    STATUS          mandatory
    DESCRIPTION     
            "This counter keeps track of outgoing Cx RTR requests."
    ::= { sonusHssCxCounters 5 }

sonusHssCxCountersOutgoingPPR OBJECT-TYPE
    SYNTAX          Counter
    ACCESS          read-only
    STATUS          mandatory
    DESCRIPTION     
            "This counter keeps track of outgoing Cx PPR requests."
    ::= { sonusHssCxCounters 6 }

sonusHssShCounters OBJECT IDENTIFIER
    ::= { sonusHomeSubscriberServerStatistics 2 }

sonusHssShCountersIncomingUDR OBJECT-TYPE
    SYNTAX          Counter
    ACCESS          read-only
    STATUS          mandatory
    DESCRIPTION     
            "This counter keeps track of incoming Sh UDR requests."
    ::= { sonusHssShCounters 1 }

sonusHssShCountersIncomingPUR OBJECT-TYPE
    SYNTAX          Counter
    ACCESS          read-only
    STATUS          mandatory
    DESCRIPTION     
            "This counter keeps track of incoming Sh PUR requests."
    ::= { sonusHssShCounters 2 }

sonusHssShCountersIncomingSNR OBJECT-TYPE
    SYNTAX          Counter
    ACCESS          read-only
    STATUS          mandatory
    DESCRIPTION     
            "This counter keeps track of incoming Sh SNR requests."
    ::= { sonusHssShCounters 3 }

sonusHssShCountersOutgoingPNR OBJECT-TYPE
    SYNTAX          Counter
    ACCESS          read-only
    STATUS          mandatory
    DESCRIPTION     
            "This counter keeps track of outgoing Sh PNR requests."
    ::= { sonusHssShCounters 4 }

sonusHssDiameterCounters OBJECT IDENTIFIER
    ::= { sonusHomeSubscriberServerStatistics 3 }

sonusHssDiameterCountersRequestTimeout OBJECT-TYPE
    SYNTAX          Counter
    ACCESS          read-only
    STATUS          mandatory
    DESCRIPTION     
            "This counter keeps track of timeouts for outgoing Diameter requests."
    ::= { sonusHssDiameterCounters 1 }

sonusHomeSubscriberServerMIBNotifications OBJECT IDENTIFIER
    ::= { sonusHomeSubscriberServerMIB 2 }

sonusHomeSubscriberServerMIBNotificationsPrefix OBJECT IDENTIFIER
    ::= { sonusHomeSubscriberServerMIBNotifications 0 }

sonusHomeSubscriberServerMIBNotificationsObjects OBJECT IDENTIFIER
    ::= { sonusHomeSubscriberServerMIBNotifications 1 }

sonusHssDiameterPeerName OBJECT-TYPE
    SYNTAX          OCTET STRING
    ACCESS          read-only
    STATUS          mandatory
    DESCRIPTION     
            "Diameter Peer Name."
    ::= { sonusHomeSubscriberServerMIBNotificationsObjects 1 }

sonusHssPipeErrorCode OBJECT-TYPE
    SYNTAX          INTEGER
    ACCESS          read-only
    STATUS          mandatory
    DESCRIPTION     
            "The unix error code, if any, will be available in this field."
    ::= { sonusHomeSubscriberServerMIBNotificationsObjects 2 }

sonusHssUpNotification TRAP-TYPE
    ENTERPRISE      sonusHomeSubscriberServerMIBNotifications
    VARIABLES       { sonusEventDescription, sonusEventClass, 
                      sonusEventLevel, sonusEventTime }
--     STATUS          mandatory
    DESCRIPTION     
            "SoftSwitch Hss is up."
    ::= 1

sonusHssDownNotification TRAP-TYPE
    ENTERPRISE      sonusHomeSubscriberServerMIBNotifications
    VARIABLES       { sonusEventDescription, sonusEventClass, 
                      sonusEventLevel, sonusEventTime }
--     STATUS          mandatory
    DESCRIPTION     
            "SoftSwitch Hss is down."
    ::= 2

sonusHssDiameterPeerOpenNotification TRAP-TYPE
    ENTERPRISE      sonusHomeSubscriberServerMIBNotifications
    VARIABLES       { sonusHssDiameterPeerName, sonusEventDescription, 
                      sonusEventClass, sonusEventLevel, sonusEventTime }
--     STATUS          mandatory
    DESCRIPTION     
            "SoftSwitch Hss Diameter Peer enters OPEN state."
    ::= 3

sonusHssDiameterPeerCloseNotification TRAP-TYPE
    ENTERPRISE      sonusHomeSubscriberServerMIBNotifications
    VARIABLES       { sonusHssDiameterPeerName, sonusEventDescription, 
                      sonusEventClass, sonusEventLevel, sonusEventTime }
--     STATUS          mandatory
    DESCRIPTION     
            "SoftSwitch Hss Diameter Peer leaves OPEN state."
    ::= 4

sonusHssDiameterPendingReqestsHighNotification TRAP-TYPE
    ENTERPRISE      sonusHomeSubscriberServerMIBNotifications
    VARIABLES       { sonusEventDescription, sonusEventClass, 
                      sonusEventLevel, sonusEventTime }
--     STATUS          mandatory
    DESCRIPTION     
            "SoftSwitch Hss Diameter pending request number crossed over
             high water mark (80% of MAX)."
    ::= 5

sonusHssDiameterPendingReqestsNotHighNotification TRAP-TYPE
    ENTERPRISE      sonusHomeSubscriberServerMIBNotifications
    VARIABLES       { sonusEventDescription, sonusEventClass, 
                      sonusEventLevel, sonusEventTime }
--     STATUS          mandatory
    DESCRIPTION     
            "SoftSwitch Hss Diameter pending request number crossed under
             low water mark (70% of MAX)."
    ::= 6

sonusHssPipeCommunicationUpNotification TRAP-TYPE
    ENTERPRISE      sonusHomeSubscriberServerMIBNotifications
    VARIABLES       { sonusEventDescription, sonusEventClass, 
                      sonusEventLevel, sonusEventTime }
--     STATUS          mandatory
    DESCRIPTION     
            "'hss' process establishes connection with master 'pipe' process."
    ::= 7

sonusHssPipeRegistrationSuccessNotification TRAP-TYPE
    ENTERPRISE      sonusHomeSubscriberServerMIBNotifications
    VARIABLES       { sonusEventDescription, sonusEventClass, 
                      sonusEventLevel, sonusEventTime }
--     STATUS          mandatory
    DESCRIPTION     
            "'hss' process registers with master 'pipe' process."
    ::= 8

sonusHssPipeCommunicationDownNotification TRAP-TYPE
    ENTERPRISE      sonusHomeSubscriberServerMIBNotifications
    VARIABLES       { sonusHssPipeErrorCode, sonusEventDescription, 
                      sonusEventClass, sonusEventLevel, sonusEventTime }
--     STATUS          mandatory
    DESCRIPTION     
            "'hss' process was unable to establish connection with master 'pipe' process."
    ::= 9

sonusHssPipeRegistrationFailureNotification TRAP-TYPE
    ENTERPRISE      sonusHomeSubscriberServerMIBNotifications
    VARIABLES       { sonusHssPipeErrorCode, sonusEventDescription, 
                      sonusEventClass, sonusEventLevel, sonusEventTime }
--     STATUS          mandatory
    DESCRIPTION     
            "'hss' process was unable to register with master 'pipe' process."
    ::= 10

sonusHssPipeIOErrorNotification TRAP-TYPE
    ENTERPRISE      sonusHomeSubscriberServerMIBNotifications
    VARIABLES       { sonusHssPipeErrorCode, sonusEventDescription, 
                      sonusEventClass, sonusEventLevel, sonusEventTime }
--     STATUS          mandatory
    DESCRIPTION     
            "'hss' process was unable to send/receive an update to 'pipe' process."
    ::= 11

END -- end of module SONUS-HSX-MIB.
