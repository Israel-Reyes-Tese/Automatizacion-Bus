--
-- This SMIv1 module has been generated by smidump 0.2-cvs. Do not edit.
--

SONUS-SOFTSWITCH-HTTP-CLIENT-MIB DEFINITIONS ::= BEGIN

IMPORTS
    InetAddress, InetAddressType
        FROM INET-ADDRESS-MIB
    OBJECT-TYPE
        FROM RFC-1212
    TRAP-TYPE
        FROM RFC-1215
    Counter, Gauge, IpAddress, TimeTicks
        FROM RFC1155-SMI
    DisplayString
        FROM SNMPv2-TC
    sonusEventClass, sonusEventDescription, sonusEventLevel, 
    sonusEventTime
        FROM SONUS-COMMON-MIB
    sonusServicesMIBs
        FROM SONUS-SMI;

sonusSoftSwitchHTTPClientMIB OBJECT IDENTIFIER
    ::= { sonusServicesMIBs 43 }

-- sonusSoftSwitchHTTPClientMIB MODULE-IDENTITY
--     LAST-UPDATED    "201807030000Z"
--     ORGANIZATION    
--             "Sonus Networks, Inc."
--     CONTACT-INFO    
--             "   Customer Support    
--              Sonus Networks, Inc.
--              250 Apollo Drive
--              Chelmsford, MA 01824
--              USA
--              
--              Tel: 978-614-8100
--              Fax: 978-614-8609"
--     DESCRIPTION     
--             "The MIB Module for SoftSwitch HTTP Client Management."
--     ::= { sonusServicesMIBs 43 }


sonusSoftSwitchHTTPClientMIBObjects OBJECT IDENTIFIER
    ::= { sonusSoftSwitchHTTPClientMIB 1 }

sonusSoftSwitchHTTPClientStatistics OBJECT IDENTIFIER
    ::= { sonusSoftSwitchHTTPClientMIBObjects 1 }

sonusSoftSwitchHTTPClientSigningCounters OBJECT IDENTIFIER
    ::= { sonusSoftSwitchHTTPClientStatistics 1 }

sonusSoftSwitchHTTPSigningQuerySentCounters OBJECT-TYPE
    SYNTAX          Counter
    ACCESS          read-only
    STATUS          mandatory
    DESCRIPTION     
            "This counter keeps track of the number of Signing requests 
             which are sent from HTTP Client Process."
    ::= { sonusSoftSwitchHTTPClientSigningCounters 1 }

sonusSoftSwitchHTTPSigningRspCounters OBJECT-TYPE
    SYNTAX          Counter
    ACCESS          read-only
    STATUS          mandatory
    DESCRIPTION     
            "This counter keeps track of the number of Signing responses 
             which have been received by HTTP Client process."
    ::= { sonusSoftSwitchHTTPClientSigningCounters 2 }

sonusSoftSwitchHTTPSigningInvalidInputCounters OBJECT-TYPE
    SYNTAX          Counter
    ACCESS          read-only
    STATUS          mandatory
    DESCRIPTION     
            "This counter keeps track of the number of signing requests 
             which failed due to invalid input."
    ::= { sonusSoftSwitchHTTPClientSigningCounters 3 }

sonusSoftSwitchHTTPSigningQueryTimeOutCounters OBJECT-TYPE
    SYNTAX          Counter
    ACCESS          read-only
    STATUS          mandatory
    DESCRIPTION     
            "This counter keeps track of the number of signing requests 
             which have timeout for response."
    ::= { sonusSoftSwitchHTTPClientSigningCounters 4 }

sonusSoftSwitchHTTPSigningQueryRetryCounters OBJECT-TYPE
    SYNTAX          Counter
    ACCESS          read-only
    STATUS          mandatory
    DESCRIPTION     
            "This counter keeps track of the number of Signing requests
             which are retried from HTTP Client Process."
    ::= { sonusSoftSwitchHTTPClientSigningCounters 5 }

sonusSoftSwitchHTTPClientVerificationCounters OBJECT IDENTIFIER
    ::= { sonusSoftSwitchHTTPClientStatistics 2 }

sonusSoftSwitchHTTPVerificationQuerySentCounters OBJECT-TYPE
    SYNTAX          Counter
    ACCESS          read-only
    STATUS          mandatory
    DESCRIPTION     
            "This counter keeps track of the number of Verification requests
             which are sent from HTTP Client Process."
    ::= { sonusSoftSwitchHTTPClientVerificationCounters 1 }

sonusSoftSwitchHTTPVerificationRspCounters OBJECT-TYPE
    SYNTAX          Counter
    ACCESS          read-only
    STATUS          mandatory
    DESCRIPTION     
            "This counter keeps track of the number of Verification responses
             which have been received by HTTP Client process."
    ::= { sonusSoftSwitchHTTPClientVerificationCounters 2 }

sonusSoftSwitchHTTPVerificationInvalidInputCounters OBJECT-TYPE
    SYNTAX          Counter
    ACCESS          read-only
    STATUS          mandatory
    DESCRIPTION     
            "This counter keeps track of the number of Verification requests
             which failed due to invalid input."
    ::= { sonusSoftSwitchHTTPClientVerificationCounters 3 }

sonusSoftSwitchHTTPVerificationQueryTimeOutCounters OBJECT-TYPE
    SYNTAX          Counter
    ACCESS          read-only
    STATUS          mandatory
    DESCRIPTION     
            "This counter keeps track of the number of Verification requests
             which have timeout for response."
    ::= { sonusSoftSwitchHTTPClientVerificationCounters 4 }

sonusSoftSwitchHTTPVerificationQueryRetryCounters OBJECT-TYPE
    SYNTAX          Counter
    ACCESS          read-only
    STATUS          mandatory
    DESCRIPTION     
            "This counter keeps track of the number of Verification requests
             which are retried from HTTP Client Process."
    ::= { sonusSoftSwitchHTTPClientVerificationCounters 5 }

sonusSoftSwitchHTTPClientSigningFailureCounters OBJECT IDENTIFIER
    ::= { sonusSoftSwitchHTTPClientStatistics 3 }

sonusSoftSwitchHTTPSigningFailureE3Counters OBJECT-TYPE
    SYNTAX          Counter
    ACCESS          read-only
    STATUS          mandatory
    DESCRIPTION     
            "This counter keeps track of the number of E3 error 
             received from signing server."
    ::= { sonusSoftSwitchHTTPClientSigningFailureCounters 1 }

sonusSoftSwitchHTTPSigningFailureX1Counters OBJECT-TYPE
    SYNTAX          Counter
    ACCESS          read-only
    STATUS          mandatory
    DESCRIPTION     
            "This counter keeps track of the number of X1 error 
             received from signing server."
    ::= { sonusSoftSwitchHTTPClientSigningFailureCounters 2 }

sonusSoftSwitchHTTPSigningFailureX2Counters OBJECT-TYPE
    SYNTAX          Counter
    ACCESS          read-only
    STATUS          mandatory
    DESCRIPTION     
            "This counter keeps track of the number of X2 error 
             received from signing server."
    ::= { sonusSoftSwitchHTTPClientSigningFailureCounters 3 }

sonusSoftSwitchHTTPSigningFailureX3Counters OBJECT-TYPE
    SYNTAX          Counter
    ACCESS          read-only
    STATUS          mandatory
    DESCRIPTION     
            "This counter keeps track of the number of X3 error 
             received from signing server."
    ::= { sonusSoftSwitchHTTPClientSigningFailureCounters 4 }

sonusSoftSwitchHTTPSigningFailureX4Counters OBJECT-TYPE
    SYNTAX          Counter
    ACCESS          read-only
    STATUS          mandatory
    DESCRIPTION     
            "This counter keeps track of the number of X4 error 
             received from signing server."
    ::= { sonusSoftSwitchHTTPClientSigningFailureCounters 5 }

sonusSoftSwitchHTTPSigningFailure400Counters OBJECT-TYPE
    SYNTAX          Counter
    ACCESS          read-only
    STATUS          mandatory
    DESCRIPTION     
            "This counter keeps track of the number of 400 error
             received from signing server."
    ::= { sonusSoftSwitchHTTPClientSigningFailureCounters 6 }

sonusSoftSwitchHTTPSigningFailure500Counters OBJECT-TYPE
    SYNTAX          Counter
    ACCESS          read-only
    STATUS          mandatory
    DESCRIPTION     
            "This counter keeps track of the number of 500 error 
             received from signing server."
    ::= { sonusSoftSwitchHTTPClientSigningFailureCounters 7 }

sonusSoftSwitchHTTPSigningFailure503Counters OBJECT-TYPE
    SYNTAX          Counter
    ACCESS          read-only
    STATUS          mandatory
    DESCRIPTION     
            "This counter keeps track of the number of 503 error 
             received from signing server."
    ::= { sonusSoftSwitchHTTPClientSigningFailureCounters 8 }

sonusSoftSwitchHTTPSigningFailure405Counters OBJECT-TYPE
    SYNTAX          Counter
    ACCESS          read-only
    STATUS          mandatory
    DESCRIPTION     
            "This counter keeps track of the number of 405 error
             received from signing server."
    ::= { sonusSoftSwitchHTTPClientSigningFailureCounters 9 }

sonusSoftSwitchHTTPSigningFailure406Counters OBJECT-TYPE
    SYNTAX          Counter
    ACCESS          read-only
    STATUS          mandatory
    DESCRIPTION     
            "This counter keeps track of the number of 406 error
             received from signing server."
    ::= { sonusSoftSwitchHTTPClientSigningFailureCounters 10 }

sonusSoftSwitchHTTPSigningFailure411Counters OBJECT-TYPE
    SYNTAX          Counter
    ACCESS          read-only
    STATUS          mandatory
    DESCRIPTION     
            "This counter keeps track of the number of 411 error
             received from signing server."
    ::= { sonusSoftSwitchHTTPClientSigningFailureCounters 11 }

sonusSoftSwitchHTTPSigningFailure415Counters OBJECT-TYPE
    SYNTAX          Counter
    ACCESS          read-only
    STATUS          mandatory
    DESCRIPTION     
            "This counter keeps track of the number of 415 error
             received from signing server."
    ::= { sonusSoftSwitchHTTPClientSigningFailureCounters 12 }

sonusSoftSwitchHTTPSigningFailureSVC4000Counters OBJECT-TYPE
    SYNTAX          Counter
    ACCESS          read-only
    STATUS          mandatory
    DESCRIPTION     
            "This counter keeps track of the number of service exception 4000 error
             received from signing server."
    ::= { sonusSoftSwitchHTTPClientSigningFailureCounters 13 }

sonusSoftSwitchHTTPSigningFailureSVC4001Counters OBJECT-TYPE
    SYNTAX          Counter
    ACCESS          read-only
    STATUS          mandatory
    DESCRIPTION     
            "This counter keeps track of the number of service exception 4001 error
             received from signing server."
    ::= { sonusSoftSwitchHTTPClientSigningFailureCounters 14 }

sonusSoftSwitchHTTPSigningFailureSVC4002Counters OBJECT-TYPE
    SYNTAX          Counter
    ACCESS          read-only
    STATUS          mandatory
    DESCRIPTION     
            "This counter keeps track of the number of service exception 4002 error
             received from signing server."
    ::= { sonusSoftSwitchHTTPClientSigningFailureCounters 15 }

sonusSoftSwitchHTTPSigningFailureSVC4003Counters OBJECT-TYPE
    SYNTAX          Counter
    ACCESS          read-only
    STATUS          mandatory
    DESCRIPTION     
            "This counter keeps track of the number of service exception 4003 error
             received from signing server."
    ::= { sonusSoftSwitchHTTPClientSigningFailureCounters 16 }

sonusSoftSwitchHTTPSigningFailureSVC4004Counters OBJECT-TYPE
    SYNTAX          Counter
    ACCESS          read-only
    STATUS          mandatory
    DESCRIPTION     
            "This counter keeps track of the number of service exception 4004 error
             received from signing server."
    ::= { sonusSoftSwitchHTTPClientSigningFailureCounters 17 }

sonusSoftSwitchHTTPSigningFailureSVC4005Counters OBJECT-TYPE
    SYNTAX          Counter
    ACCESS          read-only
    STATUS          mandatory
    DESCRIPTION     
            "This counter keeps track of the number of service exception 4005 error
             received from signing server."
    ::= { sonusSoftSwitchHTTPClientSigningFailureCounters 18 }

sonusSoftSwitchHTTPSigningFailureSVC4006Counters OBJECT-TYPE
    SYNTAX          Counter
    ACCESS          read-only
    STATUS          mandatory
    DESCRIPTION     
            "This counter keeps track of the number of service exception 4006 error
             received from signing server."
    ::= { sonusSoftSwitchHTTPClientSigningFailureCounters 19 }

sonusSoftSwitchHTTPSigningFailureSVC4007Counters OBJECT-TYPE
    SYNTAX          Counter
    ACCESS          read-only
    STATUS          mandatory
    DESCRIPTION     
            "This counter keeps track of the number of service exception 4007 error
             received from signing server."
    ::= { sonusSoftSwitchHTTPClientSigningFailureCounters 20 }

sonusSoftSwitchHTTPSigningFailurePOL4050Counters OBJECT-TYPE
    SYNTAX          Counter
    ACCESS          read-only
    STATUS          mandatory
    DESCRIPTION     
            "This counter keeps track of the number of policy exception 4050 error
             received from signing server."
    ::= { sonusSoftSwitchHTTPClientSigningFailureCounters 21 }

sonusSoftSwitchHTTPSigningFailurePOL5000Counters OBJECT-TYPE
    SYNTAX          Counter
    ACCESS          read-only
    STATUS          mandatory
    DESCRIPTION     
            "This counter keeps track of the number of policy exception 5000 error
             received from signing server."
    ::= { sonusSoftSwitchHTTPClientSigningFailureCounters 22 }

sonusSoftSwitchHTTPSigningFailure404Counters OBJECT-TYPE
    SYNTAX          Counter
    ACCESS          read-only
    STATUS          mandatory
    DESCRIPTION     
            "This counter keeps track of the number of 404 error
             received from signing server."
    ::= { sonusSoftSwitchHTTPClientSigningFailureCounters 23 }

sonusSoftSwitchHTTPClientVerificationFailureCounters OBJECT IDENTIFIER
    ::= { sonusSoftSwitchHTTPClientStatistics 4 }

sonusSoftSwitchHTTPVerificationFailureE3Counters OBJECT-TYPE
    SYNTAX          Counter
    ACCESS          read-only
    STATUS          mandatory
    DESCRIPTION     
            "This counter keeps track of the number of E3 error
             received from verification server."
    ::= { sonusSoftSwitchHTTPClientVerificationFailureCounters 1 }

sonusSoftSwitchHTTPVerificationFailureE4Counters OBJECT-TYPE
    SYNTAX          Counter
    ACCESS          read-only
    STATUS          mandatory
    DESCRIPTION     
            "This counter keeps track of the number of E4 error
             received from verification server."
    ::= { sonusSoftSwitchHTTPClientVerificationFailureCounters 2 }

sonusSoftSwitchHTTPVerificationFailureE5Counters OBJECT-TYPE
    SYNTAX          Counter
    ACCESS          read-only
    STATUS          mandatory
    DESCRIPTION     
            "This counter keeps track of the number of E5 error
             received from verification server."
    ::= { sonusSoftSwitchHTTPClientVerificationFailureCounters 3 }

sonusSoftSwitchHTTPVerificationFailureE6Counters OBJECT-TYPE
    SYNTAX          Counter
    ACCESS          read-only
    STATUS          mandatory
    DESCRIPTION     
            "This counter keeps track of the number of E6 error
             received from verification server."
    ::= { sonusSoftSwitchHTTPClientVerificationFailureCounters 4 }

sonusSoftSwitchHTTPVerificationFailureE7Counters OBJECT-TYPE
    SYNTAX          Counter
    ACCESS          read-only
    STATUS          mandatory
    DESCRIPTION     
            "This counter keeps track of the number of E7 error
             received from verification server."
    ::= { sonusSoftSwitchHTTPClientVerificationFailureCounters 5 }

sonusSoftSwitchHTTPVerificationFailureE8Counters OBJECT-TYPE
    SYNTAX          Counter
    ACCESS          read-only
    STATUS          mandatory
    DESCRIPTION     
            "This counter keeps track of the number of E8 error
             received from verification server."
    ::= { sonusSoftSwitchHTTPClientVerificationFailureCounters 6 }

sonusSoftSwitchHTTPVerificationFailureE9Counters OBJECT-TYPE
    SYNTAX          Counter
    ACCESS          read-only
    STATUS          mandatory
    DESCRIPTION     
            "This counter keeps track of the number of E9 error
             received from verification server."
    ::= { sonusSoftSwitchHTTPClientVerificationFailureCounters 7 }

sonusSoftSwitchHTTPVerificationFailureE10Counters OBJECT-TYPE
    SYNTAX          Counter
    ACCESS          read-only
    STATUS          mandatory
    DESCRIPTION     
            "This counter keeps track of the number of E10 error
             received from verification server."
    ::= { sonusSoftSwitchHTTPClientVerificationFailureCounters 8 }

sonusSoftSwitchHTTPVerificationFailureE11Counters OBJECT-TYPE
    SYNTAX          Counter
    ACCESS          read-only
    STATUS          mandatory
    DESCRIPTION     
            "This counter keeps track of the number of E11 error
             received from verification server."
    ::= { sonusSoftSwitchHTTPClientVerificationFailureCounters 9 }

sonusSoftSwitchHTTPVerificationFailureE12Counters OBJECT-TYPE
    SYNTAX          Counter
    ACCESS          read-only
    STATUS          mandatory
    DESCRIPTION     
            "This counter keeps track of the number of E12 error
             received from verification server."
    ::= { sonusSoftSwitchHTTPClientVerificationFailureCounters 10 }

sonusSoftSwitchHTTPVerificationFailureE13Counters OBJECT-TYPE
    SYNTAX          Counter
    ACCESS          read-only
    STATUS          mandatory
    DESCRIPTION     
            "This counter keeps track of the number of E13 error
             received from verification server."
    ::= { sonusSoftSwitchHTTPClientVerificationFailureCounters 11 }

sonusSoftSwitchHTTPVerificationFailureE14Counters OBJECT-TYPE
    SYNTAX          Counter
    ACCESS          read-only
    STATUS          mandatory
    DESCRIPTION     
            "This counter keeps track of the number of E14 error
             received from verification server."
    ::= { sonusSoftSwitchHTTPClientVerificationFailureCounters 12 }

sonusSoftSwitchHTTPVerificationFailureE15Counters OBJECT-TYPE
    SYNTAX          Counter
    ACCESS          read-only
    STATUS          mandatory
    DESCRIPTION     
            "This counter keeps track of the number of E15 error
             received from verification server."
    ::= { sonusSoftSwitchHTTPClientVerificationFailureCounters 13 }

sonusSoftSwitchHTTPVerificationFailureE16Counters OBJECT-TYPE
    SYNTAX          Counter
    ACCESS          read-only
    STATUS          mandatory
    DESCRIPTION     
            "This counter keeps track of the number of E16 error
             received from verification server."
    ::= { sonusSoftSwitchHTTPClientVerificationFailureCounters 14 }

sonusSoftSwitchHTTPVerificationFailureE17Counters OBJECT-TYPE
    SYNTAX          Counter
    ACCESS          read-only
    STATUS          mandatory
    DESCRIPTION     
            "This counter keeps track of the number of E17 error
             received from verification server."
    ::= { sonusSoftSwitchHTTPClientVerificationFailureCounters 15 }

sonusSoftSwitchHTTPVerificationFailureE18Counters OBJECT-TYPE
    SYNTAX          Counter
    ACCESS          read-only
    STATUS          mandatory
    DESCRIPTION     
            "This counter keeps track of the number of E18 error
             received from verification server."
    ::= { sonusSoftSwitchHTTPClientVerificationFailureCounters 16 }

sonusSoftSwitchHTTPVerificationFailureE19Counters OBJECT-TYPE
    SYNTAX          Counter
    ACCESS          read-only
    STATUS          mandatory
    DESCRIPTION     
            "This counter keeps track of the number of E19 error
             received from verification server."
    ::= { sonusSoftSwitchHTTPClientVerificationFailureCounters 17 }

sonusSoftSwitchHTTPVerificationFailureE20Counters OBJECT-TYPE
    SYNTAX          Counter
    ACCESS          read-only
    STATUS          mandatory
    DESCRIPTION     
            "This counter keeps track of the number of E20 error
             received from verification server."
    ::= { sonusSoftSwitchHTTPClientVerificationFailureCounters 18 }

sonusSoftSwitchHTTPVerificationFailureE21Counters OBJECT-TYPE
    SYNTAX          Counter
    ACCESS          read-only
    STATUS          mandatory
    DESCRIPTION     
            "This counter keeps track of the number of E21 error
             received from verification server."
    ::= { sonusSoftSwitchHTTPClientVerificationFailureCounters 19 }

sonusSoftSwitchHTTPVerificationFailureE22Counters OBJECT-TYPE
    SYNTAX          Counter
    ACCESS          read-only
    STATUS          mandatory
    DESCRIPTION     
            "This counter keeps track of the number of E22 error
             received from verification server."
    ::= { sonusSoftSwitchHTTPClientVerificationFailureCounters 20 }

sonusSoftSwitchHTTPVerificationFailureE23Counters OBJECT-TYPE
    SYNTAX          Counter
    ACCESS          read-only
    STATUS          mandatory
    DESCRIPTION     
            "This counter keeps track of the number of E23 error
             received from verification server."
    ::= { sonusSoftSwitchHTTPClientVerificationFailureCounters 21 }

sonusSoftSwitchHTTPVerificationFailureX1Counters OBJECT-TYPE
    SYNTAX          Counter
    ACCESS          read-only
    STATUS          mandatory
    DESCRIPTION     
            "This counter keeps track of the number of X1 error
             received from verification server."
    ::= { sonusSoftSwitchHTTPClientVerificationFailureCounters 22 }

sonusSoftSwitchHTTPVerificationFailureX2Counters OBJECT-TYPE
    SYNTAX          Counter
    ACCESS          read-only
    STATUS          mandatory
    DESCRIPTION     
            "This counter keeps track of the number of X2 error
             received from verification server."
    ::= { sonusSoftSwitchHTTPClientVerificationFailureCounters 23 }

sonusSoftSwitchHTTPVerificationFailureX3Counters OBJECT-TYPE
    SYNTAX          Counter
    ACCESS          read-only
    STATUS          mandatory
    DESCRIPTION     
            "This counter keeps track of the number of X3 error
             received from verification server."
    ::= { sonusSoftSwitchHTTPClientVerificationFailureCounters 24 }

sonusSoftSwitchHTTPVerificationFailureX4Counters OBJECT-TYPE
    SYNTAX          Counter
    ACCESS          read-only
    STATUS          mandatory
    DESCRIPTION     
            "This counter keeps track of the number of X4 error
             received from verification server."
    ::= { sonusSoftSwitchHTTPClientVerificationFailureCounters 25 }

sonusSoftSwitchHTTPVerificationFailure400Counters OBJECT-TYPE
    SYNTAX          Counter
    ACCESS          read-only
    STATUS          mandatory
    DESCRIPTION     
            "This counter keeps track of the number of 400 error
             received from verification server."
    ::= { sonusSoftSwitchHTTPClientVerificationFailureCounters 26 }

sonusSoftSwitchHTTPVerificationFailure500Counters OBJECT-TYPE
    SYNTAX          Counter
    ACCESS          read-only
    STATUS          mandatory
    DESCRIPTION     
            "This counter keeps track of the number of 500 error
             received from verification server."
    ::= { sonusSoftSwitchHTTPClientVerificationFailureCounters 27 }

sonusSoftSwitchHTTPVerificationFailure503Counters OBJECT-TYPE
    SYNTAX          Counter
    ACCESS          read-only
    STATUS          mandatory
    DESCRIPTION     
            "This counter keeps track of the number of 503 error
             received from verification server."
    ::= { sonusSoftSwitchHTTPClientVerificationFailureCounters 28 }

sonusSoftSwitchHTTPVerificationFailure405Counters OBJECT-TYPE
    SYNTAX          Counter
    ACCESS          read-only
    STATUS          mandatory
    DESCRIPTION     
            "This counter keeps track of the number of 405 error
             received from verification server."
    ::= { sonusSoftSwitchHTTPClientVerificationFailureCounters 29 }

sonusSoftSwitchHTTPVerificationFailure406Counters OBJECT-TYPE
    SYNTAX          Counter
    ACCESS          read-only
    STATUS          mandatory
    DESCRIPTION     
            "This counter keeps track of the number of 406 error
             received from verification server."
    ::= { sonusSoftSwitchHTTPClientVerificationFailureCounters 30 }

sonusSoftSwitchHTTPVerificationFailure411Counters OBJECT-TYPE
    SYNTAX          Counter
    ACCESS          read-only
    STATUS          mandatory
    DESCRIPTION     
            "This counter keeps track of the number of 411 error
             received from verification server."
    ::= { sonusSoftSwitchHTTPClientVerificationFailureCounters 31 }

sonusSoftSwitchHTTPVerificationFailure415Counters OBJECT-TYPE
    SYNTAX          Counter
    ACCESS          read-only
    STATUS          mandatory
    DESCRIPTION     
            "This counter keeps track of the number of 415 error
             received from verification server."
    ::= { sonusSoftSwitchHTTPClientVerificationFailureCounters 32 }

sonusSoftSwitchHTTPVerificationFailureSVC4000Counters OBJECT-TYPE
    SYNTAX          Counter
    ACCESS          read-only
    STATUS          mandatory
    DESCRIPTION     
            "This counter keeps track of the number of service exception 4000 error
             received from verification server."
    ::= { sonusSoftSwitchHTTPClientVerificationFailureCounters 33 }

sonusSoftSwitchHTTPVerificationFailureSVC4001Counters OBJECT-TYPE
    SYNTAX          Counter
    ACCESS          read-only
    STATUS          mandatory
    DESCRIPTION     
            "This counter keeps track of the number of service exception 4001 error
             received from verification server."
    ::= { sonusSoftSwitchHTTPClientVerificationFailureCounters 34 }

sonusSoftSwitchHTTPVerificationFailureSVC4002Counters OBJECT-TYPE
    SYNTAX          Counter
    ACCESS          read-only
    STATUS          mandatory
    DESCRIPTION     
            "This counter keeps track of the number of service exception 4002 error
             received from verification server."
    ::= { sonusSoftSwitchHTTPClientVerificationFailureCounters 35 }

sonusSoftSwitchHTTPVerificationFailureSVC4003Counters OBJECT-TYPE
    SYNTAX          Counter
    ACCESS          read-only
    STATUS          mandatory
    DESCRIPTION     
            "This counter keeps track of the number of service exception 4003 error
             received from verification server."
    ::= { sonusSoftSwitchHTTPClientVerificationFailureCounters 36 }

sonusSoftSwitchHTTPVerificationFailureSVC4004Counters OBJECT-TYPE
    SYNTAX          Counter
    ACCESS          read-only
    STATUS          mandatory
    DESCRIPTION     
            "This counter keeps track of the number of service exception 4004 error
             received from verification server."
    ::= { sonusSoftSwitchHTTPClientVerificationFailureCounters 37 }

sonusSoftSwitchHTTPVerificationFailureSVC4005Counters OBJECT-TYPE
    SYNTAX          Counter
    ACCESS          read-only
    STATUS          mandatory
    DESCRIPTION     
            "This counter keeps track of the number of service exception 4005 error
             received from verification server."
    ::= { sonusSoftSwitchHTTPClientVerificationFailureCounters 38 }

sonusSoftSwitchHTTPVerificationFailureSVC4006Counters OBJECT-TYPE
    SYNTAX          Counter
    ACCESS          read-only
    STATUS          mandatory
    DESCRIPTION     
            "This counter keeps track of the number of service exception 4006 error
             received from verification server."
    ::= { sonusSoftSwitchHTTPClientVerificationFailureCounters 39 }

sonusSoftSwitchHTTPVerificationFailureSVC4007Counters OBJECT-TYPE
    SYNTAX          Counter
    ACCESS          read-only
    STATUS          mandatory
    DESCRIPTION     
            "This counter keeps track of the number of service exception 4007 error
             received from verification server."
    ::= { sonusSoftSwitchHTTPClientVerificationFailureCounters 40 }

sonusSoftSwitchHTTPVerificationFailurePOL4050Counters OBJECT-TYPE
    SYNTAX          Counter
    ACCESS          read-only
    STATUS          mandatory
    DESCRIPTION     
            "This counter keeps track of the number of policy exception 4050 error
             received from verification server."
    ::= { sonusSoftSwitchHTTPClientVerificationFailureCounters 41 }

sonusSoftSwitchHTTPVerificationFailurePOL5000Counters OBJECT-TYPE
    SYNTAX          Counter
    ACCESS          read-only
    STATUS          mandatory
    DESCRIPTION     
            "This counter keeps track of the number of policy exception 5000 error
             received from verification server."
    ::= { sonusSoftSwitchHTTPClientVerificationFailureCounters 42 }

sonusSoftSwitchHTTPVerificationFailure404Counters OBJECT-TYPE
    SYNTAX          Counter
    ACCESS          read-only
    STATUS          mandatory
    DESCRIPTION     
            "This counter keeps track of the number of 404 error
             received from verification server."
    ::= { sonusSoftSwitchHTTPClientVerificationFailureCounters 43 }

sonusSoftSwitchHTTPClientInternalCounters OBJECT IDENTIFIER
    ::= { sonusSoftSwitchHTTPClientStatistics 5 }

sonusSoftSwitchHTTPNoConnectionAvailableCounters OBJECT-TYPE
    SYNTAX          Counter
    ACCESS          read-only
    STATUS          mandatory
    DESCRIPTION     
            "This counter keeps track of the number of errors with no connection available."
    ::= { sonusSoftSwitchHTTPClientInternalCounters 1 }

sonusSoftSwitchHTTPJsonErrorCounters OBJECT-TYPE
    SYNTAX          Counter
    ACCESS          read-only
    STATUS          mandatory
    DESCRIPTION     
            "This counter keeps track of the number of JSON Error."
    ::= { sonusSoftSwitchHTTPClientInternalCounters 2 }

sonusSoftSwitchHTTPCurlErrorCounters OBJECT-TYPE
    SYNTAX          Counter
    ACCESS          read-only
    STATUS          mandatory
    DESCRIPTION     
            "This counter keeps track of the number of HTTP Error."
    ::= { sonusSoftSwitchHTTPClientInternalCounters 3 }

sonusSoftSwitchHTTPMaxRetriesExhaustedCounters OBJECT-TYPE
    SYNTAX          Counter
    ACCESS          read-only
    STATUS          mandatory
    DESCRIPTION     
            "This counter keeps track of the number of failures due to Max Retries Exhausted."
    ::= { sonusSoftSwitchHTTPClientInternalCounters 4 }

sonusSoftSwitchHTTPGeneralFailureCounters OBJECT-TYPE
    SYNTAX          Counter
    ACCESS          read-only
    STATUS          mandatory
    DESCRIPTION     
            "This counter keeps track of the number of General Failure."
    ::= { sonusSoftSwitchHTTPClientInternalCounters 5 }

sonusSoftSwitchPerFqdnCounters OBJECT IDENTIFIER
    ::= { sonusSoftSwitchHTTPClientStatistics 6 }

sonusSoftSwitchPerFqdnCountersTable OBJECT-TYPE
    SYNTAX          SEQUENCE OF SonusSoftSwitchFqdnCountersEntry
    ACCESS          not-accessible
    STATUS          mandatory
    DESCRIPTION     
            "FQDN Counters PER FQDN Server"
    ::= { sonusSoftSwitchPerFqdnCounters 1 }

sonusSoftSwitchFqdnCountersEntry OBJECT-TYPE
    SYNTAX          SonusSoftSwitchFqdnCountersEntry
    ACCESS          not-accessible
    STATUS          mandatory
    DESCRIPTION     
            "An entry of Traffic counters related to FQDN Servers"
    INDEX           { sonusSoftSwitchPerFqdnCountersFqdnName }
    ::= { sonusSoftSwitchPerFqdnCountersTable 1 }

SonusSoftSwitchFqdnCountersEntry ::=
    SEQUENCE {
        sonusSoftSwitchPerFqdnCountersFqdnName      DisplayString,
        sonusSoftSwitchPerFqdnCountersRequestsSent          Counter,
        sonusSoftSwitchPerFqdnCountersResponsesRcvd           Counter,
        sonusSoftSwitchPerFqdnCounters400Rcvd     Counter,
        sonusSoftSwitchPerFqdnCounters500Rcvd     Counter,
        sonusSoftSwitchPerFqdnCounters503Rcvd     Counter,
        sonusSoftSwitchPerFqdnCountersTimeouts      Counter,
        sonusSoftSwitchPerFqdnCountersNoConnAvailable             Counter,
        sonusSoftSwitchPerFqdnCountersJsonErr     Counter,
        sonusSoftSwitchPerFqdnCountersHttpErr     Counter,
        sonusSoftSwitchPerFqdnCountersMaxRetryExhausted               Counter,
        sonusSoftSwitchPerFqdnCountersGenFailure        Counter,
        sonusSoftSwitchPerFqdnCounters403Rcvd     Counter
    }

sonusSoftSwitchPerFqdnCountersFqdnName OBJECT-TYPE
    SYNTAX          DisplayString
    ACCESS          read-only
    STATUS          mandatory
    DESCRIPTION     
            "FQDN Name."
    ::= { sonusSoftSwitchFqdnCountersEntry 1 }

sonusSoftSwitchPerFqdnCountersRequestsSent OBJECT-TYPE
    SYNTAX          Counter
    ACCESS          read-only
    STATUS          mandatory
    DESCRIPTION     
            "This counter keeps track of the number of requests
             which have been sent by the http process counted for each Fqdn"
    ::= { sonusSoftSwitchFqdnCountersEntry 2 }

sonusSoftSwitchPerFqdnCountersResponsesRcvd OBJECT-TYPE
    SYNTAX          Counter
    ACCESS          read-only
    STATUS          mandatory
    DESCRIPTION     
            "This counter keeps track of the number of responses
             which have been received by the http process counted for each Fqdn "
    ::= { sonusSoftSwitchFqdnCountersEntry 3 }

sonusSoftSwitchPerFqdnCounters400Rcvd OBJECT-TYPE
    SYNTAX          Counter
    ACCESS          read-only
    STATUS          mandatory
    DESCRIPTION     
            "This counter keeps track of the number of 400 responses
             which have been received by the http process counted for each Fqdn "
    ::= { sonusSoftSwitchFqdnCountersEntry 4 }

sonusSoftSwitchPerFqdnCounters500Rcvd OBJECT-TYPE
    SYNTAX          Counter
    ACCESS          read-only
    STATUS          mandatory
    DESCRIPTION     
            "This counter keeps track of the number of 500 responses
             which have been received by the http process counted for each Fqdn "
    ::= { sonusSoftSwitchFqdnCountersEntry 5 }

sonusSoftSwitchPerFqdnCounters503Rcvd OBJECT-TYPE
    SYNTAX          Counter
    ACCESS          read-only
    STATUS          mandatory
    DESCRIPTION     
            "This counter keeps track of the number of 503 responses
             which have been received by the http process counted for each Fqdn "
    ::= { sonusSoftSwitchFqdnCountersEntry 6 }

sonusSoftSwitchPerFqdnCountersTimeouts OBJECT-TYPE
    SYNTAX          Counter
    ACCESS          read-only
    STATUS          mandatory
    DESCRIPTION     
            "This counter keeps track of the number of Timeouts "
    ::= { sonusSoftSwitchFqdnCountersEntry 7 }

sonusSoftSwitchPerFqdnCountersNoConnAvailable OBJECT-TYPE
    SYNTAX          Counter
    ACCESS          read-only
    STATUS          mandatory
    DESCRIPTION     
            "This counter keeps track of the number of No Connections Available "
    ::= { sonusSoftSwitchFqdnCountersEntry 8 }

sonusSoftSwitchPerFqdnCountersJsonErr OBJECT-TYPE
    SYNTAX          Counter
    ACCESS          read-only
    STATUS          mandatory
    DESCRIPTION     
            "This counter keeps track of the number of JSON Error "
    ::= { sonusSoftSwitchFqdnCountersEntry 9 }

sonusSoftSwitchPerFqdnCountersHttpErr OBJECT-TYPE
    SYNTAX          Counter
    ACCESS          read-only
    STATUS          mandatory
    DESCRIPTION     
            "This counter keeps track of the number of HTTP Error "
    ::= { sonusSoftSwitchFqdnCountersEntry 10 }

sonusSoftSwitchPerFqdnCountersMaxRetryExhausted OBJECT-TYPE
    SYNTAX          Counter
    ACCESS          read-only
    STATUS          mandatory
    DESCRIPTION     
            "This counter keeps track of the number of Failures due to Max Retry Exhausted "
    ::= { sonusSoftSwitchFqdnCountersEntry 11 }

sonusSoftSwitchPerFqdnCountersGenFailure OBJECT-TYPE
    SYNTAX          Counter
    ACCESS          read-only
    STATUS          mandatory
    DESCRIPTION     
            "This counter keeps track of the number of General Failures"
    ::= { sonusSoftSwitchFqdnCountersEntry 12 }

sonusSoftSwitchPerFqdnCounters403Rcvd OBJECT-TYPE
    SYNTAX          Counter
    ACCESS          read-only
    STATUS          mandatory
    DESCRIPTION     
            "This counter keeps track of the number of 403 responses
             which have been received by the http process counted for each Fqdn "
    ::= { sonusSoftSwitchFqdnCountersEntry 13 }

sonusSoftSwitchHTTPClientPerServerIpCounters OBJECT IDENTIFIER
    ::= { sonusSoftSwitchHTTPClientStatistics 7 }

sonusSoftSwitchHTTPClientPerIpCountersTable OBJECT-TYPE
    SYNTAX          SEQUENCE OF SonusSoftSwitchHTTPClientPerIpCountersEntry
    ACCESS          not-accessible
    STATUS          mandatory
    DESCRIPTION     
            "HTTP Client counters per IP"
    ::= { sonusSoftSwitchHTTPClientPerServerIpCounters 1 }

sonusSoftSwitchHTTPClientPerIpCountersEntry OBJECT-TYPE
    SYNTAX          SonusSoftSwitchHTTPClientPerIpCountersEntry
    ACCESS          not-accessible
    STATUS          mandatory
    DESCRIPTION     
            "An entry of Traffic counters related to Stir IP Servers"
    INDEX           { sonusSoftSwitchHTTPClientPerIpCountersIpAddrType, 
                      sonusSoftSwitchHTTPClientPerIpCountersIpAddr, 
                      sonusSoftSwitchHTTPClientPerIpCountersIpPort }
    ::= { sonusSoftSwitchHTTPClientPerIpCountersTable 1 }

SonusSoftSwitchHTTPClientPerIpCountersEntry ::=
    SEQUENCE {
        sonusSoftSwitchHTTPClientPerIpCountersIpAddrType                InetAddressType,
        sonusSoftSwitchHTTPClientPerIpCountersIpAddr            InetAddress,
        sonusSoftSwitchHTTPClientPerIpCountersIpPort            INTEGER,
        sonusSoftSwitchHTTPClientPerIpCountersMaxConnTime                 Gauge,
        sonusSoftSwitchHTTPClientPerIpCountersMinConnTime                 Gauge,
        sonusSoftSwitchHTTPClientPerIpCountersAvgConnTime                 Gauge,
        sonusSoftSwitchHTTPClientPerIpCountersMaxRespTime                 Gauge,
        sonusSoftSwitchHTTPClientPerIpCountersMinRespTime                 Gauge,
        sonusSoftSwitchHTTPClientPerIpCountersAvgRespTime                 Gauge
    }

sonusSoftSwitchHTTPClientPerIpCountersIpAddrType OBJECT-TYPE
    SYNTAX          InetAddressType
    ACCESS          read-only
    STATUS          mandatory
    DESCRIPTION     
            "The Server IP address Type."
    ::= { sonusSoftSwitchHTTPClientPerIpCountersEntry 1 }

sonusSoftSwitchHTTPClientPerIpCountersIpAddr OBJECT-TYPE
    SYNTAX          InetAddress
    ACCESS          read-only
    STATUS          mandatory
    DESCRIPTION     
            " IP address of STIR Server"
    ::= { sonusSoftSwitchHTTPClientPerIpCountersEntry 2 }

sonusSoftSwitchHTTPClientPerIpCountersIpPort OBJECT-TYPE
    SYNTAX          INTEGER
    ACCESS          read-only
    STATUS          mandatory
    DESCRIPTION     
            "The Port on which server is listening."
    ::= { sonusSoftSwitchHTTPClientPerIpCountersEntry 3 }

sonusSoftSwitchHTTPClientPerIpCountersMaxConnTime OBJECT-TYPE
    SYNTAX          Gauge
    ACCESS          read-only
    STATUS          mandatory
    DESCRIPTION     
            "This counter keeps track of the maximum time taken to establish a connection."
    ::= { sonusSoftSwitchHTTPClientPerIpCountersEntry 4 }

sonusSoftSwitchHTTPClientPerIpCountersMinConnTime OBJECT-TYPE
    SYNTAX          Gauge
    ACCESS          read-only
    STATUS          mandatory
    DESCRIPTION     
            "This counter keeps track of the minimum time taken to establish a connection."
    ::= { sonusSoftSwitchHTTPClientPerIpCountersEntry 5 }

sonusSoftSwitchHTTPClientPerIpCountersAvgConnTime OBJECT-TYPE
    SYNTAX          Gauge
    ACCESS          read-only
    STATUS          mandatory
    DESCRIPTION     
            "This counter keeps track of the average time taken to establish a connection."
    ::= { sonusSoftSwitchHTTPClientPerIpCountersEntry 6 }

sonusSoftSwitchHTTPClientPerIpCountersMaxRespTime OBJECT-TYPE
    SYNTAX          Gauge
    ACCESS          read-only
    STATUS          mandatory
    DESCRIPTION     
            "This counter keeps track of the maximum time taken for the server response."
    ::= { sonusSoftSwitchHTTPClientPerIpCountersEntry 7 }

sonusSoftSwitchHTTPClientPerIpCountersMinRespTime OBJECT-TYPE
    SYNTAX          Gauge
    ACCESS          read-only
    STATUS          mandatory
    DESCRIPTION     
            "This counter keeps track of the minimum time taken for the server response."
    ::= { sonusSoftSwitchHTTPClientPerIpCountersEntry 8 }

sonusSoftSwitchHTTPClientPerIpCountersAvgRespTime OBJECT-TYPE
    SYNTAX          Gauge
    ACCESS          read-only
    STATUS          mandatory
    DESCRIPTION     
            "This counter keeps track of the average time taken for the server response."
    ::= { sonusSoftSwitchHTTPClientPerIpCountersEntry 9 }

sonusSoftSwitchHTTPPerSvrTypeSignVerCounters OBJECT IDENTIFIER
    ::= { sonusSoftSwitchHTTPClientStatistics 8 }

sonusSoftSwitchHTTPPerSvrTypeSignVerCountersTable OBJECT-TYPE
    SYNTAX          SEQUENCE OF SonusSoftSwitchHTTPPerSvrTypeSignVerCountersEntry
    ACCESS          not-accessible
    STATUS          mandatory
    DESCRIPTION     
            "HTTP Client Signing Verification Counters Per Server Type"
    ::= { sonusSoftSwitchHTTPPerSvrTypeSignVerCounters 1 }

sonusSoftSwitchHTTPPerSvrTypeSignVerCountersEntry OBJECT-TYPE
    SYNTAX          SonusSoftSwitchHTTPPerSvrTypeSignVerCountersEntry
    ACCESS          not-accessible
    STATUS          mandatory
    DESCRIPTION     
            "An entry of Traffic counters related to FQDN Servers"
    INDEX           { 
                      sonusSoftSwitchHTTPPerSvrTypeSignVerCountersSignVerServerName }
    ::= { sonusSoftSwitchHTTPPerSvrTypeSignVerCountersTable 1 }

SonusSoftSwitchHTTPPerSvrTypeSignVerCountersEntry ::=
    SEQUENCE {
        sonusSoftSwitchHTTPPerSvrTypeSignVerCountersSignVerServerName                             DisplayString,
        sonusSoftSwitchHTTPPerSvrTypeSignVerCountersSigningQuerySent                            Counter,
        sonusSoftSwitchHTTPPerSvrTypeSignVerCountersSigningRsp                      Counter,
        sonusSoftSwitchHTTPPerSvrTypeSignVerCountersSigningInvalidInput                               Counter,
        sonusSoftSwitchHTTPPerSvrTypeSignVerCountersSigningQueryTimeOut                               Counter,
        sonusSoftSwitchHTTPPerSvrTypeSignVerCountersSigningQueryRetry                             Counter,
        sonusSoftSwitchHTTPPerSvrTypeSignVerCountersVerQuerySent                        Counter,
        sonusSoftSwitchHTTPPerSvrTypeSignVerCountersVerificationRsp                           Counter,
        sonusSoftSwitchHTTPPerSvrTypeSignVerCountersVerInvalidInput                           Counter,
        sonusSoftSwitchHTTPPerSvrTypeSignVerCountersVerQueryTimeOut                           Counter,
        sonusSoftSwitchHTTPPerSvrTypeSignVerCountersVerQueryRetry                         Counter
    }

sonusSoftSwitchHTTPPerSvrTypeSignVerCountersSignVerServerName OBJECT-TYPE
    SYNTAX          DisplayString
    ACCESS          read-only
    STATUS          mandatory
    DESCRIPTION     
            "Server Type Name."
    ::= { sonusSoftSwitchHTTPPerSvrTypeSignVerCountersEntry 1 }

sonusSoftSwitchHTTPPerSvrTypeSignVerCountersSigningQuerySent OBJECT-TYPE
    SYNTAX          Counter
    ACCESS          read-only
    STATUS          mandatory
    DESCRIPTION     
            "This counter keeps track of the number of Signing requests 
             which are sent from HTTP Client Process Per Server Type."
    ::= { sonusSoftSwitchHTTPPerSvrTypeSignVerCountersEntry 2 }

sonusSoftSwitchHTTPPerSvrTypeSignVerCountersSigningRsp OBJECT-TYPE
    SYNTAX          Counter
    ACCESS          read-only
    STATUS          mandatory
    DESCRIPTION     
            "This counter keeps track of the number of Signing responses 
             which have been received by HTTP Client process Per Server Type."
    ::= { sonusSoftSwitchHTTPPerSvrTypeSignVerCountersEntry 3 }

sonusSoftSwitchHTTPPerSvrTypeSignVerCountersSigningInvalidInput OBJECT-TYPE
    SYNTAX          Counter
    ACCESS          read-only
    STATUS          mandatory
    DESCRIPTION     
            "This counter keeps track of the number of signing requests 
             which failed due to invalid input Per Server Type."
    ::= { sonusSoftSwitchHTTPPerSvrTypeSignVerCountersEntry 4 }

sonusSoftSwitchHTTPPerSvrTypeSignVerCountersSigningQueryTimeOut OBJECT-TYPE
    SYNTAX          Counter
    ACCESS          read-only
    STATUS          mandatory
    DESCRIPTION     
            "This counter keeps track of the number of signing requests 
             which have timeout for response Per Server Type."
    ::= { sonusSoftSwitchHTTPPerSvrTypeSignVerCountersEntry 5 }

sonusSoftSwitchHTTPPerSvrTypeSignVerCountersSigningQueryRetry OBJECT-TYPE
    SYNTAX          Counter
    ACCESS          read-only
    STATUS          mandatory
    DESCRIPTION     
            "This counter keeps track of the number of Signing requests
             which are retried from HTTP Client Process Per Server Type."
    ::= { sonusSoftSwitchHTTPPerSvrTypeSignVerCountersEntry 6 }

sonusSoftSwitchHTTPPerSvrTypeSignVerCountersVerQuerySent OBJECT-TYPE
    SYNTAX          Counter
    ACCESS          read-only
    STATUS          mandatory
    DESCRIPTION     
            "This counter keeps track of the number of Verification requests
             which are sent from HTTP Client Process."
    ::= { sonusSoftSwitchHTTPPerSvrTypeSignVerCountersEntry 7 }

sonusSoftSwitchHTTPPerSvrTypeSignVerCountersVerificationRsp OBJECT-TYPE
    SYNTAX          Counter
    ACCESS          read-only
    STATUS          mandatory
    DESCRIPTION     
            "This counter keeps track of the number of Verification responses
             which have been received by HTTP Client process."
    ::= { sonusSoftSwitchHTTPPerSvrTypeSignVerCountersEntry 8 }

sonusSoftSwitchHTTPPerSvrTypeSignVerCountersVerInvalidInput OBJECT-TYPE
    SYNTAX          Counter
    ACCESS          read-only
    STATUS          mandatory
    DESCRIPTION     
            "This counter keeps track of the number of Verification requests
             which failed due to invalid input."
    ::= { sonusSoftSwitchHTTPPerSvrTypeSignVerCountersEntry 9 }

sonusSoftSwitchHTTPPerSvrTypeSignVerCountersVerQueryTimeOut OBJECT-TYPE
    SYNTAX          Counter
    ACCESS          read-only
    STATUS          mandatory
    DESCRIPTION     
            "This counter keeps track of the number of Verification requests
             which have timeout for response."
    ::= { sonusSoftSwitchHTTPPerSvrTypeSignVerCountersEntry 10 }

sonusSoftSwitchHTTPPerSvrTypeSignVerCountersVerQueryRetry OBJECT-TYPE
    SYNTAX          Counter
    ACCESS          read-only
    STATUS          mandatory
    DESCRIPTION     
            "This counter keeps track of the number of Verification requests
             which are retried from HTTP Client Process."
    ::= { sonusSoftSwitchHTTPPerSvrTypeSignVerCountersEntry 11 }

sonusSoftSwitchHTTPPerSvrTypeFailureCounters OBJECT IDENTIFIER
    ::= { sonusSoftSwitchHTTPClientStatistics 9 }

sonusSoftSwitchHTTPPerSvrTypeFailureCountersTable OBJECT-TYPE
    SYNTAX          SEQUENCE OF SonusSoftSwitchHTTPPerSvrTypeFailureCountersEntry
    ACCESS          not-accessible
    STATUS          mandatory
    DESCRIPTION     
            "HTTP Client Signing-Verification Failure Counters PER Server Type"
    ::= { sonusSoftSwitchHTTPPerSvrTypeFailureCounters 1 }

sonusSoftSwitchHTTPPerSvrTypeFailureCountersEntry OBJECT-TYPE
    SYNTAX          SonusSoftSwitchHTTPPerSvrTypeFailureCountersEntry
    ACCESS          not-accessible
    STATUS          mandatory
    DESCRIPTION     
            "An entry of Traffic counters related to HTTP Client Verification Counters Per Server Type"
    INDEX           { 
                      sonusSoftSwitchHTTPPerSvrTypeFailureCountersServerName }
    ::= { sonusSoftSwitchHTTPPerSvrTypeFailureCountersTable 1 }

SonusSoftSwitchHTTPPerSvrTypeFailureCountersEntry ::=
    SEQUENCE {
        sonusSoftSwitchHTTPPerSvrTypeFailureCountersServerName                      DisplayString,
        sonusSoftSwitchHTTPPerSvrTypeFailureCountersSignFailureE3                         Counter,
        sonusSoftSwitchHTTPPerSvrTypeFailureCountersSignFailureX1                         Counter,
        sonusSoftSwitchHTTPPerSvrTypeFailureCountersSignFailureX2                         Counter,
        sonusSoftSwitchHTTPPerSvrTypeFailureCountersSignFailureX3                         Counter,
        sonusSoftSwitchHTTPPerSvrTypeFailureCountersSignFailureX4                         Counter,
        sonusSoftSwitchHTTPPerSvrTypeFailureCountersSignFailure400                          Counter,
        sonusSoftSwitchHTTPPerSvrTypeFailureCountersSignFailure404                          Counter,
        sonusSoftSwitchHTTPPerSvrTypeFailureCountersSignFailure405                          Counter,
        sonusSoftSwitchHTTPPerSvrTypeFailureCountersSignFailure406                          Counter,
        sonusSoftSwitchHTTPPerSvrTypeFailureCountersSignFailure411                          Counter,
        sonusSoftSwitchHTTPPerSvrTypeFailureCountersSignFailure415                          Counter,
        sonusSoftSwitchHTTPPerSvrTypeFailureCountersSignFailure500                          Counter,
        sonusSoftSwitchHTTPPerSvrTypeFailureCountersSignFailure503                          Counter,
        sonusSoftSwitchHTTPPerSvrTypeFailureCountersSignFailureSVC4000                              Counter,
        sonusSoftSwitchHTTPPerSvrTypeFailureCountersSignFailureSVC4001                              Counter,
        sonusSoftSwitchHTTPPerSvrTypeFailureCountersSignFailureSVC4002                              Counter,
        sonusSoftSwitchHTTPPerSvrTypeFailureCountersSignFailureSVC4003                              Counter,
        sonusSoftSwitchHTTPPerSvrTypeFailureCountersSignFailureSVC4004                              Counter,
        sonusSoftSwitchHTTPPerSvrTypeFailureCountersSignFailureSVC4005                              Counter,
        sonusSoftSwitchHTTPPerSvrTypeFailureCountersSignFailureSVC4006                              Counter,
        sonusSoftSwitchHTTPPerSvrTypeFailureCountersSignFailureSVC4007                              Counter,
        sonusSoftSwitchHTTPPerSvrTypeFailureCountersSignFailurePOL4050                              Counter,
        sonusSoftSwitchHTTPPerSvrTypeFailureCountersSignFailurePOL5000                              Counter,
        sonusSoftSwitchHTTPPerSvrTypeFailureCountersVerFailureE3                        Counter,
        sonusSoftSwitchHTTPPerSvrTypeFailureCountersVerFailureE4                        Counter,
        sonusSoftSwitchHTTPPerSvrTypeFailureCountersVerFailureE5                        Counter,
        sonusSoftSwitchHTTPPerSvrTypeFailureCountersVerFailureE6                        Counter,
        sonusSoftSwitchHTTPPerSvrTypeFailureCountersVerFailureE7                        Counter,
        sonusSoftSwitchHTTPPerSvrTypeFailureCountersVerFailureE8                        Counter,
        sonusSoftSwitchHTTPPerSvrTypeFailureCountersVerFailureE9                        Counter,
        sonusSoftSwitchHTTPPerSvrTypeFailureCountersVerFailureE10                         Counter,
        sonusSoftSwitchHTTPPerSvrTypeFailureCountersVerFailureE11                         Counter,
        sonusSoftSwitchHTTPPerSvrTypeFailureCountersVerFailureE12                         Counter,
        sonusSoftSwitchHTTPPerSvrTypeFailureCountersVerFailureE13                         Counter,
        sonusSoftSwitchHTTPPerSvrTypeFailureCountersVerFailureE14                         Counter,
        sonusSoftSwitchHTTPPerSvrTypeFailureCountersVerFailureE15                         Counter,
        sonusSoftSwitchHTTPPerSvrTypeFailureCountersVerFailureE16                         Counter,
        sonusSoftSwitchHTTPPerSvrTypeFailureCountersVerFailureE17                         Counter,
        sonusSoftSwitchHTTPPerSvrTypeFailureCountersVerFailureE18                         Counter,
        sonusSoftSwitchHTTPPerSvrTypeFailureCountersVerFailureE19                         Counter,
        sonusSoftSwitchHTTPPerSvrTypeFailureCountersVerFailureE20                         Counter,
        sonusSoftSwitchHTTPPerSvrTypeFailureCountersVerFailureE21                         Counter,
        sonusSoftSwitchHTTPPerSvrTypeFailureCountersVerFailureE22                         Counter,
        sonusSoftSwitchHTTPPerSvrTypeFailureCountersVerFailureE23                         Counter,
        sonusSoftSwitchHTTPPerSvrTypeFailureCountersVerFailureX1                        Counter,
        sonusSoftSwitchHTTPPerSvrTypeFailureCountersVerFailureX2                        Counter,
        sonusSoftSwitchHTTPPerSvrTypeFailureCountersVerFailureX3                        Counter,
        sonusSoftSwitchHTTPPerSvrTypeFailureCountersVerFailureX4                        Counter,
        sonusSoftSwitchHTTPPerSvrTypeFailureCountersVerFailure400                         Counter,
        sonusSoftSwitchHTTPPerSvrTypeFailureCountersVerFailure404                         Counter,
        sonusSoftSwitchHTTPPerSvrTypeFailureCountersVerFailure405                         Counter,
        sonusSoftSwitchHTTPPerSvrTypeFailureCountersVerFailure406                         Counter,
        sonusSoftSwitchHTTPPerSvrTypeFailureCountersVerFailure411                         Counter,
        sonusSoftSwitchHTTPPerSvrTypeFailureCountersVerFailure415                         Counter,
        sonusSoftSwitchHTTPPerSvrTypeFailureCountersVerFailure500                         Counter,
        sonusSoftSwitchHTTPPerSvrTypeFailureCountersVerFailure503                         Counter,
        sonusSoftSwitchHTTPPerSvrTypeFailureCountersVerFailureSVC4000                             Counter,
        sonusSoftSwitchHTTPPerSvrTypeFailureCountersVerFailureSVC4001                             Counter,
        sonusSoftSwitchHTTPPerSvrTypeFailureCountersVerFailureSVC4002                             Counter,
        sonusSoftSwitchHTTPPerSvrTypeFailureCountersVerFailureSVC4003                             Counter,
        sonusSoftSwitchHTTPPerSvrTypeFailureCountersVerFailureSVC4004                             Counter,
        sonusSoftSwitchHTTPPerSvrTypeFailureCountersVerFailureSVC4005                             Counter,
        sonusSoftSwitchHTTPPerSvrTypeFailureCountersVerFailureSVC4006                             Counter,
        sonusSoftSwitchHTTPPerSvrTypeFailureCountersVerFailureSVC4007                             Counter,
        sonusSoftSwitchHTTPPerSvrTypeFailureCountersVerFailurePOL4050                             Counter,
        sonusSoftSwitchHTTPPerSvrTypeFailureCountersVerFailurePOL5000                             Counter
    }

sonusSoftSwitchHTTPPerSvrTypeFailureCountersServerName OBJECT-TYPE
    SYNTAX          DisplayString
    ACCESS          read-only
    STATUS          mandatory
    DESCRIPTION     
            "Server Type Name."
    ::= { sonusSoftSwitchHTTPPerSvrTypeFailureCountersEntry 1 }

sonusSoftSwitchHTTPPerSvrTypeFailureCountersSignFailureE3 OBJECT-TYPE
    SYNTAX          Counter
    ACCESS          read-only
    STATUS          mandatory
    DESCRIPTION     
            "This counter keeps track of the number of E3 error 
             received from signing server per server type."
    ::= { sonusSoftSwitchHTTPPerSvrTypeFailureCountersEntry 2 }

sonusSoftSwitchHTTPPerSvrTypeFailureCountersSignFailureX1 OBJECT-TYPE
    SYNTAX          Counter
    ACCESS          read-only
    STATUS          mandatory
    DESCRIPTION     
            "This counter keeps track of the number of X1 error 
             received from signing server per server type."
    ::= { sonusSoftSwitchHTTPPerSvrTypeFailureCountersEntry 3 }

sonusSoftSwitchHTTPPerSvrTypeFailureCountersSignFailureX2 OBJECT-TYPE
    SYNTAX          Counter
    ACCESS          read-only
    STATUS          mandatory
    DESCRIPTION     
            "This counter keeps track of the number of X2 error 
             received from signing server per server type."
    ::= { sonusSoftSwitchHTTPPerSvrTypeFailureCountersEntry 4 }

sonusSoftSwitchHTTPPerSvrTypeFailureCountersSignFailureX3 OBJECT-TYPE
    SYNTAX          Counter
    ACCESS          read-only
    STATUS          mandatory
    DESCRIPTION     
            "This counter keeps track of the number of X3 error 
             received from signing server per server type."
    ::= { sonusSoftSwitchHTTPPerSvrTypeFailureCountersEntry 5 }

sonusSoftSwitchHTTPPerSvrTypeFailureCountersSignFailureX4 OBJECT-TYPE
    SYNTAX          Counter
    ACCESS          read-only
    STATUS          mandatory
    DESCRIPTION     
            "This counter keeps track of the number of X4 error 
             received from signing server per server type."
    ::= { sonusSoftSwitchHTTPPerSvrTypeFailureCountersEntry 6 }

sonusSoftSwitchHTTPPerSvrTypeFailureCountersSignFailure400 OBJECT-TYPE
    SYNTAX          Counter
    ACCESS          read-only
    STATUS          mandatory
    DESCRIPTION     
            "This counter keeps track of the number of 400 error
             received from signing server per server type."
    ::= { sonusSoftSwitchHTTPPerSvrTypeFailureCountersEntry 7 }

sonusSoftSwitchHTTPPerSvrTypeFailureCountersSignFailure404 OBJECT-TYPE
    SYNTAX          Counter
    ACCESS          read-only
    STATUS          mandatory
    DESCRIPTION     
            "This counter keeps track of the number of 404 error
             received from signing server per server type."
    ::= { sonusSoftSwitchHTTPPerSvrTypeFailureCountersEntry 8 }

sonusSoftSwitchHTTPPerSvrTypeFailureCountersSignFailure405 OBJECT-TYPE
    SYNTAX          Counter
    ACCESS          read-only
    STATUS          mandatory
    DESCRIPTION     
            "This counter keeps track of the number of 405 error
             received from signing server per server type."
    ::= { sonusSoftSwitchHTTPPerSvrTypeFailureCountersEntry 9 }

sonusSoftSwitchHTTPPerSvrTypeFailureCountersSignFailure406 OBJECT-TYPE
    SYNTAX          Counter
    ACCESS          read-only
    STATUS          mandatory
    DESCRIPTION     
            "This counter keeps track of the number of 406 error
             received from signing server per server type."
    ::= { sonusSoftSwitchHTTPPerSvrTypeFailureCountersEntry 10 }

sonusSoftSwitchHTTPPerSvrTypeFailureCountersSignFailure411 OBJECT-TYPE
    SYNTAX          Counter
    ACCESS          read-only
    STATUS          mandatory
    DESCRIPTION     
            "This counter keeps track of the number of 411 error
             received from signing server per server type."
    ::= { sonusSoftSwitchHTTPPerSvrTypeFailureCountersEntry 11 }

sonusSoftSwitchHTTPPerSvrTypeFailureCountersSignFailure415 OBJECT-TYPE
    SYNTAX          Counter
    ACCESS          read-only
    STATUS          mandatory
    DESCRIPTION     
            "This counter keeps track of the number of 415 error
             received from signing server per server type."
    ::= { sonusSoftSwitchHTTPPerSvrTypeFailureCountersEntry 12 }

sonusSoftSwitchHTTPPerSvrTypeFailureCountersSignFailure500 OBJECT-TYPE
    SYNTAX          Counter
    ACCESS          read-only
    STATUS          mandatory
    DESCRIPTION     
            "This counter keeps track of the number of 500 error 
             received from signing server per server type."
    ::= { sonusSoftSwitchHTTPPerSvrTypeFailureCountersEntry 13 }

sonusSoftSwitchHTTPPerSvrTypeFailureCountersSignFailure503 OBJECT-TYPE
    SYNTAX          Counter
    ACCESS          read-only
    STATUS          mandatory
    DESCRIPTION     
            "This counter keeps track of the number of 503 error 
             received from signing server per server type."
    ::= { sonusSoftSwitchHTTPPerSvrTypeFailureCountersEntry 14 }

sonusSoftSwitchHTTPPerSvrTypeFailureCountersSignFailureSVC4000 OBJECT-TYPE
    SYNTAX          Counter
    ACCESS          read-only
    STATUS          mandatory
    DESCRIPTION     
            "This counter keeps track of the number of service exception 4000 error
             received from signing server per server type."
    ::= { sonusSoftSwitchHTTPPerSvrTypeFailureCountersEntry 15 }

sonusSoftSwitchHTTPPerSvrTypeFailureCountersSignFailureSVC4001 OBJECT-TYPE
    SYNTAX          Counter
    ACCESS          read-only
    STATUS          mandatory
    DESCRIPTION     
            "This counter keeps track of the number of service exception 4001 error
             received from signing server per server type."
    ::= { sonusSoftSwitchHTTPPerSvrTypeFailureCountersEntry 16 }

sonusSoftSwitchHTTPPerSvrTypeFailureCountersSignFailureSVC4002 OBJECT-TYPE
    SYNTAX          Counter
    ACCESS          read-only
    STATUS          mandatory
    DESCRIPTION     
            "This counter keeps track of the number of service exception 4002 error
             received from signing server per server type."
    ::= { sonusSoftSwitchHTTPPerSvrTypeFailureCountersEntry 17 }

sonusSoftSwitchHTTPPerSvrTypeFailureCountersSignFailureSVC4003 OBJECT-TYPE
    SYNTAX          Counter
    ACCESS          read-only
    STATUS          mandatory
    DESCRIPTION     
            "This counter keeps track of the number of service exception 4003 error
             received from signing server per server type."
    ::= { sonusSoftSwitchHTTPPerSvrTypeFailureCountersEntry 18 }

sonusSoftSwitchHTTPPerSvrTypeFailureCountersSignFailureSVC4004 OBJECT-TYPE
    SYNTAX          Counter
    ACCESS          read-only
    STATUS          mandatory
    DESCRIPTION     
            "This counter keeps track of the number of service exception 4004 error
             received from signing server per server type."
    ::= { sonusSoftSwitchHTTPPerSvrTypeFailureCountersEntry 19 }

sonusSoftSwitchHTTPPerSvrTypeFailureCountersSignFailureSVC4005 OBJECT-TYPE
    SYNTAX          Counter
    ACCESS          read-only
    STATUS          mandatory
    DESCRIPTION     
            "This counter keeps track of the number of service exception 4005 error
             received from signing server per server type."
    ::= { sonusSoftSwitchHTTPPerSvrTypeFailureCountersEntry 20 }

sonusSoftSwitchHTTPPerSvrTypeFailureCountersSignFailureSVC4006 OBJECT-TYPE
    SYNTAX          Counter
    ACCESS          read-only
    STATUS          mandatory
    DESCRIPTION     
            "This counter keeps track of the number of service exception 4006 error
             received from signing server per server type."
    ::= { sonusSoftSwitchHTTPPerSvrTypeFailureCountersEntry 21 }

sonusSoftSwitchHTTPPerSvrTypeFailureCountersSignFailureSVC4007 OBJECT-TYPE
    SYNTAX          Counter
    ACCESS          read-only
    STATUS          mandatory
    DESCRIPTION     
            "This counter keeps track of the number of service exception 4007 error
             received from signing server per server type."
    ::= { sonusSoftSwitchHTTPPerSvrTypeFailureCountersEntry 22 }

sonusSoftSwitchHTTPPerSvrTypeFailureCountersSignFailurePOL4050 OBJECT-TYPE
    SYNTAX          Counter
    ACCESS          read-only
    STATUS          mandatory
    DESCRIPTION     
            "This counter keeps track of the number of policy exception 4050 error
             received from signing server per server type."
    ::= { sonusSoftSwitchHTTPPerSvrTypeFailureCountersEntry 23 }

sonusSoftSwitchHTTPPerSvrTypeFailureCountersSignFailurePOL5000 OBJECT-TYPE
    SYNTAX          Counter
    ACCESS          read-only
    STATUS          mandatory
    DESCRIPTION     
            "This counter keeps track of the number of policy exception 5000 error
             received from signing server per server type."
    ::= { sonusSoftSwitchHTTPPerSvrTypeFailureCountersEntry 24 }

sonusSoftSwitchHTTPPerSvrTypeFailureCountersVerFailureE3 OBJECT-TYPE
    SYNTAX          Counter
    ACCESS          read-only
    STATUS          mandatory
    DESCRIPTION     
            "This counter keeps track of the number of E3 error
             received from verification server per server type."
    ::= { sonusSoftSwitchHTTPPerSvrTypeFailureCountersEntry 25 }

sonusSoftSwitchHTTPPerSvrTypeFailureCountersVerFailureE4 OBJECT-TYPE
    SYNTAX          Counter
    ACCESS          read-only
    STATUS          mandatory
    DESCRIPTION     
            "This counter keeps track of the number of E4 error
             received from verification server per server type."
    ::= { sonusSoftSwitchHTTPPerSvrTypeFailureCountersEntry 26 }

sonusSoftSwitchHTTPPerSvrTypeFailureCountersVerFailureE5 OBJECT-TYPE
    SYNTAX          Counter
    ACCESS          read-only
    STATUS          mandatory
    DESCRIPTION     
            "This counter keeps track of the number of E5 error
             received from verification server per server type."
    ::= { sonusSoftSwitchHTTPPerSvrTypeFailureCountersEntry 27 }

sonusSoftSwitchHTTPPerSvrTypeFailureCountersVerFailureE6 OBJECT-TYPE
    SYNTAX          Counter
    ACCESS          read-only
    STATUS          mandatory
    DESCRIPTION     
            "This counter keeps track of the number of E6 error
             received from verification server per server type."
    ::= { sonusSoftSwitchHTTPPerSvrTypeFailureCountersEntry 28 }

sonusSoftSwitchHTTPPerSvrTypeFailureCountersVerFailureE7 OBJECT-TYPE
    SYNTAX          Counter
    ACCESS          read-only
    STATUS          mandatory
    DESCRIPTION     
            "This counter keeps track of the number of E7 error
             received from verification server per server type."
    ::= { sonusSoftSwitchHTTPPerSvrTypeFailureCountersEntry 29 }

sonusSoftSwitchHTTPPerSvrTypeFailureCountersVerFailureE8 OBJECT-TYPE
    SYNTAX          Counter
    ACCESS          read-only
    STATUS          mandatory
    DESCRIPTION     
            "This counter keeps track of the number of E8 error
             received from verification server per server type."
    ::= { sonusSoftSwitchHTTPPerSvrTypeFailureCountersEntry 30 }

sonusSoftSwitchHTTPPerSvrTypeFailureCountersVerFailureE9 OBJECT-TYPE
    SYNTAX          Counter
    ACCESS          read-only
    STATUS          mandatory
    DESCRIPTION     
            "This counter keeps track of the number of E9 error
             received from verification server per server type."
    ::= { sonusSoftSwitchHTTPPerSvrTypeFailureCountersEntry 31 }

sonusSoftSwitchHTTPPerSvrTypeFailureCountersVerFailureE10 OBJECT-TYPE
    SYNTAX          Counter
    ACCESS          read-only
    STATUS          mandatory
    DESCRIPTION     
            "This counter keeps track of the number of E10 error
             received from verification server per server type."
    ::= { sonusSoftSwitchHTTPPerSvrTypeFailureCountersEntry 32 }

sonusSoftSwitchHTTPPerSvrTypeFailureCountersVerFailureE11 OBJECT-TYPE
    SYNTAX          Counter
    ACCESS          read-only
    STATUS          mandatory
    DESCRIPTION     
            "This counter keeps track of the number of E11 error
             received from verification server per server type."
    ::= { sonusSoftSwitchHTTPPerSvrTypeFailureCountersEntry 33 }

sonusSoftSwitchHTTPPerSvrTypeFailureCountersVerFailureE12 OBJECT-TYPE
    SYNTAX          Counter
    ACCESS          read-only
    STATUS          mandatory
    DESCRIPTION     
            "This counter keeps track of the number of E12 error
             received from verification server per server type."
    ::= { sonusSoftSwitchHTTPPerSvrTypeFailureCountersEntry 34 }

sonusSoftSwitchHTTPPerSvrTypeFailureCountersVerFailureE13 OBJECT-TYPE
    SYNTAX          Counter
    ACCESS          read-only
    STATUS          mandatory
    DESCRIPTION     
            "This counter keeps track of the number of E13 error
             received from verification server per server type."
    ::= { sonusSoftSwitchHTTPPerSvrTypeFailureCountersEntry 35 }

sonusSoftSwitchHTTPPerSvrTypeFailureCountersVerFailureE14 OBJECT-TYPE
    SYNTAX          Counter
    ACCESS          read-only
    STATUS          mandatory
    DESCRIPTION     
            "This counter keeps track of the number of E14 error
             received from verification server per server type ."
    ::= { sonusSoftSwitchHTTPPerSvrTypeFailureCountersEntry 36 }

sonusSoftSwitchHTTPPerSvrTypeFailureCountersVerFailureE15 OBJECT-TYPE
    SYNTAX          Counter
    ACCESS          read-only
    STATUS          mandatory
    DESCRIPTION     
            "This counter keeps track of the number of E15 error
             received from verification server per server type."
    ::= { sonusSoftSwitchHTTPPerSvrTypeFailureCountersEntry 37 }

sonusSoftSwitchHTTPPerSvrTypeFailureCountersVerFailureE16 OBJECT-TYPE
    SYNTAX          Counter
    ACCESS          read-only
    STATUS          mandatory
    DESCRIPTION     
            "This counter keeps track of the number of E16 error
             received from verification server per server type."
    ::= { sonusSoftSwitchHTTPPerSvrTypeFailureCountersEntry 38 }

sonusSoftSwitchHTTPPerSvrTypeFailureCountersVerFailureE17 OBJECT-TYPE
    SYNTAX          Counter
    ACCESS          read-only
    STATUS          mandatory
    DESCRIPTION     
            "This counter keeps track of the number of E17 error
             received from verification server per server type."
    ::= { sonusSoftSwitchHTTPPerSvrTypeFailureCountersEntry 39 }

sonusSoftSwitchHTTPPerSvrTypeFailureCountersVerFailureE18 OBJECT-TYPE
    SYNTAX          Counter
    ACCESS          read-only
    STATUS          mandatory
    DESCRIPTION     
            "This counter keeps track of the number of E18 error
             received from verification server per server type."
    ::= { sonusSoftSwitchHTTPPerSvrTypeFailureCountersEntry 40 }

sonusSoftSwitchHTTPPerSvrTypeFailureCountersVerFailureE19 OBJECT-TYPE
    SYNTAX          Counter
    ACCESS          read-only
    STATUS          mandatory
    DESCRIPTION     
            "This counter keeps track of the number of E19 error
             received from verification server per server type."
    ::= { sonusSoftSwitchHTTPPerSvrTypeFailureCountersEntry 41 }

sonusSoftSwitchHTTPPerSvrTypeFailureCountersVerFailureE20 OBJECT-TYPE
    SYNTAX          Counter
    ACCESS          read-only
    STATUS          mandatory
    DESCRIPTION     
            "This counter keeps track of the number of E20 error
             received from verification server per server type."
    ::= { sonusSoftSwitchHTTPPerSvrTypeFailureCountersEntry 42 }

sonusSoftSwitchHTTPPerSvrTypeFailureCountersVerFailureE21 OBJECT-TYPE
    SYNTAX          Counter
    ACCESS          read-only
    STATUS          mandatory
    DESCRIPTION     
            "This counter keeps track of the number of E21 error
             received from verification server per server type."
    ::= { sonusSoftSwitchHTTPPerSvrTypeFailureCountersEntry 43 }

sonusSoftSwitchHTTPPerSvrTypeFailureCountersVerFailureE22 OBJECT-TYPE
    SYNTAX          Counter
    ACCESS          read-only
    STATUS          mandatory
    DESCRIPTION     
            "This counter keeps track of the number of E22 error
             received from verification server per server type."
    ::= { sonusSoftSwitchHTTPPerSvrTypeFailureCountersEntry 44 }

sonusSoftSwitchHTTPPerSvrTypeFailureCountersVerFailureE23 OBJECT-TYPE
    SYNTAX          Counter
    ACCESS          read-only
    STATUS          mandatory
    DESCRIPTION     
            "This counter keeps track of the number of E23 error
             received from verification server per server type."
    ::= { sonusSoftSwitchHTTPPerSvrTypeFailureCountersEntry 45 }

sonusSoftSwitchHTTPPerSvrTypeFailureCountersVerFailureX1 OBJECT-TYPE
    SYNTAX          Counter
    ACCESS          read-only
    STATUS          mandatory
    DESCRIPTION     
            "This counter keeps track of the number of X1 error
             received from verification server per server type."
    ::= { sonusSoftSwitchHTTPPerSvrTypeFailureCountersEntry 46 }

sonusSoftSwitchHTTPPerSvrTypeFailureCountersVerFailureX2 OBJECT-TYPE
    SYNTAX          Counter
    ACCESS          read-only
    STATUS          mandatory
    DESCRIPTION     
            "This counter keeps track of the number of X2 error
             received from verification server per server type."
    ::= { sonusSoftSwitchHTTPPerSvrTypeFailureCountersEntry 47 }

sonusSoftSwitchHTTPPerSvrTypeFailureCountersVerFailureX3 OBJECT-TYPE
    SYNTAX          Counter
    ACCESS          read-only
    STATUS          mandatory
    DESCRIPTION     
            "This counter keeps track of the number of X3 error
             received from verification server per server type."
    ::= { sonusSoftSwitchHTTPPerSvrTypeFailureCountersEntry 48 }

sonusSoftSwitchHTTPPerSvrTypeFailureCountersVerFailureX4 OBJECT-TYPE
    SYNTAX          Counter
    ACCESS          read-only
    STATUS          mandatory
    DESCRIPTION     
            "This counter keeps track of the number of X4 error
             received from verification server per server type."
    ::= { sonusSoftSwitchHTTPPerSvrTypeFailureCountersEntry 49 }

sonusSoftSwitchHTTPPerSvrTypeFailureCountersVerFailure400 OBJECT-TYPE
    SYNTAX          Counter
    ACCESS          read-only
    STATUS          mandatory
    DESCRIPTION     
            "This counter keeps track of the number of 400 error
             received from verification server per server type."
    ::= { sonusSoftSwitchHTTPPerSvrTypeFailureCountersEntry 50 }

sonusSoftSwitchHTTPPerSvrTypeFailureCountersVerFailure404 OBJECT-TYPE
    SYNTAX          Counter
    ACCESS          read-only
    STATUS          mandatory
    DESCRIPTION     
            "This counter keeps track of the number of 404 error
             received from verification server per server type."
    ::= { sonusSoftSwitchHTTPPerSvrTypeFailureCountersEntry 51 }

sonusSoftSwitchHTTPPerSvrTypeFailureCountersVerFailure405 OBJECT-TYPE
    SYNTAX          Counter
    ACCESS          read-only
    STATUS          mandatory
    DESCRIPTION     
            "This counter keeps track of the number of 405 error
             received from verification server per server type."
    ::= { sonusSoftSwitchHTTPPerSvrTypeFailureCountersEntry 52 }

sonusSoftSwitchHTTPPerSvrTypeFailureCountersVerFailure406 OBJECT-TYPE
    SYNTAX          Counter
    ACCESS          read-only
    STATUS          mandatory
    DESCRIPTION     
            "This counter keeps track of the number of 406 error
             received from verification server per server type."
    ::= { sonusSoftSwitchHTTPPerSvrTypeFailureCountersEntry 53 }

sonusSoftSwitchHTTPPerSvrTypeFailureCountersVerFailure411 OBJECT-TYPE
    SYNTAX          Counter
    ACCESS          read-only
    STATUS          mandatory
    DESCRIPTION     
            "This counter keeps track of the number of 411 error
             received from verification server per server type."
    ::= { sonusSoftSwitchHTTPPerSvrTypeFailureCountersEntry 54 }

sonusSoftSwitchHTTPPerSvrTypeFailureCountersVerFailure415 OBJECT-TYPE
    SYNTAX          Counter
    ACCESS          read-only
    STATUS          mandatory
    DESCRIPTION     
            "This counter keeps track of the number of 415 error
             received from verification server per server type."
    ::= { sonusSoftSwitchHTTPPerSvrTypeFailureCountersEntry 55 }

sonusSoftSwitchHTTPPerSvrTypeFailureCountersVerFailure500 OBJECT-TYPE
    SYNTAX          Counter
    ACCESS          read-only
    STATUS          mandatory
    DESCRIPTION     
            "This counter keeps track of the number of 500 error
             received from verification server per server type."
    ::= { sonusSoftSwitchHTTPPerSvrTypeFailureCountersEntry 56 }

sonusSoftSwitchHTTPPerSvrTypeFailureCountersVerFailure503 OBJECT-TYPE
    SYNTAX          Counter
    ACCESS          read-only
    STATUS          mandatory
    DESCRIPTION     
            "This counter keeps track of the number of 503 error
             received from verification server per server type."
    ::= { sonusSoftSwitchHTTPPerSvrTypeFailureCountersEntry 57 }

sonusSoftSwitchHTTPPerSvrTypeFailureCountersVerFailureSVC4000 OBJECT-TYPE
    SYNTAX          Counter
    ACCESS          read-only
    STATUS          mandatory
    DESCRIPTION     
            "This counter keeps track of the number of service exception 4000 error
             received from verification server per server type."
    ::= { sonusSoftSwitchHTTPPerSvrTypeFailureCountersEntry 58 }

sonusSoftSwitchHTTPPerSvrTypeFailureCountersVerFailureSVC4001 OBJECT-TYPE
    SYNTAX          Counter
    ACCESS          read-only
    STATUS          mandatory
    DESCRIPTION     
            "This counter keeps track of the number of service exception 4001 error
             received from verification server per server type."
    ::= { sonusSoftSwitchHTTPPerSvrTypeFailureCountersEntry 59 }

sonusSoftSwitchHTTPPerSvrTypeFailureCountersVerFailureSVC4002 OBJECT-TYPE
    SYNTAX          Counter
    ACCESS          read-only
    STATUS          mandatory
    DESCRIPTION     
            "This counter keeps track of the number of service exception 4002 error
             received from verification server per server type."
    ::= { sonusSoftSwitchHTTPPerSvrTypeFailureCountersEntry 60 }

sonusSoftSwitchHTTPPerSvrTypeFailureCountersVerFailureSVC4003 OBJECT-TYPE
    SYNTAX          Counter
    ACCESS          read-only
    STATUS          mandatory
    DESCRIPTION     
            "This counter keeps track of the number of service exception 4003 error
             received from verification server per server type."
    ::= { sonusSoftSwitchHTTPPerSvrTypeFailureCountersEntry 61 }

sonusSoftSwitchHTTPPerSvrTypeFailureCountersVerFailureSVC4004 OBJECT-TYPE
    SYNTAX          Counter
    ACCESS          read-only
    STATUS          mandatory
    DESCRIPTION     
            "This counter keeps track of the number of service exception 4004 error
             received from verification server per server type."
    ::= { sonusSoftSwitchHTTPPerSvrTypeFailureCountersEntry 62 }

sonusSoftSwitchHTTPPerSvrTypeFailureCountersVerFailureSVC4005 OBJECT-TYPE
    SYNTAX          Counter
    ACCESS          read-only
    STATUS          mandatory
    DESCRIPTION     
            "This counter keeps track of the number of service exception 4005 error
             received from verification server per server type."
    ::= { sonusSoftSwitchHTTPPerSvrTypeFailureCountersEntry 63 }

sonusSoftSwitchHTTPPerSvrTypeFailureCountersVerFailureSVC4006 OBJECT-TYPE
    SYNTAX          Counter
    ACCESS          read-only
    STATUS          mandatory
    DESCRIPTION     
            "This counter keeps track of the number of service exception 4006 error
             received from verification server per server type."
    ::= { sonusSoftSwitchHTTPPerSvrTypeFailureCountersEntry 64 }

sonusSoftSwitchHTTPPerSvrTypeFailureCountersVerFailureSVC4007 OBJECT-TYPE
    SYNTAX          Counter
    ACCESS          read-only
    STATUS          mandatory
    DESCRIPTION     
            "This counter keeps track of the number of service exception 4007 error
             received from verification server per server type."
    ::= { sonusSoftSwitchHTTPPerSvrTypeFailureCountersEntry 65 }

sonusSoftSwitchHTTPPerSvrTypeFailureCountersVerFailurePOL4050 OBJECT-TYPE
    SYNTAX          Counter
    ACCESS          read-only
    STATUS          mandatory
    DESCRIPTION     
            "This counter keeps track of the number of policy exception 4050 error
             received from verification server per server type."
    ::= { sonusSoftSwitchHTTPPerSvrTypeFailureCountersEntry 66 }

sonusSoftSwitchHTTPPerSvrTypeFailureCountersVerFailurePOL5000 OBJECT-TYPE
    SYNTAX          Counter
    ACCESS          read-only
    STATUS          mandatory
    DESCRIPTION     
            "This counter keeps track of the number of policy exception 5000 error
             received from verification server per server type."
    ::= { sonusSoftSwitchHTTPPerSvrTypeFailureCountersEntry 67 }

sonusSoftSwitchHTTPPerSvrTypeInternalCounters OBJECT IDENTIFIER
    ::= { sonusSoftSwitchHTTPClientStatistics 10 }

sonusSoftSwitchHTTPPerSvrTypeInternalCountersTable OBJECT-TYPE
    SYNTAX          SEQUENCE OF SonusSoftSwitchHTTPPerSvrTypeInternalCountersEntry
    ACCESS          not-accessible
    STATUS          mandatory
    DESCRIPTION     
            "HTTP Client Internal Counters Per Server Type"
    ::= { sonusSoftSwitchHTTPPerSvrTypeInternalCounters 1 }

sonusSoftSwitchHTTPPerSvrTypeInternalCountersEntry OBJECT-TYPE
    SYNTAX          SonusSoftSwitchHTTPPerSvrTypeInternalCountersEntry
    ACCESS          not-accessible
    STATUS          mandatory
    DESCRIPTION     
            "An entry of Traffic counters related to HTTPC Client Servers"
    INDEX           { 
                      sonusSoftSwitchHTTPPerSvrTypeInternalCountersServerName }
    ::= { sonusSoftSwitchHTTPPerSvrTypeInternalCountersTable 1 }

SonusSoftSwitchHTTPPerSvrTypeInternalCountersEntry ::=
    SEQUENCE {
        sonusSoftSwitchHTTPPerSvrTypeInternalCountersServerName                       DisplayString,
        sonusSoftSwitchHTTPPerSvrTypeInternalCountersNoConnAvailable                            Counter,
        sonusSoftSwitchHTTPPerSvrTypeInternalCountersJsonError                      Counter,
        sonusSoftSwitchHTTPPerSvrTypeInternalCountersCurlError                      Counter,
        sonusSoftSwitchHTTPPerSvrTypeInternalCountersMaxRetriesExhausted                                Counter,
        sonusSoftSwitchHTTPPerSvrTypeInternalCountersGeneralFailure                           Counter
    }

sonusSoftSwitchHTTPPerSvrTypeInternalCountersServerName OBJECT-TYPE
    SYNTAX          DisplayString
    ACCESS          read-only
    STATUS          mandatory
    DESCRIPTION     
            "Server Type Name."
    ::= { sonusSoftSwitchHTTPPerSvrTypeInternalCountersEntry 1 }

sonusSoftSwitchHTTPPerSvrTypeInternalCountersNoConnAvailable OBJECT-TYPE
    SYNTAX          Counter
    ACCESS          read-only
    STATUS          mandatory
    DESCRIPTION     
            "This counter keeps track of the number of errors with no connection available Per Server Type."
    ::= { sonusSoftSwitchHTTPPerSvrTypeInternalCountersEntry 2 }

sonusSoftSwitchHTTPPerSvrTypeInternalCountersJsonError OBJECT-TYPE
    SYNTAX          Counter
    ACCESS          read-only
    STATUS          mandatory
    DESCRIPTION     
            "This counter keeps track of the number of JSON Error Per Server Type."
    ::= { sonusSoftSwitchHTTPPerSvrTypeInternalCountersEntry 3 }

sonusSoftSwitchHTTPPerSvrTypeInternalCountersCurlError OBJECT-TYPE
    SYNTAX          Counter
    ACCESS          read-only
    STATUS          mandatory
    DESCRIPTION     
            "This counter keeps track of the number of HTTP Error Per Server Type."
    ::= { sonusSoftSwitchHTTPPerSvrTypeInternalCountersEntry 4 }

sonusSoftSwitchHTTPPerSvrTypeInternalCountersMaxRetriesExhausted OBJECT-TYPE
    SYNTAX          Counter
    ACCESS          read-only
    STATUS          mandatory
    DESCRIPTION     
            "This counter keeps track of the number of failures due to Max Retries Exhausted Per Server Type."
    ::= { sonusSoftSwitchHTTPPerSvrTypeInternalCountersEntry 5 }

sonusSoftSwitchHTTPPerSvrTypeInternalCountersGeneralFailure OBJECT-TYPE
    SYNTAX          Counter
    ACCESS          read-only
    STATUS          mandatory
    DESCRIPTION     
            "This counter keeps track of the number of General Failure Per Server Type."
    ::= { sonusSoftSwitchHTTPPerSvrTypeInternalCountersEntry 6 }

sonusSoftSwitchHTTPClientRESTServiceCounters OBJECT IDENTIFIER
    ::= { sonusSoftSwitchHTTPClientStatistics 11 }

sonusSoftSwitchHTTPRESTServiceQuerySentCounters OBJECT-TYPE
    SYNTAX          Counter
    ACCESS          read-only
    STATUS          mandatory
    DESCRIPTION     
            "This counter keeps track of the number of REST Service requests
             which are sent from HTTP Client Process."
    ::= { sonusSoftSwitchHTTPClientRESTServiceCounters 1 }

sonusSoftSwitchHTTPRESTServiceRspCounters OBJECT-TYPE
    SYNTAX          Counter
    ACCESS          read-only
    STATUS          mandatory
    DESCRIPTION     
            "This counter keeps track of the number of REST Service responses
             which have been received by HTTP Client process."
    ::= { sonusSoftSwitchHTTPClientRESTServiceCounters 2 }

sonusSoftSwitchHTTPRESTServiceQueryTimeOutCounters OBJECT-TYPE
    SYNTAX          Counter
    ACCESS          read-only
    STATUS          mandatory
    DESCRIPTION     
            "This counter keeps track of the number of REST Service requests
             which have timeout for response."
    ::= { sonusSoftSwitchHTTPClientRESTServiceCounters 3 }

sonusSoftSwitchHTTPRESTServiceQueryRetryCounters OBJECT-TYPE
    SYNTAX          Counter
    ACCESS          read-only
    STATUS          mandatory
    DESCRIPTION     
            "This counter keeps track of the number of REST Service requests
             which are retried from HTTP Client Process."
    ::= { sonusSoftSwitchHTTPClientRESTServiceCounters 4 }

sonusSoftSwitchHTTPClientRESTServiceFailureCounters OBJECT IDENTIFIER
    ::= { sonusSoftSwitchHTTPClientStatistics 12 }

sonusSoftSwitchHTTPRESTServiceFailure400Counters OBJECT-TYPE
    SYNTAX          Counter
    ACCESS          read-only
    STATUS          mandatory
    DESCRIPTION     
            "This counter keeps track of the number of 400 error
             received from REST Service server."
    ::= { sonusSoftSwitchHTTPClientRESTServiceFailureCounters 1 }

sonusSoftSwitchHTTPRESTServiceFailure403Counters OBJECT-TYPE
    SYNTAX          Counter
    ACCESS          read-only
    STATUS          mandatory
    DESCRIPTION     
            "This counter keeps track of the number of 403 error
             received from REST Service server."
    ::= { sonusSoftSwitchHTTPClientRESTServiceFailureCounters 2 }

sonusSoftSwitchHTTPRESTServiceFailure500Counters OBJECT-TYPE
    SYNTAX          Counter
    ACCESS          read-only
    STATUS          mandatory
    DESCRIPTION     
            "This counter keeps track of the number of 500 error
             received from REST Service server."
    ::= { sonusSoftSwitchHTTPClientRESTServiceFailureCounters 3 }

sonusSoftSwitchHTTPRESTServiceFailure503Counters OBJECT-TYPE
    SYNTAX          Counter
    ACCESS          read-only
    STATUS          mandatory
    DESCRIPTION     
            "This counter keeps track of the number of 503 error
             received from REST Service server."
    ::= { sonusSoftSwitchHTTPClientRESTServiceFailureCounters 4 }

sonusSoftSwitchHTTPClientMIBNotifications OBJECT IDENTIFIER
    ::= { sonusSoftSwitchHTTPClientMIB 2 }

sonusSoftSwitchHTTPClientMIBNotificationsPrefix OBJECT IDENTIFIER
    ::= { sonusSoftSwitchHTTPClientMIBNotifications 0 }

sonusSoftSwitchHTTPClientUpNotification TRAP-TYPE
    ENTERPRISE      sonusSoftSwitchHTTPClientMIBNotifications
    VARIABLES       { sonusEventDescription, sonusEventClass, 
                      sonusEventLevel, sonusEventTime }
--     STATUS          mandatory
    DESCRIPTION     
            "SoftSwitch HTTP Client is up."
    ::= 1

sonusSoftSwitchHTTPClientDownNotification TRAP-TYPE
    ENTERPRISE      sonusSoftSwitchHTTPClientMIBNotifications
    VARIABLES       { sonusEventDescription, sonusEventClass, 
                      sonusEventLevel, sonusEventTime }
--     STATUS          mandatory
    DESCRIPTION     
            "SoftSwitch HTTP Client is down."
    ::= 2

sonusSoftSwitchHTTPClientDnsServiceUpNotification TRAP-TYPE
    ENTERPRISE      sonusSoftSwitchHTTPClientMIBNotifications
    VARIABLES       { sonusEventDescription, sonusEventClass, 
                      sonusEventLevel, sonusEventTime }
--     STATUS          mandatory
    DESCRIPTION     
            "SoftSwitch HTTPC-DNS communication is up."
    ::= 3

sonusSoftSwitchHTTPClientDnsServiceDownNotification TRAP-TYPE
    ENTERPRISE      sonusSoftSwitchHTTPClientMIBNotifications
    VARIABLES       { sonusEventDescription, sonusEventClass, 
                      sonusEventLevel, sonusEventTime }
--     STATUS          mandatory
    DESCRIPTION     
            "SoftSwitch HTTPC-DNS communication is down."
    ::= 4

sonusSoftSwitchHTTPPeerConnectionBlacklisted TRAP-TYPE
    ENTERPRISE      sonusSoftSwitchHTTPClientMIBNotifications
    VARIABLES       { sonusEventDescription, sonusEventClass, 
                      sonusEventLevel, sonusEventTime }
--     STATUS          mandatory
    DESCRIPTION     
            "SVS SERVER connection Blacklisted."
    ::= 5

sonusSoftSwitchHTTPPeerConnectionRecovered TRAP-TYPE
    ENTERPRISE      sonusSoftSwitchHTTPClientMIBNotifications
    VARIABLES       { sonusEventDescription, sonusEventClass, 
                      sonusEventLevel, sonusEventTime }
--     STATUS          mandatory
    DESCRIPTION     
            "SVS SERVER connection Recovered from Blacklist."
    ::= 6

sonusSoftSwitchServerConnectionFailureNotification TRAP-TYPE
    ENTERPRISE      sonusSoftSwitchHTTPClientMIBNotifications
    VARIABLES       { sonusEventDescription, sonusEventClass, 
                      sonusEventLevel, sonusEventTime }
--     STATUS          mandatory
    DESCRIPTION     
            "SVS SERVER connection failure."
    ::= 7

sonusSoftSwitchHttpConnectionFailureNotification TRAP-TYPE
    ENTERPRISE      sonusSoftSwitchHTTPClientMIBNotifications
    VARIABLES       { sonusEventDescription, sonusEventClass, 
                      sonusEventLevel, sonusEventTime }
--     STATUS          mandatory
    DESCRIPTION     
            "Connection establishment failed to Http server."
    ::= 8

sonusSoftSwitchHttpSTIServersNotConfigured TRAP-TYPE
    ENTERPRISE      sonusSoftSwitchHTTPClientMIBNotifications
    VARIABLES       { sonusEventDescription, sonusEventClass, 
                      sonusEventLevel, sonusEventTime }
--     STATUS          mandatory
    DESCRIPTION     
            "STI Servers are not configured."
    ::= 9

sonusSoftSwitchHttpThreadKeepAliveFailedNotification TRAP-TYPE
    ENTERPRISE      sonusSoftSwitchHTTPClientMIBNotifications
    VARIABLES       { sonusEventDescription, sonusEventClass, 
                      sonusEventLevel, sonusEventTime }
--     STATUS          mandatory
    DESCRIPTION     
            "Indicates that the one of the threads of HTTP process failed to send keepalive message."
    ::= 10

END -- end of module SONUS-SOFTSWITCH-HTTP-CLIENT-MIB.
