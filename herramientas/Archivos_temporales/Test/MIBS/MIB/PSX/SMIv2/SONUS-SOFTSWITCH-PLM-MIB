--
-- This SMIv2 module has been generated by smidump 0.2-cvs. Do not edit.
--

SONUS-SOFTSWITCH-PLM-MIB DEFINITIONS ::= BEGIN

IMPORTS
    Counter32, Gauge32, Integer32, MODULE-IDENTITY, NOTIFICATION-TYPE, 
    OBJECT-TYPE
        FROM SNMPv2-SMI
    sonusEventClass, sonusEventDescription, sonusEventLevel, 
    sonusEventTime
        FROM SONUS-COMMON-MIB
    sonusServicesMIBs
        FROM SONUS-SMI;

sonusSoftSwitchProductLicenseManagerMIB MODULE-IDENTITY
    LAST-UPDATED    "200205030000Z"
    ORGANIZATION    
            "Sonus Networks, Inc."
    CONTACT-INFO    
            " Customer Support
             Sonus Networks, Inc.
             250 Apollo Drive
             Chelmsford, MA 01824
             USA
             Tel: 978-614-8100
             Fax: 978-614-8609"
    DESCRIPTION     
            "The MIB Module for SoftSwitch Product License Manager."
    ::= { sonusServicesMIBs 42 }


sonusSoftSwitchProductLicenseManagerMIBObjects OBJECT IDENTIFIER
    ::= { sonusSoftSwitchProductLicenseManagerMIB 1 }

sonusSoftSwitchPlmMIBNotifications OBJECT IDENTIFIER
    ::= { sonusSoftSwitchProductLicenseManagerMIB 2 }

sonusSoftSwitchPlmMIBNotificationsPrefix OBJECT IDENTIFIER
    ::= { sonusSoftSwitchPlmMIBNotifications 0 }

sonusSoftSwitchPlmMIBNotificationsObjects OBJECT IDENTIFIER
    ::= { sonusSoftSwitchPlmMIBNotifications 1 }

sonusSoftSwitchPlmUpNotification NOTIFICATION-TYPE
    OBJECTS         { sonusEventDescription, sonusEventClass, 
                      sonusEventLevel, sonusEventTime }
    STATUS          current
    DESCRIPTION     
            "SoftSwitch PLM is up."
    ::= { sonusSoftSwitchPlmMIBNotificationsPrefix 1 }

sonusSoftSwitchPlmDownNotification NOTIFICATION-TYPE
    OBJECTS         { sonusEventDescription, sonusEventClass, 
                      sonusEventLevel, sonusEventTime }
    STATUS          current
    DESCRIPTION     
            "SoftSwitch PLM is down."
    ::= { sonusSoftSwitchPlmMIBNotificationsPrefix 2 }

sonusSoftSwitchPlmServerUnreachable NOTIFICATION-TYPE
    OBJECTS         { sonusEventDescription, sonusEventClass, 
                      sonusEventLevel, sonusEventTime }
    STATUS          current
    DESCRIPTION     
            "The PSX PLM process cannot set up a connection with the site license server."
    ::= { sonusSoftSwitchPlmMIBNotificationsPrefix 3 }

sonusSoftSwitchPlmServerReachable NOTIFICATION-TYPE
    OBJECTS         { sonusEventDescription, sonusEventClass, 
                      sonusEventLevel, sonusEventTime }
    STATUS          current
    DESCRIPTION     
            "The PSX PLM process can set up a connection with the site license server."
    ::= { sonusSoftSwitchPlmMIBNotificationsPrefix 4 }

sonusSoftSwitchPlmLicenseUnavailable NOTIFICATION-TYPE
    OBJECTS         { sonusEventDescription, sonusEventClass, 
                      sonusEventLevel, sonusEventTime }
    STATUS          current
    DESCRIPTION     
            "The PSX PLM process cannot fetch a License for a feature from the site license server."
    ::= { sonusSoftSwitchPlmMIBNotificationsPrefix 5 }

sonusSoftSwitchPlmLicenseAvailable NOTIFICATION-TYPE
    OBJECTS         { sonusEventDescription, sonusEventClass, 
                      sonusEventLevel, sonusEventTime }
    STATUS          current
    DESCRIPTION     
            "The PSX PLM process can fetch a License for a feature from the site license server."
    ::= { sonusSoftSwitchPlmMIBNotificationsPrefix 6 }

sonusSoftSwitchPlmLicenseGraceMode NOTIFICATION-TYPE
    OBJECTS         { sonusEventDescription, sonusEventClass, 
                      sonusEventLevel, sonusEventTime }
    STATUS          current
    DESCRIPTION     
            "The PSX Network based Licenses have transitioned to grace mode."
    ::= { sonusSoftSwitchPlmMIBNotificationsPrefix 7 }

sonusSoftSwitchPlmLicenseGraceModeCleared NOTIFICATION-TYPE
    OBJECTS         { sonusEventDescription, sonusEventClass, 
                      sonusEventLevel, sonusEventTime }
    STATUS          current
    DESCRIPTION     
            "The PSX Network based Licenses are out of grace mode and getting into the network mode."
    ::= { sonusSoftSwitchPlmMIBNotificationsPrefix 8 }

sonusSoftSwitchPlmLicenseGraceExpiring NOTIFICATION-TYPE
    OBJECTS         { sonusEventDescription, sonusEventClass, 
                      sonusEventLevel, sonusEventTime }
    STATUS          current
    DESCRIPTION     
            "The PSX Grace Licenses will expire in x days."
    ::= { sonusSoftSwitchPlmMIBNotificationsPrefix 9 }

sonusSoftSwitchPlmLicenseGraceExpired NOTIFICATION-TYPE
    OBJECTS         { sonusEventDescription, sonusEventClass, 
                      sonusEventLevel, sonusEventTime }
    STATUS          current
    DESCRIPTION     
            "The PSX Grace Licenses have expired."
    ::= { sonusSoftSwitchPlmMIBNotificationsPrefix 10 }

sonusSoftSwitchPlmLicenseReleased NOTIFICATION-TYPE
    OBJECTS         { sonusEventDescription, sonusEventClass, 
                      sonusEventLevel, sonusEventTime }
    STATUS          current
    DESCRIPTION     
            "The PSX has released the Network Based License."
    ::= { sonusSoftSwitchPlmMIBNotificationsPrefix 11 }

sonusSoftSwitchPlmMinimumLicenseCountThresholdNotReached NOTIFICATION-TYPE
    OBJECTS         { sonusEventDescription, sonusEventClass, 
                      sonusEventLevel, sonusEventTime }
    STATUS          current
    DESCRIPTION     
            "The PSX feature license count has not reached the minimum license count threshold."
    ::= { sonusSoftSwitchPlmMIBNotificationsPrefix 12 }

sonusSoftSwitchPlmClearMinimumLicenseCountThresholdNotReached NOTIFICATION-TYPE
    OBJECTS         { sonusEventDescription, sonusEventClass, 
                      sonusEventLevel, sonusEventTime }
    STATUS          current
    DESCRIPTION     
            "The PSX feature license count has reached the minimum license count threshold."
    ::= { sonusSoftSwitchPlmMIBNotificationsPrefix 13 }

sonusSoftSwitchPlmMaximumLicenseCountThresholdExceeded NOTIFICATION-TYPE
    OBJECTS         { sonusEventDescription, sonusEventClass, 
                      sonusEventLevel, sonusEventTime }
    STATUS          current
    DESCRIPTION     
            "The PSX feature license count has exceeded the maximum license count threshold."
    ::= { sonusSoftSwitchPlmMIBNotificationsPrefix 14 }

sonusSoftSwitchPlmClearMaximumLicenseCountThresholdExceeded NOTIFICATION-TYPE
    OBJECTS         { sonusEventDescription, sonusEventClass, 
                      sonusEventLevel, sonusEventTime }
    STATUS          current
    DESCRIPTION     
            "The PSX feature license count is below the maximum license count threshold."
    ::= { sonusSoftSwitchPlmMIBNotificationsPrefix 15 }

END -- end of module SONUS-SOFTSWITCH-PLM-MIB.
