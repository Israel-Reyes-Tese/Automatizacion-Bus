--
-- This SMIv1 module has been generated by smidump 0.2-cvs. Do not edit.
--

RIVERSTONE-SNMP-MIB DEFINITIONS ::= BEGIN

IMPORTS
    OBJECT-TYPE
        FROM RFC-1212
    riverstoneMibs
        FROM RIVERSTONE-SMI-MIB
    snmpCommunityEntry
        FROM SNMP-COMMUNITY-MIB
    snmpNotifyEntry, snmpNotifyFilterEntry, snmpNotifyFilterProfileEntry
        FROM SNMP-NOTIFICATION-MIB
    snmpTargetAddrEntry, snmpTargetParamsEntry
        FROM SNMP-TARGET-MIB
    usmUserEntry
        FROM SNMP-USER-BASED-SM-MIB
    vacmAccessEntry, vacmSecurityToGroupEntry, vacmViewTreeFamilyEntry
        FROM SNMP-VIEW-BASED-ACM-MIB
    DateAndTime
        FROM SNMPv2-TC;

rsSnmpMib OBJECT IDENTIFIER
    ::= { riverstoneMibs 15 }

-- rsSnmpMib MODULE-IDENTITY
--     LAST-UPDATED    "200012040000Z"
--     ORGANIZATION    
--             "Riverstone Networks, Inc"
--     CONTACT-INFO    
--             "Riverstone Networks, Inc
--              5200 Great America Parkway
--              Santa Clara CA USA 95054
--              PHONE:+1 408.878.6500
--              EMAIL: nms-eng@riverstonenet.com
--              WEB: http://www.riverstonenet.com"
--     DESCRIPTION     
--             "This mib module defines addtional configuration and statistics
--              for SNMP v3 Protocol Management as defined in RFCs 2570-2580
--              Copyright (C) Riverstone Networks, Inc 2000"
--     REVISION        "200012040000Z"
--     DESCRIPTION     
--             "Initial version of of RIVERSTONE-SNMP-MIB."
--     ::= { riverstoneMibs 15 }


rsSnmpObjects OBJECT IDENTIFIER
    ::= { rsSnmpMib 1 }

rsSnmpV3LastChange OBJECT-TYPE
    SYNTAX          DateAndTime
    ACCESS          read-only
    STATUS          mandatory
    DESCRIPTION     
            "The lastChange time of any of snmpV3 configuration."
    ::= { rsSnmpObjects 1 }

rsSnmpTargetAddrTable OBJECT-TYPE
    SYNTAX          SEQUENCE OF RsSnmpTargetAddrEntry
    ACCESS          not-accessible
    STATUS          mandatory
    DESCRIPTION     
            "A table of to add a LastChange to the snmpTargetAddrTable."
    ::= { rsSnmpObjects 2 }

rsSnmpTargetAddrEntry OBJECT-TYPE
    SYNTAX          RsSnmpTargetAddrEntry
    ACCESS          not-accessible
    STATUS          mandatory
    DESCRIPTION     
            "Adds a LastChange to snmpTargetAddrEntry."
    INDEX           { IMPLIED snmpTargetAddrName }
--     AUGMENTS        { snmpTargetAddrEntry }
    ::= { rsSnmpTargetAddrTable 1 }

RsSnmpTargetAddrEntry ::=
    SEQUENCE {
        rsSnmpTargetAddrLastChange      DateAndTime
    }

rsSnmpTargetAddrLastChange OBJECT-TYPE
    SYNTAX          DateAndTime
    ACCESS          read-only
    STATUS          mandatory
    DESCRIPTION     
            "This object specifies the date and time of
             creation / last modification of this conceptual 
             row."
    ::= { rsSnmpTargetAddrEntry 1 }

rsSnmpTargetParamsTable OBJECT-TYPE
    SYNTAX          SEQUENCE OF RsSnmpTargetParamsEntry
    ACCESS          not-accessible
    STATUS          mandatory
    DESCRIPTION     
            "A table of to add a LastChange to the snmpTargetParamsTable."
    ::= { rsSnmpObjects 3 }

rsSnmpTargetParamsEntry OBJECT-TYPE
    SYNTAX          RsSnmpTargetParamsEntry
    ACCESS          not-accessible
    STATUS          mandatory
    DESCRIPTION     
            "Adds a LastChange to snmpTargetParamsEntry."
    INDEX           { IMPLIED snmpTargetParamsName }
--     AUGMENTS        { snmpTargetParamsEntry }
    ::= { rsSnmpTargetParamsTable 1 }

RsSnmpTargetParamsEntry ::=
    SEQUENCE {
        rsSnmpTargetParamsLastChange    DateAndTime
    }

rsSnmpTargetParamsLastChange OBJECT-TYPE
    SYNTAX          DateAndTime
    ACCESS          read-only
    STATUS          mandatory
    DESCRIPTION     
            "This object specifies the date and time of
             creation / last modification of this conceptual 
             row."
    ::= { rsSnmpTargetParamsEntry 1 }

rsSnmpNotifyTable OBJECT-TYPE
    SYNTAX          SEQUENCE OF RsSnmpNotifyEntry
    ACCESS          not-accessible
    STATUS          mandatory
    DESCRIPTION     
            "A table of to add a LastChange to the snmpNotifyTable."
    ::= { rsSnmpObjects 4 }

rsSnmpNotifyEntry OBJECT-TYPE
    SYNTAX          RsSnmpNotifyEntry
    ACCESS          not-accessible
    STATUS          mandatory
    DESCRIPTION     
            "Adds a LastChange to snmpNotifyEntry."
    INDEX           { IMPLIED snmpNotifyName }
--     AUGMENTS        { snmpNotifyEntry }
    ::= { rsSnmpNotifyTable 1 }

RsSnmpNotifyEntry ::=
    SEQUENCE {
        rsSnmpNotifyLastChange          DateAndTime
    }

rsSnmpNotifyLastChange OBJECT-TYPE
    SYNTAX          DateAndTime
    ACCESS          read-only
    STATUS          mandatory
    DESCRIPTION     
            "This object specifies the date and time of
             creation / last modification of this conceptual 
             row."
    ::= { rsSnmpNotifyEntry 1 }

rsSnmpNotifyFilterProfileTable OBJECT-TYPE
    SYNTAX          SEQUENCE OF RsSnmpNotifyFilterProfileEntry
    ACCESS          not-accessible
    STATUS          mandatory
    DESCRIPTION     
            "A table of to add a LastChange to the snmpNotifyFilterProfileTable."
    ::= { rsSnmpObjects 5 }

rsSnmpNotifyFilterProfileEntry OBJECT-TYPE
    SYNTAX          RsSnmpNotifyFilterProfileEntry
    ACCESS          not-accessible
    STATUS          mandatory
    DESCRIPTION     
            "Adds a LastChange to snmpNotifyFilterProfileEntry."
    INDEX           { IMPLIED snmpTargetParamsName }
--     AUGMENTS        { snmpNotifyFilterProfileEntry }
    ::= { rsSnmpNotifyFilterProfileTable 1 }

RsSnmpNotifyFilterProfileEntry ::=
    SEQUENCE {
        rsSnmpNotifyFilterProfileLastChange   DateAndTime
    }

rsSnmpNotifyFilterProfileLastChange OBJECT-TYPE
    SYNTAX          DateAndTime
    ACCESS          read-only
    STATUS          mandatory
    DESCRIPTION     
            "This object specifies the date and time of
             creation / last modification of this conceptual 
             row."
    ::= { rsSnmpNotifyFilterProfileEntry 1 }

rsSnmpNotifyFilterTable OBJECT-TYPE
    SYNTAX          SEQUENCE OF RsSnmpNotifyFilterEntry
    ACCESS          not-accessible
    STATUS          mandatory
    DESCRIPTION     
            "A table of to add a LastChange to the snmpNotifyFilterTable."
    ::= { rsSnmpObjects 6 }

rsSnmpNotifyFilterEntry OBJECT-TYPE
    SYNTAX          RsSnmpNotifyFilterEntry
    ACCESS          not-accessible
    STATUS          mandatory
    DESCRIPTION     
            "Adds a LastChange to snmpNotifyFilterEntry."
    INDEX           { snmpNotifyFilterProfileName, IMPLIED 
                      snmpNotifyFilterSubtree }
--     AUGMENTS        { snmpNotifyFilterEntry }
    ::= { rsSnmpNotifyFilterTable 1 }

RsSnmpNotifyFilterEntry ::=
    SEQUENCE {
        rsSnmpNotifyFilterLastChange    DateAndTime
    }

rsSnmpNotifyFilterLastChange OBJECT-TYPE
    SYNTAX          DateAndTime
    ACCESS          read-only
    STATUS          mandatory
    DESCRIPTION     
            "This object specifies the date and time of
             creation / last modification of this conceptual 
             row."
    ::= { rsSnmpNotifyFilterEntry 1 }

rsUsmUserTable OBJECT-TYPE
    SYNTAX          SEQUENCE OF RsUsmUserEntry
    ACCESS          not-accessible
    STATUS          mandatory
    DESCRIPTION     
            "A table of to add a LastChange to the usmUserTable."
    ::= { rsSnmpObjects 7 }

rsUsmUserEntry OBJECT-TYPE
    SYNTAX          RsUsmUserEntry
    ACCESS          not-accessible
    STATUS          mandatory
    DESCRIPTION     
            "Adds a LastChange to usmUserEntry."
    INDEX           { usmUserEngineID, usmUserName }
--     AUGMENTS        { usmUserEntry }
    ::= { rsUsmUserTable 1 }

RsUsmUserEntry ::=
    SEQUENCE {
        rsUsmUserLastChange             DateAndTime
    }

rsUsmUserLastChange OBJECT-TYPE
    SYNTAX          DateAndTime
    ACCESS          read-only
    STATUS          mandatory
    DESCRIPTION     
            "This object specifies the date and time of
             creation / last modification of this conceptual 
             row."
    ::= { rsUsmUserEntry 1 }

rsVacmSecurityToGroupTable OBJECT-TYPE
    SYNTAX          SEQUENCE OF RsVacmSecurityToGroupEntry
    ACCESS          not-accessible
    STATUS          mandatory
    DESCRIPTION     
            "A table of to add a LastChange to the vacmSecurityToGroupTable."
    ::= { rsSnmpObjects 8 }

rsVacmSecurityToGroupEntry OBJECT-TYPE
    SYNTAX          RsVacmSecurityToGroupEntry
    ACCESS          not-accessible
    STATUS          mandatory
    DESCRIPTION     
            "Adds a LastChange to vacmSecurityToGroupEntry."
    INDEX           { vacmSecurityModel, vacmSecurityName }
--     AUGMENTS        { vacmSecurityToGroupEntry }
    ::= { rsVacmSecurityToGroupTable 1 }

RsVacmSecurityToGroupEntry ::=
    SEQUENCE {
        rsVacmSecurityToGroupLastChange DateAndTime
    }

rsVacmSecurityToGroupLastChange OBJECT-TYPE
    SYNTAX          DateAndTime
    ACCESS          read-only
    STATUS          mandatory
    DESCRIPTION     
            "This object specifies the date and time of
             creation / last modification of this conceptual 
             row."
    ::= { rsVacmSecurityToGroupEntry 1 }

rsVacmAccessTable OBJECT-TYPE
    SYNTAX          SEQUENCE OF RsVacmAccessEntry
    ACCESS          not-accessible
    STATUS          mandatory
    DESCRIPTION     
            "A table of to add a LastChange to the vacmAccessTable."
    ::= { rsSnmpObjects 9 }

rsVacmAccessEntry OBJECT-TYPE
    SYNTAX          RsVacmAccessEntry
    ACCESS          not-accessible
    STATUS          mandatory
    DESCRIPTION     
            "Adds a LastChange to vacmAccessEntry."
    INDEX           { vacmGroupName, vacmAccessContextPrefix, 
                      vacmAccessSecurityModel, vacmAccessSecurityLevel }
--     AUGMENTS        { vacmAccessEntry }
    ::= { rsVacmAccessTable 1 }

RsVacmAccessEntry ::=
    SEQUENCE {
        rsVacmAccessLastChange          DateAndTime
    }

rsVacmAccessLastChange OBJECT-TYPE
    SYNTAX          DateAndTime
    ACCESS          read-only
    STATUS          mandatory
    DESCRIPTION     
            "This object specifies the date and time of
             creation / last modification of this conceptual 
             row."
    ::= { rsVacmAccessEntry 1 }

rsVacmViewTreeFamilyTable OBJECT-TYPE
    SYNTAX          SEQUENCE OF RsVacmViewTreeFamilyEntry
    ACCESS          not-accessible
    STATUS          mandatory
    DESCRIPTION     
            "A table of to add a LastChange to the vacmViewTreeFamilyTable."
    ::= { rsSnmpObjects 10 }

rsVacmViewTreeFamilyEntry OBJECT-TYPE
    SYNTAX          RsVacmViewTreeFamilyEntry
    ACCESS          not-accessible
    STATUS          mandatory
    DESCRIPTION     
            "Adds a LastChange to vacmViewTreeFamilyEntry."
    INDEX           { vacmViewTreeFamilyViewName, 
                      vacmViewTreeFamilySubtree }
--     AUGMENTS        { vacmViewTreeFamilyEntry }
    ::= { rsVacmViewTreeFamilyTable 1 }

RsVacmViewTreeFamilyEntry ::=
    SEQUENCE {
        rsVacmViewTreeFamilyLastChange  DateAndTime
    }

rsVacmViewTreeFamilyLastChange OBJECT-TYPE
    SYNTAX          DateAndTime
    ACCESS          read-only
    STATUS          mandatory
    DESCRIPTION     
            "This object specifies the date and time of
             creation / last modification of this conceptual 
             row."
    ::= { rsVacmViewTreeFamilyEntry 1 }

rsSnmpCommunityTable OBJECT-TYPE
    SYNTAX          SEQUENCE OF RsSnmpCommunityEntry
    ACCESS          not-accessible
    STATUS          mandatory
    DESCRIPTION     
            "A table of to add a LastChange to the snmpCommunityTable."
    ::= { rsSnmpObjects 11 }

rsSnmpCommunityEntry OBJECT-TYPE
    SYNTAX          RsSnmpCommunityEntry
    ACCESS          not-accessible
    STATUS          mandatory
    DESCRIPTION     
            "Adds a LastChange to snmpCommunityEntry."
    INDEX           { IMPLIED snmpCommunityIndex }
--     AUGMENTS        { snmpCommunityEntry }
    ::= { rsSnmpCommunityTable 1 }

RsSnmpCommunityEntry ::=
    SEQUENCE {
        rsSnmpCommunityLastChange       DateAndTime
    }

rsSnmpCommunityLastChange OBJECT-TYPE
    SYNTAX          DateAndTime
    ACCESS          read-only
    STATUS          mandatory
    DESCRIPTION     
            "This object specifies the date and time of
             creation / last modification of this conceptual 
             row."
    ::= { rsSnmpCommunityEntry 1 }

rsSnmpConformance OBJECT IDENTIFIER
    ::= { rsSnmpMib 2 }

rsSnmpGroups OBJECT IDENTIFIER
    ::= { rsSnmpConformance 1 }

rsSnmpCompliances OBJECT IDENTIFIER
    ::= { rsSnmpConformance 2 }

rsSnmpBaseGroup OBJECT IDENTIFIER
    ::= { rsSnmpGroups 1 }

-- rsSnmpBaseGroup OBJECT-GROUP
--     OBJECTS         { rsSnmpV3LastChange, rsSnmpTargetAddrLastChange, 
--                       rsSnmpTargetParamsLastChange, 
--                       rsSnmpNotifyLastChange, 
--                       rsSnmpNotifyFilterProfileLastChange, 
--                       rsSnmpNotifyFilterLastChange, 
--                       rsUsmUserLastChange, 
--                       rsVacmSecurityToGroupLastChange, 
--                       rsVacmAccessLastChange, 
--                       rsVacmViewTreeFamilyLastChange, 
--                       rsSnmpCommunityLastChange }
--     STATUS          mandatory
--     DESCRIPTION     
--             "A collection of objects providing 
--              configuration and monitoring capabilites of SNMP v3
--              Protocol on a given device."
--     ::= { rsSnmpGroups 1 }

rsSnmpMibCompliance OBJECT IDENTIFIER
    ::= { rsSnmpCompliances 1 }

-- rsSnmpMibCompliance MODULE-COMPLIANCE
--     STATUS          mandatory
--     DESCRIPTION     
--             "The compliance statement for device support of 
--              extended SNMP v3 support."

--     MODULE          -- -- this module

--         MANDATORY-GROUPS    { rsSnmpBaseGroup }

--     ::= { rsSnmpCompliances 1 }

END -- end of module RIVERSTONE-SNMP-MIB.
