--
-- This SMIv1 module has been generated by smidump 0.2-cvs. Do not edit.
--

SONUS-COMMUNICATOR-MIB DEFINITIONS ::= BEGIN

IMPORTS
    OBJECT-TYPE
        FROM RFC-1212
    TRAP-TYPE
        FROM RFC-1215
    sonusEventClass, sonusEventDescription, sonusEventLevel, 
    sonusEventTime
        FROM SONUS-COMMON-MIB
    sonusHostID
        FROM SONUS-HOST-MIB
    sonusServicesMIBs
        FROM SONUS-SMI;

sonusCommunicatorMIB OBJECT IDENTIFIER
    ::= { sonusServicesMIBs 21 }

-- sonusCommunicatorMIB MODULE-IDENTITY
--     LAST-UPDATED    "201506160000Z"
--     ORGANIZATION    
--             "Sonus Networks, Inc."
--     CONTACT-INFO    
--             "   Customer Support    
--              Sonus Networks, Inc.
--              250 Apollo Drive
--              Chelmsford, MA 01824
--              USA
--              
--              Tel: 978-614-8100
--              Fax: 978-614-8609"
--     DESCRIPTION     
--             "The MIB Module for Sonus Communicator Management."
--     ::= { sonusServicesMIBs 21 }


sonusCommMIBObjects OBJECT IDENTIFIER
    ::= { sonusCommunicatorMIB 1 }

sonusCommMIBNotifications OBJECT IDENTIFIER
    ::= { sonusCommMIBObjects 1 }

sonusCommMIBNotificationsPrefix OBJECT IDENTIFIER
    ::= { sonusCommMIBNotifications 0 }

sonusCommMIBNotificationsObjects OBJECT IDENTIFIER
    ::= { sonusCommMIBNotifications 1 }

sonusCommProcMgmtMIBObjects OBJECT IDENTIFIER
    ::= { sonusCommunicatorMIB 2 }

sonusCommProcMgmtMIBNotifications OBJECT IDENTIFIER
    ::= { sonusCommProcMgmtMIBObjects 1 }

sonusCommProcMgmtMIBNotificationsPrefix OBJECT IDENTIFIER
    ::= { sonusCommProcMgmtMIBNotifications 0 }

sonusCommProcMgmtMIBNotificationsObjects OBJECT IDENTIFIER
    ::= { sonusCommProcMgmtMIBNotifications 1 }

sonusCommProcMgmtProcessName OBJECT-TYPE
    SYNTAX          DisplayString (SIZE(0..50))
    ACCESS          read-only
    STATUS          mandatory
    DESCRIPTION     
            "This object defines the process name."
    ::= { sonusCommProcMgmtMIBNotificationsObjects 1 }

sonusCommChassisStartupNotification TRAP-TYPE
    ENTERPRISE      sonusCommMIBNotifications
    VARIABLES       { sonusEventTime, sonusEventDescription, 
                      sonusEventClass, sonusEventLevel, sonusHostID }
--     STATUS          mandatory
    DESCRIPTION     
            "The Sonus Communicator Chassis has started."
    ::= 1

sonusCommChassisTestNotification TRAP-TYPE
    ENTERPRISE      sonusCommMIBNotifications
    VARIABLES       { sonusEventTime, sonusEventDescription, 
                      sonusEventClass, sonusEventLevel, sonusHostID }
--     STATUS          mandatory
    DESCRIPTION     
            "Chassis Test Trap."
    ::= 2

sonusCommChassisCriticalTestNotification TRAP-TYPE
    ENTERPRISE      sonusCommMIBNotifications
    VARIABLES       { sonusEventTime, sonusEventDescription, 
                      sonusEventClass, sonusEventLevel, sonusHostID }
--     STATUS          mandatory
    DESCRIPTION     
            "Test Trap with CRITICAL severity."
    ::= 3

sonusCommChassisMajorTestNotification TRAP-TYPE
    ENTERPRISE      sonusCommMIBNotifications
    VARIABLES       { sonusEventTime, sonusEventDescription, 
                      sonusEventClass, sonusEventLevel, sonusHostID }
--     STATUS          mandatory
    DESCRIPTION     
            "Test Trap with MAJOR severity.."
    ::= 4

sonusCommChassisMinorTestNotification TRAP-TYPE
    ENTERPRISE      sonusCommMIBNotifications
    VARIABLES       { sonusEventTime, sonusEventDescription, 
                      sonusEventClass, sonusEventLevel, sonusHostID }
--     STATUS          mandatory
    DESCRIPTION     
            "Test Trap with MINOR severity."
    ::= 5

sonusCommChassisWarnTestNotification TRAP-TYPE
    ENTERPRISE      sonusCommMIBNotifications
    VARIABLES       { sonusEventTime, sonusEventDescription, 
                      sonusEventClass, sonusEventLevel, sonusHostID }
--     STATUS          mandatory
    DESCRIPTION     
            "Test Trap with WARN severity"
    ::= 6

sonusCommChassisClearTestNotification TRAP-TYPE
    ENTERPRISE      sonusCommMIBNotifications
    VARIABLES       { sonusEventTime, sonusEventDescription, 
                      sonusEventClass, sonusEventLevel, sonusHostID }
--     STATUS          mandatory
    DESCRIPTION     
            "Test Trap with CLEARING severity"
    ::= 7

sonusHostPMStatsFileGenerationFailedNotification TRAP-TYPE
    ENTERPRISE      sonusCommMIBNotifications
    VARIABLES       { sonusEventTime, sonusEventDescription, 
                      sonusEventClass, sonusEventLevel, sonusHostID }
--     STATUS          mandatory
    DESCRIPTION     
            "Generation of Performace Statistics tar file failed.  Detailed message is specified in sonusEventDescription."
    ::= 8

sonusCommProcMgmtProcessRestartedNotification TRAP-TYPE
    ENTERPRISE      sonusCommProcMgmtMIBNotifications
    VARIABLES       { sonusEventTime, sonusEventDescription, 
                      sonusEventClass, sonusEventLevel, 
                      sonusCommProcMgmtProcessName, sonusHostID }
--     STATUS          mandatory
    DESCRIPTION     
            "The process specified by sonusCommProcMgmtProcessName has been restarted by Process Management.  This will occur when Process Management's status request has failed a specified number of times."
    ::= 1

sonusCommProcMgmtProcessRestartFailureNotification TRAP-TYPE
    ENTERPRISE      sonusCommProcMgmtMIBNotifications
    VARIABLES       { sonusEventTime, sonusEventDescription, 
                      sonusEventClass, sonusEventLevel, 
                      sonusCommProcMgmtProcessName, sonusHostID }
--     STATUS          mandatory
    DESCRIPTION     
            "An attempt to restart the process specified by sonusCommProcMgmtProcessName by Process Management has failed."
    ::= 2

sonusCommProcMgmtGiveUpRestartNotification TRAP-TYPE
    ENTERPRISE      sonusCommProcMgmtMIBNotifications
    VARIABLES       { sonusEventTime, sonusEventDescription, 
                      sonusEventClass, sonusEventLevel, 
                      sonusCommProcMgmtProcessName, sonusHostID }
--     STATUS          mandatory
    DESCRIPTION     
            "Process Management has given up attempting to restart the specified process.  This will occur after Process Management has failed to restart the process a specified number of times over a specified time interval."
    ::= 3

END -- end of module SONUS-COMMUNICATOR-MIB.
