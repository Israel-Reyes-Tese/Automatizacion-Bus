--
-- This SMIv1 module has been generated by smidump 0.2-cvs. Do not edit.
--

SONUS-ANNOUNCEMENT-RESOURCES-MIB DEFINITIONS ::= BEGIN

IMPORTS
    OBJECT-TYPE
        FROM RFC-1212
    TRAP-TYPE
        FROM RFC-1215
    sonusEventClass, sonusEventDescription, sonusEventLevel, 
    sonusEventTime, sonusSequenceId, sonusShelfIndex, sonusSlotIndex
        FROM SONUS-COMMON-MIB
    sonusResourcesMIBs
        FROM SONUS-SMI
    SonusBoolean, SonusShelfIndex, SonusSlotIndex
        FROM SONUS-TC;

sonusAnnouncementResourcesMIB OBJECT IDENTIFIER
    ::= { sonusResourcesMIBs 5 }

-- sonusAnnouncementResourcesMIB MODULE-IDENTITY
--     LAST-UPDATED    "200703280000Z"
--     ORGANIZATION    
--             "Sonus Networks, Inc."
--     CONTACT-INFO    
--             "   Customer Support    
--              Sonus Networks, Inc.
--              7 Technology Park Drive
--              Westford, MA 01886
--              USA
--              
--              Tel: 978-614-8100
--              Fax: 978-614-8609"
--     DESCRIPTION     
--             "The MIB Module for Announcements."
--     ::= { sonusResourcesMIBs 5 }


sonusAnnouncementResourcesMIBObjects OBJECT IDENTIFIER
    ::= { sonusAnnouncementResourcesMIB 1 }

sonusAnnSegStatTable OBJECT-TYPE
    SYNTAX          SEQUENCE OF SonusAnnSegStatEntry
    ACCESS          not-accessible
    STATUS          mandatory
    DESCRIPTION     
            "This table contains Announcement Segment File statistics"
    ::= { sonusAnnouncementResourcesMIBObjects 1 }

sonusAnnSegStatEntry OBJECT-TYPE
    SYNTAX          SonusAnnSegStatEntry
    ACCESS          not-accessible
    STATUS          mandatory
    DESCRIPTION     
            ""
    INDEX           { sonusAnnSegStatSegId }
    ::= { sonusAnnSegStatTable 1 }

SonusAnnSegStatEntry ::=
    SEQUENCE {
        sonusAnnSegStatSegId            INTEGER,
        sonusAnnSegStatLength           INTEGER,
        sonusAnnSegStatVersion          INTEGER,
        sonusAnnSegStatPreload          SonusBoolean,
        sonusAnnSegStatNfsPath          DisplayString
    }

sonusAnnSegStatSegId OBJECT-TYPE
    SYNTAX          INTEGER
    ACCESS          read-only
    STATUS          mandatory
    DESCRIPTION     
            "Represents the segment identity"
    ::= { sonusAnnSegStatEntry 1 }

sonusAnnSegStatLength OBJECT-TYPE
    SYNTAX          INTEGER
    ACCESS          read-only
    STATUS          mandatory
    DESCRIPTION     
            "Represents segment length in bytes"
    ::= { sonusAnnSegStatEntry 2 }

sonusAnnSegStatVersion OBJECT-TYPE
    SYNTAX          INTEGER
    ACCESS          read-only
    STATUS          mandatory
    DESCRIPTION     
            "Represents number of segment file modifications detected"
    ::= { sonusAnnSegStatEntry 3 }

sonusAnnSegStatPreload OBJECT-TYPE
    SYNTAX          SonusBoolean
    ACCESS          read-only
    STATUS          mandatory
    DESCRIPTION     
            "If TRUE, servers load segment during initialization rather
             than at first playback"
    ::= { sonusAnnSegStatEntry 4 }

sonusAnnSegStatNfsPath OBJECT-TYPE
    SYNTAX          DisplayString (SIZE(0..63))
    ACCESS          read-only
    STATUS          mandatory
    DESCRIPTION     
            "Represents the NFS pathname of the segment file"
    ::= { sonusAnnSegStatEntry 5 }

sonusAnnSegMemStatTable OBJECT-TYPE
    SYNTAX          SEQUENCE OF SonusAnnSegMemStatEntry
    ACCESS          not-accessible
    STATUS          mandatory
    DESCRIPTION     
            "This table contains Announcement Segment Memory statistics"
    ::= { sonusAnnouncementResourcesMIBObjects 2 }

sonusAnnSegMemStatEntry OBJECT-TYPE
    SYNTAX          SonusAnnSegMemStatEntry
    ACCESS          not-accessible
    STATUS          mandatory
    DESCRIPTION     
            ""
    INDEX           { sonusAnnSegMemStatShelfIndex, 
                      sonusAnnSegMemStatSlotIndex }
    ::= { sonusAnnSegMemStatTable 1 }

SonusAnnSegMemStatEntry ::=
    SEQUENCE {
        sonusAnnSegMemStatShelfIndex    SonusShelfIndex,
        sonusAnnSegMemStatSlotIndex     SonusSlotIndex,
        sonusAnnSegMemStatNumSegs       INTEGER,
        sonusAnnSegMemStatTotalBytes    INTEGER,
        sonusAnnSegMemStatUsedBytes     INTEGER
    }

sonusAnnSegMemStatShelfIndex OBJECT-TYPE
    SYNTAX          SonusShelfIndex
    ACCESS          read-only
    STATUS          mandatory
    DESCRIPTION     
            "Shelf index for this table"
    ::= { sonusAnnSegMemStatEntry 1 }

sonusAnnSegMemStatSlotIndex OBJECT-TYPE
    SYNTAX          SonusSlotIndex
    ACCESS          read-only
    STATUS          mandatory
    DESCRIPTION     
            "Slot index for this table"
    ::= { sonusAnnSegMemStatEntry 2 }

sonusAnnSegMemStatNumSegs OBJECT-TYPE
    SYNTAX          INTEGER
    ACCESS          read-only
    STATUS          mandatory
    DESCRIPTION     
            "Represents the number of segments server has loaded"
    ::= { sonusAnnSegMemStatEntry 3 }

sonusAnnSegMemStatTotalBytes OBJECT-TYPE
    SYNTAX          INTEGER
    ACCESS          read-only
    STATUS          mandatory
    DESCRIPTION     
            "Represents the server's segment memory size in bytes"
    ::= { sonusAnnSegMemStatEntry 4 }

sonusAnnSegMemStatUsedBytes OBJECT-TYPE
    SYNTAX          INTEGER
    ACCESS          read-only
    STATUS          mandatory
    DESCRIPTION     
            "Represents the number of segment memory bytes used by
             all loaded segments.  Segment memory is composed of 2K
             byte blocks.  Therefore the actual number of bytes used by
             each segment is equal to the segment length rounded up to
             the next 2K byte boundary."
    ::= { sonusAnnSegMemStatEntry 5 }

sonusAnnSegPlayStatTable OBJECT-TYPE
    SYNTAX          SEQUENCE OF SonusAnnSegPlayStatEntry
    ACCESS          not-accessible
    STATUS          mandatory
    DESCRIPTION     
            "This table contains Announcement Segment Playback statistics"
    ::= { sonusAnnouncementResourcesMIBObjects 3 }

sonusAnnSegPlayStatEntry OBJECT-TYPE
    SYNTAX          SonusAnnSegPlayStatEntry
    ACCESS          not-accessible
    STATUS          mandatory
    DESCRIPTION     
            ""
    INDEX           { sonusAnnSegPlayStatShelfIndex, 
                      sonusAnnSegPlayStatSlotIndex, 
                      sonusAnnSegPlayStatSegId }
    ::= { sonusAnnSegPlayStatTable 1 }

SonusAnnSegPlayStatEntry ::=
    SEQUENCE {
        sonusAnnSegPlayStatShelfIndex   SonusShelfIndex,
        sonusAnnSegPlayStatSlotIndex    SonusSlotIndex,
        sonusAnnSegPlayStatSegId        INTEGER,
        sonusAnnSegPlayStatVersion      INTEGER,
        sonusAnnSegPlayStatState        INTEGER,
        sonusAnnSegPlayStatDelOnceFree  SonusBoolean,
        sonusAnnSegPlayStatUseCount     INTEGER
--         sonusAnnSegPlayStatTotalPlays   Counter64
    }

sonusAnnSegPlayStatShelfIndex OBJECT-TYPE
    SYNTAX          SonusShelfIndex
    ACCESS          read-only
    STATUS          mandatory
    DESCRIPTION     
            "Shelf index for this table"
    ::= { sonusAnnSegPlayStatEntry 1 }

sonusAnnSegPlayStatSlotIndex OBJECT-TYPE
    SYNTAX          SonusSlotIndex
    ACCESS          read-only
    STATUS          mandatory
    DESCRIPTION     
            "Slot index for this table"
    ::= { sonusAnnSegPlayStatEntry 2 }

sonusAnnSegPlayStatSegId OBJECT-TYPE
    SYNTAX          INTEGER
    ACCESS          read-only
    STATUS          mandatory
    DESCRIPTION     
            "SegId index for this table"
    ::= { sonusAnnSegPlayStatEntry 3 }

sonusAnnSegPlayStatVersion OBJECT-TYPE
    SYNTAX          INTEGER
    ACCESS          read-only
    STATUS          mandatory
    DESCRIPTION     
            "Represents version of segment currently loaded"
    ::= { sonusAnnSegPlayStatEntry 4 }

sonusAnnSegPlayStatState OBJECT-TYPE
    SYNTAX          INTEGER { notPresent(0), loading(1), loaded(2), 
                        updatePending(3) }
    ACCESS          read-only
    STATUS          mandatory
    DESCRIPTION     
            "Represents current state of the segment"
    ::= { sonusAnnSegPlayStatEntry 5 }

sonusAnnSegPlayStatDelOnceFree OBJECT-TYPE
    SYNTAX          SonusBoolean
    ACCESS          read-only
    STATUS          mandatory
    DESCRIPTION     
            "If TRUE, the current version of segment data will be
             deleted from memory once sonusAnnSegPlayStatUseCount
             drops to zero.  If a new version of the segment exists,
             then the new segment data will be automatically loaded."
    ::= { sonusAnnSegPlayStatEntry 6 }

sonusAnnSegPlayStatUseCount OBJECT-TYPE
    SYNTAX          INTEGER
    ACCESS          read-only
    STATUS          mandatory
    DESCRIPTION     
            "Represents the number of calls currently playing this
             segment"
    ::= { sonusAnnSegPlayStatEntry 7 }

-- sonusAnnSegPlayStatTotalPlays OBJECT-TYPE
--     SYNTAX          Counter64
--     ACCESS          read-only
--     STATUS          mandatory
--     DESCRIPTION     
--             "Represents the cumulative number of times this version of
--              the segment has been played since it was loaded"
--     ::= { sonusAnnSegPlayStatEntry 8 }

sonusAnnouncementAdmnObjects OBJECT IDENTIFIER
    ::= { sonusAnnouncementResourcesMIBObjects 4 }

sonusAnnouncementDisk OBJECT-TYPE
    SYNTAX          INTEGER { nfsServer(1), localDisk(2) }
    ACCESS          read-write
    STATUS          mandatory
    DESCRIPTION     
            "Selects the disk location where announcement files are obtained from.
             The local disk option is available for MNS modules with a local
             disk physically present."
    ::= { sonusAnnouncementAdmnObjects 1 }

sonusAnnouncementDirectory OBJECT-TYPE
    SYNTAX          DisplayString (SIZE(1..63))
    ACCESS          read-write
    STATUS          mandatory
    DESCRIPTION     
            "Controls the directory under the disk mount point where announcement
             files are obtained from."
    ::= { sonusAnnouncementAdmnObjects 2 }

sonusAnnouncementResourcesMIBNotifications OBJECT IDENTIFIER
    ::= { sonusAnnouncementResourcesMIB 2 }

sonusAnnouncementResourcesMIBNotificationsPrefix OBJECT IDENTIFIER
    ::= { sonusAnnouncementResourcesMIBNotifications 0 }

sonusAnnouncementResourcesMIBNotificationsObjects OBJECT IDENTIFIER
    ::= { sonusAnnouncementResourcesMIBNotifications 1 }

sonusAresUnavailCount OBJECT-TYPE
    SYNTAX          INTEGER
    ACCESS          read-only
    STATUS          mandatory
    DESCRIPTION     
            "Represents number of announcement resource allocate failures
             since the rising threshold was met."
    ::= { sonusAnnouncementResourcesMIBNotificationsObjects 1 }

sonusAnnSegMemFullCount OBJECT-TYPE
    SYNTAX          INTEGER
    ACCESS          read-only
    STATUS          mandatory
    DESCRIPTION     
            "Represents number of times an announcement cound not be
             loaded because segment memory was full for a given slot."
    ::= { sonusAnnouncementResourcesMIBNotificationsObjects 2 }

sonusAnnouncementFileNotFoundNotification TRAP-TYPE
    ENTERPRISE      sonusAnnouncementResourcesMIBNotifications
    VARIABLES       { sonusAnnSegStatSegId, sonusShelfIndex, 
                      sonusSlotIndex, sonusEventDescription, 
                      sonusEventClass, sonusEventLevel, sonusSequenceId, 
                      sonusEventTime }
--     STATUS          mandatory
    DESCRIPTION     
            "This trap indicates that the requested segment file
             could not be found.  The segment file must be copied
             into either the <node>/announcement/preload or
             or <node>/announcement/ondemand directory."
    ::= 1

sonusAnnouncementFileFoundNotification TRAP-TYPE
    ENTERPRISE      sonusAnnouncementResourcesMIBNotifications
    VARIABLES       { sonusAnnSegStatSegId, sonusAnnSegStatNfsPath, 
                      sonusShelfIndex, sonusSlotIndex, 
                      sonusEventDescription, sonusEventClass, 
                      sonusEventLevel }
--     STATUS          deprecated
    DESCRIPTION     
            "This trap had been replaced by sonusAnnounceFileFoundNotification
             in V04.01.03R000 & beyond."
    ::= 2

sonusAnnouncementFileInvalidNotification TRAP-TYPE
    ENTERPRISE      sonusAnnouncementResourcesMIBNotifications
    VARIABLES       { sonusAnnSegStatSegId, sonusAnnSegStatNfsPath, 
                      sonusEventDescription, sonusEventClass, 
                      sonusEventLevel, sonusSequenceId, sonusEventTime }
--     STATUS          mandatory
    DESCRIPTION     
            "This trap indicates that the specified segment file contains
             one or more format errors.  Check SYS log for more detail."
    ::= 3

sonusAnnouncementFileValidNotification TRAP-TYPE
    ENTERPRISE      sonusAnnouncementResourcesMIBNotifications
    VARIABLES       { sonusAnnSegStatNfsPath, sonusEventDescription, 
                      sonusEventClass, sonusEventLevel, 
                      sonusAnnSegStatSegId, sonusSequenceId, 
                      sonusEventTime }
--     STATUS          mandatory
    DESCRIPTION     
            "This trap indicates that previously invalid segment file
             has been replaced by a valid segment file."
    ::= 4

sonusAnnouncementSegmentLoadFailureNotification TRAP-TYPE
    ENTERPRISE      sonusAnnouncementResourcesMIBNotifications
    VARIABLES       { sonusShelfIndex, sonusSlotIndex, 
                      sonusAnnSegStatSegId, sonusAnnSegStatVersion, 
                      sonusAnnSegStatLength, sonusAnnSegMemFullCount, 
                      sonusEventDescription, sonusEventClass, 
                      sonusEventLevel, sonusSequenceId, sonusEventTime }
--     STATUS          mandatory
    DESCRIPTION     
            "This trap indicates that announcement segment could not
             be loaded because segment memory on the specified card is
             full.  Segment ID, Version and Length pertain to the most
             		 recent segment load failure.  Verify the length of this
             		 segment is within reason."
    ::= 5

sonusAnnouncementResUnavailRisingThresholdNotification TRAP-TYPE
    ENTERPRISE      sonusAnnouncementResourcesMIBNotifications
    VARIABLES       { sonusShelfIndex, sonusSlotIndex, 
                      sonusEventDescription, sonusEventClass, 
                      sonusEventLevel, sonusSequenceId, sonusEventTime }
--     STATUS          mandatory
    DESCRIPTION     
            "This trap indicates that all announcement resources on
             the specified card are in use."
    ::= 6

sonusAnnouncementResUnavailFallingThresholdNotification TRAP-TYPE
    ENTERPRISE      sonusAnnouncementResourcesMIBNotifications
    VARIABLES       { sonusShelfIndex, sonusSlotIndex, 
                      sonusAresUnavailCount, sonusEventDescription, 
                      sonusEventClass, sonusEventLevel, sonusSequenceId, 
                      sonusEventTime }
--     STATUS          mandatory
    DESCRIPTION     
            "This trap indicates that announcement resource usage on
             the specified card has dropped below a threshold."
    ::= 7

sonusAnnounceFileFoundNotification TRAP-TYPE
    ENTERPRISE      sonusAnnouncementResourcesMIBNotifications
    VARIABLES       { sonusAnnSegStatSegId, sonusAnnSegStatNfsPath, 
                      sonusEventDescription, sonusEventClass, 
                      sonusEventLevel, sonusSequenceId, sonusEventTime }
--     STATUS          mandatory
    DESCRIPTION     
            "This trap indicates that a segment file, which
             previously cound not be found, was found."
    ::= 8

END -- end of module SONUS-ANNOUNCEMENT-RESOURCES-MIB.
