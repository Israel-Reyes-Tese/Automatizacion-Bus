--
-- This SMIv1 module has been generated by smidump 0.2-cvs. Do not edit.
--

SONUS-GEN2-SOFTWARE-UPGRADE-SERVICES-MIB DEFINITIONS ::= BEGIN

IMPORTS
    OBJECT-TYPE
        FROM RFC-1212
    Counter, Gauge, IpAddress
        FROM RFC1155-SMI
    DateAndTime, RowStatus
        FROM SNMPv2-TC
    sonusCommonSoftwarePlatformServicesMIBs
        FROM SONUS-SMI;

sonusGen2SoftwareUpgradeMIB OBJECT IDENTIFIER
    ::= { sonusCommonSoftwarePlatformServicesMIBs 9 }

-- sonusGen2SoftwareUpgradeMIB MODULE-IDENTITY
--     LAST-UPDATED    "200906010000Z"
--     ORGANIZATION    
--             "Sonus Networks, Inc."
--     CONTACT-INFO    
--             "Customer Support        
--              Sonus Networks, Inc.    
--              7 Technology Park Drive 
--              Westford, MA 01886      
--              USA                     
--                                      
--              Tel: 978-614-8100       
--              Fax: 978-614-8609"
--     DESCRIPTION     
--             "
--              The MIB Module for Software Upgrade Configuration.
--              "
--     REVISION        "200906010000Z"
--     DESCRIPTION     
--             "Auto generated MIB."
--     ::= { sonusCommonSoftwarePlatformServicesMIBs 9 }


Token ::=
    OCTET STRING

-- Token ::= TEXTUAL-CONVENTION
--     DISPLAY-HINT    "1t"
--     STATUS          mandatory
--     DESCRIPTION     
--             "xs:token"
--     SYNTAX          OCTET STRING

String ::=
    OCTET STRING

-- String ::= TEXTUAL-CONVENTION
--     DISPLAY-HINT    "1t"
--     STATUS          mandatory
--     DESCRIPTION     
--             "xs:string"
--     SYNTAX          OCTET STRING

SonusSwUpgradeShelfAdmnDirectoryType ::=
    OCTET STRING (SIZE(0..255))

-- SonusSwUpgradeShelfAdmnDirectoryType ::= TEXTUAL-CONVENTION
--     DISPLAY-HINT    "1t"
--     STATUS          mandatory
--     DESCRIPTION     
--             ""
--     SYNTAX          OCTET STRING (SIZE(0..255))

SonusSwUpgradeShelfStatStatusType ::=
    INTEGER { idle(1), busy(2), complete(3), incomplete(4), 
                        commitRequired(5) }

-- SonusSwUpgradeShelfStatStatusType ::= TEXTUAL-CONVENTION
--     STATUS          mandatory
--     DESCRIPTION     
--             "
--              "
--     SYNTAX          INTEGER
--                       { idle(1), busy(2), complete(3), incomplete(4), 
--                         commitRequired(5) }

SonusSwUpgradeShelfStatLastReasonType ::=
    INTEGER { none(0), successfulCompletion(1), initTimeout(2), 
                        manualHalt(3), upgradeNotRequired(4), 
                        fileUnavailable(5), parametersNotSaved(6), 
                        flashUpdateInProgress(7), redundSlotActive(8), 
                        switchover1Timeout(9), sync1Timeout(10), 
                        switchover2Timeout(11), sync2Timeout(12), 
                        rebootTimeout(13), mnsNotSynced(14), 
                        notActive(15), internalTimerUnavailable(16), 
                        internalQueryTimeout(17), 
                        internalResourceUnavailable(18), 
                        internalRtmError(19), mnsSwitchover(20), 
                        overallSyncTimeout(21), unexpectedSwitchover(22), 
                        syncFailure(23), skipUnprotectedModules(24), 
                        invalidVersion(25), matrixFileUnavailable(26), 
                        unsupportedUpgradePath(27), 
                        mnsLocalDisksNotSynced(28), nvsReadError(29), 
                        nvsNotValid(30), 
                        unsupportedAcctUpgradePatchVer(31) }

-- SonusSwUpgradeShelfStatLastReasonType ::= TEXTUAL-CONVENTION
--     STATUS          mandatory
--     DESCRIPTION     
--             "
--              "
--     SYNTAX          INTEGER
--                       { none(0), successfulCompletion(1), 
--                         initTimeout(2), manualHalt(3), 
--                         upgradeNotRequired(4), fileUnavailable(5), 
--                         parametersNotSaved(6), 
--                         flashUpdateInProgress(7), redundSlotActive(8), 
--                         switchover1Timeout(9), sync1Timeout(10), 
--                         switchover2Timeout(11), sync2Timeout(12), 
--                         rebootTimeout(13), mnsNotSynced(14), 
--                         notActive(15), internalTimerUnavailable(16), 
--                         internalQueryTimeout(17), 
--                         internalResourceUnavailable(18), 
--                         internalRtmError(19), mnsSwitchover(20), 
--                         overallSyncTimeout(21), 
--                         unexpectedSwitchover(22), syncFailure(23), 
--                         skipUnprotectedModules(24), 
--                         invalidVersion(25), matrixFileUnavailable(26), 
--                         unsupportedUpgradePath(27), 
--                         mnsLocalDisksNotSynced(28), nvsReadError(29), 
--                         nvsNotValid(30), 
--                         unsupportedAcctUpgradePatchVer(31) }

SonusSwUpgradeSlotStatUpgradeType ::=
    INTEGER { none(1), smooth(2), disrupt(3), unavailable(4), unknown(5) }

-- SonusSwUpgradeSlotStatUpgradeType ::= TEXTUAL-CONVENTION
--     STATUS          mandatory
--     DESCRIPTION     
--             "
--              "
--     SYNTAX          INTEGER
--                       { none(1), smooth(2), disrupt(3), 
--                         unavailable(4), unknown(5) }

SonusSwUpgradeSlotStatVersionType ::=
    OCTET STRING (SIZE(0..255))

-- SonusSwUpgradeSlotStatVersionType ::= TEXTUAL-CONVENTION
--     DISPLAY-HINT    "1t"
--     STATUS          mandatory
--     DESCRIPTION     
--             ""
--     SYNTAX          OCTET STRING (SIZE(0..255))

SonusSwUpgradeShelfAdmnUnprotectedControlType ::=
    INTEGER { upgrade(1), skip(2) }

-- SonusSwUpgradeShelfAdmnUnprotectedControlType ::= TEXTUAL-CONVENTION
--     STATUS          mandatory
--     DESCRIPTION     
--             "
--              "
--     SYNTAX          INTEGER
--                       { upgrade(1), skip(2) }

SonusSoftwareUpgradeState ::=
    INTEGER { idle(0), query(1), init(2), delay1(3), start(4), sxOne(5), 
                        waitSync(6), sxTwoTx(7), sxTwoRx(8), 
                        sxTwoWait(9), variant(10), prepare(11), 
                        stopCalls(12), firstPns(13), cnsReset(14), 
                        spsReset(15), pnsReset(16), sxDelay(17), 
                        done(18), redundOosReset(19), redundOosWait(20), 
                        groupSetup(21), clientSx(22), clientRevert(23), 
                        groupRestore(24), firstUnprotectedReset(25), 
                        secondUnprotectedReset(26), parameterSave(27) }

-- SonusSoftwareUpgradeState ::= TEXTUAL-CONVENTION
--     STATUS          mandatory
--     DESCRIPTION     
--             "
--              Represents the different states in LSWU FSM. (Internal use only)
--              "
--     SYNTAX          INTEGER
--                       { idle(0), query(1), init(2), delay1(3), 
--                         start(4), sxOne(5), waitSync(6), sxTwoTx(7), 
--                         sxTwoRx(8), sxTwoWait(9), variant(10), 
--                         prepare(11), stopCalls(12), firstPns(13), 
--                         cnsReset(14), spsReset(15), pnsReset(16), 
--                         sxDelay(17), done(18), redundOosReset(19), 
--                         redundOosWait(20), groupSetup(21), 
--                         clientSx(22), clientRevert(23), 
--                         groupRestore(24), firstUnprotectedReset(25), 
--                         secondUnprotectedReset(26), parameterSave(27) }

SonusSwUpgradeShelfAdmnOverrideFeatureCheckType ::=
    INTEGER { ready(1), override(2) }

-- SonusSwUpgradeShelfAdmnOverrideFeatureCheckType ::= TEXTUAL-CONVENTION
--     STATUS          mandatory
--     DESCRIPTION     
--             "
--              "
--     SYNTAX          INTEGER
--                       { ready(1), override(2) }

SonusSwUpgradeSlotStatStatusType ::=
    INTEGER { idle(1), busy(2), complete(3), unknown(4), noImageFile(5), 
                        invalidVersion(6) }

-- SonusSwUpgradeSlotStatStatusType ::= TEXTUAL-CONVENTION
--     STATUS          mandatory
--     DESCRIPTION     
--             "
--              "
--     SYNTAX          INTEGER
--                       { idle(1), busy(2), complete(3), unknown(4), 
--                         noImageFile(5), invalidVersion(6) }

SonusSwUpgradeShelfAdmnCommitDirectoryType ::=
    INTEGER { ready(1), commit(2) }

-- SonusSwUpgradeShelfAdmnCommitDirectoryType ::= TEXTUAL-CONVENTION
--     STATUS          mandatory
--     DESCRIPTION     
--             "
--              "
--     SYNTAX          INTEGER
--                       { ready(1), commit(2) }

sonusSwUpgradeServices OBJECT IDENTIFIER
    ::= { sonusGen2SoftwareUpgradeMIB 1 }

sonusSwUpgradeServicesShelfAdmnTable OBJECT-TYPE
    SYNTAX          SEQUENCE OF SonusSwUpgradeServicesShelfAdmnEntry
    ACCESS          not-accessible
    STATUS          mandatory
    DESCRIPTION     
            "
             This table specifies the software upgrade configuration.
             "
    ::= { sonusSwUpgradeServices 1 }

sonusSwUpgradeServicesShelfAdmnEntry OBJECT-TYPE
    SYNTAX          SonusSwUpgradeServicesShelfAdmnEntry
    ACCESS          not-accessible
    STATUS          mandatory
    DESCRIPTION     
            ""
    INDEX           { sonusSwUpgradeServicesShelfAdmnShelf }
    ::= { sonusSwUpgradeServicesShelfAdmnTable 1 }

SonusSwUpgradeServicesShelfAdmnEntry ::=
    SEQUENCE {
        sonusSwUpgradeServicesShelfAdmnShelf    Gauge,
        sonusSwUpgradeServicesShelfAdmnCommitDirectory              SonusSwUpgradeShelfAdmnCommitDirectoryType,
        sonusSwUpgradeServicesShelfAdmnDirectory        SonusSwUpgradeShelfAdmnDirectoryType,
        sonusSwUpgradeServicesShelfAdmnOverrideFeatureCheck                   SonusSwUpgradeShelfAdmnOverrideFeatureCheckType,
        sonusSwUpgradeServicesShelfAdmnUnprotectedControl                 SonusSwUpgradeShelfAdmnUnprotectedControlType,
        sonusSwUpgradeServicesShelfAdmnRowstatus        RowStatus
    }

sonusSwUpgradeServicesShelfAdmnShelf OBJECT-TYPE
    SYNTAX          Gauge (1..6)
    ACCESS          not-accessible
    STATUS          mandatory
    DESCRIPTION     
            "
             The shelf index of this software upgrade entry.
             "
    ::= { sonusSwUpgradeServicesShelfAdmnEntry 1 }

sonusSwUpgradeServicesShelfAdmnCommitDirectory OBJECT-TYPE
    SYNTAX          SonusSwUpgradeShelfAdmnCommitDirectoryType
    ACCESS          read-write
    STATUS          mandatory
    DESCRIPTION     
            "
             Commit the new software distribution directory name into NVS.
               
             This MIB object can only be set by a user with admin
             privileges; it always reads as ready(1).
             "
    DEFVAL          { ready }
    ::= { sonusSwUpgradeServicesShelfAdmnEntry 2 }

sonusSwUpgradeServicesShelfAdmnDirectory OBJECT-TYPE
    SYNTAX          SonusSwUpgradeShelfAdmnDirectoryType
    ACCESS          read-write
    STATUS          mandatory
    DESCRIPTION     
            "
             The new software distribution directory name.
               
             This MIB object can only be set by a user with admin
             privileges.
             "
    ::= { sonusSwUpgradeServicesShelfAdmnEntry 3 }

sonusSwUpgradeServicesShelfAdmnOverrideFeatureCheck OBJECT-TYPE
    SYNTAX          SonusSwUpgradeShelfAdmnOverrideFeatureCheckType
    ACCESS          read-write
    STATUS          mandatory
    DESCRIPTION     
            "
             Ignore the check for unsupported features (i.e. features
             that would prevent a software upgrade from occurring) during
             initialization.  This MIB object must be set with
             sonusSwUpgradeShelfAdmnInit in the same request.
               
             This MIB object can only be set through the CLI, and only
             by a user with admin privileges; it always reads as ready(1).
             "
    DEFVAL          { ready }
    ::= { sonusSwUpgradeServicesShelfAdmnEntry 4 }

sonusSwUpgradeServicesShelfAdmnUnprotectedControl OBJECT-TYPE
    SYNTAX          SonusSwUpgradeShelfAdmnUnprotectedControlType
    ACCESS          read-write
    STATUS          mandatory
    DESCRIPTION     
            "
             Controls the handling of server modules that are In Service, but
             not protected by redundancy during a Live Software Upgrade.  This
             MIB object must be set before an upgrade is initialized.
               
             If set to upgrade(1), these server modules will be individually
             reset during the upgrade, thereby dropping any calls they are
             carrying at the time.  This is the default behavior.
               
             If set to skip(2), the upgrade process will exit early, leaving
             these server modules running the old version of software in an
             Out of Service/dryup state.  When calls on these server modules
             are sufficiently dried up, a second upgrade must be initiated by
             the user to complete the shelf upgrade.  It is important not to
             make any configuration changes until the upgrade is completed.
               
             This MIB object can only be set through the CLI, and only by a
             user with admin privileges; the default value is upgrade(1).
             "
    DEFVAL          { upgrade }
    ::= { sonusSwUpgradeServicesShelfAdmnEntry 5 }

sonusSwUpgradeServicesShelfAdmnRowstatus OBJECT-TYPE
    SYNTAX          RowStatus
    ACCESS          read-write
    STATUS          mandatory
    DESCRIPTION     
            ""
    ::= { sonusSwUpgradeServicesShelfAdmnEntry 6 }

sonusSwUpgradeServicesShelfStatusTable OBJECT-TYPE
    SYNTAX          SEQUENCE OF SonusSwUpgradeServicesShelfStatusEntry
    ACCESS          not-accessible
    STATUS          mandatory
    DESCRIPTION     
            "
             This table contains status information about the software upgrade 
             on a shelf.
             "
    ::= { sonusSwUpgradeServices 2 }

sonusSwUpgradeServicesShelfStatusEntry OBJECT-TYPE
    SYNTAX          SonusSwUpgradeServicesShelfStatusEntry
    ACCESS          not-accessible
    STATUS          mandatory
    DESCRIPTION     
            ""
    INDEX           { sonusSwUpgradeServicesShelfStatusShelf }
    ::= { sonusSwUpgradeServicesShelfStatusTable 1 }

SonusSwUpgradeServicesShelfStatusEntry ::=
    SEQUENCE {
        sonusSwUpgradeServicesShelfStatusShelf      Gauge,
        sonusSwUpgradeServicesShelfStatusStatus       SonusSwUpgradeShelfStatStatusType,
        sonusSwUpgradeServicesShelfStatusCurrrentSlot             Gauge,
        sonusSwUpgradeServicesShelfStatusSlotsRemaining               Gauge,
        sonusSwUpgradeServicesShelfStatusGroupsRemaining                INTEGER,
        sonusSwUpgradeServicesShelfStatusDuration         Counter,
        sonusSwUpgradeServicesShelfStatusStartTime          DateAndTime,
        sonusSwUpgradeServicesShelfStatusLastExitReason               SonusSwUpgradeShelfStatLastReasonType,
        sonusSwUpgradeServicesShelfStatusLastState          SonusSoftwareUpgradeState,
        sonusSwUpgradeServicesShelfStatusCurrentState             SonusSoftwareUpgradeState,
        sonusSwUpgradeServicesShelfStatusCurrentRedundancyGroup                       INTEGER
    }

sonusSwUpgradeServicesShelfStatusShelf OBJECT-TYPE
    SYNTAX          Gauge (1..6)
    ACCESS          not-accessible
    STATUS          mandatory
    DESCRIPTION     
            "
             Identifies the target shelf within the node.
             "
    ::= { sonusSwUpgradeServicesShelfStatusEntry 1 }

sonusSwUpgradeServicesShelfStatusStatus OBJECT-TYPE
    SYNTAX          SonusSwUpgradeShelfStatStatusType
    ACCESS          read-only
    STATUS          mandatory
    DESCRIPTION     
            "
             Indicates the software upgrade status of the shelf.
             "
    ::= { sonusSwUpgradeServicesShelfStatusEntry 2 }

sonusSwUpgradeServicesShelfStatusCurrrentSlot OBJECT-TYPE
    SYNTAX          Gauge (1..18)
    ACCESS          read-only
    STATUS          mandatory
    DESCRIPTION     
            "
             Identifies the slot currently being upgraded with new software.
             "
    ::= { sonusSwUpgradeServicesShelfStatusEntry 3 }

sonusSwUpgradeServicesShelfStatusSlotsRemaining OBJECT-TYPE
    SYNTAX          Gauge (1..18)
    ACCESS          read-only
    STATUS          mandatory
    DESCRIPTION     
            "
             Identifies number of slots within the shelf remained to be upgraded.
             "
    ::= { sonusSwUpgradeServicesShelfStatusEntry 4 }

sonusSwUpgradeServicesShelfStatusGroupsRemaining OBJECT-TYPE
    SYNTAX          INTEGER
    ACCESS          read-only
    STATUS          mandatory
    DESCRIPTION     
            "
             
             "
    ::= { sonusSwUpgradeServicesShelfStatusEntry 5 }

sonusSwUpgradeServicesShelfStatusDuration OBJECT-TYPE
    SYNTAX          Counter
    ACCESS          read-only
    STATUS          mandatory
    DESCRIPTION     
            "
             Indicates the duration of the software upgrade in seconds.
             "
    ::= { sonusSwUpgradeServicesShelfStatusEntry 6 }

sonusSwUpgradeServicesShelfStatusStartTime OBJECT-TYPE
    SYNTAX          DateAndTime
    ACCESS          read-only
    STATUS          mandatory
    DESCRIPTION     
            "
             Indicates the start time of the software upgrade
             "
    ::= { sonusSwUpgradeServicesShelfStatusEntry 7 }

sonusSwUpgradeServicesShelfStatusLastExitReason OBJECT-TYPE
    SYNTAX          SonusSwUpgradeShelfStatLastReasonType
    ACCESS          read-only
    STATUS          mandatory
    DESCRIPTION     
            "
             Indicates the exit reason of the last live software upgrade.
             "
    ::= { sonusSwUpgradeServicesShelfStatusEntry 8 }

sonusSwUpgradeServicesShelfStatusLastState OBJECT-TYPE
    SYNTAX          SonusSoftwareUpgradeState
    ACCESS          read-only
    STATUS          mandatory
    DESCRIPTION     
            "
             Indicates the last state of the LSWU FSM. (Internal use only)
             "
    ::= { sonusSwUpgradeServicesShelfStatusEntry 9 }

sonusSwUpgradeServicesShelfStatusCurrentState OBJECT-TYPE
    SYNTAX          SonusSoftwareUpgradeState
    ACCESS          read-only
    STATUS          mandatory
    DESCRIPTION     
            "
             Indicates the current state of the LSWU FSM. (Internal use only)
             "
    ::= { sonusSwUpgradeServicesShelfStatusEntry 10 }

sonusSwUpgradeServicesShelfStatusCurrentRedundancyGroup OBJECT-TYPE
    SYNTAX          INTEGER
    ACCESS          read-only
    STATUS          mandatory
    DESCRIPTION     
            "
             Identifies the Redundancy Group Index currently being upgraded with new software.
             This is the index into the sonusRedundGroupTable MIB table.
             "
    ::= { sonusSwUpgradeServicesShelfStatusEntry 11 }

sonusSwUpgradeServicesSlotStatusTable OBJECT-TYPE
    SYNTAX          SEQUENCE OF SonusSwUpgradeServicesSlotStatusEntry
    ACCESS          not-accessible
    STATUS          mandatory
    DESCRIPTION     
            "
             This table contains status information about the software upgrade 
             on a shelf.
             "
    ::= { sonusSwUpgradeServices 3 }

sonusSwUpgradeServicesSlotStatusEntry OBJECT-TYPE
    SYNTAX          SonusSwUpgradeServicesSlotStatusEntry
    ACCESS          not-accessible
    STATUS          mandatory
    DESCRIPTION     
            ""
    INDEX           { sonusSwUpgradeServicesSlotStatusShelf, 
                      sonusSwUpgradeServicesSlotStatusSlot }
    ::= { sonusSwUpgradeServicesSlotStatusTable 1 }

SonusSwUpgradeServicesSlotStatusEntry ::=
    SEQUENCE {
        sonusSwUpgradeServicesSlotStatusShelf     Gauge,
        sonusSwUpgradeServicesSlotStatusSlot    Gauge,
        sonusSwUpgradeServicesSlotStatusStatus      SonusSwUpgradeSlotStatStatusType,
        sonusSwUpgradeServicesSlotStatusUpgrade       SonusSwUpgradeSlotStatUpgradeType,
        sonusSwUpgradeServicesSlotStatusVersion       SonusSwUpgradeSlotStatVersionType
    }

sonusSwUpgradeServicesSlotStatusShelf OBJECT-TYPE
    SYNTAX          Gauge (1..6)
    ACCESS          not-accessible
    STATUS          mandatory
    DESCRIPTION     
            "
             Identifies the target shelf within the node.
             "
    ::= { sonusSwUpgradeServicesSlotStatusEntry 1 }

sonusSwUpgradeServicesSlotStatusSlot OBJECT-TYPE
    SYNTAX          Gauge (1..18)
    ACCESS          not-accessible
    STATUS          mandatory
    DESCRIPTION     
            "
             Identifies the target slot within the shelf.
             "
    ::= { sonusSwUpgradeServicesSlotStatusEntry 2 }

sonusSwUpgradeServicesSlotStatusStatus OBJECT-TYPE
    SYNTAX          SonusSwUpgradeSlotStatStatusType
    ACCESS          read-only
    STATUS          mandatory
    DESCRIPTION     
            "
             Identifies the software upgrade status of a slot.
             "
    ::= { sonusSwUpgradeServicesSlotStatusEntry 3 }

sonusSwUpgradeServicesSlotStatusUpgrade OBJECT-TYPE
    SYNTAX          SonusSwUpgradeSlotStatUpgradeType
    ACCESS          read-only
    STATUS          mandatory
    DESCRIPTION     
            "
             
             "
    ::= { sonusSwUpgradeServicesSlotStatusEntry 4 }

sonusSwUpgradeServicesSlotStatusVersion OBJECT-TYPE
    SYNTAX          SonusSwUpgradeSlotStatVersionType
    ACCESS          read-only
    STATUS          mandatory
    DESCRIPTION     
            "
             The software version available for upgrade on the slot.
             "
    ::= { sonusSwUpgradeServicesSlotStatusEntry 5 }

END -- end of module SONUS-GEN2-SOFTWARE-UPGRADE-SERVICES-MIB.
