--
-- This SMIv1 module has been generated by smidump 0.2-cvs. Do not edit.
--

RIVERSTONE-VLAN-EXTENSIONS-MIB DEFINITIONS ::= BEGIN

IMPORTS
    dot1dBasePort
        FROM BRIDGE-MIB
    dot1qVlanIndex
        FROM Q-BRIDGE-MIB
    OBJECT-TYPE
        FROM RFC-1212
    Counter
        FROM RFC1155-SMI
    riverstoneMibs
        FROM RIVERSTONE-SMI-MIB;

rsVlanExtensionsMIB OBJECT IDENTIFIER
    ::= { riverstoneMibs 65 }

-- rsVlanExtensionsMIB MODULE-IDENTITY
--     LAST-UPDATED    "200208050000Z"
--     ORGANIZATION    
--             "Riverstone Networks, Inc"
--     CONTACT-INFO    
--             "Riverstone Networks
--              Customer Service
--              
--              Postal:
--              Riverstone Networks, Inc
--              5200 Great America Parkway
--              Santa Clara CA 95054 USA
--              
--              PHONE:+1 408.878.6500
--              EMAIL: nms-eng@riverstonenet.com
--              WEB: http://www.riverstonenet.com"
--     DESCRIPTION     
--             "This module complements VLAN information in qBridgeMIB from RFC2674."
--     REVISION        "200208060000Z"
--     DESCRIPTION     
--             "Initial version of Riverstone VLAN extensions."
--     ::= { riverstoneMibs 65 }


rsVlanObjects OBJECT IDENTIFIER
    ::= { rsVlanExtensionsMIB 1 }

rsVlanStats OBJECT IDENTIFIER
    ::= { rsVlanObjects 10 }

rsPortVlanStatsTable OBJECT-TYPE
    SYNTAX          SEQUENCE OF RsPortVlanStatsEntry
    ACCESS          not-accessible
    STATUS          mandatory
    DESCRIPTION     
            "A table that has statistics not defined in 
             dot1qPortVlanStatisticsTable."
    ::= { rsVlanStats 1 }

rsPortVlanStatsEntry OBJECT-TYPE
    SYNTAX          RsPortVlanStatsEntry
    ACCESS          not-accessible
    STATUS          mandatory
    DESCRIPTION     
            "More traffic statistics for a VLAN on a physical interface."
    INDEX           { dot1dBasePort, dot1qVlanIndex }
    ::= { rsPortVlanStatsTable 1 }

RsPortVlanStatsEntry ::=
    SEQUENCE {
        rsPortVlanInOctets              Counter,
        rsPortVlanOutOctets             Counter,
        rsPortVlanInOverflowOctets      Counter,
        rsPortVlanOutOverflowOctets     Counter
    }

rsPortVlanInOctets OBJECT-TYPE
    SYNTAX          Counter
    ACCESS          read-only
    STATUS          mandatory
    DESCRIPTION     
            "The number of octets of the frames received by this port 
             from its segment that were classified as belonging to this
             VLAN. Note that a frame received on this port is
             counted by this object if and only if it is for a
             protocol being processed by the local forwarding process
             for this VLAN. This object includes received bridge
             management frames classified as belonging to this VLAN
             (e.g. GMRP, but not GVRP or STP)."
    ::= { rsPortVlanStatsEntry 101 }

rsPortVlanOutOctets OBJECT-TYPE
    SYNTAX          Counter
    ACCESS          read-only
    STATUS          mandatory
    DESCRIPTION     
            "The number of octets of the valid frames transmitted 
             by this port from its segment from the local forwarding 
             process for this VLAN. This includes bridge management 
             frames originated by this device which are classified 
             as belonging to this VLAN (e.g. GMRP, but not GVRP or 
             STP)."
    ::= { rsPortVlanStatsEntry 102 }

rsPortVlanInOverflowOctets OBJECT-TYPE
    SYNTAX          Counter
    ACCESS          read-only
    STATUS          mandatory
    DESCRIPTION     
            "The number of times the associated rsPortVlanInOctets
             counter has overflowed."
    ::= { rsPortVlanStatsEntry 103 }

rsPortVlanOutOverflowOctets OBJECT-TYPE
    SYNTAX          Counter
    ACCESS          read-only
    STATUS          mandatory
    DESCRIPTION     
            "The number of times the associated rsPortVlanOutOctets
             counter has overflowed."
    ::= { rsPortVlanStatsEntry 104 }

rsPortVlanHCStatsTable OBJECT-TYPE
    SYNTAX          SEQUENCE OF RsPortVlanHCStatsEntry
    ACCESS          not-accessible
    STATUS          mandatory
    DESCRIPTION     
            "A table that has statistics not defined in 
             dot1qPortVlanHCStatisticsTable."
    ::= { rsVlanStats 2 }

rsPortVlanHCStatsEntry OBJECT-TYPE
    SYNTAX          RsPortVlanHCStatsEntry
    ACCESS          not-accessible
    STATUS          mandatory
    DESCRIPTION     
            "More traffic statistics for a VLAN on a physical interface."
    INDEX           { dot1dBasePort, dot1qVlanIndex }
    ::= { rsPortVlanHCStatsTable 1 }

RsPortVlanHCStatsEntry ::=
    SEQUENCE {
--         rsPortVlanHCInOctets            Counter64,
--         rsPortVlanHCOutOctets           Counter64
    }

-- rsPortVlanHCInOctets OBJECT-TYPE
--     SYNTAX          Counter64
--     ACCESS          read-only
--     STATUS          mandatory
--     DESCRIPTION     
--             "The number of octets of the frames received by this port 
--              from its segment that were classified as belonging to this
--              VLAN. Note that a frame received on this port is
--              counted by this object if and only if it is for a
--              protocol being processed by the local forwarding process
--              for this VLAN. This object includes received bridge
--              management frames classified as belonging to this VLAN
--              (e.g. GMRP, but not GVRP or STP)."
--     ::= { rsPortVlanHCStatsEntry 101 }

-- rsPortVlanHCOutOctets OBJECT-TYPE
--     SYNTAX          Counter64
--     ACCESS          read-only
--     STATUS          mandatory
--     DESCRIPTION     
--             "The number of octets of the valid frames transmitted 
--              by this port from its segment from the local forwarding 
--              process for this VLAN. This includes bridge management 
--              frames originated by this device which are classified 
--              as belonging to this VLAN (e.g. GMRP, but not GVRP or 
--              STP)."
--     ::= { rsPortVlanHCStatsEntry 102 }

rsVlanConformance OBJECT IDENTIFIER
    ::= { rsVlanExtensionsMIB 2 }

rsVlanCompliances OBJECT IDENTIFIER
    ::= { rsVlanConformance 1 }

rsVlanGroups OBJECT IDENTIFIER
    ::= { rsVlanConformance 2 }

rsPortVlanStatsGroup OBJECT IDENTIFIER
    ::= { rsVlanGroups 1 }

-- rsPortVlanStatsGroup OBJECT-GROUP
--     OBJECTS         { rsPortVlanInOctets, rsPortVlanOutOctets }
--     STATUS          mandatory
--     DESCRIPTION     
--             "A collection of additional objects providing per-port 
--              packet statistics for all VLANs currently configured on 
--              this device."
--     ::= { rsVlanGroups 1 }

rsPortVlanStatsOverflowGroup OBJECT IDENTIFIER
    ::= { rsVlanGroups 2 }

-- rsPortVlanStatsOverflowGroup OBJECT-GROUP
--     OBJECTS         { rsPortVlanInOverflowOctets, 
--                       rsPortVlanOutOverflowOctets }
--     STATUS          mandatory
--     DESCRIPTION     
--             "A collection of additional objects providing overflow 
--              counters for per-port packet statistics for all VLANs currently
--              configured on this device for high capacity interfaces, 
--              defined as those that have the value of the corresponding 
--              instance of ifSpeed greater than 20,000,000 bits/second."
--     ::= { rsVlanGroups 2 }

rsPortVlanHCStatsGroup OBJECT IDENTIFIER
    ::= { rsVlanGroups 3 }

-- rsPortVlanHCStatsGroup OBJECT-GROUP
--     OBJECTS         { rsPortVlanHCInOctets, rsPortVlanHCOutOctets }
--     STATUS          mandatory
--     DESCRIPTION     
--             "A collection of additional objects providing per-port packet
--              statistics for all VLANs currently configured on this
--              device for high capacity interfaces, defined as those
--              that have the value of the corresponding instance of
--              ifSpeed greater than 20,000,000 bits/second."
--     ::= { rsVlanGroups 3 }

rsVlanCompliance OBJECT IDENTIFIER
    ::= { rsVlanCompliances 1 }

-- rsVlanCompliance MODULE-COMPLIANCE
--     STATUS          mandatory
--     DESCRIPTION     
--             "The compliance statement for RIVERSTONE-VLAN-EXTENSIONS-MIB."

--     MODULE          -- -- this module

--         MANDATORY-GROUPS    { rsPortVlanStatsGroup }

--         GROUP       rsPortVlanStatsOverflowGroup
--         DESCRIPTION 
--             "This group is optional. It is most relevant for high
--              capacity interfaces where the SNMP agent supports only
--              SNMPv1."

--         GROUP       rsPortVlanHCStatsGroup
--         DESCRIPTION 
--             "This group is optional. It is most relevant for high
--              capacity interfaces."

--     ::= { rsVlanCompliances 1 }

END -- end of module RIVERSTONE-VLAN-EXTENSIONS-MIB.
