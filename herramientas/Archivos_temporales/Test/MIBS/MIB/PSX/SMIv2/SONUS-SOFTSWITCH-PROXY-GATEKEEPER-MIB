--
-- This SMIv2 module has been generated by smidump 0.2-cvs. Do not edit.
--

SONUS-SOFTSWITCH-PROXY-GATEKEEPER-MIB DEFINITIONS ::= BEGIN

IMPORTS
    MODULE-IDENTITY, NOTIFICATION-TYPE, OBJECT-TYPE
        FROM SNMPv2-SMI
    sonusEventClass, sonusEventDescription, sonusEventLevel, 
    sonusEventTime
        FROM SONUS-COMMON-MIB
    sonusServicesMIBs
        FROM SONUS-SMI;

sonusSoftSwitchProxyGatekeeperMIB MODULE-IDENTITY
    LAST-UPDATED    "200004230000Z"
    ORGANIZATION    
            "Sonus Networks, Inc."
    CONTACT-INFO    
            "   Customer Support    
             Sonus Networks, Inc.
             250 Apollo Drive
             Chelmsford, MA 01824
             USA
             
             Tel: 978-614-8100
             Fax: 978-614-8609"
    DESCRIPTION     
            "The MIB Module for SoftSwitch Proxy Gatekeeper Management."
    ::= { sonusServicesMIBs 13 }


sonusSoftSwitchProxyGatekeeperMIBObjects OBJECT IDENTIFIER
    ::= { sonusSoftSwitchProxyGatekeeperMIB 1 }

sonusSoftSwitchProxyGatekeeperMIBNotifications OBJECT IDENTIFIER
    ::= { sonusSoftSwitchProxyGatekeeperMIB 2 }

sonusSoftSwitchProxyGatekeeperMIBNotificationsPrefix OBJECT IDENTIFIER
    ::= { sonusSoftSwitchProxyGatekeeperMIBNotifications 0 }

sonusSoftSwitchProxyGatekeeperMIBNotificationsObjects OBJECT IDENTIFIER
    ::= { sonusSoftSwitchProxyGatekeeperMIBNotifications 1 }

sonusPesInterfaceIdentifier OBJECT-TYPE
    SYNTAX          INTEGER { primary(1), secondary(2) }
    MAX-ACCESS      read-only
    STATUS          current
    DESCRIPTION     
            "PGK redundant interface identifier"
    ::= { sonusSoftSwitchProxyGatekeeperMIBNotificationsObjects 1 }

sonusSoftSwitchPgkUpNotification NOTIFICATION-TYPE
    OBJECTS         { sonusEventDescription, sonusEventClass, 
                      sonusEventLevel, sonusEventTime }
    STATUS          current
    DESCRIPTION     
            "SoftSwitch Proxy Gatekeeper is up."
    ::= { sonusSoftSwitchProxyGatekeeperMIBNotificationsPrefix 1 }

sonusSoftSwitchPgkDownNotification NOTIFICATION-TYPE
    OBJECTS         { sonusEventDescription, sonusEventClass, 
                      sonusEventLevel, sonusEventTime }
    STATUS          current
    DESCRIPTION     
            "SoftSwitch Proxy Gatekeeper is down."
    ::= { sonusSoftSwitchProxyGatekeeperMIBNotificationsPrefix 2 }

sonusSoftSwitchPgkPesServiceUpNotification NOTIFICATION-TYPE
    OBJECTS         { sonusEventDescription, sonusEventClass, 
                      sonusEventLevel, sonusEventTime }
    STATUS          current
    DESCRIPTION     
            "PES is up."
    ::= { sonusSoftSwitchProxyGatekeeperMIBNotificationsPrefix 3 }

sonusSoftSwitchPgkPesServiceDownNotification NOTIFICATION-TYPE
    OBJECTS         { sonusEventDescription, sonusEventClass, 
                      sonusEventLevel, sonusEventTime }
    STATUS          current
    DESCRIPTION     
            "PES is down."
    ::= { sonusSoftSwitchProxyGatekeeperMIBNotificationsPrefix 4 }

sonusSoftSwitchPgkPesInterfaceUpNotification NOTIFICATION-TYPE
    OBJECTS         { sonusPesInterfaceIdentifier, sonusEventDescription, 
                      sonusEventClass, sonusEventLevel, sonusEventTime }
    STATUS          current
    DESCRIPTION     
            "PES Interface is up."
    ::= { sonusSoftSwitchProxyGatekeeperMIBNotificationsPrefix 5 }

sonusSoftSwitchPgkPesInterfaceDownNotification NOTIFICATION-TYPE
    OBJECTS         { sonusPesInterfaceIdentifier, sonusEventDescription, 
                      sonusEventClass, sonusEventLevel, sonusEventTime }
    STATUS          current
    DESCRIPTION     
            "PES Interface is down."
    ::= { sonusSoftSwitchProxyGatekeeperMIBNotificationsPrefix 6 }

sonusSoftSwitchPgkPesChangeoverNotification NOTIFICATION-TYPE
    OBJECTS         { sonusPesInterfaceIdentifier, sonusEventDescription, 
                      sonusEventClass, sonusEventLevel, sonusEventTime }
    STATUS          current
    DESCRIPTION     
            "Changing Active PES."
    ::= { sonusSoftSwitchProxyGatekeeperMIBNotificationsPrefix 7 }

END -- end of module SONUS-SOFTSWITCH-PROXY-GATEKEEPER-MIB.
