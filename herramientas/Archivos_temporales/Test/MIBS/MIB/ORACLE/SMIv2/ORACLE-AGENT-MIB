--
-- This SMIv2 module has been generated by smidump 0.2-cvs. Do not edit.
--

ORACLE-AGENT-MIB DEFINITIONS ::= BEGIN

IMPORTS
    Integer32, NOTIFICATION-TYPE, OBJECT-TYPE, enterprises
        FROM SNMPv2-SMI
    DisplayString
        FROM SNMPv2-TC;

DateAndTime ::=
    OCTET STRING (SIZE(8..11))

oracle OBJECT IDENTIFIER
    ::= { enterprises 111 }

oraAgent OBJECT IDENTIFIER
    ::= { enterprises 111 12 }

oraAgentObjects OBJECT IDENTIFIER
    ::= { oraAgent 1 }

oraAgentEventTable OBJECT-TYPE
    SYNTAX          SEQUENCE OF OraAgentEventEntry
    MAX-ACCESS      not-accessible
    STATUS          current
    DESCRIPTION     
            ""
    ::= { oraAgentObjects 1 }

oraAgentEventEntry OBJECT-TYPE
    SYNTAX          OraAgentEventEntry
    MAX-ACCESS      not-accessible
    STATUS          current
    DESCRIPTION     
            ""
    INDEX           { oraAgentEventIndex }
    ::= { oraAgentEventTable 1 }

OraAgentEventEntry ::=
    SEQUENCE {
        oraAgentEventIndex              Integer32,
        oraAgentEventName               DisplayString,
        oraAgentEventID                 Integer32,
        oraAgentEventService            DisplayString,
        oraAgentEventTime               DateAndTime,
        oraAgentEventSeverity           INTEGER,
        oraAgentEventUser               DisplayString,
        oraAgentEventAppID              Integer32,
        oraAgentEventMessage            DisplayString,
        oraAgentEventArguments          DisplayString,
        oraAgentEventResults            DisplayString
    }

oraAgentEventIndex OBJECT-TYPE
    SYNTAX          Integer32
    MAX-ACCESS      read-only
    STATUS          current
    DESCRIPTION     
            ""
    ::= { oraAgentEventEntry 1 }

oraAgentEventName OBJECT-TYPE
    SYNTAX          DisplayString
    MAX-ACCESS      read-only
    STATUS          current
    DESCRIPTION     
            "The name of the event that occurred."
    ::= { oraAgentEventEntry 2 }

oraAgentEventID OBJECT-TYPE
    SYNTAX          Integer32
    MAX-ACCESS      read-only
    STATUS          current
    DESCRIPTION     
            "The ID of the registration that generated this event occurrence."
    ::= { oraAgentEventEntry 3 }

oraAgentEventService OBJECT-TYPE
    SYNTAX          DisplayString
    MAX-ACCESS      read-only
    STATUS          current
    DESCRIPTION     
            "The name of the service (database, SQL*Net listener, etc.) 
             being monitored by this event."
    ::= { oraAgentEventEntry 4 }

oraAgentEventTime OBJECT-TYPE
    SYNTAX          DateAndTime
    MAX-ACCESS      read-only
    STATUS          current
    DESCRIPTION     
            "The time at which this event was detected."
    ::= { oraAgentEventEntry 5 }

oraAgentEventSeverity OBJECT-TYPE
    SYNTAX          INTEGER { warning(1), alert(2), clear(-1) }
    MAX-ACCESS      read-only
    STATUS          current
    DESCRIPTION     
            "A relative measure of the severity of the event."
    ::= { oraAgentEventEntry 6 }

oraAgentEventUser OBJECT-TYPE
    SYNTAX          DisplayString
    MAX-ACCESS      read-only
    STATUS          current
    DESCRIPTION     
            "The name of the user who registered for this event."
    ::= { oraAgentEventEntry 7 }

oraAgentEventAppID OBJECT-TYPE
    SYNTAX          Integer32
    MAX-ACCESS      read-only
    STATUS          current
    DESCRIPTION     
            "The ID of the Enterprise Manager console application through
             which this event was registered."
    ::= { oraAgentEventEntry 8 }

oraAgentEventMessage OBJECT-TYPE
    SYNTAX          DisplayString
    MAX-ACCESS      read-only
    STATUS          current
    DESCRIPTION     
            "<Isn't this always blank right now?>."
    ::= { oraAgentEventEntry 9 }

oraAgentEventArguments OBJECT-TYPE
    SYNTAX          DisplayString
    MAX-ACCESS      read-only
    STATUS          current
    DESCRIPTION     
            "The arguments that were passed to the script that detected
             this event."
    ::= { oraAgentEventEntry 10 }

oraAgentEventResults OBJECT-TYPE
    SYNTAX          DisplayString
    MAX-ACCESS      read-only
    STATUS          current
    DESCRIPTION     
            "The results generated by the script that detected this event."
    ::= { oraAgentEventEntry 11 }

oraAgentTraps OBJECT IDENTIFIER
    ::= { oraAgent 2 }

oraAgentEventOcc NOTIFICATION-TYPE
    OBJECTS         { oraAgentEventName, oraAgentEventID, 
                      oraAgentEventService, oraAgentEventTime, 
                      oraAgentEventSeverity, oraAgentEventUser, 
                      oraAgentEventAppID, oraAgentEventMessage, 
                      oraAgentEventArguments, oraAgentEventResults }
    STATUS          current
    DESCRIPTION     
            "The Enterprise Manager agent has detected an occurrence of
             an event for which it has no specific trap."
    ::= { oraAgentTraps 0 2 }

END -- end of module ORACLE-AGENT-MIB.
