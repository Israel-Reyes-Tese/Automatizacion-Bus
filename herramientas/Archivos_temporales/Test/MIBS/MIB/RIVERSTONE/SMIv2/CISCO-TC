--
-- This SMIv2 module has been generated by smidump 0.2-cvs. Do not edit.
--

CISCO-TC DEFINITIONS ::= BEGIN

IMPORTS
    ciscoModules, ciscoProducts
        FROM CISCO-SMI
    Gauge32, Integer32, MODULE-IDENTITY
        FROM SNMPv2-SMI
    TEXTUAL-CONVENTION
        FROM SNMPv2-TC;

ciscoTextualConventions MODULE-IDENTITY
    LAST-UPDATED    "199810280000Z"
    ORGANIZATION    
            "Cisco Systems, Inc."
    CONTACT-INFO    
            "       Cisco Systems
             Customer Service
             
             Postal: 170 W Tasman Drive
             San Jose, CA  95134
             USA
             
             Tel: +1 800 553-NETS
             
             E-mail: cs-snmp@cisco.com"
    DESCRIPTION     
            "This module defines textual conventions used throughout
             cisco enterprise mibs."
    REVISION        "199703130000Z"
    DESCRIPTION     
            "Added CountryCode textual convention."
    REVISION        "199703130000Z"
    DESCRIPTION     
            "Added SAPType textual convention."
    REVISION        "199608140000Z"
    DESCRIPTION     
            "Added InterfaceIndexOrZero textual convention."
    REVISION        "199607080000Z"
    DESCRIPTION     
            "Added new CiscoNetworkProtocol enumerations."
    REVISION        "199602220000Z"
    DESCRIPTION     
            "Added Unsigned32 textual conventions."
    REVISION        "199506070000Z"
    DESCRIPTION     
            "Miscellaneous updates/corrections, including making
             CiscoNetworkProtocol enumerations contiguous."
    REVISION        "199810280000Z"
    DESCRIPTION     
            "Added Port and IpProtocol textual conventions."
    ::= { ciscoModules 1 }


CiscoNetworkProtocol ::= TEXTUAL-CONVENTION
    STATUS          current
    DESCRIPTION     
            "Represents the different types of network layer protocols."
    SYNTAX          INTEGER { ip(1), decnet(2), pup(3), chaos(4), xns(5), 
                        x121(6), appletalk(7), clns(8), lat(9), 
                        vines(10), cons(11), apollo(12), stun(13), 
                        novell(14), qllc(15), snapshot(16), atmIlmi(17), 
                        bstun(18), x25pvc(19), unknown(65535) }

CiscoNetworkAddress ::= TEXTUAL-CONVENTION
    DISPLAY-HINT    "1x:"
    STATUS          current
    DESCRIPTION     
            "Represents a network layer address.  The length and format of
             the address is protocol dependent as follows:
             ip		4 octets
             decnet		2 octets
             pup		obsolete
             chaos		2 octets
             xns		10 octets
             		first 4 octets are the net number
             		last 6 octets are the host number
             x121	
             appletalk	3 octets
             		first 2 octets are the net number
             		last octet is the host number
             clns
             lat
             vines		6 octets
             		first 4 octets are the net number
             		last 2 octets are the host number
             cons
             apollo		10 octets
             		first 4 octets are the net number
             		last 6 octets are the host number
             stun 		8 octets
             novell		10 octets
             		first 4 octets are the net number
             		last 6 octets are the host number
             qllc		6 octets
             bstun		1 octet - bi-sync serial tunnel 
             snapshot	1 octet
             atmIlmi		4 octets
             x25 pvc		2 octets (12 bits)
             "
    SYNTAX          OCTET STRING

Unsigned32 ::= TEXTUAL-CONVENTION
    STATUS          current
    DESCRIPTION     
            "An unsigned 32-bit quantity indistinguishable from Gauge32."
    SYNTAX          Gauge32

InterfaceIndexOrZero ::= TEXTUAL-CONVENTION
    DISPLAY-HINT    "d"
    STATUS          current
    DESCRIPTION     
            "Either the value 0, or the ifIndex value of an
             interface in the ifTable."
    SYNTAX          Integer32 (0..2147483647)

SAPType ::= TEXTUAL-CONVENTION
    DISPLAY-HINT    "1x:"
    STATUS          current
    DESCRIPTION     
            "Service Access Point - is a term that denotes the means
             by which a user entity in layer n+1 accesses a service
             of a provider entity in layer n."
    SYNTAX          Integer32 (0..254)

CountryCode ::= TEXTUAL-CONVENTION
    DISPLAY-HINT    "2a"
    STATUS          current
    DESCRIPTION     
            "Represents a case-insensitive 2-letter country code taken from
             ISO-3166. Unrecognized countries are represented as empty string.
             "
    SYNTAX          OCTET STRING (SIZE(0 | 2))

EntPhysicalIndexOrZero ::= TEXTUAL-CONVENTION
    STATUS          current
    DESCRIPTION     
            "This textual convention is an extension of entPhysicalIndex.
             If non-zero, the object is an entPhysicalIndex. If zero, no
             appropriate entPhysicalIndex exists. Any additional semantics
             are object specific."
    SYNTAX          Integer32 (0..2147483647)

CiscoRowOperStatus ::= TEXTUAL-CONVENTION
    STATUS          current
    DESCRIPTION     
            "Represents the operational status of an table entry.
             This textual convention allows explicitly representing
             the states of rows dependent on rows in other tables.
             
                 active(1) -
                     Indicates this entry's RowStatus is active
                     and the RowStatus for each dependency is active.
             
                 activeDependencies(2) -
                     Indicates that the RowStatus for each dependency
                     is active, but the entry's RowStatus is not active.
             
                 inactiveDependency(3) -
                     Indicates that the RowStatus for at least one
                     dependency is not active.
             
                 missingDependency(4) -
                     Indicates that at least one dependency does
                     not exist in it's table.
             "
    SYNTAX          INTEGER { active(1), activeDependencies(2), 
                        inactiveDependency(3), missingDependency(4) }

CiscoPort ::= TEXTUAL-CONVENTION
    STATUS          current
    DESCRIPTION     
            "The TCP or UDP port number range."
    REFERENCE       
            "The TCP or UDP port number range."
    SYNTAX          Integer32 (0..65535)

CiscoIpProtocol ::= TEXTUAL-CONVENTION
    STATUS          current
    DESCRIPTION     
            "IP protocol number range."
    REFERENCE       
            "IP protocol number range."
    SYNTAX          Integer32 (0..255)

END -- end of module CISCO-TC.
