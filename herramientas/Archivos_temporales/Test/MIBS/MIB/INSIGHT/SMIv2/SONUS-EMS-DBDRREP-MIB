--
-- This SMIv2 module has been generated by smidump 0.2-cvs. Do not edit.
--

SONUS-EMS-DBDRREP-MIB DEFINITIONS ::= BEGIN

IMPORTS
    MODULE-IDENTITY, NOTIFICATION-TYPE, OBJECT-TYPE
        FROM SNMPv2-SMI
    sonusEventClass, sonusEventDescription, sonusEventLevel, 
    sonusEventTime
        FROM SONUS-COMMON-MIB
    sonusEmsMIB
        FROM SONUS-EMS-MIB
    sonusHostID
        FROM SONUS-HOST-MIB;

sonusEmsDbDrRepMIB MODULE-IDENTITY
    LAST-UPDATED    "200805060000Z"
    ORGANIZATION    
            "Sonus Networks, Inc."
    CONTACT-INFO    
            "   Customer Support    
             Sonus Networks, Inc.
             7 Technology Park Drive
             Westford, MA 01886
             USA
             
             Tel: 978-614-8100
             Fax: 978-614-8609"
    DESCRIPTION     
            "The MIB Module for Sonus EMS Database Replication Management."
    ::= { sonusEmsMIB 4 }


sonusEmsDbDrRepMIBObjects OBJECT IDENTIFIER
    ::= { sonusEmsDbDrRepMIB 1 }

sonusEmsDbDrRepMIBNotifications OBJECT IDENTIFIER
    ::= { sonusEmsDbDrRepMIB 2 }

sonusEmsDbDrRepMIBNotificationsPrefix OBJECT IDENTIFIER
    ::= { sonusEmsDbDrRepMIBNotifications 0 }

sonusEmsDbDrRepMIBNotificationsObjects OBJECT IDENTIFIER
    ::= { sonusEmsDbDrRepMIBNotifications 1 }

sonusEmsDbDrRepDRState OBJECT-TYPE
    SYNTAX          INTEGER { standalone(1), dr-source(2), dr-target(3) }
    MAX-ACCESS      read-only
    STATUS          current
    DESCRIPTION     
            "Specifies the disaster recovery status of the source device."
    ::= { sonusEmsDbDrRepMIBNotificationsObjects 1 }

sonusEmsDbDrRepOutOfSyncReason OBJECT-TYPE
    SYNTAX          INTEGER { notReceivingArchiveLogs(1), 
                        noReplicationProgress(2), 
                        slowReplicationProgress(3) }
    MAX-ACCESS      read-only
    STATUS          current
    DESCRIPTION     
            "Specifies why the databases are not in sync."
    ::= { sonusEmsDbDrRepMIBNotificationsObjects 2 }

sonusEmsDbDrErrorNotification NOTIFICATION-TYPE
    OBJECTS         { sonusEventDescription, sonusEventClass, 
                      sonusEventLevel, sonusEventTime, sonusHostID, 
                      sonusEmsDbDrRepDRState }
    STATUS          current
    DESCRIPTION     
            "Database error"
    ::= { sonusEmsDbDrRepMIBNotificationsPrefix 1 }

sonusEmsDbDrRepOutOfSyncNotification NOTIFICATION-TYPE
    OBJECTS         { sonusEventDescription, sonusEventClass, 
                      sonusEventLevel, sonusEventTime, sonusHostID, 
                      sonusEmsDbDrRepDRState, 
                      sonusEmsDbDrRepOutOfSyncReason }
    STATUS          current
    DESCRIPTION     
            "Target is out of sync."
    ::= { sonusEmsDbDrRepMIBNotificationsPrefix 2 }

sonusEmsDbDrRepConnectErrorNotification NOTIFICATION-TYPE
    OBJECTS         { sonusEventDescription, sonusEventClass, 
                      sonusEventLevel, sonusEventTime, sonusHostID, 
                      sonusEmsDbDrRepDRState }
    STATUS          current
    DESCRIPTION     
            "Error when attempting to connect to the DR peer."
    ::= { sonusEmsDbDrRepMIBNotificationsPrefix 3 }

sonusEmsDbDrRepConnectFailNotification NOTIFICATION-TYPE
    OBJECTS         { sonusEventDescription, sonusEventClass, 
                      sonusEventLevel, sonusEventTime, sonusHostID, 
                      sonusEmsDbDrRepDRState }
    STATUS          current
    DESCRIPTION     
            "Failed to connect to the DR peer."
    ::= { sonusEmsDbDrRepMIBNotificationsPrefix 4 }

END -- end of module SONUS-EMS-DBDRREP-MIB.
