--
-- This SMIv1 module has been generated by smidump 0.2-cvs. Do not edit.
--

SONUS-BT-SERVICE-GROUP-MIB DEFINITIONS ::= BEGIN

IMPORTS
    OBJECT-TYPE
        FROM RFC-1212
    TRAP-TYPE
        FROM RFC-1215
    RowStatus
        FROM SNMPv2-TC
    sonusEventClass, sonusEventDescription, sonusEventLevel, 
    sonusEventTime, sonusSequenceId, sonusShelfIndex, sonusSlotIndex
        FROM SONUS-COMMON-MIB
    sonusSignallingMIBs
        FROM SONUS-SMI
    PointCode, SonusAdminState, SonusName, SonusNameReference, 
    SonusPointCode, SonusSupportFlag
        FROM SONUS-TC;

sonusBtServiceGroupMIB OBJECT IDENTIFIER
    ::= { sonusSignallingMIBs 8 }

-- sonusBtServiceGroupMIB MODULE-IDENTITY
--     LAST-UPDATED    "201511220000Z"
--     ORGANIZATION    
--             "Sonus Networks, Inc."
--     CONTACT-INFO    
--             "   Customer Support    
--              Sonus Networks, Inc.
--              7 Technology Park Drive
--              Westford, MA 01886
--              USA
--              
--              Tel: 978-614-8100
--              Fax: 978-614-8609"
--     DESCRIPTION     
--             "The MIB Module for BT Service Group Management."
--     ::= { sonusSignallingMIBs 8 }


sonusBtServiceGroupMIBObjects OBJECT IDENTIFIER
    ::= { sonusBtServiceGroupMIB 1 }

sonusBtsgServiceGroup OBJECT IDENTIFIER
    ::= { sonusBtServiceGroupMIBObjects 1 }

sonusBtsgServiceGroupNextIndex OBJECT-TYPE
    SYNTAX          INTEGER
    ACCESS          read-only
    STATUS          mandatory
    DESCRIPTION     
            "The next valid index to use when creating a new sonusBtsgServiceGroupEntry"
    ::= { sonusBtsgServiceGroup 1 }

sonusBtsgServiceGroupTable OBJECT-TYPE
    SYNTAX          SEQUENCE OF SonusBtsgServiceGroupEntry
    ACCESS          not-accessible
    STATUS          mandatory
    DESCRIPTION     
            "This table contains information about each BT Service Group
             configured to be a member of the node. 
             
             A management entity may create rows for Service Group that are
             anticipated to be supported in the future."
    ::= { sonusBtsgServiceGroup 2 }

sonusBtsgServiceGroupEntry OBJECT-TYPE
    SYNTAX          SonusBtsgServiceGroupEntry
    ACCESS          not-accessible
    STATUS          mandatory
    DESCRIPTION     
            "This table describes the BT Service Groups that are configured as
             members of the GSX9000 BT Service Group."
    INDEX           { sonusBtsgServiceGroupListIndex }
    ::= { sonusBtsgServiceGroupTable 1 }

SonusBtsgServiceGroupEntry ::=
    SEQUENCE {
        sonusBtsgServiceGroupListIndex  INTEGER,
        sonusBtsgServiceGroupName       SonusName,
        sonusBtsgServiceGroupRemotePointCode    PointCode,
        sonusBtsgServiceGroupTG         SonusNameReference,
        sonusBtsgServiceGroupSwitchType INTEGER,
        sonusBtsgServiceGroupHuntAlgorithm  INTEGER,
        sonusBtsgServiceGroupCost       INTEGER,
        sonusBtsgServiceGroupCicControl INTEGER,
        sonusBtsgServiceGroupOperation  INTEGER,
        sonusBtsgServiceGroupMode       INTEGER,
        sonusBtsgServiceGroupAction     INTEGER,
        sonusBtsgServiceGroupTimeout    INTEGER,
        sonusBtsgServiceGroupAdminState SonusAdminState,
        sonusBtsgServiceGroupProfileName DisplayString,
        sonusBtsgServiceGroupRowStatus  RowStatus,
        sonusBtsgServiceGroupGrsStartup INTEGER,
        sonusBtsgServiceGroupRemPc      SonusPointCode,
        sonusBtsgServiceGroupIntlNoa    SonusSupportFlag,
        sonusBtsgServiceGroupDoubleRel  SonusSupportFlag,
        sonusBtsgServiceGroup12aIdle    SonusSupportFlag,
        sonusBtsgServiceGroupCliReq     INTEGER,
        sonusBtsgServiceGroupPcliStoredValue    SonusSupportFlag,
        sonusBtsgServiceGroupGatewayOutage  INTEGER,
        sonusBtsgServiceGroupMinDigitsForQuery      INTEGER,
        sonusBtsgServiceGroupSatelliteCircuits      INTEGER,
        sonusBtsgServiceGroupCongRelTimeout   INTEGER,
        sonusBtsgServiceGroupPnReq      INTEGER,
        sonusBtsgServiceGroupLdcTimeout INTEGER,
        sonusBtsgServiceGroupLdcAction  INTEGER,
        sonusBtsgServiceGroupLdcRelCause INTEGER,
        sonusBtsgServiceGroupLdcEmergencyCalls      INTEGER,
        sonusBtsgServiceGroup30Digit    SonusSupportFlag,
        sonusBtsgServiceGroupIwkLineIdPostRoute       SonusSupportFlag,
        sonusBtsgServiceGroupMessageThrottling      SonusSupportFlag,
        sonusBtsgServiceGroupMessageThrottlingTimer           INTEGER,
        sonusBtsgServiceGroupPddTimeout INTEGER,
        sonusBtsgServiceGroupPddRelCause INTEGER,
        sonusBtsgServiceGroupSignalOnlySipAlert       SonusSupportFlag,
        sonusBtsgServiceGroupSendingEnbloc  SonusSupportFlag,
        sonusBtsgServiceGroupLdliReq    INTEGER
    }

sonusBtsgServiceGroupListIndex OBJECT-TYPE
    SYNTAX          INTEGER (1..2048)
    ACCESS          read-only
    STATUS          mandatory
    DESCRIPTION     
            "The index of the BT Service Group entry."
    ::= { sonusBtsgServiceGroupEntry 1 }

sonusBtsgServiceGroupName OBJECT-TYPE
    SYNTAX          SonusName
    ACCESS          read-write
    STATUS          mandatory
    DESCRIPTION     
            "The name of the BT Service Group."
    ::= { sonusBtsgServiceGroupEntry 2 }

sonusBtsgServiceGroupRemotePointCode OBJECT-TYPE
    SYNTAX          PointCode
    ACCESS          read-write
    STATUS          mandatory
    DESCRIPTION     
            "Identifies the SS7 Point Code of the BT Service Group in decimal format,
             the least significant three bytes representing Network-Cluster-Member values."
    ::= { sonusBtsgServiceGroupEntry 3 }

sonusBtsgServiceGroupTG OBJECT-TYPE
    SYNTAX          SonusNameReference
    ACCESS          read-write
    STATUS          mandatory
    DESCRIPTION     
            "The Trunk Group, which the BT Service Group belongs to."
    ::= { sonusBtsgServiceGroupEntry 4 }

sonusBtsgServiceGroupSwitchType OBJECT-TYPE
    SYNTAX          INTEGER { dms500(1), dms250(2), dms200(3), dms100(4), 
                        lucent5ESS(5), lucent4ESS(6) }
    ACCESS          read-write
    STATUS          obsolete
    DESCRIPTION     
            "This field is not used in 6.1 onwards"
    ::= { sonusBtsgServiceGroupEntry 5 }

sonusBtsgServiceGroupHuntAlgorithm OBJECT-TYPE
    SYNTAX          INTEGER { bottom2top(1), top2bottom(2), 
                        circuithi2lo(3), circuitlo2hi(4), 
                        mostnleastidle(5), circularbottom2top(6), 
                        circulartop2bottom(7) }
    ACCESS          read-write
    STATUS          mandatory
    DESCRIPTION     
            "The hunting method used to select circuits for calls destined
             to the Service Group destination."
    ::= { sonusBtsgServiceGroupEntry 6 }

sonusBtsgServiceGroupCost OBJECT-TYPE
    SYNTAX          INTEGER (0..100)
    ACCESS          read-write
    STATUS          mandatory
    DESCRIPTION     
            "The routing cost to the BT Service Group."
    ::= { sonusBtsgServiceGroupEntry 7 }

sonusBtsgServiceGroupCicControl OBJECT-TYPE
    SYNTAX          INTEGER { noCics(1), oddCics(2), evenCics(3), 
                        allCics(4) }
    ACCESS          read-write
    STATUS          mandatory
    DESCRIPTION     
            "The CICs being controlled to resolve dual seizure."
    ::= { sonusBtsgServiceGroupEntry 8 }

sonusBtsgServiceGroupOperation OBJECT-TYPE
    SYNTAX          INTEGER { block(1), unblock(2), reset(3) }
    ACCESS          read-write
    STATUS          mandatory
    DESCRIPTION     
            "The operation to be applied to the circuits in the BT Service Group."
    ::= { sonusBtsgServiceGroupEntry 9 }

sonusBtsgServiceGroupMode OBJECT-TYPE
    SYNTAX          INTEGER { outOfService(1), inService(2) }
    ACCESS          read-write
    STATUS          mandatory
    DESCRIPTION     
            "The mode of operation of circuits in the BT Service Group."
    ::= { sonusBtsgServiceGroupEntry 10 }

sonusBtsgServiceGroupAction OBJECT-TYPE
    SYNTAX          INTEGER { dryUp(1), force(2) }
    ACCESS          read-write
    STATUS          mandatory
    DESCRIPTION     
            "The action taken on the circuits in the BT Service Group."
    ::= { sonusBtsgServiceGroupEntry 11 }

sonusBtsgServiceGroupTimeout OBJECT-TYPE
    SYNTAX          INTEGER (1..1440)
    ACCESS          read-write
    STATUS          mandatory
    DESCRIPTION     
            "The timeout value in minutes for dryup action on the BT Service Group."
    ::= { sonusBtsgServiceGroupEntry 12 }

sonusBtsgServiceGroupAdminState OBJECT-TYPE
    SYNTAX          SonusAdminState
    ACCESS          read-write
    STATUS          mandatory
    DESCRIPTION     
            "The admin state of the BT Service Group."
    ::= { sonusBtsgServiceGroupEntry 13 }

sonusBtsgServiceGroupProfileName OBJECT-TYPE
    SYNTAX          DisplayString (SIZE(0..23))
    ACCESS          read-write
    STATUS          mandatory
    DESCRIPTION     
            "The BT Service Group profile name."
    ::= { sonusBtsgServiceGroupEntry 14 }

sonusBtsgServiceGroupRowStatus OBJECT-TYPE
    SYNTAX          RowStatus
    ACCESS          read-write
    STATUS          mandatory
    DESCRIPTION     
            ""
    ::= { sonusBtsgServiceGroupEntry 15 }

sonusBtsgServiceGroupGrsStartup OBJECT-TYPE
    SYNTAX          INTEGER { disabled(1), enabled(2) }
    ACCESS          read-write
    STATUS          mandatory
    DESCRIPTION     
            "Reset at Startup for the BT Service Group."
    ::= { sonusBtsgServiceGroupEntry 16 }

sonusBtsgServiceGroupRemPc OBJECT-TYPE
    SYNTAX          SonusPointCode
    ACCESS          read-write
    STATUS          mandatory
    DESCRIPTION     
            "The Remote point code is not maintained as an OCTET STRING"
    ::= { sonusBtsgServiceGroupEntry 18 }

sonusBtsgServiceGroupIntlNoa OBJECT-TYPE
    SYNTAX          SonusSupportFlag
    ACCESS          read-write
    STATUS          mandatory
    DESCRIPTION     
            "International Nature of Address Supported for this BT Service Group."
    DEFVAL          { unsupported }
    ::= { sonusBtsgServiceGroupEntry 35 }

sonusBtsgServiceGroupDoubleRel OBJECT-TYPE
    SYNTAX          SonusSupportFlag
    ACCESS          read-write
    STATUS          mandatory
    DESCRIPTION     
            "Send Two Rel's when communicating with System X for this BT Service Group."
    DEFVAL          { unsupported }
    ::= { sonusBtsgServiceGroupEntry 36 }

sonusBtsgServiceGroup12aIdle OBJECT-TYPE
    SYNTAX          SonusSupportFlag
    ACCESS          read-write
    STATUS          mandatory
    DESCRIPTION     
            "On Third Expiry of Timer 12a, Idle Circuit for this BT Service Group."
    DEFVAL          { unsupported }
    ::= { sonusBtsgServiceGroupEntry 37 }

sonusBtsgServiceGroupCliReq OBJECT-TYPE
    SYNTAX          INTEGER { essential(1), nonEssential(2), 
                        noRequest(3) }
    ACCESS          read-write
    STATUS          mandatory
    DESCRIPTION     
            "Request the CLI before Routing for this BT Service Group."
    DEFVAL          { nonEssential }
    ::= { sonusBtsgServiceGroupEntry 38 }

sonusBtsgServiceGroupPcliStoredValue OBJECT-TYPE
    SYNTAX          SonusSupportFlag
    ACCESS          read-write
    STATUS          mandatory
    DESCRIPTION     
            "Previous CLI request failed and a PCLI was returned, use this stored PCLI or Transit CLI Request for this BT Service Group."
    DEFVAL          { unsupported }
    ::= { sonusBtsgServiceGroupEntry 39 }

sonusBtsgServiceGroupGatewayOutage OBJECT-TYPE
    SYNTAX          INTEGER { keepCalls(1), removeCalls(2) }
    ACCESS          read-write
    STATUS          obsolete
    DESCRIPTION     
            "Specifies if the service group should try to keep active calls when the ss7 gateway disconnects. - Not used in 6.5 onwards"
    ::= { sonusBtsgServiceGroupEntry 40 }

sonusBtsgServiceGroupMinDigitsForQuery OBJECT-TYPE
    SYNTAX          INTEGER (0..30)
    ACCESS          read-write
    STATUS          mandatory
    DESCRIPTION     
            "If the received Called Address is not complete, this is the minimum number of digits required before we go for a Route Query"
    DEFVAL          { 0 }
    ::= { sonusBtsgServiceGroupEntry 41 }

sonusBtsgServiceGroupSatelliteCircuits OBJECT-TYPE
    SYNTAX          INTEGER { disabled(1), enabled(2) }
    ACCESS          read-write
    STATUS          obsolete
    DESCRIPTION     
            "This field is not used in 6.1 onwards"
    ::= { sonusBtsgServiceGroupEntry 42 }

sonusBtsgServiceGroupCongRelTimeout OBJECT-TYPE
    SYNTAX          INTEGER (0..5)
    ACCESS          read-write
    STATUS          mandatory
    DESCRIPTION     
            "Time to delay sending of CNG message during congestion."
    DEFVAL          { 0 }
    ::= { sonusBtsgServiceGroupEntry 44 }

sonusBtsgServiceGroupPnReq OBJECT-TYPE
    SYNTAX          INTEGER { noRequest(1), essential(2), 
                        nonEssential(3) }
    ACCESS          read-write
    STATUS          mandatory
    DESCRIPTION     
            "Request the Presentation Number before Routing for this BT Service Group."
    DEFVAL          { nonEssential }
    ::= { sonusBtsgServiceGroupEntry 45 }

sonusBtsgServiceGroupLdcTimeout OBJECT-TYPE
    SYNTAX          INTEGER (0..2880)
    ACCESS          read-write
    STATUS          mandatory
    DESCRIPTION     
            "The timeout value of the long duration call timer in minutes.
             Allowed values are 0 to disable the timer, 60-2880 minutes to set the timer."
    DEFVAL          { 0 }
    ::= { sonusBtsgServiceGroupEntry 46 }

sonusBtsgServiceGroupLdcAction OBJECT-TYPE
    SYNTAX          INTEGER { noAction(0), trap(1), release(2), 
                        trapAndRelease(3) }
    ACCESS          read-write
    STATUS          mandatory
    DESCRIPTION     
            "This is the action to take if the long duration call timer
             expires.  The call may be released or a trap fired, or both."
    DEFVAL          { noAction }
    ::= { sonusBtsgServiceGroupEntry 47 }

sonusBtsgServiceGroupLdcRelCause OBJECT-TYPE
    SYNTAX          INTEGER (0..127)
    ACCESS          read-write
    STATUS          mandatory
    DESCRIPTION     
            "The IUP release value to use should the call be released 
             due to long duration call timer expiry"
    DEFVAL          { 2 }
    ::= { sonusBtsgServiceGroupEntry 48 }

sonusBtsgServiceGroupLdcEmergencyCalls OBJECT-TYPE
    SYNTAX          INTEGER { include(0), exclude(1) }
    ACCESS          read-write
    STATUS          mandatory
    DESCRIPTION     
            "Whether Emergency Calls should be excluded from or included 
             in Long Duration Call Disconnect procedures"
    DEFVAL          { exclude }
    ::= { sonusBtsgServiceGroupEntry 49 }

sonusBtsgServiceGroup30Digit OBJECT-TYPE
    SYNTAX          SonusSupportFlag
    ACCESS          read-write
    STATUS          mandatory
    DESCRIPTION     
            "Option to ovveride the PNO006 standard and support upto 30 digits in the I(F)AM message"
    DEFVAL          { unsupported }
    ::= { sonusBtsgServiceGroupEntry 50 }

sonusBtsgServiceGroupIwkLineIdPostRoute OBJECT-TYPE
    SYNTAX          SonusSupportFlag
    ACCESS          read-write
    STATUS          mandatory
    DESCRIPTION     
            "Indicates whether the interworking of line IDs received post-routing is supported for this BT Service Group."
    DEFVAL          { unsupported }
    ::= { sonusBtsgServiceGroupEntry 51 }

sonusBtsgServiceGroupMessageThrottling OBJECT-TYPE
    SYNTAX          SonusSupportFlag
    ACCESS          read-write
    STATUS          mandatory
    DESCRIPTION     
            "Is the procedure to throttle automatic message generation active for 
             this service."
    DEFVAL          { supported }
    ::= { sonusBtsgServiceGroupEntry 52 }

sonusBtsgServiceGroupMessageThrottlingTimer OBJECT-TYPE
    SYNTAX          INTEGER (0..1000)
    ACCESS          read-write
    STATUS          mandatory
    DESCRIPTION     
            "Time in milliseconds used by the message throttling inserted between messages 
             which would otherwise be simultaneous."
    DEFVAL          { 10 }
    ::= { sonusBtsgServiceGroupEntry 53 }

sonusBtsgServiceGroupPddTimeout OBJECT-TYPE
    SYNTAX          INTEGER (0..20)
    ACCESS          read-write
    STATUS          mandatory
    DESCRIPTION     
            "Post Dial Delay timer in seconds."
    DEFVAL          { 0 }
    ::= { sonusBtsgServiceGroupEntry 54 }

sonusBtsgServiceGroupPddRelCause OBJECT-TYPE
    SYNTAX          INTEGER (1..127)
    ACCESS          read-write
    STATUS          mandatory
    DESCRIPTION     
            "The Q.850 release value to use should the call be released
             due to PDD timer expiry"
    DEFVAL          { 42 }
    ::= { sonusBtsgServiceGroupEntry 55 }

sonusBtsgServiceGroupSignalOnlySipAlert OBJECT-TYPE
    SYNTAX          SonusSupportFlag
    ACCESS          read-write
    STATUS          mandatory
    DESCRIPTION     
            "On an IUP-SIP call, only generate the ACM message in response to
             an 180 message - alerting. No ACM should be generated for other
             18x messages or 300 messages."
    DEFVAL          { unsupported }
    ::= { sonusBtsgServiceGroupEntry 56 }

sonusBtsgServiceGroupSendingEnbloc OBJECT-TYPE
    SYNTAX          SonusSupportFlag
    ACCESS          read-write
    STATUS          mandatory
    DESCRIPTION     
            "PROTOCOLS   - BT-IUP
             UNSUPPORTED - The Trunkgroup is able to send overlap 
             and enbloc.
             SUPPORTED   - The Trunkgroup is only able to send enbloc.
             CMD         - SENDING ENBLOC "
    DEFVAL          { unsupported }
    ::= { sonusBtsgServiceGroupEntry 57 }

sonusBtsgServiceGroupLdliReq OBJECT-TYPE
    SYNTAX          INTEGER { disabled(1), enabled(2) }
    ACCESS          read-write
    STATUS          mandatory
    DESCRIPTION     
            " Request the LDLI before Routing for this BT Service Group.
             PROTOCOLS   - BT-IUP
             DISABLED    - LDLI routing post psx query
             ENABLED     - LDLI routing before PSX query
             CMD         - LDLI REQUEST BEFORE ROUTING "
    DEFVAL          { disabled }
    ::= { sonusBtsgServiceGroupEntry 58 }

sonusBtsgServiceGroupStatTable OBJECT-TYPE
    SYNTAX          SEQUENCE OF SonusBtsgServiceGroupStatEntry
    ACCESS          not-accessible
    STATUS          mandatory
    DESCRIPTION     
            "This table contains status information about each BT access point
             in the GSX9000 Switch node.  BT Service Groups within the node can
             can be configured before SS7 connections is physically attached to
             the node.  The remote BT user part may be unavailable or the SS7
             links to the destination may not be connected or correctly configured.
             Therefore, it is possible that an access point can be unavailable,
             and is absent."
    ::= { sonusBtServiceGroupMIBObjects 2 }

sonusBtsgServiceGroupStatEntry OBJECT-TYPE
    SYNTAX          SonusBtsgServiceGroupStatEntry
    ACCESS          not-accessible
    STATUS          mandatory
    DESCRIPTION     
            "This table describes the status of the Service Groups that are configured
             as destinations BT IUP nodes for the GSX9000 Switch node."
    INDEX           { sonusBtsgServiceGroupStatListIndex }
    ::= { sonusBtsgServiceGroupStatTable 1 }

SonusBtsgServiceGroupStatEntry ::=
    SEQUENCE {
        sonusBtsgServiceGroupStatListIndex  INTEGER,
        sonusBtsgServiceGroupStatName   SonusNameReference,
        sonusBtsgServiceGroupStatStatus INTEGER
    }

sonusBtsgServiceGroupStatListIndex OBJECT-TYPE
    SYNTAX          INTEGER (0..2048)
    ACCESS          read-only
    STATUS          mandatory
    DESCRIPTION     
            "The index of the BT Service Group."
    ::= { sonusBtsgServiceGroupStatEntry 1 }

sonusBtsgServiceGroupStatName OBJECT-TYPE
    SYNTAX          SonusNameReference
    ACCESS          read-only
    STATUS          mandatory
    DESCRIPTION     
            "The name of the BT Service Group."
    ::= { sonusBtsgServiceGroupStatEntry 2 }

sonusBtsgServiceGroupStatStatus OBJECT-TYPE
    SYNTAX          INTEGER { available(1), unavailable(2), congested(3) }
    ACCESS          read-only
    STATUS          mandatory
    DESCRIPTION     
            "The state of the BT Service Group."
    ::= { sonusBtsgServiceGroupStatEntry 3 }

sonusBtsgSvcGrpProfile OBJECT IDENTIFIER
    ::= { sonusBtServiceGroupMIBObjects 3 }

sonusBtsgSvcGrpProfileNextIndex OBJECT-TYPE
    SYNTAX          INTEGER
    ACCESS          read-only
    STATUS          mandatory
    DESCRIPTION     
            "The next valid index to use when creating a new sonusBtsgSvcGrpProfileEntry"
    ::= { sonusBtsgSvcGrpProfile 1 }

sonusBtsgSvcGrpProfileTable OBJECT-TYPE
    SYNTAX          SEQUENCE OF SonusBtsgSvcGrpProfileEntry
    ACCESS          not-accessible
    STATUS          mandatory
    DESCRIPTION     
            "This table contains BT Service Group profiles."
    ::= { sonusBtsgSvcGrpProfile 2 }

sonusBtsgSvcGrpProfileEntry OBJECT-TYPE
    SYNTAX          SonusBtsgSvcGrpProfileEntry
    ACCESS          not-accessible
    STATUS          mandatory
    DESCRIPTION     
            "This table describes the Service Group profile."
    INDEX           { sonusBtsgSvcGrpProfileListIndex }
    ::= { sonusBtsgSvcGrpProfileTable 1 }

SonusBtsgSvcGrpProfileEntry ::=
    SEQUENCE {
        sonusBtsgSvcGrpProfileListIndex INTEGER,
        sonusBtsgSvcGrpProfileName      SonusName,
        sonusBtsgSvcGrpProfileTG        SonusNameReference,
        sonusBtsgSvcGrpProfileSwitchType INTEGER,
        sonusBtsgSvcGrpProfileHuntAlgorithm   INTEGER,
        sonusBtsgSvcGrpProfileCost      INTEGER,
        sonusBtsgSvcGrpProfileCicControl INTEGER,
        sonusBtsgSvcGrpProfileAdminState SonusAdminState,
        sonusBtsgSvcGrpProfileRowStatus RowStatus,
        sonusBtsgSvcGrpProfileGrsStartup INTEGER,
        sonusBtsgSvcGrpProfileIntlNoa   SonusSupportFlag,
        sonusBtsgSvcGrpProfileDoubleRel SonusSupportFlag,
        sonusBtsgSvcGrpProfile12aIdle   SonusSupportFlag,
        sonusBtsgSvcGrpProfileCliReq    INTEGER,
        sonusBtsgSvcGrpProfilePcliStoredValue     SonusSupportFlag,
        sonusBtsgSvcGrpProfileMinDigitsForQuery       INTEGER,
        sonusBtsgSvcGrpProfileSatelliteCircuits       INTEGER,
        sonusBtsgSvcGrpProfileCongRelTimeout    INTEGER,
        sonusBtsgSvcGrpProfilePnReq     INTEGER,
        sonusBtsgSvcGrpProfileLdcTimeout INTEGER,
        sonusBtsgSvcGrpProfileLdcAction INTEGER,
        sonusBtsgSvcGrpProfileLdcRelCause INTEGER,
        sonusBtsgSvcGrpProfileLdcEmergencyCalls       INTEGER,
        sonusBtsgSvcGrpProfile30Digit   SonusSupportFlag,
        sonusBtsgSvcGrpProfileIwkLineIdPostRoute        SonusSupportFlag,
        sonusBtsgSvcGrpProfileMessageThrottling       SonusSupportFlag,
        sonusBtsgSvcGrpProfileMessageThrottlingTimer            INTEGER,
        sonusBtsgSvcGrpProfilePddTimeout INTEGER,
        sonusBtsgSvcGrpProfilePddRelCause INTEGER,
        sonusBtsgSvcGrpProfileSendingEnbloc   SonusSupportFlag,
        sonusBtsgSvcGrpProfileLdliReq   INTEGER
    }

sonusBtsgSvcGrpProfileListIndex OBJECT-TYPE
    SYNTAX          INTEGER (0..127)
    ACCESS          read-only
    STATUS          mandatory
    DESCRIPTION     
            "The index of the BT Service Group Profile."
    ::= { sonusBtsgSvcGrpProfileEntry 1 }

sonusBtsgSvcGrpProfileName OBJECT-TYPE
    SYNTAX          SonusName
    ACCESS          read-write
    STATUS          mandatory
    DESCRIPTION     
            "The name of the BT Service Group Profile."
    ::= { sonusBtsgSvcGrpProfileEntry 2 }

sonusBtsgSvcGrpProfileTG OBJECT-TYPE
    SYNTAX          SonusNameReference
    ACCESS          read-write
    STATUS          mandatory
    DESCRIPTION     
            "The Trunk Group, which the BT Service Group belongs to."
    ::= { sonusBtsgSvcGrpProfileEntry 3 }

sonusBtsgSvcGrpProfileSwitchType OBJECT-TYPE
    SYNTAX          INTEGER { dms500(1), dms250(2), dms200(3), dms100(4), 
                        lucent5ESS(5), lucent4ESS(6) }
    ACCESS          read-write
    STATUS          obsolete
    DESCRIPTION     
            "This field is not used in 6.1 onwards"
    ::= { sonusBtsgSvcGrpProfileEntry 4 }

sonusBtsgSvcGrpProfileHuntAlgorithm OBJECT-TYPE
    SYNTAX          INTEGER { bottom2top(1), top2bottom(2), 
                        circuithi2lo(3), circuitlo2hi(4), 
                        mostnleastidle(5), circularbottom2top(6), 
                        circulartop2bottom(7) }
    ACCESS          read-write
    STATUS          mandatory
    DESCRIPTION     
            "The hunting method used to select circuits for calls destined
             to the Service Group destination."
    ::= { sonusBtsgSvcGrpProfileEntry 5 }

sonusBtsgSvcGrpProfileCost OBJECT-TYPE
    SYNTAX          INTEGER (0..100)
    ACCESS          read-write
    STATUS          mandatory
    DESCRIPTION     
            "The routing cost to the BT Service Group."
    ::= { sonusBtsgSvcGrpProfileEntry 6 }

sonusBtsgSvcGrpProfileCicControl OBJECT-TYPE
    SYNTAX          INTEGER { noCics(1), oddCics(2), evenCics(3), 
                        allCics(4) }
    ACCESS          read-write
    STATUS          mandatory
    DESCRIPTION     
            "The CICs being controlled to resolve dual seizure."
    ::= { sonusBtsgSvcGrpProfileEntry 7 }

sonusBtsgSvcGrpProfileAdminState OBJECT-TYPE
    SYNTAX          SonusAdminState
    ACCESS          read-write
    STATUS          mandatory
    DESCRIPTION     
            "The admin state of the BT Service Group Profile."
    ::= { sonusBtsgSvcGrpProfileEntry 8 }

sonusBtsgSvcGrpProfileRowStatus OBJECT-TYPE
    SYNTAX          RowStatus
    ACCESS          read-write
    STATUS          mandatory
    DESCRIPTION     
            ""
    ::= { sonusBtsgSvcGrpProfileEntry 9 }

sonusBtsgSvcGrpProfileGrsStartup OBJECT-TYPE
    SYNTAX          INTEGER { disabled(1), enabled(2) }
    ACCESS          read-write
    STATUS          mandatory
    DESCRIPTION     
            "Reset  at Startup for the BT Service Group Profile."
    ::= { sonusBtsgSvcGrpProfileEntry 10 }

sonusBtsgSvcGrpProfileIntlNoa OBJECT-TYPE
    SYNTAX          SonusSupportFlag
    ACCESS          read-write
    STATUS          mandatory
    DESCRIPTION     
            "International Nature of Address supported for the BT Service Group Profile."
    DEFVAL          { unsupported }
    ::= { sonusBtsgSvcGrpProfileEntry 28 }

sonusBtsgSvcGrpProfileDoubleRel OBJECT-TYPE
    SYNTAX          SonusSupportFlag
    ACCESS          read-write
    STATUS          mandatory
    DESCRIPTION     
            "Send Two Rel's when communicating with System X for the BT Service Group Profile."
    DEFVAL          { unsupported }
    ::= { sonusBtsgSvcGrpProfileEntry 29 }

sonusBtsgSvcGrpProfile12aIdle OBJECT-TYPE
    SYNTAX          SonusSupportFlag
    ACCESS          read-write
    STATUS          mandatory
    DESCRIPTION     
            "On Third Expiry of Timer 12a, Idle Circuit for this BT Service Group Profile."
    DEFVAL          { unsupported }
    ::= { sonusBtsgSvcGrpProfileEntry 30 }

sonusBtsgSvcGrpProfileCliReq OBJECT-TYPE
    SYNTAX          INTEGER { essential(1), nonEssential(2), 
                        noRequest(3) }
    ACCESS          read-write
    STATUS          mandatory
    DESCRIPTION     
            "Request the CLI before Routing for this BT Service Group Profile."
    DEFVAL          { nonEssential }
    ::= { sonusBtsgSvcGrpProfileEntry 31 }

sonusBtsgSvcGrpProfilePcliStoredValue OBJECT-TYPE
    SYNTAX          SonusSupportFlag
    ACCESS          read-write
    STATUS          mandatory
    DESCRIPTION     
            "Previous CLI request failed and a PCLI was returned, use this stored PCLI or Transit CLI Request for this BT Service Profile."
    DEFVAL          { unsupported }
    ::= { sonusBtsgSvcGrpProfileEntry 32 }

sonusBtsgSvcGrpProfileMinDigitsForQuery OBJECT-TYPE
    SYNTAX          INTEGER (0..30)
    ACCESS          read-write
    STATUS          mandatory
    DESCRIPTION     
            "If the received Called Address is not complete, this is the minimum number 
             of digits required before we go for a Route Query"
    DEFVAL          { 0 }
    ::= { sonusBtsgSvcGrpProfileEntry 33 }

sonusBtsgSvcGrpProfileSatelliteCircuits OBJECT-TYPE
    SYNTAX          INTEGER { disabled(1), enabled(2) }
    ACCESS          read-write
    STATUS          obsolete
    DESCRIPTION     
            "This field is not used in 6.1 onwards"
    ::= { sonusBtsgSvcGrpProfileEntry 34 }

sonusBtsgSvcGrpProfileCongRelTimeout OBJECT-TYPE
    SYNTAX          INTEGER (0..5)
    ACCESS          read-write
    STATUS          mandatory
    DESCRIPTION     
            "Time to delay sending of CNG message during congestion."
    DEFVAL          { 0 }
    ::= { sonusBtsgSvcGrpProfileEntry 36 }

sonusBtsgSvcGrpProfilePnReq OBJECT-TYPE
    SYNTAX          INTEGER { noRequest(1), essential(2), 
                        nonEssential(3) }
    ACCESS          read-write
    STATUS          mandatory
    DESCRIPTION     
            "Request the Presentation Number before Routing for this BT Service Group Profile."
    DEFVAL          { nonEssential }
    ::= { sonusBtsgSvcGrpProfileEntry 37 }

sonusBtsgSvcGrpProfileLdcTimeout OBJECT-TYPE
    SYNTAX          INTEGER (0..2880)
    ACCESS          read-write
    STATUS          mandatory
    DESCRIPTION     
            "The timeout value of the long duration call timer in minutes.
             Allowed values are 0 to disable the timer, 60-2880 minutes to set the timer."
    DEFVAL          { 0 }
    ::= { sonusBtsgSvcGrpProfileEntry 38 }

sonusBtsgSvcGrpProfileLdcAction OBJECT-TYPE
    SYNTAX          INTEGER { noAction(0), trap(1), release(2), 
                        trapAndRelease(3) }
    ACCESS          read-write
    STATUS          mandatory
    DESCRIPTION     
            "This is the action to take if the long duration call timer
             expires.  The call may be released or a trap fired, or both."
    DEFVAL          { noAction }
    ::= { sonusBtsgSvcGrpProfileEntry 39 }

sonusBtsgSvcGrpProfileLdcRelCause OBJECT-TYPE
    SYNTAX          INTEGER (0..127)
    ACCESS          read-write
    STATUS          mandatory
    DESCRIPTION     
            "The IUP release value to use should the call be released 
             due to long duration call timer expiry"
    DEFVAL          { 2 }
    ::= { sonusBtsgSvcGrpProfileEntry 40 }

sonusBtsgSvcGrpProfileLdcEmergencyCalls OBJECT-TYPE
    SYNTAX          INTEGER { include(0), exclude(1) }
    ACCESS          read-write
    STATUS          mandatory
    DESCRIPTION     
            "Whether Emergency Calls should be excluded from or included 
             in Long Duration Call Disconnect procedures"
    DEFVAL          { exclude }
    ::= { sonusBtsgSvcGrpProfileEntry 41 }

sonusBtsgSvcGrpProfile30Digit OBJECT-TYPE
    SYNTAX          SonusSupportFlag
    ACCESS          read-write
    STATUS          mandatory
    DESCRIPTION     
            "Option to ovveride the PNO006 standard and support upto 30 digits in the I(F)AM message"
    DEFVAL          { unsupported }
    ::= { sonusBtsgSvcGrpProfileEntry 42 }

sonusBtsgSvcGrpProfileIwkLineIdPostRoute OBJECT-TYPE
    SYNTAX          SonusSupportFlag
    ACCESS          read-write
    STATUS          mandatory
    DESCRIPTION     
            "Indicates whether the interworking of line IDs received post-routing is supported for this BT Service Group Profile."
    DEFVAL          { unsupported }
    ::= { sonusBtsgSvcGrpProfileEntry 43 }

sonusBtsgSvcGrpProfileMessageThrottling OBJECT-TYPE
    SYNTAX          SonusSupportFlag
    ACCESS          read-write
    STATUS          mandatory
    DESCRIPTION     
            "Is the procedure to throttle automatic message generation active for 
             this service."
    DEFVAL          { supported }
    ::= { sonusBtsgSvcGrpProfileEntry 44 }

sonusBtsgSvcGrpProfileMessageThrottlingTimer OBJECT-TYPE
    SYNTAX          INTEGER (0..1000)
    ACCESS          read-write
    STATUS          mandatory
    DESCRIPTION     
            "Time in milliseconds used by the message throttling inserted between messages 
             which would otherwise be simultaneous."
    DEFVAL          { 10 }
    ::= { sonusBtsgSvcGrpProfileEntry 45 }

sonusBtsgSvcGrpProfilePddTimeout OBJECT-TYPE
    SYNTAX          INTEGER (0..20)
    ACCESS          read-write
    STATUS          mandatory
    DESCRIPTION     
            "Post Dial Delay timeout in seconds."
    DEFVAL          { 0 }
    ::= { sonusBtsgSvcGrpProfileEntry 46 }

sonusBtsgSvcGrpProfilePddRelCause OBJECT-TYPE
    SYNTAX          INTEGER (1..127)
    ACCESS          read-write
    STATUS          mandatory
    DESCRIPTION     
            "The Q.850 release value to use should the call be released
             due to PDD timer expiry"
    DEFVAL          { 42 }
    ::= { sonusBtsgSvcGrpProfileEntry 47 }

sonusBtsgSvcGrpProfileSendingEnbloc OBJECT-TYPE
    SYNTAX          SonusSupportFlag
    ACCESS          read-write
    STATUS          mandatory
    DESCRIPTION     
            "PROTOCOLS   -  BT_IUP
             UNSUPPORTED - The Trunkgroup is able to send overlap 
             and enbloc.
             SUPPORTED   - The Trunkgroup is only able to send enbloc.
             CMD         - SENDING ENBLOC"
    DEFVAL          { unsupported }
    ::= { sonusBtsgSvcGrpProfileEntry 48 }

sonusBtsgSvcGrpProfileLdliReq OBJECT-TYPE
    SYNTAX          INTEGER { disabled(1), enabled(2) }
    ACCESS          read-write
    STATUS          mandatory
    DESCRIPTION     
            " Request the LDLI before Routing for this BT Service Group.
             PROTOCOLS   - BT-IUP
             DISABLED    - LDLI routing post psx query
             ENABLED     - LDLI routing before PSX query
             CMD         - LDLI REQUEST BEFORE ROUTING "
    DEFVAL          { disabled }
    ::= { sonusBtsgSvcGrpProfileEntry 49 }

sonusBtServiceGroupMIBNotifications OBJECT IDENTIFIER
    ::= { sonusBtServiceGroupMIB 2 }

sonusBtServiceGroupMIBNotificationsPrefix OBJECT IDENTIFIER
    ::= { sonusBtServiceGroupMIBNotifications 0 }

sonusBtServiceGroupMIBNotificationsObjects OBJECT IDENTIFIER
    ::= { sonusBtServiceGroupMIBNotifications 1 }

sonusBtSvcGrpName OBJECT-TYPE
    SYNTAX          DisplayString (SIZE(0..23))
    ACCESS          read-only
    STATUS          mandatory
    DESCRIPTION     
            "Name of the BT service group."
    ::= { sonusBtServiceGroupMIBNotificationsObjects 1 }

sonusBtMaintReason OBJECT-TYPE
    SYNTAX          INTEGER { ss7GwRegistration(1), 
                        remoteSs7PointCodeAccess(2), trunkGroupMode(3), 
                        serviceGroupMode(4), circuitMode(5), ds1Mode(6), 
                        serverMode(7), localHardware(8), 
                        remoteMaintenance(9), remoteHardware(10), 
                        remoteUnequipped(11), ss7GwResynchronization(12), 
                        localMaintenance(13) }
    ACCESS          read-only
    STATUS          mandatory
    DESCRIPTION     
            "Maintenance reason for blocking/unblocking of the circuit."
    ::= { sonusBtServiceGroupMIBNotificationsObjects 2 }

sonusBtTrunkGrpName OBJECT-TYPE
    SYNTAX          DisplayString (SIZE(0..23))
    ACCESS          read-only
    STATUS          mandatory
    DESCRIPTION     
            "Name of the trunk group."
    ::= { sonusBtServiceGroupMIBNotificationsObjects 3 }

sonusBtCircuit OBJECT-TYPE
    SYNTAX          INTEGER (0..16383)
    ACCESS          read-only
    STATUS          mandatory
    DESCRIPTION     
            "Base circuit identity code (CIC) for the circuit."
    ::= { sonusBtServiceGroupMIBNotificationsObjects 4 }

sonusBtCircuitOffsets OBJECT-TYPE
    SYNTAX          OCTET STRING
--                       { cicOffset0(0), cicOffset1(1), cicOffset2(2), 
--                         cicOffset3(3), cicOffset4(4), cicOffset5(5), 
--                         cicOffset6(6), cicOffset7(7), cicOffset8(8), 
--                         cicOffset9(9), cicOffset10(10), 
--                         cicOffset11(11), cicOffset12(12), 
--                         cicOffset13(13), cicOffset14(14), 
--                         cicOffset15(15), cicOffset16(16), 
--                         cicOffset17(17), cicOffset18(18), 
--                         cicOffset19(19), cicOffset20(20), 
--                         cicOffset21(21), cicOffset22(22), 
--                         cicOffset23(23) }
    ACCESS          read-only
    STATUS          mandatory
    DESCRIPTION     
            "Circuit maintenance status bitmap for CIC range starting with base CIC."
    ::= { sonusBtServiceGroupMIBNotificationsObjects 5 }

sonusBtCalledPartyNumber OBJECT-TYPE
    SYNTAX          DisplayString (SIZE(0..31))
    ACCESS          read-only
    STATUS          mandatory
    DESCRIPTION     
            "Called Party Number."
    ::= { sonusBtServiceGroupMIBNotificationsObjects 6 }

sonusBtCallingPartyNumber OBJECT-TYPE
    SYNTAX          DisplayString (SIZE(0..31))
    ACCESS          read-only
    STATUS          mandatory
    DESCRIPTION     
            "Calling Party Number."
    ::= { sonusBtServiceGroupMIBNotificationsObjects 7 }

sonusBtCircuitBlockedEvents OBJECT-TYPE
    SYNTAX          Gauge (0..4294967295)
    ACCESS          read-only
    STATUS          mandatory
    DESCRIPTION     
            "The number of BT circuit Blocked events generated during consolidation period"
    ::= { sonusBtServiceGroupMIBNotificationsObjects 8 }

sonusBtCircuitBlockedCount OBJECT-TYPE
    SYNTAX          Gauge (0..4294967295)
    ACCESS          read-only
    STATUS          mandatory
    DESCRIPTION     
            "The number of BT circuits Blocked relating to Blocked events"
    ::= { sonusBtServiceGroupMIBNotificationsObjects 9 }

sonusBtCircuitUnblockedEvents OBJECT-TYPE
    SYNTAX          Gauge (0..4294967295)
    ACCESS          read-only
    STATUS          mandatory
    DESCRIPTION     
            "The number of BT circuit Unblocked events generated during consolidation period"
    ::= { sonusBtServiceGroupMIBNotificationsObjects 10 }

sonusBtCircuitUnblockedCount OBJECT-TYPE
    SYNTAX          Gauge (0..4294967295)
    ACCESS          read-only
    STATUS          mandatory
    DESCRIPTION     
            "The number of BT circuits Unblocked relating to Unblocked events"
    ::= { sonusBtServiceGroupMIBNotificationsObjects 11 }

sonusBtCircuitResetEvents OBJECT-TYPE
    SYNTAX          Gauge (0..4294967295)
    ACCESS          read-only
    STATUS          mandatory
    DESCRIPTION     
            "The number of BT circuit Reset events generated during consolidation period"
    ::= { sonusBtServiceGroupMIBNotificationsObjects 12 }

sonusBtCircuitResetCount OBJECT-TYPE
    SYNTAX          Gauge (0..4294967295)
    ACCESS          read-only
    STATUS          mandatory
    DESCRIPTION     
            "The number of BT circuits Reset relating to reset events"
    ::= { sonusBtServiceGroupMIBNotificationsObjects 13 }

sonusBtLocalPointCode OBJECT-TYPE
    SYNTAX          INTEGER (0..16777215)
    ACCESS          read-only
    STATUS          mandatory
    DESCRIPTION     
            "Local Point Code."
    ::= { sonusBtServiceGroupMIBNotificationsObjects 14 }

sonusBtRemotePointCode OBJECT-TYPE
    SYNTAX          INTEGER (0..16777215)
    ACCESS          read-only
    STATUS          mandatory
    DESCRIPTION     
            "Remote Point Code."
    ::= { sonusBtServiceGroupMIBNotificationsObjects 15 }

sonusBtSvcGrpInServiceNotification TRAP-TYPE
    ENTERPRISE      sonusBtServiceGroupMIBNotifications
    VARIABLES       { sonusBtSvcGrpName, sonusEventDescription, 
                      sonusEventClass, sonusEventLevel, sonusSequenceId, 
                      sonusEventTime }
--     STATUS          mandatory
    DESCRIPTION     
            "This trap indicates that the BT Service Group was put in service by maintenance staff."
    ::= 1

sonusBtSvcGrpOutOfServiceNotification TRAP-TYPE
    ENTERPRISE      sonusBtServiceGroupMIBNotifications
    VARIABLES       { sonusBtSvcGrpName, sonusEventDescription, 
                      sonusEventClass, sonusEventLevel, sonusSequenceId, 
                      sonusEventTime }
--     STATUS          mandatory
    DESCRIPTION     
            "This trap indicates that the BT Service Group was taken out of service by maintenance staff."
    ::= 2

sonusBtCircuitBlockedNotification TRAP-TYPE
    ENTERPRISE      sonusBtServiceGroupMIBNotifications
    VARIABLES       { sonusBtSvcGrpName, sonusBtMaintReason, 
                      sonusBtTrunkGrpName, sonusBtCircuit, 
                      sonusBtCircuitOffsets, sonusEventDescription, 
                      sonusEventClass, sonusEventLevel, sonusSequenceId, 
                      sonusEventTime }
--     STATUS          mandatory
    DESCRIPTION     
            "This trap indicates that the BT Circuit(s) were blocked."
    ::= 3

sonusBtCircuitUnblockedNotification TRAP-TYPE
    ENTERPRISE      sonusBtServiceGroupMIBNotifications
    VARIABLES       { sonusBtSvcGrpName, sonusBtMaintReason, 
                      sonusBtTrunkGrpName, sonusBtCircuit, 
                      sonusBtCircuitOffsets, sonusEventDescription, 
                      sonusEventClass, sonusEventLevel, sonusSequenceId, 
                      sonusEventTime }
--     STATUS          mandatory
    DESCRIPTION     
            "This trap indicates that the BT Circuit(s) were unblocked."
    ::= 4

sonusBtCircuitResetNotification TRAP-TYPE
    ENTERPRISE      sonusBtServiceGroupMIBNotifications
    VARIABLES       { sonusBtSvcGrpName, sonusBtTrunkGrpName, 
                      sonusBtCircuit, sonusBtCircuitOffsets, 
                      sonusEventDescription, sonusEventClass, 
                      sonusEventLevel, sonusSequenceId, sonusEventTime }
--     STATUS          mandatory
    DESCRIPTION     
            "This trap indicates that the BT Circuit(s) were reset."
    ::= 5

sonusBtCicRegistrationFailedNotification TRAP-TYPE
    ENTERPRISE      sonusBtServiceGroupMIBNotifications
    VARIABLES       { sonusBtCircuit, sonusEventDescription, 
                      sonusEventClass, sonusEventLevel, sonusSequenceId, 
                      sonusEventTime, sonusBtCircuit, 
                      sonusBtLocalPointCode, sonusBtRemotePointCode, 
                      sonusBtSvcGrpName, sonusBtTrunkGrpName }
--     STATUS          mandatory
    DESCRIPTION     
            "This trap indicates that the CIC Registration failed after multiple retries."
    ::= 7

sonusBtSvcGrpCircuitsUnblockedNotification TRAP-TYPE
    ENTERPRISE      sonusBtServiceGroupMIBNotifications
    VARIABLES       { sonusBtSvcGrpName, sonusBtMaintReason, 
                      sonusBtTrunkGrpName, sonusEventDescription, 
                      sonusEventClass, sonusEventLevel, sonusSequenceId, 
                      sonusEventTime }
--     STATUS          mandatory
    DESCRIPTION     
            "This trap indicates that the all IUP Circuits in the
             Service Group were unblocked."
    ::= 8

sonusBtSgConsolidatedCctBlockedNotification TRAP-TYPE
    ENTERPRISE      sonusBtServiceGroupMIBNotifications
    VARIABLES       { sonusBtSvcGrpName, sonusBtTrunkGrpName, 
                      sonusShelfIndex, sonusSlotIndex, 
                      sonusBtCircuitBlockedEvents, 
                      sonusBtCircuitBlockedCount, sonusEventDescription, 
                      sonusEventClass, sonusEventLevel, sonusSequenceId, 
                      sonusEventTime }
--     STATUS          mandatory
    DESCRIPTION     
            "This trap indicates that BT circuit Blocked traps have been suppressed. 
             The counters specify the number of traps that have been suppressed"
    ::= 9

sonusBtSgConsolidatedCctUnblockedNotification TRAP-TYPE
    ENTERPRISE      sonusBtServiceGroupMIBNotifications
    VARIABLES       { sonusBtSvcGrpName, sonusBtTrunkGrpName, 
                      sonusShelfIndex, sonusSlotIndex, 
                      sonusBtCircuitUnblockedEvents, 
                      sonusBtCircuitUnblockedCount, 
                      sonusEventDescription, sonusEventClass, 
                      sonusEventLevel, sonusSequenceId, sonusEventTime }
--     STATUS          mandatory
    DESCRIPTION     
            "This trap indicates that BT circuit Unblocked traps have been suppressed. 
             The counters specify the number of traps that have been suppressed"
    ::= 10

sonusBtSgConsolidatedCctResetNotification TRAP-TYPE
    ENTERPRISE      sonusBtServiceGroupMIBNotifications
    VARIABLES       { sonusBtSvcGrpName, sonusBtTrunkGrpName, 
                      sonusShelfIndex, sonusSlotIndex, 
                      sonusBtCircuitResetEvents, 
                      sonusBtCircuitResetCount, sonusEventDescription, 
                      sonusEventClass, sonusEventLevel, sonusSequenceId, 
                      sonusEventTime }
--     STATUS          mandatory
    DESCRIPTION     
            "This trap indicates that BT circuit reset traps have been suppressed. 
             The counters specify the number of traps that have been suppressed"
    ::= 11

END -- end of module SONUS-BT-SERVICE-GROUP-MIB.
