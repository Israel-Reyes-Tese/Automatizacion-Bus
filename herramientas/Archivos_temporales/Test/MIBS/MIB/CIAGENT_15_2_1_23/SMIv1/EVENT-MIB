--
-- This SMIv1 module has been generated by smidump 0.2-cvs. Do not edit.
--

EVENT-MIB DEFINITIONS ::= BEGIN

IMPORTS
    OBJECT-TYPE
        FROM RFC-1212
    TRAP-TYPE
        FROM RFC-1215
    Counter
        FROM RFC1155-SMI
    SnmpAdminString
        FROM SNMP-FRAMEWORK-MIB
    srExperimentalMIBs
        FROM SNMP-RESEARCH-MIB
    SnmpTagValue
        FROM SNMP-TARGET-MIB
    experimental
        FROM SNMPv2-SMI
    DisplayString, RowStatus, TruthValue
        FROM SNMPv2-TC;

eventMIB OBJECT IDENTIFIER
    ::= { srExperimentalMIBs 5 }

-- eventMIB MODULE-IDENTITY
--     LAST-UPDATED    "199810071700Z"
--     ORGANIZATION    
--             "IETF Distributed Management Working Group"
--     CONTACT-INFO    
--             "Bob Stewart
--              Cisco Systems, Inc.
--              170 West Tasman Drive,
--              San Jose CA 95134-1706.
--              Phone: +1 408 526 4527
--              Email: bstewart@cisco.com"
--     DESCRIPTION     
--             "The MIB module for defining event triggers and actions
--              for network management purposes."
--     ::= { srExperimentalMIBs 5 }


FailureReason ::=
    INTEGER { tooBig(1), noSuchName(2), badValue(3), readOnly(4), 
                        genErr(5), noAccess(6), wrongType(7), 
                        wrongLength(8), wrongEncoding(9), wrongValue(10), 
                        noCreation(11), inconsistentValue(12), 
                        resourceUnavailable(13), commitFailed(14), 
                        undoFailed(15), authorizationError(16), 
                        notWritable(17), inconsistentName(18), 
                        localResourceLack(101), badDestination(102), 
                        noAck(103) }

-- FailureReason ::= TEXTUAL-CONVENTION
--     STATUS          mandatory
--     DESCRIPTION     
--             "Reasons for failures in an attempt to send a management
--              message.
--              
--              The first group of errors, numbered less than 100, are copied
--              directly from SNMP protocol operations and are intended to carry
--              
--              
--              
--              
--              
--              
--              exactly the meanings defined for the protocol as returned in
--              an SNMP response.  Those numbered 100 or greater are related
--              to problems in sending the request."
--     SYNTAX          INTEGER
--                       { tooBig(1), noSuchName(2), badValue(3), 
--                         readOnly(4), genErr(5), noAccess(6), 
--                         wrongType(7), wrongLength(8), 
--                         wrongEncoding(9), wrongValue(10), 
--                         noCreation(11), inconsistentValue(12), 
--                         resourceUnavailable(13), commitFailed(14), 
--                         undoFailed(15), authorizationError(16), 
--                         notWritable(17), inconsistentName(18), 
--                         localResourceLack(101), badDestination(102), 
--                         noAck(103) }

eventMIBObjects OBJECT IDENTIFIER
    ::= { eventMIB 1 }

srExMteTrigger OBJECT IDENTIFIER
    ::= { eventMIBObjects 1 }

srExMteTriggerFailures OBJECT-TYPE
    SYNTAX          Counter
    ACCESS          read-only
    STATUS          mandatory
    DESCRIPTION     
            "The number of times an attempt to check for a trigger
             condition has failed.  This counts individually for each
             attempt in a group of targets or each attempt for a
             wildcarded object."
    ::= { srExMteTrigger 1 }

srExMteTriggerTable OBJECT-TYPE
    SYNTAX          SEQUENCE OF SrExMteTriggerEntry
    ACCESS          not-accessible
    STATUS          mandatory
    DESCRIPTION     
            "A table of management event trigger information."
    ::= { srExMteTrigger 2 }

srExMteTriggerEntry OBJECT-TYPE
    SYNTAX          SrExMteTriggerEntry
    ACCESS          not-accessible
    STATUS          mandatory
    DESCRIPTION     
            "Information about a single trigger.  Applications create and
             delete entries using srExMteTriggerStatus."
    INDEX           { IMPLIED srExMteTriggerName }
    ::= { srExMteTriggerTable 1 }

SrExMteTriggerEntry ::=
    SEQUENCE {
        srExMteTriggerName              SnmpAdminString,
        srExMteTriggerComment           DisplayString,
        srExMteTriggerTest              INTEGER,
        srExMteTriggerValueID           OBJECT IDENTIFIER,
        srExMteTriggerValueIDWildcard   TruthValue,
        srExMteTriggerTargetTag         SnmpTagValue,
        srExMteTriggerContextName       SnmpAdminString,
        srExMteTriggerContextNameWildcard TruthValue,
        srExMteTriggerFrequency         INTEGER,
        srExMteTriggerBooleanStartup    TruthValue,
        srExMteTriggerThresholdStartup  INTEGER,
        srExMteTriggerRisingThreshold   INTEGER,
        srExMteTriggerFallingThreshold  INTEGER,
        srExMteTriggerEvent             SnmpAdminString,
        srExMteTriggerRisingEvent       SnmpAdminString,
        srExMteTriggerFallingEvent      SnmpAdminString,
        srExMteTriggerObjects           SnmpAdminString,
        srExMteTriggerStatus            RowStatus
    }

srExMteTriggerName OBJECT-TYPE
    SYNTAX          SnmpAdminString (SIZE(1..64))
    ACCESS          not-accessible
    STATUS          mandatory
    DESCRIPTION     
            "A locally-unique, administratively assigned name for the
             trigger."
    ::= { srExMteTriggerEntry 1 }

srExMteTriggerComment OBJECT-TYPE
    SYNTAX          DisplayString
    ACCESS          read-write
    STATUS          mandatory
    DESCRIPTION     
            "A description of the trigger's function and use."
    DEFVAL          { "" }
    ::= { srExMteTriggerEntry 2 }

srExMteTriggerTest OBJECT-TYPE
    SYNTAX          INTEGER { boolean(1), threshold(2) }
    ACCESS          read-write
    STATUS          mandatory
    DESCRIPTION     
            "The type of trigger test to perform.  For all tests,
             srExMteTriggerValue must evaluate to an integer.
             
             For 'boolean', a value of 0 is false. A non-zero value is true
             and fires the trigger.  The trigger will not fire again until
             the value has become false and come back to true.
             
             For 'threshold' it works as described below for
             srExMteTriggerThresholdStartup, srExMteTriggerRisingThreshold, and
             srExMteTriggerFallingThreshold."
    DEFVAL          { boolean }
    ::= { srExMteTriggerEntry 3 }

srExMteTriggerValueID OBJECT-TYPE
    SYNTAX          OBJECT IDENTIFIER
    ACCESS          read-write
    STATUS          mandatory
    DESCRIPTION     
            "The object identifier of the MIB object to check to see
             if the trigger should fire.
             
             This may be wildcarded by truncating all or part of the
             instance portion, in which case the condition is obtained
             as if with a GetNext function, checking multiple values
             if they exist.  If such wildcarding is applied,
             
             
             
             
             
             
             
             srExMteTriggerIDWildcard must be 'true' and if not it must
             be 'false'."
    ::= { srExMteTriggerEntry 4 }

srExMteTriggerValueIDWildcard OBJECT-TYPE
    SYNTAX          TruthValue
    ACCESS          read-write
    STATUS          mandatory
    DESCRIPTION     
            "Control for whether srExMteTriggerValueID is to be treated as
             fully-specified or wildcarded, with 'true' indicating wildcard."
    DEFVAL          { false }
    ::= { srExMteTriggerEntry 5 }

srExMteTriggerTargetTag OBJECT-TYPE
    SYNTAX          SnmpTagValue
    ACCESS          read-write
    STATUS          mandatory
    DESCRIPTION     
            " "
    DEFVAL          { "" }
    ::= { srExMteTriggerEntry 6 }

srExMteTriggerContextName OBJECT-TYPE
    SYNTAX          SnmpAdminString
    ACCESS          read-write
    STATUS          mandatory
    DESCRIPTION     
            "The management context from which to obtain srExMteTriggerValueID.
             
             This may be wildcarded by leaving characters off the end.  To
             indicate such wildcarding srExMteTriggerContextNameWildcard must
             be 'true'."
    DEFVAL          { "" }
    ::= { srExMteTriggerEntry 7 }

srExMteTriggerContextNameWildcard OBJECT-TYPE
    SYNTAX          TruthValue
    ACCESS          read-write
    STATUS          mandatory
    DESCRIPTION     
            "Control for whether srExMteTriggerContextName is to be treated as
             fully-specified or wildcarded, with 'true' indicating wildcard."
    DEFVAL          { false }
    ::= { srExMteTriggerEntry 8 }

srExMteTriggerFrequency OBJECT-TYPE
    SYNTAX          INTEGER (0..65535)
    ACCESS          read-write
    STATUS          mandatory
    DESCRIPTION     
            "The number of seconds to wait between trigger condition
             checks.  To encourage consistency in sampling, the
             interval is measured from the beginning of one check to
             the beginning of the next and the timer is restarted immediately
             when it expires, not when the check completes.
             
             If the next check begins before the previous one completed the
             system may either attempt to make the check or treat this as an
             error condition.
             
             A frequency of 0 indicates instantaneous recognition of the
             condition.  This is not possible in many cases, but such may
             be supported in cases where it makes sense and the system is
             able to do so."
    DEFVAL          { 600 }
    ::= { srExMteTriggerEntry 9 }

srExMteTriggerBooleanStartup OBJECT-TYPE
    SYNTAX          TruthValue
    ACCESS          read-write
    STATUS          mandatory
    DESCRIPTION     
            "Control for whether an event may be triggered when this entry
             is first set to 'active'.  If the value srExMteTriggerBooleanStartup
             is 'true' and the first sample after this entry becomes active
             is true then one srExMteTriggerEvent is triggered.
             
             If srExMteTriggerType is not 'boolean', this object is not
             instantiated."
    DEFVAL          { true }
    ::= { srExMteTriggerEntry 10 }

srExMteTriggerThresholdStartup OBJECT-TYPE
    SYNTAX          INTEGER { rising(1), falling(2), risingOrFalling(3) }
    ACCESS          read-write
    STATUS          mandatory
    DESCRIPTION     
            "The event that may be triggered when this entry is first
             set to 'active'.  If the first sample after this entry
             becomes active is greater than or equal to
             srExMteTriggerRisingThreshold and srExMteTriggerThresholdStartup is
             equal to 'rising' or 'risingOrFalling', then one
             srExMteTriggerRisingEvent is triggered.  If the first
             sample after this entry becomes active is less than
             or equal to srExMteTriggerFallingThreshold and
             srExMteTriggerThresholdStartup is equal to 'falling' or
             'risingOrFalling', then one srExMteTriggerRisingEvent is triggered.
             
             If srExMteTriggerType is not 'threshold', this object is not
             instantiated."
    DEFVAL          { risingOrFalling }
    ::= { srExMteTriggerEntry 11 }

srExMteTriggerRisingThreshold OBJECT-TYPE
    SYNTAX          INTEGER
    ACCESS          read-write
    STATUS          mandatory
    DESCRIPTION     
            "A threshold value to check against if srExMteTriggerType is
             'threshold'.
             
             When the current sampled value is greater than or equal to
             this threshold, and the value at the last sampling
             interval was less than this threshold, one srExMteTriggerRisingEvent
             is triggered.  That event is also triggered if the first sample
             afer this entry bcomes active is greater than or equal to this
             threshold and srExMteTriggerThresholdStartup is equal to 'rising'
             or 'risingOrFalling'.
             
             After a rising event is generated, another such event is not
             triggered until the sampled value falls below this threshold and
             reaches srExMteTriggerFallingThreshold.
             
             If srExMteTriggerType is not 'threshold', this object is not
             
             
             
             
             
             
             
             instantiated."
    DEFVAL          { 0 }
    ::= { srExMteTriggerEntry 12 }

srExMteTriggerFallingThreshold OBJECT-TYPE
    SYNTAX          INTEGER
    ACCESS          read-write
    STATUS          mandatory
    DESCRIPTION     
            "A threshold value to check against if srExMteTriggerType is
             'threshold'.
             
             When the current sampled value is less than or equal to
             this threshold, and the value at the last sampling interval
             was greater than this threshold, one srExMteTriggerFallingEvent
             is triggered.  That event is also triggered if the first sample
             afer this entry bcomes active is less than or equal to this
             threshold and srExMteTriggerThresholdStartup is equal to 'falling'
             or 'risingOrFalling'.
             
             After a falling event is generated, another such event is not
             triggered until the sampled value rises above this threshold and
             reaches srExMteTriggerRisingThreshold.
             
             If srExMteTriggerType is not 'threshold', this object is not
             instantiated."
    DEFVAL          { 0 }
    ::= { srExMteTriggerEntry 13 }

srExMteTriggerEvent OBJECT-TYPE
    SYNTAX          SnmpAdminString (SIZE(0..64))
    ACCESS          read-write
    STATUS          mandatory
    DESCRIPTION     
            "The event to invoke when srExMteTriggerType is 'boolean' and
             this trigger fires.  A length of 0 indicates no event.
             
             If srExMteTriggerType is not 'boolean', this object is not
             instantiated."
    DEFVAL          { "" }
    ::= { srExMteTriggerEntry 14 }

srExMteTriggerRisingEvent OBJECT-TYPE
    SYNTAX          SnmpAdminString (SIZE(0..64))
    ACCESS          read-write
    STATUS          mandatory
    DESCRIPTION     
            "The event to invoke when srExMteTriggerType is 'threshold' and
             this trigger fires based on srExMteTriggerRisingThreshold.  A
             value of 0 indicates no event.
             
             If srExMteTriggerType is not 'threshold', this object is not
             instantiated."
    DEFVAL          { "" }
    ::= { srExMteTriggerEntry 15 }

srExMteTriggerFallingEvent OBJECT-TYPE
    SYNTAX          SnmpAdminString (SIZE(0..64))
    ACCESS          read-write
    STATUS          mandatory
    DESCRIPTION     
            "The event to invoke when srExMteTriggerType is 'threshold' and
             this trigger fires based on srExMteTriggerFallingThreshold.  A
             value of 0 indicates no event.
             
             If srExMteTriggerType is not 'threshold', this object is not
             instantiated."
    DEFVAL          { "" }
    ::= { srExMteTriggerEntry 16 }

srExMteTriggerObjects OBJECT-TYPE
    SYNTAX          SnmpAdminString (SIZE(0..64))
    ACCESS          read-write
    STATUS          mandatory
    DESCRIPTION     
            "The srExMteTriggerObjectNName of a group of objects from
             srExMteTriggerObjectTable.  These objects are to be added to any
             Notification resulting from the firing of this trigger.
             
             A length of 0 indicates no additional objects."
    DEFVAL          { "" }
    ::= { srExMteTriggerEntry 17 }

srExMteTriggerStatus OBJECT-TYPE
    SYNTAX          RowStatus
    ACCESS          read-write
    STATUS          mandatory
    DESCRIPTION     
            "The control that allows creation and deletion of entries.
             Once made active an entry may not be modified except to
             
             
             
             
             
             
             
             delete it."
    DEFVAL          { createAndWait }
    ::= { srExMteTriggerEntry 18 }

srExMteTriggerObjectTable OBJECT-TYPE
    SYNTAX          SEQUENCE OF SrExMteTriggerObjectEntry
    ACCESS          not-accessible
    STATUS          mandatory
    DESCRIPTION     
            "A table of objects related to a trigger and to be added to
             Notifications resulting from that trigger."
    ::= { srExMteTrigger 3 }

srExMteTriggerObjectEntry OBJECT-TYPE
    SYNTAX          SrExMteTriggerObjectEntry
    ACCESS          not-accessible
    STATUS          mandatory
    DESCRIPTION     
            "Objects for a single trigger.  Applications create and
             delete entries using srExMteTriggerObjectStatus."
    INDEX           { srExMteTriggerObjectName, 
                      srExMteTriggerObjectIndex }
    ::= { srExMteTriggerObjectTable 1 }

SrExMteTriggerObjectEntry ::=
    SEQUENCE {
        srExMteTriggerObjectName        SnmpAdminString,
        srExMteTriggerObjectIndex       Gauge,
        srExMteTriggerObjectID          OBJECT IDENTIFIER,
        srExMteTriggerObjectIDWildcard  TruthValue,
        srExMteTriggerObjectStatus      RowStatus
    }

srExMteTriggerObjectName OBJECT-TYPE
    SYNTAX          SnmpAdminString (SIZE(1..64))
    ACCESS          not-accessible
    STATUS          mandatory
    DESCRIPTION     
            "A locally-unique, administratively assigned name for a group of
             objects to associate with a trigger."
    ::= { srExMteTriggerObjectEntry 1 }

srExMteTriggerObjectIndex OBJECT-TYPE
    SYNTAX          Gauge (1..4294967295)
    ACCESS          not-accessible
    STATUS          mandatory
    DESCRIPTION     
            "An arbitrary small integer for the purpose of identifying
             individual objects with a srExMteTriggerObjectName group."
    ::= { srExMteTriggerObjectEntry 2 }

srExMteTriggerObjectID OBJECT-TYPE
    SYNTAX          OBJECT IDENTIFIER
    ACCESS          read-write
    STATUS          mandatory
    DESCRIPTION     
            "The object identifier of a MIB object to add to a Notification
             that results from the firing of a trigger.
             
             This may be wildcarded by truncating all or part of the
             instance portion, in which case the instance portion of the
             OID for obtaining this object will be the same as that used
             in obtaining the srExMteTriggerObjectValueID that fired.
             If such wildcarding is applied, srExMteTriggerObjectIDWildcard
             must be 'true' and if not it must be 'false'."
    ::= { srExMteTriggerObjectEntry 3 }

srExMteTriggerObjectIDWildcard OBJECT-TYPE
    SYNTAX          TruthValue
    ACCESS          read-write
    STATUS          mandatory
    DESCRIPTION     
            "Control for whether srExMteTriggerObjectValueID is to be treated as
             fully-specified or wildcarded, with 'true' indicating wildcard."
    DEFVAL          { false }
    ::= { srExMteTriggerObjectEntry 4 }

srExMteTriggerObjectStatus OBJECT-TYPE
    SYNTAX          RowStatus
    ACCESS          read-write
    STATUS          mandatory
    DESCRIPTION     
            "The control that allows creation and deletion of entries.
             Once made active an entry may not be modified except to
             delete it."
    DEFVAL          { createAndWait }
    ::= { srExMteTriggerObjectEntry 5 }

srExMteEvent OBJECT IDENTIFIER
    ::= { eventMIBObjects 2 }

srExMteEventFailures OBJECT-TYPE
    SYNTAX          Counter
    ACCESS          read-only
    STATUS          mandatory
    DESCRIPTION     
            "The number of times an attempt to invoke an event
             has failed.  This counts individually for each
             attempt in a group of targets or each attempt for a
             wildcarded trigger object."
    ::= { srExMteEvent 1 }

srExMteEventTable OBJECT-TYPE
    SYNTAX          SEQUENCE OF SrExMteEventEntry
    ACCESS          not-accessible
    STATUS          mandatory
    DESCRIPTION     
            "A table of management event action information."
    ::= { srExMteEvent 2 }

srExMteEventEntry OBJECT-TYPE
    SYNTAX          SrExMteEventEntry
    ACCESS          not-accessible
    STATUS          mandatory
    DESCRIPTION     
            "Information about a single event.  Applications create and
             delete entries using srExMteEventStatus."
    INDEX           { IMPLIED srExMteEventName }
    ::= { srExMteEventTable 1 }

SrExMteEventEntry ::=
    SEQUENCE {
        srExMteEventName                SnmpAdminString,
        srExMteEventComment             DisplayString,
        srExMteEventActions             OCTET STRING,
        srExMteEventNotification        OBJECT IDENTIFIER,
        srExMteEventObjects             SnmpAdminString,
        srExMteEventSetObject           OBJECT IDENTIFIER,
        srExMteEventSetObjectWildcard   TruthValue,
        srExMteEventSetValue            INTEGER,
        srExMteEventSetTargetTag        SnmpTagValue,
        srExMteEventSetContextName      SnmpAdminString,
        srExMteEventSetContextNameWildcard  TruthValue,
        srExMteEventStatus              RowStatus
    }

srExMteEventName OBJECT-TYPE
    SYNTAX          SnmpAdminString (SIZE(1..64))
    ACCESS          not-accessible
    STATUS          mandatory
    DESCRIPTION     
            "A locally-unique, administratively assigned name for the
             event."
    ::= { srExMteEventEntry 1 }

srExMteEventComment OBJECT-TYPE
    SYNTAX          DisplayString
    ACCESS          read-write
    STATUS          mandatory
    DESCRIPTION     
            "A description of the event's function and use."
    DEFVAL          { "" }
    ::= { srExMteEventEntry 2 }

srExMteEventActions OBJECT-TYPE
    SYNTAX          OCTET STRING
--                       { notification(1), set(2) }
    ACCESS          read-write
    STATUS          mandatory
    DESCRIPTION     
            "The actions to peform when this event occurs.
             
             For 'notification', Traps and/or Informs are sent according
             to the configuration in the SNMP Notification MIB.
             
             For 'set', an SNMP Set operation is performed according to
             control values in this entry."
    DEFVAL          { 0 }
    ::= { srExMteEventEntry 3 }

srExMteEventNotification OBJECT-TYPE
    SYNTAX          OBJECT IDENTIFIER
    ACCESS          read-write
    STATUS          mandatory
    DESCRIPTION     
            "The object identifier from the NOTIFICATION-TYPE for the
             notification to use if metEventActions has 'notification' set.
             
             If 'notification' is not set, this object is not instantiated."
    ::= { srExMteEventEntry 4 }

srExMteEventObjects OBJECT-TYPE
    SYNTAX          SnmpAdminString (SIZE(0..64))
    ACCESS          read-write
    STATUS          mandatory
    DESCRIPTION     
            "The srExMteTriggerObjectName of a group of objects from
             srExMteTriggerObjectTable if srExMteEventActions has 'notification' set.
             These objects are to be added to any Notification generated by
             this event.
             
             If 'notification' is not set, this object is not instantiated.
             
             A length of 0 indicates no additional objects."
    DEFVAL          { "" }
    ::= { srExMteEventEntry 5 }

srExMteEventSetObject OBJECT-TYPE
    SYNTAX          OBJECT IDENTIFIER
    ACCESS          read-write
    STATUS          mandatory
    DESCRIPTION     
            "The object identifier from the MIB object to set if
             srExMteEventActions has 'set' set.
             
             This object identifier may be wildcarded by leaving
             sub-identifiers off the end, in which case
             nteEventSetObjectWildCard must be 'true'.
             
             If srExMteEventSetObject is wildcarded the instance used to set it
             is the same as the instance for the value of srExMteTriggerValueID
             that triggered the event.
             
             If 'set' is not set, this object is not instantiated."
    ::= { srExMteEventEntry 6 }

srExMteEventSetObjectWildcard OBJECT-TYPE
    SYNTAX          TruthValue
    ACCESS          read-write
    STATUS          mandatory
    DESCRIPTION     
            "Control over whether srExMteEventSetObject is to be treated as
             fully-specified or wildcarded, with 'true' indicating wildcard
             if srExMteEventActions has 'set' set.
             
             If 'set' is not set, this object is not instantiated."
    DEFVAL          { false }
    ::= { srExMteEventEntry 7 }

srExMteEventSetValue OBJECT-TYPE
    SYNTAX          INTEGER
    ACCESS          read-write
    STATUS          mandatory
    DESCRIPTION     
            "The value to which to set the object at srExMteEventSetObject
             if srExMteEventActions has 'set' set.
             
             If 'set' is not set, this object is not instantiated."
    DEFVAL          { 0 }
    ::= { srExMteEventEntry 8 }

srExMteEventSetTargetTag OBJECT-TYPE
    SYNTAX          SnmpTagValue
    ACCESS          read-write
    STATUS          mandatory
    DESCRIPTION     
            "The tag for the target(s) at which to set the object at
             srExMteEventSetObject to srExMteEventSetValue if srExMteEventActions
             has 'set' set.
             
             If 'set' is not set, this object is not instantiated.
             
             Systems limited to self management may not accept a non-zero
             length for the value of this object.
             
             A length of 0 indicates the local system.  In this case,
             access to the objects indicated by srExMteEventObjectID is under
             the security credentials of the requester that set
             srExMteEventStatus to 'active'."
    DEFVAL          { "" }
    ::= { srExMteEventEntry 9 }

srExMteEventSetContextName OBJECT-TYPE
    SYNTAX          SnmpAdminString
    ACCESS          read-write
    STATUS          mandatory
    DESCRIPTION     
            "The management context in which to set srExMteEventObjectID.
             if srExMteEventActions has 'set' set.
             
             If 'set' is not set, this object is not instantiated.
             
             This may be wildcarded by leaving characters off the end.  To
             indicate such wildcarding srExMteEventSetContextNameWildcard must
             be 'true'.
             
             If this context name is wildcarded the value used to complete
             the wildcarding of srExMteTriggerContextName will be appended."
    DEFVAL          { "" }
    ::= { srExMteEventEntry 10 }

srExMteEventSetContextNameWildcard OBJECT-TYPE
    SYNTAX          TruthValue
    ACCESS          read-write
    STATUS          mandatory
    DESCRIPTION     
            "Control for whether srExMteEventSetContextName is to be treated as
             fully-specified or wildcarded, with 'true' indicating wildcard
             if srExMteEventActions has 'set' set.
             
             If 'set' is not set, this object is not instantiated."
    DEFVAL          { false }
    ::= { srExMteEventEntry 11 }

srExMteEventStatus OBJECT-TYPE
    SYNTAX          RowStatus
    ACCESS          read-write
    STATUS          mandatory
    DESCRIPTION     
            "The control that allows creation and deletion of entries.
             Once made active an entry may not be modified except to
             delete it."
    DEFVAL          { createAndWait }
    ::= { srExMteEventEntry 12 }

eventMIBNotificationPrefix OBJECT IDENTIFIER
    ::= { eventMIB 2 }

eventMIBNotifications OBJECT IDENTIFIER
    ::= { eventMIBNotificationPrefix 0 }

eventMIBNotificationObjects OBJECT IDENTIFIER
    ::= { eventMIBNotificationPrefix 1 }

srExMteHotTrigger OBJECT-TYPE
    SYNTAX          SnmpAdminString
    ACCESS          read-only
    STATUS          mandatory
    DESCRIPTION     
            "The name of the trigger causing the notification."
    ::= { eventMIBNotificationObjects 1 }

srExMteHotTargetName OBJECT-TYPE
    SYNTAX          SnmpAdminString
    ACCESS          read-only
    STATUS          mandatory
    DESCRIPTION     
            "The SNMP Target MIB's snmpTargetAddrName related to the
             notification."
    ::= { eventMIBNotificationObjects 2 }

srExMteHotContextName OBJECT-TYPE
    SYNTAX          SnmpAdminString
    ACCESS          read-only
    STATUS          mandatory
    DESCRIPTION     
            "The context name related to the notification.  This must be as
             fully-qualified as possible, including filling in wildcard
             informaation determined in processing."
    ::= { eventMIBNotificationObjects 3 }

srExMteHotOID OBJECT-TYPE
    SYNTAX          OBJECT IDENTIFIER
    ACCESS          read-only
    STATUS          mandatory
    DESCRIPTION     
            "The object identifier of the destination object related to the
             notification.  This must be as fully-qualified as possible,
             inluding filling in wildcard informaation determined in
             processing.
             
             For a trigger-related notification this is from
             srExMteTriggerValueID.
             
             For a set failure this is from srExMteEventSetObject."
    ::= { eventMIBNotificationObjects 4 }

srExMteHotValue OBJECT-TYPE
    SYNTAX          INTEGER
    ACCESS          read-only
    STATUS          mandatory
    DESCRIPTION     
            "The value of the object at srExMteTriggerValueID when a
             trigger fired."
    ::= { eventMIBNotificationObjects 5 }

srExMteFailedReason OBJECT-TYPE
    SYNTAX          FailureReason
    ACCESS          read-only
    STATUS          mandatory
    DESCRIPTION     
            "The reason for the failure of an attempt to check for a
             trigger condition or set an object in response to an event."
    ::= { eventMIBNotificationObjects 6 }

srExMteTriggerSenseAlarm TRAP-TYPE
    ENTERPRISE      eventMIBNotificationPrefix
    VARIABLES       { srExMteHotTrigger, srExMteHotTargetName, 
                      srExMteHotContextName, srExMteHotOID, 
                      srExMteHotValue }
--     STATUS          mandatory
    DESCRIPTION     
            "Notification that the trigger indicated by the object
             instances has fired, for triggers with srExMteTriggerType
             'boolean'."
    ::= 1

srExMteTriggerRisingAlarm TRAP-TYPE
    ENTERPRISE      eventMIBNotificationPrefix
    VARIABLES       { srExMteHotTrigger, srExMteHotTargetName, 
                      srExMteHotContextName, srExMteHotOID, 
                      srExMteHotValue }
--     STATUS          mandatory
    DESCRIPTION     
            "Notification that the rising threshold was met for triggers
             with srExMteTriggerType 'threshold'."
    ::= 2

srExMteTriggerFallingAlarm TRAP-TYPE
    ENTERPRISE      eventMIBNotificationPrefix
    VARIABLES       { srExMteHotTrigger, srExMteHotTargetName, 
                      srExMteHotContextName, srExMteHotOID, 
                      srExMteHotValue }
--     STATUS          mandatory
    DESCRIPTION     
            "Notification that the falling threshold was met for triggers
             with srExMteTriggerType 'threshold'."
    ::= 3

srExMteTriggerFailureAlarm TRAP-TYPE
    ENTERPRISE      eventMIBNotificationPrefix
    VARIABLES       { srExMteHotTrigger, srExMteHotTargetName, 
                      srExMteHotContextName, srExMteHotOID, 
                      srExMteFailedReason }
--     STATUS          mandatory
    DESCRIPTION     
            "Notification that an attempt to check a trigger has failed.
             
             The network manager must enable this notification only with
             a certain fear and trembling, as it can easily crowd out more
             important information.  It should be used only to help diagnose
             a problem that has appeared in the error counters and can not
             be found otherwise."
    ::= 4

srExMteEventSetFailureAlarm TRAP-TYPE
    ENTERPRISE      eventMIBNotificationPrefix
    VARIABLES       { srExMteHotTrigger, srExMteHotTargetName, 
                      srExMteHotContextName, srExMteHotOID, 
                      srExMteFailedReason }
--     STATUS          mandatory
    DESCRIPTION     
            "Notification that an attempt to do a set in response to an
             event has failed.
             
             The network manager must enable this notification only with
             a certain fear and trembling, as it can easily crowd out more
             important information.  It should be used only to help diagnose
             a problem that has appeared in the error counters and can not
             be found otherwise."
    ::= 5

END -- end of module EVENT-MIB.
