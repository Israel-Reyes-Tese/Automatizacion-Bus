--
-- This SMIv1 module has been generated by smidump 0.2-cvs. Do not edit.
--

SONUS-HA-INSIGHT-MIB DEFINITIONS ::= BEGIN

IMPORTS
    TRAP-TYPE
        FROM RFC-1215
    IpAddress
        FROM RFC1155-SMI
    sonusEventClass, sonusEventDescription, sonusEventLevel, 
    sonusEventTime, sonusSequenceId
        FROM SONUS-COMMON-MIB
    sonusSystemMIBs
        FROM SONUS-SMI;

sonusHAInsightMIB OBJECT IDENTIFIER
    ::= { sonusSystemMIBs 14 }

-- sonusHAInsightMIB MODULE-IDENTITY
--     LAST-UPDATED    "200811220000Z"
--     ORGANIZATION    
--             "Sonus Networks, Inc."
--     CONTACT-INFO    
--             "   Customer Support    
--              Sonus Networks, Inc.
--              250 Apollo Drive
--              Chelmsford, MA 01824
--              USA
--              
--              Tel: 978-614-8100
--              Fax: 978-614-8609"
--     DESCRIPTION     
--             "The MIB Module for  HA Insight related objects."
--     ::= { sonusSystemMIBs 14 }


sonusHAInsightMIBObjects OBJECT IDENTIFIER
    ::= { sonusHAInsightMIB 1 }

sonusHAInsightNotifications OBJECT IDENTIFIER
    ::= { sonusHAInsightMIB 2 }

sonusHAInsightNotificationsPrefix OBJECT IDENTIFIER
    ::= { sonusHAInsightNotifications 0 }

sonusHAInsightStartFailureNotification TRAP-TYPE
    ENTERPRISE      sonusHAInsightNotifications
    VARIABLES       { sonusEventTime, sonusEventDescription, 
                      sonusEventClass, sonusEventLevel }
--     STATUS          mandatory
    DESCRIPTION     
            "Insight failed to start after failover"
    ::= 1

sonusHAInsightStopFailureNotification TRAP-TYPE
    ENTERPRISE      sonusHAInsightNotifications
    VARIABLES       { sonusEventTime, sonusEventDescription, 
                      sonusEventClass, sonusEventLevel }
--     STATUS          mandatory
    DESCRIPTION     
            "Insight failed to stop before failing over"
    ::= 2

END -- end of module SONUS-HA-INSIGHT-MIB.
