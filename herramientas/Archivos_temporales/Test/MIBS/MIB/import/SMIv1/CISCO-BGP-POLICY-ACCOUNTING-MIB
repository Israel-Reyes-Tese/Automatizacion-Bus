--
-- This SMIv1 module has been generated by smidump 0.2-cvs. Do not edit.
--

CISCO-BGP-POLICY-ACCOUNTING-MIB DEFINITIONS ::= BEGIN

IMPORTS
    ciscoMgmt
        FROM CISCO-SMI
    ifIndex
        FROM IF-MIB
    OBJECT-TYPE
        FROM RFC-1212;

ciscoBgpPolAcctMIB OBJECT IDENTIFIER
    ::= { ciscoMgmt 148 }

-- ciscoBgpPolAcctMIB MODULE-IDENTITY
--     LAST-UPDATED    "199912170000Z"
--     ORGANIZATION    
--             "Cisco Systems, Inc."
--     CONTACT-INFO    
--             "	Cisco Systems
--              Customer Service
--              
--              Postal:	170 W. Tasman Drive
--              San Jose, CA  95134
--              USA
--              
--              Tel: +1 800 553-NETS
--              
--              E-mail: cs-snmp@cisco.com"
--     DESCRIPTION     
--             "BGP policy based accounting information"
--     REVISION        "199912170000Z"
--     DESCRIPTION     
--             "Initial version of this MIB module."
--     ::= { ciscoMgmt 148 }


ciscoBgpPolAcctMIBObjects OBJECT IDENTIFIER
    ::= { ciscoBgpPolAcctMIB 1 }

cbpAcctTable OBJECT-TYPE
    SYNTAX          SEQUENCE OF CbpAcctEntry
    ACCESS          not-accessible
    STATUS          mandatory
    DESCRIPTION     
            "The cbpAcctTable provides statistics about ingress traffic
             on an interface. This data could be used for purposes like
             billing."
    ::= { ciscoBgpPolAcctMIBObjects 1 }

cbpAcctEntry OBJECT-TYPE
    SYNTAX          CbpAcctEntry
    ACCESS          not-accessible
    STATUS          mandatory
    DESCRIPTION     
            "Each cbpAcctEntry provides statistics for traffic of interest
             on an ingress interface. The traffic of interest may be used
             for purposes like billing, and is referred to from here on in
             the MIB by the term 'traffic-type', which corresponds to
             cbpAcctTrafficIndex. Traffic-types are configured by the user
             on a per interface basis.
             
             The statistics include ingress packet counts and ingress octet
             counts. Entries are created when traffic-type is configured on
             an interface. Entries are deleted automatically when the user 
             removes the corresponding traffic-type configuration from an
             interface."
    INDEX           { ifIndex, cbpAcctTrafficIndex }
    ::= { cbpAcctTable 1 }

CbpAcctEntry ::=
    SEQUENCE {
        cbpAcctTrafficIndex             INTEGER
--         cbpAcctInPacketCount            Counter64,
--         cbpAcctInOctetCount             Counter64
    }

cbpAcctTrafficIndex OBJECT-TYPE
    SYNTAX          INTEGER (0..2147483647)
    ACCESS          read-only
    STATUS          mandatory
    DESCRIPTION     
            "An integer value greater than 0, that uniquely identifies
             a traffic-type. The traffic-type has no intrinsic meaning.
             It just means the traffic coming into an interface can be
             differentiated into different types. It is up to the user to
             give meaning to and configure the various traffic-types on an 
             interface."
    ::= { cbpAcctEntry 1 }

-- cbpAcctInPacketCount OBJECT-TYPE
--     SYNTAX          Counter64
--     ACCESS          read-only
--     STATUS          mandatory
--     DESCRIPTION     
--             "The total number of packets received for a particular
--              traffic-type on an interface."
--     ::= { cbpAcctEntry 2 }

-- cbpAcctInOctetCount OBJECT-TYPE
--     SYNTAX          Counter64
--     ACCESS          read-only
--     STATUS          mandatory
--     DESCRIPTION     
--             "The total number of octets received for a particular
--              traffic-type on an interface."
--     ::= { cbpAcctEntry 3 }

ciscoBgpPolAcctMIBConformance OBJECT IDENTIFIER
    ::= { ciscoBgpPolAcctMIB 3 }

ciscoBgpPolAcctMIBCompliances OBJECT IDENTIFIER
    ::= { ciscoBgpPolAcctMIBConformance 1 }

ciscoBgpPolAcctMIBGroups OBJECT IDENTIFIER
    ::= { ciscoBgpPolAcctMIBConformance 2 }

cbpAcctTableGroup OBJECT IDENTIFIER
    ::= { ciscoBgpPolAcctMIBGroups 1 }

-- cbpAcctTableGroup OBJECT-GROUP
--     OBJECTS         { cbpAcctTrafficIndex, cbpAcctInPacketCount, 
--                       cbpAcctInOctetCount }
--     STATUS          mandatory
--     DESCRIPTION     
--             "A collection of objects providing customer traffic 
--              related parameters."
--     ::= { ciscoBgpPolAcctMIBGroups 1 }

ciscoBgpPolAcctMIBCompliance OBJECT IDENTIFIER
    ::= { ciscoBgpPolAcctMIBCompliances 1 }

-- ciscoBgpPolAcctMIBCompliance MODULE-COMPLIANCE
--     STATUS          mandatory
--     DESCRIPTION     
--             "The compliance statement for entities which implement
--              this Cisco BGP-Policy Traffic Accounting MIB."

--     MODULE          -- -- this module

--         MANDATORY-GROUPS    { cbpAcctTableGroup }

--     ::= { ciscoBgpPolAcctMIBCompliances 1 }

END -- end of module CISCO-BGP-POLICY-ACCOUNTING-MIB.
