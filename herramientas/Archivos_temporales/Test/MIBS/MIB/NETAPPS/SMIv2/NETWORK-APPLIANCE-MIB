--
-- This SMIv2 module has been generated by smidump 0.2-cvs. Do not edit.
--

NETWORK-APPLIANCE-MIB DEFINITIONS ::= BEGIN

IMPORTS
    Counter32, Integer32, IpAddress, NOTIFICATION-TYPE, OBJECT-TYPE, 
    TimeTicks, enterprises
        FROM SNMPv2-SMI;

DisplayString ::=
    OCTET STRING

netapp OBJECT IDENTIFIER
    ::= { enterprises 789 }

netapp1 OBJECT IDENTIFIER
    ::= { netapp 1 }

product OBJECT IDENTIFIER
    ::= { netapp1 1 }

productType OBJECT-TYPE
    SYNTAX          INTEGER { eisa-based(1), pci-based(2) }
    MAX-ACCESS      read-only
    STATUS          current
    DESCRIPTION     
            "The product type representing the target platform."
    ::= { product 1 }

productVersion OBJECT-TYPE
    SYNTAX          DisplayString
    MAX-ACCESS      read-only
    STATUS          current
    DESCRIPTION     
            "Version String for the Software Running on
             this platform."
    ::= { product 2 }

productId OBJECT-TYPE
    SYNTAX          DisplayString
    MAX-ACCESS      read-only
    STATUS          current
    DESCRIPTION     
            "The serial id of this system."
    ::= { product 3 }

productVendor OBJECT-TYPE
    SYNTAX          INTEGER { netapp(1), dell(2) }
    MAX-ACCESS      read-only
    STATUS          current
    DESCRIPTION     
            "The vendor id of this system, indicating the company
             that has supplied the product."
    ::= { product 4 }

sysStat OBJECT IDENTIFIER
    ::= { netapp1 2 }

cpu OBJECT IDENTIFIER
    ::= { sysStat 1 }

cpuUpTime OBJECT-TYPE
    SYNTAX          TimeTicks
    MAX-ACCESS      read-only
    STATUS          current
    DESCRIPTION     
            "The time (in hundredths of a second) that the
             CPU has been up since the last boot."
    ::= { cpu 1 }

cpuBusyTime OBJECT-TYPE
    SYNTAX          TimeTicks
    MAX-ACCESS      read-only
    STATUS          current
    DESCRIPTION     
            "The time (in hundredths of a second) that the
             CPU has been doing useful work since the last
             boot."
    ::= { cpu 2 }

cpuBusyTimePerCent OBJECT-TYPE
    SYNTAX          Integer32 (0..100)
    MAX-ACCESS      read-only
    STATUS          current
    DESCRIPTION     
            "The percent of time that the CPU has been doing
             useful work since the last boot."
    ::= { cpu 3 }

cpuIdleTime OBJECT-TYPE
    SYNTAX          TimeTicks
    MAX-ACCESS      read-only
    STATUS          current
    DESCRIPTION     
            "The time (in hundredths of a second) that the
             CPU has been idle since the last boot."
    ::= { cpu 4 }

cpuIdleTimePerCent OBJECT-TYPE
    SYNTAX          Integer32 (0..100)
    MAX-ACCESS      read-only
    STATUS          current
    DESCRIPTION     
            "The percent of time that the CPU has been idle
             since the last boot."
    ::= { cpu 5 }

misc OBJECT IDENTIFIER
    ::= { sysStat 2 }

miscNfsOps OBJECT-TYPE
    SYNTAX          Integer32
    MAX-ACCESS      read-only
    STATUS          current
    DESCRIPTION     
            "The total number of Server side NFS calls since
             the last boot"
    ::= { misc 1 }

miscNetRcvdKB OBJECT-TYPE
    SYNTAX          Integer32
    MAX-ACCESS      read-only
    STATUS          current
    DESCRIPTION     
            "The total number of KBytes received on all the
             network interfaces, since the last boot."
    ::= { misc 2 }

miscNetSentKB OBJECT-TYPE
    SYNTAX          Integer32
    MAX-ACCESS      read-only
    STATUS          current
    DESCRIPTION     
            "The total number of KBytes transmitted on all the
             network interfaces, since the last boot."
    ::= { misc 3 }

miscGlobalStatus OBJECT-TYPE
    SYNTAX          INTEGER { other(1), unknown(2), ok(3), 
                        nonCritical(4), critical(5), nonRecoverable(6) }
    MAX-ACCESS      read-only
    STATUS          current
    DESCRIPTION     
            "This indicates the overall status of the appliance.
             The algorithm to determine the value uses both
             hardware status (e.g. the number of failed fans) and
             volume status (e.g. number of volumes that are full).
             The algorithm is subject to change in future releases,
             but the range of values will not change."
    ::= { misc 4 }

miscGlobalStatusMessage OBJECT-TYPE
    SYNTAX          DisplayString
    MAX-ACCESS      read-only
    STATUS          current
    DESCRIPTION     
            "A string describing the global status,
             including a description of the condition (if
             any) that caused the status to be anything
             other than ok(3)."
    ::= { misc 25 }

cf OBJECT IDENTIFIER
    ::= { sysStat 3 }

cfSettings OBJECT-TYPE
    SYNTAX          INTEGER { notConfigured(1), enabled(2), disabled(3), 
                        takeoverByPartnerDisabled(4), thisNodeDead(5) }
    MAX-ACCESS      read-only
    STATUS          current
    DESCRIPTION     
            "Clustered Failover configuration settings.
             The value notConfigured(1) indicates that the
             cluster is not licensed. The thisNodeDead(5)
             setting indicates that this node has been 
             taken over."
    ::= { cf 1 }

cfState OBJECT-TYPE
    SYNTAX          INTEGER { dead(1), canTakeover(2), cannotTakeover(3), 
                        takeover(4) }
    MAX-ACCESS      read-only
    STATUS          current
    DESCRIPTION     
            "Clustered Failover state."
    ::= { cf 2 }

cfCannotTakeoverCause OBJECT-TYPE
    SYNTAX          INTEGER { ok(1), unknownReason(2), 
                        disabledByOperator(3), interconnectOffline(4), 
                        disabledByPartner(5), takeoverFailed(6) }
    MAX-ACCESS      read-only
    STATUS          current
    DESCRIPTION     
            "The reason this node cannot takeover its
             partner"
    ::= { cf 3 }

cfPartnerStatus OBJECT-TYPE
    SYNTAX          INTEGER { maybeDown(1), ok(2), dead(3) }
    MAX-ACCESS      read-only
    STATUS          current
    DESCRIPTION     
            "This is the status last returned by the
             Clustered Failover partner."
    ::= { cf 4 }

cfPartnerLastStatusUpdate OBJECT-TYPE
    SYNTAX          TimeTicks
    MAX-ACCESS      read-only
    STATUS          current
    DESCRIPTION     
            "If non-zero, the absolute time of the last
             update from the Clustered Failover partner."
    ::= { cf 5 }

cfPartnerName OBJECT-TYPE
    SYNTAX          DisplayString
    MAX-ACCESS      read-only
    STATUS          current
    DESCRIPTION     
            "Hostname for Clustered Failover partner."
    ::= { cf 6 }

cfPartnerSysid OBJECT-TYPE
    SYNTAX          Integer32
    MAX-ACCESS      read-only
    STATUS          current
    DESCRIPTION     
            "System ID for Clustered Failover partner."
    ::= { cf 7 }

cfInterconnectStatus OBJECT-TYPE
    SYNTAX          INTEGER { notPresent(1), down(2), partialFailure(3), 
                        up(4) }
    MAX-ACCESS      read-only
    STATUS          current
    DESCRIPTION     
            "The current status of the interconnect.
             The partialFailure(3) status indicates that
             one of the links in the interconnect hardware
             is down."
    ::= { cf 8 }

environment OBJECT IDENTIFIER
    ::= { sysStat 4 }

envOverTemperature OBJECT-TYPE
    SYNTAX          INTEGER { no(1), yes(2) }
    MAX-ACCESS      read-only
    STATUS          current
    DESCRIPTION     
            "An indication of whether the hardware is
             currently operating above its maximum rated
             temperature."
    ::= { environment 1 }

envFailedFanCount OBJECT-TYPE
    SYNTAX          Integer32
    MAX-ACCESS      read-only
    STATUS          current
    DESCRIPTION     
            "Count of the number of fans which are currently
             not running."
    ::= { environment 2 }

envFailedFanMessage OBJECT-TYPE
    SYNTAX          DisplayString
    MAX-ACCESS      read-only
    STATUS          current
    DESCRIPTION     
            "Text message describing the failed fans.  This is
             useful only if envFailedFanCount is not zero."
    ::= { environment 3 }

envFailedPowerSupplyCount OBJECT-TYPE
    SYNTAX          Integer32
    MAX-ACCESS      read-only
    STATUS          current
    DESCRIPTION     
            "Count of the number of power supplies which are
             currently not working."
    ::= { environment 4 }

envFailedPowerSupplyMessage OBJECT-TYPE
    SYNTAX          DisplayString
    MAX-ACCESS      read-only
    STATUS          current
    DESCRIPTION     
            "Text message describing the failed power supply
             or supplies.  This is useful only if
             envFailedPowerSupplyCount is not zero."
    ::= { environment 5 }

nfs OBJECT IDENTIFIER
    ::= { netapp1 3 }

curNfs OBJECT IDENTIFIER
    ::= { nfs 1 }

rpcServ OBJECT IDENTIFIER
    ::= { curNfs 1 }

rpcCalls OBJECT-TYPE
    SYNTAX          Counter32
    MAX-ACCESS      read-only
    STATUS          current
    DESCRIPTION     
            "The total number of RPC calls received, since
             the last time the statistics were cleared."
    ::= { rpcServ 1 }

rpcBadCalls OBJECT-TYPE
    SYNTAX          Counter32
    MAX-ACCESS      read-only
    STATUS          current
    DESCRIPTION     
            "The total number of calls rejected by the RPC
             layer, since the last time the statistics were
             cleared."
    ::= { rpcServ 2 }

rpcNullRecvs OBJECT-TYPE
    SYNTAX          Counter32
    MAX-ACCESS      read-only
    STATUS          current
    DESCRIPTION     
            "The number of times an RPC call was not available
             when it was thought to be received, since the
             last time the statistics were cleared."
    ::= { rpcServ 3 }

rpcBadLens OBJECT-TYPE
    SYNTAX          Counter32
    MAX-ACCESS      read-only
    STATUS          current
    DESCRIPTION     
            "The number of RPC calls received with a length
             shorter than a minimum-sized RPC call, since the
             last time the statistics were cleared."
    ::= { rpcServ 4 }

rpcServXDRCalls OBJECT-TYPE
    SYNTAX          Counter32
    MAX-ACCESS      read-only
    STATUS          current
    DESCRIPTION     
            "The number of RPC calls received whose header
             could not be XDR decoded, since the last time
             the statistics were cleared."
    ::= { rpcServ 5 }

nfsServ OBJECT IDENTIFIER
    ::= { curNfs 2 }

nfsCalls OBJECT-TYPE
    SYNTAX          Counter32
    MAX-ACCESS      read-only
    STATUS          current
    DESCRIPTION     
            "The total number of NFS calls received, since
             the last time the statistics were cleared."
    ::= { nfsServ 1 }

nfsServBadCalls OBJECT-TYPE
    SYNTAX          Counter32
    MAX-ACCESS      read-only
    STATUS          current
    DESCRIPTION     
            "The total number of received NFS calls rejected,
             since the last time the statistics were cleared."
    ::= { nfsServ 2 }

nfsV2 OBJECT IDENTIFIER
    ::= { nfsServ 3 }

v2Calls OBJECT IDENTIFIER
    ::= { nfsV2 1 }

v2cNulls OBJECT-TYPE
    SYNTAX          Counter32
    MAX-ACCESS      read-only
    STATUS          current
    DESCRIPTION     
            "The number of NFS Version 2 calls received
             for the NFSPROC_NULL (Do Nothing) procedure,
             since the last time the statistics were cleared."
    ::= { v2Calls 1 }

v2cGetattrs OBJECT-TYPE
    SYNTAX          Counter32
    MAX-ACCESS      read-only
    STATUS          current
    DESCRIPTION     
            "The number of NFS Version 2 calls received
             for the NFSPROC_GETATTR (Get File Attributes)
             procedure, since the last time the statistics
             were cleared."
    ::= { v2Calls 2 }

v2cSetattrs OBJECT-TYPE
    SYNTAX          Counter32
    MAX-ACCESS      read-only
    STATUS          current
    DESCRIPTION     
            "The number of NFS Version 2 calls received
             for the NFSPROC_SETATTR (Set File Attributes)
             procedure, since the last time the statistics
             were cleared."
    ::= { v2Calls 3 }

v2cRoots OBJECT-TYPE
    SYNTAX          Counter32
    MAX-ACCESS      read-only
    STATUS          current
    DESCRIPTION     
            "The number of NFS Version 2 calls received
             for the NFSPROC_ROOT (Get Filesystem Root)
             procedure, since the last time the statistics
             were cleared."
    ::= { v2Calls 4 }

v2cLookups OBJECT-TYPE
    SYNTAX          Counter32
    MAX-ACCESS      read-only
    STATUS          current
    DESCRIPTION     
            "The number of NFS Version 2 calls received
             for the NFSPROC_LOOKUP (Look Up File Name)
             procedure, since the last time the statistics
             were cleared."
    ::= { v2Calls 5 }

v2cReadlinks OBJECT-TYPE
    SYNTAX          Counter32
    MAX-ACCESS      read-only
    STATUS          current
    DESCRIPTION     
            "The number of NFS Version 2 calls received
             for the NFSPROC_READLINK (Read From Symbolic
             Link) procedure, since the last time the
             statistics were cleared."
    ::= { v2Calls 6 }

v2cReads OBJECT-TYPE
    SYNTAX          Counter32
    MAX-ACCESS      read-only
    STATUS          current
    DESCRIPTION     
            "The number of NFS Version 2 calls received
             for the NFSPROC_READ (Read From File)
             procedure, since the last time the statistics
             were cleared."
    ::= { v2Calls 7 }

v2cWrcaches OBJECT-TYPE
    SYNTAX          Counter32
    MAX-ACCESS      read-only
    STATUS          current
    DESCRIPTION     
            "The number of NFS Version 2 calls received
             for the NFSPROC_WRITECACHE (Write to Cache)
             procedure, since the last time the statistics
             were cleared."
    ::= { v2Calls 8 }

v2cWrites OBJECT-TYPE
    SYNTAX          Counter32
    MAX-ACCESS      read-only
    STATUS          current
    DESCRIPTION     
            "The number of NFS Version 2 calls received
             for the NFSPROC_WRITE (Write to File)
             procedure, since the last time the statistics
             were cleared."
    ::= { v2Calls 9 }

v2cCreates OBJECT-TYPE
    SYNTAX          Counter32
    MAX-ACCESS      read-only
    STATUS          current
    DESCRIPTION     
            "The number of NFS Version 2 calls received
             for the NFSPROC_CREATE (Create File)
             procedure, since the last time the statistics
             were cleared."
    ::= { v2Calls 10 }

v2cRemoves OBJECT-TYPE
    SYNTAX          Counter32
    MAX-ACCESS      read-only
    STATUS          current
    DESCRIPTION     
            "The number of NFS Version 2 calls received
             for the NFSPROC_REMOVE (Remove File)
             procedure, since the last time the statistics
             were cleared."
    ::= { v2Calls 11 }

v2cRenames OBJECT-TYPE
    SYNTAX          Counter32
    MAX-ACCESS      read-only
    STATUS          current
    DESCRIPTION     
            "The number of NFS Version 2 calls received
             for the NFSPROC_RENAME (Rename File)
             procedure, since the last time the statistics
             were cleared."
    ::= { v2Calls 12 }

v2cLinks OBJECT-TYPE
    SYNTAX          Counter32
    MAX-ACCESS      read-only
    STATUS          current
    DESCRIPTION     
            "The number of NFS Version 2 calls received
             for the NFSPROC_LINK (Create Link to File)
             procedure, since the last time the statistics
             were cleared."
    ::= { v2Calls 13 }

v2cSymlinks OBJECT-TYPE
    SYNTAX          Counter32
    MAX-ACCESS      read-only
    STATUS          current
    DESCRIPTION     
            "The number of NFS Version 2 calls received
             for the NFSPROC_SYMLINK (Create Symbolic Link)
             procedure, since the last time the statistics
             were cleared."
    ::= { v2Calls 14 }

v2cMkdirs OBJECT-TYPE
    SYNTAX          Counter32
    MAX-ACCESS      read-only
    STATUS          current
    DESCRIPTION     
            "The number of NFS Version 2 calls received
             for the NFSPROC_MKDIR (Create Directory)
             procedure, since the last time the statistics
             were cleared."
    ::= { v2Calls 15 }

v2cRmdirs OBJECT-TYPE
    SYNTAX          Counter32
    MAX-ACCESS      read-only
    STATUS          current
    DESCRIPTION     
            "The number of NFS Version 2 calls received
             for the NFSPROC_RMDIR (Remove Directory)
             procedure, since the last time the statistics
             were cleared."
    ::= { v2Calls 16 }

v2cReaddirs OBJECT-TYPE
    SYNTAX          Counter32
    MAX-ACCESS      read-only
    STATUS          current
    DESCRIPTION     
            "The number of NFS Version 2 calls received
             for the NFSPROC_READDIR (Read From Directory)
             procedure, since the last time the statistics
             were cleared."
    ::= { v2Calls 17 }

v2cStatfss OBJECT-TYPE
    SYNTAX          Counter32
    MAX-ACCESS      read-only
    STATUS          current
    DESCRIPTION     
            "The number of NFS Version 2 calls received
             for the NFSPROC_STATFS (Get Filesystem
             Attributes) procedure, since the last time
             the statistics were cleared."
    ::= { v2Calls 18 }

v2Percent OBJECT IDENTIFIER
    ::= { nfsV2 2 }

v2pNulls OBJECT-TYPE
    SYNTAX          Integer32 (0..100)
    MAX-ACCESS      read-only
    STATUS          current
    DESCRIPTION     
            "The number of NFS Version 2 calls received
             for the NFSPROC_NULL (Do Nothing) procedure
             as a percentage of total NFS calls received,
             since the last time the statistics were cleared."
    ::= { v2Percent 1 }

v2pGetattrs OBJECT-TYPE
    SYNTAX          Integer32 (0..100)
    MAX-ACCESS      read-only
    STATUS          current
    DESCRIPTION     
            "The number of NFS Version 2 calls received
             for the NFSPROC_GETATTR (Get File Attributes)
             procedure as a percentage of total NFS calls
             received, since the last time the statistics
             were cleared."
    ::= { v2Percent 2 }

v2pSetattrs OBJECT-TYPE
    SYNTAX          Integer32 (0..100)
    MAX-ACCESS      read-only
    STATUS          current
    DESCRIPTION     
            "The number of NFS Version 2 calls received
             for the NFSPROC_SETATTR (Set File Attributes)
             procedure as a percentage of total NFS calls
             received, since the last time the statistics
             were cleared."
    ::= { v2Percent 3 }

v2pRoots OBJECT-TYPE
    SYNTAX          Integer32 (0..100)
    MAX-ACCESS      read-only
    STATUS          current
    DESCRIPTION     
            "The number of NFS Version 2 calls received
             for the NFSPROC_ROOT (Get Filesystem Root)
             procedure as a percentage of total NFS calls
             received, since the last time the statistics
             were cleared."
    ::= { v2Percent 4 }

v2pLookups OBJECT-TYPE
    SYNTAX          Integer32 (0..100)
    MAX-ACCESS      read-only
    STATUS          current
    DESCRIPTION     
            "The number of NFS Version 2 calls received
             for the NFSPROC_LOOKUP (Look Up File Name)
             procedure as a percentage of total NFS calls
             received, since the last time the statistics
             were cleared."
    ::= { v2Percent 5 }

v2pReadlinks OBJECT-TYPE
    SYNTAX          Integer32 (0..100)
    MAX-ACCESS      read-only
    STATUS          current
    DESCRIPTION     
            "The number of NFS Version 2 calls received
             for the NFSPROC_READLINK (Read From Symbolic
             Link) procedure as a percentage of total NFS
             calls received, since the last time the
             statistics were cleared."
    ::= { v2Percent 6 }

v2pReads OBJECT-TYPE
    SYNTAX          Integer32 (0..100)
    MAX-ACCESS      read-only
    STATUS          current
    DESCRIPTION     
            "The number of NFS Version 2 calls received
             for the NFSPROC_READ (Read From File)
             procedure as a percentage of total NFS calls
             received, since the last time the statistics
             were cleared."
    ::= { v2Percent 7 }

v2pWrcaches OBJECT-TYPE
    SYNTAX          Integer32 (0..100)
    MAX-ACCESS      read-only
    STATUS          current
    DESCRIPTION     
            "The number of NFS Version 2 calls received
             for the NFSPROC_WRITECACHE (Write to Cache)
             procedure as a percentage of total NFS calls
             received, since the last time the statistics
             were cleared."
    ::= { v2Percent 8 }

v2pWrites OBJECT-TYPE
    SYNTAX          Integer32 (0..100)
    MAX-ACCESS      read-only
    STATUS          current
    DESCRIPTION     
            "The number of NFS Version 2 calls received
             for the NFSPROC_WRITE (Write to File)
             procedure as a percentage of total NFS calls
             received, since the last time the statistics
             were cleared."
    ::= { v2Percent 9 }

v2pCreates OBJECT-TYPE
    SYNTAX          Integer32 (0..100)
    MAX-ACCESS      read-only
    STATUS          current
    DESCRIPTION     
            "The number of NFS Version 2 calls received
             for the NFSPROC_CREATE (Create File)
             procedure as a percentage of total NFS calls
             received, since the last time the statistics
             were cleared."
    ::= { v2Percent 10 }

v2pRemoves OBJECT-TYPE
    SYNTAX          Integer32 (0..100)
    MAX-ACCESS      read-only
    STATUS          current
    DESCRIPTION     
            "The number of NFS Version 2 calls received
             for the NFSPROC_REMOVE (Remove File)
             procedure as a percentage of total NFS calls
             received, since the last time the statistics
             were cleared."
    ::= { v2Percent 11 }

v2pRenames OBJECT-TYPE
    SYNTAX          Integer32 (0..100)
    MAX-ACCESS      read-only
    STATUS          current
    DESCRIPTION     
            "The number of NFS Version 2 calls received
             for the NFSPROC_RENAME (Rename File)
             procedure as a percentage of total NFS calls
             received, since the last time the statistics
             were cleared."
    ::= { v2Percent 12 }

v2pLinks OBJECT-TYPE
    SYNTAX          Integer32 (0..100)
    MAX-ACCESS      read-only
    STATUS          current
    DESCRIPTION     
            "The number of NFS Version 2 calls received
             for the NFSPROC_LINK (Create Link to File)
             procedure as a percentage of total NFS calls
             received, since the last time the statistics
             were cleared."
    ::= { v2Percent 13 }

v2pSymlinks OBJECT-TYPE
    SYNTAX          Integer32 (0..100)
    MAX-ACCESS      read-only
    STATUS          current
    DESCRIPTION     
            "The number of NFS Version 2 calls received
             for the NFSPROC_SYMLINK (Create Symbolic Link)
             procedure as a percentage of total NFS calls
             received, since the last time the statistics
             were cleared."
    ::= { v2Percent 14 }

v2pMkdirs OBJECT-TYPE
    SYNTAX          Integer32 (0..100)
    MAX-ACCESS      read-only
    STATUS          current
    DESCRIPTION     
            "The number of NFS Version 2 calls received
             for the NFSPROC_MKDIR (Create Directory)
             procedure as a percentage of total NFS calls
             received, since the last time the statistics
             were cleared."
    ::= { v2Percent 15 }

v2pRmdirs OBJECT-TYPE
    SYNTAX          Integer32 (0..100)
    MAX-ACCESS      read-only
    STATUS          current
    DESCRIPTION     
            "The number of NFS Version 2 calls received
             for the NFSPROC_RMDIR (Remove Directory)
             procedure as a percentage of total NFS calls
             received, since the last time the statistics
             were cleared."
    ::= { v2Percent 16 }

v2pReaddirs OBJECT-TYPE
    SYNTAX          Integer32 (0..100)
    MAX-ACCESS      read-only
    STATUS          current
    DESCRIPTION     
            "The number of NFS Version 2 calls received
             for the NFSPROC_READDIR (Read From Directory)
             procedure as a percentage of total NFS calls
             received, since the last time the statistics
             were cleared."
    ::= { v2Percent 17 }

v2pStatfss OBJECT-TYPE
    SYNTAX          Integer32 (0..100)
    MAX-ACCESS      read-only
    STATUS          current
    DESCRIPTION     
            "The number of NFS Version 2 calls received
             for the NFSPROC_STATFS (Get Filesystem
             Attributes) procedure as a percentage of
             total NFS calls received, since the last
             time the statistics were cleared."
    ::= { v2Percent 18 }

v2CachedCalls OBJECT IDENTIFIER
    ::= { nfsV2 3 }

v2ccNulls OBJECT-TYPE
    SYNTAX          Counter32
    MAX-ACCESS      read-only
    STATUS          current
    DESCRIPTION     
            "The number of NFS Version 2 calls received
             for the NFSPROC_NULL (Do Nothing) procedure,
             that did not result in the filesystem
             blocking to read from disk, since the last
             time the statistics were cleared."
    ::= { v2CachedCalls 1 }

v2ccGetattrs OBJECT-TYPE
    SYNTAX          Counter32
    MAX-ACCESS      read-only
    STATUS          current
    DESCRIPTION     
            "The number of NFS Version 2 calls received
             for the NFSPROC_GETATTR (Get File Attributes)
             procedure, that did not result in the
             filesystem blocking to read from disk, since
             the last time the statistics were cleared."
    ::= { v2CachedCalls 2 }

v2ccSetattrs OBJECT-TYPE
    SYNTAX          Counter32
    MAX-ACCESS      read-only
    STATUS          current
    DESCRIPTION     
            "The number of NFS Version 2 calls received
             for the NFSPROC_SETATTR (Set File Attributes)
             procedure, that did not result in the
             filesystem blocking to read from disk, since
             the last time the statistics were cleared."
    ::= { v2CachedCalls 3 }

v2ccRoots OBJECT-TYPE
    SYNTAX          Counter32
    MAX-ACCESS      read-only
    STATUS          current
    DESCRIPTION     
            "The number of NFS Version 2 calls received
             for the NFSPROC_ROOT (Get Filesystem Root)
             procedure, that did not result in the
             filesystem blocking to read from disk, since
             the last time the statistics were cleared."
    ::= { v2CachedCalls 4 }

v2ccLookups OBJECT-TYPE
    SYNTAX          Counter32
    MAX-ACCESS      read-only
    STATUS          current
    DESCRIPTION     
            "The number of NFS Version 2 calls received
             for the NFSPROC_LOOKUP (Look Up File Name)
             procedure, that did not result in the
             filesystem blocking to read from disk, since
             the last time the statistics were cleared."
    ::= { v2CachedCalls 5 }

v2ccReadlinks OBJECT-TYPE
    SYNTAX          Counter32
    MAX-ACCESS      read-only
    STATUS          current
    DESCRIPTION     
            "The number of NFS Version 2 calls received
             for the NFSPROC_READLINK (Read From Symbolic
             Link) procedure, that did not result in the
             filesystem blocking to read from disk, since
             the last time the statistics were cleared."
    ::= { v2CachedCalls 6 }

v2ccReads OBJECT-TYPE
    SYNTAX          Counter32
    MAX-ACCESS      read-only
    STATUS          current
    DESCRIPTION     
            "The number of NFS Version 2 calls received
             for the NFSPROC_READ (Read From File)
             procedure, that did not result in the
             filesystem blocking to read from disk, since
             the last time the statistics were cleared."
    ::= { v2CachedCalls 7 }

v2ccWrcaches OBJECT-TYPE
    SYNTAX          Counter32
    MAX-ACCESS      read-only
    STATUS          current
    DESCRIPTION     
            "The number of NFS Version 2 calls received
             for the NFSPROC_WRITECACHE (Write to Cache)
             procedure, that did not result in the
             filesystem blocking to read from disk, since
             the last time the statistics were cleared."
    ::= { v2CachedCalls 8 }

v2ccWrites OBJECT-TYPE
    SYNTAX          Counter32
    MAX-ACCESS      read-only
    STATUS          current
    DESCRIPTION     
            "The number of NFS Version 2 calls received
             for the NFSPROC_WRITE (Write to File)
             procedure, that did not result in the
             filesystem blocking to read from disk, since
             the last time the statistics were cleared."
    ::= { v2CachedCalls 9 }

v2ccCreates OBJECT-TYPE
    SYNTAX          Counter32
    MAX-ACCESS      read-only
    STATUS          current
    DESCRIPTION     
            "The number of NFS Version 2 calls received
             for the NFSPROC_CREATE (Create File)
             procedure, that did not result in the
             filesystem blocking to read from disk, since
             the last time the statistics were cleared."
    ::= { v2CachedCalls 10 }

v2ccRemoves OBJECT-TYPE
    SYNTAX          Counter32
    MAX-ACCESS      read-only
    STATUS          current
    DESCRIPTION     
            "The number of NFS Version 2 calls received
             for the NFSPROC_REMOVE (Remove File)
             procedure, that did not result in the
             filesystem blocking to read from disk, since
             the last time the statistics were cleared."
    ::= { v2CachedCalls 11 }

v2ccRenames OBJECT-TYPE
    SYNTAX          Counter32
    MAX-ACCESS      read-only
    STATUS          current
    DESCRIPTION     
            "The number of NFS Version 2 calls received
             for the NFSPROC_RENAME (Rename File)
             procedure, that did not result in the
             filesystem blocking to read from disk, since
             the last time the statistics were cleared."
    ::= { v2CachedCalls 12 }

v2ccLinks OBJECT-TYPE
    SYNTAX          Counter32
    MAX-ACCESS      read-only
    STATUS          current
    DESCRIPTION     
            "The number of NFS Version 2 calls received
             for the NFSPROC_LINK (Create Link to File)
             procedure, that did not result in the
             filesystem blocking to read from disk, since
             the last time the statistics were cleared."
    ::= { v2CachedCalls 13 }

v2ccSymlinks OBJECT-TYPE
    SYNTAX          Counter32
    MAX-ACCESS      read-only
    STATUS          current
    DESCRIPTION     
            "The number of NFS Version 2 calls received
             for the NFSPROC_SYMLINK (Create Symbolic Link)
             procedure, that did not result in the
             filesystem blocking to read from disk, since
             the last time the statistics were cleared."
    ::= { v2CachedCalls 14 }

v2ccMkdirs OBJECT-TYPE
    SYNTAX          Counter32
    MAX-ACCESS      read-only
    STATUS          current
    DESCRIPTION     
            "The number of NFS Version 2 calls received
             for the NFSPROC_MKDIR (Create Directory)
             procedure, that did not result in the
             filesystem blocking to read from disk, since
             the last time the statistics were cleared."
    ::= { v2CachedCalls 15 }

v2ccRmdirs OBJECT-TYPE
    SYNTAX          Counter32
    MAX-ACCESS      read-only
    STATUS          current
    DESCRIPTION     
            "The number of NFS Version 2 calls received
             for the NFSPROC_RMDIR (Remove Directory)
             procedure, that did not result in the
             filesystem blocking to read from disk, since
             the last time the statistics were cleared."
    ::= { v2CachedCalls 16 }

v2ccReaddirs OBJECT-TYPE
    SYNTAX          Counter32
    MAX-ACCESS      read-only
    STATUS          current
    DESCRIPTION     
            "The number of NFS Version 2 calls received
             for the NFSPROC_READDIR (Read From Directory)
             procedure, that did not result in the
             filesystem blocking to read from disk, since
             the last time the statistics were cleared."
    ::= { v2CachedCalls 17 }

v2ccStatfss OBJECT-TYPE
    SYNTAX          Counter32
    MAX-ACCESS      read-only
    STATUS          current
    DESCRIPTION     
            "The number of NFS Version 2 calls received
             for the NFSPROC_STATFS (Get Filesystem
             Attributes) procedure, that did not result
             in the filesystem blocking to read from disk,
             since the last time the statistics were cleared."
    ::= { v2CachedCalls 18 }

v2CachedPerCent OBJECT IDENTIFIER
    ::= { nfsV2 4 }

v2cpNulls OBJECT-TYPE
    SYNTAX          Integer32 (0..100)
    MAX-ACCESS      read-only
    STATUS          current
    DESCRIPTION     
            "The number of NFS Version 2 calls received
             for the NFSPROC_NULL (Do Nothing) procedure,
             that did not result in the filesystem
             blocking to read from disk, as a percentage
             of the total number of calls received for
             this procedure, since the last time the
             statistics were cleared."
    ::= { v2CachedPerCent 1 }

v2cpGetattrs OBJECT-TYPE
    SYNTAX          Integer32 (0..100)
    MAX-ACCESS      read-only
    STATUS          current
    DESCRIPTION     
            "The number of NFS Version 2 calls received
             for the NFSPROC_GETATTR (Get File Attributes)
             procedure, that did not result in the
             filesystem blocking to read from disk, as a
             percentage of the total number of calls
             received for this procedure, since the last
             time the statistics were cleared."
    ::= { v2CachedPerCent 2 }

v2cpSetattrs OBJECT-TYPE
    SYNTAX          Integer32 (0..100)
    MAX-ACCESS      read-only
    STATUS          current
    DESCRIPTION     
            "The number of NFS Version 2 calls received
             for the NFSPROC_SETATTR (Set File Attributes)
             procedure, that did not result in the
             filesystem blocking to read from disk, as a
             percentage of the total number of calls
             received for this procedure, since the last
             time the statistics were cleared."
    ::= { v2CachedPerCent 3 }

v2cpRoots OBJECT-TYPE
    SYNTAX          Integer32 (0..100)
    MAX-ACCESS      read-only
    STATUS          current
    DESCRIPTION     
            "The number of NFS Version 2 calls received
             for the NFSPROC_ROOT (Get Filesystem Root)
             procedure, that did not result in the
             filesystem blocking to read from disk, as a
             percentage of the total number of calls
             received for this procedure, since the last
             time the statistics were cleared."
    ::= { v2CachedPerCent 4 }

v2cpLookups OBJECT-TYPE
    SYNTAX          Integer32 (0..100)
    MAX-ACCESS      read-only
    STATUS          current
    DESCRIPTION     
            "The number of NFS Version 2 calls received
             for the NFSPROC_LOOKUP (Look Up File Name)
             procedure, that did not result in the
             filesystem blocking to read from disk, as a
             percentage of the total number of calls
             received for this procedure, since the last
             time the statistics were cleared."
    ::= { v2CachedPerCent 5 }

v2cpReadlinks OBJECT-TYPE
    SYNTAX          Integer32 (0..100)
    MAX-ACCESS      read-only
    STATUS          current
    DESCRIPTION     
            "The number of NFS Version 2 calls received
             for the NFSPROC_READLINK (Read From Symbolic
             Link) procedure, that did not result in the
             filesystem blocking to read from disk, as a
             percentage of the total number of calls
             received for this procedure, since the last
             time the statistics were cleared."
    ::= { v2CachedPerCent 6 }

v2cpReads OBJECT-TYPE
    SYNTAX          Integer32 (0..100)
    MAX-ACCESS      read-only
    STATUS          current
    DESCRIPTION     
            "The number of NFS Version 2 calls received
             for the NFSPROC_READ (Read From File)
             procedure, that did not result in the
             filesystem blocking to read from disk, as a
             percentage of the total number of calls
             received for this procedure, since the last
             time the statistics were cleared."
    ::= { v2CachedPerCent 7 }

v2cpWrcaches OBJECT-TYPE
    SYNTAX          Integer32 (0..100)
    MAX-ACCESS      read-only
    STATUS          current
    DESCRIPTION     
            "The number of NFS Version 2 calls received
             for the NFSPROC_WRITECACHE (Write to Cache)
             procedure, that did not result in the
             filesystem blocking to read from disk, as a
             percentage of the total number of calls
             received for this procedure, since the last
             time the statistics were cleared."
    ::= { v2CachedPerCent 8 }

v2cpWrites OBJECT-TYPE
    SYNTAX          Integer32 (0..100)
    MAX-ACCESS      read-only
    STATUS          current
    DESCRIPTION     
            "The number of NFS Version 2 calls received
             for the NFSPROC_WRITE (Write to File)
             procedure, that did not result in the
             filesystem blocking to read from disk, as a
             percentage of the total number of calls
             received for this procedure, since the last
             time the statistics were cleared."
    ::= { v2CachedPerCent 9 }

v2cpCreates OBJECT-TYPE
    SYNTAX          Integer32 (0..100)
    MAX-ACCESS      read-only
    STATUS          current
    DESCRIPTION     
            "The number of NFS Version 2 calls received
             for the NFSPROC_CREATE (Create File)
             procedure, that did not result in the
             filesystem blocking to read from disk, as a
             percentage of the total number of calls
             received for this procedure, since the last
             time the statistics were cleared."
    ::= { v2CachedPerCent 10 }

v2cpRemoves OBJECT-TYPE
    SYNTAX          Integer32 (0..100)
    MAX-ACCESS      read-only
    STATUS          current
    DESCRIPTION     
            "The number of NFS Version 2 calls received
             for the NFSPROC_REMOVE (Remove File)
             procedure, that did not result in the
             filesystem blocking to read from disk, as a
             percentage of the total number of calls
             received for this procedure, since the last
             time the statistics were cleared."
    ::= { v2CachedPerCent 11 }

v2cpRenames OBJECT-TYPE
    SYNTAX          Integer32 (0..100)
    MAX-ACCESS      read-only
    STATUS          current
    DESCRIPTION     
            "The number of NFS Version 2 calls received
             for the NFSPROC_RENAME (Rename File)
             procedure, that did not result in the
             filesystem blocking to read from disk, as a
             percentage of the total number of calls
             received for this procedure, since the last
             time the statistics were cleared."
    ::= { v2CachedPerCent 12 }

v2cpLinks OBJECT-TYPE
    SYNTAX          Integer32 (0..100)
    MAX-ACCESS      read-only
    STATUS          current
    DESCRIPTION     
            "The number of NFS Version 2 calls received
             for the NFSPROC_LINK (Create Link to File)
             procedure, that did not result in the
             filesystem blocking to read from disk, as a
             percentage of the total number of calls
             received for this procedure, since the last
             time the statistics were cleared."
    ::= { v2CachedPerCent 13 }

v2cpSymlinks OBJECT-TYPE
    SYNTAX          Integer32 (0..100)
    MAX-ACCESS      read-only
    STATUS          current
    DESCRIPTION     
            "The number of NFS Version 2 calls received
             for the NFSPROC_SYMLINK (Create Symbolic
             Link) procedure, that did not result in the
             filesystem blocking to read from disk, as a
             percentage of the total number of calls
             received for this procedure, since the last
             time the statistics were cleared."
    ::= { v2CachedPerCent 14 }

v2cpMkdirs OBJECT-TYPE
    SYNTAX          Integer32 (0..100)
    MAX-ACCESS      read-only
    STATUS          current
    DESCRIPTION     
            "The number of NFS Version 2 calls received
             for the NFSPROC_MKDIR (Create Directory)
             procedure, that did not result in the
             filesystem blocking to read from disk, as a
             percentage of the total number of calls
             received for this procedure, since the last
             time the statistics were cleared."
    ::= { v2CachedPerCent 15 }

v2cpRmdirs OBJECT-TYPE
    SYNTAX          Integer32 (0..100)
    MAX-ACCESS      read-only
    STATUS          current
    DESCRIPTION     
            "The number of NFS Version 2 calls received
             for the NFSPROC_RMDIR (Remove Directory)
             procedure, that did not result in the
             filesystem blocking to read from disk, as a
             percentage of the total number of calls
             received for this procedure, since the last
             time the statistics were cleared."
    ::= { v2CachedPerCent 16 }

v2cpReaddirs OBJECT-TYPE
    SYNTAX          Integer32 (0..100)
    MAX-ACCESS      read-only
    STATUS          current
    DESCRIPTION     
            "The number of NFS Version 2 calls received
             for the NFSPROC_READDIR (Read From Directory)
             procedure, that did not result in the
             filesystem blocking to read from disk, as a
             percentage of the total number of calls
             received for this procedure, since the last
             time the statistics were cleared."
    ::= { v2CachedPerCent 17 }

v2cpStatfss OBJECT-TYPE
    SYNTAX          Integer32 (0..100)
    MAX-ACCESS      read-only
    STATUS          current
    DESCRIPTION     
            "The number of NFS Version 2 calls received
             for the NFSPROC_STATFS (Get Filesystem
             Attributes) procedure, that did not result
             in the filesystem blocking to read from
             disk, as a percentage of the total number
             of calls received for this procedure, since
             the last time the statistics were cleared."
    ::= { v2CachedPerCent 18 }

nfsV3 OBJECT IDENTIFIER
    ::= { nfsServ 4 }

v3Calls OBJECT IDENTIFIER
    ::= { nfsV3 1 }

v3cNulls OBJECT-TYPE
    SYNTAX          Counter32
    MAX-ACCESS      read-only
    STATUS          current
    DESCRIPTION     
            "The number of NFS Version 3 calls received
             for the NFSPROC3_NULL (Do Nothing) procedure,
             since the last time the statistics were cleared."
    ::= { v3Calls 1 }

v3cGetattrs OBJECT-TYPE
    SYNTAX          Counter32
    MAX-ACCESS      read-only
    STATUS          current
    DESCRIPTION     
            "The number of NFS Version 3 calls received
             for the NFSPROC3_GETATTR (Get File Attributes)
             procedure, since the last time the statistics
             were cleared."
    ::= { v3Calls 2 }

v3cSetattrs OBJECT-TYPE
    SYNTAX          Counter32
    MAX-ACCESS      read-only
    STATUS          current
    DESCRIPTION     
            "The number of NFS Version 3 calls received
             for the NFSPROC3_SETATTR (Set File Attributes)
             procedure, since the last time the statistics
             were cleared."
    ::= { v3Calls 3 }

v3cLookups OBJECT-TYPE
    SYNTAX          Counter32
    MAX-ACCESS      read-only
    STATUS          current
    DESCRIPTION     
            "The number of NFS Version 3 calls received
             for the NFSPROC3_LOOKUP (Lookup Filename)
             procedure, since the last time the statistics
             were cleared."
    ::= { v3Calls 4 }

v3cAccesss OBJECT-TYPE
    SYNTAX          Counter32
    MAX-ACCESS      read-only
    STATUS          current
    DESCRIPTION     
            "The number of NFS Version 3 calls received
             for the NFSPROC3_ACCESS (Check Access Permission)
             procedure, since the last time the statistics
             were cleared."
    ::= { v3Calls 5 }

v3cReadlinks OBJECT-TYPE
    SYNTAX          Counter32
    MAX-ACCESS      read-only
    STATUS          current
    DESCRIPTION     
            "The number of NFS Version 3 calls received
             for the NFSPROC3_READLINK (Read from Symbolic
             Link) procedure, since the last time the
             statistics were cleared."
    ::= { v3Calls 6 }

v3cReads OBJECT-TYPE
    SYNTAX          Counter32
    MAX-ACCESS      read-only
    STATUS          current
    DESCRIPTION     
            "The number of NFS Version 3 calls received
             for the NFSPROC3_READ (Read From File)
             procedure, since the last time the statistics
             were cleared."
    ::= { v3Calls 7 }

v3cWrites OBJECT-TYPE
    SYNTAX          Counter32
    MAX-ACCESS      read-only
    STATUS          current
    DESCRIPTION     
            "The number of NFS Version 3 calls received
             for the NFSPROC3_WRITE (Write to File)
             procedure, since the last time the statistics
             were cleared."
    ::= { v3Calls 8 }

v3cCreates OBJECT-TYPE
    SYNTAX          Counter32
    MAX-ACCESS      read-only
    STATUS          current
    DESCRIPTION     
            "The number of NFS Version 3 calls received
             for the NFSPROC3_CREATE (Create a File)
             procedure, since the last time the statistics
             were cleared."
    ::= { v3Calls 9 }

v3cMkdirs OBJECT-TYPE
    SYNTAX          Counter32
    MAX-ACCESS      read-only
    STATUS          current
    DESCRIPTION     
            "The number of NFS Version 3 calls received
             for the NFSPROC3_MKDIR (Create a Directory)
             procedure, since the last time the statistics
             were cleared."
    ::= { v3Calls 10 }

v3cSymlinks OBJECT-TYPE
    SYNTAX          Counter32
    MAX-ACCESS      read-only
    STATUS          current
    DESCRIPTION     
            "The number of NFS Version 3 calls received
             for the NFSPROC3_SYMLINK (Create a Symbolic
             Link) procedure, since the last time the
             statistics were cleared."
    ::= { v3Calls 11 }

v3cMknods OBJECT-TYPE
    SYNTAX          Counter32
    MAX-ACCESS      read-only
    STATUS          current
    DESCRIPTION     
            "The number of NFS Version 3 calls received
             for the NFSPROC3_MKNOD (Create a Special
             Device) procedure, since the last time the
             statistics were cleared."
    ::= { v3Calls 12 }

v3cRemoves OBJECT-TYPE
    SYNTAX          Counter32
    MAX-ACCESS      read-only
    STATUS          current
    DESCRIPTION     
            "The number of NFS Version 3 calls received
             for the NFSPROC3_REMOVE (Remove a File)
             procedure, since the last time the statistics
             were cleared."
    ::= { v3Calls 13 }

v3cRmdirs OBJECT-TYPE
    SYNTAX          Counter32
    MAX-ACCESS      read-only
    STATUS          current
    DESCRIPTION     
            "The number of NFS Version 3 calls received
             for the NFSPROC3_RMDIR (Remove a Directory)
             procedure, since the last time the statistics
             were cleared."
    ::= { v3Calls 14 }

v3cRenames OBJECT-TYPE
    SYNTAX          Counter32
    MAX-ACCESS      read-only
    STATUS          current
    DESCRIPTION     
            "The number of NFS Version 3 calls received
             for the NFSPROC3_RENAME (Rename a File or
             Directory) procedure, since the last time
             the statistics were cleared."
    ::= { v3Calls 15 }

v3cLinks OBJECT-TYPE
    SYNTAX          Counter32
    MAX-ACCESS      read-only
    STATUS          current
    DESCRIPTION     
            "The number of NFS Version 3 calls received
             for the NFSPROC3_LINK (Create Link to an
             Object) procedure, since the last time the
             statistics were cleared."
    ::= { v3Calls 16 }

v3cReaddirs OBJECT-TYPE
    SYNTAX          Counter32
    MAX-ACCESS      read-only
    STATUS          current
    DESCRIPTION     
            "The number of NFS Version 3 calls received
             for the NFSPROC3_READDIR (Read From Directory)
             procedure, since the last time the statistics
             were cleared."
    ::= { v3Calls 17 }

v3cReaddirPluss OBJECT-TYPE
    SYNTAX          Counter32
    MAX-ACCESS      read-only
    STATUS          current
    DESCRIPTION     
            "The number of NFS Version 3 calls received
             for the NFSPROC3_READDIRPLUS (Extended Read
             from Directory) procedure, since the last
             time the statistics were cleared."
    ::= { v3Calls 18 }

v3cFsstats OBJECT-TYPE
    SYNTAX          Counter32
    MAX-ACCESS      read-only
    STATUS          current
    DESCRIPTION     
            "The number of NFS Version 3 calls received
             for the NFSPROC3_FSSTAT (Get Dynamic File
             System Information) procedure, since the
             last time the statistics were cleared."
    ::= { v3Calls 19 }

v3cFsinfos OBJECT-TYPE
    SYNTAX          Counter32
    MAX-ACCESS      read-only
    STATUS          current
    DESCRIPTION     
            "The number of NFS Version 3 calls received
             for the NFSPROC3_FSINFO (Get Static File System
             Information) procedure, since the last time
             the statistics were cleared."
    ::= { v3Calls 20 }

v3cPathconfs OBJECT-TYPE
    SYNTAX          Counter32
    MAX-ACCESS      read-only
    STATUS          current
    DESCRIPTION     
            "The number of NFS Version 3 calls received
             for the NFSPROC3_PATHCONF (Retrieve POSIX
             Information) procedure, since the last time
             the statistics were cleared."
    ::= { v3Calls 21 }

v3cCommits OBJECT-TYPE
    SYNTAX          Counter32
    MAX-ACCESS      read-only
    STATUS          current
    DESCRIPTION     
            "The number of NFS Version 3 calls received
             for the NFSPROC3_COMMIT (Commit Cached Data on
             a Server to Stable Storage) procedure, since
             the last time the statistics were cleared."
    ::= { v3Calls 22 }

v3Percent OBJECT IDENTIFIER
    ::= { nfsV3 2 }

v3pNulls OBJECT-TYPE
    SYNTAX          Integer32 (0..100)
    MAX-ACCESS      read-only
    STATUS          current
    DESCRIPTION     
            "The number of NFS Version 3 calls received
             for the NFSPROC3_NULL (Do Nothing) procedure,
             as a percentage of the total NFS calls
             received, since the last time the statistics
             were cleared."
    ::= { v3Percent 1 }

v3pGetattrs OBJECT-TYPE
    SYNTAX          Integer32 (0..100)
    MAX-ACCESS      read-only
    STATUS          current
    DESCRIPTION     
            "The number of NFS Version 3 calls received
             for the NFSPROC3_GETATTR (Get File Attributes)
             procedure, as a percentage of the total NFS
             calls received, since the last time the
             statistics were cleared."
    ::= { v3Percent 2 }

v3pSetattrs OBJECT-TYPE
    SYNTAX          Integer32 (0..100)
    MAX-ACCESS      read-only
    STATUS          current
    DESCRIPTION     
            "The number of NFS Version 3 calls received
             for the NFSPROC3_SETATTR (Set File Attributes)
             procedure, as a percentage of the total NFS
             calls received, since the last time the
             statistics were cleared."
    ::= { v3Percent 3 }

v3pLookups OBJECT-TYPE
    SYNTAX          Integer32 (0..100)
    MAX-ACCESS      read-only
    STATUS          current
    DESCRIPTION     
            "The number of NFS Version 3 calls received
             for the NFSPROC3_LOOKUP (Lookup Filename)
             procedure, as a percentage of the total NFS
             calls received, since the last time the
             statistics were cleared."
    ::= { v3Percent 4 }

v3pAccesss OBJECT-TYPE
    SYNTAX          Integer32 (0..100)
    MAX-ACCESS      read-only
    STATUS          current
    DESCRIPTION     
            "The number of NFS Version 3 calls received
             for the NFSPROC3_ACCESS (Check Access
             Permission) procedure, as a percentage of
             the total NFS calls received, since the
             last time the statistics were cleared."
    ::= { v3Percent 5 }

v3pReadlinks OBJECT-TYPE
    SYNTAX          Integer32 (0..100)
    MAX-ACCESS      read-only
    STATUS          current
    DESCRIPTION     
            "The number of NFS Version 3 calls received
             for the NFSPROC3_READLINK (Read from Symbolic
             Link) procedure, as a percentage of the total
             NFS calls received, since the last time the
             statistics were cleared."
    ::= { v3Percent 6 }

v3pReads OBJECT-TYPE
    SYNTAX          Integer32 (0..100)
    MAX-ACCESS      read-only
    STATUS          current
    DESCRIPTION     
            "The number of NFS Version 3 calls received
             for the NFSPROC3_READ (Read From File)
             procedure, as a percentage of the total NFS
             calls received, since the last time the
             statistics were cleared."
    ::= { v3Percent 7 }

v3pWrites OBJECT-TYPE
    SYNTAX          Integer32 (0..100)
    MAX-ACCESS      read-only
    STATUS          current
    DESCRIPTION     
            "The number of NFS Version 3 calls received
             for the NFSPROC3_WRITE (Write to File)
             procedure, as a percentage of the total NFS
             calls received, since the last time the
             statistics were cleared."
    ::= { v3Percent 8 }

v3pCreates OBJECT-TYPE
    SYNTAX          Integer32 (0..100)
    MAX-ACCESS      read-only
    STATUS          current
    DESCRIPTION     
            "The number of NFS Version 3 calls received
             for the NFSPROC3_CREATE (Create a File)
             procedure, as a percentage of the total NFS
             calls received, since the last time the
             statistics were cleared."
    ::= { v3Percent 9 }

v3pMkdirs OBJECT-TYPE
    SYNTAX          Integer32 (0..100)
    MAX-ACCESS      read-only
    STATUS          current
    DESCRIPTION     
            "The number of NFS Version 3 calls received
             for the NFSPROC3_MKDIR (Create a Directory)
             procedure, as a percentage of the total NFS
             calls received, since the last time the
             statistics were cleared."
    ::= { v3Percent 10 }

v3pSymlinks OBJECT-TYPE
    SYNTAX          Integer32 (0..100)
    MAX-ACCESS      read-only
    STATUS          current
    DESCRIPTION     
            "The number of NFS Version 3 calls received
             for the NFSPROC3_SYMLINK (Create a Symbolic
             Link) procedure, as a percentage of the total
             NFS calls received, since the last time the
             statistics were cleared."
    ::= { v3Percent 11 }

v3pMknods OBJECT-TYPE
    SYNTAX          Integer32 (0..100)
    MAX-ACCESS      read-only
    STATUS          current
    DESCRIPTION     
            "The number of NFS Version 3 calls received
             for the NFSPROC3_MKNOD (Create a Special
             Device) procedure, as a percentage of the
             total NFS calls received, since the last
             time the statistics were cleared."
    ::= { v3Percent 12 }

v3pRemoves OBJECT-TYPE
    SYNTAX          Integer32 (0..100)
    MAX-ACCESS      read-only
    STATUS          current
    DESCRIPTION     
            "The number of NFS Version 3 calls received
             for the NFSPROC3_REMOVE (Remove a File)
             procedure, as a percentage of the total NFS
             calls received, since the last time the
             statistics were cleared."
    ::= { v3Percent 13 }

v3pRmdirs OBJECT-TYPE
    SYNTAX          Integer32 (0..100)
    MAX-ACCESS      read-only
    STATUS          current
    DESCRIPTION     
            "The number of NFS Version 3 calls received
             for the NFSPROC3_RMDIR (Remove a Directory)
             procedure, as a percentage of the total NFS
             calls received, since the last time the
             statistics were cleared."
    ::= { v3Percent 14 }

v3pRenames OBJECT-TYPE
    SYNTAX          Integer32 (0..100)
    MAX-ACCESS      read-only
    STATUS          current
    DESCRIPTION     
            "The number of NFS Version 3 calls received
             for the NFSPROC3_RENAME (Rename a File or
             Directory) procedure, as a percentage of
             the total NFS calls received, since the
             last time the statistics were cleared."
    ::= { v3Percent 15 }

v3pLinks OBJECT-TYPE
    SYNTAX          Integer32 (0..100)
    MAX-ACCESS      read-only
    STATUS          current
    DESCRIPTION     
            "The number of NFS Version 3 calls received
             for the NFSPROC3_LINK (Create Link to an
             Object) procedure, as a percentage of
             the total NFS calls received, since the
             last time the statistics were cleared."
    ::= { v3Percent 16 }

v3pReaddirs OBJECT-TYPE
    SYNTAX          Integer32 (0..100)
    MAX-ACCESS      read-only
    STATUS          current
    DESCRIPTION     
            "The number of NFS Version 3 calls received
             for the NFSPROC3_READDIR (Read From Directory)
             procedure, as a percentage of the total NFS
             calls received, since the last time the
             statistics were cleared."
    ::= { v3Percent 17 }

v3pReaddirPluss OBJECT-TYPE
    SYNTAX          Integer32 (0..100)
    MAX-ACCESS      read-only
    STATUS          current
    DESCRIPTION     
            "The number of NFS Version 3 calls received
             for the NFSPROC3_READDIRPLUS (Extended Read
             from Directory) procedure, as a percentage
             of the total NFS calls received, since the
             last time the statistics were cleared."
    ::= { v3Percent 18 }

v3pFsstats OBJECT-TYPE
    SYNTAX          Integer32 (0..100)
    MAX-ACCESS      read-only
    STATUS          current
    DESCRIPTION     
            "The number of NFS Version 3 calls received
             for the NFSPROC3_FSSTAT (Get Dynamic File
             System Information) procedure, as a percentage
             of the total NFS calls received, since the
             last time the statistics were cleared."
    ::= { v3Percent 19 }

v3pFsinfos OBJECT-TYPE
    SYNTAX          Integer32 (0..100)
    MAX-ACCESS      read-only
    STATUS          current
    DESCRIPTION     
            "The number of NFS Version 3 calls received
             for the NFSPROC3_FSINFO (Get Static File System
             Information) procedure, as a percentage of the
             total NFS calls received, since the last time
             the statistics were cleared."
    ::= { v3Percent 20 }

v3pPathconfs OBJECT-TYPE
    SYNTAX          Integer32 (0..100)
    MAX-ACCESS      read-only
    STATUS          current
    DESCRIPTION     
            "The number of NFS Version 3 calls received
             for the NFSPROC3_PATHCONF (Retrieve POSIX
             Information) procedure, as a percentage of the
             total NFS calls received, since the last time
             the statistics were cleared."
    ::= { v3Percent 21 }

v3pCommits OBJECT-TYPE
    SYNTAX          Integer32 (0..100)
    MAX-ACCESS      read-only
    STATUS          current
    DESCRIPTION     
            "The number of NFS Version 3 calls received
             for the NFSPROC3_COMMIT (Commit Cached Data on
             a Server to Stable Storage) procedure, as a
             percentage of the total NFS calls received,
             since the last time the statistics were cleared."
    ::= { v3Percent 22 }

v3CachedCalls OBJECT IDENTIFIER
    ::= { nfsV3 3 }

v3ccNulls OBJECT-TYPE
    SYNTAX          Counter32
    MAX-ACCESS      read-only
    STATUS          current
    DESCRIPTION     
            "The number of NFS Version 3 calls received
             for the NFSPROC3_NULL (Do Nothing) procedure,
             that did not result in the filesystem
             blocking to read from disk, since the last
             time the statistics were cleared."
    ::= { v3CachedCalls 1 }

v3ccGetattrs OBJECT-TYPE
    SYNTAX          Counter32
    MAX-ACCESS      read-only
    STATUS          current
    DESCRIPTION     
            "The number of NFS Version 3 calls received
             for the NFSPROC3_GETATTR (Get File Attributes)
             procedure, that did not result in the filesystem
             blocking to read from disk, since the last
             time the statistics were cleared."
    ::= { v3CachedCalls 2 }

v3ccSetattrs OBJECT-TYPE
    SYNTAX          Counter32
    MAX-ACCESS      read-only
    STATUS          current
    DESCRIPTION     
            "The number of NFS Version 3 calls received
             for the NFSPROC3_SETATTR (Set File Attributes)
             procedure, that did not result in the filesystem
             blocking to read from disk, since the last
             time the statistics were cleared."
    ::= { v3CachedCalls 3 }

v3ccLookups OBJECT-TYPE
    SYNTAX          Counter32
    MAX-ACCESS      read-only
    STATUS          current
    DESCRIPTION     
            "The number of NFS Version 3 calls received
             for the NFSPROC3_LOOKUP (Lookup Filename)
             procedure, that did not result in the filesystem
             blocking to read from disk, since the last
             time the statistics were cleared."
    ::= { v3CachedCalls 4 }

v3ccAccesss OBJECT-TYPE
    SYNTAX          Counter32
    MAX-ACCESS      read-only
    STATUS          current
    DESCRIPTION     
            "The number of NFS Version 3 calls received
             for the NFSPROC3_ACCESS (Check Access Permission)
             procedure, that did not result in the filesystem
             blocking to read from disk, since the last
             time the statistics were cleared."
    ::= { v3CachedCalls 5 }

v3ccReadlinks OBJECT-TYPE
    SYNTAX          Counter32
    MAX-ACCESS      read-only
    STATUS          current
    DESCRIPTION     
            "The number of NFS Version 3 calls received
             for the NFSPROC3_READLINK (Read from Symbolic
             Link) procedure, that did not result in the
             filesystem blocking to read from disk, since
             the last time the statistics were cleared."
    ::= { v3CachedCalls 6 }

v3ccReads OBJECT-TYPE
    SYNTAX          Counter32
    MAX-ACCESS      read-only
    STATUS          current
    DESCRIPTION     
            "The number of NFS Version 3 calls received
             for the NFSPROC3_READ (Read From File)
             procedure, that did not result in the filesystem
             blocking to read from disk, since the last
             time the statistics were cleared."
    ::= { v3CachedCalls 7 }

v3ccWrites OBJECT-TYPE
    SYNTAX          Counter32
    MAX-ACCESS      read-only
    STATUS          current
    DESCRIPTION     
            "The number of NFS Version 3 calls received
             for the NFSPROC3_WRITE (Write to File)
             procedure, that did not result in the filesystem
             blocking to read from disk, since the last
             time the statistics were cleared."
    ::= { v3CachedCalls 8 }

v3ccCreates OBJECT-TYPE
    SYNTAX          Counter32
    MAX-ACCESS      read-only
    STATUS          current
    DESCRIPTION     
            "The number of NFS Version 3 calls received
             for the NFSPROC3_CREATE (Create a File)
             procedure, that did not result in the filesystem
             blocking to read from disk, since the last
             time the statistics were cleared."
    ::= { v3CachedCalls 9 }

v3ccMkdirs OBJECT-TYPE
    SYNTAX          Counter32
    MAX-ACCESS      read-only
    STATUS          current
    DESCRIPTION     
            "The number of NFS Version 3 calls received
             for the NFSPROC3_MKDIR (Create a Directory)
             procedure, that did not result in the filesystem
             blocking to read from disk, since the last
             time the statistics were cleared."
    ::= { v3CachedCalls 10 }

v3ccSymlinks OBJECT-TYPE
    SYNTAX          Counter32
    MAX-ACCESS      read-only
    STATUS          current
    DESCRIPTION     
            "The number of NFS Version 3 calls received
             for the NFSPROC3_SYMLINK (Create a Symbolic
             Link) procedure, that did not result in the
             filesystem blocking to read from disk, since
             the last time the statistics were cleared."
    ::= { v3CachedCalls 11 }

v3ccMknods OBJECT-TYPE
    SYNTAX          Counter32
    MAX-ACCESS      read-only
    STATUS          current
    DESCRIPTION     
            "The number of NFS Version 3 calls received
             for the NFSPROC3_MKNOD (Create a Special
             Device) procedure, that did not result in the
             filesystem blocking to read from disk, since
             the last time the statistics were cleared."
    ::= { v3CachedCalls 12 }

v3ccRemoves OBJECT-TYPE
    SYNTAX          Counter32
    MAX-ACCESS      read-only
    STATUS          current
    DESCRIPTION     
            "The number of NFS Version 3 calls received
             for the NFSPROC3_REMOVE (Remove a File)
             procedure, that did not result in the
             filesystem blocking to read from disk, since
             the last time the statistics were cleared."
    ::= { v3CachedCalls 13 }

v3ccRmdirs OBJECT-TYPE
    SYNTAX          Counter32
    MAX-ACCESS      read-only
    STATUS          current
    DESCRIPTION     
            "The number of NFS Version 3 calls received
             for the NFSPROC3_RMDIR (Remove a Directory)
             procedure, that did not result in the
             filesystem blocking to read from disk, since
             the last time the statistics were cleared."
    ::= { v3CachedCalls 14 }

v3ccRenames OBJECT-TYPE
    SYNTAX          Counter32
    MAX-ACCESS      read-only
    STATUS          current
    DESCRIPTION     
            "The number of NFS Version 3 calls received
             for the NFSPROC3_RENAME (Rename a File or
             Directory) procedure, that did not result in
             the filesystem blocking to read from disk, since
             the last time the statistics were cleared."
    ::= { v3CachedCalls 15 }

v3ccLinks OBJECT-TYPE
    SYNTAX          Counter32
    MAX-ACCESS      read-only
    STATUS          current
    DESCRIPTION     
            "The number of NFS Version 3 calls received
             for the NFSPROC3_LINK (Create Link to an
             Object) procedure, that did not result in
             the filesystem blocking to read from disk, since
             the last time the statistics were cleared."
    ::= { v3CachedCalls 16 }

v3ccReaddirs OBJECT-TYPE
    SYNTAX          Counter32
    MAX-ACCESS      read-only
    STATUS          current
    DESCRIPTION     
            "The number of NFS Version 3 calls received
             for the NFSPROC3_READDIR (Read From
             Directory) procedure, that did not result in
             the filesystem blocking to read from disk, since
             the last time the statistics were cleared."
    ::= { v3CachedCalls 17 }

v3ccReaddirPluss OBJECT-TYPE
    SYNTAX          Counter32
    MAX-ACCESS      read-only
    STATUS          current
    DESCRIPTION     
            "The number of NFS Version 3 calls received
             for the NFSPROC3_READDIRPLUS (Extended Read
             from Directory) procedure, that did not result in
             the filesystem blocking to read from disk, since
             the last time the statistics were cleared."
    ::= { v3CachedCalls 18 }

v3ccFsstats OBJECT-TYPE
    SYNTAX          Counter32
    MAX-ACCESS      read-only
    STATUS          current
    DESCRIPTION     
            "The number of NFS Version 3 calls received
             for the NFSPROC3_FSSTAT (Get Dynamic File
             System Information) procedure, that did not
             result in the filesystem blocking to read
             from disk, since the last time the statistics
             were cleared."
    ::= { v3CachedCalls 19 }

v3ccFsinfos OBJECT-TYPE
    SYNTAX          Counter32
    MAX-ACCESS      read-only
    STATUS          current
    DESCRIPTION     
            "The number of NFS Version 3 calls received
             for the NFSPROC3_FSINFO (Get Static File
             System Information) procedure, that did not
             result in the filesystem blocking to read
             from disk, since the last time the statistics
             were cleared."
    ::= { v3CachedCalls 20 }

v3ccPathconfs OBJECT-TYPE
    SYNTAX          Counter32
    MAX-ACCESS      read-only
    STATUS          current
    DESCRIPTION     
            "The number of NFS Version 3 calls received
             for the NFSPROC3_PATHCONF (Retrieve POSIX
             Information) procedure, that did not result
             in the filesystem blocking to read from disk,
             since the last time the statistics were cleared."
    ::= { v3CachedCalls 21 }

v3ccCommits OBJECT-TYPE
    SYNTAX          Counter32
    MAX-ACCESS      read-only
    STATUS          current
    DESCRIPTION     
            "The number of NFS Version 3 calls received
             for the NFSPROC3_COMMIT (Commit Cached Data on
             a Server to Stable Storage) procedure, that did
             not result in the filesystem blocking to read
             from disk, since the last time the statistics
             were cleared."
    ::= { v3CachedCalls 22 }

v3CachedPerCent OBJECT IDENTIFIER
    ::= { nfsV3 4 }

v3cpNulls OBJECT-TYPE
    SYNTAX          Integer32 (0..100)
    MAX-ACCESS      read-only
    STATUS          current
    DESCRIPTION     
            "The number of NFS Version 3 calls received
             for the NFSPROC3_NULL (Do Nothing) procedure,
             that did not result in the filesystem
             blocking to read from disk, as a percentage
             of the total number of calls received for
             this procedure, since the last time the
             statistics were cleared."
    ::= { v3CachedPerCent 1 }

v3cpGetattrs OBJECT-TYPE
    SYNTAX          Integer32 (0..100)
    MAX-ACCESS      read-only
    STATUS          current
    DESCRIPTION     
            "The number of NFS Version 3 calls received
             for the NFSPROC3_GETATTR (Get File Attributes)
             procedure, that did not result in the filesystem
             blocking to read from disk, as a percentage
             of the total number of calls received for
             this procedure, since the last time the
             statistics were cleared."
    ::= { v3CachedPerCent 2 }

v3cpSetattrs OBJECT-TYPE
    SYNTAX          Integer32 (0..100)
    MAX-ACCESS      read-only
    STATUS          current
    DESCRIPTION     
            "The number of NFS Version 3 calls received
             for the NFSPROC3_SETATTR (Set File Attributes)
             procedure, that did not result in the filesystem
             blocking to read from disk, as a percentage
             of the total number of calls received for
             this procedure, since the last time the
             statistics were cleared."
    ::= { v3CachedPerCent 3 }

v3cpLookups OBJECT-TYPE
    SYNTAX          Integer32 (0..100)
    MAX-ACCESS      read-only
    STATUS          current
    DESCRIPTION     
            "The number of NFS Version 3 calls received
             for the NFSPROC3_LOOKUP (Lookup Filename)
             procedure, that did not result in the filesystem
             blocking to read from disk, as a percentage
             of the total number of calls received for
             this procedure, since the last time the
             statistics were cleared."
    ::= { v3CachedPerCent 4 }

v3cpAccesss OBJECT-TYPE
    SYNTAX          Integer32 (0..100)
    MAX-ACCESS      read-only
    STATUS          current
    DESCRIPTION     
            "The number of NFS Version 3 calls received
             for the NFSPROC3_ACCESS (Check Access Permission)
             procedure, that did not result in the filesystem
             blocking to read from disk, as a percentage
             of the total number of calls received for
             this procedure, since the last time the
             statistics were cleared."
    ::= { v3CachedPerCent 5 }

v3cpReadlinks OBJECT-TYPE
    SYNTAX          Integer32 (0..100)
    MAX-ACCESS      read-only
    STATUS          current
    DESCRIPTION     
            "The number of NFS Version 3 calls received
             for the NFSPROC3_READLINK (Read from Symbolic
             Link) procedure, that did not result in the
             filesystem blocking to read from disk, as a
             percentage of the total number of calls
             received for this procedure, since the last
             time the statistics were cleared."
    ::= { v3CachedPerCent 6 }

v3cpReads OBJECT-TYPE
    SYNTAX          Integer32 (0..100)
    MAX-ACCESS      read-only
    STATUS          current
    DESCRIPTION     
            "The number of NFS Version 3 calls received
             for the NFSPROC3_READ (Read From File)
             procedure, that did not result in the
             filesystem blocking to read from disk, as a
             percentage of the total number of calls
             received for this procedure, since the last
             time the statistics were cleared."
    ::= { v3CachedPerCent 7 }

v3cpWrites OBJECT-TYPE
    SYNTAX          Integer32 (0..100)
    MAX-ACCESS      read-only
    STATUS          current
    DESCRIPTION     
            "The number of NFS Version 3 calls received
             for the NFSPROC3_WRITE (Write to File)
             procedure, that did not result in the
             filesystem blocking to read from disk, as a
             percentage of the total number of calls
             received for this procedure, since the last
             time the statistics were cleared."
    ::= { v3CachedPerCent 8 }

v3cpCreates OBJECT-TYPE
    SYNTAX          Integer32 (0..100)
    MAX-ACCESS      read-only
    STATUS          current
    DESCRIPTION     
            "The number of NFS Version 3 calls received
             for the NFSPROC3_CREATE (Create a File)
             procedure, that did not result in the
             filesystem blocking to read from disk, as a
             percentage of the total number of calls
             received for this procedure, since the last
             time the statistics were cleared."
    ::= { v3CachedPerCent 9 }

v3cpMkdirs OBJECT-TYPE
    SYNTAX          Integer32 (0..100)
    MAX-ACCESS      read-only
    STATUS          current
    DESCRIPTION     
            "The number of NFS Version 3 calls received
             for the NFSPROC3_MKDIR (Create a Directory)
             procedure, that did not result in the
             filesystem blocking to read from disk, as a
             percentage of the total number of calls
             received for this procedure, since the last
             time the statistics were cleared."
    ::= { v3CachedPerCent 10 }

v3cpSymlinks OBJECT-TYPE
    SYNTAX          Integer32 (0..100)
    MAX-ACCESS      read-only
    STATUS          current
    DESCRIPTION     
            "The number of NFS Version 3 calls received
             for the NFSPROC3_SYMLINK (Create a Symbolic
             Link) procedure, that did not result in the
             filesystem blocking to read from disk, as a
             percentage of the total number of calls
             received for this procedure, since the last
             time the statistics were cleared."
    ::= { v3CachedPerCent 11 }

v3cpMknods OBJECT-TYPE
    SYNTAX          Integer32 (0..100)
    MAX-ACCESS      read-only
    STATUS          current
    DESCRIPTION     
            "The number of NFS Version 3 calls received
             for the NFSPROC3_MKNOD (Create a Special
             Device) procedure, that did not result in the
             filesystem blocking to read from disk, as a
             percentage of the total number of calls
             received for this procedure, since the last
             time the statistics were cleared."
    ::= { v3CachedPerCent 12 }

v3cpRemoves OBJECT-TYPE
    SYNTAX          Integer32 (0..100)
    MAX-ACCESS      read-only
    STATUS          current
    DESCRIPTION     
            "The number of NFS Version 3 calls received
             for the NFSPROC3_REMOVE (Remove a File)
             procedure, that did not result in the
             filesystem blocking to read from disk, as a
             percentage of the total number of calls
             received for this procedure, since the last
             time the statistics were cleared."
    ::= { v3CachedPerCent 13 }

v3cpRmdirs OBJECT-TYPE
    SYNTAX          Integer32 (0..100)
    MAX-ACCESS      read-only
    STATUS          current
    DESCRIPTION     
            "The number of NFS Version 3 calls received
             for the NFSPROC3_RMDIR (Remove a Directory)
             procedure, that did not result in the
             filesystem blocking to read from disk, as a
             percentage of the total number of calls
             received for this procedure, since the last
             time the statistics were cleared."
    ::= { v3CachedPerCent 14 }

v3cpRenames OBJECT-TYPE
    SYNTAX          Integer32 (0..100)
    MAX-ACCESS      read-only
    STATUS          current
    DESCRIPTION     
            "The number of NFS Version 3 calls received
             for the NFSPROC3_RENAME (Rename a File or
             Directory) procedure, that did not result in
             the filesystem blocking to read from disk,
             as a percentage of the total number of calls
             received for this procedure, since the last
             time the statistics were cleared."
    ::= { v3CachedPerCent 15 }

v3cpLinks OBJECT-TYPE
    SYNTAX          Integer32 (0..100)
    MAX-ACCESS      read-only
    STATUS          current
    DESCRIPTION     
            "The number of NFS Version 3 calls received
             for the NFSPROC3_LINK (Create Link to an
             Object) procedure, that did not result in
             the filesystem blocking to read from disk,
             as a percentage of the total number of calls
             received for this procedure, since the last
             time the statistics were cleared."
    ::= { v3CachedPerCent 16 }

v3cpReaddirs OBJECT-TYPE
    SYNTAX          Integer32 (0..100)
    MAX-ACCESS      read-only
    STATUS          current
    DESCRIPTION     
            "The number of NFS Version 3 calls received
             for the NFSPROC3_READDIR (Read From Directory)
             procedure, that did not result in the
             filesystem blocking to read from disk, as a
             percentage of the total number of calls
             received for this procedure, since the last
             time the statistics were cleared."
    ::= { v3CachedPerCent 17 }

v3cpReaddirPluss OBJECT-TYPE
    SYNTAX          Integer32 (0..100)
    MAX-ACCESS      read-only
    STATUS          current
    DESCRIPTION     
            "The number of NFS Version 3 calls received
             for the NFSPROC3_READDIRPLUS (Extended Read
             from Directory) procedure, that did not result
             in the filesystem blocking to read from disk,
             as a percentage of the total number of calls
             received for this procedure, since the last
             time the statistics were cleared."
    ::= { v3CachedPerCent 18 }

v3cpFsstats OBJECT-TYPE
    SYNTAX          Integer32 (0..100)
    MAX-ACCESS      read-only
    STATUS          current
    DESCRIPTION     
            "The number of NFS Version 3 calls received
             for the NFSPROC3_FSSTAT (Get Dynamic File
             System Information) procedure, that did not
             result in the filesystem blocking to read from
             disk, as a percentage of the total number of
             calls received for this procedure, since the
             last time the statistics were cleared."
    ::= { v3CachedPerCent 19 }

v3cpFsinfos OBJECT-TYPE
    SYNTAX          Integer32 (0..100)
    MAX-ACCESS      read-only
    STATUS          current
    DESCRIPTION     
            "The number of NFS Version 3 calls received
             for the NFSPROC3_FSINFO (Get Static File System
             Information) procedure, that did not result
             in the filesystem blocking to read from disk,
             as a percentage of the total number of calls
             received for this procedure, since the last
             time the statistics were cleared."
    ::= { v3CachedPerCent 20 }

v3cpPathconfs OBJECT-TYPE
    SYNTAX          Integer32 (0..100)
    MAX-ACCESS      read-only
    STATUS          current
    DESCRIPTION     
            "The number of NFS Version 3 calls received
             for the NFSPROC3_PATHCONF (Retrieve POSIX
             Information) procedure, that did not result
             in the filesystem blocking to read from disk,
             as a percentage of the total number of calls
             received for this procedure, since the last
             time the statistics were cleared."
    ::= { v3CachedPerCent 21 }

v3cpCommits OBJECT-TYPE
    SYNTAX          Integer32 (0..100)
    MAX-ACCESS      read-only
    STATUS          current
    DESCRIPTION     
            "The number of NFS Version 3 calls received
             for the NFSPROC3_COMMIT (Commit Cached Data on
             a Server to Stable Storage) procedure, that
             did not result in the filesystem blocking to
             read from disk, as a percentage of the total
             number of calls received for this procedure,
             since the last time the statistics were cleared."
    ::= { v3CachedPerCent 22 }

replyCache OBJECT IDENTIFIER
    ::= { nfsServ 5 }

rcInProgressHits OBJECT-TYPE
    SYNTAX          Counter32
    MAX-ACCESS      read-only
    STATUS          current
    DESCRIPTION     
            "The number of NFS requests that were dropped,
             for calls already in progress, since the last
             time the statistics were cleared."
    ::= { replyCache 1 }

rcDelayHits OBJECT-TYPE
    SYNTAX          Counter32
    MAX-ACCESS      read-only
    STATUS          current
    DESCRIPTION     
            "The number of NFS requests that were dropped,
             for replies already generated within a short
             interval, since the last time the statistics
             were cleared."
    ::= { replyCache 2 }

rcMisses OBJECT-TYPE
    SYNTAX          Counter32
    MAX-ACCESS      read-only
    STATUS          current
    DESCRIPTION     
            "The number of NFS requests received for which
             there were no corresponding entries already in
             the Reply Cache, since the last time the
             statistics were cleared."
    ::= { replyCache 3 }

rcNonIdemDoneHits OBJECT-TYPE
    SYNTAX          Counter32
    MAX-ACCESS      read-only
    STATUS          current
    DESCRIPTION     
            "The number of NFS requests received that
             resulted in replies being replayed from
             the Reply Cache, since the last time the
             statistics were cleared."
    ::= { replyCache 4 }

rcNonIdemNotDoneHits OBJECT-TYPE
    SYNTAX          Counter32
    MAX-ACCESS      read-only
    STATUS          current
    DESCRIPTION     
            "The number of NFS requests received for calls
             that resulted in this request being processed
             as a new request even when a corresponding
             entry existed in the Reply Cache, since the
             last time the statistics were cleared."
    ::= { replyCache 5 }

nfsPerClient OBJECT IDENTIFIER
    ::= { curNfs 3 }

pclTable OBJECT-TYPE
    SYNTAX          SEQUENCE OF PclEntry
    MAX-ACCESS      not-accessible
    STATUS          current
    DESCRIPTION     
            "Provide a report of per-client NFS statistics
             since the last time the statistics were cleared."
    ::= { nfsPerClient 1 }

pclEntry OBJECT-TYPE
    SYNTAX          PclEntry
    MAX-ACCESS      not-accessible
    STATUS          current
    DESCRIPTION     
            "Provide a report of NFS statistics for the
             referenced NFS client since the last time the
             statistics were cleared."
    INDEX           { pclIpAddr }
    ::= { pclTable 1 }

PclEntry ::=
    SEQUENCE {
        pclIpAddr                       IpAddress,
        pclRpcCalls                     Counter32,
        pclRpcBadCalls                  Counter32,
        pclRpcNullRecvs                 Counter32,
        pclRpcBadLens                   Counter32,
        pclRpcServXDRCalls              Counter32,
        pclNfsCalls                     Counter32,
        pclNfsServBadCalls              Counter32,
        pclNfsV2Nulls                   Counter32,
        pclNfsV2Getattrs                Counter32,
        pclNfsV2Setattrs                Counter32,
        pclNfsV2Roots                   Counter32,
        pclNfsV2Lookups                 Counter32,
        pclNfsV2Readlinks               Counter32,
        pclNfsV2Reads                   Counter32,
        pclNfsV2Wrcaches                Counter32,
        pclNfsV2Writes                  Counter32,
        pclNfsV2Creates                 Counter32,
        pclNfsV2Removes                 Counter32,
        pclNfsV2Renames                 Counter32,
        pclNfsV2Links                   Counter32,
        pclNfsV2Symlinks                Counter32,
        pclNfsV2Mkdirs                  Counter32,
        pclNfsV2Rmdirs                  Counter32,
        pclNfsV2Readdirs                Counter32,
        pclNfsV2Statfss                 Counter32,
        pclNfsV3Nulls                   Counter32,
        pclNfsV3Getattrs                Counter32,
        pclNfsV3Setattrs                Counter32,
        pclNfsV3Lookups                 Counter32,
        pclNfsV3Accesss                 Counter32,
        pclNfsV3Readlinks               Counter32,
        pclNfsV3Reads                   Counter32,
        pclNfsV3Writes                  Counter32,
        pclNfsV3Creates                 Counter32,
        pclNfsV3Mkdirs                  Counter32,
        pclNfsV3Symlinks                Counter32,
        pclNfsV3Mknods                  Counter32,
        pclNfsV3Removes                 Counter32,
        pclNfsV3Rmdirs                  Counter32,
        pclNfsV3Renames                 Counter32,
        pclNfsV3Links                   Counter32,
        pclNfsV3Readdirs                Counter32,
        pclNfsV3ReaddirPluss            Counter32,
        pclNfsV3Fsstats                 Counter32,
        pclNfsV3Fsinfos                 Counter32,
        pclNfsV3Pathconfs               Counter32,
        pclNfsV3Commits                 Counter32,
        pclPerCent                      Integer32,
        pclNfsV2NullPerCent             Integer32,
        pclNfsV2GetattrPerCent          Integer32,
        pclNfsV2SetattrPerCent          Integer32,
        pclNfsV2RootPerCent             Integer32,
        pclNfsV2LookupPerCent           Integer32,
        pclNfsV2ReadlinkPerCent         Integer32,
        pclNfsV2ReadPerCent             Integer32,
        pclNfsV2WrcachePerCent          Integer32,
        pclNfsV2WritePerCent            Integer32,
        pclNfsV2CreatePerCent           Integer32,
        pclNfsV2RemovePerCent           Integer32,
        pclNfsV2RenamePerCent           Integer32,
        pclNfsV2LinkPerCent             Integer32,
        pclNfsV2SymlinkPerCent          Integer32,
        pclNfsV2MkdirPerCent            Integer32,
        pclNfsV2RmdirPerCent            Integer32,
        pclNfsV2ReaddirPerCent          Integer32,
        pclNfsV2StatfsPerCent           Integer32,
        pclNfsV3NullPerCent             Integer32,
        pclNfsV3GetattrPerCent          Integer32,
        pclNfsV3SetattrPerCent          Integer32,
        pclNfsV3LookupPerCent           Integer32,
        pclNfsV3AccessPerCent           Integer32,
        pclNfsV3ReadlinkPerCent         Integer32,
        pclNfsV3ReadPerCent             Integer32,
        pclNfsV3WritePerCent            Integer32,
        pclNfsV3CreatePerCent           Integer32,
        pclNfsV3MkdirPerCent            Integer32,
        pclNfsV3SymlinkPerCent          Integer32,
        pclNfsV3MknodPerCent            Integer32,
        pclNfsV3RemovePerCent           Integer32,
        pclNfsV3RmdirPerCent            Integer32,
        pclNfsV3RenamePerCent           Integer32,
        pclNfsV3LinkPerCent             Integer32,
        pclNfsV3ReaddirPerCent          Integer32,
        pclNfsV3ReaddirPlusPerCent      Integer32,
        pclNfsV3FsstatPerCent           Integer32,
        pclNfsV3FsinfoPerCent           Integer32,
        pclNfsV3PathconfPerCent         Integer32,
        pclNfsV3CommitPerCent           Integer32
    }

pclIpAddr OBJECT-TYPE
    SYNTAX          IpAddress
    MAX-ACCESS      read-only
    STATUS          current
    DESCRIPTION     
            "The IP address of the referenced client."
    ::= { pclEntry 1 }

pclRpcCalls OBJECT-TYPE
    SYNTAX          Counter32
    MAX-ACCESS      read-only
    STATUS          current
    DESCRIPTION     
            "The total number of RPC calls received from
             the referenced client, since the last time the
             statistics were cleared."
    ::= { pclEntry 2 }

pclRpcBadCalls OBJECT-TYPE
    SYNTAX          Counter32
    MAX-ACCESS      read-only
    STATUS          current
    DESCRIPTION     
            "The total number of calls received from the
             referenced client that were rejected by the
             RPC layer, since the last time the
             statistics were cleared."
    ::= { pclEntry 3 }

pclRpcNullRecvs OBJECT-TYPE
    SYNTAX          Counter32
    MAX-ACCESS      read-only
    STATUS          current
    DESCRIPTION     
            "The number of times an RPC call was not available
             when it was thought to be received from
             referenced client, since the last time the
             statistics were cleared."
    ::= { pclEntry 4 }

pclRpcBadLens OBJECT-TYPE
    SYNTAX          Counter32
    MAX-ACCESS      read-only
    STATUS          current
    DESCRIPTION     
            "The number of RPC calls received from the
             referenced client with a length shorter
             than a minimum-sized RPC call, since the
             last time the statistics were cleared."
    ::= { pclEntry 5 }

pclRpcServXDRCalls OBJECT-TYPE
    SYNTAX          Counter32
    MAX-ACCESS      read-only
    STATUS          current
    DESCRIPTION     
            "The number of RPC calls received from the
             referenced client whose header could not
             be XDR decoded, since the last time the
             statistics were cleared."
    ::= { pclEntry 6 }

pclNfsCalls OBJECT-TYPE
    SYNTAX          Counter32
    MAX-ACCESS      read-only
    STATUS          current
    DESCRIPTION     
            "The total number of NFS calls received from
             the referenced client, since the last time
             the statistics were cleared."
    ::= { pclEntry 7 }

pclNfsServBadCalls OBJECT-TYPE
    SYNTAX          Counter32
    MAX-ACCESS      read-only
    STATUS          current
    DESCRIPTION     
            "The total number of NFS calls received from
             the referenced client that were rejected, since
             the last time the statistics were cleared."
    ::= { pclEntry 8 }

pclNfsV2Nulls OBJECT-TYPE
    SYNTAX          Counter32
    MAX-ACCESS      read-only
    STATUS          current
    DESCRIPTION     
            "The number of NFS Version 2 calls received
             from the referenced client for the NFSPROC_NULL
             (Do Nothing) procedure, since the last time the
             statistics were cleared."
    ::= { pclEntry 9 }

pclNfsV2Getattrs OBJECT-TYPE
    SYNTAX          Counter32
    MAX-ACCESS      read-only
    STATUS          current
    DESCRIPTION     
            "The number of NFS Version 2 calls received
             from the referenced client for the NFSPROC_GETATTR
             (Get File Attributes) procedure, since the last
             time the statistics were cleared."
    ::= { pclEntry 10 }

pclNfsV2Setattrs OBJECT-TYPE
    SYNTAX          Counter32
    MAX-ACCESS      read-only
    STATUS          current
    DESCRIPTION     
            "The number of NFS Version 2 calls received
             from the referenced client for the NFSPROC_SETATTR
             (Set File Attributes) procedure, since the last
             time the statistics were cleared."
    ::= { pclEntry 11 }

pclNfsV2Roots OBJECT-TYPE
    SYNTAX          Counter32
    MAX-ACCESS      read-only
    STATUS          current
    DESCRIPTION     
            "The number of NFS Version 2 calls received
             from the referenced client for the NFSPROC_ROOT
             (Get Filesystem Root) procedure, since the last
             time the statistics were cleared."
    ::= { pclEntry 12 }

pclNfsV2Lookups OBJECT-TYPE
    SYNTAX          Counter32
    MAX-ACCESS      read-only
    STATUS          current
    DESCRIPTION     
            "The number of NFS Version 2 calls received
             from the referenced client for the NFSPROC_LOOKUP
             (Look Up File Name) procedure, since the last
             time the statistics were cleared."
    ::= { pclEntry 13 }

pclNfsV2Readlinks OBJECT-TYPE
    SYNTAX          Counter32
    MAX-ACCESS      read-only
    STATUS          current
    DESCRIPTION     
            "The number of NFS Version 2 calls received
             from the referenced client for the NFSPROC_READLINK
             (Read From Symbolic Link) procedure, since the last
             time the statistics were cleared."
    ::= { pclEntry 14 }

pclNfsV2Reads OBJECT-TYPE
    SYNTAX          Counter32
    MAX-ACCESS      read-only
    STATUS          current
    DESCRIPTION     
            "The number of NFS Version 2 calls received
             from the referenced client for the NFSPROC_READ
             (Read From File) procedure, since the last
             time the statistics were cleared."
    ::= { pclEntry 15 }

pclNfsV2Wrcaches OBJECT-TYPE
    SYNTAX          Counter32
    MAX-ACCESS      read-only
    STATUS          current
    DESCRIPTION     
            "The number of NFS Version 2 calls received
             from the referenced client for the NFSPROC_WRITECACHE
             (Write to Cache) procedure, since the last
             time the statistics were cleared."
    ::= { pclEntry 16 }

pclNfsV2Writes OBJECT-TYPE
    SYNTAX          Counter32
    MAX-ACCESS      read-only
    STATUS          current
    DESCRIPTION     
            "The number of NFS Version 2 calls received
             from the referenced client for the NFSPROC_WRITE
             (Write to File) procedure, since the last
             time the statistics were cleared."
    ::= { pclEntry 17 }

pclNfsV2Creates OBJECT-TYPE
    SYNTAX          Counter32
    MAX-ACCESS      read-only
    STATUS          current
    DESCRIPTION     
            "The number of NFS Version 2 calls received
             from the referenced client for the NFSPROC_CREATE
             (Create File) procedure, since the last
             time the statistics were cleared."
    ::= { pclEntry 18 }

pclNfsV2Removes OBJECT-TYPE
    SYNTAX          Counter32
    MAX-ACCESS      read-only
    STATUS          current
    DESCRIPTION     
            "The number of NFS Version 2 calls received
             from the referenced client for the NFSPROC_REMOVE
             (Remove File) procedure, since the last
             time the statistics were cleared."
    ::= { pclEntry 19 }

pclNfsV2Renames OBJECT-TYPE
    SYNTAX          Counter32
    MAX-ACCESS      read-only
    STATUS          current
    DESCRIPTION     
            "The number of NFS Version 2 calls received
             from the referenced client for the NFSPROC_RENAME
             (Rename File) procedure, since the last
             time the statistics were cleared."
    ::= { pclEntry 20 }

pclNfsV2Links OBJECT-TYPE
    SYNTAX          Counter32
    MAX-ACCESS      read-only
    STATUS          current
    DESCRIPTION     
            "The number of NFS Version 2 calls received
             from the referenced client for the NFSPROC_LINK
             (Create Link to File) procedure, since the last
             time the statistics were cleared."
    ::= { pclEntry 21 }

pclNfsV2Symlinks OBJECT-TYPE
    SYNTAX          Counter32
    MAX-ACCESS      read-only
    STATUS          current
    DESCRIPTION     
            "The number of NFS Version 2 calls received
             from the referenced client for the NFSPROC_SYMLINK
             (Create Symbolic Link) procedure, since the last
             time the statistics were cleared."
    ::= { pclEntry 22 }

pclNfsV2Mkdirs OBJECT-TYPE
    SYNTAX          Counter32
    MAX-ACCESS      read-only
    STATUS          current
    DESCRIPTION     
            "The number of NFS Version 2 calls received
             from the referenced client for the NFSPROC_MKDIR
             (Create Directory) procedure, since the last
             time the statistics were cleared."
    ::= { pclEntry 23 }

pclNfsV2Rmdirs OBJECT-TYPE
    SYNTAX          Counter32
    MAX-ACCESS      read-only
    STATUS          current
    DESCRIPTION     
            "The number of NFS Version 2 calls received
             from the referenced client for the NFSPROC_RMDIR
             (Remove Directory) procedure, since the last
             time the statistics were cleared."
    ::= { pclEntry 24 }

pclNfsV2Readdirs OBJECT-TYPE
    SYNTAX          Counter32
    MAX-ACCESS      read-only
    STATUS          current
    DESCRIPTION     
            "The number of NFS Version 2 calls received
             from the referenced client for the NFSPROC_READDIR
             (Read From Directory) procedure, since the last
             time the statistics were cleared."
    ::= { pclEntry 25 }

pclNfsV2Statfss OBJECT-TYPE
    SYNTAX          Counter32
    MAX-ACCESS      read-only
    STATUS          current
    DESCRIPTION     
            "The number of NFS Version 2 calls received
             from the referenced client for the NFSPROC_STATFS
             (Get Filesystem Attributes) procedure, since the
             last time the statistics were cleared."
    ::= { pclEntry 26 }

pclNfsV3Nulls OBJECT-TYPE
    SYNTAX          Counter32
    MAX-ACCESS      read-only
    STATUS          current
    DESCRIPTION     
            "The number of NFS Version 3 calls received
             from the referenced client for the NFSPROC3_NULL
             (Do Nothing) procedure, since the last time the
             statistics were cleared."
    ::= { pclEntry 27 }

pclNfsV3Getattrs OBJECT-TYPE
    SYNTAX          Counter32
    MAX-ACCESS      read-only
    STATUS          current
    DESCRIPTION     
            "The number of NFS Version 3 calls received
             from the referenced client for the NFSPROC3_GETATTR
             (Get File Attributes) procedure, since the last
             time the statistics were cleared."
    ::= { pclEntry 28 }

pclNfsV3Setattrs OBJECT-TYPE
    SYNTAX          Counter32
    MAX-ACCESS      read-only
    STATUS          current
    DESCRIPTION     
            "The number of NFS Version 3 calls received
             from the referenced client for the NFSPROC3_SETATTR
             (Set File Attributes) procedure, since the last
             time the statistics were cleared."
    ::= { pclEntry 29 }

pclNfsV3Lookups OBJECT-TYPE
    SYNTAX          Counter32
    MAX-ACCESS      read-only
    STATUS          current
    DESCRIPTION     
            "The number of NFS Version 3 calls received
             from the referenced client for the NFSPROC3_LOOKUP
             (Lookup Filename) procedure, since the last time
             the statistics were cleared."
    ::= { pclEntry 30 }

pclNfsV3Accesss OBJECT-TYPE
    SYNTAX          Counter32
    MAX-ACCESS      read-only
    STATUS          current
    DESCRIPTION     
            "The number of NFS Version 3 calls received
             from the referenced client for the NFSPROC3_ACCESS
             (Check Access Permission) procedure, since the
             last time the statistics were cleared."
    ::= { pclEntry 31 }

pclNfsV3Readlinks OBJECT-TYPE
    SYNTAX          Counter32
    MAX-ACCESS      read-only
    STATUS          current
    DESCRIPTION     
            "The number of NFS Version 3 calls received
             from the referenced client for the NFSPROC3_READLINK
             (Read from Symbolic Link) procedure, since the
             last time the statistics were cleared."
    ::= { pclEntry 32 }

pclNfsV3Reads OBJECT-TYPE
    SYNTAX          Counter32
    MAX-ACCESS      read-only
    STATUS          current
    DESCRIPTION     
            "The number of NFS Version 3 calls received
             from the referenced client for the NFSPROC3_READ
             (Read From File) procedure, since the last time
             the statistics were cleared."
    ::= { pclEntry 33 }

pclNfsV3Writes OBJECT-TYPE
    SYNTAX          Counter32
    MAX-ACCESS      read-only
    STATUS          current
    DESCRIPTION     
            "The number of NFS Version 3 calls received
             from the referenced client for the NFSPROC3_WRITE
             (Write to File) procedure, since the last time
             the statistics were cleared."
    ::= { pclEntry 34 }

pclNfsV3Creates OBJECT-TYPE
    SYNTAX          Counter32
    MAX-ACCESS      read-only
    STATUS          current
    DESCRIPTION     
            "The number of NFS Version 3 calls received
             from the referenced client for the NFSPROC3_CREATE
             (Create a File) procedure, since the last time
             the statistics were cleared."
    ::= { pclEntry 35 }

pclNfsV3Mkdirs OBJECT-TYPE
    SYNTAX          Counter32
    MAX-ACCESS      read-only
    STATUS          current
    DESCRIPTION     
            "The number of NFS Version 3 calls received
             from the referenced client for the NFSPROC3_MKDIR
             (Create a Directory) procedure, since the last
             time the statistics were cleared."
    ::= { pclEntry 36 }

pclNfsV3Symlinks OBJECT-TYPE
    SYNTAX          Counter32
    MAX-ACCESS      read-only
    STATUS          current
    DESCRIPTION     
            "The number of NFS Version 3 calls received
             from the referenced client for the NFSPROC3_SYMLINK
             (Create a Symbolic Link) procedure, since the last
             time the statistics were cleared."
    ::= { pclEntry 37 }

pclNfsV3Mknods OBJECT-TYPE
    SYNTAX          Counter32
    MAX-ACCESS      read-only
    STATUS          current
    DESCRIPTION     
            "The number of NFS Version 3 calls received
             from the referenced client for the NFSPROC3_MKNOD
             (Create a Special Device) procedure, since the
             last time the statistics were cleared."
    ::= { pclEntry 38 }

pclNfsV3Removes OBJECT-TYPE
    SYNTAX          Counter32
    MAX-ACCESS      read-only
    STATUS          current
    DESCRIPTION     
            "The number of NFS Version 3 calls received
             from the referenced client for the NFSPROC3_REMOVE
             (Remove a File) procedure, since the last time
             the statistics were cleared."
    ::= { pclEntry 39 }

pclNfsV3Rmdirs OBJECT-TYPE
    SYNTAX          Counter32
    MAX-ACCESS      read-only
    STATUS          current
    DESCRIPTION     
            "The number of NFS Version 3 calls received
             from the referenced client for the NFSPROC3_RMDIR
             (Remove a Directory) procedure, since the last
             time the statistics were cleared."
    ::= { pclEntry 40 }

pclNfsV3Renames OBJECT-TYPE
    SYNTAX          Counter32
    MAX-ACCESS      read-only
    STATUS          current
    DESCRIPTION     
            "The number of NFS Version 3 calls received
             from the referenced client for the NFSPROC3_RENAME
             (Rename a File or Directory) procedure, since the
             last time the statistics were cleared."
    ::= { pclEntry 41 }

pclNfsV3Links OBJECT-TYPE
    SYNTAX          Counter32
    MAX-ACCESS      read-only
    STATUS          current
    DESCRIPTION     
            "The number of NFS Version 3 calls received
             from the referenced client for the NFSPROC3_LINK
             (Create Link to an Object) procedure, since the
             last time the statistics were cleared."
    ::= { pclEntry 42 }

pclNfsV3Readdirs OBJECT-TYPE
    SYNTAX          Counter32
    MAX-ACCESS      read-only
    STATUS          current
    DESCRIPTION     
            "The number of NFS Version 3 calls received
             from the referenced client for the NFSPROC3_READDIR
             (Read From Directory) procedure, since the last
             time the statistics were cleared."
    ::= { pclEntry 43 }

pclNfsV3ReaddirPluss OBJECT-TYPE
    SYNTAX          Counter32
    MAX-ACCESS      read-only
    STATUS          current
    DESCRIPTION     
            "The number of NFS Version 3 calls received
             from the referenced client for the
             NFSPROC3_READDIRPLUS (Extended Read from
             Directory) procedure, since the last time
             the statistics were cleared."
    ::= { pclEntry 44 }

pclNfsV3Fsstats OBJECT-TYPE
    SYNTAX          Counter32
    MAX-ACCESS      read-only
    STATUS          current
    DESCRIPTION     
            "The number of NFS Version 3 calls received
             from the referenced client for the NFSPROC3_FSSTAT
             (Get Dynamic File System Information) procedure,
             since the last time the statistics were cleared."
    ::= { pclEntry 45 }

pclNfsV3Fsinfos OBJECT-TYPE
    SYNTAX          Counter32
    MAX-ACCESS      read-only
    STATUS          current
    DESCRIPTION     
            "The number of NFS Version 3 calls received
             from the referenced client for the NFSPROC3_FSINFO
             (Get Static File System Information) procedure,
             since the last time the statistics were cleared."
    ::= { pclEntry 46 }

pclNfsV3Pathconfs OBJECT-TYPE
    SYNTAX          Counter32
    MAX-ACCESS      read-only
    STATUS          current
    DESCRIPTION     
            "The number of NFS Version 3 calls received
             from the referenced client for the NFSPROC3_PATHCONF
             (Retrieve POSIX Information) procedure, since the
             last time the statistics were cleared."
    ::= { pclEntry 47 }

pclNfsV3Commits OBJECT-TYPE
    SYNTAX          Counter32
    MAX-ACCESS      read-only
    STATUS          current
    DESCRIPTION     
            "The number of NFS Version 3 calls received
             from the referenced client for the NFSPROC3_COMMIT
             (Commit Cached Data on a Server to Stable Storage)
             procedure, since the last time the statistics were
             cleared."
    ::= { pclEntry 48 }

pclPerCent OBJECT-TYPE
    SYNTAX          Integer32 (0..100)
    MAX-ACCESS      read-only
    STATUS          current
    DESCRIPTION     
            "The number of the total NFS calls for the
             referenced client as a percentage of the
             total NFS calls received from all
             clients, since the last time the
             statistics were cleared."
    ::= { pclEntry 49 }

pclNfsV2NullPerCent OBJECT-TYPE
    SYNTAX          Integer32 (0..100)
    MAX-ACCESS      read-only
    STATUS          current
    DESCRIPTION     
            "The number of NFS Version 2 calls
             received from the referenced client for
             the NFSPROC_NULL (Do Nothing) procedure,
             as a percentage of the total calls
             received from this client, since the
             last time the statistics were cleared."
    ::= { pclEntry 50 }

pclNfsV2GetattrPerCent OBJECT-TYPE
    SYNTAX          Integer32 (0..100)
    MAX-ACCESS      read-only
    STATUS          current
    DESCRIPTION     
            "The number of NFS Version 2 calls
             received from the referenced client for
             the NFSPROC_GETATTR (Get File Attributes)
             procedure, as a percentage of the total
             calls received from this client, since
             the last time the statistics were cleared."
    ::= { pclEntry 51 }

pclNfsV2SetattrPerCent OBJECT-TYPE
    SYNTAX          Integer32 (0..100)
    MAX-ACCESS      read-only
    STATUS          current
    DESCRIPTION     
            "The number of NFS Version 2 calls
             received from the referenced client for
             the NFSPROC_SETATTR (Set File Attributes)
             procedure, as a percentage of the total
             calls received from this client, since
             the last time the statistics were cleared."
    ::= { pclEntry 52 }

pclNfsV2RootPerCent OBJECT-TYPE
    SYNTAX          Integer32 (0..100)
    MAX-ACCESS      read-only
    STATUS          current
    DESCRIPTION     
            "The number of NFS Version 2 calls
             received from the referenced client for
             the NFSPROC_ROOT (Get Filesystem Root)
             procedure, as a percentage of the total
             calls received from this client, since
             the last time the statistics were cleared."
    ::= { pclEntry 53 }

pclNfsV2LookupPerCent OBJECT-TYPE
    SYNTAX          Integer32 (0..100)
    MAX-ACCESS      read-only
    STATUS          current
    DESCRIPTION     
            "The number of NFS Version 2 calls
             received from the referenced client for
             the NFSPROC_LOOKUP (Look Up File Name)
             procedure, as a percentage of the total
             calls received from this client, since
             the last time the statistics were cleared."
    ::= { pclEntry 54 }

pclNfsV2ReadlinkPerCent OBJECT-TYPE
    SYNTAX          Integer32 (0..100)
    MAX-ACCESS      read-only
    STATUS          current
    DESCRIPTION     
            "The number of NFS Version 2 calls
             received from the referenced client for
             the NFSPROC_READLINK (Read From Symbolic
             Link) procedure, as a percentage of the
             total calls received from this client,
             since the last time the statistics were
             cleared."
    ::= { pclEntry 55 }

pclNfsV2ReadPerCent OBJECT-TYPE
    SYNTAX          Integer32 (0..100)
    MAX-ACCESS      read-only
    STATUS          current
    DESCRIPTION     
            "The number of NFS Version 2 calls
             received from the referenced client for
             the NFSPROC_READ (Read From File)
             procedure, as a percentage of the total
             calls received from this client, since
             the last time the statistics were cleared."
    ::= { pclEntry 56 }

pclNfsV2WrcachePerCent OBJECT-TYPE
    SYNTAX          Integer32 (0..100)
    MAX-ACCESS      read-only
    STATUS          current
    DESCRIPTION     
            "The number of NFS Version 2 calls
             received from the referenced client for
             the NFSPROC_WRITECACHE (Write to Cache)
             procedure, as a percentage of the total
             calls received from this client, since
             the last time the statistics were cleared."
    ::= { pclEntry 57 }

pclNfsV2WritePerCent OBJECT-TYPE
    SYNTAX          Integer32 (0..100)
    MAX-ACCESS      read-only
    STATUS          current
    DESCRIPTION     
            "The number of NFS Version 2 calls
             received from the referenced client for
             the NFSPROC_WRITE (Write to File)
             procedure, as a percentage of the total
             calls received from this client, since
             the last time the statistics were cleared."
    ::= { pclEntry 58 }

pclNfsV2CreatePerCent OBJECT-TYPE
    SYNTAX          Integer32 (0..100)
    MAX-ACCESS      read-only
    STATUS          current
    DESCRIPTION     
            "The number of NFS Version 2 calls
             received from the referenced client for
             the NFSPROC_CREATE (Create File)
             procedure, as a percentage of the total
             calls received from this client, since
             the last time the statistics were cleared."
    ::= { pclEntry 59 }

pclNfsV2RemovePerCent OBJECT-TYPE
    SYNTAX          Integer32 (0..100)
    MAX-ACCESS      read-only
    STATUS          current
    DESCRIPTION     
            "The number of NFS Version 2 calls
             received from the referenced client for
             the NFSPROC_REMOVE (Remove File)
             procedure, as a percentage of the total
             calls received from this client, since
             the last time the statistics were cleared."
    ::= { pclEntry 60 }

pclNfsV2RenamePerCent OBJECT-TYPE
    SYNTAX          Integer32 (0..100)
    MAX-ACCESS      read-only
    STATUS          current
    DESCRIPTION     
            "The number of NFS Version 2 calls
             received from the referenced client for
             the NFSPROC_RENAME (Rename File)
             procedure, as a percentage of the total
             calls received from this client, since
             the last time the statistics were cleared."
    ::= { pclEntry 61 }

pclNfsV2LinkPerCent OBJECT-TYPE
    SYNTAX          Integer32 (0..100)
    MAX-ACCESS      read-only
    STATUS          current
    DESCRIPTION     
            "The number of NFS Version 2 calls
             received from the referenced client for
             the NFSPROC_LINK (Create Link to File)
             procedure, as a percentage of the total
             calls received from this client, since
             the last time the statistics were cleared."
    ::= { pclEntry 62 }

pclNfsV2SymlinkPerCent OBJECT-TYPE
    SYNTAX          Integer32 (0..100)
    MAX-ACCESS      read-only
    STATUS          current
    DESCRIPTION     
            "The number of NFS Version 2 calls
             received from the referenced client for
             the NFSPROC_SYMLINK (Create Symbolic Link)
             procedure, as a percentage of the total
             calls received from this client, since
             the last time the statistics were cleared."
    ::= { pclEntry 63 }

pclNfsV2MkdirPerCent OBJECT-TYPE
    SYNTAX          Integer32 (0..100)
    MAX-ACCESS      read-only
    STATUS          current
    DESCRIPTION     
            "The number of NFS Version 2 calls
             received from the referenced client for
             the NFSPROC_MKDIR (Create Directory)
             procedure, as a percentage of the total
             calls received from this client, since
             the last time the statistics were cleared."
    ::= { pclEntry 64 }

pclNfsV2RmdirPerCent OBJECT-TYPE
    SYNTAX          Integer32 (0..100)
    MAX-ACCESS      read-only
    STATUS          current
    DESCRIPTION     
            "The number of NFS Version 2 calls
             received from the referenced client for
             the NFSPROC_RMDIR (Remove Directory)
             procedure, as a percentage of the total
             calls received from this client, since
             the last time the statistics were cleared."
    ::= { pclEntry 65 }

pclNfsV2ReaddirPerCent OBJECT-TYPE
    SYNTAX          Integer32 (0..100)
    MAX-ACCESS      read-only
    STATUS          current
    DESCRIPTION     
            "The number of NFS Version 2 calls
             received from the referenced client for
             the NFSPROC_READDIR (Read From Directory)
             procedure, as a percentage of the total
             calls received from this client, since
             the last time the statistics were cleared."
    ::= { pclEntry 66 }

pclNfsV2StatfsPerCent OBJECT-TYPE
    SYNTAX          Integer32 (0..100)
    MAX-ACCESS      read-only
    STATUS          current
    DESCRIPTION     
            "The number of NFS Version 2 calls
             received from the referenced client for
             the NFSPROC_STATFS (Get Filesystem
             Attributes) procedure, as a percentage
             of the total calls received from this
             client, since the last time the
             statistics were cleared."
    ::= { pclEntry 67 }

pclNfsV3NullPerCent OBJECT-TYPE
    SYNTAX          Integer32 (0..100)
    MAX-ACCESS      read-only
    STATUS          current
    DESCRIPTION     
            "The number of NFS Version 3 calls
             received from the referenced client for
             the NFSPROC3_NULL (Do Nothing) 
             procedure, as a percentage of the total
             calls received from this client, since
             the last time the statistics were cleared."
    ::= { pclEntry 68 }

pclNfsV3GetattrPerCent OBJECT-TYPE
    SYNTAX          Integer32 (0..100)
    MAX-ACCESS      read-only
    STATUS          current
    DESCRIPTION     
            "The number of NFS Version 3 calls
             received from the referenced client for
             the NFSPROC3_GETATTR (Get File Attributes)
             procedure, as a percentage of the total
             calls received from this client, since
             the last time the statistics were cleared."
    ::= { pclEntry 69 }

pclNfsV3SetattrPerCent OBJECT-TYPE
    SYNTAX          Integer32 (0..100)
    MAX-ACCESS      read-only
    STATUS          current
    DESCRIPTION     
            "The number of NFS Version 3 calls
             received from the referenced client for
             the NFSPROC3_SETATTR (Set File Attributes)
             procedure, as a percentage of the total
             calls received from this client, since
             the last time the statistics were cleared."
    ::= { pclEntry 70 }

pclNfsV3LookupPerCent OBJECT-TYPE
    SYNTAX          Integer32 (0..100)
    MAX-ACCESS      read-only
    STATUS          current
    DESCRIPTION     
            "The number of NFS Version 3 calls
             received from the referenced client for
             the NFSPROC3_LOOKUP (Lookup Filename)
             procedure, as a percentage of the total
             calls received from this client, since
             the last time the statistics were cleared."
    ::= { pclEntry 71 }

pclNfsV3AccessPerCent OBJECT-TYPE
    SYNTAX          Integer32 (0..100)
    MAX-ACCESS      read-only
    STATUS          current
    DESCRIPTION     
            "The number of NFS Version 3 calls
             received from the referenced client for
             the NFSPROC3_ACCESS (Check Access Permission)
             procedure, as a percentage of the total
             calls received from this client, since
             the last time the statistics were cleared."
    ::= { pclEntry 72 }

pclNfsV3ReadlinkPerCent OBJECT-TYPE
    SYNTAX          Integer32 (0..100)
    MAX-ACCESS      read-only
    STATUS          current
    DESCRIPTION     
            "The number of NFS Version 3 calls
             received from the referenced client for
             the NFSPROC3_READLINK (Read from Symbolic
             Link) procedure, as a percentage of the total
             calls received from this client, since
             the last time the statistics were cleared."
    ::= { pclEntry 73 }

pclNfsV3ReadPerCent OBJECT-TYPE
    SYNTAX          Integer32 (0..100)
    MAX-ACCESS      read-only
    STATUS          current
    DESCRIPTION     
            "The number of NFS Version 3 calls
             received from the referenced client for
             the NFSPROC3_READ (Read From File)
             procedure, as a percentage of the total
             calls received from this client, since
             the last time the statistics were cleared."
    ::= { pclEntry 74 }

pclNfsV3WritePerCent OBJECT-TYPE
    SYNTAX          Integer32 (0..100)
    MAX-ACCESS      read-only
    STATUS          current
    DESCRIPTION     
            "The number of NFS Version 3 calls
             received from the referenced client for
             the NFSPROC3_WRITE (Write to File)
             procedure, as a percentage of the total
             calls received from this client, since
             the last time the statistics were cleared."
    ::= { pclEntry 75 }

pclNfsV3CreatePerCent OBJECT-TYPE
    SYNTAX          Integer32 (0..100)
    MAX-ACCESS      read-only
    STATUS          current
    DESCRIPTION     
            "The number of NFS Version 3 calls
             received from the referenced client for
             the NFSPROC3_CREATE (Create a File)
             procedure, as a percentage of the total
             calls received from this client, since
             the last time the statistics were cleared."
    ::= { pclEntry 76 }

pclNfsV3MkdirPerCent OBJECT-TYPE
    SYNTAX          Integer32 (0..100)
    MAX-ACCESS      read-only
    STATUS          current
    DESCRIPTION     
            "The number of NFS Version 3 calls
             received from the referenced client for
             the NFSPROC3_MKDIR (Create a Directory)
             procedure, as a percentage of the total
             calls received from this client, since
             the last time the statistics were cleared."
    ::= { pclEntry 77 }

pclNfsV3SymlinkPerCent OBJECT-TYPE
    SYNTAX          Integer32 (0..100)
    MAX-ACCESS      read-only
    STATUS          current
    DESCRIPTION     
            "The number of NFS Version 3 calls
             received from the referenced client for
             the NFSPROC3_SYMLINK (Create a Symbolic
             Link) procedure, as a percentage of the
             total calls received from this client, since
             the last time the statistics were cleared."
    ::= { pclEntry 78 }

pclNfsV3MknodPerCent OBJECT-TYPE
    SYNTAX          Integer32 (0..100)
    MAX-ACCESS      read-only
    STATUS          current
    DESCRIPTION     
            "The number of NFS Version 3 calls
             received from the referenced client for
             the NFSPROC3_MKNOD (Create a Special
             Device) procedure, as a percentage of the
             total calls received from this client, since
             the last time the statistics were cleared."
    ::= { pclEntry 79 }

pclNfsV3RemovePerCent OBJECT-TYPE
    SYNTAX          Integer32 (0..100)
    MAX-ACCESS      read-only
    STATUS          current
    DESCRIPTION     
            "The number of NFS Version 3 calls
             received from the referenced client for
             the NFSPROC3_REMOVE (Remove a File)
             procedure, as a percentage of the total
             calls received from this client, since
             the last time the statistics were cleared."
    ::= { pclEntry 80 }

pclNfsV3RmdirPerCent OBJECT-TYPE
    SYNTAX          Integer32 (0..100)
    MAX-ACCESS      read-only
    STATUS          current
    DESCRIPTION     
            "The number of NFS Version 3 calls
             received from the referenced client for
             the NFSPROC3_RMDIR (Remove a Directory)
             procedure, as a percentage of the total
             calls received from this client, since
             the last time the statistics were cleared."
    ::= { pclEntry 81 }

pclNfsV3RenamePerCent OBJECT-TYPE
    SYNTAX          Integer32 (0..100)
    MAX-ACCESS      read-only
    STATUS          current
    DESCRIPTION     
            "The number of NFS Version 3 calls
             received from the referenced client for
             the NFSPROC3_RENAME (Rename a File or
             Directory) procedure, as a percentage of
             the total calls received from this client,
             since the last time the statistics were
             cleared."
    ::= { pclEntry 82 }

pclNfsV3LinkPerCent OBJECT-TYPE
    SYNTAX          Integer32 (0..100)
    MAX-ACCESS      read-only
    STATUS          current
    DESCRIPTION     
            "The number of NFS Version 3 calls
             received from the referenced client for
             the NFSPROC3_LINK (Create Link to an Object) 
             procedure, as a percentage of the total
             calls received from this client, since
             the last time the statistics were cleared."
    ::= { pclEntry 83 }

pclNfsV3ReaddirPerCent OBJECT-TYPE
    SYNTAX          Integer32 (0..100)
    MAX-ACCESS      read-only
    STATUS          current
    DESCRIPTION     
            "The number of NFS Version 3 calls
             received from the referenced client for
             the NFSPROC3_READDIR (Read From Directory)
             procedure, as a percentage of the total
             calls received from this client, since
             the last time the statistics were cleared."
    ::= { pclEntry 84 }

pclNfsV3ReaddirPlusPerCent OBJECT-TYPE
    SYNTAX          Integer32 (0..100)
    MAX-ACCESS      read-only
    STATUS          current
    DESCRIPTION     
            "The number of NFS Version 3 calls
             received from the referenced client for
             the NFSPROC3_READDIRPLUS (Extended Read from
             Directory) procedure, as a percentage of the
             total calls received from this client, since
             the last time the statistics were cleared."
    ::= { pclEntry 85 }

pclNfsV3FsstatPerCent OBJECT-TYPE
    SYNTAX          Integer32 (0..100)
    MAX-ACCESS      read-only
    STATUS          current
    DESCRIPTION     
            "The number of NFS Version 3 calls
             received from the referenced client for
             the NFSPROC3_FSSTAT (Get Dynamic File
             System Information) procedure, as a
             percentage of the total calls received
             from this client, since the last time
             the statistics were cleared."
    ::= { pclEntry 86 }

pclNfsV3FsinfoPerCent OBJECT-TYPE
    SYNTAX          Integer32 (0..100)
    MAX-ACCESS      read-only
    STATUS          current
    DESCRIPTION     
            "The number of NFS Version 3 calls
             received from the referenced client for
             the NFSPROC3_FSINFO (Get Static File System
             Information) procedure, as a percentage of the
             total calls received from this client, since
             the last time the statistics were cleared."
    ::= { pclEntry 87 }

pclNfsV3PathconfPerCent OBJECT-TYPE
    SYNTAX          Integer32 (0..100)
    MAX-ACCESS      read-only
    STATUS          current
    DESCRIPTION     
            "The number of NFS Version 3 calls
             received from the referenced client for
             the NFSPROC3_PATHCONF (Retrieve POSIX
             Information) procedure, as a percentage of the
             total calls received from this client, since
             the last time the statistics were cleared."
    ::= { pclEntry 88 }

pclNfsV3CommitPerCent OBJECT-TYPE
    SYNTAX          Integer32 (0..100)
    MAX-ACCESS      read-only
    STATUS          current
    DESCRIPTION     
            "The number of NFS Version 3 calls
             received from the referenced client for
             the NFSPROC3_COMMIT (Commit Cached Data on
             a Server to Stable Storage) procedure, as
             a percentage of the total calls received
             from this client, since the last time the
             statistics were cleared."
    ::= { pclEntry 89 }

totNfs OBJECT IDENTIFIER
    ::= { nfs 2 }

trpcServ OBJECT IDENTIFIER
    ::= { totNfs 1 }

trpcCalls OBJECT-TYPE
    SYNTAX          Counter32
    MAX-ACCESS      read-only
    STATUS          current
    DESCRIPTION     
            "The total number of RPC calls received,
             since the last boot."
    ::= { trpcServ 1 }

trpcBadCalls OBJECT-TYPE
    SYNTAX          Counter32
    MAX-ACCESS      read-only
    STATUS          current
    DESCRIPTION     
            "The total number of calls rejected by the RPC
             layer, since the last boot."
    ::= { trpcServ 2 }

trpcNullRecvs OBJECT-TYPE
    SYNTAX          Counter32
    MAX-ACCESS      read-only
    STATUS          current
    DESCRIPTION     
            "The number of times an RPC call was not
             available when it was thought to be received,
             since the last boot."
    ::= { trpcServ 3 }

trpcBadLens OBJECT-TYPE
    SYNTAX          Counter32
    MAX-ACCESS      read-only
    STATUS          current
    DESCRIPTION     
            "The number of RPC calls received with a length
             shorter than a minimum-sized RPC call, since
             the last boot."
    ::= { trpcServ 4 }

trpcServXDRCalls OBJECT-TYPE
    SYNTAX          Counter32
    MAX-ACCESS      read-only
    STATUS          current
    DESCRIPTION     
            "The number of RPC calls received whose header
             could not be XDR decoded, since the last boot."
    ::= { trpcServ 5 }

tnfsServ OBJECT IDENTIFIER
    ::= { totNfs 2 }

tnfsCalls OBJECT-TYPE
    SYNTAX          Counter32
    MAX-ACCESS      read-only
    STATUS          current
    DESCRIPTION     
            "The total number of NFS calls received, since
             since the last boot."
    ::= { tnfsServ 1 }

tnfsServBadCalls OBJECT-TYPE
    SYNTAX          Counter32
    MAX-ACCESS      read-only
    STATUS          current
    DESCRIPTION     
            "The total number of received NFS calls rejected,
             since the last boot."
    ::= { tnfsServ 2 }

tnfsV2 OBJECT IDENTIFIER
    ::= { tnfsServ 3 }

tv2Calls OBJECT IDENTIFIER
    ::= { tnfsV2 1 }

tv2cNulls OBJECT-TYPE
    SYNTAX          Counter32
    MAX-ACCESS      read-only
    STATUS          current
    DESCRIPTION     
            "The number of NFS Version 2 calls received
             for the NFSPROC_NULL (Do Nothing) procedure,
             since the last boot."
    ::= { tv2Calls 1 }

tv2cGetattrs OBJECT-TYPE
    SYNTAX          Counter32
    MAX-ACCESS      read-only
    STATUS          current
    DESCRIPTION     
            "The number of NFS Version 2 calls received
             for the NFSPROC_GETATTR (Get File Attributes)
             procedure, since the last boot."
    ::= { tv2Calls 2 }

tv2cSetattrs OBJECT-TYPE
    SYNTAX          Counter32
    MAX-ACCESS      read-only
    STATUS          current
    DESCRIPTION     
            "The number of NFS Version 2 calls received
             for the NFSPROC_SETATTR (Set File Attributes)
             procedure, since the the last boot."
    ::= { tv2Calls 3 }

tv2cRoots OBJECT-TYPE
    SYNTAX          Counter32
    MAX-ACCESS      read-only
    STATUS          current
    DESCRIPTION     
            "The number of NFS Version 2 calls received
             for the NFSPROC_ROOT (Get Filesystem Root)
             procedure, since the last boot."
    ::= { tv2Calls 4 }

tv2cLookups OBJECT-TYPE
    SYNTAX          Counter32
    MAX-ACCESS      read-only
    STATUS          current
    DESCRIPTION     
            "The number of NFS Version 2 calls received
             for the NFSPROC_LOOKUP (Look Up File Name)
             procedure, since the last boot."
    ::= { tv2Calls 5 }

tv2cReadlinks OBJECT-TYPE
    SYNTAX          Counter32
    MAX-ACCESS      read-only
    STATUS          current
    DESCRIPTION     
            "The number of NFS Version 2 calls received
             for the NFSPROC_READLINK (Read From Symbolic
             Link) procedure, since the last boot."
    ::= { tv2Calls 6 }

tv2cReads OBJECT-TYPE
    SYNTAX          Counter32
    MAX-ACCESS      read-only
    STATUS          current
    DESCRIPTION     
            "The number of NFS Version 2 calls received
             for the NFSPROC_READ (Read From File)
             procedure, since the last boot."
    ::= { tv2Calls 7 }

tv2cWrcaches OBJECT-TYPE
    SYNTAX          Counter32
    MAX-ACCESS      read-only
    STATUS          current
    DESCRIPTION     
            "The number of NFS Version 2 calls received
             for the NFSPROC_WRITECACHE (Write to Cache)
             procedure, since the last boot."
    ::= { tv2Calls 8 }

tv2cWrites OBJECT-TYPE
    SYNTAX          Counter32
    MAX-ACCESS      read-only
    STATUS          current
    DESCRIPTION     
            "The number of NFS Version 2 calls received
             for the NFSPROC_WRITE (Write to File)
             procedure, since the last boot."
    ::= { tv2Calls 9 }

tv2cCreates OBJECT-TYPE
    SYNTAX          Counter32
    MAX-ACCESS      read-only
    STATUS          current
    DESCRIPTION     
            "The number of NFS Version 2 calls received
             for the NFSPROC_CREATE (Create File)
             procedure, since the last boot."
    ::= { tv2Calls 10 }

tv2cRemoves OBJECT-TYPE
    SYNTAX          Counter32
    MAX-ACCESS      read-only
    STATUS          current
    DESCRIPTION     
            "The number of NFS Version 2 calls received
             for the NFSPROC_REMOVE (Remove File)
             procedure, since the last boot."
    ::= { tv2Calls 11 }

tv2cRenames OBJECT-TYPE
    SYNTAX          Counter32
    MAX-ACCESS      read-only
    STATUS          current
    DESCRIPTION     
            "The number of NFS Version 2 calls received
             for the NFSPROC_RENAME (Rename File)
             procedure, since the last boot."
    ::= { tv2Calls 12 }

tv2cLinks OBJECT-TYPE
    SYNTAX          Counter32
    MAX-ACCESS      read-only
    STATUS          current
    DESCRIPTION     
            "The number of NFS Version 2 calls received
             for the NFSPROC_LINK (Create Link to File)
             procedure, since the last boot."
    ::= { tv2Calls 13 }

tv2cSymlinks OBJECT-TYPE
    SYNTAX          Counter32
    MAX-ACCESS      read-only
    STATUS          current
    DESCRIPTION     
            "The number of NFS Version 2 calls received
             for the NFSPROC_SYMLINK (Create Symbolic Link)
             procedure, since the last boot."
    ::= { tv2Calls 14 }

tv2cMkdirs OBJECT-TYPE
    SYNTAX          Counter32
    MAX-ACCESS      read-only
    STATUS          current
    DESCRIPTION     
            "The number of NFS Version 2 calls received
             for the NFSPROC_MKDIR (Create Directory)
             procedure, since the last boot."
    ::= { tv2Calls 15 }

tv2cRmdirs OBJECT-TYPE
    SYNTAX          Counter32
    MAX-ACCESS      read-only
    STATUS          current
    DESCRIPTION     
            "The number of NFS Version 2 calls received
             for the NFSPROC_RMDIR (Remove Directory)
             procedure, since the last boot."
    ::= { tv2Calls 16 }

tv2cReaddirs OBJECT-TYPE
    SYNTAX          Counter32
    MAX-ACCESS      read-only
    STATUS          current
    DESCRIPTION     
            "The number of NFS Version 2 calls received
             for the NFSPROC_READDIR (Read From Directory)
             procedure, since the last boot."
    ::= { tv2Calls 17 }

tv2cStatfss OBJECT-TYPE
    SYNTAX          Counter32
    MAX-ACCESS      read-only
    STATUS          current
    DESCRIPTION     
            "The number of NFS Version 2 calls received
             for the NFSPROC_STATFS (Get Filesystem
             Attributes) procedure, since the last boot."
    ::= { tv2Calls 18 }

tv2Percent OBJECT IDENTIFIER
    ::= { tnfsV2 2 }

tv2pNulls OBJECT-TYPE
    SYNTAX          Integer32 (0..100)
    MAX-ACCESS      read-only
    STATUS          current
    DESCRIPTION     
            "The number of NFS Version 2 calls received
             for the NFSPROC_NULL (Do Nothing) procedure
             as a percentage of total NFS calls received,
             since the last boot."
    ::= { tv2Percent 1 }

tv2pGetattrs OBJECT-TYPE
    SYNTAX          Integer32 (0..100)
    MAX-ACCESS      read-only
    STATUS          current
    DESCRIPTION     
            "The number of NFS Version 2 calls received
             for the NFSPROC_GETATTR (Get File Attributes)
             procedure as a percentage of total NFS calls
             received, since the last boot."
    ::= { tv2Percent 2 }

tv2pSetattrs OBJECT-TYPE
    SYNTAX          Integer32 (0..100)
    MAX-ACCESS      read-only
    STATUS          current
    DESCRIPTION     
            "The number of NFS Version 2 calls received
             for the NFSPROC_SETATTR (Set File Attributes)
             procedure as a percentage of total NFS calls
             received, since the last boot."
    ::= { tv2Percent 3 }

tv2pRoots OBJECT-TYPE
    SYNTAX          Integer32 (0..100)
    MAX-ACCESS      read-only
    STATUS          current
    DESCRIPTION     
            "The number of NFS Version 2 calls received
             for the NFSPROC_ROOT (Get Filesystem Root)
             procedure as a percentage of total NFS calls
             received, since the last boot."
    ::= { tv2Percent 4 }

tv2pLookups OBJECT-TYPE
    SYNTAX          Integer32 (0..100)
    MAX-ACCESS      read-only
    STATUS          current
    DESCRIPTION     
            "The number of NFS Version 2 calls received
             for the NFSPROC_LOOKUP (Look Up File Name)
             procedure as a percentage of total NFS calls
             received, since the last boot."
    ::= { tv2Percent 5 }

tv2pReadlinks OBJECT-TYPE
    SYNTAX          Integer32 (0..100)
    MAX-ACCESS      read-only
    STATUS          current
    DESCRIPTION     
            "The number of NFS Version 2 calls received
             for the NFSPROC_READLINK (Read From Symbolic
             Link) procedure as a percentage of total NFS
             calls received, since the last boot."
    ::= { tv2Percent 6 }

tv2pReads OBJECT-TYPE
    SYNTAX          Integer32 (0..100)
    MAX-ACCESS      read-only
    STATUS          current
    DESCRIPTION     
            "The number of NFS Version 2 calls received
             for the NFSPROC_READ (Read From File)
             procedure as a percentage of total NFS calls
             received, since the last boot."
    ::= { tv2Percent 7 }

tv2pWrcaches OBJECT-TYPE
    SYNTAX          Integer32 (0..100)
    MAX-ACCESS      read-only
    STATUS          current
    DESCRIPTION     
            "The number of NFS Version 2 calls received
             for the NFSPROC_WRITECACHE (Write to Cache)
             procedure as a percentage of total NFS calls
             received, since the last boot."
    ::= { tv2Percent 8 }

tv2pWrites OBJECT-TYPE
    SYNTAX          Integer32 (0..100)
    MAX-ACCESS      read-only
    STATUS          current
    DESCRIPTION     
            "The number of NFS Version 2 calls received
             for the NFSPROC_WRITE (Write to File)
             procedure as a percentage of total NFS calls
             received, since the last boot."
    ::= { tv2Percent 9 }

tv2pCreates OBJECT-TYPE
    SYNTAX          Integer32 (0..100)
    MAX-ACCESS      read-only
    STATUS          current
    DESCRIPTION     
            "The number of NFS Version 2 calls received
             for the NFSPROC_CREATE (Create File)
             procedure as a percentage of total NFS calls
             received, since the last boot."
    ::= { tv2Percent 10 }

tv2pRemoves OBJECT-TYPE
    SYNTAX          Integer32 (0..100)
    MAX-ACCESS      read-only
    STATUS          current
    DESCRIPTION     
            "The number of NFS Version 2 calls received
             for the NFSPROC_REMOVE (Remove File)
             procedure as a percentage of total NFS calls
             received, since the last boot."
    ::= { tv2Percent 11 }

tv2pRenames OBJECT-TYPE
    SYNTAX          Integer32 (0..100)
    MAX-ACCESS      read-only
    STATUS          current
    DESCRIPTION     
            "The number of NFS Version 2 calls received
             for the NFSPROC_RENAME (Rename File)
             procedure as a percentage of total NFS calls
             received, since the last boot."
    ::= { tv2Percent 12 }

tv2pLinks OBJECT-TYPE
    SYNTAX          Integer32 (0..100)
    MAX-ACCESS      read-only
    STATUS          current
    DESCRIPTION     
            "The number of NFS Version 2 calls received
             for the NFSPROC_LINK (Create Link to File)
             procedure as a percentage of total NFS calls
             received, since the last boot."
    ::= { tv2Percent 13 }

tv2pSymlinks OBJECT-TYPE
    SYNTAX          Integer32 (0..100)
    MAX-ACCESS      read-only
    STATUS          current
    DESCRIPTION     
            "The number of NFS Version 2 calls received
             for the NFSPROC_SYMLINK (Create Symbolic Link)
             procedure as a percentage of total NFS calls
             received, since the last boot."
    ::= { tv2Percent 14 }

tv2pMkdirs OBJECT-TYPE
    SYNTAX          Integer32 (0..100)
    MAX-ACCESS      read-only
    STATUS          current
    DESCRIPTION     
            "The number of NFS Version 2 calls received
             for the NFSPROC_MKDIR (Create Directory)
             procedure as a percentage of total NFS calls
             received, since the last boot."
    ::= { tv2Percent 15 }

tv2pRmdirs OBJECT-TYPE
    SYNTAX          Integer32 (0..100)
    MAX-ACCESS      read-only
    STATUS          current
    DESCRIPTION     
            "The number of NFS Version 2 calls received
             for the NFSPROC_RMDIR (Remove Directory)
             procedure as a percentage of total NFS calls
             received, since the last boot."
    ::= { tv2Percent 16 }

tv2pReaddirs OBJECT-TYPE
    SYNTAX          Integer32 (0..100)
    MAX-ACCESS      read-only
    STATUS          current
    DESCRIPTION     
            "The number of NFS Version 2 calls received
             for the NFSPROC_READDIR (Read From Directory)
             procedure as a percentage of total NFS calls
             received, since the last boot."
    ::= { tv2Percent 17 }

tv2pStatfss OBJECT-TYPE
    SYNTAX          Integer32 (0..100)
    MAX-ACCESS      read-only
    STATUS          current
    DESCRIPTION     
            "The number of NFS Version 2 calls received
             for the NFSPROC_STATFS (Get Filesystem
             Attributes) procedure as a percentage of
             total NFS calls received, since the last boot."
    ::= { tv2Percent 18 }

tv2CachedCalls OBJECT IDENTIFIER
    ::= { tnfsV2 3 }

tv2ccNulls OBJECT-TYPE
    SYNTAX          Counter32
    MAX-ACCESS      read-only
    STATUS          current
    DESCRIPTION     
            "The number of NFS Version 2 calls received
             for the NFSPROC_NULL (Do Nothing) procedure,
             that did not result in the filesystem blocking
             to read from disk, since the last boot."
    ::= { tv2CachedCalls 1 }

tv2ccGetattrs OBJECT-TYPE
    SYNTAX          Counter32
    MAX-ACCESS      read-only
    STATUS          current
    DESCRIPTION     
            "The number of NFS Version 2 calls received
             for the NFSPROC_GETATTR (Get File Attributes)
             procedure, that did not result in the
             filesystem blocking to read from disk, 
             since the last boot."
    ::= { tv2CachedCalls 2 }

tv2ccSetattrs OBJECT-TYPE
    SYNTAX          Counter32
    MAX-ACCESS      read-only
    STATUS          current
    DESCRIPTION     
            "The number of NFS Version 2 calls received
             for the NFSPROC_SETATTR (Set File Attributes)
             procedure, that did not result in the
             filesystem blocking to read from disk,
             since the last boot."
    ::= { tv2CachedCalls 3 }

tv2ccRoots OBJECT-TYPE
    SYNTAX          Counter32
    MAX-ACCESS      read-only
    STATUS          current
    DESCRIPTION     
            "The number of NFS Version 2 calls received
             for the NFSPROC_ROOT (Get Filesystem Root)
             procedure, that did not result in the
             filesystem blocking to read from disk,
             since the last boot."
    ::= { tv2CachedCalls 4 }

tv2ccLookups OBJECT-TYPE
    SYNTAX          Counter32
    MAX-ACCESS      read-only
    STATUS          current
    DESCRIPTION     
            "The number of NFS Version 2 calls received
             for the NFSPROC_LOOKUP (Look Up File Name)
             procedure, that did not result in the
             filesystem blocking to read from disk,
             since the last boot."
    ::= { tv2CachedCalls 5 }

tv2ccReadlinks OBJECT-TYPE
    SYNTAX          Counter32
    MAX-ACCESS      read-only
    STATUS          current
    DESCRIPTION     
            "The number of NFS Version 2 calls received
             for the NFSPROC_READLINK (Read From Symbolic
             Link) procedure, that did not result in the
             filesystem blocking to read from disk, 
             since the last boot."
    ::= { tv2CachedCalls 6 }

tv2ccReads OBJECT-TYPE
    SYNTAX          Counter32
    MAX-ACCESS      read-only
    STATUS          current
    DESCRIPTION     
            "The number of NFS Version 2 calls received
             for the NFSPROC_READ (Read From File)
             procedure, that did not result in the
             filesystem blocking to read from disk,
             since the last boot."
    ::= { tv2CachedCalls 7 }

tv2ccWrcaches OBJECT-TYPE
    SYNTAX          Counter32
    MAX-ACCESS      read-only
    STATUS          current
    DESCRIPTION     
            "The number of NFS Version 2 calls received
             for the NFSPROC_WRITECACHE (Write to Cache)
             procedure, that did not result in the
             filesystem blocking to read from disk,
             since the last boot."
    ::= { tv2CachedCalls 8 }

tv2ccWrites OBJECT-TYPE
    SYNTAX          Counter32
    MAX-ACCESS      read-only
    STATUS          current
    DESCRIPTION     
            "The number of NFS Version 2 calls received
             for the NFSPROC_WRITE (Write to File)
             procedure, that did not result in the
             filesystem blocking to read from disk,
             since the last boot."
    ::= { tv2CachedCalls 9 }

tv2ccCreates OBJECT-TYPE
    SYNTAX          Counter32
    MAX-ACCESS      read-only
    STATUS          current
    DESCRIPTION     
            "The number of NFS Version 2 calls received
             for the NFSPROC_CREATE (Create File)
             procedure, that did not result in the
             filesystem blocking to read from disk,
             since the last boot."
    ::= { tv2CachedCalls 10 }

tv2ccRemoves OBJECT-TYPE
    SYNTAX          Counter32
    MAX-ACCESS      read-only
    STATUS          current
    DESCRIPTION     
            "The number of NFS Version 2 calls received
             for the NFSPROC_REMOVE (Remove File)
             procedure, that did not result in the
             filesystem blocking to read from disk,
             since the last boot."
    ::= { tv2CachedCalls 11 }

tv2ccRenames OBJECT-TYPE
    SYNTAX          Counter32
    MAX-ACCESS      read-only
    STATUS          current
    DESCRIPTION     
            "The number of NFS Version 2 calls received
             for the NFSPROC_RENAME (Rename File)
             procedure, that did not result in the
             filesystem blocking to read from disk,
             since the last boot."
    ::= { tv2CachedCalls 12 }

tv2ccLinks OBJECT-TYPE
    SYNTAX          Counter32
    MAX-ACCESS      read-only
    STATUS          current
    DESCRIPTION     
            "The number of NFS Version 2 calls received
             for the NFSPROC_LINK (Create Link to File)
             procedure, that did not result in the
             filesystem blocking to read from disk,
             since the last boot."
    ::= { tv2CachedCalls 13 }

tv2ccSymlinks OBJECT-TYPE
    SYNTAX          Counter32
    MAX-ACCESS      read-only
    STATUS          current
    DESCRIPTION     
            "The number of NFS Version 2 calls received
             for the NFSPROC_SYMLINK (Create Symbolic Link)
             procedure, that did not result in the
             filesystem blocking to read from disk,
             since the last boot."
    ::= { tv2CachedCalls 14 }

tv2ccMkdirs OBJECT-TYPE
    SYNTAX          Counter32
    MAX-ACCESS      read-only
    STATUS          current
    DESCRIPTION     
            "The number of NFS Version 2 calls received
             for the NFSPROC_MKDIR (Create Directory)
             procedure, that did not result in the
             filesystem blocking to read from disk,
             since the last boot."
    ::= { tv2CachedCalls 15 }

tv2ccRmdirs OBJECT-TYPE
    SYNTAX          Counter32
    MAX-ACCESS      read-only
    STATUS          current
    DESCRIPTION     
            "The number of NFS Version 2 calls received
             for the NFSPROC_RMDIR (Remove Directory)
             procedure, that did not result in the
             filesystem blocking to read from disk,
             since the last boot."
    ::= { tv2CachedCalls 16 }

tv2ccReaddirs OBJECT-TYPE
    SYNTAX          Counter32
    MAX-ACCESS      read-only
    STATUS          current
    DESCRIPTION     
            "The number of NFS Version 2 calls received
             for the NFSPROC_READDIR (Read From Directory)
             procedure, that did not result in the
             filesystem blocking to read from disk,
             since the last boot."
    ::= { tv2CachedCalls 17 }

tv2ccStatfss OBJECT-TYPE
    SYNTAX          Counter32
    MAX-ACCESS      read-only
    STATUS          current
    DESCRIPTION     
            "The number of NFS Version 2 calls received
             for the NFSPROC_STATFS (Get Filesystem
             Attributes) procedure, that did not result
             in the filesystem blocking to read from disk,
             since the last boot."
    ::= { tv2CachedCalls 18 }

tv2CachedPerCent OBJECT IDENTIFIER
    ::= { tnfsV2 4 }

tv2cpNulls OBJECT-TYPE
    SYNTAX          Integer32 (0..100)
    MAX-ACCESS      read-only
    STATUS          current
    DESCRIPTION     
            "The number of NFS Version 2 calls received
             for the NFSPROC_NULL (Do Nothing) procedure,
             that did not result in the filesystem
             blocking to read from disk, as a percentage
             of the total number of calls received for
             this procedure, since the last boot."
    ::= { tv2CachedPerCent 1 }

tv2cpGetattrs OBJECT-TYPE
    SYNTAX          Integer32 (0..100)
    MAX-ACCESS      read-only
    STATUS          current
    DESCRIPTION     
            "The number of NFS Version 2 calls received
             for the NFSPROC_GETATTR (Get File Attributes)
             procedure, that did not result in the
             filesystem blocking to read from disk, as a
             percentage of the total number of calls
             received for this procedure, since the last boot."
    ::= { tv2CachedPerCent 2 }

tv2cpSetattrs OBJECT-TYPE
    SYNTAX          Integer32 (0..100)
    MAX-ACCESS      read-only
    STATUS          current
    DESCRIPTION     
            "The number of NFS Version 2 calls received
             for the NFSPROC_SETATTR (Set File Attributes)
             procedure, that did not result in the
             filesystem blocking to read from disk, as a
             percentage of the total number of calls
             received for this procedure, since the last boot."
    ::= { tv2CachedPerCent 3 }

tv2cpRoots OBJECT-TYPE
    SYNTAX          Integer32 (0..100)
    MAX-ACCESS      read-only
    STATUS          current
    DESCRIPTION     
            "The number of NFS Version 2 calls received
             for the NFSPROC_ROOT (Get Filesystem Root)
             procedure, that did not result in the
             filesystem blocking to read from disk, as a
             percentage of the total number of calls
             received for this procedure, since the last boot."
    ::= { tv2CachedPerCent 4 }

tv2cpLookups OBJECT-TYPE
    SYNTAX          Integer32 (0..100)
    MAX-ACCESS      read-only
    STATUS          current
    DESCRIPTION     
            "The number of NFS Version 2 calls received
             for the NFSPROC_LOOKUP (Look Up File Name)
             procedure, that did not result in the
             filesystem blocking to read from disk, as a
             percentage of the total number of calls
             received for this procedure, since the last boot."
    ::= { tv2CachedPerCent 5 }

tv2cpReadlinks OBJECT-TYPE
    SYNTAX          Integer32 (0..100)
    MAX-ACCESS      read-only
    STATUS          current
    DESCRIPTION     
            "The number of NFS Version 2 calls received
             for the NFSPROC_READLINK (Read From Symbolic
             Link) procedure, that did not result in the
             filesystem blocking to read from disk, as a
             percentage of the total number of calls
             received for this procedure, since the last boot."
    ::= { tv2CachedPerCent 6 }

tv2cpReads OBJECT-TYPE
    SYNTAX          Integer32 (0..100)
    MAX-ACCESS      read-only
    STATUS          current
    DESCRIPTION     
            "The number of NFS Version 2 calls received
             for the NFSPROC_READ (Read From File)
             procedure, that did not result in the
             filesystem blocking to read from disk, as a
             percentage of the total number of calls
             received for this procedure, since the last boot."
    ::= { tv2CachedPerCent 7 }

tv2cpWrcaches OBJECT-TYPE
    SYNTAX          Integer32 (0..100)
    MAX-ACCESS      read-only
    STATUS          current
    DESCRIPTION     
            "The number of NFS Version 2 calls received
             for the NFSPROC_WRITECACHE (Write to Cache)
             procedure, that did not result in the
             filesystem blocking to read from disk, as a
             percentage of the total number of calls
             received for this procedure, since the last boot."
    ::= { tv2CachedPerCent 8 }

tv2cpWrites OBJECT-TYPE
    SYNTAX          Integer32 (0..100)
    MAX-ACCESS      read-only
    STATUS          current
    DESCRIPTION     
            "The number of NFS Version 2 calls received
             for the NFSPROC_WRITE (Write to File)
             procedure, that did not result in the
             filesystem blocking to read from disk, as a
             percentage of the total number of calls
             received for this procedure, since the last boot."
    ::= { tv2CachedPerCent 9 }

tv2cpCreates OBJECT-TYPE
    SYNTAX          Integer32 (0..100)
    MAX-ACCESS      read-only
    STATUS          current
    DESCRIPTION     
            "The number of NFS Version 2 calls received
             for the NFSPROC_CREATE (Create File)
             procedure, that did not result in the
             filesystem blocking to read from disk, as a
             percentage of the total number of calls
             received for this procedure, since the last boot."
    ::= { tv2CachedPerCent 10 }

tv2cpRemoves OBJECT-TYPE
    SYNTAX          Integer32 (0..100)
    MAX-ACCESS      read-only
    STATUS          current
    DESCRIPTION     
            "The number of NFS Version 2 calls received
             for the NFSPROC_REMOVE (Remove File)
             procedure, that did not result in the
             filesystem blocking to read from disk, as a
             percentage of the total number of calls
             received for this procedure, since the last boot."
    ::= { tv2CachedPerCent 11 }

tv2cpRenames OBJECT-TYPE
    SYNTAX          Integer32 (0..100)
    MAX-ACCESS      read-only
    STATUS          current
    DESCRIPTION     
            "The number of NFS Version 2 calls received
             for the NFSPROC_RENAME (Rename File)
             procedure, that did not result in the
             filesystem blocking to read from disk, as a
             percentage of the total number of calls
             received for this procedure, since the last boot."
    ::= { tv2CachedPerCent 12 }

tv2cpLinks OBJECT-TYPE
    SYNTAX          Integer32 (0..100)
    MAX-ACCESS      read-only
    STATUS          current
    DESCRIPTION     
            "The number of NFS Version 2 calls received
             for the NFSPROC_LINK (Create Link to File)
             procedure, that did not result in the
             filesystem blocking to read from disk, as a
             percentage of the total number of calls
             received for this procedure, since the last boot."
    ::= { tv2CachedPerCent 13 }

tv2cpSymlinks OBJECT-TYPE
    SYNTAX          Integer32 (0..100)
    MAX-ACCESS      read-only
    STATUS          current
    DESCRIPTION     
            "The number of NFS Version 2 calls received
             for the NFSPROC_SYMLINK (Create Symbolic
             Link) procedure, that did not result in the
             filesystem blocking to read from disk, as a
             percentage of the total number of calls
             received for this procedure, since the last boot."
    ::= { tv2CachedPerCent 14 }

tv2cpMkdirs OBJECT-TYPE
    SYNTAX          Integer32 (0..100)
    MAX-ACCESS      read-only
    STATUS          current
    DESCRIPTION     
            "The number of NFS Version 2 calls received
             for the NFSPROC_MKDIR (Create Directory)
             procedure, that did not result in the
             filesystem blocking to read from disk, as a
             percentage of the total number of calls
             received for this procedure, since the last boot."
    ::= { tv2CachedPerCent 15 }

tv2cpRmdirs OBJECT-TYPE
    SYNTAX          Integer32 (0..100)
    MAX-ACCESS      read-only
    STATUS          current
    DESCRIPTION     
            "The number of NFS Version 2 calls received
             for the NFSPROC_RMDIR (Remove Directory)
             procedure, that did not result in the
             filesystem blocking to read from disk, as a
             percentage of the total number of calls
             received for this procedure, since the last boot."
    ::= { tv2CachedPerCent 16 }

tv2cpReaddirs OBJECT-TYPE
    SYNTAX          Integer32 (0..100)
    MAX-ACCESS      read-only
    STATUS          current
    DESCRIPTION     
            "The number of NFS Version 2 calls received
             for the NFSPROC_READDIR (Read From Directory)
             procedure, that did not result in the
             filesystem blocking to read from disk, as a
             percentage of the total number of calls
             received for this procedure, since the last boot."
    ::= { tv2CachedPerCent 17 }

tv2cpStatfss OBJECT-TYPE
    SYNTAX          Integer32 (0..100)
    MAX-ACCESS      read-only
    STATUS          current
    DESCRIPTION     
            "The number of NFS Version 2 calls received
             for the NFSPROC_STATFS (Get Filesystem
             Attributes) procedure, that did not result
             in the filesystem blocking to read from
             disk, as a percentage of the total number
             of calls received for this procedure, 
             since the last boot."
    ::= { tv2CachedPerCent 18 }

tnfsV3 OBJECT IDENTIFIER
    ::= { tnfsServ 4 }

tv3Calls OBJECT IDENTIFIER
    ::= { tnfsV3 1 }

tv3cNulls OBJECT-TYPE
    SYNTAX          Counter32
    MAX-ACCESS      read-only
    STATUS          current
    DESCRIPTION     
            "The number of NFS Version 3 calls received
             for the NFSPROC3_NULL (Do Nothing) procedure,
             since the last boot."
    ::= { tv3Calls 1 }

tv3cGetattrs OBJECT-TYPE
    SYNTAX          Counter32
    MAX-ACCESS      read-only
    STATUS          current
    DESCRIPTION     
            "The number of NFS Version 3 calls received
             for the NFSPROC3_GETATTR (Get File Attributes)
             procedure, since the last boot."
    ::= { tv3Calls 2 }

tv3cSetattrs OBJECT-TYPE
    SYNTAX          Counter32
    MAX-ACCESS      read-only
    STATUS          current
    DESCRIPTION     
            "The number of NFS Version 3 calls received
             for the NFSPROC3_SETATTR (Set File Attributes)
             procedure, since the last boot."
    ::= { tv3Calls 3 }

tv3cLookups OBJECT-TYPE
    SYNTAX          Counter32
    MAX-ACCESS      read-only
    STATUS          current
    DESCRIPTION     
            "The number of NFS Version 3 calls received
             for the NFSPROC3_LOOKUP (Lookup Filename)
             procedure, since the last boot."
    ::= { tv3Calls 4 }

tv3cAccesss OBJECT-TYPE
    SYNTAX          Counter32
    MAX-ACCESS      read-only
    STATUS          current
    DESCRIPTION     
            "The number of NFS Version 3 calls received
             for the NFSPROC3_ACCESS (Check Access Permission)
             procedure, since the last boot."
    ::= { tv3Calls 5 }

tv3cReadlinks OBJECT-TYPE
    SYNTAX          Counter32
    MAX-ACCESS      read-only
    STATUS          current
    DESCRIPTION     
            "The number of NFS Version 3 calls received
             for the NFSPROC3_READLINK (Read from Symbolic
             Link) procedure, since the last boot."
    ::= { tv3Calls 6 }

tv3cReads OBJECT-TYPE
    SYNTAX          Counter32
    MAX-ACCESS      read-only
    STATUS          current
    DESCRIPTION     
            "The number of NFS Version 3 calls received
             for the NFSPROC3_READ (Read From File)
             procedure, since the last boot."
    ::= { tv3Calls 7 }

tv3cWrites OBJECT-TYPE
    SYNTAX          Counter32
    MAX-ACCESS      read-only
    STATUS          current
    DESCRIPTION     
            "The number of NFS Version 3 calls received
             for the NFSPROC3_WRITE (Write to File)
             procedure, since the last boot."
    ::= { tv3Calls 8 }

tv3cCreates OBJECT-TYPE
    SYNTAX          Counter32
    MAX-ACCESS      read-only
    STATUS          current
    DESCRIPTION     
            "The number of NFS Version 3 calls received
             for the NFSPROC3_CREATE (Create a File)
             procedure, since the last boot."
    ::= { tv3Calls 9 }

tv3cMkdirs OBJECT-TYPE
    SYNTAX          Counter32
    MAX-ACCESS      read-only
    STATUS          current
    DESCRIPTION     
            "The number of NFS Version 3 calls received
             for the NFSPROC3_MKDIR (Create a Directory)
             procedure, since the last boot."
    ::= { tv3Calls 10 }

tv3cSymlinks OBJECT-TYPE
    SYNTAX          Counter32
    MAX-ACCESS      read-only
    STATUS          current
    DESCRIPTION     
            "The number of NFS Version 3 calls received
             for the NFSPROC3_SYMLINK (Create a Symbolic
             Link) procedure, since the last boot."
    ::= { tv3Calls 11 }

tv3cMknods OBJECT-TYPE
    SYNTAX          Counter32
    MAX-ACCESS      read-only
    STATUS          current
    DESCRIPTION     
            "The number of NFS Version 3 calls received
             for the NFSPROC3_MKNOD (Create a Special
             Device) procedure, since the last boot."
    ::= { tv3Calls 12 }

tv3cRemoves OBJECT-TYPE
    SYNTAX          Counter32
    MAX-ACCESS      read-only
    STATUS          current
    DESCRIPTION     
            "The number of NFS Version 3 calls received
             for the NFSPROC3_REMOVE (Remove a File)
             procedure, since the last boot."
    ::= { tv3Calls 13 }

tv3cRmdirs OBJECT-TYPE
    SYNTAX          Counter32
    MAX-ACCESS      read-only
    STATUS          current
    DESCRIPTION     
            "The number of NFS Version 3 calls received
             for the NFSPROC3_RMDIR (Remove a Directory)
             procedure, since the last boot."
    ::= { tv3Calls 14 }

tv3cRenames OBJECT-TYPE
    SYNTAX          Counter32
    MAX-ACCESS      read-only
    STATUS          current
    DESCRIPTION     
            "The number of NFS Version 3 calls received
             for the NFSPROC3_RENAME (Rename a File or
             Directory) procedure, since the last boot."
    ::= { tv3Calls 15 }

tv3cLinks OBJECT-TYPE
    SYNTAX          Counter32
    MAX-ACCESS      read-only
    STATUS          current
    DESCRIPTION     
            "The number of NFS Version 3 calls received
             for the NFSPROC3_LINK (Create Link to an
             Object) procedure, since the last boot."
    ::= { tv3Calls 16 }

tv3cReaddirs OBJECT-TYPE
    SYNTAX          Counter32
    MAX-ACCESS      read-only
    STATUS          current
    DESCRIPTION     
            "The number of NFS Version 3 calls received
             for the NFSPROC3_READDIR (Read From Directory)
             procedure, since the last boot."
    ::= { tv3Calls 17 }

tv3cReaddirPluss OBJECT-TYPE
    SYNTAX          Counter32
    MAX-ACCESS      read-only
    STATUS          current
    DESCRIPTION     
            "The number of NFS Version 3 calls received
             for the NFSPROC3_READDIRPLUS (Extended Read
             from Directory) procedure, since the last boot."
    ::= { tv3Calls 18 }

tv3cFsstats OBJECT-TYPE
    SYNTAX          Counter32
    MAX-ACCESS      read-only
    STATUS          current
    DESCRIPTION     
            "The number of NFS Version 3 calls received
             for the NFSPROC3_FSSTAT (Get Dynamic File
             System Information) procedure, since the
             last boot."
    ::= { tv3Calls 19 }

tv3cFsinfos OBJECT-TYPE
    SYNTAX          Counter32
    MAX-ACCESS      read-only
    STATUS          current
    DESCRIPTION     
            "The number of NFS Version 3 calls received
             for the NFSPROC3_FSINFO (Get Static File System
             Information) procedure, since the last boot."
    ::= { tv3Calls 20 }

tv3cPathconfs OBJECT-TYPE
    SYNTAX          Counter32
    MAX-ACCESS      read-only
    STATUS          current
    DESCRIPTION     
            "The number of NFS Version 3 calls received
             for the NFSPROC3_PATHCONF (Retrieve POSIX
             Information) procedure, since the last boot."
    ::= { tv3Calls 21 }

tv3cCommits OBJECT-TYPE
    SYNTAX          Counter32
    MAX-ACCESS      read-only
    STATUS          current
    DESCRIPTION     
            "The number of NFS Version 3 calls received
             for the NFSPROC3_COMMIT (Commit Cached Data on
             a Server to Stable Storage) procedure, since
             the last boot."
    ::= { tv3Calls 22 }

tv3Percent OBJECT IDENTIFIER
    ::= { tnfsV3 2 }

tv3pNulls OBJECT-TYPE
    SYNTAX          Integer32 (0..100)
    MAX-ACCESS      read-only
    STATUS          current
    DESCRIPTION     
            "The number of NFS Version 3 calls received
             for the NFSPROC3_NULL (Do Nothing) procedure,
             as a percentage of the total NFS calls
             received, since the last boot."
    ::= { tv3Percent 1 }

tv3pGetattrs OBJECT-TYPE
    SYNTAX          Integer32 (0..100)
    MAX-ACCESS      read-only
    STATUS          current
    DESCRIPTION     
            "The number of NFS Version 3 calls received
             for the NFSPROC3_GETATTR (Get File Attributes)
             procedure, as a percentage of the total NFS
             calls received, since the last boot."
    ::= { tv3Percent 2 }

tv3pSetattrs OBJECT-TYPE
    SYNTAX          Integer32 (0..100)
    MAX-ACCESS      read-only
    STATUS          current
    DESCRIPTION     
            "The number of NFS Version 3 calls received
             for the NFSPROC3_SETATTR (Set File Attributes)
             procedure, as a percentage of the total NFS
             calls received, since the last boot."
    ::= { tv3Percent 3 }

tv3pLookups OBJECT-TYPE
    SYNTAX          Integer32 (0..100)
    MAX-ACCESS      read-only
    STATUS          current
    DESCRIPTION     
            "The number of NFS Version 3 calls received
             for the NFSPROC3_LOOKUP (Lookup Filename)
             procedure, as a percentage of the total NFS
             calls received, since the last boot."
    ::= { tv3Percent 4 }

tv3pAccesss OBJECT-TYPE
    SYNTAX          Integer32 (0..100)
    MAX-ACCESS      read-only
    STATUS          current
    DESCRIPTION     
            "The number of NFS Version 3 calls received
             for the NFSPROC3_ACCESS (Check Access
             Permission) procedure, as a percentage of
             the total NFS calls received, since the last boot."
    ::= { tv3Percent 5 }

tv3pReadlinks OBJECT-TYPE
    SYNTAX          Integer32 (0..100)
    MAX-ACCESS      read-only
    STATUS          current
    DESCRIPTION     
            "The number of NFS Version 3 calls received
             for the NFSPROC3_READLINK (Read from Symbolic
             Link) procedure, as a percentage of the total
             NFS calls received, since the last boot."
    ::= { tv3Percent 6 }

tv3pReads OBJECT-TYPE
    SYNTAX          Integer32 (0..100)
    MAX-ACCESS      read-only
    STATUS          current
    DESCRIPTION     
            "The number of NFS Version 3 calls received
             for the NFSPROC3_READ (Read From File)
             procedure, as a percentage of the total NFS
             calls received, since the last boot."
    ::= { tv3Percent 7 }

tv3pWrites OBJECT-TYPE
    SYNTAX          Integer32 (0..100)
    MAX-ACCESS      read-only
    STATUS          current
    DESCRIPTION     
            "The number of NFS Version 3 calls received
             for the NFSPROC3_WRITE (Write to File)
             procedure, as a percentage of the total NFS
             calls received, since the last boot."
    ::= { tv3Percent 8 }

tv3pCreates OBJECT-TYPE
    SYNTAX          Integer32 (0..100)
    MAX-ACCESS      read-only
    STATUS          current
    DESCRIPTION     
            "The number of NFS Version 3 calls received
             for the NFSPROC3_CREATE (Create a File)
             procedure, as a percentage of the total NFS
             calls received, since the last boot."
    ::= { tv3Percent 9 }

tv3pMkdirs OBJECT-TYPE
    SYNTAX          Integer32 (0..100)
    MAX-ACCESS      read-only
    STATUS          current
    DESCRIPTION     
            "The number of NFS Version 3 calls received
             for the NFSPROC3_MKDIR (Create a Directory)
             procedure, as a percentage of the total NFS
             calls received, since the last boot."
    ::= { tv3Percent 10 }

tv3pSymlinks OBJECT-TYPE
    SYNTAX          Integer32 (0..100)
    MAX-ACCESS      read-only
    STATUS          current
    DESCRIPTION     
            "The number of NFS Version 3 calls received
             for the NFSPROC3_SYMLINK (Create a Symbolic
             Link) procedure, as a percentage of the total
             NFS calls received, since the last boot."
    ::= { tv3Percent 11 }

tv3pMknods OBJECT-TYPE
    SYNTAX          Integer32 (0..100)
    MAX-ACCESS      read-only
    STATUS          current
    DESCRIPTION     
            "The number of NFS Version 3 calls received
             for the NFSPROC3_MKNOD (Create a Special
             Device) procedure, as a percentage of the
             total NFS calls received, since the last boot."
    ::= { tv3Percent 12 }

tv3pRemoves OBJECT-TYPE
    SYNTAX          Integer32 (0..100)
    MAX-ACCESS      read-only
    STATUS          current
    DESCRIPTION     
            "The number of NFS Version 3 calls received
             for the NFSPROC3_REMOVE (Remove a File)
             procedure, as a percentage of the total NFS
             calls received, since the last boot."
    ::= { tv3Percent 13 }

tv3pRmdirs OBJECT-TYPE
    SYNTAX          Integer32 (0..100)
    MAX-ACCESS      read-only
    STATUS          current
    DESCRIPTION     
            "The number of NFS Version 3 calls received
             for the NFSPROC3_RMDIR (Remove a Directory)
             procedure, as a percentage of the total NFS
             calls received, since the last boot."
    ::= { tv3Percent 14 }

tv3pRenames OBJECT-TYPE
    SYNTAX          Integer32 (0..100)
    MAX-ACCESS      read-only
    STATUS          current
    DESCRIPTION     
            "The number of NFS Version 3 calls received
             for the NFSPROC3_RENAME (Rename a File or
             Directory) procedure, as a percentage of
             the total NFS calls received, since the
             last boot."
    ::= { tv3Percent 15 }

tv3pLinks OBJECT-TYPE
    SYNTAX          Integer32 (0..100)
    MAX-ACCESS      read-only
    STATUS          current
    DESCRIPTION     
            "The number of NFS Version 3 calls received
             for the NFSPROC3_LINK (Create Link to an
             Object) procedure, as a percentage of
             the total NFS calls received, since the
             last boot."
    ::= { tv3Percent 16 }

tv3pReaddirs OBJECT-TYPE
    SYNTAX          Integer32 (0..100)
    MAX-ACCESS      read-only
    STATUS          current
    DESCRIPTION     
            "The number of NFS Version 3 calls received
             for the NFSPROC3_READDIR (Read From Directory)
             procedure, as a percentage of the total NFS
             calls received, since the last boot."
    ::= { tv3Percent 17 }

tv3pReaddirPluss OBJECT-TYPE
    SYNTAX          Integer32 (0..100)
    MAX-ACCESS      read-only
    STATUS          current
    DESCRIPTION     
            "The number of NFS Version 3 calls received
             for the NFSPROC3_READDIRPLUS (Extended Read
             from Directory) procedure, as a percentage
             of the total NFS calls received, since the
             last boot."
    ::= { tv3Percent 18 }

tv3pFsstats OBJECT-TYPE
    SYNTAX          Integer32 (0..100)
    MAX-ACCESS      read-only
    STATUS          current
    DESCRIPTION     
            "The number of NFS Version 3 calls received
             for the NFSPROC3_FSSTAT (Get Dynamic File
             System Information) procedure, as a percentage
             of the total NFS calls received, since the
             last boot."
    ::= { tv3Percent 19 }

tv3pFsinfos OBJECT-TYPE
    SYNTAX          Integer32 (0..100)
    MAX-ACCESS      read-only
    STATUS          current
    DESCRIPTION     
            "The number of NFS Version 3 calls received
             for the NFSPROC3_FSINFO (Get Static File System
             Information) procedure, as a percentage of the
             total NFS calls received, since the last boot."
    ::= { tv3Percent 20 }

tv3pPathconfs OBJECT-TYPE
    SYNTAX          Integer32 (0..100)
    MAX-ACCESS      read-only
    STATUS          current
    DESCRIPTION     
            "The number of NFS Version 3 calls received
             for the NFSPROC3_PATHCONF (Retrieve POSIX
             Information) procedure, as a percentage of the
             total NFS calls received, since the last boot."
    ::= { tv3Percent 21 }

tv3pCommits OBJECT-TYPE
    SYNTAX          Integer32 (0..100)
    MAX-ACCESS      read-only
    STATUS          current
    DESCRIPTION     
            "The number of NFS Version 3 calls received
             for the NFSPROC3_COMMIT (Commit Cached Data on
             a Server to Stable Storage) procedure, as a
             percentage of the total NFS calls received,
             since the last boot."
    ::= { tv3Percent 22 }

tv3CachedCalls OBJECT IDENTIFIER
    ::= { tnfsV3 3 }

tv3ccNulls OBJECT-TYPE
    SYNTAX          Counter32
    MAX-ACCESS      read-only
    STATUS          current
    DESCRIPTION     
            "The number of NFS Version 3 calls received
             for the NFSPROC3_NULL (Do Nothing) procedure,
             that did not result in the filesystem blocking
             to read from disk, since the last boot."
    ::= { tv3CachedCalls 1 }

tv3ccGetattrs OBJECT-TYPE
    SYNTAX          Counter32
    MAX-ACCESS      read-only
    STATUS          current
    DESCRIPTION     
            "The number of NFS Version 3 calls received
             for the NFSPROC3_GETATTR (Get File Attributes)
             procedure, that did not result in the filesystem
             blocking to read from disk, since the last boot."
    ::= { tv3CachedCalls 2 }

tv3ccSetattrs OBJECT-TYPE
    SYNTAX          Counter32
    MAX-ACCESS      read-only
    STATUS          current
    DESCRIPTION     
            "The number of NFS Version 3 calls received
             for the NFSPROC3_SETATTR (Set File Attributes)
             procedure, that did not result in the filesystem
             blocking to read from disk, since the last boot."
    ::= { tv3CachedCalls 3 }

tv3ccLookups OBJECT-TYPE
    SYNTAX          Counter32
    MAX-ACCESS      read-only
    STATUS          current
    DESCRIPTION     
            "The number of NFS Version 3 calls received
             for the NFSPROC3_LOOKUP (Lookup Filename)
             procedure, that did not result in the filesystem
             blocking to read from disk, since the last boot."
    ::= { tv3CachedCalls 4 }

tv3ccAccesss OBJECT-TYPE
    SYNTAX          Counter32
    MAX-ACCESS      read-only
    STATUS          current
    DESCRIPTION     
            "The number of NFS Version 3 calls received
             for the NFSPROC3_ACCESS (Check Access Permission)
             procedure, that did not result in the filesystem
             blocking to read from disk, since the last boot."
    ::= { tv3CachedCalls 5 }

tv3ccReadlinks OBJECT-TYPE
    SYNTAX          Counter32
    MAX-ACCESS      read-only
    STATUS          current
    DESCRIPTION     
            "The number of NFS Version 3 calls received
             for the NFSPROC3_READLINK (Read from Symbolic
             Link) procedure, that did not result in the
             filesystem blocking to read from disk, since
             the last boot."
    ::= { tv3CachedCalls 6 }

tv3ccReads OBJECT-TYPE
    SYNTAX          Counter32
    MAX-ACCESS      read-only
    STATUS          current
    DESCRIPTION     
            "The number of NFS Version 3 calls received
             for the NFSPROC3_READ (Read From File)
             procedure, that did not result in the filesystem
             blocking to read from disk, since the last boot."
    ::= { tv3CachedCalls 7 }

tv3ccWrites OBJECT-TYPE
    SYNTAX          Counter32
    MAX-ACCESS      read-only
    STATUS          current
    DESCRIPTION     
            "The number of NFS Version 3 calls received
             for the NFSPROC3_WRITE (Write to File)
             procedure, that did not result in the filesystem
             blocking to read from disk, since the last boot."
    ::= { tv3CachedCalls 8 }

tv3ccCreates OBJECT-TYPE
    SYNTAX          Counter32
    MAX-ACCESS      read-only
    STATUS          current
    DESCRIPTION     
            "The number of NFS Version 3 calls received
             for the NFSPROC3_CREATE (Create a File)
             procedure, that did not result in the filesystem
             blocking to read from disk, since the last boot."
    ::= { tv3CachedCalls 9 }

tv3ccMkdirs OBJECT-TYPE
    SYNTAX          Counter32
    MAX-ACCESS      read-only
    STATUS          current
    DESCRIPTION     
            "The number of NFS Version 3 calls received
             for the NFSPROC3_MKDIR (Create a Directory)
             procedure, that did not result in the filesystem
             blocking to read from disk, since the last boot."
    ::= { tv3CachedCalls 10 }

tv3ccSymlinks OBJECT-TYPE
    SYNTAX          Counter32
    MAX-ACCESS      read-only
    STATUS          current
    DESCRIPTION     
            "The number of NFS Version 3 calls received
             for the NFSPROC3_SYMLINK (Create a Symbolic
             Link) procedure, that did not result in the
             filesystem blocking to read from disk, since
             the last boot."
    ::= { tv3CachedCalls 11 }

tv3ccMknods OBJECT-TYPE
    SYNTAX          Counter32
    MAX-ACCESS      read-only
    STATUS          current
    DESCRIPTION     
            "The number of NFS Version 3 calls received
             for the NFSPROC3_MKNOD (Create a Special
             Device) procedure, that did not result in the
             filesystem blocking to read from disk, since
             the last boot."
    ::= { tv3CachedCalls 12 }

tv3ccRemoves OBJECT-TYPE
    SYNTAX          Counter32
    MAX-ACCESS      read-only
    STATUS          current
    DESCRIPTION     
            "The number of NFS Version 3 calls received
             for the NFSPROC3_REMOVE (Remove a File)
             procedure, that did not result in the
             filesystem blocking to read from disk, 
             since the last boot."
    ::= { tv3CachedCalls 13 }

tv3ccRmdirs OBJECT-TYPE
    SYNTAX          Counter32
    MAX-ACCESS      read-only
    STATUS          current
    DESCRIPTION     
            "The number of NFS Version 3 calls received
             for the NFSPROC3_RMDIR (Remove a Directory)
             procedure, that did not result in the
             filesystem blocking to read from disk,
             since the last boot."
    ::= { tv3CachedCalls 14 }

tv3ccRenames OBJECT-TYPE
    SYNTAX          Counter32
    MAX-ACCESS      read-only
    STATUS          current
    DESCRIPTION     
            "The number of NFS Version 3 calls received
             for the NFSPROC3_RENAME (Rename a File or
             Directory) procedure, that did not result in
             the filesystem blocking to read from disk,
             since the last boot."
    ::= { tv3CachedCalls 15 }

tv3ccLinks OBJECT-TYPE
    SYNTAX          Counter32
    MAX-ACCESS      read-only
    STATUS          current
    DESCRIPTION     
            "The number of NFS Version 3 calls received
             for the NFSPROC3_LINK (Create Link to an
             Object) procedure, that did not result in
             the filesystem blocking to read from disk, 
             since the last boot."
    ::= { tv3CachedCalls 16 }

tv3ccReaddirs OBJECT-TYPE
    SYNTAX          Counter32
    MAX-ACCESS      read-only
    STATUS          current
    DESCRIPTION     
            "The number of NFS Version 3 calls received
             for the NFSPROC3_READDIR (Read From
             Directory) procedure, that did not result in
             the filesystem blocking to read from disk, 
             since the last boot."
    ::= { tv3CachedCalls 17 }

tv3ccReaddirPluss OBJECT-TYPE
    SYNTAX          Counter32
    MAX-ACCESS      read-only
    STATUS          current
    DESCRIPTION     
            "The number of NFS Version 3 calls received
             for the NFSPROC3_READDIRPLUS (Extended Read
             from Directory) procedure, that did not result in
             the filesystem blocking to read from disk, 
             since the last boot."
    ::= { tv3CachedCalls 18 }

tv3ccFsstats OBJECT-TYPE
    SYNTAX          Counter32
    MAX-ACCESS      read-only
    STATUS          current
    DESCRIPTION     
            "The number of NFS Version 3 calls received
             for the NFSPROC3_FSSTAT (Get Dynamic File
             System Information) procedure, that did not
             result in the filesystem blocking to read
             from disk, since the last boot."
    ::= { tv3CachedCalls 19 }

tv3ccFsinfos OBJECT-TYPE
    SYNTAX          Counter32
    MAX-ACCESS      read-only
    STATUS          current
    DESCRIPTION     
            "The number of NFS Version 3 calls received
             for the NFSPROC3_FSINFO (Get Static File
             System Information) procedure, that did not
             result in the filesystem blocking to read
             from disk, since the last boot."
    ::= { tv3CachedCalls 20 }

tv3ccPathconfs OBJECT-TYPE
    SYNTAX          Counter32
    MAX-ACCESS      read-only
    STATUS          current
    DESCRIPTION     
            "The number of NFS Version 3 calls received
             for the NFSPROC3_PATHCONF (Retrieve POSIX
             Information) procedure, that did not result
             in the filesystem blocking to read from disk,
             since the last boot."
    ::= { tv3CachedCalls 21 }

tv3ccCommits OBJECT-TYPE
    SYNTAX          Counter32
    MAX-ACCESS      read-only
    STATUS          current
    DESCRIPTION     
            "The number of NFS Version 3 calls received
             for the NFSPROC3_COMMIT (Commit Cached Data on
             a Server to Stable Storage) procedure, that did
             not result in the filesystem blocking to read
             from disk, since the last boot."
    ::= { tv3CachedCalls 22 }

tv3CachedPerCent OBJECT IDENTIFIER
    ::= { tnfsV3 4 }

tv3cpNulls OBJECT-TYPE
    SYNTAX          Integer32 (0..100)
    MAX-ACCESS      read-only
    STATUS          current
    DESCRIPTION     
            "The number of NFS Version 3 calls received
             for the NFSPROC3_NULL (Do Nothing) procedure,
             that did not result in the filesystem
             blocking to read from disk, as a percentage
             of the total number of calls received for
             this procedure, since the last boot."
    ::= { tv3CachedPerCent 1 }

tv3cpGetattrs OBJECT-TYPE
    SYNTAX          Integer32 (0..100)
    MAX-ACCESS      read-only
    STATUS          current
    DESCRIPTION     
            "The number of NFS Version 3 calls received
             for the NFSPROC3_GETATTR (Get File Attributes)
             procedure, that did not result in the filesystem
             blocking to read from disk, as a percentage
             of the total number of calls received for
             this procedure, since the last boot."
    ::= { tv3CachedPerCent 2 }

tv3cpSetattrs OBJECT-TYPE
    SYNTAX          Integer32 (0..100)
    MAX-ACCESS      read-only
    STATUS          current
    DESCRIPTION     
            "The number of NFS Version 3 calls received
             for the NFSPROC3_SETATTR (Set File Attributes)
             procedure, that did not result in the filesystem
             blocking to read from disk, as a percentage
             of the total number of calls received for
             this procedure, since the last boot."
    ::= { tv3CachedPerCent 3 }

tv3cpLookups OBJECT-TYPE
    SYNTAX          Integer32 (0..100)
    MAX-ACCESS      read-only
    STATUS          current
    DESCRIPTION     
            "The number of NFS Version 3 calls received
             for the NFSPROC3_LOOKUP (Lookup Filename)
             procedure, that did not result in the filesystem
             blocking to read from disk, as a percentage
             of the total number of calls received for
             this procedure, since the last boot."
    ::= { tv3CachedPerCent 4 }

tv3cpAccesss OBJECT-TYPE
    SYNTAX          Integer32 (0..100)
    MAX-ACCESS      read-only
    STATUS          current
    DESCRIPTION     
            "The number of NFS Version 3 calls received
             for the NFSPROC3_ACCESS (Check Access Permission)
             procedure, that did not result in the filesystem
             blocking to read from disk, as a percentage
             of the total number of calls received for
             this procedure, since the last boot."
    ::= { tv3CachedPerCent 5 }

tv3cpReadlinks OBJECT-TYPE
    SYNTAX          Integer32 (0..100)
    MAX-ACCESS      read-only
    STATUS          current
    DESCRIPTION     
            "The number of NFS Version 3 calls received
             for the NFSPROC3_READLINK (Read from Symbolic
             Link) procedure, that did not result in the
             filesystem blocking to read from disk, as a
             percentage of the total number of calls
             received for this procedure, since the last
             last boot."
    ::= { tv3CachedPerCent 6 }

tv3cpReads OBJECT-TYPE
    SYNTAX          Integer32 (0..100)
    MAX-ACCESS      read-only
    STATUS          current
    DESCRIPTION     
            "The number of NFS Version 3 calls received
             for the NFSPROC3_READ (Read From File)
             procedure, that did not result in the
             filesystem blocking to read from disk, as a
             percentage of the total number of calls
             received for this procedure, since the last boot."
    ::= { tv3CachedPerCent 7 }

tv3cpWrites OBJECT-TYPE
    SYNTAX          Integer32 (0..100)
    MAX-ACCESS      read-only
    STATUS          current
    DESCRIPTION     
            "The number of NFS Version 3 calls received
             for the NFSPROC3_WRITE (Write to File)
             procedure, that did not result in the
             filesystem blocking to read from disk, as a
             percentage of the total number of calls
             received for this procedure, since the last boot."
    ::= { tv3CachedPerCent 8 }

tv3cpCreates OBJECT-TYPE
    SYNTAX          Integer32 (0..100)
    MAX-ACCESS      read-only
    STATUS          current
    DESCRIPTION     
            "The number of NFS Version 3 calls received
             for the NFSPROC3_CREATE (Create a File)
             procedure, that did not result in the
             filesystem blocking to read from disk, as a
             percentage of the total number of calls
             received for this procedure, since the last boot."
    ::= { tv3CachedPerCent 9 }

tv3cpMkdirs OBJECT-TYPE
    SYNTAX          Integer32 (0..100)
    MAX-ACCESS      read-only
    STATUS          current
    DESCRIPTION     
            "The number of NFS Version 3 calls received
             for the NFSPROC3_MKDIR (Create a Directory)
             procedure, that did not result in the
             filesystem blocking to read from disk, as a
             percentage of the total number of calls
             received for this procedure, since the last boot."
    ::= { tv3CachedPerCent 10 }

tv3cpSymlinks OBJECT-TYPE
    SYNTAX          Integer32 (0..100)
    MAX-ACCESS      read-only
    STATUS          current
    DESCRIPTION     
            "The number of NFS Version 3 calls received
             for the NFSPROC3_SYMLINK (Create a Symbolic
             Link) procedure, that did not result in the
             filesystem blocking to read from disk, as a
             percentage of the total number of calls
             received for this procedure, since the last boot."
    ::= { tv3CachedPerCent 11 }

tv3cpMknods OBJECT-TYPE
    SYNTAX          Integer32 (0..100)
    MAX-ACCESS      read-only
    STATUS          current
    DESCRIPTION     
            "The number of NFS Version 3 calls received
             for the NFSPROC3_MKNOD (Create a Special
             Device) procedure, that did not result in the
             filesystem blocking to read from disk, as a
             percentage of the total number of calls
             received for this procedure, since the last boot."
    ::= { tv3CachedPerCent 12 }

tv3cpRemoves OBJECT-TYPE
    SYNTAX          Integer32 (0..100)
    MAX-ACCESS      read-only
    STATUS          current
    DESCRIPTION     
            "The number of NFS Version 3 calls received
             for the NFSPROC3_REMOVE (Remove a File)
             procedure, that did not result in the
             filesystem blocking to read from disk, as a
             percentage of the total number of calls
             received for this procedure, since the last boot."
    ::= { tv3CachedPerCent 13 }

tv3cpRmdirs OBJECT-TYPE
    SYNTAX          Integer32 (0..100)
    MAX-ACCESS      read-only
    STATUS          current
    DESCRIPTION     
            "The number of NFS Version 3 calls received
             for the NFSPROC3_RMDIR (Remove a Directory)
             procedure, that did not result in the
             filesystem blocking to read from disk, as a
             percentage of the total number of calls
             received for this procedure, since the last boot."
    ::= { tv3CachedPerCent 14 }

tv3cpRenames OBJECT-TYPE
    SYNTAX          Integer32 (0..100)
    MAX-ACCESS      read-only
    STATUS          current
    DESCRIPTION     
            "The number of NFS Version 3 calls received
             for the NFSPROC3_RENAME (Rename a File or
             Directory) procedure, that did not result in
             the filesystem blocking to read from disk,
             as a percentage of the total number of calls
             received for this procedure, since the last boot."
    ::= { tv3CachedPerCent 15 }

tv3cpLinks OBJECT-TYPE
    SYNTAX          Integer32 (0..100)
    MAX-ACCESS      read-only
    STATUS          current
    DESCRIPTION     
            "The number of NFS Version 3 calls received
             for the NFSPROC3_LINK (Create Link to an
             Object) procedure, that did not result in
             the filesystem blocking to read from disk,
             as a percentage of the total number of calls
             received for this procedure, since the last boot."
    ::= { tv3CachedPerCent 16 }

tv3cpReaddirs OBJECT-TYPE
    SYNTAX          Integer32 (0..100)
    MAX-ACCESS      read-only
    STATUS          current
    DESCRIPTION     
            "The number of NFS Version 3 calls received
             for the NFSPROC3_READDIR (Read From Directory)
             procedure, that did not result in the
             filesystem blocking to read from disk, as a
             percentage of the total number of calls
             received for this procedure, since the last boot."
    ::= { tv3CachedPerCent 17 }

tv3cpReaddirPluss OBJECT-TYPE
    SYNTAX          Integer32 (0..100)
    MAX-ACCESS      read-only
    STATUS          current
    DESCRIPTION     
            "The number of NFS Version 3 calls received
             for the NFSPROC3_READDIRPLUS (Extended Read
             from Directory) procedure, that did not result
             in the filesystem blocking to read from disk,
             as a percentage of the total number of calls
             received for this procedure, since the last boot."
    ::= { tv3CachedPerCent 18 }

tv3cpFsstats OBJECT-TYPE
    SYNTAX          Integer32 (0..100)
    MAX-ACCESS      read-only
    STATUS          current
    DESCRIPTION     
            "The number of NFS Version 3 calls received
             for the NFSPROC3_FSSTAT (Get Dynamic File
             System Information) procedure, that did not
             result in the filesystem blocking to read from
             disk, as a percentage of the total number of
             calls received for this procedure, since the
             last boot."
    ::= { tv3CachedPerCent 19 }

tv3cpFsinfos OBJECT-TYPE
    SYNTAX          Integer32 (0..100)
    MAX-ACCESS      read-only
    STATUS          current
    DESCRIPTION     
            "The number of NFS Version 3 calls received
             for the NFSPROC3_FSINFO (Get Static File System
             Information) procedure, that did not result
             in the filesystem blocking to read from disk,
             as a percentage of the total number of calls
             received for this procedure, since the last boot."
    ::= { tv3CachedPerCent 20 }

tv3cpPathconfs OBJECT-TYPE
    SYNTAX          Integer32 (0..100)
    MAX-ACCESS      read-only
    STATUS          current
    DESCRIPTION     
            "The number of NFS Version 3 calls received
             for the NFSPROC3_PATHCONF (Retrieve POSIX
             Information) procedure, that did not result
             in the filesystem blocking to read from disk,
             as a percentage of the total number of calls
             received for this procedure, since the last boot."
    ::= { tv3CachedPerCent 21 }

tv3cpCommits OBJECT-TYPE
    SYNTAX          Integer32 (0..100)
    MAX-ACCESS      read-only
    STATUS          current
    DESCRIPTION     
            "The number of NFS Version 3 calls received
             for the NFSPROC3_COMMIT (Commit Cached Data on
             a Server to Stable Storage) procedure, that
             did not result in the filesystem blocking to
             read from disk, as a percentage of the total
             number of calls received for this procedure,
             since the last boot."
    ::= { tv3CachedPerCent 22 }

treplyCache OBJECT IDENTIFIER
    ::= { tnfsServ 5 }

trcInProgressHits OBJECT-TYPE
    SYNTAX          Counter32
    MAX-ACCESS      read-only
    STATUS          current
    DESCRIPTION     
            "The number of NFS requests that were dropped, for
             calls already in progress, since the last boot."
    ::= { treplyCache 1 }

trcDelayHits OBJECT-TYPE
    SYNTAX          Counter32
    MAX-ACCESS      read-only
    STATUS          current
    DESCRIPTION     
            "The number of NFS requests that were dropped,
             for replies already generated within a short
             interval, since the last boot."
    ::= { treplyCache 2 }

trcMisses OBJECT-TYPE
    SYNTAX          Counter32
    MAX-ACCESS      read-only
    STATUS          current
    DESCRIPTION     
            "The number of NFS requests received for which
             there were no corresponding entries already in
             the Reply Cache, since the last boot."
    ::= { treplyCache 3 }

trcNonIdemDoneHits OBJECT-TYPE
    SYNTAX          Counter32
    MAX-ACCESS      read-only
    STATUS          current
    DESCRIPTION     
            "The number of NFS requests received that
             resulted in replies being replayed from
             the Reply Cache, since the last boot."
    ::= { treplyCache 4 }

trcNonIdemNotDoneHits OBJECT-TYPE
    SYNTAX          Counter32
    MAX-ACCESS      read-only
    STATUS          current
    DESCRIPTION     
            "The number of NFS requests received for calls
             that resulted in this request being processed
             as a new request even when a corresponding
             entry existed in the Reply Cache, since the
             last boot."
    ::= { treplyCache 5 }

quota OBJECT IDENTIFIER
    ::= { netapp1 4 }

quotaState OBJECT-TYPE
    SYNTAX          INTEGER { quotaStateOff(1), quotaStateOn(2), 
                        quotaStateInit(3) }
    MAX-ACCESS      read-only
    STATUS          obsolete
    DESCRIPTION     
            "Indicates whether the root volume's quotas are ON, 
             OFF or initializing.  This object is deprecated -
             use qvStateTable.qvStateStat instead."
    ::= { quota 1 }

quotaInitPercent OBJECT-TYPE
    SYNTAX          Integer32 (0..100)
    MAX-ACCESS      read-only
    STATUS          obsolete
    DESCRIPTION     
            "Indicates percentage of root volume quota 
             computation done while quotas are in initializing 
             state. This object is deprecated - use 
             qvStateTable.qvInitPercent instead."
    ::= { quota 2 }

qrTable OBJECT-TYPE
    SYNTAX          SEQUENCE OF QrEntry
    MAX-ACCESS      not-accessible
    STATUS          obsolete
    DESCRIPTION     
            "Provide a report of the current file and
             space consumption for each user or group with
             a quota in /etc/quotas.  All quotas are displayed
             regardless of volume, and no volume information
             is given.  This table is deprecated - use qrVTable 
             instead."
    ::= { quota 3 }

qrEntry OBJECT-TYPE
    SYNTAX          QrEntry
    MAX-ACCESS      not-accessible
    STATUS          obsolete
    DESCRIPTION     
            "Provide a report of the current file and
             space consumption for a referenced entry
             with a quota in the file /etc/quotas.
             All quotas are displayed regardless of volume, 
             and no volume information is given.  This object is 
             deprecated - use qrVEntry instead."
    INDEX           { qrIndex }
    ::= { qrTable 1 }

QrEntry ::=
    SEQUENCE {
        qrIndex                         Integer32,
        qrType                          INTEGER,
        qrId                            Integer32,
        qrKBytesUsed                    Integer32,
        qrKBytesLimit                   Integer32,
        qrFilesUsed                     Integer32,
        qrFileLimit                     Integer32,
        qrPathName                      DisplayString
    }

qrIndex OBJECT-TYPE
    SYNTAX          Integer32
    MAX-ACCESS      read-only
    STATUS          obsolete
    DESCRIPTION     
            "A number that identifies this entry in the
             file /etc/quotas."
    ::= { qrEntry 1 }

qrType OBJECT-TYPE
    SYNTAX          INTEGER { qrTypeUser(1), qrTypeGroup(2), 
                        qrTypeTree(3), qrTypeUnknown(4) }
    MAX-ACCESS      read-only
    STATUS          obsolete
    DESCRIPTION     
            "Identifies the kind of quota for this qrEntry."
    ::= { qrEntry 2 }

qrId OBJECT-TYPE
    SYNTAX          Integer32
    MAX-ACCESS      read-only
    STATUS          obsolete
    DESCRIPTION     
            "The UID (user's numerical ID) or the GID (numerical
             ID of  the  group  that a user belongs to), as
             applicable, associated with this qrEntry."
    ::= { qrEntry 3 }

qrKBytesUsed OBJECT-TYPE
    SYNTAX          Integer32
    MAX-ACCESS      read-only
    STATUS          obsolete
    DESCRIPTION     
            "The current number of KBytes used for this
             qrEntry."
    ::= { qrEntry 4 }

qrKBytesLimit OBJECT-TYPE
    SYNTAX          Integer32
    MAX-ACCESS      read-only
    STATUS          obsolete
    DESCRIPTION     
            "The limit of KBytes that can be used for this
             qrEntry."
    ::= { qrEntry 5 }

qrFilesUsed OBJECT-TYPE
    SYNTAX          Integer32
    MAX-ACCESS      read-only
    STATUS          obsolete
    DESCRIPTION     
            "The current number of files used for this
             qrEntry."
    ::= { qrEntry 6 }

qrFileLimit OBJECT-TYPE
    SYNTAX          Integer32
    MAX-ACCESS      read-only
    STATUS          obsolete
    DESCRIPTION     
            "The limit of files that can be used for this
             qrEntry."
    ::= { qrEntry 7 }

qrPathName OBJECT-TYPE
    SYNTAX          DisplayString
    MAX-ACCESS      read-only
    STATUS          obsolete
    DESCRIPTION     
            "A textual string that contains the path
             corresponding to this qrEntry."
    ::= { qrEntry 8 }

qvStateTable OBJECT-TYPE
    SYNTAX          SEQUENCE OF QvStateEntry
    MAX-ACCESS      not-accessible
    STATUS          current
    DESCRIPTION     
            "Provide a report of the current quota state of
             each volume in the system."
    ::= { quota 4 }

qvStateEntry OBJECT-TYPE
    SYNTAX          QvStateEntry
    MAX-ACCESS      not-accessible
    STATUS          current
    DESCRIPTION     
            "Provide a report of the current quota state of
             each volume in the system."
    INDEX           { qvStateVolume }
    ::= { qvStateTable 1 }

QvStateEntry ::=
    SEQUENCE {
        qvStateVolume                   Integer32,
        qvStateName                     DisplayString,
        qvStateStat                     INTEGER,
        qvStateInitPercent              Integer32
    }

qvStateVolume OBJECT-TYPE
    SYNTAX          Integer32
    MAX-ACCESS      read-only
    STATUS          current
    DESCRIPTION     
            "A number that identifies this volume.  The mapping
             of this number to actual volumes may change if 
             volumes are added or deleted.  Use qvStateName to 
             unambiguously identify a volume.  The mapping
             established by this object is the same as 
             the mapping of qrVVolume (below) to actual volumes.
             For instance, if a qvStateVolume value of '5'
             represents the volume 'vol2', a value of '5'
             in qrVVolume also represents the volume 'vol2'."
    ::= { qvStateEntry 1 }

qvStateName OBJECT-TYPE
    SYNTAX          DisplayString
    MAX-ACCESS      read-only
    STATUS          current
    DESCRIPTION     
            "Indicates the name of this volume."
    ::= { qvStateEntry 2 }

qvStateStat OBJECT-TYPE
    SYNTAX          INTEGER { quotaStateOff(1), quotaStateOn(2), 
                        quotaStateInit(3) }
    MAX-ACCESS      read-only
    STATUS          current
    DESCRIPTION     
            "Indicates whether quotas are ON, OFF or
             initializing."
    ::= { qvStateEntry 3 }

qvStateInitPercent OBJECT-TYPE
    SYNTAX          Integer32 (0..100)
    MAX-ACCESS      read-only
    STATUS          current
    DESCRIPTION     
            "Indicates percentage of quota computation done
             while quotas are in initializing state."
    ::= { qvStateEntry 4 }

qrVTable OBJECT-TYPE
    SYNTAX          SEQUENCE OF QrVEntry
    MAX-ACCESS      not-accessible
    STATUS          current
    DESCRIPTION     
            "Provide a report of the current file and
             space consumption for each user or group with
             a quota in /etc/quotas."
    ::= { quota 5 }

qrVEntry OBJECT-TYPE
    SYNTAX          QrVEntry
    MAX-ACCESS      not-accessible
    STATUS          current
    DESCRIPTION     
            "Provide a report of the current file and
             space consumption for a referenced entry
             with a quota in the file /etc/quotas.  Indices
             select the volume of the quota and the quota entry
             itself."
    INDEX           { qrVVolume, qrVIndex }
    ::= { qrVTable 1 }

QrVEntry ::=
    SEQUENCE {
        qrVIndex                        Integer32,
        qrVType                         INTEGER,
        qrVId                           Integer32,
        qrVKBytesUsed                   Integer32,
        qrVKBytesLimit                  Integer32,
        qrVFilesUsed                    Integer32,
        qrVFileLimit                    Integer32,
        qrVPathName                     DisplayString,
        qrVVolume                       Integer32,
        qrVTree                         DisplayString
    }

qrVIndex OBJECT-TYPE
    SYNTAX          Integer32
    MAX-ACCESS      read-only
    STATUS          current
    DESCRIPTION     
            "A number that identifies this entry in the
             file /etc/quotas in the given volume."
    ::= { qrVEntry 1 }

qrVType OBJECT-TYPE
    SYNTAX          INTEGER { qrVTypeUser(1), qrVTypeGroup(2), 
                        qrVTypeTree(3), qrVTypeUserDefault(4), 
                        qrVTypeGroupDefault(5), qrVTypeUnknown(6) }
    MAX-ACCESS      read-only
    STATUS          current
    DESCRIPTION     
            "Identifies the kind of quota for this qrVEntry."
    ::= { qrVEntry 2 }

qrVId OBJECT-TYPE
    SYNTAX          Integer32
    MAX-ACCESS      read-only
    STATUS          current
    DESCRIPTION     
            "The UID (user's numerical ID) or the GID (numerical
             ID of  the  group  that a user belongs to), as
             applicable, associated with this qrVEntry."
    ::= { qrVEntry 3 }

qrVKBytesUsed OBJECT-TYPE
    SYNTAX          Integer32
    MAX-ACCESS      read-only
    STATUS          current
    DESCRIPTION     
            "The current number of KBytes used for this
             qrVEntry."
    ::= { qrVEntry 4 }

qrVKBytesLimit OBJECT-TYPE
    SYNTAX          Integer32
    MAX-ACCESS      read-only
    STATUS          current
    DESCRIPTION     
            "The limit of KBytes that can be used for this
             qrVEntry."
    ::= { qrVEntry 5 }

qrVFilesUsed OBJECT-TYPE
    SYNTAX          Integer32
    MAX-ACCESS      read-only
    STATUS          current
    DESCRIPTION     
            "The current number of files used for this
             qrVEntry."
    ::= { qrVEntry 6 }

qrVFileLimit OBJECT-TYPE
    SYNTAX          Integer32
    MAX-ACCESS      read-only
    STATUS          current
    DESCRIPTION     
            "The limit of files that can be used for this
             qrVEntry."
    ::= { qrVEntry 7 }

qrVPathName OBJECT-TYPE
    SYNTAX          DisplayString
    MAX-ACCESS      read-only
    STATUS          current
    DESCRIPTION     
            "A textual string that contains the path
             corresponding to this qrVEntry."
    ::= { qrVEntry 8 }

qrVVolume OBJECT-TYPE
    SYNTAX          Integer32
    MAX-ACCESS      read-only
    STATUS          current
    DESCRIPTION     
            "A number that identifies the volume for which
             this quota is in effect on.  The volume that this
             value represents can be determined by checking
             the value of qvStateName (above) with 
             qvStateVolume set to the value found here."
    ::= { qrVEntry 9 }

qrVTree OBJECT-TYPE
    SYNTAX          DisplayString
    MAX-ACCESS      read-only
    STATUS          current
    DESCRIPTION     
            "A string that indicates which qtree this quota
             belongs to."
    ::= { qrVEntry 10 }

filesys OBJECT IDENTIFIER
    ::= { netapp1 5 }

filesysMaxfilesAvail OBJECT-TYPE
    SYNTAX          Integer32
    MAX-ACCESS      read-only
    STATUS          obsolete
    DESCRIPTION     
            "The count of the maximum number of
             files allowable on the root volume.  This
             object is deprecated - use 
             dfEntry.dfMaxFilesAvail instead."
    ::= { filesys 1 }

filesysMaxfilesUsed OBJECT-TYPE
    SYNTAX          Integer32
    MAX-ACCESS      read-only
    STATUS          obsolete
    DESCRIPTION     
            "The count of the number of files
             currently in use on the root volume.  
             This object is deprecated - use
             dfEntry.dfMaxFilesUsed instead."
    ::= { filesys 2 }

filesysMaxfilesPossible OBJECT-TYPE
    SYNTAX          Integer32
    MAX-ACCESS      read-only
    STATUS          obsolete
    DESCRIPTION     
            "The largest value to which the
             filesysMaxfilesAvail parameter above can
             be increased by reconfiguration on the
             root volume.  This object is deprecated -
             use dfEntry.dfMaxFilesPossible."
    ::= { filesys 3 }

dfTable OBJECT-TYPE
    SYNTAX          SEQUENCE OF DfEntry
    MAX-ACCESS      not-accessible
    STATUS          current
    DESCRIPTION     
            "Provide a report of the available disk space
             on the file systems."
    ::= { filesys 4 }

dfEntry OBJECT-TYPE
    SYNTAX          DfEntry
    MAX-ACCESS      not-accessible
    STATUS          current
    DESCRIPTION     
            "Provide a report of the available disk space on
             the referenced file system."
    INDEX           { dfIndex }
    ::= { dfTable 1 }

DfEntry ::=
    SEQUENCE {
        dfIndex                         Integer32,
        dfFileSys                       DisplayString,
        dfKBytesTotal                   Integer32,
        dfKBytesUsed                    Integer32,
        dfKBytesAvail                   Integer32,
        dfPerCentKBytesCapacity         Integer32,
        dfInodesUsed                    Integer32,
        dfInodesFree                    Integer32,
        dfPerCentInodeCapacity          Integer32,
        dfMountedOn                     DisplayString,
        dfMaxFilesAvail                 Integer32,
        dfMaxFilesUsed                  Integer32,
        dfMaxFilesPossible              Integer32,
        dfHighTotalKBytes               Counter32,
        dfLowTotalKBytes                Counter32,
        dfHighUsedKBytes                Counter32,
        dfLowUsedKBytes                 Counter32,
        dfHighAvailKBytes               Counter32,
        dfLowAvailKBytes                Counter32
    }

dfIndex OBJECT-TYPE
    SYNTAX          Integer32
    MAX-ACCESS      read-only
    STATUS          current
    DESCRIPTION     
            "A number that identifies this entry for the
             referenced file system."
    ::= { dfEntry 1 }

dfFileSys OBJECT-TYPE
    SYNTAX          DisplayString
    MAX-ACCESS      read-only
    STATUS          current
    DESCRIPTION     
            "The name for the referenced file system."
    ::= { dfEntry 2 }

dfKBytesTotal OBJECT-TYPE
    SYNTAX          Integer32
    MAX-ACCESS      read-only
    STATUS          current
    DESCRIPTION     
            "The total capacity in KBytes for the
             referenced file system."
    ::= { dfEntry 3 }

dfKBytesUsed OBJECT-TYPE
    SYNTAX          Integer32
    MAX-ACCESS      read-only
    STATUS          current
    DESCRIPTION     
            "The total disk space in KBytes that is in use
             on the referenced file system."
    ::= { dfEntry 4 }

dfKBytesAvail OBJECT-TYPE
    SYNTAX          Integer32
    MAX-ACCESS      read-only
    STATUS          current
    DESCRIPTION     
            "The total disk space in KBytes that is
             free for use on the referenced file system."
    ::= { dfEntry 5 }

dfPerCentKBytesCapacity OBJECT-TYPE
    SYNTAX          Integer32
    MAX-ACCESS      read-only
    STATUS          current
    DESCRIPTION     
            "The percentage of disk space currently
             in use on the referenced file system."
    ::= { dfEntry 6 }

dfInodesUsed OBJECT-TYPE
    SYNTAX          Integer32
    MAX-ACCESS      read-only
    STATUS          current
    DESCRIPTION     
            "The total number of inodes in use on the
             referenced file system."
    ::= { dfEntry 7 }

dfInodesFree OBJECT-TYPE
    SYNTAX          Integer32
    MAX-ACCESS      read-only
    STATUS          current
    DESCRIPTION     
            "The total number of inodes that are
             available for use on the referenced
             file system."
    ::= { dfEntry 8 }

dfPerCentInodeCapacity OBJECT-TYPE
    SYNTAX          Integer32
    MAX-ACCESS      read-only
    STATUS          current
    DESCRIPTION     
            "The percentage of disk space currently
             in use based on inode counts, on the
             referenced file system."
    ::= { dfEntry 9 }

dfMountedOn OBJECT-TYPE
    SYNTAX          DisplayString
    MAX-ACCESS      read-only
    STATUS          current
    DESCRIPTION     
            "The name of the file on which this file
             system is mounted."
    ::= { dfEntry 10 }

dfMaxFilesAvail OBJECT-TYPE
    SYNTAX          Integer32
    MAX-ACCESS      read-only
    STATUS          current
    DESCRIPTION     
            "The count of the maximum number of
             files allowable on the referenced file
             system."
    ::= { dfEntry 11 }

dfMaxFilesUsed OBJECT-TYPE
    SYNTAX          Integer32
    MAX-ACCESS      read-only
    STATUS          current
    DESCRIPTION     
            "The count of the number of files
             currently in use on the referenced file
             system."
    ::= { dfEntry 12 }

dfMaxFilesPossible OBJECT-TYPE
    SYNTAX          Integer32
    MAX-ACCESS      read-only
    STATUS          current
    DESCRIPTION     
            "The largest value to which the
             filesysMaxfilesAvail parameter above can
             be increased by reconfiguration on the
             referenced file system."
    ::= { dfEntry 13 }

dfHighTotalKBytes OBJECT-TYPE
    SYNTAX          Counter32
    MAX-ACCESS      read-only
    STATUS          current
    DESCRIPTION     
            "The total capacity in KBytes for the
             referenced file system.  This object returns
             the most significant 32 bits of the value."
    ::= { dfEntry 14 }

dfLowTotalKBytes OBJECT-TYPE
    SYNTAX          Counter32
    MAX-ACCESS      read-only
    STATUS          current
    DESCRIPTION     
            "The total capacity in KBytes for the
             referenced file system.  This object returns
             the least significant 32 bits of the value."
    ::= { dfEntry 15 }

dfHighUsedKBytes OBJECT-TYPE
    SYNTAX          Counter32
    MAX-ACCESS      read-only
    STATUS          current
    DESCRIPTION     
            "The total disk space in KBytes that is in use
             on the referenced file system.  This object
             returns the most significant 32 bits of the
             value."
    ::= { dfEntry 16 }

dfLowUsedKBytes OBJECT-TYPE
    SYNTAX          Counter32
    MAX-ACCESS      read-only
    STATUS          current
    DESCRIPTION     
            "The total disk space in KBytes that is in use
             on the referenced file system.  This object
             returns the least significant 32 bits of the
             value."
    ::= { dfEntry 17 }

dfHighAvailKBytes OBJECT-TYPE
    SYNTAX          Counter32
    MAX-ACCESS      read-only
    STATUS          current
    DESCRIPTION     
            "The total disk space in KBytes that is free
             for use on the referenced file system.
             This object returns the most significant
             32 bits of the value."
    ::= { dfEntry 18 }

dfLowAvailKBytes OBJECT-TYPE
    SYNTAX          Counter32
    MAX-ACCESS      read-only
    STATUS          current
    DESCRIPTION     
            "The total disk space in KBytes that is free
             for use on the referenced file system.
             This object returns the least significant
             32 bits of the value."
    ::= { dfEntry 19 }

snapshot OBJECT IDENTIFIER
    ::= { filesys 5 }

slTable OBJECT-TYPE
    SYNTAX          SEQUENCE OF SlEntry
    MAX-ACCESS      not-accessible
    STATUS          obsolete
    DESCRIPTION     
            "Provide a report of the snapshots on the
             root volume.  This table is deprecated - use
             slVTable instead."
    ::= { snapshot 1 }

slEntry OBJECT-TYPE
    SYNTAX          SlEntry
    MAX-ACCESS      not-accessible
    STATUS          obsolete
    DESCRIPTION     
            "Provide a report on a given snapshot on the
             root volume.  This object is deprecated - use
             slVEntry instead."
    INDEX           { slIndex }
    ::= { slTable 1 }

SlEntry ::=
    SEQUENCE {
        slIndex                         Integer32,
        slMonth                         INTEGER,
        slDay                           Integer32,
        slHour                          Integer32,
        slMinutes                       Integer32,
        slName                          DisplayString
    }

slIndex OBJECT-TYPE
    SYNTAX          Integer32
    MAX-ACCESS      read-only
    STATUS          obsolete
    DESCRIPTION     
            "A number that identifies this entry for the
             referenced file system."
    ::= { slEntry 1 }

slMonth OBJECT-TYPE
    SYNTAX          INTEGER { january(1), february(2), march(3), 
                        april(4), may(5), june(6), july(7), august(8), 
                        september(9), october(10), november(11), 
                        december(12) }
    MAX-ACCESS      read-only
    STATUS          obsolete
    DESCRIPTION     
            "The month in which the snapshot was created."
    ::= { slEntry 2 }

slDay OBJECT-TYPE
    SYNTAX          Integer32 (1..31)
    MAX-ACCESS      read-only
    STATUS          obsolete
    DESCRIPTION     
            "The day on which the snapshot was created."
    ::= { slEntry 3 }

slHour OBJECT-TYPE
    SYNTAX          Integer32 (0..23)
    MAX-ACCESS      read-only
    STATUS          obsolete
    DESCRIPTION     
            "The hour in which the snapshot was created."
    ::= { slEntry 4 }

slMinutes OBJECT-TYPE
    SYNTAX          Integer32 (0..59)
    MAX-ACCESS      read-only
    STATUS          obsolete
    DESCRIPTION     
            "The minute in which the snapshot was created."
    ::= { slEntry 5 }

slName OBJECT-TYPE
    SYNTAX          DisplayString
    MAX-ACCESS      read-only
    STATUS          obsolete
    DESCRIPTION     
            "The name of the referenced snapshot."
    ::= { slEntry 6 }

slVTable OBJECT-TYPE
    SYNTAX          SEQUENCE OF SlVEntry
    MAX-ACCESS      not-accessible
    STATUS          current
    DESCRIPTION     
            "Provide a report of the snapshots on the
             file systems."
    ::= { snapshot 2 }

slVEntry OBJECT-TYPE
    SYNTAX          SlVEntry
    MAX-ACCESS      not-accessible
    STATUS          current
    DESCRIPTION     
            "Provide a report on a given snapshot on the
             file system.  Indices select the volume of
             the snapshot and the snapshot entry itself."
    INDEX           { slVVolume, slVIndex }
    ::= { slVTable 1 }

SlVEntry ::=
    SEQUENCE {
        slVIndex                        Integer32,
        slVMonth                        INTEGER,
        slVDay                          Integer32,
        slVHour                         Integer32,
        slVMinutes                      Integer32,
        slVName                         DisplayString,
        slVVolume                       Integer32
    }

slVIndex OBJECT-TYPE
    SYNTAX          Integer32
    MAX-ACCESS      read-only
    STATUS          current
    DESCRIPTION     
            "A number that identifies this entry for the
             referenced file system."
    ::= { slVEntry 1 }

slVMonth OBJECT-TYPE
    SYNTAX          INTEGER { january(1), february(2), march(3), 
                        april(4), may(5), june(6), july(7), august(8), 
                        september(9), october(10), november(11), 
                        december(12) }
    MAX-ACCESS      read-only
    STATUS          current
    DESCRIPTION     
            "The month in which the snapshot was created."
    ::= { slVEntry 2 }

slVDay OBJECT-TYPE
    SYNTAX          Integer32 (1..31)
    MAX-ACCESS      read-only
    STATUS          current
    DESCRIPTION     
            "The day on which the snapshot was created."
    ::= { slVEntry 3 }

slVHour OBJECT-TYPE
    SYNTAX          Integer32 (0..23)
    MAX-ACCESS      read-only
    STATUS          current
    DESCRIPTION     
            "The hour in which the snapshot was created."
    ::= { slVEntry 4 }

slVMinutes OBJECT-TYPE
    SYNTAX          Integer32 (0..59)
    MAX-ACCESS      read-only
    STATUS          current
    DESCRIPTION     
            "The minute in which the snapshot was created."
    ::= { slVEntry 5 }

slVName OBJECT-TYPE
    SYNTAX          DisplayString
    MAX-ACCESS      read-only
    STATUS          current
    DESCRIPTION     
            "The name of the referenced snapshot."
    ::= { slVEntry 6 }

slVVolume OBJECT-TYPE
    SYNTAX          Integer32
    MAX-ACCESS      read-only
    STATUS          current
    DESCRIPTION     
            "A number that identifies the volume that contains
             this snapshot."
    ::= { slVEntry 7 }

raid OBJECT IDENTIFIER
    ::= { netapp1 6 }

raidTable OBJECT-TYPE
    SYNTAX          SEQUENCE OF RaidEntry
    MAX-ACCESS      not-accessible
    STATUS          obsolete
    DESCRIPTION     
            "Display RAID configuration information for the
             root volume.  This table is deprecated - use
             raidVTable instead."
    ::= { raid 1 }

raidEntry OBJECT-TYPE
    SYNTAX          RaidEntry
    MAX-ACCESS      not-accessible
    STATUS          obsolete
    DESCRIPTION     
            "Display RAID configuration information for
             the referenced disk drive.  This only works for
             disks contained within the root volume, and will
             include spare drives.  This object is 
             deprecated - use raidVEntry instead."
    INDEX           { raidIndex }
    ::= { raidTable 1 }

RaidEntry ::=
    SEQUENCE {
        raidIndex                       Integer32,
        raidDiskName                    DisplayString,
        raidStatus                      INTEGER,
        raidDiskId                      Integer32,
        raidScsiAdapter                 DisplayString,
        raidScsiId                      Integer32,
        raidUsedMb                      Integer32,
        raidUsedBlocks                  Integer32,
        raidTotalMb                     Integer32,
        raidTotalBlocks                 Integer32,
        raidCompletionPerCent           Integer32
    }

raidIndex OBJECT-TYPE
    SYNTAX          Integer32
    MAX-ACCESS      read-only
    STATUS          obsolete
    DESCRIPTION     
            "A number that identifies this entry for the
             referenced disk drive."
    ::= { raidEntry 1 }

raidDiskName OBJECT-TYPE
    SYNTAX          DisplayString
    MAX-ACCESS      read-only
    STATUS          obsolete
    DESCRIPTION     
            "The name identifying the referenced disk drive."
    ::= { raidEntry 2 }

raidStatus OBJECT-TYPE
    SYNTAX          INTEGER { active(1), reconstructionInProgress(2), 
                        parityReconstructionInProgress(3), 
                        parityVerificationInProgress(4), 
                        scrubbingInProgress(5), failed(6), 
                        addingSpare(7), spare(8) }
    MAX-ACCESS      read-only
    STATUS          obsolete
    DESCRIPTION     
            "The status of the referenced disk drive."
    ::= { raidEntry 3 }

raidDiskId OBJECT-TYPE
    SYNTAX          Integer32
    MAX-ACCESS      read-only
    STATUS          obsolete
    DESCRIPTION     
            "The disk identifier for the referenced disk
             drive."
    ::= { raidEntry 4 }

raidScsiAdapter OBJECT-TYPE
    SYNTAX          DisplayString
    MAX-ACCESS      read-only
    STATUS          obsolete
    DESCRIPTION     
            "The identifier of the SCSI adapter for the
             referenced disk drive."
    ::= { raidEntry 5 }

raidScsiId OBJECT-TYPE
    SYNTAX          Integer32 (0..100)
    MAX-ACCESS      read-only
    STATUS          obsolete
    DESCRIPTION     
            "The identifier for the referenced disk drive
             on the referenced SCSI adapter."
    ::= { raidEntry 6 }

raidUsedMb OBJECT-TYPE
    SYNTAX          Integer32
    MAX-ACCESS      read-only
    STATUS          obsolete
    DESCRIPTION     
            "The number of MBytes currently in use on
             the referenced disk drive."
    ::= { raidEntry 7 }

raidUsedBlocks OBJECT-TYPE
    SYNTAX          Integer32
    MAX-ACCESS      read-only
    STATUS          obsolete
    DESCRIPTION     
            "The number of Blocks currently in use on
             the referenced disk drive."
    ::= { raidEntry 8 }

raidTotalMb OBJECT-TYPE
    SYNTAX          Integer32
    MAX-ACCESS      read-only
    STATUS          obsolete
    DESCRIPTION     
            "The number of MBytes physically available
             on the referenced disk drive."
    ::= { raidEntry 9 }

raidTotalBlocks OBJECT-TYPE
    SYNTAX          Integer32
    MAX-ACCESS      read-only
    STATUS          obsolete
    DESCRIPTION     
            "The number of Blocks physically available
             on the referenced disk drive."
    ::= { raidEntry 10 }

raidCompletionPerCent OBJECT-TYPE
    SYNTAX          Integer32 (0..100)
    MAX-ACCESS      read-only
    STATUS          obsolete
    DESCRIPTION     
            "In the case when reconstruction/adding a
             spare, verification or scrubbing is in progress,
             the percent of such reconstruction, verification
             or scrubbing that has been completed on the
             referenced disk drive."
    ::= { raidEntry 11 }

raidVTable OBJECT-TYPE
    SYNTAX          SEQUENCE OF RaidVEntry
    MAX-ACCESS      not-accessible
    STATUS          current
    DESCRIPTION     
            "Display RAID configuration information."
    ::= { raid 2 }

raidVEntry OBJECT-TYPE
    SYNTAX          RaidVEntry
    MAX-ACCESS      not-accessible
    STATUS          current
    DESCRIPTION     
            "Display RAID configuration information for
             the referenced volume, raid group, and disk drive."
    INDEX           { raidVVol, raidVGroup, raidVIndex }
    ::= { raidVTable 1 }

RaidVEntry ::=
    SEQUENCE {
        raidVIndex                      Integer32,
        raidVDiskName                   DisplayString,
        raidVStatus                     INTEGER,
        raidVDiskId                     Integer32,
        raidVScsiAdapter                DisplayString,
        raidVScsiId                     Integer32,
        raidVUsedMb                     Integer32,
        raidVUsedBlocks                 Integer32,
        raidVTotalMb                    Integer32,
        raidVTotalBlocks                Integer32,
        raidVCompletionPerCent          Integer32,
        raidVVol                        Integer32,
        raidVGroup                      Integer32
    }

raidVIndex OBJECT-TYPE
    SYNTAX          Integer32
    MAX-ACCESS      read-only
    STATUS          current
    DESCRIPTION     
            "A number that identifies this disk drive within 
             the given volume and RAID group."
    ::= { raidVEntry 1 }

raidVDiskName OBJECT-TYPE
    SYNTAX          DisplayString
    MAX-ACCESS      read-only
    STATUS          current
    DESCRIPTION     
            "The name identifying the referenced disk drive."
    ::= { raidVEntry 2 }

raidVStatus OBJECT-TYPE
    SYNTAX          INTEGER { active(1), reconstructionInProgress(2), 
                        parityReconstructionInProgress(3), 
                        parityVerificationInProgress(4), 
                        scrubbingInProgress(5), failed(6) }
    MAX-ACCESS      read-only
    STATUS          current
    DESCRIPTION     
            "The status of the referenced disk drive."
    ::= { raidVEntry 3 }

raidVDiskId OBJECT-TYPE
    SYNTAX          Integer32
    MAX-ACCESS      read-only
    STATUS          current
    DESCRIPTION     
            "The disk identifier for the referenced disk
             drive."
    ::= { raidVEntry 4 }

raidVScsiAdapter OBJECT-TYPE
    SYNTAX          DisplayString
    MAX-ACCESS      read-only
    STATUS          current
    DESCRIPTION     
            "The identifier of the SCSI adapter for the
             referenced disk drive."
    ::= { raidVEntry 5 }

raidVScsiId OBJECT-TYPE
    SYNTAX          Integer32 (0..100)
    MAX-ACCESS      read-only
    STATUS          current
    DESCRIPTION     
            "The identifier for the referenced disk drive
             on the referenced SCSI adapter."
    ::= { raidVEntry 6 }

raidVUsedMb OBJECT-TYPE
    SYNTAX          Integer32
    MAX-ACCESS      read-only
    STATUS          current
    DESCRIPTION     
            "The number of MBytes currently in use on
             the referenced disk drive."
    ::= { raidVEntry 7 }

raidVUsedBlocks OBJECT-TYPE
    SYNTAX          Integer32
    MAX-ACCESS      read-only
    STATUS          current
    DESCRIPTION     
            "The number of Blocks currently in use on
             the referenced disk drive."
    ::= { raidVEntry 8 }

raidVTotalMb OBJECT-TYPE
    SYNTAX          Integer32
    MAX-ACCESS      read-only
    STATUS          current
    DESCRIPTION     
            "The number of MBytes physically available
             on the referenced disk drive."
    ::= { raidVEntry 9 }

raidVTotalBlocks OBJECT-TYPE
    SYNTAX          Integer32
    MAX-ACCESS      read-only
    STATUS          current
    DESCRIPTION     
            "The number of Blocks physically available
             on the referenced disk drive."
    ::= { raidVEntry 10 }

raidVCompletionPerCent OBJECT-TYPE
    SYNTAX          Integer32 (0..100)
    MAX-ACCESS      read-only
    STATUS          current
    DESCRIPTION     
            "In the case when reconstruction/adding a
             spare, verification or scrubbing is in progress,
             the percent of such reconstruction, verification
             or scrubbing that has been completed on the
             referenced disk drive."
    ::= { raidVEntry 11 }

raidVVol OBJECT-TYPE
    SYNTAX          Integer32
    MAX-ACCESS      read-only
    STATUS          current
    DESCRIPTION     
            "A number that identifies the volume that this entry
             belongs to."
    ::= { raidVEntry 12 }

raidVGroup OBJECT-TYPE
    SYNTAX          Integer32
    MAX-ACCESS      read-only
    STATUS          current
    DESCRIPTION     
            "A number that identifies the RAID group within the
             given volume that this entry belongs to."
    ::= { raidVEntry 13 }

spareTable OBJECT-TYPE
    SYNTAX          SEQUENCE OF SpareEntry
    MAX-ACCESS      not-accessible
    STATUS          current
    DESCRIPTION     
            "Display spare disk configuration information."
    ::= { raid 3 }

spareEntry OBJECT-TYPE
    SYNTAX          SpareEntry
    MAX-ACCESS      not-accessible
    STATUS          current
    DESCRIPTION     
            "Display configuration information for
             the referenced spare disk drive."
    INDEX           { spareIndex }
    ::= { spareTable 1 }

SpareEntry ::=
    SEQUENCE {
        spareIndex                      Integer32,
        spareDiskName                   DisplayString,
        spareStatus                     INTEGER,
        spareDiskId                     Integer32,
        spareScsiAdapter                DisplayString,
        spareScsiId                     Integer32,
        spareTotalMb                    Integer32,
        spareTotalBlocks                Integer32
    }

spareIndex OBJECT-TYPE
    SYNTAX          Integer32
    MAX-ACCESS      read-only
    STATUS          current
    DESCRIPTION     
            "A number that identifies this entry for the
             referenced disk drive in the list of spare disk
             drives."
    ::= { spareEntry 1 }

spareDiskName OBJECT-TYPE
    SYNTAX          DisplayString
    MAX-ACCESS      read-only
    STATUS          current
    DESCRIPTION     
            "The name identifying the referenced spare disk 
             drive."
    ::= { spareEntry 2 }

spareStatus OBJECT-TYPE
    SYNTAX          INTEGER { spare(1), addingspare(2) }
    MAX-ACCESS      read-only
    STATUS          current
    DESCRIPTION     
            "The status of the referenced spare disk drive."
    ::= { spareEntry 3 }

spareDiskId OBJECT-TYPE
    SYNTAX          Integer32
    MAX-ACCESS      read-only
    STATUS          current
    DESCRIPTION     
            "The disk identifier for the referenced spare disk
             drive."
    ::= { spareEntry 4 }

spareScsiAdapter OBJECT-TYPE
    SYNTAX          DisplayString
    MAX-ACCESS      read-only
    STATUS          current
    DESCRIPTION     
            "The identifier of the SCSI adapter for the
             referenced spare disk drive."
    ::= { spareEntry 5 }

spareScsiId OBJECT-TYPE
    SYNTAX          Integer32 (0..100)
    MAX-ACCESS      read-only
    STATUS          current
    DESCRIPTION     
            "The identifier for the referenced spare disk drive
             on the referenced SCSI adapter."
    ::= { spareEntry 6 }

spareTotalMb OBJECT-TYPE
    SYNTAX          Integer32
    MAX-ACCESS      read-only
    STATUS          current
    DESCRIPTION     
            "The number of MBytes physically available
             on the referenced spare disk drive."
    ::= { spareEntry 7 }

spareTotalBlocks OBJECT-TYPE
    SYNTAX          Integer32
    MAX-ACCESS      read-only
    STATUS          current
    DESCRIPTION     
            "The number of Blocks physically available
             on the referenced spare disk drive."
    ::= { spareEntry 8 }

diskSummary OBJECT IDENTIFIER
    ::= { raid 4 }

diskTotalCount OBJECT-TYPE
    SYNTAX          Integer32
    MAX-ACCESS      read-only
    STATUS          current
    DESCRIPTION     
            "The total number of disks on the system."
    ::= { diskSummary 1 }

diskActiveCount OBJECT-TYPE
    SYNTAX          Integer32
    MAX-ACCESS      read-only
    STATUS          current
    DESCRIPTION     
            "The number of disks which are currently active,
             including parity disks."
    ::= { diskSummary 2 }

diskReconstructingCount OBJECT-TYPE
    SYNTAX          Integer32
    MAX-ACCESS      read-only
    STATUS          current
    DESCRIPTION     
            "The number of disks which are
             currently being reconstructed."
    ::= { diskSummary 3 }

diskReconstructingParityCount OBJECT-TYPE
    SYNTAX          Integer32
    MAX-ACCESS      read-only
    STATUS          current
    DESCRIPTION     
            "The number of parity disks which are
             currently being reconstructed."
    ::= { diskSummary 4 }

diskVerifyingParityCount OBJECT-TYPE
    SYNTAX          Integer32
    MAX-ACCESS      read-only
    STATUS          current
    DESCRIPTION     
            "The number of parity disks which are
             currently being verified."
    ::= { diskSummary 5 }

diskScrubbingCount OBJECT-TYPE
    SYNTAX          Integer32
    MAX-ACCESS      read-only
    STATUS          current
    DESCRIPTION     
            "The number of disks which are
             currently being scrubbed."
    ::= { diskSummary 6 }

diskFailedCount OBJECT-TYPE
    SYNTAX          Integer32
    MAX-ACCESS      read-only
    STATUS          current
    DESCRIPTION     
            "The number of disks which are
             currently broken."
    ::= { diskSummary 7 }

diskSpareCount OBJECT-TYPE
    SYNTAX          Integer32
    MAX-ACCESS      read-only
    STATUS          current
    DESCRIPTION     
            "The number of available spare disks."
    ::= { diskSummary 8 }

diskAddingSpareCount OBJECT-TYPE
    SYNTAX          Integer32
    MAX-ACCESS      read-only
    STATUS          current
    DESCRIPTION     
            "The number of spare disks which are
             currently being added into a RAID group."
    ::= { diskSummary 9 }

cifs OBJECT IDENTIFIER
    ::= { netapp1 7 }

cifsOptions OBJECT IDENTIFIER
    ::= { cifs 1 }

cifsIsEnabled OBJECT-TYPE
    SYNTAX          INTEGER { false(1), true(2) }
    MAX-ACCESS      read-only
    STATUS          current
    DESCRIPTION     
            "Whether the CIFS protocol is active on the
             filer."
    ::= { cifsOptions 1 }

cifsIsLoginEnabled OBJECT-TYPE
    SYNTAX          INTEGER { false(1), true(2) }
    MAX-ACCESS      read-only
    STATUS          current
    DESCRIPTION     
            "XXX."
    ::= { cifsOptions 2 }

cifsHostName OBJECT-TYPE
    SYNTAX          DisplayString
    MAX-ACCESS      read-only
    STATUS          current
    DESCRIPTION     
            "The host name used by the CIFS protocol on this
             filer."
    ::= { cifsOptions 3 }

cifsAltNames OBJECT-TYPE
    SYNTAX          DisplayString
    MAX-ACCESS      read-only
    STATUS          current
    DESCRIPTION     
            "Alternate names recognized by the filer."
    ::= { cifsOptions 4 }

cifsDomainJoined OBJECT-TYPE
    SYNTAX          INTEGER { false(1), true(2) }
    MAX-ACCESS      read-only
    STATUS          current
    DESCRIPTION     
            "Has the filer joined an NT domain?
             If this value is true, cifsDomainName
             will contain the name of the domain.
             Otherwise, the filer may have joined
             a WorkGroup, and cifsWGName will contain
             the name of the WorkGroup. "
    ::= { cifsOptions 5 }

cifsDomainName OBJECT-TYPE
    SYNTAX          DisplayString
    MAX-ACCESS      read-only
    STATUS          current
    DESCRIPTION     
            "The domain name used by the CIFS 
             protocol on this filer."
    ::= { cifsOptions 6 }

cifsWGName OBJECT-TYPE
    SYNTAX          DisplayString
    MAX-ACCESS      read-only
    STATUS          current
    DESCRIPTION     
            "The workgroup name (if any) used by 
             the CIFS protocol on this filer."
    ::= { cifsOptions 7 }

cifsDCName OBJECT-TYPE
    SYNTAX          DisplayString
    MAX-ACCESS      read-only
    STATUS          current
    DESCRIPTION     
            "The name of the Domain Controller used by
             this filer to authenticate users and file
             requests."
    ::= { cifsOptions 8 }

cifsIsWinsEnabled OBJECT-TYPE
    SYNTAX          INTEGER { false(1), true(2) }
    MAX-ACCESS      read-only
    STATUS          current
    DESCRIPTION     
            "True if WINS name resolution is enabled
             on the filer."
    ::= { cifsOptions 9 }

cifsWinsServers OBJECT-TYPE
    SYNTAX          DisplayString
    MAX-ACCESS      read-only
    STATUS          current
    DESCRIPTION     
            "The name(s) of the WINS servers registered
             with the filer."
    ::= { cifsOptions 10 }

cifsSecurityModel OBJECT-TYPE
    SYNTAX          INTEGER { unix(1), pc(2) }
    MAX-ACCESS      read-only
    STATUS          current
    DESCRIPTION     
            "Which type of authentication semantics
             (Unix or PC) are in use on the filer.
             If Unix semantics are in use, no ACL on
             a file is ever checked.  If PC semantics
             are in use, XXX."
    ::= { cifsOptions 11 }

cifsPCGenericUser OBJECT-TYPE
    SYNTAX          DisplayString
    MAX-ACCESS      read-only
    STATUS          current
    DESCRIPTION     
            "The name of the generic PC user, if any.  This
             username is used for CIFS access by Unix users
             who have not authenticated through CIFS or NT."
    ::= { cifsOptions 12 }

cifsOplocksEnabled OBJECT-TYPE
    SYNTAX          INTEGER { not-enabled(1), enabled(2) }
    MAX-ACCESS      read-only
    STATUS          current
    DESCRIPTION     
            "Whether oplocks are enabled on the filer."
    ::= { cifsOptions 15 }

cifsLevel2OplocksEnabled OBJECT-TYPE
    SYNTAX          INTEGER { not-enabled(1), enabled(2) }
    MAX-ACCESS      read-only
    STATUS          current
    DESCRIPTION     
            "Whether level 2 oplocks are enabled on the filer."
    ::= { cifsOptions 16 }

cifsPreserveCase OBJECT-TYPE
    SYNTAX          INTEGER { no-preserve-case(1), preserve-case(2) }
    MAX-ACCESS      read-only
    STATUS          current
    DESCRIPTION     
            "If this option is set to preserve-case
             (the default), all filename references
             will be case preserving.  Otherwise,
             they are forced to lowercase."
    ::= { cifsOptions 17 }

cifsSymlinksEnabled OBJECT-TYPE
    SYNTAX          INTEGER { not-enabled(1), enabled(2) }
    MAX-ACCESS      read-only
    STATUS          current
    DESCRIPTION     
            "If this option is enabled, CIFS accesses will
             follow symbolic links using Unix semantics."
    ::= { cifsOptions 19 }

cifsSymlinkCycleProtEnabled OBJECT-TYPE
    SYNTAX          INTEGER { not-enabled(1), enabled(2) }
    MAX-ACCESS      read-only
    STATUS          current
    DESCRIPTION     
            "If this option is enabled, CIFS accesses will
             through symbolic links will check for cycles
             in the link graph."
    ::= { cifsOptions 20 }

cifsInfo OBJECT IDENTIFIER
    ::= { cifs 2 }

cifsStatus OBJECT-TYPE
    SYNTAX          Integer32
    MAX-ACCESS      read-only
    STATUS          current
    DESCRIPTION     
            "Encoding of CIFS startup state on the filer."
    ::= { cifsInfo 1 }

cifsNeedPW OBJECT-TYPE
    SYNTAX          Integer32
    MAX-ACCESS      read-only
    STATUS          current
    DESCRIPTION     
            "Does the administrative password need 
             to be set before start?"
    ::= { cifsInfo 2 }

cifsTimeToShutdown OBJECT-TYPE
    SYNTAX          Integer32
    MAX-ACCESS      read-only
    STATUS          current
    DESCRIPTION     
            "Time remaining until CIFS shutdown"
    ::= { cifsInfo 3 }

cifsMaxConnections OBJECT-TYPE
    SYNTAX          Integer32
    MAX-ACCESS      read-only
    STATUS          current
    DESCRIPTION     
            "The maximum number of simultaneous CIFS 
             connections allowed on the filer."
    ::= { cifsInfo 4 }

cifsMaxTrees OBJECT-TYPE
    SYNTAX          Integer32
    MAX-ACCESS      read-only
    STATUS          current
    DESCRIPTION     
            "XXX."
    ::= { cifsInfo 5 }

cifsMaxShares OBJECT-TYPE
    SYNTAX          Integer32
    MAX-ACCESS      read-only
    STATUS          current
    DESCRIPTION     
            "XXX."
    ::= { cifsInfo 6 }

cifsMaxFiles OBJECT-TYPE
    SYNTAX          Integer32
    MAX-ACCESS      read-only
    STATUS          current
    DESCRIPTION     
            "XXX."
    ::= { cifsInfo 7 }

cifsMaxACLs OBJECT-TYPE
    SYNTAX          Integer32
    MAX-ACCESS      read-only
    STATUS          current
    DESCRIPTION     
            "XXX."
    ::= { cifsInfo 8 }

cifsConnectedUsers OBJECT-TYPE
    SYNTAX          Counter32
    MAX-ACCESS      read-only
    STATUS          current
    DESCRIPTION     
            "XXX."
    ::= { cifsInfo 9 }

cifsNTrees OBJECT-TYPE
    SYNTAX          Counter32
    MAX-ACCESS      read-only
    STATUS          current
    DESCRIPTION     
            "XXX."
    ::= { cifsInfo 10 }

cifsNShares OBJECT-TYPE
    SYNTAX          Counter32
    MAX-ACCESS      read-only
    STATUS          current
    DESCRIPTION     
            "XXX."
    ::= { cifsInfo 11 }

cifsNSessions OBJECT-TYPE
    SYNTAX          Counter32
    MAX-ACCESS      read-only
    STATUS          current
    DESCRIPTION     
            "XXX."
    ::= { cifsInfo 12 }

cifsNOpenFiles OBJECT-TYPE
    SYNTAX          Counter32
    MAX-ACCESS      read-only
    STATUS          current
    DESCRIPTION     
            "XXX."
    ::= { cifsInfo 13 }

cifsNOpenDirs OBJECT-TYPE
    SYNTAX          Counter32
    MAX-ACCESS      read-only
    STATUS          current
    DESCRIPTION     
            "XXX."
    ::= { cifsInfo 14 }

cifsNOplockBreakWaits OBJECT-TYPE
    SYNTAX          Counter32
    MAX-ACCESS      read-only
    STATUS          current
    DESCRIPTION     
            "The number of open files waiting for oplock
             break messages to be sent."
    ::= { cifsInfo 16 }

cifsNOplockAckWaits OBJECT-TYPE
    SYNTAX          Counter32
    MAX-ACCESS      read-only
    STATUS          current
    DESCRIPTION     
            "The number of open files waiting for 
             acknowledgements to oplock break messages."
    ::= { cifsInfo 17 }

cifsStats OBJECT IDENTIFIER
    ::= { cifs 3 }

cifsServ OBJECT IDENTIFIER
    ::= { cifsStats 1 }

cifsOps OBJECT IDENTIFIER
    ::= { cifsServ 1 }

cifsTotalOps OBJECT-TYPE
    SYNTAX          Counter32
    MAX-ACCESS      read-only
    STATUS          current
    DESCRIPTION     
            "The number of CIFS operations done by the filer,
             since the last time the statistics were cleared."
    ::= { cifsOps 1 }

cifsTotalCalls OBJECT-TYPE
    SYNTAX          Counter32
    MAX-ACCESS      read-only
    STATUS          current
    DESCRIPTION     
            "The total number of CIFS calls received, since
             the last time the statistics were cleared.  This
             is the number of cifsTotalOps plus the number of
             miscellaneous operations that are not logged
             which were received in that time period."
    ::= { cifsOps 2 }

cifsBadCalls OBJECT-TYPE
    SYNTAX          Counter32
    MAX-ACCESS      read-only
    STATUS          current
    DESCRIPTION     
            "The total number of received CIFS calls rejected,
             since the last time the statistics were cleared."
    ::= { cifsOps 3 }

cifsGetAttrs OBJECT-TYPE
    SYNTAX          Counter32
    MAX-ACCESS      read-only
    STATUS          current
    DESCRIPTION     
            "The total number of CIFS operations to get
             the attributes on a file or directory, since
             the last time the statistics were reset."
    ::= { cifsOps 4 }

cifsReads OBJECT-TYPE
    SYNTAX          Counter32
    MAX-ACCESS      read-only
    STATUS          current
    DESCRIPTION     
            "The total number of CIFS Read operations on
             a file or directory, since the last time the
             statistics were reset."
    ::= { cifsOps 5 }

cifsWrites OBJECT-TYPE
    SYNTAX          Counter32
    MAX-ACCESS      read-only
    STATUS          current
    DESCRIPTION     
            "The total number of CIFS write operations on
             a file or directory, since the last time the
             statistics were reset."
    ::= { cifsOps 6 }

cifsLocks OBJECT-TYPE
    SYNTAX          Counter32
    MAX-ACCESS      read-only
    STATUS          current
    DESCRIPTION     
            "The number of CIFS file locking requests
             since the last time the statistics were reset."
    ::= { cifsOps 7 }

cifsOpens OBJECT-TYPE
    SYNTAX          Counter32
    MAX-ACCESS      read-only
    STATUS          current
    DESCRIPTION     
            "The number of calls, via CIFS, to open
             a file or directory, since the last time
             the statistics were reset."
    ::= { cifsOps 8 }

cifsDirOps OBJECT-TYPE
    SYNTAX          Counter32
    MAX-ACCESS      read-only
    STATUS          current
    DESCRIPTION     
            "The number of CIFS directory operations,
             since the last time the statistics were reset."
    ::= { cifsOps 9 }

cifsOthers OBJECT-TYPE
    SYNTAX          Counter32
    MAX-ACCESS      read-only
    STATUS          current
    DESCRIPTION     
            "The number of CIFS operations, since the
             last time the statistics were reset, that
             don't fall into the categories for GetAttr,
             Read, Write, Lock, DirOp and Open."
    ::= { cifsOps 10 }

cifsReqs OBJECT IDENTIFIER
    ::= { cifsServ 2 }

smbNegProts OBJECT-TYPE
    SYNTAX          Counter32
    MAX-ACCESS      read-only
    STATUS          current
    DESCRIPTION     
            "The number of SMB NEGOTIATE requests,
             since the last time the statistics were cleared."
    ::= { cifsReqs 1 }

smbSessionSetupAndXs OBJECT-TYPE
    SYNTAX          Counter32
    MAX-ACCESS      read-only
    STATUS          current
    DESCRIPTION     
            "The number of SMB SESSION_SETUP_ANDX requests,
             since the last time the statistics were cleared."
    ::= { cifsReqs 2 }

smbLogoffAndXs OBJECT-TYPE
    SYNTAX          Counter32
    MAX-ACCESS      read-only
    STATUS          current
    DESCRIPTION     
            "The number of SMB LOGOFF_ANDX requests,
             since the last time the statistics were cleared."
    ::= { cifsReqs 3 }

smbTreeConnectAndXs OBJECT-TYPE
    SYNTAX          Counter32
    MAX-ACCESS      read-only
    STATUS          current
    DESCRIPTION     
            "The number of SMB TREE_CONNECT_ANDX requests,
             since the last time the statistics were cleared."
    ::= { cifsReqs 4 }

smbTreeDisconnects OBJECT-TYPE
    SYNTAX          Counter32
    MAX-ACCESS      read-only
    STATUS          current
    DESCRIPTION     
            "The number of SMB TREE_DISCONNECT requests,
             since the last time the statistics were cleared."
    ::= { cifsReqs 5 }

smbTrans2QueryFSInfos OBJECT-TYPE
    SYNTAX          Counter32
    MAX-ACCESS      read-only
    STATUS          current
    DESCRIPTION     
            "The number of SMB TRANS2_QUERY_FS_INFORMATION
             requests, since the last time the statistics 
             were cleared."
    ::= { cifsReqs 6 }

smbEchos OBJECT-TYPE
    SYNTAX          Counter32
    MAX-ACCESS      read-only
    STATUS          current
    DESCRIPTION     
            "The number of SMB ECHO requests,
             since the last time the statistics were cleared."
    ::= { cifsReqs 7 }

smbNTCancels OBJECT-TYPE
    SYNTAX          Counter32
    MAX-ACCESS      read-only
    STATUS          current
    DESCRIPTION     
            "SMB NT_CANCEL requests are not presently logged, 
             so this value should always be zero."
    ::= { cifsReqs 8 }

smbNTCreateAndXs OBJECT-TYPE
    SYNTAX          Counter32
    MAX-ACCESS      read-only
    STATUS          current
    DESCRIPTION     
            "The number of SMB NT_CREATE_ANDX requests,
             since the last time the statistics were cleared."
    ::= { cifsReqs 9 }

smbNTTransactCreates OBJECT-TYPE
    SYNTAX          Counter32
    MAX-ACCESS      read-only
    STATUS          current
    DESCRIPTION     
            "The number of SMB NT_TRANSACT_CREATE requests,
             since the last time the statistics were cleared."
    ::= { cifsReqs 10 }

smbCreateTemporaries OBJECT-TYPE
    SYNTAX          Counter32
    MAX-ACCESS      read-only
    STATUS          current
    DESCRIPTION     
            "The SMB CREATE_TEMPORARY operation is not presently
             supported, so this value should always be zero."
    ::= { cifsReqs 11 }

smbReadAndXs OBJECT-TYPE
    SYNTAX          Counter32
    MAX-ACCESS      read-only
    STATUS          current
    DESCRIPTION     
            "The number of SMB READ_ANDX requests,
             since the last time the statistics were cleared."
    ::= { cifsReqs 12 }

smbWriteAndXs OBJECT-TYPE
    SYNTAX          Counter32
    MAX-ACCESS      read-only
    STATUS          current
    DESCRIPTION     
            "The number of SMB WRITE_ANDX requests,
             since the last time the statistics were cleared."
    ::= { cifsReqs 13 }

smbLockingAndXs OBJECT-TYPE
    SYNTAX          Counter32
    MAX-ACCESS      read-only
    STATUS          current
    DESCRIPTION     
            "The number of SMB LOCKING_ANDX requests,
             since the last time the statistics were cleared."
    ::= { cifsReqs 14 }

smbSeeks OBJECT-TYPE
    SYNTAX          Counter32
    MAX-ACCESS      read-only
    STATUS          current
    DESCRIPTION     
            "The number of SMB SEEK requests,
             since the last time the statistics were cleared."
    ::= { cifsReqs 15 }

smbFlushes OBJECT-TYPE
    SYNTAX          Counter32
    MAX-ACCESS      read-only
    STATUS          current
    DESCRIPTION     
            "The number of SMB FLUSH requests,
             since the last time the statistics were cleared."
    ::= { cifsReqs 16 }

smbCloses OBJECT-TYPE
    SYNTAX          Counter32
    MAX-ACCESS      read-only
    STATUS          current
    DESCRIPTION     
            "The number of SMB CLOSE requests,
             since the last time the statistics were cleared."
    ::= { cifsReqs 17 }

smbDeletes OBJECT-TYPE
    SYNTAX          Counter32
    MAX-ACCESS      read-only
    STATUS          current
    DESCRIPTION     
            "The number of SMB DELETE requests,
             since the last time the statistics were cleared."
    ::= { cifsReqs 18 }

smbRenames OBJECT-TYPE
    SYNTAX          Counter32
    MAX-ACCESS      read-only
    STATUS          current
    DESCRIPTION     
            "The number of SMB RENAME requests,
             since the last time the statistics were cleared."
    ::= { cifsReqs 19 }

smbMoves OBJECT-TYPE
    SYNTAX          Counter32
    MAX-ACCESS      read-only
    STATUS          current
    DESCRIPTION     
            "The SMB MOVE request is not presently supported,
             so this value should always be zero."
    ::= { cifsReqs 20 }

smbCopies OBJECT-TYPE
    SYNTAX          Counter32
    MAX-ACCESS      read-only
    STATUS          current
    DESCRIPTION     
            "The SMB COPY request is not presently supported,
             so this value should always be zero."
    ::= { cifsReqs 21 }

smbTrans2QueryPathInfos OBJECT-TYPE
    SYNTAX          Counter32
    MAX-ACCESS      read-only
    STATUS          current
    DESCRIPTION     
            "The number of SMB TRANS2_QUERY_PATH_INFORMATION
             requests, since the last time the statistics 
             were cleared."
    ::= { cifsReqs 22 }

smbTrans2QueryFileInfos OBJECT-TYPE
    SYNTAX          Counter32
    MAX-ACCESS      read-only
    STATUS          current
    DESCRIPTION     
            "The number of SMB TRANS2_QUERY_FILE_INFORMATION
             requests, since the last time the statistics 
             were cleared."
    ::= { cifsReqs 23 }

smbTrans2SetPathInfos OBJECT-TYPE
    SYNTAX          Counter32
    MAX-ACCESS      read-only
    STATUS          current
    DESCRIPTION     
            "The number of SMB TRANS2_SET_PATH_INFORMATION
             requests, since the last time the statistics 
             were cleared."
    ::= { cifsReqs 24 }

smbTrans2SetFileInfos OBJECT-TYPE
    SYNTAX          Counter32
    MAX-ACCESS      read-only
    STATUS          current
    DESCRIPTION     
            "The number of SMB TRANS2_SET_FILE_INFORMATION
             requests, since the last time the statistics 
             were cleared."
    ::= { cifsReqs 25 }

smbDeleteDirs OBJECT-TYPE
    SYNTAX          Counter32
    MAX-ACCESS      read-only
    STATUS          current
    DESCRIPTION     
            "The number of SMB DELETE_DIRECTORY requests,
             since the last time the statistics were cleared."
    ::= { cifsReqs 26 }

smbCheckDirs OBJECT-TYPE
    SYNTAX          Counter32
    MAX-ACCESS      read-only
    STATUS          current
    DESCRIPTION     
            "The SMB COPY request is not presently supported,
             so this value should always be zero."
    ::= { cifsReqs 27 }

smbTrans2FindFirst2s OBJECT-TYPE
    SYNTAX          Counter32
    MAX-ACCESS      read-only
    STATUS          current
    DESCRIPTION     
            "The number of SMB TRANS2_FIND_FIRST2 requests,
             since the last time the statistics were cleared."
    ::= { cifsReqs 28 }

smbTrans2FindNext2s OBJECT-TYPE
    SYNTAX          Counter32
    MAX-ACCESS      read-only
    STATUS          current
    DESCRIPTION     
            "The number of SMB TRANS2_FIND_NEXT2 requests,
             since the last time the statistics were cleared."
    ::= { cifsReqs 29 }

smbFindClose2s OBJECT-TYPE
    SYNTAX          Counter32
    MAX-ACCESS      read-only
    STATUS          current
    DESCRIPTION     
            "The number of SMB FIND_CLOSE2 requests,
             since the last time the statistics were cleared."
    ::= { cifsReqs 30 }

smbNTTransactNotifyChgs OBJECT-TYPE
    SYNTAX          Counter32
    MAX-ACCESS      read-only
    STATUS          current
    DESCRIPTION     
            "The number of SMB NT_TRANSACT_NOTIFY_CHANGE
             requests, since the last time the statistics 
             were cleared."
    ::= { cifsReqs 31 }

smbTrans2GetDFSReferrals OBJECT-TYPE
    SYNTAX          Counter32
    MAX-ACCESS      read-only
    STATUS          current
    DESCRIPTION     
            "The SMB TRANS2_GET_DFS_REFERRAL request is 
             not presently supported, so this value should 
             always be zero."
    ::= { cifsReqs 32 }

smbTrans2ReportDFSIncs OBJECT-TYPE
    SYNTAX          Counter32
    MAX-ACCESS      read-only
    STATUS          current
    DESCRIPTION     
            "The SMB TRANS2_REPORT_DFS_INCONSISTENCY request is 
             not presently supported, so this value should 
             always be zero."
    ::= { cifsReqs 33 }

smbOpenPrintFiles OBJECT-TYPE
    SYNTAX          Counter32
    MAX-ACCESS      read-only
    STATUS          current
    DESCRIPTION     
            "The SMB OPEN_PRINT_FILE request is not supported,
             so this value should always be zero."
    ::= { cifsReqs 34 }

smbGetPrintQueues OBJECT-TYPE
    SYNTAX          Counter32
    MAX-ACCESS      read-only
    STATUS          current
    DESCRIPTION     
            "The SMB GET_PRINT_QUEUE request is not supported,
             so this value should always be zero."
    ::= { cifsReqs 35 }

smbNTTransactIoctls OBJECT-TYPE
    SYNTAX          Counter32
    MAX-ACCESS      read-only
    STATUS          current
    DESCRIPTION     
            "The number of SMB NT_TRANSACT_IOCTL requests,
             since the last time the statistics were cleared."
    ::= { cifsReqs 36 }

smbNTTransactQuerySecDescs OBJECT-TYPE
    SYNTAX          Counter32
    MAX-ACCESS      read-only
    STATUS          current
    DESCRIPTION     
            "The number of SMB NT_TRANSACT_QUERY_SECURITY_DESC
             requests, since the last time the statistics 
             were cleared."
    ::= { cifsReqs 37 }

smbNTTransactSetSecDescs OBJECT-TYPE
    SYNTAX          Counter32
    MAX-ACCESS      read-only
    STATUS          current
    DESCRIPTION     
            "The number of SMB NT_TRANSACT_SET_SECURITY_DESC
             requests, since the last time the statistics 
             were cleared."
    ::= { cifsReqs 38 }

smbTrans2CreateDirs OBJECT-TYPE
    SYNTAX          Counter32
    MAX-ACCESS      read-only
    STATUS          current
    DESCRIPTION     
            "The number of SMB TRANS2_CREATE_DIRECTORY 
             requests, since the last time the statistics 
             were cleared."
    ::= { cifsReqs 39 }

cifsPercent OBJECT IDENTIFIER
    ::= { cifsServ 3 }

smbNegProtPct OBJECT-TYPE
    SYNTAX          Integer32 (0..100)
    MAX-ACCESS      read-only
    STATUS          current
    DESCRIPTION     
            "The number of SMB NEGOTIATE requests,
             as a percentage of total CIFS calls received,
             since the last time the statistics were cleared."
    ::= { cifsPercent 1 }

smbSessionSetupAndXPct OBJECT-TYPE
    SYNTAX          Integer32 (0..100)
    MAX-ACCESS      read-only
    STATUS          current
    DESCRIPTION     
            "The number of SMB SESSION_SETUP_ANDX requests,
             as a percentage of total CIFS calls received,
             since the last time the statistics were cleared."
    ::= { cifsPercent 2 }

smbLogoffAndXPct OBJECT-TYPE
    SYNTAX          Integer32 (0..100)
    MAX-ACCESS      read-only
    STATUS          current
    DESCRIPTION     
            "The number of SMB LOGOFF_ANDX requests,
             as a percentage of total CIFS calls received,
             since the last time the statistics were cleared."
    ::= { cifsPercent 3 }

smbTreeConnectAndXPct OBJECT-TYPE
    SYNTAX          Integer32 (0..100)
    MAX-ACCESS      read-only
    STATUS          current
    DESCRIPTION     
            "The number of SMB TREE_CONNECT_ANDX requests,
             as a percentage of total CIFS calls received,
             since the last time the statistics were cleared."
    ::= { cifsPercent 4 }

smbTreeDisconnectAndXPct OBJECT-TYPE
    SYNTAX          Integer32 (0..100)
    MAX-ACCESS      read-only
    STATUS          current
    DESCRIPTION     
            "The number of SMB TREE_DISCONNECT_ANDX requests,
             as a percentage of total CIFS calls received,
             since the last time the statistics were cleared."
    ::= { cifsPercent 5 }

smbTrans2QueryFSInfoPct OBJECT-TYPE
    SYNTAX          Integer32 (0..100)
    MAX-ACCESS      read-only
    STATUS          current
    DESCRIPTION     
            "The number of SMB TRANS2_QUERY_FS_INFORMATION
             requests, as a percentage of total CIFS calls
             received, since the last time the statistics 
             were cleared."
    ::= { cifsPercent 6 }

smbEchoPct OBJECT-TYPE
    SYNTAX          Integer32 (0..100)
    MAX-ACCESS      read-only
    STATUS          current
    DESCRIPTION     
            "The number of SMB ECHO requests,
             as a percentage of total CIFS calls received,
             since the last time the statistics were cleared."
    ::= { cifsPercent 7 }

smbNTCancelPct OBJECT-TYPE
    SYNTAX          Integer32 (0..100)
    MAX-ACCESS      read-only
    STATUS          current
    DESCRIPTION     
            "The number of SMB NT_CANCEL requests,
             as a percentage of total CIFS calls received,
             since the last time the statistics were cleared."
    ::= { cifsPercent 8 }

smbCreateAndXPct OBJECT-TYPE
    SYNTAX          Integer32 (0..100)
    MAX-ACCESS      read-only
    STATUS          current
    DESCRIPTION     
            "The number of SMB NT_CREATE_ANDX requests,
             as a percentage of total CIFS calls received,
             since the last time the statistics were cleared."
    ::= { cifsPercent 9 }

smbTransactCreatePct OBJECT-TYPE
    SYNTAX          Integer32 (0..100)
    MAX-ACCESS      read-only
    STATUS          current
    DESCRIPTION     
            "The number of SMB NT_TRANSACT_CREATE requests,
             as a percentage of total CIFS calls received,
             since the last time the statistics were cleared."
    ::= { cifsPercent 10 }

smbCreateTemporaryPct OBJECT-TYPE
    SYNTAX          Integer32 (0..100)
    MAX-ACCESS      read-only
    STATUS          current
    DESCRIPTION     
            "The number of SMB CREATE_TEMPORARY requests,
             as a percentage of total CIFS calls received,
             since the last time the statistics were cleared."
    ::= { cifsPercent 11 }

smbReadAndXPct OBJECT-TYPE
    SYNTAX          Integer32 (0..100)
    MAX-ACCESS      read-only
    STATUS          current
    DESCRIPTION     
            "The number of SMB READ_ANDX requests,
             as a percentage of total CIFS calls received,
             since the last time the statistics were cleared."
    ::= { cifsPercent 12 }

smbWriteAndXPct OBJECT-TYPE
    SYNTAX          Integer32 (0..100)
    MAX-ACCESS      read-only
    STATUS          current
    DESCRIPTION     
            "The number of SMB WRITE_ANDX requests,
             as a percentage of total CIFS calls received,
             since the last time the statistics were cleared."
    ::= { cifsPercent 13 }

smbLockingAndXPct OBJECT-TYPE
    SYNTAX          Integer32 (0..100)
    MAX-ACCESS      read-only
    STATUS          current
    DESCRIPTION     
            "The number of SMB LOCKING_ANDX requests,
             as a percentage of total CIFS calls received,
             since the last time the statistics were cleared."
    ::= { cifsPercent 14 }

smbSeekPct OBJECT-TYPE
    SYNTAX          Integer32 (0..100)
    MAX-ACCESS      read-only
    STATUS          current
    DESCRIPTION     
            "The number of SMB SEEK requests,
             as a percentage of total CIFS calls received,
             since the last time the statistics were cleared."
    ::= { cifsPercent 15 }

smbFlushPct OBJECT-TYPE
    SYNTAX          Integer32 (0..100)
    MAX-ACCESS      read-only
    STATUS          current
    DESCRIPTION     
            "The number of SMB FLUSH requests,
             as a percentage of total CIFS calls received,
             since the last time the statistics were cleared."
    ::= { cifsPercent 16 }

smbClosePct OBJECT-TYPE
    SYNTAX          Integer32 (0..100)
    MAX-ACCESS      read-only
    STATUS          current
    DESCRIPTION     
            "The number of SMB CLOSE requests,
             as a percentage of total CIFS calls received,
             since the last time the statistics were cleared."
    ::= { cifsPercent 17 }

smbDeletePct OBJECT-TYPE
    SYNTAX          Integer32 (0..100)
    MAX-ACCESS      read-only
    STATUS          current
    DESCRIPTION     
            "The number of SMB DELETE requests,
             as a percentage of total CIFS calls received,
             since the last time the statistics were cleared."
    ::= { cifsPercent 18 }

smbRenamePct OBJECT-TYPE
    SYNTAX          Integer32 (0..100)
    MAX-ACCESS      read-only
    STATUS          current
    DESCRIPTION     
            "The number of SMB RENAME requests,
             as a percentage of total CIFS calls received,
             since the last time the statistics were cleared."
    ::= { cifsPercent 19 }

smbMovePct OBJECT-TYPE
    SYNTAX          Integer32 (0..100)
    MAX-ACCESS      read-only
    STATUS          current
    DESCRIPTION     
            "The number of SMB MOVE requests,
             as a percentage of total CIFS calls received,
             since the last time the statistics were cleared."
    ::= { cifsPercent 20 }

smbCopyPct OBJECT-TYPE
    SYNTAX          Integer32 (0..100)
    MAX-ACCESS      read-only
    STATUS          current
    DESCRIPTION     
            "The number of SMB COPY requests,
             as a percentage of total CIFS calls received,
             since the last time the statistics were cleared."
    ::= { cifsPercent 21 }

smbTrans2QueryPathInfoPct OBJECT-TYPE
    SYNTAX          Integer32 (0..100)
    MAX-ACCESS      read-only
    STATUS          current
    DESCRIPTION     
            "The number of SMB TRANS2_QUERY_PATH_INFORMATION
             requests, as a percentage of total CIFS calls
             received, since the last time the statistics 
             were cleared."
    ::= { cifsPercent 22 }

smbTrans2QueryFileInfoPct OBJECT-TYPE
    SYNTAX          Integer32 (0..100)
    MAX-ACCESS      read-only
    STATUS          current
    DESCRIPTION     
            "The number of SMB TRANS2_QUERY_FILE_INFORMATION
             requests, as a percentage of total CIFS calls
             received, since the last time the statistics 
             were cleared."
    ::= { cifsPercent 23 }

smbTrans2SetPathInfoPct OBJECT-TYPE
    SYNTAX          Integer32 (0..100)
    MAX-ACCESS      read-only
    STATUS          current
    DESCRIPTION     
            "The number of SMB TRANS2_SET_PATH_INFORMATION
             requests, as a percentage of total CIFS calls
             received, since the last time the statistics 
             were cleared."
    ::= { cifsPercent 24 }

smbTrans2SetFileInfoPct OBJECT-TYPE
    SYNTAX          Integer32 (0..100)
    MAX-ACCESS      read-only
    STATUS          current
    DESCRIPTION     
            "The number of SMB TRANS2_SET_FILE_INFORMATION
             requests, as a percentage of total CIFS calls
             received, since the last time the statistics 
             were cleared."
    ::= { cifsPercent 25 }

smbDeleteDirPct OBJECT-TYPE
    SYNTAX          Integer32 (0..100)
    MAX-ACCESS      read-only
    STATUS          current
    DESCRIPTION     
            "The number of SMB DELETE_DIRECTORY requests,
             as a percentage of total CIFS calls received,
             since the last time the statistics were cleared."
    ::= { cifsPercent 26 }

smbCheckDirPct OBJECT-TYPE
    SYNTAX          Integer32 (0..100)
    MAX-ACCESS      read-only
    STATUS          current
    DESCRIPTION     
            "The number of SMB CHECK_DIRECTORY requests,
             as a percentage of total CIFS calls received,
             since the last time the statistics were cleared."
    ::= { cifsPercent 27 }

smbTrans2FindFirst2Pct OBJECT-TYPE
    SYNTAX          Integer32 (0..100)
    MAX-ACCESS      read-only
    STATUS          current
    DESCRIPTION     
            "The number of SMB TRANS2_FIND_FIRST2 requests,
             as a percentage of total CIFS calls received,
             since the last time the statistics were cleared."
    ::= { cifsPercent 28 }

smbTrans2FindNext2Pct OBJECT-TYPE
    SYNTAX          Integer32 (0..100)
    MAX-ACCESS      read-only
    STATUS          current
    DESCRIPTION     
            "The number of SMB TRANS2_FIND_NEXT2 requests,
             as a percentage of total CIFS calls received,
             since the last time the statistics were cleared."
    ::= { cifsPercent 29 }

smbFindClose2Pct OBJECT-TYPE
    SYNTAX          Integer32 (0..100)
    MAX-ACCESS      read-only
    STATUS          current
    DESCRIPTION     
            "The number of SMB FIND_CLOSE2 requests,
             as a percentage of total CIFS calls received,
             since the last time the statistics were cleared."
    ::= { cifsPercent 30 }

smbNTTransactNotifyChgPct OBJECT-TYPE
    SYNTAX          Integer32 (0..100)
    MAX-ACCESS      read-only
    STATUS          current
    DESCRIPTION     
            "The number of SMB NT_TRANSACT_NOTIFY_CHANGE
             requests, as a percentage of total CIFS calls
             received, since the last time the statistics 
             were cleared."
    ::= { cifsPercent 31 }

smbTrans2GetDFSReferralPct OBJECT-TYPE
    SYNTAX          Integer32 (0..100)
    MAX-ACCESS      read-only
    STATUS          current
    DESCRIPTION     
            "The number of SMB TRANS2_GET_DFS_REFERRAL
             requests, as a percentage of total CIFS calls
             received, since the last time the statistics 
             were cleared."
    ::= { cifsPercent 32 }

smbTrans2ReportDFSIncPct OBJECT-TYPE
    SYNTAX          Integer32 (0..100)
    MAX-ACCESS      read-only
    STATUS          current
    DESCRIPTION     
            "The number of SMB TRANS2_REPORT_DFS_INCONSISTENCY
             requests, as a percentage of total CIFS calls
             received, since the last time the statistics 
             were cleared."
    ::= { cifsPercent 33 }

smbOpenPrintFilePct OBJECT-TYPE
    SYNTAX          Integer32 (0..100)
    MAX-ACCESS      read-only
    STATUS          current
    DESCRIPTION     
            "The number of SMB OPEN_PRINT_FILE requests,
             as a percentage of total CIFS calls received,
             since the last time the statistics were cleared."
    ::= { cifsPercent 34 }

smbGetPrintQueuePct OBJECT-TYPE
    SYNTAX          Integer32 (0..100)
    MAX-ACCESS      read-only
    STATUS          current
    DESCRIPTION     
            "The number of SMB GET_PRINT_QUEUE requests,
             as a percentage of total CIFS calls received,
             since the last time the statistics were cleared."
    ::= { cifsPercent 35 }

smbNTTransactIoctlPct OBJECT-TYPE
    SYNTAX          Integer32 (0..100)
    MAX-ACCESS      read-only
    STATUS          current
    DESCRIPTION     
            "The number of SMB NT_TRANSACT_IOCTL requests,
             as a percentage of total CIFS calls received,
             since the last time the statistics were cleared."
    ::= { cifsPercent 36 }

smbNTTransactQuerySecDescPct OBJECT-TYPE
    SYNTAX          Integer32 (0..100)
    MAX-ACCESS      read-only
    STATUS          current
    DESCRIPTION     
            "The number of SMB NT_TRANSACT_QUERY_SECURITY_DESC
             requests, as a percentage of total CIFS calls
             received, since the last time the statistics 
             were cleared."
    ::= { cifsPercent 37 }

smbNTTransactSetSecDescPct OBJECT-TYPE
    SYNTAX          Integer32 (0..100)
    MAX-ACCESS      read-only
    STATUS          current
    DESCRIPTION     
            "The number of SMB NT_TRANSACT_SET_SECURITY_DESC
             requests, as a percentage of total CIFS calls
             received, since the last time the statistics 
             were cleared."
    ::= { cifsPercent 38 }

smbTrans2CreateDirPct OBJECT-TYPE
    SYNTAX          Integer32 (0..100)
    MAX-ACCESS      read-only
    STATUS          current
    DESCRIPTION     
            "The number of SMB TRANS2_CREATE_DIRECTORY 
             requests, as a percentage of total CIFS calls
             received, since the last time the statistics 
             were cleared."
    ::= { cifsPercent 39 }

cifsObsReqs OBJECT IDENTIFIER
    ::= { cifsServ 4 }

obsSmbClosePrintFiles OBJECT-TYPE
    SYNTAX          Counter32
    MAX-ACCESS      read-only
    STATUS          current
    DESCRIPTION     
            "The number of SMB CLOSE_PRINT_FILE requests,
             since the last time the statistics were cleared."
    ::= { cifsObsReqs 1 }

obsSmbCreates OBJECT-TYPE
    SYNTAX          Counter32
    MAX-ACCESS      read-only
    STATUS          current
    DESCRIPTION     
            "The number of SMB CREATE requests,
             since the last time the statistics were cleared."
    ::= { cifsObsReqs 2 }

obsSmbCreateDirs OBJECT-TYPE
    SYNTAX          Counter32
    MAX-ACCESS      read-only
    STATUS          current
    DESCRIPTION     
            "The number of SMB CREATE_DIRECTORY requests,
             since the last time the statistics were cleared."
    ::= { cifsObsReqs 3 }

obsSmbCreateNews OBJECT-TYPE
    SYNTAX          Counter32
    MAX-ACCESS      read-only
    STATUS          current
    DESCRIPTION     
            "The number of SMB CREATE_NEW requests,
             since the last time the statistics were cleared."
    ::= { cifsObsReqs 4 }

obsSmbLockAndReads OBJECT-TYPE
    SYNTAX          Counter32
    MAX-ACCESS      read-only
    STATUS          current
    DESCRIPTION     
            "The number of SMB LOCK_AND_READ requests,
             since the last time the statistics were cleared."
    ::= { cifsObsReqs 5 }

obsSmbLockByteRanges OBJECT-TYPE
    SYNTAX          Counter32
    MAX-ACCESS      read-only
    STATUS          current
    DESCRIPTION     
            "The number of SMB LOCK_BYTE_RANGE requests,
             since the last time the statistics were cleared."
    ::= { cifsObsReqs 6 }

obsSmbOpens OBJECT-TYPE
    SYNTAX          Counter32
    MAX-ACCESS      read-only
    STATUS          current
    DESCRIPTION     
            "The number of SMB OPEN requests,
             since the last time the statistics were cleared."
    ::= { cifsObsReqs 7 }

obsSmbOpenAndXs OBJECT-TYPE
    SYNTAX          Counter32
    MAX-ACCESS      read-only
    STATUS          current
    DESCRIPTION     
            "The number of SMB OPEN_ANDX requests,
             since the last time the statistics were cleared."
    ::= { cifsObsReqs 8 }

obsSmbProcessExits OBJECT-TYPE
    SYNTAX          Counter32
    MAX-ACCESS      read-only
    STATUS          current
    DESCRIPTION     
            "The number of SMB PROCESS_EXIT requests,
             since the last time the statistics were cleared."
    ::= { cifsObsReqs 9 }

obsSmbQueryInfos OBJECT-TYPE
    SYNTAX          Counter32
    MAX-ACCESS      read-only
    STATUS          current
    DESCRIPTION     
            "The number of SMB QUERY_INFORMATION requests,
             since the last time the statistics were cleared."
    ::= { cifsObsReqs 10 }

obsSmbQueryInfo2s OBJECT-TYPE
    SYNTAX          Counter32
    MAX-ACCESS      read-only
    STATUS          current
    DESCRIPTION     
            "The number of SMB QUERY_INFORMATION2 requests,
             since the last time the statistics were cleared."
    ::= { cifsObsReqs 11 }

obsSmbReads OBJECT-TYPE
    SYNTAX          Counter32
    MAX-ACCESS      read-only
    STATUS          current
    DESCRIPTION     
            "The number of SMB READ requests,
             since the last time the statistics were cleared."
    ::= { cifsObsReqs 12 }

obsSmbReadMPXs OBJECT-TYPE
    SYNTAX          Counter32
    MAX-ACCESS      read-only
    STATUS          current
    DESCRIPTION     
            "The SMB READ_MPX request is not supported,
             so this value should always be zero."
    ::= { cifsObsReqs 13 }

obsSmbReadRaws OBJECT-TYPE
    SYNTAX          Counter32
    MAX-ACCESS      read-only
    STATUS          current
    DESCRIPTION     
            "The number of SMB READ_RAW requests,
             since the last time the statistics were cleared."
    ::= { cifsObsReqs 14 }

obsSmbSearchs OBJECT-TYPE
    SYNTAX          Counter32
    MAX-ACCESS      read-only
    STATUS          current
    DESCRIPTION     
            "The number of SMB SEARCH requests,
             since the last time the statistics were cleared."
    ::= { cifsObsReqs 15 }

obsSmbSetInfos OBJECT-TYPE
    SYNTAX          Counter32
    MAX-ACCESS      read-only
    STATUS          current
    DESCRIPTION     
            "The number of SMB SET_INFORMATION requests,
             since the last time the statistics were cleared."
    ::= { cifsObsReqs 16 }

obsSmbSetInfo2s OBJECT-TYPE
    SYNTAX          Counter32
    MAX-ACCESS      read-only
    STATUS          current
    DESCRIPTION     
            "The number of SMB SET_INFORMATION2 requests,
             since the last time the statistics were cleared."
    ::= { cifsObsReqs 17 }

obsSmbQueryInfoDisks OBJECT-TYPE
    SYNTAX          Counter32
    MAX-ACCESS      read-only
    STATUS          current
    DESCRIPTION     
            "The number of SMB QUERY_INFORMATION_DISK
             requests, since the last time the statistics 
             were cleared."
    ::= { cifsObsReqs 18 }

obsSmbTrans2Open2s OBJECT-TYPE
    SYNTAX          Counter32
    MAX-ACCESS      read-only
    STATUS          current
    DESCRIPTION     
            "The number of SMB TRANS2_OPEN2 requests,
             since the last time the statistics were cleared."
    ::= { cifsObsReqs 19 }

obsSmbTreeConnects OBJECT-TYPE
    SYNTAX          Counter32
    MAX-ACCESS      read-only
    STATUS          current
    DESCRIPTION     
            "The number of SMB TREE_CONNECT requests,
             since the last time the statistics were cleared."
    ::= { cifsObsReqs 20 }

obsSmbUnlockByteRanges OBJECT-TYPE
    SYNTAX          Counter32
    MAX-ACCESS      read-only
    STATUS          current
    DESCRIPTION     
            "The number of SMB UNLOCK_BYTE_RANGE requests,
             since the last time the statistics were cleared."
    ::= { cifsObsReqs 21 }

obsSmbWrites OBJECT-TYPE
    SYNTAX          Counter32
    MAX-ACCESS      read-only
    STATUS          current
    DESCRIPTION     
            "The number of SMB WRITE requests,
             since the last time the statistics were cleared."
    ::= { cifsObsReqs 22 }

obsSmbWriteAndUnlocks OBJECT-TYPE
    SYNTAX          Counter32
    MAX-ACCESS      read-only
    STATUS          current
    DESCRIPTION     
            "The number of SMB WRITE_AND_UNLOCK requests,
             since the last time the statistics were cleared."
    ::= { cifsObsReqs 23 }

obsSmbWriteAndCloses OBJECT-TYPE
    SYNTAX          Counter32
    MAX-ACCESS      read-only
    STATUS          current
    DESCRIPTION     
            "The number of SMB WRITE_AND_CLOSE requests,
             since the last time the statistics were cleared."
    ::= { cifsObsReqs 24 }

obsSmbWriteMPXs OBJECT-TYPE
    SYNTAX          Counter32
    MAX-ACCESS      read-only
    STATUS          current
    DESCRIPTION     
            "The SMB WRITE_MPX request is not supported,
             so this value should always be zero."
    ::= { cifsObsReqs 25 }

obsSmbWritePrintFiles OBJECT-TYPE
    SYNTAX          Counter32
    MAX-ACCESS      read-only
    STATUS          current
    DESCRIPTION     
            "The SMB WRITE_PRINT_FILE request is not supported,
             so this value should always be zero."
    ::= { cifsObsReqs 26 }

obsSmbWriteRaws OBJECT-TYPE
    SYNTAX          Counter32
    MAX-ACCESS      read-only
    STATUS          current
    DESCRIPTION     
            "The number of SMB WRITE_RAW requests,
             since the last time the statistics were cleared."
    ::= { cifsObsReqs 27 }

cifsObsPercent OBJECT IDENTIFIER
    ::= { cifsServ 5 }

obsSmbClosePrintFilePct OBJECT-TYPE
    SYNTAX          Integer32 (0..100)
    MAX-ACCESS      read-only
    STATUS          current
    DESCRIPTION     
            "The number of SMB CLOSE_PRINT_FILE requests,
             as a percentage of total CIFS calls received,
             since the last time the statistics were cleared."
    ::= { cifsObsPercent 1 }

obsSmbCreatePct OBJECT-TYPE
    SYNTAX          Integer32 (0..100)
    MAX-ACCESS      read-only
    STATUS          current
    DESCRIPTION     
            "The number of SMB CREATE requests,
             as a percentage of total CIFS calls received,
             since the last time the statistics were cleared."
    ::= { cifsObsPercent 2 }

obsSmbCreateDirPct OBJECT-TYPE
    SYNTAX          Integer32 (0..100)
    MAX-ACCESS      read-only
    STATUS          current
    DESCRIPTION     
            "The number of SMB CREATE_DIRECTORY requests,
             as a percentage of total CIFS calls received,
             since the last time the statistics were cleared."
    ::= { cifsObsPercent 3 }

obsSmbCreateNewPct OBJECT-TYPE
    SYNTAX          Integer32 (0..100)
    MAX-ACCESS      read-only
    STATUS          current
    DESCRIPTION     
            "The number of SMB CREATE_NEW requests,
             as a percentage of total CIFS calls received,
             since the last time the statistics were cleared."
    ::= { cifsObsPercent 4 }

obsSmbLockAndReadPct OBJECT-TYPE
    SYNTAX          Integer32 (0..100)
    MAX-ACCESS      read-only
    STATUS          current
    DESCRIPTION     
            "The number of SMB LOCK_AND_READ requests,
             as a percentage of total CIFS calls received,
             since the last time the statistics were cleared."
    ::= { cifsObsPercent 5 }

obsSmbLockByteRangePct OBJECT-TYPE
    SYNTAX          Integer32 (0..100)
    MAX-ACCESS      read-only
    STATUS          current
    DESCRIPTION     
            "The number of SMB LOCK_BYTE_RANGE requests,
             as a percentage of total CIFS calls received,
             since the last time the statistics were cleared."
    ::= { cifsObsPercent 6 }

obsSmbOpenPct OBJECT-TYPE
    SYNTAX          Integer32 (0..100)
    MAX-ACCESS      read-only
    STATUS          current
    DESCRIPTION     
            "The number of SMB OPEN requests,
             as a percentage of total CIFS calls received,
             since the last time the statistics were cleared."
    ::= { cifsObsPercent 7 }

obsSmbOpenAndXPct OBJECT-TYPE
    SYNTAX          Integer32 (0..100)
    MAX-ACCESS      read-only
    STATUS          current
    DESCRIPTION     
            "The number of SMB OPEN_ANDX requests,
             as a percentage of total CIFS calls received,
             since the last time the statistics were cleared."
    ::= { cifsObsPercent 8 }

obsSmbProcessExitPct OBJECT-TYPE
    SYNTAX          Integer32 (0..100)
    MAX-ACCESS      read-only
    STATUS          current
    DESCRIPTION     
            "The number of SMB PROCESS_EXIT requests,
             as a percentage of total CIFS calls received,
             since the last time the statistics were cleared."
    ::= { cifsObsPercent 9 }

obsSmbQueryInfoPct OBJECT-TYPE
    SYNTAX          Integer32 (0..100)
    MAX-ACCESS      read-only
    STATUS          current
    DESCRIPTION     
            "The number of SMB QUERY_INFORMATION requests,
             as a percentage of total CIFS calls received,
             since the last time the statistics were cleared."
    ::= { cifsObsPercent 10 }

obsSmbQueryInfo2Pct OBJECT-TYPE
    SYNTAX          Integer32 (0..100)
    MAX-ACCESS      read-only
    STATUS          current
    DESCRIPTION     
            "The number of SMB QUERY_INFORMATION2 requests,
             as a percentage of total CIFS calls received,
             since the last time the statistics were cleared."
    ::= { cifsObsPercent 11 }

obsSmbReadPct OBJECT-TYPE
    SYNTAX          Integer32 (0..100)
    MAX-ACCESS      read-only
    STATUS          current
    DESCRIPTION     
            "The number of SMB READ requests,
             as a percentage of total CIFS calls received,
             since the last time the statistics were cleared."
    ::= { cifsObsPercent 12 }

obsSmbReadMPXPct OBJECT-TYPE
    SYNTAX          Integer32 (0..100)
    MAX-ACCESS      read-only
    STATUS          current
    DESCRIPTION     
            "The number of SMB READ_MPX requests,
             as a percentage of total CIFS calls received,
             since the last time the statistics were cleared."
    ::= { cifsObsPercent 13 }

obsSmbReadRawPct OBJECT-TYPE
    SYNTAX          Integer32 (0..100)
    MAX-ACCESS      read-only
    STATUS          current
    DESCRIPTION     
            "The number of SMB READ_RAW requests,
             as a percentage of total CIFS calls received,
             since the last time the statistics were cleared."
    ::= { cifsObsPercent 14 }

obsSmbSearchPct OBJECT-TYPE
    SYNTAX          Integer32 (0..100)
    MAX-ACCESS      read-only
    STATUS          current
    DESCRIPTION     
            "The number of SMB SEARCH requests,
             as a percentage of total CIFS calls received,
             since the last time the statistics were cleared."
    ::= { cifsObsPercent 15 }

obsSmbSetInfoPct OBJECT-TYPE
    SYNTAX          Integer32 (0..100)
    MAX-ACCESS      read-only
    STATUS          current
    DESCRIPTION     
            "The number of SMB SET_INFORMATION requests,
             as a percentage of total CIFS calls received,
             since the last time the statistics were cleared."
    ::= { cifsObsPercent 16 }

obsSmbSetInfo2Pct OBJECT-TYPE
    SYNTAX          Integer32 (0..100)
    MAX-ACCESS      read-only
    STATUS          current
    DESCRIPTION     
            "The number of SMB SET_INFORMATION2 requests,
             as a percentage of total CIFS calls received,
             since the last time the statistics were cleared."
    ::= { cifsObsPercent 17 }

obsSmbQueryInfoDiskPct OBJECT-TYPE
    SYNTAX          Integer32 (0..100)
    MAX-ACCESS      read-only
    STATUS          current
    DESCRIPTION     
            "The number of SMB QUERY_INFORMATION_DISK
             requests, as a percentage of total CIFS calls
             received, since the last time the statistics 
             were cleared."
    ::= { cifsObsPercent 18 }

obsSmbTrans2Open2Pct OBJECT-TYPE
    SYNTAX          Integer32 (0..100)
    MAX-ACCESS      read-only
    STATUS          current
    DESCRIPTION     
            "The number of SMB TRANS2_OPEN2 requests,
             as a percentage of total CIFS calls received,
             since the last time the statistics were cleared."
    ::= { cifsObsPercent 19 }

obsSmbTreeConnectPct OBJECT-TYPE
    SYNTAX          Integer32 (0..100)
    MAX-ACCESS      read-only
    STATUS          current
    DESCRIPTION     
            "The number of SMB TREE_CONNECT requests,
             as a percentage of total CIFS calls received,
             since the last time the statistics were cleared."
    ::= { cifsObsPercent 20 }

obsSmbUnlockByteRangePct OBJECT-TYPE
    SYNTAX          Integer32 (0..100)
    MAX-ACCESS      read-only
    STATUS          current
    DESCRIPTION     
            "The number of SMB UNLOCK_BYTE_RANGE requests,
             as a percentage of total CIFS calls received,
             since the last time the statistics were cleared."
    ::= { cifsObsPercent 21 }

obsSmbWritePct OBJECT-TYPE
    SYNTAX          Integer32 (0..100)
    MAX-ACCESS      read-only
    STATUS          current
    DESCRIPTION     
            "The number of SMB WRITE requests,
             as a percentage of total CIFS calls received,
             since the last time the statistics were cleared."
    ::= { cifsObsPercent 22 }

obsSmbWriteAndUnlockPct OBJECT-TYPE
    SYNTAX          Integer32 (0..100)
    MAX-ACCESS      read-only
    STATUS          current
    DESCRIPTION     
            "The number of SMB WRITE_AND_UNLOCK requests,
             as a percentage of total CIFS calls received,
             since the last time the statistics were cleared."
    ::= { cifsObsPercent 23 }

obsSmbWriteAndClosePct OBJECT-TYPE
    SYNTAX          Integer32 (0..100)
    MAX-ACCESS      read-only
    STATUS          current
    DESCRIPTION     
            "The number of SMB WRITE_AND_CLOSE requests,
             as a percentage of total CIFS calls received,
             since the last time the statistics were cleared."
    ::= { cifsObsPercent 24 }

obsSmbWriteMPXPct OBJECT-TYPE
    SYNTAX          Integer32 (0..100)
    MAX-ACCESS      read-only
    STATUS          current
    DESCRIPTION     
            "The number of SMB WRITE_MPX requests,
             as a percentage of total CIFS calls received,
             since the last time the statistics were cleared."
    ::= { cifsObsPercent 25 }

obsSmbWritePrintFilePct OBJECT-TYPE
    SYNTAX          Integer32 (0..100)
    MAX-ACCESS      read-only
    STATUS          current
    DESCRIPTION     
            "The number of SMB WRITE_PRINT_FILE requests,
             as a percentage of total CIFS calls received,
             since the last time the statistics were cleared."
    ::= { cifsObsPercent 26 }

obsSmbWriteRawPct OBJECT-TYPE
    SYNTAX          Integer32 (0..100)
    MAX-ACCESS      read-only
    STATUS          current
    DESCRIPTION     
            "The number of SMB WRITE_RAW requests,
             as a percentage of total CIFS calls received,
             since the last time the statistics were cleared."
    ::= { cifsObsPercent 27 }

cifsMisc OBJECT IDENTIFIER
    ::= { cifs 4 }

cifsCancelLocks OBJECT-TYPE
    SYNTAX          Counter32
    MAX-ACCESS      read-only
    STATUS          current
    DESCRIPTION     
            "Undocumented"
    ::= { cifsMisc 1 }

cifsWaitLocks OBJECT-TYPE
    SYNTAX          Counter32
    MAX-ACCESS      read-only
    STATUS          current
    DESCRIPTION     
            "Undocumented"
    ::= { cifsMisc 2 }

cifsCopyToAligns OBJECT-TYPE
    SYNTAX          Counter32
    MAX-ACCESS      read-only
    STATUS          current
    DESCRIPTION     
            "Undocumented"
    ::= { cifsMisc 3 }

cifsAlignedSmalls OBJECT-TYPE
    SYNTAX          Counter32
    MAX-ACCESS      read-only
    STATUS          current
    DESCRIPTION     
            "Undocumented"
    ::= { cifsMisc 4 }

cifsAlignedLarges OBJECT-TYPE
    SYNTAX          Counter32
    MAX-ACCESS      read-only
    STATUS          current
    DESCRIPTION     
            "Undocumented"
    ::= { cifsMisc 5 }

cifsAlignedSmallRels OBJECT-TYPE
    SYNTAX          Counter32
    MAX-ACCESS      read-only
    STATUS          current
    DESCRIPTION     
            "Undocumented"
    ::= { cifsMisc 6 }

cifsAlignedLargeRels OBJECT-TYPE
    SYNTAX          Counter32
    MAX-ACCESS      read-only
    STATUS          current
    DESCRIPTION     
            "Undocumented"
    ::= { cifsMisc 7 }

cifsMbufWaits OBJECT-TYPE
    SYNTAX          Counter32
    MAX-ACCESS      read-only
    STATUS          current
    DESCRIPTION     
            "Undocumented"
    ::= { cifsMisc 8 }

cifsNbtWaits OBJECT-TYPE
    SYNTAX          Counter32
    MAX-ACCESS      read-only
    STATUS          current
    DESCRIPTION     
            "Undocumented"
    ::= { cifsMisc 9 }

cifsCwaWaits OBJECT-TYPE
    SYNTAX          Counter32
    MAX-ACCESS      read-only
    STATUS          current
    DESCRIPTION     
            "Undocumented"
    ::= { cifsMisc 10 }

cifsMultipleVCs OBJECT-TYPE
    SYNTAX          Counter32
    MAX-ACCESS      read-only
    STATUS          current
    DESCRIPTION     
            "Undocumented"
    ::= { cifsMisc 11 }

cifsPDCUpcalls OBJECT-TYPE
    SYNTAX          Counter32
    MAX-ACCESS      read-only
    STATUS          current
    DESCRIPTION     
            "Undocumented"
    ::= { cifsMisc 12 }

cifsQueuedWriteRaws OBJECT-TYPE
    SYNTAX          Counter32
    MAX-ACCESS      read-only
    STATUS          current
    DESCRIPTION     
            "Undocumented"
    ::= { cifsMisc 13 }

cifsNBTDisconnects OBJECT-TYPE
    SYNTAX          Counter32
    MAX-ACCESS      read-only
    STATUS          current
    DESCRIPTION     
            "Undocumented"
    ::= { cifsMisc 14 }

cifsSMBDisconnects OBJECT-TYPE
    SYNTAX          Counter32
    MAX-ACCESS      read-only
    STATUS          current
    DESCRIPTION     
            "Undocumented"
    ::= { cifsMisc 15 }

cifsDupDisconnects OBJECT-TYPE
    SYNTAX          Counter32
    MAX-ACCESS      read-only
    STATUS          current
    DESCRIPTION     
            "Undocumented"
    ::= { cifsMisc 16 }

cifsOpLkBatchToL2s OBJECT-TYPE
    SYNTAX          Counter32
    MAX-ACCESS      read-only
    STATUS          current
    DESCRIPTION     
            "Undocumented"
    ::= { cifsMisc 17 }

cifsOpLkBatchToNones OBJECT-TYPE
    SYNTAX          Counter32
    MAX-ACCESS      read-only
    STATUS          current
    DESCRIPTION     
            "Undocumented"
    ::= { cifsMisc 18 }

cifsOpLkL2ToNones OBJECT-TYPE
    SYNTAX          Counter32
    MAX-ACCESS      read-only
    STATUS          current
    DESCRIPTION     
            "Undocumented"
    ::= { cifsMisc 19 }

cifsOpLkNoBreakAcks OBJECT-TYPE
    SYNTAX          Counter32
    MAX-ACCESS      read-only
    STATUS          current
    DESCRIPTION     
            "Undocumented"
    ::= { cifsMisc 20 }

cifsOpLkIgnoredAcks OBJECT-TYPE
    SYNTAX          Counter32
    MAX-ACCESS      read-only
    STATUS          current
    DESCRIPTION     
            "Undocumented"
    ::= { cifsMisc 21 }

cifsOpLkMultiWaiters OBJECT-TYPE
    SYNTAX          Counter32
    MAX-ACCESS      read-only
    STATUS          current
    DESCRIPTION     
            "Undocumented"
    ::= { cifsMisc 22 }

cifsSharingErrorRetries OBJECT-TYPE
    SYNTAX          Counter32
    MAX-ACCESS      read-only
    STATUS          current
    DESCRIPTION     
            "Undocumented"
    ::= { cifsMisc 23 }

userDefined NOTIFICATION-TYPE
    STATUS          current
    DESCRIPTION     
            "A polling-style trap built using the 'traps'
             command on the filer"
    ::= { netapp 0 2 }

globalStatusNonRecoverable NOTIFICATION-TYPE
    STATUS          current
    DESCRIPTION     
            "The appliance's overall status changed to
             'nonRecoverable', indicating a problem so severe
             that the appliance is shutting down."
    ::= { netapp 0 111 }

globalStatusCritical NOTIFICATION-TYPE
    STATUS          current
    DESCRIPTION     
            "The appliance's overall status changed to 'critical',
             indicating a problem that needs immediate attention."
    ::= { netapp 0 113 }

globalStatusNonCritical NOTIFICATION-TYPE
    STATUS          current
    DESCRIPTION     
            "The appliance's overall status changed to 'nonCritical',
             indicating a problem that needs attention."
    ::= { netapp 0 115 }

globalStatusOk NOTIFICATION-TYPE
    STATUS          current
    DESCRIPTION     
            "The appliance's overall status returned to normal."
    ::= { netapp 0 116 }

END -- end of module NETWORK-APPLIANCE-MIB.
