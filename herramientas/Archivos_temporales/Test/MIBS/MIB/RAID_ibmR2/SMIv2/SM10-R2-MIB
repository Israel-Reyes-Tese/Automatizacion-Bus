--
-- This SMIv2 module has been generated by smidump 0.2-cvs. Do not edit.
--

SM10-R2-MIB DEFINITIONS ::= BEGIN

IMPORTS
    InetAddress, InetAddressType
        FROM INET-ADDRESS-MIB
    NOTIFICATION-TYPE, OBJECT-TYPE, enterprises
        FROM SNMPv2-SMI
    DisplayString
        FROM SNMPv2-TC;

engenioinformationtechnologies OBJECT IDENTIFIER
    ::= { enterprises 1123 }

wichita OBJECT IDENTIFIER
    ::= { engenioinformationtechnologies 1 }

ftcollins OBJECT IDENTIFIER
    ::= { engenioinformationtechnologies 2 }

cosprings OBJECT IDENTIFIER
    ::= { engenioinformationtechnologies 3 }

austin OBJECT IDENTIFIER
    ::= { engenioinformationtechnologies 4 }

sm10R2 OBJECT IDENTIFIER
    ::= { austin 500 }

infoTable OBJECT-TYPE
    SYNTAX          SEQUENCE OF InfoEntry
    MAX-ACCESS      not-accessible
    STATUS          current
    DESCRIPTION     
            "Information for array traps."
    ::= { sm10R2 1 }

infoEntry OBJECT-TYPE
    SYNTAX          InfoEntry
    MAX-ACCESS      not-accessible
    STATUS          current
    DESCRIPTION     
            "The data for array traps."
    INDEX           { deviceHostIPType }
    ::= { infoTable 1 }

InfoEntry ::=
    SEQUENCE {
        deviceHostIPType                InetAddressType,
        deviceHostIPAddr                InetAddress,
        deviceHostName                  DisplayString,
        deviceUserLabel                 DisplayString,
        deviceErrorCode                 DisplayString,
        eventTime                       DisplayString,
        trapDescription                 DisplayString,
        componentType                   DisplayString,
        componentLocation               DisplayString
    }

deviceHostIPType OBJECT-TYPE
    SYNTAX          InetAddressType
    MAX-ACCESS      read-only
    STATUS          current
    DESCRIPTION     
            "Type of IP Address of the network-attached device or device host. 0 unknown, 1 ipv4, 2 ipv6"
    ::= { infoEntry 1 }

deviceHostIPAddr OBJECT-TYPE
    SYNTAX          InetAddress
    MAX-ACCESS      read-only
    STATUS          current
    DESCRIPTION     
            "IP Address of the network-attached device or device host."
    ::= { infoEntry 2 }

deviceHostName OBJECT-TYPE
    SYNTAX          DisplayString (SIZE(0..17))
    MAX-ACCESS      read-only
    STATUS          current
    DESCRIPTION     
            "The user label for the host of the device being reported on."
    ::= { infoEntry 3 }

deviceUserLabel OBJECT-TYPE
    SYNTAX          DisplayString (SIZE(0..29))
    MAX-ACCESS      read-only
    STATUS          current
    DESCRIPTION     
            "The user label for the device being reported on."
    ::= { infoEntry 4 }

deviceErrorCode OBJECT-TYPE
    SYNTAX          DisplayString (SIZE(0..19))
    MAX-ACCESS      read-only
    STATUS          current
    DESCRIPTION     
            "The error code as reported by the device or host."
    ::= { infoEntry 5 }

eventTime OBJECT-TYPE
    SYNTAX          DisplayString (SIZE(0..39))
    MAX-ACCESS      read-only
    STATUS          current
    DESCRIPTION     
            "The time at which the event happen on the device."
    ::= { infoEntry 6 }

trapDescription OBJECT-TYPE
    SYNTAX          DisplayString (SIZE(0..69))
    MAX-ACCESS      read-only
    STATUS          current
    DESCRIPTION     
            "A string to indicate the nature of the trap"
    ::= { infoEntry 7 }

componentType OBJECT-TYPE
    SYNTAX          DisplayString (SIZE(0..59))
    MAX-ACCESS      read-only
    STATUS          current
    DESCRIPTION     
            "A string to identify the failing component type"
    ::= { infoEntry 8 }

componentLocation OBJECT-TYPE
    SYNTAX          DisplayString (SIZE(0..39))
    MAX-ACCESS      read-only
    STATUS          current
    DESCRIPTION     
            "A string to identify the location of the failing component"
    ::= { infoEntry 9 }

tucson OBJECT IDENTIFIER
    ::= { engenioinformationtechnologies 5 }

reston OBJECT IDENTIFIER
    ::= { engenioinformationtechnologies 6 }

boulder OBJECT IDENTIFIER
    ::= { engenioinformationtechnologies 7 }

storageArrayCritical NOTIFICATION-TYPE
    OBJECTS         { deviceHostIPType, deviceHostIPAddr, deviceHostName, 
                      deviceUserLabel, deviceErrorCode, eventTime, 
                      trapDescription, componentType, componentLocation }
    STATUS          current
    DESCRIPTION     
            "This trap indicates an event where user-interaction is required immediately.
             Some example events are component failures or critical errors."
    ::= { sm10R2 2 }

END -- end of module SM10-R2-MIB.
