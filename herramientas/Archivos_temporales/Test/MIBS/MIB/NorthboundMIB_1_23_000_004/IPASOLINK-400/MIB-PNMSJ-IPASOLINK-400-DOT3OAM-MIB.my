MIB-PNMSJ-IPASOLINK-400-DOT3OAM-MIB DEFINITIONS ::= BEGIN
    
    IMPORTS
        InterfaceIndex
            FROM IF-MIB
        OBJECT-TYPE
            FROM RFC-1212
        Counter, Gauge, IpAddress, Opaque
            FROM RFC1155-SMI
        enterprises
            FROM SNMPv2-SMI
        MacAddress
            FROM SNMPv2-TC;
    
    EnableDisableValue ::=
        INTEGER { invalid(0), disable(1), enable(2) }
    
    
    SeverityValue ::=
        INTEGER { cleared(1), indetermine(2), critical(3), major(4),
                        minor(5), warning(6) }
    
    
    -- 1.3.6.1.4.1.119
    nec OBJECT IDENTIFIER
        ::= { enterprises 119 }
    
    -- 1.3.6.1.4.1.119.2
    nec-mib OBJECT IDENTIFIER
        ::= { nec 2 }
    
    -- 1.3.6.1.4.1.119.2.3
    necProductDepend OBJECT IDENTIFIER
        ::= { nec-mib 3 }
    
    -- 1.3.6.1.4.1.119.2.3.69
    radioEquipment OBJECT IDENTIFIER
        ::= { necProductDepend 69 }
    
    -- 1.3.6.1.4.1.119.2.3.69.203
    commonPnms OBJECT IDENTIFIER
        ::= { radioEquipment 203 }
    
    -- 1.3.6.1.4.1.119.2.3.69.203.503
    ipasolink400 OBJECT IDENTIFIER
        ::= { commonPnms 503 }
    
    -- 1.3.6.1.4.1.119.2.3.69.203.503.501
    pasoNeoIpe-common OBJECT IDENTIFIER
        ::= { ipasolink400 501 }
    
    -- 1.3.6.1.4.1.119.2.3.69.203.503.501.3
    alarmStatusGroup OBJECT IDENTIFIER
        ::= { pasoNeoIpe-common 3 }
    
    -- 1.3.6.1.4.1.119.2.3.69.203.503.501.3.46
    asDot3OamGroup OBJECT IDENTIFIER
        ::= { alarmStatusGroup 46 }
    
    -- 1.3.6.1.4.1.119.2.3.69.203.503.501.3.46.1
    asDot3OamPortTable OBJECT-TYPE
        SYNTAX      SEQUENCE OF AsDot3OamPortEntry
        ACCESS      not-accessible
        STATUS      mandatory
        DESCRIPTION
            "This table contains status of the OAM capabilities of the
             interface."
        ::= { asDot3OamGroup 1 }
    
    -- 1.3.6.1.4.1.119.2.3.69.203.503.501.3.46.1.1
    asDot3OamPortEntry OBJECT-TYPE
        SYNTAX      AsDot3OamPortEntry
        ACCESS      not-accessible
        STATUS      mandatory
        DESCRIPTION
            "Entries in the table are created automatically."
        INDEX       { asDot3OamPortNEAddress, asDot3OamPortIfIndex }
        ::= { asDot3OamPortTable 1 }
    
    AsDot3OamPortEntry ::= SEQUENCE {
        asDot3OamPortIfIndex                InterfaceIndex,
        asDot3OamPortNEAddress              IpAddress,
        asDot3OamPortOperStatus             INTEGER,
        asDot3OamPortMaxOamPduSize          Gauge,
        asDot3OamPortConfigRevision         Gauge,
        asDot3OamPortFunctionsSupported     OCTET STRING
    }
    
    -- 1.3.6.1.4.1.119.2.3.69.203.503.501.3.46.1.1.1
    asDot3OamPortIfIndex OBJECT-TYPE
        SYNTAX      InterfaceIndex
        ACCESS      not-accessible
        STATUS      mandatory
        DESCRIPTION
            "Index of the entry."
        ::= { asDot3OamPortEntry 1 }
    
    -- 1.3.6.1.4.1.119.2.3.69.203.503.501.3.46.1.1.2
    asDot3OamPortNEAddress OBJECT-TYPE
        SYNTAX      IpAddress
        ACCESS      not-accessible
        STATUS      mandatory
        DESCRIPTION
            "reserved."
        ::= { asDot3OamPortEntry 2 }
    
    -- 1.3.6.1.4.1.119.2.3.69.203.503.501.3.46.1.1.3
    asDot3OamPortOperStatus OBJECT-TYPE
        SYNTAX      INTEGER { invalid(0), disabled(1), linkFault(2),
                        passiveWait(3), activeSendLocal(4),
                        sendLocalAndRemote(5), sendLocalAndRemoteOK(6),
                        oamPeeringLocallyRejected(7),
                        oamPeeringRemotelyRejected(8), operational(9),
                        nonOperHalfDuplex(10) }
        ACCESS      read-only
        STATUS      mandatory
        DESCRIPTION
            "This value is always disabled(1) if OAM is disabled on the
             interface via the provDot3OamPortEnabled.
    
             If the link has detected a fault and is transmitting OAMPDUs with
             a link fault indication or the interface is not operational, the
             value is linkFault(2).
    
             The passiveWait(3) state is returned only by OAM entities in
             passive mode and reflects the state in which the OAM entity is
             waiting to see if the peer device is OA capable. The
             activeSendLocal(4) value is used by active mode trying to
             discover whether the peer has OAM capability but has not yet made
             that determination.
    
             The state sendLocalAndRemote(5) reflects that the local OA entity
             has discovered the peer but has not yet accepted or rejected the
             configuration of the peer. The local device can, for whatever
             reason, decide that the peer device is unacceptable and decline
             OAM peering. If the local OAM entity rejects the peer OAM entity,
             the state becomes oamPeeringLocallyRejected(7). If the OAM
             peering is allowed by the local device, the state moves to
             sendLocalAndRemoteOk(6).
    
             If the remote OAM entity rejects the peering, the state becomes
             oamPeeringRemotelyRejected(8). When the local OAM entity learns
             that both it and the remote OAM entity have accepted the peering,
             the state moves to operational(9). Since Ethernet OAM functions
             are not designed to work completely over half-duplex interfaces,
             the value nonOperHalfDuplex(10) is returned whenever Ethernet OAM
             is enabled, but the interface is in half-duplex operation."
        ::= { asDot3OamPortEntry 3 }
    
    -- 1.3.6.1.4.1.119.2.3.69.203.503.501.3.46.1.1.4
    asDot3OamPortMaxOamPduSize OBJECT-TYPE
        SYNTAX      Gauge (64..1518)
        ACCESS      read-only
        STATUS      mandatory
        DESCRIPTION
            "The largest OAMPDU that the OAM entity supports. OA entities
             exchange maximum OAMPDU sizes and negotiate to use the smaller of
             the two maximum OAMPDU sizes between the peers."
        ::= { asDot3OamPortEntry 4 }
    
    -- 1.3.6.1.4.1.119.2.3.69.203.503.501.3.46.1.1.5
    asDot3OamPortConfigRevision OBJECT-TYPE
        SYNTAX      Gauge (0..65535)
        ACCESS      read-only
        STATUS      mandatory
        DESCRIPTION
            "The configuration revision of the OAM entity as reflected in the
             latest OAMPDU sent by the OAM entity. The config revision is used
             by OAM entities to indicate that configuration changes have
             occurred, which might require the peer OAM entity to re-evaluate
             whether OAM peering is allowed."
        ::= { asDot3OamPortEntry 5 }
    
    -- 1.3.6.1.4.1.119.2.3.69.203.503.501.3.46.1.1.6
    asDot3OamPortFunctionsSupported OBJECT-TYPE
        SYNTAX      OCTET STRING
        ACCESS      read-only
        STATUS      mandatory
        DESCRIPTION
            "The OAM functions supported on this interface. OAM consists of
             separate functional sets beyond the basic discovery process that
             is always required. These functional groups can be supported
             independently by any implementation. These values are
             communicated to the peer via the local configuration field of
             Information OAMPDUs.
    
             Setting unidirectionalSupport(0) indicates that the OA entity
             supports the transmission of OAMPDUs on links that are operating
             in unidirectional mode. Setting loopbackSupport(1) indicates that
             the OAM entity can initiate and respond to loopback commands.
             Setting eventSupport(2) indicates that the OAM entity can send
             and receive Event Notification OAMPDUs. Setting
             variableSupport(3) indicates that the OAM entity can send and
             receive Variable Request and Response OAMPDUs."
        ::= { asDot3OamPortEntry 6 }
    
    -- 1.3.6.1.4.1.119.2.3.69.203.503.501.3.46.2
    asDot3OamPeerTable OBJECT-TYPE
        SYNTAX      SEQUENCE OF AsDot3OamPeerEntry
        ACCESS      not-accessible
        STATUS      mandatory
        DESCRIPTION
            "This table contains information about the OAM peer for a
             particular interface. OAM entities communicates with a single OAM
             peer entity on Ethernet links."
        ::= { asDot3OamGroup 2 }
    
    -- 1.3.6.1.4.1.119.2.3.69.203.503.501.3.46.2.1
    asDot3OamPeerEntry OBJECT-TYPE
        SYNTAX      AsDot3OamPeerEntry
        ACCESS      not-accessible
        STATUS      mandatory
        DESCRIPTION
            "An entry in the table containing information on the peer entity
             for a single interface.
    
             Note that there is at most on OAM peer for each interface. Peer
             information is not reliable when asDot3OamPortStatus is
             disabled(1), linkFault(2), passiveWait(3), activeSendLocal(4), or
             nonOperHalfDuplex(10)."
        INDEX       { asDot3OamPeerNEAddress, asDot3OamPeerIfIndex }
        ::= { asDot3OamPeerTable 1 }
    
    AsDot3OamPeerEntry ::= SEQUENCE {
        asDot3OamPeerIfIndex                InterfaceIndex,
        asDot3OamPeerNEAddress              IpAddress,
        asDot3OamPeerMacAddress             MacAddress,
        asDot3OamPeerVendorOui              OCTET STRING,
        asDot3OamPeerVendorInfo             Gauge,
        asDot3OamPeerMode                   INTEGER,
        asDot3OamPeerMaxOamPduSize          Gauge,
        asDot3OamPeerConfigRevision         Gauge,
        asDot3OamPeerFunctionsSupported     OCTET STRING
    }
    
    -- 1.3.6.1.4.1.119.2.3.69.203.503.501.3.46.2.1.1
    asDot3OamPeerIfIndex OBJECT-TYPE
        SYNTAX      InterfaceIndex
        ACCESS      not-accessible
        STATUS      mandatory
        DESCRIPTION
            "Index of this table."
        ::= { asDot3OamPeerEntry 1 }
    
    -- 1.3.6.1.4.1.119.2.3.69.203.503.501.3.46.2.1.2
    asDot3OamPeerNEAddress OBJECT-TYPE
        SYNTAX      IpAddress
        ACCESS      not-accessible
        STATUS      mandatory
        DESCRIPTION
            "reserved."
        ::= { asDot3OamPeerEntry 2 }
    
    -- 1.3.6.1.4.1.119.2.3.69.203.503.501.3.46.2.1.3
    asDot3OamPeerMacAddress OBJECT-TYPE
        SYNTAX      MacAddress
        ACCESS      read-only
        STATUS      mandatory
        DESCRIPTION
            "The MAC address of the peer OAM entity. The MAC address is
             derived from the most recently received OAMPDU."
        ::= { asDot3OamPeerEntry 3 }
    
    -- 1.3.6.1.4.1.119.2.3.69.203.503.501.3.46.2.1.4
    asDot3OamPeerVendorOui OBJECT-TYPE
        SYNTAX      OCTET STRING (SIZE(3))
        ACCESS      read-only
        STATUS      mandatory
        DESCRIPTION
            "The OUI of the OAM peer as reflected in the latest Information
             OAMPDU received with a Local Information TLV. The OUI can be used
             to identify the vendor of the remote OA entity. This value is
             initialized to three octets of zero before any Local Information
             TLV is received."
        ::= { asDot3OamPeerEntry 4 }
    
    -- 1.3.6.1.4.1.119.2.3.69.203.503.501.3.46.2.1.5
    asDot3OamPeerVendorInfo OBJECT-TYPE
        SYNTAX      Gauge
        ACCESS      read-only
        STATUS      mandatory
        DESCRIPTION
            "The Vendor Info of the OAM peer as reflected in the latest
             Information OAMPDU received with a Local Information TLV.
             The semantics of the Vendor Information field is proprietary and
             specific to the vendor. This value is initialized to zero before
             any Local Information TLV is received."
        ::= { asDot3OamPeerEntry 5 }
    
    -- 1.3.6.1.4.1.119.2.3.69.203.503.501.3.46.2.1.6
    asDot3OamPeerMode OBJECT-TYPE
        SYNTAX      INTEGER { invalid(0), passive(1), active(2), unknown(3) }
        ACCESS      read-only
        STATUS      mandatory
        DESCRIPTION
            "The mode of the OAM peer as reflected in the latest Information
             OAMPDU received with a Local Information TLV. The mode of the
             peer can be determined from the Configuration field in the Local
             Information TLV of the last Information OAMPDU received from the
             peer. The value is unknown(3) whenever no Local Information TLV
             has been received. The values of active(2) and passive(1) are
             returned when a Local Information TLV has been received
             indicating that the peer is in active or passive mode,
             respectively."
        ::= { asDot3OamPeerEntry 6 }
    
    -- 1.3.6.1.4.1.119.2.3.69.203.503.501.3.46.2.1.7
    asDot3OamPeerMaxOamPduSize OBJECT-TYPE
        SYNTAX      Gauge (0 | 64..1518)
        ACCESS      read-only
        STATUS      mandatory
        DESCRIPTION
            "The maximum size of OAMPDU supported by the peer as reflected in
             the latest Information OAMPDU received with a Local Information
             TLV. Ethernet OAM on this interface must not use OAMPDUs that
             exceed this size. The maximum OAMPDU size can be determined from
             the PDU Configuration field of the Local Information TLV of the
             last Information OAMPDU received from the peer. A value of zero
             is returned if no Local Information TLV has been received.
             Otherwise, the value of the OAM peer's maximum OAMPDU size is
             returned in this value."
        ::= { asDot3OamPeerEntry 7 }
    
    -- 1.3.6.1.4.1.119.2.3.69.203.503.501.3.46.2.1.8
    asDot3OamPeerConfigRevision OBJECT-TYPE
        SYNTAX      Gauge (0..65535)
        ACCESS      read-only
        STATUS      mandatory
        DESCRIPTION
            "The configuration revision of the OAM peer as reflected in the
             latest OAMPDU. This attribute is changed by the peer whenever it
             has a local configuration change for Ethernet OA on this
             interface. The configuration revision can be determined from the
             Revision field of the Local Information TLV of the most recently
             received Information OAMPDU with a Local Information TLV. A value
             of zero is returned if no Local Information TLV has been
             received."
        ::= { asDot3OamPeerEntry 8 }
    
    -- 1.3.6.1.4.1.119.2.3.69.203.503.501.3.46.2.1.9
    asDot3OamPeerFunctionsSupported OBJECT-TYPE
        SYNTAX      OCTET STRING
        ACCESS      read-only
        STATUS      mandatory
        DESCRIPTION
            "The OAM functions supported on the interface. OAM consists of
             separate functionality sets above the basic discovery process.
             This value indicates the capabilities of the peer OAM entity with
             respect to these functions. This value is initialized so all bits
             are clear.
    
             If unidirectionalSupport(0) is set, the the peer OAM entity
             supports sending OAM frames on the interfaces when the receive
             path is known to be inoperable. If loopbackSupport(1) is set,
             then the peer OAM entity can send and receive OAM loopback
             commands. If eventSupport(2) is set, then the peer OAM entity can
             send and receive event OAMPDUs to signal various error
             conditions. If variableSupport(3) is set, then the peer OAM
             entity can send and receive variable requests to monitor the
             attribute value.
    
             The capabilities of the OAM peer can be determined from the
             configuration field of the Local Information TLV of the most
             recently received Information OAMPDU with a Local Information
             TLV. All zeros are returned if no Local Information TLV has yet
             been received."
        ::= { asDot3OamPeerEntry 9 }
    
    -- 1.3.6.1.4.1.119.2.3.69.203.503.501.3.46.3
    asDot3OamPortStatsTable OBJECT-TYPE
        SYNTAX      SEQUENCE OF AsDot3OamPortStatsEntry
        ACCESS      not-accessible
        STATUS      mandatory
        DESCRIPTION
            "This table contains statistics for the OAM function on a
             particular interface. There is an entry in the table for every
             asDot3OamPortTable."
        ::= { asDot3OamGroup 3 }
    
    -- 1.3.6.1.4.1.119.2.3.69.203.503.501.3.46.3.1
    asDot3OamPortStatsEntry OBJECT-TYPE
        SYNTAX      AsDot3OamPortStatsEntry
        ACCESS      not-accessible
        STATUS      mandatory
        DESCRIPTION
            "An entry in the table containing statistics information on the
             Ethernet OAM function for a single interface. Entries are
             automatically created for every entry in the asDot3OamPortTable.
             Counters are maintained across transitions in
             asDot3OamPortStatus."
        INDEX       { asDot3OamPortStatsNEAddress, asDot3OamPortStatsIfIndex }
        ::= { asDot3OamPortStatsTable 1 }
    
    AsDot3OamPortStatsEntry ::= SEQUENCE {
        asDot3OamPortStatsIfIndex       InterfaceIndex,
        asDot3OamPortStatsNEAddress     IpAddress,
        asDot3OamInformationTx          Counter,
        asDot3OamInformationRx          Counter,
        asDot3OamUniqueEventNotifTx     Counter,
        asDot3OamUniqueEventNotifRx     Counter,
        asDot3OamDuplicateEventNotifTx  Counter,
        asDot3OamDuplicateEventNotifRx  Counter,
        asDot3OamLoopbackControlTx      Counter,
        asDot3OamLoopbackControlRx      Counter,
        asDot3OamVariableRequestTx      Counter,
        asDot3OamVariableRequestRx      Counter,
        asDot3OamVariableResponseTx     Counter,
        asDot3OamVariableResponseRx     Counter,
        asDot3OamOrgSpecificTx          Counter,
        asDot3OamOrgSpecificRx          Counter,
        asDot3OamUnsupportedCodesTx     Counter,
        asDot3OamUnsupportedCodesRx     Counter,
        asDot3OamFramesLostDueToOam     Counter
    }
    
    -- 1.3.6.1.4.1.119.2.3.69.203.503.501.3.46.3.1.1
    asDot3OamPortStatsIfIndex OBJECT-TYPE
        SYNTAX      InterfaceIndex
        ACCESS      not-accessible
        STATUS      mandatory
        DESCRIPTION
            "Index of this table."
        ::= { asDot3OamPortStatsEntry 1 }
    
    -- 1.3.6.1.4.1.119.2.3.69.203.503.501.3.46.3.1.2
    asDot3OamPortStatsNEAddress OBJECT-TYPE
        SYNTAX      IpAddress
        ACCESS      not-accessible
        STATUS      mandatory
        DESCRIPTION
            "reserved."
        ::= { asDot3OamPortStatsEntry 2 }
    
    -- 1.3.6.1.4.1.119.2.3.69.203.503.501.3.46.3.1.3
    asDot3OamInformationTx OBJECT-TYPE
        SYNTAX      Counter
        ACCESS      read-only
        STATUS      mandatory
        DESCRIPTION
            "A count of the number of Information OAMPDUs transmitted on the
             interface."
        ::= { asDot3OamPortStatsEntry 3 }
    
    -- 1.3.6.1.4.1.119.2.3.69.203.503.501.3.46.3.1.4
    asDot3OamInformationRx OBJECT-TYPE
        SYNTAX      Counter
        ACCESS      read-only
        STATUS      mandatory
        DESCRIPTION
            "A count of the number of Information OAMPDUs received on the
             interface."
        ::= { asDot3OamPortStatsEntry 4 }
    
    -- 1.3.6.1.4.1.119.2.3.69.203.503.501.3.46.3.1.5
    asDot3OamUniqueEventNotifTx OBJECT-TYPE
        SYNTAX      Counter
        ACCESS      read-only
        STATUS      mandatory
        DESCRIPTION
            "A count of the number of unique Event OAMPDUs transmitted on the
             interface. Event Notifications may be sent in duplicate to
             increase the probability of successfully being received, given
             the possibility that a frame may be lost in transit. Duplicate
             Event Notification transmissions are counted by
             asDot3OamDuplicatedEventNotifTx.
    
             A unique Event Notification OAMPDU is indicated as an Event
             Notification OAMPDU with a Sequence Number field that is distinct
             from the previously transmitted Event Notification OAMPDU
             Sequence Number."
        ::= { asDot3OamPortStatsEntry 5 }
    
    -- 1.3.6.1.4.1.119.2.3.69.203.503.501.3.46.3.1.6
    asDot3OamUniqueEventNotifRx OBJECT-TYPE
        SYNTAX      Counter
        ACCESS      read-only
        STATUS      mandatory
        DESCRIPTION
            "A count of the number of unique Event OAMPDUs received on the
             interface. Event Notifications may be sent in duplicate to
             increase the probability of successfully being received, given
             the possibility that a frame may be lost in transit. Duplicate
             Event Notification receptions are counted by
             asDot3OamDuplicateEventNotifRx.
    
             A unique Event Notification OAMPDU is indicated as an Event
             Notification OAMPDU with a Sequence Nubmer field that is distinct
             from the previously received Event Notification OAMPDU Sequence
             Number."
        ::= { asDot3OamPortStatsEntry 6 }
    
    -- 1.3.6.1.4.1.119.2.3.69.203.503.501.3.46.3.1.7
    asDot3OamDuplicateEventNotifTx OBJECT-TYPE
        SYNTAX      Counter
        ACCESS      read-only
        STATUS      mandatory
        DESCRIPTION
            "A count of the number of duplicate Event OAMPDUs transmitted on
             the interface. Event Notification OAMPDUs may be sent in
             duplicate to increase the probability of successfully being
             received, given the possibility that a frame may be lost in
             transit.
    
             A duplicate Event Notification OAMPDU is indicated as an Event
             Notification OAMPDU with a Sequence Number field that is
             identical to the previously transmitted Event Notification OAMPDU
             Sequence Number."
        ::= { asDot3OamPortStatsEntry 7 }
    
    -- 1.3.6.1.4.1.119.2.3.69.203.503.501.3.46.3.1.8
    asDot3OamDuplicateEventNotifRx OBJECT-TYPE
        SYNTAX      Counter
        ACCESS      read-only
        STATUS      mandatory
        DESCRIPTION
            "A count of the number of duplicate Event OAMPDUs received on the
             interface. Event Notification OAMPDUs may be sent in duplicate to
             increase the probability of successfully being received, given
             the possibility that a frame may be lost in transit.
    
             A duplicate Event Notification OAMPDU is indicated as an Event
             Notification OAMPDU with a Sequence Number field that is
             identical to the previously received Event Notification OAMPDU
             Sequence Number."
        ::= { asDot3OamPortStatsEntry 8 }
    
    -- 1.3.6.1.4.1.119.2.3.69.203.503.501.3.46.3.1.9
    asDot3OamLoopbackControlTx OBJECT-TYPE
        SYNTAX      Counter
        ACCESS      read-only
        STATUS      mandatory
        DESCRIPTION
            "A count of the number of Loopback Control OAMPDUs transmitted on
             the interface."
        ::= { asDot3OamPortStatsEntry 9 }
    
    -- 1.3.6.1.4.1.119.2.3.69.203.503.501.3.46.3.1.10
    asDot3OamLoopbackControlRx OBJECT-TYPE
        SYNTAX      Counter
        ACCESS      read-only
        STATUS      mandatory
        DESCRIPTION
            "A count of the number of Loopback Control OAMPDUs received on
             the interface."
        ::= { asDot3OamPortStatsEntry 10 }
    
    -- 1.3.6.1.4.1.119.2.3.69.203.503.501.3.46.3.1.11
    asDot3OamVariableRequestTx OBJECT-TYPE
        SYNTAX      Counter
        ACCESS      read-only
        STATUS      mandatory
        DESCRIPTION
            "A count of the number of Variable Request OAMPDUs transmitted on
             the interface."
        ::= { asDot3OamPortStatsEntry 11 }
    
    -- 1.3.6.1.4.1.119.2.3.69.203.503.501.3.46.3.1.12
    asDot3OamVariableRequestRx OBJECT-TYPE
        SYNTAX      Counter
        ACCESS      read-only
        STATUS      mandatory
        DESCRIPTION
            "A count of the number of Variable Request OAMPDUs received on
             the interface."
        ::= { asDot3OamPortStatsEntry 12 }
    
    -- 1.3.6.1.4.1.119.2.3.69.203.503.501.3.46.3.1.13
    asDot3OamVariableResponseTx OBJECT-TYPE
        SYNTAX      Counter
        ACCESS      read-only
        STATUS      mandatory
        DESCRIPTION
            "A count of the number of Variable Response OAMPDUs transmitted
             on the interface."
        ::= { asDot3OamPortStatsEntry 13 }
    
    -- 1.3.6.1.4.1.119.2.3.69.203.503.501.3.46.3.1.14
    asDot3OamVariableResponseRx OBJECT-TYPE
        SYNTAX      Counter
        ACCESS      read-only
        STATUS      mandatory
        DESCRIPTION
            "A count of the number of Variable Response OAMPDUs received on
             the interface."
        ::= { asDot3OamPortStatsEntry 14 }
    
    -- 1.3.6.1.4.1.119.2.3.69.203.503.501.3.46.3.1.15
    asDot3OamOrgSpecificTx OBJECT-TYPE
        SYNTAX      Counter
        ACCESS      read-only
        STATUS      mandatory
        DESCRIPTION
            "A count of the number of Organization Specific OAMPDUs
             transmitted on the interface."
        ::= { asDot3OamPortStatsEntry 15 }
    
    -- 1.3.6.1.4.1.119.2.3.69.203.503.501.3.46.3.1.16
    asDot3OamOrgSpecificRx OBJECT-TYPE
        SYNTAX      Counter
        ACCESS      read-only
        STATUS      mandatory
        DESCRIPTION
            "A count of the number of Organization Specific OAMPDUs received
             on the interface."
        ::= { asDot3OamPortStatsEntry 16 }
    
    -- 1.3.6.1.4.1.119.2.3.69.203.503.501.3.46.3.1.17
    asDot3OamUnsupportedCodesTx OBJECT-TYPE
        SYNTAX      Counter
        ACCESS      read-only
        STATUS      mandatory
        DESCRIPTION
            "A count of the number of OAMPDUs transmitted on the interface
             with an unsupported op-code."
        ::= { asDot3OamPortStatsEntry 17 }
    
    -- 1.3.6.1.4.1.119.2.3.69.203.503.501.3.46.3.1.18
    asDot3OamUnsupportedCodesRx OBJECT-TYPE
        SYNTAX      Counter
        ACCESS      read-only
        STATUS      mandatory
        DESCRIPTION
            "A count of the number of OAMPDUs received on the interface with
             an unsupported op-code."
        ::= { asDot3OamPortStatsEntry 18 }
    
    -- 1.3.6.1.4.1.119.2.3.69.203.503.501.3.46.3.1.19
    asDot3OamFramesLostDueToOam OBJECT-TYPE
        SYNTAX      Counter
        ACCESS      read-only
        STATUS      mandatory
        DESCRIPTION
            "A count of the number of frames that were dropped by the OA
             multiplexer. Since the OAM multiplexer has multiple inputs and a
             single output, there may be cases where frames are dropped due to
             transmit resource contention. This counter is incremented
             whenever a fram is dropped by the OAM layer.
             Note that any Ethernet frame, not just OAMPDUs, may be dropped by
             the OAM layer. This can occur when an OAMPDU takes precedence
             over a 'normal' frame resulting in the 'normal' frame being
             dropped.
    
             When this counter is incremented, no other counters in ths MIB
             are incremented."
        ::= { asDot3OamPortStatsEntry 19 }
    
    -- 1.3.6.1.4.1.119.2.3.69.203.503.501.3.46.4
    asDot3OamPortAlarmTable OBJECT-TYPE
        SYNTAX      SEQUENCE OF AsDot3OamPortAlarmEntry
        ACCESS      not-accessible
        STATUS      mandatory
        DESCRIPTION
            "This table contains alarm & status information of the
             interface."
        ::= { asDot3OamGroup 4 }
    
    -- 1.3.6.1.4.1.119.2.3.69.203.503.501.3.46.4.1
    asDot3OamPortAlarmEntry OBJECT-TYPE
        SYNTAX      AsDot3OamPortAlarmEntry
        ACCESS      not-accessible
        STATUS      mandatory
        DESCRIPTION
            "An entry in the table containing alarm & status information on
             the Ethernet OAM function for a single interface. Entries are
             automatically created for enery entry in the asDot3OamPortTable."
        INDEX       { asDot3OamPortAlarmNEAddress, asDot3OamPortAlarmIfIndex }
        ::= { asDot3OamPortAlarmTable 1 }
    
    AsDot3OamPortAlarmEntry ::= SEQUENCE {
        asDot3OamPortAlarmIfIndex                   InterfaceIndex,
        asDot3OamPortAlarmNEAddress                 IpAddress,
        asDot3OamPortLinkOamDown                    SeverityValue,
        asDot3OamPortLocalDyingGasp                 INTEGER,
        asDot3OamPortLocalCriticalEvent             INTEGER,
        asDot3OamPortRemoteErroredSymbolEvent       INTEGER,
        asDot3OamPortRemoteErroredFramePeriodEvent  INTEGER,
        asDot3OamPortRemoteErroredFrameEvent        INTEGER,
        asDot3OamPortRemoteErroredFrameSecondEvent  INTEGER,
        asDot3OamPortRemoteLinkFault                SeverityValue,
        asDot3OamPortRemoteDyingGasp                SeverityValue,
        asDot3OamPortRemoteCriticalEvent            SeverityValue
    }
    
    -- 1.3.6.1.4.1.119.2.3.69.203.503.501.3.46.4.1.1
    asDot3OamPortAlarmIfIndex OBJECT-TYPE
        SYNTAX      InterfaceIndex
        ACCESS      not-accessible
        STATUS      mandatory
        DESCRIPTION
            "Index of this table."
        ::= { asDot3OamPortAlarmEntry 1 }
    
    -- 1.3.6.1.4.1.119.2.3.69.203.503.501.3.46.4.1.2
    asDot3OamPortAlarmNEAddress OBJECT-TYPE
        SYNTAX      IpAddress
        ACCESS      not-accessible
        STATUS      mandatory
        DESCRIPTION
            "reserved."
        ::= { asDot3OamPortAlarmEntry 2 }
    
    -- 1.3.6.1.4.1.119.2.3.69.203.503.501.3.46.4.1.3
    asDot3OamPortLinkOamDown OBJECT-TYPE
        SYNTAX      SeverityValue
        ACCESS      read-only
        STATUS      mandatory
        DESCRIPTION
            "The alarm status of the OAM function status. When the Discovery
             State of the interface is not in SEND_ANY, the object becomes
             alarm state."
        ::= { asDot3OamPortAlarmEntry 3 }
    
    -- 1.3.6.1.4.1.119.2.3.69.203.503.501.3.46.4.1.4
    asDot3OamPortLocalDyingGasp OBJECT-TYPE
        SYNTAX      INTEGER { invalid(0), normal(1), generated(2) }
        ACCESS      read-only
        STATUS      mandatory
        DESCRIPTION
            "Generating Dying Gasp OAMPDU status.
             If the OAM entity sends the DyingGasp OAMPDUs, the object will
             return the value 'generated'."
        ::= { asDot3OamPortAlarmEntry 4 }
    
    -- 1.3.6.1.4.1.119.2.3.69.203.503.501.3.46.4.1.5
    asDot3OamPortLocalCriticalEvent OBJECT-TYPE
        SYNTAX      INTEGER { invalid(0), normal(1), generated(2) }
        ACCESS      read-only
        STATUS      mandatory
        DESCRIPTION
            "Generating Critical Event OAMPDU status.
             If the OAM entity sends the CriticalEvent OAMPDUs, the object
             will return the value 'generated'."
        ::= { asDot3OamPortAlarmEntry 5 }
    
    -- 1.3.6.1.4.1.119.2.3.69.203.503.501.3.46.4.1.6
    asDot3OamPortRemoteErroredSymbolEvent OBJECT-TYPE
        SYNTAX      INTEGER { invalid(0), normal(1), received(2) }
        ACCESS      read-only
        STATUS      mandatory
        DESCRIPTION
            "Receiving Errored Symbol Event OAMPDU status.
             If the OAM entity receives the ErroredSymbolEvent OAMPDUs from
             peer, the object will show the value 'received'."
        ::= { asDot3OamPortAlarmEntry 6 }
    
    -- 1.3.6.1.4.1.119.2.3.69.203.503.501.3.46.4.1.7
    asDot3OamPortRemoteErroredFramePeriodEvent OBJECT-TYPE
        SYNTAX      INTEGER { invalid(0), normal(1), received(2) }
        ACCESS      read-only
        STATUS      mandatory
        DESCRIPTION
            "Receiving Errored Frame Period Event OAMPDU status.
             If the OAM entity receives the ErroredFramePeriodEvent OAMPDUs
             from peer, the object will show the value 'received'."
        ::= { asDot3OamPortAlarmEntry 7 }
    
    -- 1.3.6.1.4.1.119.2.3.69.203.503.501.3.46.4.1.8
    asDot3OamPortRemoteErroredFrameEvent OBJECT-TYPE
        SYNTAX      INTEGER { invalid(0), normal(1), received(2) }
        ACCESS      read-only
        STATUS      mandatory
        DESCRIPTION
            "Receiving Errored Frame Event OAMPDU status.
             If the OAM entity receives the ErroredFrameEvent OAMPDUs from
             peer, the object will show the value 'received'."
        ::= { asDot3OamPortAlarmEntry 8 }
    
    -- 1.3.6.1.4.1.119.2.3.69.203.503.501.3.46.4.1.9
    asDot3OamPortRemoteErroredFrameSecondEvent OBJECT-TYPE
        SYNTAX      INTEGER { invalid(0), normal(1), received(2) }
        ACCESS      read-only
        STATUS      mandatory
        DESCRIPTION
            "Receiving Errored Frame Second Event OAMPDU status.
             If the OAM entity receives the ErroredFrameSecondEvent OAMPDUs
             from peer, the object will show the value 'received'."
        ::= { asDot3OamPortAlarmEntry 9 }
    
    -- 1.3.6.1.4.1.119.2.3.69.203.503.501.3.46.4.1.10
    asDot3OamPortRemoteLinkFault OBJECT-TYPE
        SYNTAX      SeverityValue
        ACCESS      read-only
        STATUS      mandatory
        DESCRIPTION
            "Receiving Link Fault OAMPDU.
             If the OAM entity receives the LinkFault OAMPDUs from peer, the
             object will report Link Fault Alarm of the interface."
        ::= { asDot3OamPortAlarmEntry 10 }
    
    -- 1.3.6.1.4.1.119.2.3.69.203.503.501.3.46.4.1.11
    asDot3OamPortRemoteDyingGasp OBJECT-TYPE
        SYNTAX      SeverityValue
        ACCESS      read-only
        STATUS      mandatory
        DESCRIPTION
            "Receiving DyingGasp OAMPDU.
             If the OAM entity receives the DyingGasp OAMPDUs from peer, the
             object will report DyingGasp Alarm of the interface."
        ::= { asDot3OamPortAlarmEntry 11 }
    
    -- 1.3.6.1.4.1.119.2.3.69.203.503.501.3.46.4.1.12
    asDot3OamPortRemoteCriticalEvent OBJECT-TYPE
        SYNTAX      SeverityValue
        ACCESS      read-only
        STATUS      mandatory
        DESCRIPTION
            "Receiving Critial Event OAMPDU.
             If the OAM entity receives the CriticalEvent OAMPDUs from peer,
             the object will report CriticalEvent Alarm of the interface."
        ::= { asDot3OamPortAlarmEntry 12 }
    
END -- end of module MIB-PNMSJ-IPASOLINK-400-DOT3OAM-MIB.
