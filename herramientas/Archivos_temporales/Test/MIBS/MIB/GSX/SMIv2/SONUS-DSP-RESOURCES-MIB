--
-- This SMIv2 module has been generated by smidump 0.2-cvs. Do not edit.
--

SONUS-DSP-RESOURCES-MIB DEFINITIONS ::= BEGIN

IMPORTS
    Gauge32, Integer32, MODULE-IDENTITY, NOTIFICATION-TYPE, OBJECT-TYPE
        FROM SNMPv2-SMI
    DisplayString, RowStatus
        FROM SNMPv2-TC
    sonusEventClass, sonusEventDescription, sonusEventLevel, 
    sonusEventTime, sonusSequenceId, sonusShelfIndex, sonusSlotIndex
        FROM SONUS-COMMON-MIB
    sonusResourcesMIBs
        FROM SONUS-SMI
    SonusAdminState, SonusName, SonusServiceState, SonusShelfIndex, 
    SonusSlotIndex
        FROM SONUS-TC;

sonusDspResourcesMIB MODULE-IDENTITY
    LAST-UPDATED    "201511010000Z"
    ORGANIZATION    
            "Sonus Networks, Inc."
    CONTACT-INFO    
            "   Customer Support    
             Sonus Networks, Inc.
             7 Technology Park Drive
             Westford, MA 01886
             USA
             
             Tel: 978-614-8100
             Fax: 978-614-8609"
    DESCRIPTION     
            "The MIB Module for DSP Resources Management."
    ::= { sonusResourcesMIBs 1 }


sonusDspResourcesMIBObjects OBJECT IDENTIFIER
    ::= { sonusDspResourcesMIB 1 }

sonusChannelStatTable OBJECT IDENTIFIER
    ::= { sonusDspResourcesMIBObjects 1 }

sonusDspAdmnTable OBJECT-TYPE
    SYNTAX          SEQUENCE OF SonusDspAdmnEntry
    MAX-ACCESS      not-accessible
    STATUS          current
    DESCRIPTION     
            "Table of Sonus Enterprise DSP Admn information"
    ::= { sonusDspResourcesMIBObjects 2 }

sonusDspAdmnEntry OBJECT-TYPE
    SYNTAX          SonusDspAdmnEntry
    MAX-ACCESS      not-accessible
    STATUS          current
    DESCRIPTION     
            "Entry in Table consisting of the all the Sonus DSP ADMN information"
    INDEX           { sonusDspAdmnShelfIndex, sonusDspAdmnSlotIndex, 
                      sonusDspAdmnDspIndex }
    ::= { sonusDspAdmnTable 1 }

SonusDspAdmnEntry ::=
    SEQUENCE {
        sonusDspAdmnShelfIndex          SonusShelfIndex,
        sonusDspAdmnSlotIndex           SonusSlotIndex,
        sonusDspAdmnDspIndex            Integer32,
        sonusDspAdmnType                INTEGER,
        sonusDspAdmnNumChannels         Integer32,
        sonusDspAdmnMaxTail             INTEGER,
        sonusDspAdmnEcAudioType         INTEGER,
        sonusDspAdmnEcSignallingTone    INTEGER,
        sonusDspAdmnNlpDisable          Integer32,
        sonusDspAdmnNlpEnable           Integer32,
        sonusDspAdmnJitterEvalPeriod    Integer32,
        sonusDspAdmnJitterMinOccThsh    Integer32,
        sonusDspResidualEchoControl     INTEGER,
        sonusDspEchoReturnLoss          INTEGER,
        sonusDspModemDisable            INTEGER,
        sonusDspHighLevelComp           INTEGER
    }

sonusDspAdmnShelfIndex OBJECT-TYPE
    SYNTAX          SonusShelfIndex
    MAX-ACCESS      read-only
    STATUS          current
    DESCRIPTION     
            "Shelf Index for this table"
    ::= { sonusDspAdmnEntry 1 }

sonusDspAdmnSlotIndex OBJECT-TYPE
    SYNTAX          SonusSlotIndex
    MAX-ACCESS      read-only
    STATUS          current
    DESCRIPTION     
            "Slot index for this table"
    ::= { sonusDspAdmnEntry 2 }

sonusDspAdmnDspIndex OBJECT-TYPE
    SYNTAX          Integer32
    MAX-ACCESS      read-only
    STATUS          current
    DESCRIPTION     
            "DSP index into this table"
    ::= { sonusDspAdmnEntry 3 }

sonusDspAdmnType OBJECT-TYPE
    SYNTAX          INTEGER { vpad(1), hdlc(2), g729AB(3), tone(4), 
                        g7231(5), g726(6), universalcompression(8) }
    MAX-ACCESS      read-write
    STATUS          current
    DESCRIPTION     
            "DSP Function Type, VPAD XPAD TONE etc."
    ::= { sonusDspAdmnEntry 4 }

sonusDspAdmnNumChannels OBJECT-TYPE
    SYNTAX          Integer32
    MAX-ACCESS      read-write
    STATUS          current
    DESCRIPTION     
            "Number of channels on this DSP"
    ::= { sonusDspAdmnEntry 5 }

sonusDspAdmnMaxTail OBJECT-TYPE
    SYNTAX          INTEGER { millisecs24(1), millisec32(2), 
                        millisec48(3), millisec64(4) }
    MAX-ACCESS      read-write
    STATUS          current
    DESCRIPTION     
            "Maximum Echo tail length"
    DEFVAL          { millisec64 }
    ::= { sonusDspAdmnEntry 6 }

sonusDspAdmnEcAudioType OBJECT-TYPE
    SYNTAX          INTEGER { uLaw(1), aLaw(2) }
    MAX-ACCESS      read-write
    STATUS          current
    DESCRIPTION     
            "Echo Cancellation: A-law or U-law"
    DEFVAL          { uLaw }
    ::= { sonusDspAdmnEntry 7 }

sonusDspAdmnEcSignallingTone OBJECT-TYPE
    SYNTAX          INTEGER { none(1), c5(2) }
    MAX-ACCESS      read-write
    STATUS          current
    DESCRIPTION     
            "Echo Cancellation: None, 2400, 2600 or 2101 Hz"
    DEFVAL          { none }
    ::= { sonusDspAdmnEntry 8 }

sonusDspAdmnNlpDisable OBJECT-TYPE
    SYNTAX          Integer32 (0..15)
    MAX-ACCESS      read-write
    STATUS          current
    DESCRIPTION     
            "Non-linear processing control, Disable"
    DEFVAL          { 6 }
    ::= { sonusDspAdmnEntry 9 }

sonusDspAdmnNlpEnable OBJECT-TYPE
    SYNTAX          Integer32 (0..15)
    MAX-ACCESS      read-write
    STATUS          current
    DESCRIPTION     
            "Non-linear processing control, Enable"
    DEFVAL          { 12 }
    ::= { sonusDspAdmnEntry 10 }

sonusDspAdmnJitterEvalPeriod OBJECT-TYPE
    SYNTAX          Integer32 (0..65535)
    MAX-ACCESS      read-write
    STATUS          current
    DESCRIPTION     
            "Time period to decide when to periodically evaluate playout
             occupancy in units of 1.25 msec = 1 subframe"
    DEFVAL          { 800 }
    ::= { sonusDspAdmnEntry 11 }

sonusDspAdmnJitterMinOccThsh OBJECT-TYPE
    SYNTAX          Integer32 (10..65535)
    MAX-ACCESS      read-write
    STATUS          current
    DESCRIPTION     
            "If occupancy falls below this threshold for some time
             period we advance the playout time. Units are 125usec samples"
    DEFVAL          { 160 }
    ::= { sonusDspAdmnEntry 12 }

sonusDspResidualEchoControl OBJECT-TYPE
    SYNTAX          INTEGER { cancelOnly(1), suppressResidual(2), 
                        comfortNoise(4) }
    MAX-ACCESS      read-write
    STATUS          current
    DESCRIPTION     
            "For Network Echo Cancellation, specifies the residual echo
             cancellation."
    DEFVAL          { comfortNoise }
    ::= { sonusDspAdmnEntry 13 }

sonusDspEchoReturnLoss OBJECT-TYPE
    SYNTAX          INTEGER { dB6(1), dB3(2), dB0(3) }
    MAX-ACCESS      read-write
    STATUS          current
    DESCRIPTION     
            "For Network Echo Cancellation, specifies the echo
             return loss in dB's. Default value is 6dB."
    DEFVAL          { dB6 }
    ::= { sonusDspAdmnEntry 14 }

sonusDspModemDisable OBJECT-TYPE
    SYNTAX          INTEGER { ignore2100Hz(1), g164(2), g165(4) }
    MAX-ACCESS      read-write
    STATUS          current
    DESCRIPTION     
            "For Network Echo Cancellation, specifies whether to disable
             echo cancellation when a modem tone is detected."
    DEFVAL          { g165 }
    ::= { sonusDspAdmnEntry 15 }

sonusDspHighLevelComp OBJECT-TYPE
    SYNTAX          INTEGER { none(1), dB6(2) }
    MAX-ACCESS      read-write
    STATUS          current
    DESCRIPTION     
            "For Network Echo Cancellation, the high level compensation
             value. Default value is to attenuate by 6dB."
    DEFVAL          { dB6 }
    ::= { sonusDspAdmnEntry 16 }

sonusDspStatTable OBJECT IDENTIFIER
    ::= { sonusDspResourcesMIBObjects 3 }

sonusDspSlotStatTable OBJECT-TYPE
    SYNTAX          SEQUENCE OF SonusDspSlotStatEntry
    MAX-ACCESS      not-accessible
    STATUS          current
    DESCRIPTION     
            "Table of Sonus Enterprise DSP Resource Status for a particular slot"
    ::= { sonusDspResourcesMIBObjects 4 }

sonusDspSlotStatEntry OBJECT-TYPE
    SYNTAX          SonusDspSlotStatEntry
    MAX-ACCESS      not-accessible
    STATUS          current
    DESCRIPTION     
            "Entry in Table consisting of Sonus DSP Resource Status information for a particular slot"
    INDEX           { sonusDspSlotStatShelfIndex, 
                      sonusDspSlotStatSlotIndex }
    ::= { sonusDspSlotStatTable 1 }

SonusDspSlotStatEntry ::=
    SEQUENCE {
        sonusDspSlotStatShelfIndex      SonusShelfIndex,
        sonusDspSlotStatSlotIndex       SonusSlotIndex,
        sonusDspSlotStatG711EcTotal     Integer32,
        sonusDspSlotStatG711Total       Integer32,
        sonusDspSlotStatHdlcTotal       Integer32,
        sonusDspSlotStatToneTotal       Integer32,
        sonusDspSlotStatG729AbTotal     Integer32,
        sonusDspSlotStatG711EcUtilization Integer32,
        sonusDspSlotStatG711EcAllocFailures   Integer32,
        sonusDspSlotStatG711Utilization Integer32,
        sonusDspSlotStatG711AllocFailures Integer32,
        sonusDspSlotStatHdlcUtilization Integer32,
        sonusDspSlotStatHdlcAllocFailures Integer32,
        sonusDspSlotStatToneUtilization Integer32,
        sonusDspSlotStatToneAllocFailures Integer32,
        sonusDspSlotStatG729AbUtilization Integer32,
        sonusDspSlotStatG729AbAllocFailures   Integer32,
        sonusDspSlotStatPacketOutageTotal Integer32,
        sonusDspSlotStatPacketOutageInterval    Integer32,
        sonusDspSlotStatG7231Total      Integer32,
        sonusDspSlotStatG7231Utilization Integer32,
        sonusDspSlotStatG7231AllocFailures  Integer32,
        sonusDspSlotStatG726Total       Integer32,
        sonusDspSlotStatG726Utilization Integer32,
        sonusDspSlotStatG726AllocFailures Integer32,
        sonusDspSlotStatCompressionTotal Integer32,
        sonusDspSlotStatCompressionUtilization      Integer32,
        sonusDspSlotStatCompressionAllocFailures        Integer32,
        sonusDspSlotStatConferenceTotal Integer32,
        sonusDspSlotStatConferenceUtilization     Integer32,
        sonusDspSlotStatConferenceAllocFailures       Integer32,
        sonusDspSlotStatConferenceParticipantTotal          Integer32,
        sonusDspSlotStatConferenceParticipantUtilization                Integer32,
        sonusDspSlotStatConferenceParticipantAllocFailures                  Integer32,
        sonusDspSlotStatIlbcTotal       Integer32,
        sonusDspSlotStatIlbcUtilization Gauge32,
        sonusDspSlotStatIlbcAllocFailures Integer32,
        sonusDspSlotStatGsmTotal        Integer32,
        sonusDspSlotStatGsmUtilization  Gauge32,
        sonusDspSlotStatGsmAllocFailures Integer32,
        sonusDspSlotStatEvrc0Total      Integer32,
        sonusDspSlotStatEvrc0Utilization Gauge32,
        sonusDspSlotStatEvrc0AllocFailures  Integer32,
        sonusDspSlotStatEcmTotal        Integer32,
        sonusDspSlotStatEcmUtilization  Integer32,
        sonusDspSlotStatEcmAllocFailures Integer32,
        sonusDspSlotStatEvrcb0Total     Integer32,
        sonusDspSlotStatEvrcb0Utilization Gauge32,
        sonusDspSlotStatEvrcb0AllocFailures   Integer32,
        sonusDspSlotStatG722Total       Integer32,
        sonusDspSlotStatG722Utilization Gauge32,
        sonusDspSlotStatG722AllocFailures Integer32,
        sonusDspSlotStatAmrwbTotal      Integer32,
        sonusDspSlotStatAmrwbUtilization Gauge32,
        sonusDspSlotStatAmrwbAllocFailures  Integer32,
        sonusDspSlotStatG711PktTotal    Integer32,
        sonusDspSlotStatG711PktUtilization  Integer32,
        sonusDspSlotStatG711PktAllocFailures    Integer32
    }

sonusDspSlotStatShelfIndex OBJECT-TYPE
    SYNTAX          SonusShelfIndex
    MAX-ACCESS      read-only
    STATUS          current
    DESCRIPTION     
            "Shelf index for this table"
    ::= { sonusDspSlotStatEntry 1 }

sonusDspSlotStatSlotIndex OBJECT-TYPE
    SYNTAX          SonusSlotIndex
    MAX-ACCESS      read-only
    STATUS          current
    DESCRIPTION     
            "Slot index for this table"
    ::= { sonusDspSlotStatEntry 2 }

sonusDspSlotStatG711EcTotal OBJECT-TYPE
    SYNTAX          Integer32
    MAX-ACCESS      read-only
    STATUS          current
    DESCRIPTION     
            "Total number of G711 with Echo Cancellation resources available on this slot"
    ::= { sonusDspSlotStatEntry 3 }

sonusDspSlotStatG711Total OBJECT-TYPE
    SYNTAX          Integer32
    MAX-ACCESS      read-only
    STATUS          current
    DESCRIPTION     
            "Total number of G711 No Echo Cancel resources available on this slot"
    ::= { sonusDspSlotStatEntry 4 }

sonusDspSlotStatHdlcTotal OBJECT-TYPE
    SYNTAX          Integer32
    MAX-ACCESS      read-only
    STATUS          current
    DESCRIPTION     
            "Total number of HDLC resources available on this slot"
    ::= { sonusDspSlotStatEntry 5 }

sonusDspSlotStatToneTotal OBJECT-TYPE
    SYNTAX          Integer32
    MAX-ACCESS      read-only
    STATUS          current
    DESCRIPTION     
            "Total number of Tones resources available on this slot"
    ::= { sonusDspSlotStatEntry 6 }

sonusDspSlotStatG729AbTotal OBJECT-TYPE
    SYNTAX          Integer32
    MAX-ACCESS      read-only
    STATUS          current
    DESCRIPTION     
            "Total number of G729A+B resources available on this slot"
    ::= { sonusDspSlotStatEntry 7 }

sonusDspSlotStatG711EcUtilization OBJECT-TYPE
    SYNTAX          Integer32
    MAX-ACCESS      read-only
    STATUS          current
    DESCRIPTION     
            "Percentage utilization of G711 Echo canceller resources on this slot"
    ::= { sonusDspSlotStatEntry 8 }

sonusDspSlotStatG711EcAllocFailures OBJECT-TYPE
    SYNTAX          Integer32
    MAX-ACCESS      read-only
    STATUS          current
    DESCRIPTION     
            "Percentage of G711 Echo canceller resources allocation failures on this slot"
    ::= { sonusDspSlotStatEntry 9 }

sonusDspSlotStatG711Utilization OBJECT-TYPE
    SYNTAX          Integer32
    MAX-ACCESS      read-only
    STATUS          current
    DESCRIPTION     
            "Percentage utilization of G711 resources on this slot"
    ::= { sonusDspSlotStatEntry 10 }

sonusDspSlotStatG711AllocFailures OBJECT-TYPE
    SYNTAX          Integer32
    MAX-ACCESS      read-only
    STATUS          current
    DESCRIPTION     
            "Percentage of G711 resources allocation failures on this slot"
    ::= { sonusDspSlotStatEntry 11 }

sonusDspSlotStatHdlcUtilization OBJECT-TYPE
    SYNTAX          Integer32
    MAX-ACCESS      read-only
    STATUS          current
    DESCRIPTION     
            "Percentage utilization HDLC resources on this slot"
    ::= { sonusDspSlotStatEntry 12 }

sonusDspSlotStatHdlcAllocFailures OBJECT-TYPE
    SYNTAX          Integer32
    MAX-ACCESS      read-only
    STATUS          current
    DESCRIPTION     
            "Percentage of HDLC resources allocation failures on this slot"
    ::= { sonusDspSlotStatEntry 13 }

sonusDspSlotStatToneUtilization OBJECT-TYPE
    SYNTAX          Integer32
    MAX-ACCESS      read-only
    STATUS          current
    DESCRIPTION     
            "Percentage utilization of Tone resources on this slot"
    ::= { sonusDspSlotStatEntry 14 }

sonusDspSlotStatToneAllocFailures OBJECT-TYPE
    SYNTAX          Integer32
    MAX-ACCESS      read-only
    STATUS          current
    DESCRIPTION     
            "Percentage of Tone resources allocation failures on this slot"
    ::= { sonusDspSlotStatEntry 15 }

sonusDspSlotStatG729AbUtilization OBJECT-TYPE
    SYNTAX          Integer32
    MAX-ACCESS      read-only
    STATUS          current
    DESCRIPTION     
            "Percentage utilization of G729A+B resources on this slot"
    ::= { sonusDspSlotStatEntry 16 }

sonusDspSlotStatG729AbAllocFailures OBJECT-TYPE
    SYNTAX          Integer32
    MAX-ACCESS      read-only
    STATUS          current
    DESCRIPTION     
            "Percentage of G729A+B resources allocation failures on this slot"
    ::= { sonusDspSlotStatEntry 17 }

sonusDspSlotStatPacketOutageTotal OBJECT-TYPE
    SYNTAX          Integer32
    MAX-ACCESS      read-only
    STATUS          current
    DESCRIPTION     
            "Total number of packet outages exceeding the
             user-specified threshold on a CNS or SPS.
             This object can be reset by the user."
    ::= { sonusDspSlotStatEntry 18 }

sonusDspSlotStatPacketOutageInterval OBJECT-TYPE
    SYNTAX          Integer32
    MAX-ACCESS      read-only
    STATUS          current
    DESCRIPTION     
            "Number of packet outages exceeding the user-specified
             threshold since the last PacketOutageThresholdExceeded
             trap was generated on a CNS or SPS."
    ::= { sonusDspSlotStatEntry 19 }

sonusDspSlotStatG7231Total OBJECT-TYPE
    SYNTAX          Integer32
    MAX-ACCESS      read-only
    STATUS          current
    DESCRIPTION     
            "Total number of G723.1 resources available on this slot"
    ::= { sonusDspSlotStatEntry 20 }

sonusDspSlotStatG7231Utilization OBJECT-TYPE
    SYNTAX          Integer32
    MAX-ACCESS      read-only
    STATUS          current
    DESCRIPTION     
            "Percentage utilization of G7231 resources on this slot"
    ::= { sonusDspSlotStatEntry 21 }

sonusDspSlotStatG7231AllocFailures OBJECT-TYPE
    SYNTAX          Integer32
    MAX-ACCESS      read-only
    STATUS          current
    DESCRIPTION     
            "Percentage of G7231 resources allocation failures on this slot"
    ::= { sonusDspSlotStatEntry 22 }

sonusDspSlotStatG726Total OBJECT-TYPE
    SYNTAX          Integer32
    MAX-ACCESS      read-only
    STATUS          current
    DESCRIPTION     
            "Total number of G726 resources available on this slot"
    ::= { sonusDspSlotStatEntry 23 }

sonusDspSlotStatG726Utilization OBJECT-TYPE
    SYNTAX          Integer32
    MAX-ACCESS      read-only
    STATUS          current
    DESCRIPTION     
            "Percentage utilization of G726 resources on this slot"
    ::= { sonusDspSlotStatEntry 24 }

sonusDspSlotStatG726AllocFailures OBJECT-TYPE
    SYNTAX          Integer32
    MAX-ACCESS      read-only
    STATUS          current
    DESCRIPTION     
            "Percentage of G726 resources allocation failures on this slot"
    ::= { sonusDspSlotStatEntry 25 }

sonusDspSlotStatCompressionTotal OBJECT-TYPE
    SYNTAX          Integer32
    MAX-ACCESS      read-only
    STATUS          current
    DESCRIPTION     
            "Total number of compression resources available on this slot"
    ::= { sonusDspSlotStatEntry 26 }

sonusDspSlotStatCompressionUtilization OBJECT-TYPE
    SYNTAX          Integer32
    MAX-ACCESS      read-only
    STATUS          current
    DESCRIPTION     
            "Percentage utilization of compression resources on this slot"
    ::= { sonusDspSlotStatEntry 27 }

sonusDspSlotStatCompressionAllocFailures OBJECT-TYPE
    SYNTAX          Integer32
    MAX-ACCESS      read-only
    STATUS          current
    DESCRIPTION     
            "Percentage of compression resources allocation failures on this slot"
    ::= { sonusDspSlotStatEntry 28 }

sonusDspSlotStatConferenceTotal OBJECT-TYPE
    SYNTAX          Integer32
    MAX-ACCESS      read-only
    STATUS          current
    DESCRIPTION     
            "Total number of conference resources available on this slot"
    ::= { sonusDspSlotStatEntry 29 }

sonusDspSlotStatConferenceUtilization OBJECT-TYPE
    SYNTAX          Integer32
    MAX-ACCESS      read-only
    STATUS          current
    DESCRIPTION     
            "Percentage utilization of conference resources on this slot"
    ::= { sonusDspSlotStatEntry 30 }

sonusDspSlotStatConferenceAllocFailures OBJECT-TYPE
    SYNTAX          Integer32
    MAX-ACCESS      read-only
    STATUS          current
    DESCRIPTION     
            "Percentage of conference resources allocation failures on this slot"
    ::= { sonusDspSlotStatEntry 31 }

sonusDspSlotStatConferenceParticipantTotal OBJECT-TYPE
    SYNTAX          Integer32
    MAX-ACCESS      read-only
    STATUS          current
    DESCRIPTION     
            "Total number of participant resources available on this slot"
    ::= { sonusDspSlotStatEntry 32 }

sonusDspSlotStatConferenceParticipantUtilization OBJECT-TYPE
    SYNTAX          Integer32
    MAX-ACCESS      read-only
    STATUS          current
    DESCRIPTION     
            "Percentage utilization of participant resources on this slot"
    ::= { sonusDspSlotStatEntry 33 }

sonusDspSlotStatConferenceParticipantAllocFailures OBJECT-TYPE
    SYNTAX          Integer32
    MAX-ACCESS      read-only
    STATUS          current
    DESCRIPTION     
            "Percentage of participant resources allocation failures on this slot"
    ::= { sonusDspSlotStatEntry 34 }

sonusDspSlotStatIlbcTotal OBJECT-TYPE
    SYNTAX          Integer32
    MAX-ACCESS      read-only
    STATUS          current
    DESCRIPTION     
            "Total number of iLBC resources available on this slot"
    ::= { sonusDspSlotStatEntry 35 }

sonusDspSlotStatIlbcUtilization OBJECT-TYPE
    SYNTAX          Gauge32
    MAX-ACCESS      read-only
    STATUS          current
    DESCRIPTION     
            "Percentage utilization of iLBC resources on this slot"
    ::= { sonusDspSlotStatEntry 36 }

sonusDspSlotStatIlbcAllocFailures OBJECT-TYPE
    SYNTAX          Integer32
    MAX-ACCESS      read-only
    STATUS          current
    DESCRIPTION     
            "Percentage of iLBC resources allocation failures on this slot"
    ::= { sonusDspSlotStatEntry 37 }

sonusDspSlotStatGsmTotal OBJECT-TYPE
    SYNTAX          Integer32
    MAX-ACCESS      read-only
    STATUS          current
    DESCRIPTION     
            "Total number of GSM resources available on this slot"
    ::= { sonusDspSlotStatEntry 38 }

sonusDspSlotStatGsmUtilization OBJECT-TYPE
    SYNTAX          Gauge32
    MAX-ACCESS      read-only
    STATUS          current
    DESCRIPTION     
            "Percentage utilization of GSM resources on this slot"
    ::= { sonusDspSlotStatEntry 39 }

sonusDspSlotStatGsmAllocFailures OBJECT-TYPE
    SYNTAX          Integer32
    MAX-ACCESS      read-only
    STATUS          current
    DESCRIPTION     
            "Percentage of GSM resources allocation failures on this slot"
    ::= { sonusDspSlotStatEntry 40 }

sonusDspSlotStatEvrc0Total OBJECT-TYPE
    SYNTAX          Integer32
    MAX-ACCESS      read-only
    STATUS          current
    DESCRIPTION     
            "Total number of Evrc0  resources available on this slot"
    ::= { sonusDspSlotStatEntry 41 }

sonusDspSlotStatEvrc0Utilization OBJECT-TYPE
    SYNTAX          Gauge32
    MAX-ACCESS      read-only
    STATUS          current
    DESCRIPTION     
            "Percentage utilization of Evrc0 resources on this slot"
    ::= { sonusDspSlotStatEntry 42 }

sonusDspSlotStatEvrc0AllocFailures OBJECT-TYPE
    SYNTAX          Integer32
    MAX-ACCESS      read-only
    STATUS          current
    DESCRIPTION     
            "Percentage of Evrc0 resources allocation failures on this slot"
    ::= { sonusDspSlotStatEntry 43 }

sonusDspSlotStatEcmTotal OBJECT-TYPE
    SYNTAX          Integer32
    MAX-ACCESS      read-only
    STATUS          current
    DESCRIPTION     
            "Total number of T.38 ECM resources available on this slot"
    ::= { sonusDspSlotStatEntry 44 }

sonusDspSlotStatEcmUtilization OBJECT-TYPE
    SYNTAX          Integer32
    MAX-ACCESS      read-only
    STATUS          current
    DESCRIPTION     
            "Percentage utilization of T.38 ECM resources on this slot"
    ::= { sonusDspSlotStatEntry 45 }

sonusDspSlotStatEcmAllocFailures OBJECT-TYPE
    SYNTAX          Integer32
    MAX-ACCESS      read-only
    STATUS          current
    DESCRIPTION     
            "Percentage of T.38 ECM resources allocation failures on this slot"
    ::= { sonusDspSlotStatEntry 46 }

sonusDspSlotStatEvrcb0Total OBJECT-TYPE
    SYNTAX          Integer32
    MAX-ACCESS      read-only
    STATUS          current
    DESCRIPTION     
            "Total number of Evrcb0  resources available on this slot"
    ::= { sonusDspSlotStatEntry 47 }

sonusDspSlotStatEvrcb0Utilization OBJECT-TYPE
    SYNTAX          Gauge32
    MAX-ACCESS      read-only
    STATUS          current
    DESCRIPTION     
            "Percentage utilization of Evrcb0 resources on this slot"
    ::= { sonusDspSlotStatEntry 48 }

sonusDspSlotStatEvrcb0AllocFailures OBJECT-TYPE
    SYNTAX          Integer32
    MAX-ACCESS      read-only
    STATUS          current
    DESCRIPTION     
            "Percentage of Evrcb0 resources allocation failures on this slot"
    ::= { sonusDspSlotStatEntry 49 }

sonusDspSlotStatG722Total OBJECT-TYPE
    SYNTAX          Integer32
    MAX-ACCESS      read-only
    STATUS          current
    DESCRIPTION     
            "Total number of G722  resources available on this slot"
    ::= { sonusDspSlotStatEntry 50 }

sonusDspSlotStatG722Utilization OBJECT-TYPE
    SYNTAX          Gauge32
    MAX-ACCESS      read-only
    STATUS          current
    DESCRIPTION     
            "Percentage utilization of G722 resources on this slot"
    ::= { sonusDspSlotStatEntry 51 }

sonusDspSlotStatG722AllocFailures OBJECT-TYPE
    SYNTAX          Integer32
    MAX-ACCESS      read-only
    STATUS          current
    DESCRIPTION     
            "Percentage of G722 resources allocation failures on this slot"
    ::= { sonusDspSlotStatEntry 52 }

sonusDspSlotStatAmrwbTotal OBJECT-TYPE
    SYNTAX          Integer32
    MAX-ACCESS      read-only
    STATUS          current
    DESCRIPTION     
            "Total number of Amrwb  resources available on this slot"
    ::= { sonusDspSlotStatEntry 53 }

sonusDspSlotStatAmrwbUtilization OBJECT-TYPE
    SYNTAX          Gauge32
    MAX-ACCESS      read-only
    STATUS          current
    DESCRIPTION     
            "Percentage utilization of Amrwb resources on this slot"
    ::= { sonusDspSlotStatEntry 54 }

sonusDspSlotStatAmrwbAllocFailures OBJECT-TYPE
    SYNTAX          Integer32
    MAX-ACCESS      read-only
    STATUS          current
    DESCRIPTION     
            "Percentage of Amrwb resources allocation failures on this slot"
    ::= { sonusDspSlotStatEntry 55 }

sonusDspSlotStatG711PktTotal OBJECT-TYPE
    SYNTAX          Integer32
    MAX-ACCESS      read-only
    STATUS          current
    DESCRIPTION     
            "Total number of G711 Packet resources available on this slot"
    ::= { sonusDspSlotStatEntry 56 }

sonusDspSlotStatG711PktUtilization OBJECT-TYPE
    SYNTAX          Integer32
    MAX-ACCESS      read-only
    STATUS          current
    DESCRIPTION     
            "Percentage utilization of G711Pkt resources on this slot"
    ::= { sonusDspSlotStatEntry 57 }

sonusDspSlotStatG711PktAllocFailures OBJECT-TYPE
    SYNTAX          Integer32
    MAX-ACCESS      read-only
    STATUS          current
    DESCRIPTION     
            "Percentage of G711 resources allocation failures on this slot"
    ::= { sonusDspSlotStatEntry 58 }

sonusPadAdmnTable OBJECT-TYPE
    SYNTAX          SEQUENCE OF SonusPadAdmnEntry
    MAX-ACCESS      not-accessible
    STATUS          current
    DESCRIPTION     
            "Table of Sonus Enterprise Packet Assembler Dis-Assembler Admn information"
    ::= { sonusDspResourcesMIBObjects 5 }

sonusPadAdmnEntry OBJECT-TYPE
    SYNTAX          SonusPadAdmnEntry
    MAX-ACCESS      not-accessible
    STATUS          current
    DESCRIPTION     
            "Entry in Table consisting of the Sonus Packet Assembler Dis-assembler Administartion information"
    INDEX           { sonusPadAdmnShelfIndex }
    ::= { sonusPadAdmnTable 1 }

SonusPadAdmnEntry ::=
    SEQUENCE {
        sonusPadAdmnShelfIndex          SonusShelfIndex,
        sonusPadAdmnJitterEvalPeriod    Integer32,
        sonusPadAdmnJitterMinOccThsh    Integer32,
        sonusPadAdmnRtpG711ALaw         Integer32,
        sonusPadAdmnRtpG711ULaw         Integer32,
        sonusPadAdmnRtpG729A            Integer32,
        sonusPadAdmnRtpG729AB           Integer32,
        sonusPadAdmnG729ABThreshold     Integer32,
        sonusPadAdmnG729ABThresholdState SonusAdminState,
        sonusPadAdmnToneThreshold       Integer32,
        sonusPadAdmnToneThresholdState  SonusAdminState,
        sonusPadAdmnRowStatus           RowStatus,
        sonusPadAdmnRtpDtmfRelay        Integer32,
        sonusPadAdmnRtpFaxRelay         Integer32,
        sonusPadAdmnSidMinTime          Integer32,
        sonusPadAdmnSidMaxTime          Integer32,
        sonusPadAdmnSidHangoverTime     Integer32,
        sonusPadAdmnSidMinNoiseFloor    Integer32,
        sonusPadAdmnSidMaxNoiseFloor    Integer32,
        sonusPadAdmnComfortEnergy       Integer32,
        sonusPadAdmnPacketOutageThreshold Integer32,
        sonusPadAdmnPacketOutageTotalReset  INTEGER,
        sonusPadAdmnG7231Threshold      Integer32,
        sonusPadAdmnG7231ThresholdState SonusAdminState,
        sonusPadAdmnG726Threshold       Integer32,
        sonusPadAdmnG726ThresholdState  SonusAdminState,
        sonusPadAdmnSignalingTone       INTEGER,
        sonusPadAdmnNlpDisable          Integer32,
        sonusPadAdmnNlpEnable           Integer32,
        sonusPadAdmnNarrowbandDetection INTEGER,
        sonusPadAdmnUniversalCompressionThreshold         Integer32,
        sonusPadAdmnUniversalCompressionThresholdState              SonusAdminState,
        sonusPadAdmnPlayoutTimeseriesPeriod   Integer32,
        sonusPadAdmnPlayoutTimeseriesThreshold0       Integer32,
        sonusPadAdmnPlayoutTimeseriesThreshold1       Integer32,
        sonusPadAdmnPlayoutTimeseriesThreshold2       Integer32,
        sonusPadAdmnPacketOutageInterval Integer32,
        sonusPadAdmnPacketLossEvalInterval  Integer32,
        sonusPadAdmnPacketLossThreshold Integer32,
        sonusPadAdmnPacketLossThresholdDuration       Integer32,
        sonusPadAdmnCnProfile           INTEGER,
        sonusPadAdmnCnRateControl       Integer32,
        sonusPadAdmnChecksumAction      INTEGER,
        sonusPadAdmnDcsTcfGap           Integer32,
        sonusPadAdmnEpt                 SonusAdminState,
        sonusPadAdmnDTMFConfigDuration  Integer32,
        sonusPadAdmnDryupTimer          Integer32,
        sonusPadAdmnAudioTxDuring2833   SonusAdminState,
        sonusPadAdmnBusErrorInterrupt   SonusAdminState,
        sonusPadAdmnDtmfTDD             SonusAdminState
    }

sonusPadAdmnShelfIndex OBJECT-TYPE
    SYNTAX          SonusShelfIndex
    MAX-ACCESS      read-only
    STATUS          current
    DESCRIPTION     
            "Shelf Index for Sonus PAD table."
    ::= { sonusPadAdmnEntry 1 }

sonusPadAdmnJitterEvalPeriod OBJECT-TYPE
    SYNTAX          Integer32 (10..300000)
    MAX-ACCESS      read-write
    STATUS          current
    DESCRIPTION     
            "Time period to decide when to periodically evaluate playout
             occupancy in units of millisecond."
    DEFVAL          { 1000 }
    ::= { sonusPadAdmnEntry 2 }

sonusPadAdmnJitterMinOccThsh OBJECT-TYPE
    SYNTAX          Integer32 (2..200)
    MAX-ACCESS      read-write
    STATUS          current
    DESCRIPTION     
            "If occupancy falls below this threshold for some time
             period we advance the playout time in units of millisecond."
    DEFVAL          { 20 }
    ::= { sonusPadAdmnEntry 3 }

sonusPadAdmnRtpG711ALaw OBJECT-TYPE
    SYNTAX          Integer32 (0..127)
    MAX-ACCESS      read-write
    STATUS          obsolete
    DESCRIPTION     
            "This Payload type is no longer configurable. It has been standardized in
             RFC 1890."
    DEFVAL          { 8 }
    ::= { sonusPadAdmnEntry 4 }

sonusPadAdmnRtpG711ULaw OBJECT-TYPE
    SYNTAX          Integer32 (0..127)
    MAX-ACCESS      read-write
    STATUS          obsolete
    DESCRIPTION     
            "This Payload type is no longer configurable. It has been standardized in
             RFC 1890."
    DEFVAL          { 0 }
    ::= { sonusPadAdmnEntry 5 }

sonusPadAdmnRtpG729A OBJECT-TYPE
    SYNTAX          Integer32 (0..127)
    MAX-ACCESS      read-write
    STATUS          obsolete
    DESCRIPTION     
            "This Payload type is no longer configurable. It has been standardized in
             RFC 1890."
    DEFVAL          { 18 }
    ::= { sonusPadAdmnEntry 6 }

sonusPadAdmnRtpG729AB OBJECT-TYPE
    SYNTAX          Integer32 (0..127)
    MAX-ACCESS      read-write
    STATUS          obsolete
    DESCRIPTION     
            "This Payload type is no longer configurable. It has been standardized in
             RFC 1890."
    DEFVAL          { 18 }
    ::= { sonusPadAdmnEntry 7 }

sonusPadAdmnG729ABThreshold OBJECT-TYPE
    SYNTAX          Integer32 (1..100)
    MAX-ACCESS      read-write
    STATUS          current
    DESCRIPTION     
            "Perecentage Threshold crossing value for G729AB resources. When this threshold is 
             reached an event will be generated if sonusPadAdmnG729ABThresholdState is enabled."
    DEFVAL          { 90 }
    ::= { sonusPadAdmnEntry 8 }

sonusPadAdmnG729ABThresholdState OBJECT-TYPE
    SYNTAX          SonusAdminState
    MAX-ACCESS      read-write
    STATUS          current
    DESCRIPTION     
            "State of G729AB Threshold Event, Enabled/Disabled. An event will be generated only 
             if state is enabled."
    DEFVAL          { enabled }
    ::= { sonusPadAdmnEntry 9 }

sonusPadAdmnToneThreshold OBJECT-TYPE
    SYNTAX          Integer32 (1..100)
    MAX-ACCESS      read-write
    STATUS          current
    DESCRIPTION     
            "Perecentage Threshold crossing value for tone resources. When this threshold is 
             reached an event will be generated if sonusPadAdmnToneThresholdState is enabled."
    DEFVAL          { 90 }
    ::= { sonusPadAdmnEntry 10 }

sonusPadAdmnToneThresholdState OBJECT-TYPE
    SYNTAX          SonusAdminState
    MAX-ACCESS      read-write
    STATUS          current
    DESCRIPTION     
            "State of Tone Threshold Event, Enabled/Disabled. An event will be generated only 
             if state is enabled."
    DEFVAL          { enabled }
    ::= { sonusPadAdmnEntry 11 }

sonusPadAdmnRowStatus OBJECT-TYPE
    SYNTAX          RowStatus
    MAX-ACCESS      read-only
    STATUS          current
    DESCRIPTION     
            "This object is used to create, delete, or modify a row in this table."
    ::= { sonusPadAdmnEntry 12 }

sonusPadAdmnRtpDtmfRelay OBJECT-TYPE
    SYNTAX          Integer32 (0..127)
    MAX-ACCESS      read-write
    STATUS          current
    DESCRIPTION     
            "RTP Payload type to be received as DTMF relay during compressed calls."
    DEFVAL          { 100 }
    ::= { sonusPadAdmnEntry 13 }

sonusPadAdmnRtpFaxRelay OBJECT-TYPE
    SYNTAX          Integer32 (0..127)
    MAX-ACCESS      read-write
    STATUS          deprecated
    DESCRIPTION     
            "This field has been deprecated-- fax relay now UDP."
    DEFVAL          { 101 }
    ::= { sonusPadAdmnEntry 14 }

sonusPadAdmnSidMinTime OBJECT-TYPE
    SYNTAX          Integer32 (50..300000)
    MAX-ACCESS      read-write
    STATUS          current
    DESCRIPTION     
            "Minimum time between silence packets. In units of millisecond."
    DEFVAL          { 200 }
    ::= { sonusPadAdmnEntry 15 }

sonusPadAdmnSidMaxTime OBJECT-TYPE
    SYNTAX          Integer32 (50..300000)
    MAX-ACCESS      read-write
    STATUS          current
    DESCRIPTION     
            "Maximum time between silence packets. Must be larger than minimum time
             between silence packets. In units of millisecond."
    DEFVAL          { 2000 }
    ::= { sonusPadAdmnEntry 16 }

sonusPadAdmnSidHangoverTime OBJECT-TYPE
    SYNTAX          Integer32 (80..2560)
    MAX-ACCESS      read-write
    STATUS          current
    DESCRIPTION     
            "Minimum time after a VAD detects speaker going inactive before sending a
             silence packets. In units of millisecond."
    DEFVAL          { 300 }
    ::= { sonusPadAdmnEntry 17 }

sonusPadAdmnSidMinNoiseFloor OBJECT-TYPE
    SYNTAX          Integer32 (24..62)
    MAX-ACCESS      read-write
    STATUS          current
    DESCRIPTION     
            "Minimum noise floor, if energy level is below this it will be 
             considered as silence. Configuration range is between -62dBm -24dBm."
    DEFVAL          { 60 }
    ::= { sonusPadAdmnEntry 18 }

sonusPadAdmnSidMaxNoiseFloor OBJECT-TYPE
    SYNTAX          Integer32 (24..62)
    MAX-ACCESS      read-write
    STATUS          current
    DESCRIPTION     
            "Maximum noise floor, if the energy level is above this it will 
             be considered as speech. Configuration range is between -62dBm -24dBm."
    DEFVAL          { 48 }
    ::= { sonusPadAdmnEntry 19 }

sonusPadAdmnComfortEnergy OBJECT-TYPE
    SYNTAX          Integer32 (35..90)
    MAX-ACCESS      read-write
    STATUS          current
    DESCRIPTION     
            "Initial estimate to be used for generating comfort noise. It is used when 
             no silence packets are received to generate comfort noise. 
             Configuration range is between -90dBm and -35dBm."
    DEFVAL          { 56 }
    ::= { sonusPadAdmnEntry 20 }

sonusPadAdmnPacketOutageThreshold OBJECT-TYPE
    SYNTAX          Integer32 (100..60000)
    MAX-ACCESS      read-write
    STATUS          current
    DESCRIPTION     
            "Packet outage threshold in milliseconds. A trap is generated if the DSP detects
             an outage that exceeds this threshold."
    DEFVAL          { 6000 }
    ::= { sonusPadAdmnEntry 21 }

sonusPadAdmnPacketOutageTotalReset OBJECT-TYPE
    SYNTAX          INTEGER { unknown(1), reset(2) }
    MAX-ACCESS      read-write
    STATUS          current
    DESCRIPTION     
            "This object is used to reset the total packet outage counter on each shelf and slot."
    DEFVAL          { unknown }
    ::= { sonusPadAdmnEntry 22 }

sonusPadAdmnG7231Threshold OBJECT-TYPE
    SYNTAX          Integer32 (1..100)
    MAX-ACCESS      read-write
    STATUS          current
    DESCRIPTION     
            "Percentage Threshold crossing value for G7231 resources. When this threshold is 
             reached an event will be generated if sonusPadAdmnG7231ThresholdState is enabled."
    DEFVAL          { 90 }
    ::= { sonusPadAdmnEntry 23 }

sonusPadAdmnG7231ThresholdState OBJECT-TYPE
    SYNTAX          SonusAdminState
    MAX-ACCESS      read-write
    STATUS          current
    DESCRIPTION     
            "State of G7231 Threshold Event, Enabled/Disabled. An event will be generated only 
             if state is enabled."
    DEFVAL          { enabled }
    ::= { sonusPadAdmnEntry 24 }

sonusPadAdmnG726Threshold OBJECT-TYPE
    SYNTAX          Integer32 (1..100)
    MAX-ACCESS      read-write
    STATUS          current
    DESCRIPTION     
            "Percentage Threshold crossing value for G726 resources. When this threshold is 
             reached an event will be generated if sonusPadAdmnG726ThresholdState is enabled."
    DEFVAL          { 90 }
    ::= { sonusPadAdmnEntry 25 }

sonusPadAdmnG726ThresholdState OBJECT-TYPE
    SYNTAX          SonusAdminState
    MAX-ACCESS      read-write
    STATUS          current
    DESCRIPTION     
            "State of G726 Threshold Event, Enabled/Disabled. An event will be generated only 
             if state is enabled."
    DEFVAL          { enabled }
    ::= { sonusPadAdmnEntry 26 }

sonusPadAdmnSignalingTone OBJECT-TYPE
    SYNTAX          INTEGER { none(1), c5(2) }
    MAX-ACCESS      read-write
    STATUS          current
    DESCRIPTION     
            "Echo Cancellation: None, 2400, 2600 or 2101 Hz"
    DEFVAL          { none }
    ::= { sonusPadAdmnEntry 27 }

sonusPadAdmnNlpDisable OBJECT-TYPE
    SYNTAX          Integer32 (0..16)
    MAX-ACCESS      read-write
    STATUS          current
    DESCRIPTION     
            "Non-linear processing control, Disable"
    DEFVAL          { 6 }
    ::= { sonusPadAdmnEntry 28 }

sonusPadAdmnNlpEnable OBJECT-TYPE
    SYNTAX          Integer32 (0..127)
    MAX-ACCESS      read-write
    STATUS          current
    DESCRIPTION     
            "Non-linear processing control, Enable"
    DEFVAL          { 75 }
    ::= { sonusPadAdmnEntry 29 }

sonusPadAdmnNarrowbandDetection OBJECT-TYPE
    SYNTAX          INTEGER { off(1), on(2) }
    MAX-ACCESS      read-write
    STATUS          current
    DESCRIPTION     
            "For Network Echo Cancellation, narrow band detection is OFF or ON. If set ON
             it narrows the G.164 detection bandwidth in G.165 mode to the G.165 band."
    DEFVAL          { off }
    ::= { sonusPadAdmnEntry 30 }

sonusPadAdmnUniversalCompressionThreshold OBJECT-TYPE
    SYNTAX          Integer32 (1..100)
    MAX-ACCESS      read-write
    STATUS          current
    DESCRIPTION     
            "Percentage Threshold crossing value for Universal Compression resources. When 
             this threshold is reached an event will be generated if 
             sonusPadAdmnUniversalCompressionThresholdState is enabled."
    DEFVAL          { 90 }
    ::= { sonusPadAdmnEntry 31 }

sonusPadAdmnUniversalCompressionThresholdState OBJECT-TYPE
    SYNTAX          SonusAdminState
    MAX-ACCESS      read-write
    STATUS          current
    DESCRIPTION     
            "State of Universal Compression Threshold Event, Enabled/Disabled. An event will 
             be generated only if state is enabled."
    DEFVAL          { enabled }
    ::= { sonusPadAdmnEntry 32 }

sonusPadAdmnPlayoutTimeseriesPeriod OBJECT-TYPE
    SYNTAX          Integer32
    MAX-ACCESS      read-write
    STATUS          current
    DESCRIPTION     
            "This is the duration of one period of the RTP playout buffer loss
             timeseries statistic.  This statistic is used only when an RTP stream
             is terminated (it does not operate in a Packet Monitor channel type).
             Units: milliseconds (will be converted to 10 msec increments)
             Default: 20000 (20 sec)"
    DEFVAL          { 20000 }
    ::= { sonusPadAdmnEntry 33 }

sonusPadAdmnPlayoutTimeseriesThreshold0 OBJECT-TYPE
    SYNTAX          Integer32
    MAX-ACCESS      read-write
    STATUS          current
    DESCRIPTION     
            "Threshold #0 for generation of the playout loss timeseries
             statistic.  The first quantization level is <= this threshold.
             The set of three thresholds specified here are used for all 
             channel instances. 
             Units: milliseconds (will be converted to 10 msec increments)
             Default: 0 (0.0 sec, 0% of playoutTimeseriesPerdiod)"
    DEFVAL          { 0 }
    ::= { sonusPadAdmnEntry 34 }

sonusPadAdmnPlayoutTimeseriesThreshold1 OBJECT-TYPE
    SYNTAX          Integer32
    MAX-ACCESS      read-write
    STATUS          current
    DESCRIPTION     
            "Threshold #1 for generation of the playout loss timeseries
             statistic.  The second quantization level is:
             Threshold #0 < #Interpolations <= Threshold #1
             Units: milliseconds (will be converted to 10 msec increments)
             Default: 200 (0.2 sec, 1% of playoutTimeseriesPerdiod)"
    DEFVAL          { 200 }
    ::= { sonusPadAdmnEntry 35 }

sonusPadAdmnPlayoutTimeseriesThreshold2 OBJECT-TYPE
    SYNTAX          Integer32
    MAX-ACCESS      read-write
    STATUS          current
    DESCRIPTION     
            "Threshold #2 for generation of the playout loss timeseries
             statistic.  The third quantization level is:
             Threshold #1 < #Interpolations <= Threshold #2 
             Units: milliseconds (will be converted to 10 msec increments)
             Default: 600 (0.6 sec, 3% of playoutTimeseriesPerdiod)"
    DEFVAL          { 600 }
    ::= { sonusPadAdmnEntry 36 }

sonusPadAdmnPacketOutageInterval OBJECT-TYPE
    SYNTAX          Integer32 (1..60)
    MAX-ACCESS      read-write
    STATUS          current
    DESCRIPTION     
            " Packet outage (Link loss) detection interval, it's expressed in the units of seconds. When
             the link loss is detected, indication will be sent to trigger hand-over procedure"
    DEFVAL          { 4 }
    ::= { sonusPadAdmnEntry 37 }

sonusPadAdmnPacketLossEvalInterval OBJECT-TYPE
    SYNTAX          Integer32 (1..60)
    MAX-ACCESS      read-write
    STATUS          current
    DESCRIPTION     
            "This is the time period during which the frame loss rate is evaluated; Based on the frame loss
             ratio, the Codec Mode Change (for AMR codecs) is performed; it's expressed in the units of seconds.
             The default value is 10s (= 500 AMR frames)"
    DEFVAL          { 10 }
    ::= { sonusPadAdmnEntry 38 }

sonusPadAdmnPacketLossThreshold OBJECT-TYPE
    SYNTAX          Integer32 (0..100)
    MAX-ACCESS      read-write
    STATUS          current
    DESCRIPTION     
            " This is expressed as the % of the packet loss during Packet Loss Exceeded Threshold Duration "
    DEFVAL          { 10 }
    ::= { sonusPadAdmnEntry 39 }

sonusPadAdmnPacketLossThresholdDuration OBJECT-TYPE
    SYNTAX          Integer32 (1..60)
    MAX-ACCESS      read-write
    STATUS          current
    DESCRIPTION     
            " This is the time period during which packet loss rate is evaluated, expressed as the units of seconds."
    DEFVAL          { 10 }
    ::= { sonusPadAdmnEntry 40 }

sonusPadAdmnCnProfile OBJECT-TYPE
    SYNTAX          INTEGER { adaptive(1), fixed(2) }
    MAX-ACCESS      read-write
    STATUS          current
    DESCRIPTION     
            "Comfort noise profile."
    DEFVAL          { adaptive }
    ::= { sonusPadAdmnEntry 41 }

sonusPadAdmnCnRateControl OBJECT-TYPE
    SYNTAX          Integer32 (0..2)
    MAX-ACCESS      read-write
    STATUS          current
    DESCRIPTION     
            "Comfort noise rate control."
    DEFVAL          { 0 }
    ::= { sonusPadAdmnEntry 42 }

sonusPadAdmnChecksumAction OBJECT-TYPE
    SYNTAX          INTEGER { ignore(1), logonly(2), coredump(3), 
                        repair(4) }
    MAX-ACCESS      read-write
    STATUS          current
    DESCRIPTION     
            "This object controls the system behavior in the event of a checksum error on a dsp.
             the behavior for the settins are as follows:
             ignore - no action is taken.
             logonly - an event is generated and a sonusPadDspChecksumNotification trap is sent to 
             the EMS.
             coredump - an event	is generated, a sonusPadDspChecksumNotification  trap is sent to 
             the EMS and the card is core dumped.  
             repair - the dsp will attempt to correct the error. If successful, an event is 
                      generated and a sonusPadDspErrRepaired trap is sent to the EMS.  
             If unsuccessful, an event is generated and a sonusPadDspRepairFailed
             trap is sent to the EMS and 
             the card is core dumped."
    DEFVAL          { ignore }
    ::= { sonusPadAdmnEntry 43 }

sonusPadAdmnDcsTcfGap OBJECT-TYPE
    SYNTAX          Integer32 (55..95)
    MAX-ACCESS      read-write
    STATUS          current
    DESCRIPTION     
            " GAP between T.38 DCS and TCF, expressed in ms "
    DEFVAL          { 55 }
    ::= { sonusPadAdmnEntry 44 }

sonusPadAdmnEpt OBJECT-TYPE
    SYNTAX          SonusAdminState
    MAX-ACCESS      read-write
    STATUS          current
    DESCRIPTION     
            " Echo Protect Tone settings"
    DEFVAL          { disabled }
    ::= { sonusPadAdmnEntry 45 }

sonusPadAdmnDTMFConfigDuration OBJECT-TYPE
    SYNTAX          Integer32 (300..4000)
    MAX-ACCESS      read-write
    STATUS          current
    DESCRIPTION     
            " DTMF initial duration, expressed in ms "
    DEFVAL          { 300 }
    ::= { sonusPadAdmnEntry 46 }

sonusPadAdmnDryupTimer OBJECT-TYPE
    SYNTAX          Integer32 (0..60)
    MAX-ACCESS      read-write
    STATUS          current
    DESCRIPTION     
            "Dry Up timer duration, expressed in Minutes"
    DEFVAL          { 3 }
    ::= { sonusPadAdmnEntry 47 }

sonusPadAdmnAudioTxDuring2833 OBJECT-TYPE
    SYNTAX          SonusAdminState
    MAX-ACCESS      read-write
    STATUS          current
    DESCRIPTION     
            "Configurable parameter that allows the user to inhibit the transmission of audio packets during the period lasting from the start of a transmitted RFC4733 event to the end of the transmitted RFC4733 event"
    DEFVAL          { enabled }
    ::= { sonusPadAdmnEntry 48 }

sonusPadAdmnBusErrorInterrupt OBJECT-TYPE
    SYNTAX          SonusAdminState
    MAX-ACCESS      read-write
    STATUS          current
    DESCRIPTION     
            "Configurable flag to enable/disable BusErrorInterrupt available in DSPs present on SPS80/CNS85/6/CNS45 cards. Upon enabling BusErrorInterrupt, any invalid memory access within DSP would cause switchover"
    DEFVAL          { enabled }
    ::= { sonusPadAdmnEntry 49 }

sonusPadAdmnDtmfTDD OBJECT-TYPE
    SYNTAX          SonusAdminState
    MAX-ACCESS      read-write
    STATUS          current
    DESCRIPTION     
            "When enabled, dosen't filter frequencies near TTY signals."
    DEFVAL          { disabled }
    ::= { sonusPadAdmnEntry 50 }

sonusEchoCancellorProfile OBJECT IDENTIFIER
    ::= { sonusDspResourcesMIBObjects 6 }

sonusEchoCancellorProfileNextIndex OBJECT-TYPE
    SYNTAX          Integer32
    MAX-ACCESS      read-only
    STATUS          current
    DESCRIPTION     
            "The next valid index to use when creating an entry in
             the sonusEchoCancellorProfile."
    ::= { sonusEchoCancellorProfile 1 }

sonusEchoCancellorProfileTable OBJECT-TYPE
    SYNTAX          SEQUENCE OF SonusEchoCancellorProfileEntry
    MAX-ACCESS      not-accessible
    STATUS          current
    DESCRIPTION     
            "Table of Sonus Enterprise Echo Canceller Profile information"
    ::= { sonusEchoCancellorProfile 2 }

sonusEchoCancellorProfileEntry OBJECT-TYPE
    SYNTAX          SonusEchoCancellorProfileEntry
    MAX-ACCESS      not-accessible
    STATUS          current
    DESCRIPTION     
            "Entry in Table consisting of the Sonus Echo Canceller Profile entries"
    INDEX           { sonusEchoCancellorProfileIndex }
    ::= { sonusEchoCancellorProfileTable 1 }

SonusEchoCancellorProfileEntry ::=
    SEQUENCE {
        sonusEchoCancellorProfileIndex  Integer32,
        sonusEchoCancellorProfileName   SonusName,
        sonusEchoCancellorProfileState  SonusAdminState,
        sonusEchoCancellorProfileMaxTail INTEGER,
        sonusEchoCancellorProfileAudioType  INTEGER,
        sonusEchoCancellorProfileSignallingTone       INTEGER,
        sonusEchoCancellorProfileNlpDisable   Integer32,
        sonusEchoCancellorProfileNlpEnable  Integer32,
        sonusEchoCancellorProfileReturnLoss   INTEGER,
        sonusEchoCancellorProfileResidualEcho     INTEGER,
        sonusEchoCancellorProfileHiLevelComp    INTEGER,
        sonusEchoCancellorProfileModemDisable     INTEGER,
        sonusEchoCancellorProfileRowStatus  RowStatus,
        sonusEchoCancellorProfileNarrowbandDetection            INTEGER
    }

sonusEchoCancellorProfileIndex OBJECT-TYPE
    SYNTAX          Integer32
    MAX-ACCESS      read-only
    STATUS          current
    DESCRIPTION     
            "Index into the Echo Canceller Profile table"
    ::= { sonusEchoCancellorProfileEntry 1 }

sonusEchoCancellorProfileName OBJECT-TYPE
    SYNTAX          SonusName
    MAX-ACCESS      read-write
    STATUS          current
    DESCRIPTION     
            "Name of this Echo Canceller Profile"
    ::= { sonusEchoCancellorProfileEntry 2 }

sonusEchoCancellorProfileState OBJECT-TYPE
    SYNTAX          SonusAdminState
    MAX-ACCESS      read-write
    STATUS          current
    DESCRIPTION     
            "Echo Canceller Profile state. Profile can only be applied when in enabled state."
    DEFVAL          { disabled }
    ::= { sonusEchoCancellorProfileEntry 3 }

sonusEchoCancellorProfileMaxTail OBJECT-TYPE
    SYNTAX          INTEGER { millisec24(1), millisec32(2), 
                        millisec48(3), millisec64(4), millisec80(5), 
                        millisec96(6), millisec112(7), millisec128(8), 
                        maximum(9) }
    MAX-ACCESS      read-write
    STATUS          current
    DESCRIPTION     
            "Maximum Echo canceller tail length"
    DEFVAL          { maximum }
    ::= { sonusEchoCancellorProfileEntry 4 }

sonusEchoCancellorProfileAudioType OBJECT-TYPE
    SYNTAX          INTEGER { uLaw(1), aLaw(2) }
    MAX-ACCESS      read-write
    STATUS          current
    DESCRIPTION     
            "Audio encoding type A-law or U-law"
    DEFVAL          { uLaw }
    ::= { sonusEchoCancellorProfileEntry 5 }

sonusEchoCancellorProfileSignallingTone OBJECT-TYPE
    SYNTAX          INTEGER { none(1), c5(2) }
    MAX-ACCESS      read-write
    STATUS          deprecated
    DESCRIPTION     
            "This field has been deprecated, this parameter has moved to PAD admin.
             Echo Cancellation: None, 2400, 2600 or 2101 Hz"
    DEFVAL          { none }
    ::= { sonusEchoCancellorProfileEntry 6 }

sonusEchoCancellorProfileNlpDisable OBJECT-TYPE
    SYNTAX          Integer32 (0..16)
    MAX-ACCESS      read-write
    STATUS          deprecated
    DESCRIPTION     
            "This field has been deprecated, this parameter has moved to PAD admin.
             Non-linear processing control, Disable"
    DEFVAL          { 6 }
    ::= { sonusEchoCancellorProfileEntry 7 }

sonusEchoCancellorProfileNlpEnable OBJECT-TYPE
    SYNTAX          Integer32 (0..80)
    MAX-ACCESS      read-write
    STATUS          deprecated
    DESCRIPTION     
            "This field has been deprecated, this parameter has moved to PAD admin.
             Non-linear processing control, Enable"
    DEFVAL          { 75 }
    ::= { sonusEchoCancellorProfileEntry 8 }

sonusEchoCancellorProfileReturnLoss OBJECT-TYPE
    SYNTAX          INTEGER { dB6(1), dB3(2), dB0(3) }
    MAX-ACCESS      read-write
    STATUS          current
    DESCRIPTION     
            "For Network Echo Cancellation, specifies the echo
             return loss in dB's. Default value is 6dB."
    DEFVAL          { dB6 }
    ::= { sonusEchoCancellorProfileEntry 9 }

sonusEchoCancellorProfileResidualEcho OBJECT-TYPE
    SYNTAX          INTEGER { cancelOnly(1), suppressResidual(2), 
                        comfortNoise(4) }
    MAX-ACCESS      read-write
    STATUS          current
    DESCRIPTION     
            "For Network Echo Cancellation, specifies the residual echo
             cancellation."
    DEFVAL          { comfortNoise }
    ::= { sonusEchoCancellorProfileEntry 10 }

sonusEchoCancellorProfileHiLevelComp OBJECT-TYPE
    SYNTAX          INTEGER { none(1), dB6(2) }
    MAX-ACCESS      read-write
    STATUS          deprecated
    DESCRIPTION     
            "For Network Echo Cancellation, the high level compensation
             value. Default value is to attenuate by 6dB."
    DEFVAL          { dB6 }
    ::= { sonusEchoCancellorProfileEntry 11 }

sonusEchoCancellorProfileModemDisable OBJECT-TYPE
    SYNTAX          INTEGER { ignore2100Hz(1), g164(2), g165(4), 
                        sonusCustom(5) }
    MAX-ACCESS      read-write
    STATUS          current
    DESCRIPTION     
            "For Network Echo Cancellation, specifies whether to disable
             echo cancellation when a modem tone is detected."
    DEFVAL          { g165 }
    ::= { sonusEchoCancellorProfileEntry 12 }

sonusEchoCancellorProfileRowStatus OBJECT-TYPE
    SYNTAX          RowStatus
    MAX-ACCESS      read-write
    STATUS          current
    DESCRIPTION     
            "This object is used to create, delete, or modify a row in this table."
    ::= { sonusEchoCancellorProfileEntry 13 }

sonusEchoCancellorProfileNarrowbandDetection OBJECT-TYPE
    SYNTAX          INTEGER { off(1), on(2) }
    MAX-ACCESS      read-write
    STATUS          deprecated
    DESCRIPTION     
            "This field has been deprecated, this parameter has moved to PAD admin.
             Narrowband detection"
    DEFVAL          { off }
    ::= { sonusEchoCancellorProfileEntry 14 }

sonusPadProvisioningAdmnTable OBJECT-TYPE
    SYNTAX          SEQUENCE OF SonusPadProvisioningAdmnEntry
    MAX-ACCESS      not-accessible
    STATUS          current
    DESCRIPTION     
            "Table of Sonus Enterprise PAD Provisioning Admn information"
    ::= { sonusDspResourcesMIBObjects 7 }

sonusPadProvisioningAdmnEntry OBJECT-TYPE
    SYNTAX          SonusPadProvisioningAdmnEntry
    MAX-ACCESS      not-accessible
    STATUS          current
    DESCRIPTION     
            "Entry in Table consisting of the Sonus PAD Provisioning Administration information"
    INDEX           { sonusPadProvisioningAdmnShelfIndex, 
                      sonusPadProvisioningAdmnSlotIndex }
    ::= { sonusPadProvisioningAdmnTable 1 }

SonusPadProvisioningAdmnEntry ::=
    SEQUENCE {
        sonusPadProvisioningAdmnShelfIndex  SonusShelfIndex,
        sonusPadProvisioningAdmnSlotIndex Integer32,
        sonusPadProvisioningAdmnDefaultCompressionType              INTEGER,
        sonusPadProvisioningAdmnDs1Type Integer32,
        sonusPadProvisioningAdmnNumVpadDsps   Integer32,
        sonusPadProvisioningAdmnNumVpadNoEchoDsps         Integer32,
        sonusPadProvisioningAdmnNumHdlcDsps   Integer32,
        sonusPadProvisioningAdmnNumToneDsps   Integer32,
        sonusPadProvisioningAdmnNumXpad729Dsps      Integer32,
        sonusPadProvisioningAdmnNumXpad7231Dsps       Integer32,
        sonusPadProvisioningAdmnNumXpad726Dsps      Integer32,
        sonusPadProvisioningAdmnRowStatus RowStatus,
        sonusPadProvisioningAdmnMediaProfileName        DisplayString,
        sonusPadProvisioningAdmnServiceState    INTEGER,
        sonusPadProvisioningAdmnMediaProfilePercent           INTEGER,
        sonusPadProvisioningAdmnMediaProfileNameTwo           DisplayString,
        sonusPadProvisioningAdmnMediaProfilePercentTwo              INTEGER,
        sonusPadProvisioningAdmnMediaProfileNameThree             DisplayString,
        sonusPadProvisioningAdmnMediaProfilePercentThree                INTEGER,
        sonusPadProvisioningAdmnMediaProfileNameFour            DisplayString,
        sonusPadProvisioningAdmnMediaProfilePercentNum              Integer32,
        sonusPadProvisioningAdmnMediaProfilePercentTwoNum                 Integer32,
        sonusPadProvisioningAdmnMediaProfilePercentThreeNum                   Integer32,
        sonusPadProvisioningAdmnMediaProfilePercentFourNum                  Integer32,
        sonusPadProvisioningAdmnRedundantSlotIndex          Integer32
    }

sonusPadProvisioningAdmnShelfIndex OBJECT-TYPE
    SYNTAX          SonusShelfIndex
    MAX-ACCESS      read-only
    STATUS          current
    DESCRIPTION     
            "Shelf Index for Sonus PAD Provisioning table."
    ::= { sonusPadProvisioningAdmnEntry 1 }

sonusPadProvisioningAdmnSlotIndex OBJECT-TYPE
    SYNTAX          Integer32
    MAX-ACCESS      read-only
    STATUS          current
    DESCRIPTION     
            "Slot Index for Sonus PAD Provisioning table."
    ::= { sonusPadProvisioningAdmnEntry 2 }

sonusPadProvisioningAdmnDefaultCompressionType OBJECT-TYPE
    SYNTAX          INTEGER { none(0), g729AB(3), g7231(5), g726(6) }
    MAX-ACCESS      read-write
    STATUS          current
    DESCRIPTION     
            "PAD Provisioning Default Compression Type"
    DEFVAL          { none }
    ::= { sonusPadProvisioningAdmnEntry 3 }

sonusPadProvisioningAdmnDs1Type OBJECT-TYPE
    SYNTAX          Integer32
    MAX-ACCESS      read-write
    STATUS          current
    DESCRIPTION     
            "PAD Provisioning Ds1 Type"
    ::= { sonusPadProvisioningAdmnEntry 4 }

sonusPadProvisioningAdmnNumVpadDsps OBJECT-TYPE
    SYNTAX          Integer32
    MAX-ACCESS      read-write
    STATUS          current
    DESCRIPTION     
            "PAD Provisioning Quantity VPAD DSPs"
    ::= { sonusPadProvisioningAdmnEntry 5 }

sonusPadProvisioningAdmnNumVpadNoEchoDsps OBJECT-TYPE
    SYNTAX          Integer32
    MAX-ACCESS      read-write
    STATUS          current
    DESCRIPTION     
            "PAD Provisioning Quantity VPAD NoEcho DSPs"
    ::= { sonusPadProvisioningAdmnEntry 6 }

sonusPadProvisioningAdmnNumHdlcDsps OBJECT-TYPE
    SYNTAX          Integer32
    MAX-ACCESS      read-write
    STATUS          current
    DESCRIPTION     
            "PAD Provisioning Quantity HDLC DSPs"
    ::= { sonusPadProvisioningAdmnEntry 7 }

sonusPadProvisioningAdmnNumToneDsps OBJECT-TYPE
    SYNTAX          Integer32
    MAX-ACCESS      read-write
    STATUS          current
    DESCRIPTION     
            "PAD Provisioning Quantity Tone DSPs"
    ::= { sonusPadProvisioningAdmnEntry 8 }

sonusPadProvisioningAdmnNumXpad729Dsps OBJECT-TYPE
    SYNTAX          Integer32
    MAX-ACCESS      read-write
    STATUS          current
    DESCRIPTION     
            "PAD Provisioning Quantity XPAD G.729A+B DSPs"
    ::= { sonusPadProvisioningAdmnEntry 9 }

sonusPadProvisioningAdmnNumXpad7231Dsps OBJECT-TYPE
    SYNTAX          Integer32
    MAX-ACCESS      read-write
    STATUS          current
    DESCRIPTION     
            "PAD Provisioning Quantity XPAD G.723.1 DSPs"
    ::= { sonusPadProvisioningAdmnEntry 10 }

sonusPadProvisioningAdmnNumXpad726Dsps OBJECT-TYPE
    SYNTAX          Integer32
    MAX-ACCESS      read-write
    STATUS          current
    DESCRIPTION     
            "PAD Provisioning Quantity XPAD G.726 DSPs"
    ::= { sonusPadProvisioningAdmnEntry 11 }

sonusPadProvisioningAdmnRowStatus OBJECT-TYPE
    SYNTAX          RowStatus
    MAX-ACCESS      read-write
    STATUS          current
    DESCRIPTION     
            "This object is used to create, delete, or modify a row in this table."
    ::= { sonusPadProvisioningAdmnEntry 12 }

sonusPadProvisioningAdmnMediaProfileName OBJECT-TYPE
    SYNTAX          DisplayString (SIZE(1..23))
    MAX-ACCESS      read-write
    STATUS          current
    DESCRIPTION     
            "The name of the Media Profile applied to this PAD-provisioned server"
    ::= { sonusPadProvisioningAdmnEntry 13 }

sonusPadProvisioningAdmnServiceState OBJECT-TYPE
    SYNTAX          INTEGER { disabled(1), oos-enabled(2), is-enabled(3), 
                        oos-loading(4), oos-loaded(5), oos-dryup(6), 
                        is-loading(7), is-loaded(8), is-dryup(9) }
    MAX-ACCESS      read-only
    STATUS          current
    DESCRIPTION     
            "PAD Provisioning service state"
    DEFVAL          { disabled }
    ::= { sonusPadProvisioningAdmnEntry 14 }

sonusPadProvisioningAdmnMediaProfilePercent OBJECT-TYPE
    SYNTAX          INTEGER { five(1), ten(2), twenty-five(3), fifty(4), 
                        one-hundred(5), none(6) }
    MAX-ACCESS      read-write
    STATUS          current
    DESCRIPTION     
            "Percent of Universal XPADs to configure with the media profile
             specified by sonusPadProvisioningAdmnMediaProfileName.  The balance
             of the Universal XPADs (100 - sonusPadProvisioningAdmnMediaProfilePercent)
             will be configured with the media profile specified by 
             sonusPadProvisioningAdmnMediaProfileNameTwo"
    DEFVAL          { 5 }
    ::= { sonusPadProvisioningAdmnEntry 15 }

sonusPadProvisioningAdmnMediaProfileNameTwo OBJECT-TYPE
    SYNTAX          DisplayString (SIZE(0..23))
    MAX-ACCESS      read-write
    STATUS          current
    DESCRIPTION     
            "The name of the Media Profile applied to this PAD-provisioned server"
    ::= { sonusPadProvisioningAdmnEntry 16 }

sonusPadProvisioningAdmnMediaProfilePercentTwo OBJECT-TYPE
    SYNTAX          INTEGER { five(1), ten(2), twenty-five(3), fifty(4), 
                        one-hundred(5), none(6) }
    MAX-ACCESS      read-write
    STATUS          current
    DESCRIPTION     
            "Percent of Universal XPADs to configure with the media profile
             specified by sonusPadProvisioningAdmnMediaProfileName.  The balance
             		 of the Universal XPADs will be configured with the last media profile specified"
    DEFVAL          { 6 }
    ::= { sonusPadProvisioningAdmnEntry 17 }

sonusPadProvisioningAdmnMediaProfileNameThree OBJECT-TYPE
    SYNTAX          DisplayString (SIZE(0..23))
    MAX-ACCESS      read-write
    STATUS          current
    DESCRIPTION     
            "The name of the Media Profile applied to this PAD-provisioned server"
    ::= { sonusPadProvisioningAdmnEntry 18 }

sonusPadProvisioningAdmnMediaProfilePercentThree OBJECT-TYPE
    SYNTAX          INTEGER { five(1), ten(2), twenty-five(3), fifty(4), 
                        one-hundred(5), none(6) }
    MAX-ACCESS      read-write
    STATUS          current
    DESCRIPTION     
            "Percent of Universal XPADs to configure with the media profile
             specified by sonusPadProvisioningAdmnMediaProfileName.  The balance
             		 of the Universal XPADs will be configured with the last media profile specified"
    DEFVAL          { 6 }
    ::= { sonusPadProvisioningAdmnEntry 19 }

sonusPadProvisioningAdmnMediaProfileNameFour OBJECT-TYPE
    SYNTAX          DisplayString (SIZE(0..23))
    MAX-ACCESS      read-write
    STATUS          current
    DESCRIPTION     
            "The name of the Media Profile applied to this PAD-provisioned server"
    ::= { sonusPadProvisioningAdmnEntry 20 }

sonusPadProvisioningAdmnMediaProfilePercentNum OBJECT-TYPE
    SYNTAX          Integer32
    MAX-ACCESS      read-write
    STATUS          current
    DESCRIPTION     
            "Percent of Universal XPADs to configure with the media profile
             specified by sonusPadProvisioningAdmnMediaProfilePercentNum. Last media profile
             percentage is  balance of rest of media profile percentages."
    DEFVAL          { 100 }
    ::= { sonusPadProvisioningAdmnEntry 21 }

sonusPadProvisioningAdmnMediaProfilePercentTwoNum OBJECT-TYPE
    SYNTAX          Integer32
    MAX-ACCESS      read-write
    STATUS          current
    DESCRIPTION     
            "Percent of Universal XPADs to configure with the media profile
             specified by sonusPadProvisioningAdmnMediaProfilePercentTwoNum. Last media profile
             percentage is  balance of rest of media profile percentages."
    DEFVAL          { 0 }
    ::= { sonusPadProvisioningAdmnEntry 22 }

sonusPadProvisioningAdmnMediaProfilePercentThreeNum OBJECT-TYPE
    SYNTAX          Integer32
    MAX-ACCESS      read-write
    STATUS          current
    DESCRIPTION     
            "Percent of Universal XPADs to configure with the media profile
             specified by sonusPadProvisioningAdmnMediaProfilePercentThreeNum. Last media profile
             percentage is  balance of rest of media profile percentages."
    DEFVAL          { 0 }
    ::= { sonusPadProvisioningAdmnEntry 23 }

sonusPadProvisioningAdmnMediaProfilePercentFourNum OBJECT-TYPE
    SYNTAX          Integer32
    MAX-ACCESS      read-write
    STATUS          current
    DESCRIPTION     
            "Percent of Universal XPADs to configure with the media profile
             specified by sonusPadProvisioningAdmnMediaProfilePercentFourNum. Used to store
             and display forth media profile percentage ."
    DEFVAL          { 0 }
    ::= { sonusPadProvisioningAdmnEntry 24 }

sonusPadProvisioningAdmnRedundantSlotIndex OBJECT-TYPE
    SYNTAX          Integer32
    MAX-ACCESS      read-write
    STATUS          current
    DESCRIPTION     
            "Slot Index for Redundant slot for a redundancy group."
    ::= { sonusPadProvisioningAdmnEntry 25 }

sonusMediaProfileBase OBJECT IDENTIFIER
    ::= { sonusDspResourcesMIBObjects 8 }

sonusMediaProfileBaseNextIndex OBJECT-TYPE
    SYNTAX          Integer32
    MAX-ACCESS      read-only
    STATUS          current
    DESCRIPTION     
            "The next valid index to use when creating an entry in
             the sonusMediaProfileBase table."
    ::= { sonusMediaProfileBase 1 }

sonusMediaProfileBaseTable OBJECT-TYPE
    SYNTAX          SEQUENCE OF SonusMediaProfileBaseEntry
    MAX-ACCESS      not-accessible
    STATUS          current
    DESCRIPTION     
            "Table of Sonus Enterprise Media Profile Base information"
    ::= { sonusMediaProfileBase 2 }

sonusMediaProfileBaseEntry OBJECT-TYPE
    SYNTAX          SonusMediaProfileBaseEntry
    MAX-ACCESS      not-accessible
    STATUS          current
    DESCRIPTION     
            "Entry in Table consisting of the Sonus Media Profile Base entries"
    INDEX           { sonusMediaProfileBaseIndex }
    ::= { sonusMediaProfileBaseTable 1 }

SonusMediaProfileBaseEntry ::=
    SEQUENCE {
        sonusMediaProfileBaseRowStatus  RowStatus,
        sonusMediaProfileBaseIndex      Integer32,
        sonusMediaProfileBaseDescription SonusName
    }

sonusMediaProfileBaseRowStatus OBJECT-TYPE
    SYNTAX          RowStatus
    MAX-ACCESS      read-write
    STATUS          current
    DESCRIPTION     
            "This object is used to create, delete, or modify a row in this table."
    ::= { sonusMediaProfileBaseEntry 1 }

sonusMediaProfileBaseIndex OBJECT-TYPE
    SYNTAX          Integer32
    MAX-ACCESS      read-only
    STATUS          current
    DESCRIPTION     
            "Index into the Media Profile Base table"
    ::= { sonusMediaProfileBaseEntry 2 }

sonusMediaProfileBaseDescription OBJECT-TYPE
    SYNTAX          SonusName
    MAX-ACCESS      read-only
    STATUS          current
    DESCRIPTION     
            "Name/description of this Media Profile Base entry"
    ::= { sonusMediaProfileBaseEntry 3 }

sonusMediaProfile OBJECT IDENTIFIER
    ::= { sonusDspResourcesMIBObjects 9 }

sonusMediaProfileNextIndex OBJECT-TYPE
    SYNTAX          Integer32
    MAX-ACCESS      read-only
    STATUS          current
    DESCRIPTION     
            "The next valid index to use when creating an entry in
             the sonusMediaProfile table."
    ::= { sonusMediaProfile 1 }

sonusMediaProfileTable OBJECT-TYPE
    SYNTAX          SEQUENCE OF SonusMediaProfileEntry
    MAX-ACCESS      not-accessible
    STATUS          current
    DESCRIPTION     
            "Table of Sonus Enterprise Media Profile information"
    ::= { sonusMediaProfile 2 }

sonusMediaProfileEntry OBJECT-TYPE
    SYNTAX          SonusMediaProfileEntry
    MAX-ACCESS      not-accessible
    STATUS          current
    DESCRIPTION     
            "Entry in Table consisting of the Sonus Media Profile entries"
    INDEX           { sonusMediaProfileIndex }
    ::= { sonusMediaProfileTable 1 }

SonusMediaProfileEntry ::=
    SEQUENCE {
        sonusMediaProfileRowStatus      RowStatus,
        sonusMediaProfileIndex          Integer32,
        sonusMediaProfileName           SonusName,
        sonusMediaProfileAdminState     SonusAdminState,
        sonusMediaProfileServiceState   SonusServiceState,
        sonusMediaProfileMediaProfileBaseIndex      Integer32,
        sonusMediaProfileCapabilityG729AB SonusAdminState,
        sonusMediaProfileCapabilityG7231 SonusAdminState,
        sonusMediaProfileCapabilityG726 SonusAdminState,
        sonusMediaProfileCapabilityTone SonusAdminState,
        sonusMediaProfileCapabilityMonitor  SonusAdminState,
        sonusMediaProfileCapabilityConference     SonusAdminState,
        sonusMediaProfileCapabilityIlbc SonusAdminState,
        sonusMediaProfileCapabilityGsm  SonusAdminState,
        sonusMediaProfileCapabilityPxpad SonusAdminState,
        sonusMediaProfileCapabilityEvrc0 SonusAdminState,
        sonusMediaProfileCapabilityEcm  SonusAdminState,
        sonusMediaProfileCapabilityEvrcb0 SonusAdminState,
        sonusMediaProfileCapabilityG722 SonusAdminState,
        sonusMediaProfileCapabilityAmrwb SonusAdminState,
        sonusMediaProfileCapabilityG711 SonusAdminState,
        sonusMediaProfileCapabilityT38  SonusAdminState
    }

sonusMediaProfileRowStatus OBJECT-TYPE
    SYNTAX          RowStatus
    MAX-ACCESS      read-write
    STATUS          current
    DESCRIPTION     
            "This object is used to create, delete, or modify a row in this table."
    ::= { sonusMediaProfileEntry 1 }

sonusMediaProfileIndex OBJECT-TYPE
    SYNTAX          Integer32
    MAX-ACCESS      read-only
    STATUS          current
    DESCRIPTION     
            "Index into the Media Profile table"
    ::= { sonusMediaProfileEntry 2 }

sonusMediaProfileName OBJECT-TYPE
    SYNTAX          SonusName
    MAX-ACCESS      read-write
    STATUS          current
    DESCRIPTION     
            "Name of this Media Profile entry"
    ::= { sonusMediaProfileEntry 3 }

sonusMediaProfileAdminState OBJECT-TYPE
    SYNTAX          SonusAdminState
    MAX-ACCESS      read-write
    STATUS          current
    DESCRIPTION     
            "Media Profile admin state. Profile can only be applied to remote
             agent when in enabled state.  Profile can only be modified or deleted 
             when in disabled state."
    DEFVAL          { disabled }
    ::= { sonusMediaProfileEntry 4 }

sonusMediaProfileServiceState OBJECT-TYPE
    SYNTAX          SonusServiceState
    MAX-ACCESS      read-only
    STATUS          current
    DESCRIPTION     
            "Media Profile service state.  Profile can only be administratively
             disabled (then modified or deleted) when in service state OOS."
    DEFVAL          { outOfService }
    ::= { sonusMediaProfileEntry 5 }

sonusMediaProfileMediaProfileBaseIndex OBJECT-TYPE
    SYNTAX          Integer32 (1..4)
    MAX-ACCESS      read-write
    STATUS          current
    DESCRIPTION     
            "Index of the Media Profile Base type used by this Media Profile"
    DEFVAL          { 1 }
    ::= { sonusMediaProfileEntry 6 }

sonusMediaProfileCapabilityG729AB OBJECT-TYPE
    SYNTAX          SonusAdminState
    MAX-ACCESS      read-write
    STATUS          current
    DESCRIPTION     
            "Media Profile capability state for G729AB"
    DEFVAL          { disabled }
    ::= { sonusMediaProfileEntry 7 }

sonusMediaProfileCapabilityG7231 OBJECT-TYPE
    SYNTAX          SonusAdminState
    MAX-ACCESS      read-write
    STATUS          current
    DESCRIPTION     
            "Media Profile capability state for G7231"
    DEFVAL          { disabled }
    ::= { sonusMediaProfileEntry 8 }

sonusMediaProfileCapabilityG726 OBJECT-TYPE
    SYNTAX          SonusAdminState
    MAX-ACCESS      read-write
    STATUS          current
    DESCRIPTION     
            "Media Profile capability state for G726"
    DEFVAL          { disabled }
    ::= { sonusMediaProfileEntry 9 }

sonusMediaProfileCapabilityTone OBJECT-TYPE
    SYNTAX          SonusAdminState
    MAX-ACCESS      read-write
    STATUS          current
    DESCRIPTION     
            "Media Profile capability state for Tone"
    DEFVAL          { enabled }
    ::= { sonusMediaProfileEntry 10 }

sonusMediaProfileCapabilityMonitor OBJECT-TYPE
    SYNTAX          SonusAdminState
    MAX-ACCESS      read-write
    STATUS          current
    DESCRIPTION     
            "Media Profile capability state for Monitor"
    DEFVAL          { enabled }
    ::= { sonusMediaProfileEntry 11 }

sonusMediaProfileCapabilityConference OBJECT-TYPE
    SYNTAX          SonusAdminState
    MAX-ACCESS      read-write
    STATUS          current
    DESCRIPTION     
            "Media Profile capability state for Conference"
    DEFVAL          { enabled }
    ::= { sonusMediaProfileEntry 12 }

sonusMediaProfileCapabilityIlbc OBJECT-TYPE
    SYNTAX          SonusAdminState
    MAX-ACCESS      read-write
    STATUS          current
    DESCRIPTION     
            "Media Profile capability state for iLBC"
    DEFVAL          { disabled }
    ::= { sonusMediaProfileEntry 13 }

sonusMediaProfileCapabilityGsm OBJECT-TYPE
    SYNTAX          SonusAdminState
    MAX-ACCESS      read-write
    STATUS          current
    DESCRIPTION     
            "Media Profile capability state for GSM (AMR/EFR)"
    DEFVAL          { disabled }
    ::= { sonusMediaProfileEntry 14 }

sonusMediaProfileCapabilityPxpad OBJECT-TYPE
    SYNTAX          SonusAdminState
    MAX-ACCESS      read-write
    STATUS          current
    DESCRIPTION     
            "Media Profile capability state for PXPAD"
    DEFVAL          { disabled }
    ::= { sonusMediaProfileEntry 15 }

sonusMediaProfileCapabilityEvrc0 OBJECT-TYPE
    SYNTAX          SonusAdminState
    MAX-ACCESS      read-write
    STATUS          current
    DESCRIPTION     
            "Media Profile capability state for CDMA (EVRC0)"
    DEFVAL          { disabled }
    ::= { sonusMediaProfileEntry 16 }

sonusMediaProfileCapabilityEcm OBJECT-TYPE
    SYNTAX          SonusAdminState
    MAX-ACCESS      read-write
    STATUS          current
    DESCRIPTION     
            "Media Profile capability state for T.38 ECM"
    DEFVAL          { disabled }
    ::= { sonusMediaProfileEntry 17 }

sonusMediaProfileCapabilityEvrcb0 OBJECT-TYPE
    SYNTAX          SonusAdminState
    MAX-ACCESS      read-write
    STATUS          current
    DESCRIPTION     
            "Media Profile capability state for CDMA (EVRCB0)"
    DEFVAL          { disabled }
    ::= { sonusMediaProfileEntry 18 }

sonusMediaProfileCapabilityG722 OBJECT-TYPE
    SYNTAX          SonusAdminState
    MAX-ACCESS      read-write
    STATUS          current
    DESCRIPTION     
            "Media Profile capability state for G722 (SBADPCM)"
    DEFVAL          { disabled }
    ::= { sonusMediaProfileEntry 19 }

sonusMediaProfileCapabilityAmrwb OBJECT-TYPE
    SYNTAX          SonusAdminState
    MAX-ACCESS      read-write
    STATUS          current
    DESCRIPTION     
            "Media Profile capability state for G722.2 (AMRWB)"
    DEFVAL          { disabled }
    ::= { sonusMediaProfileEntry 20 }

sonusMediaProfileCapabilityG711 OBJECT-TYPE
    SYNTAX          SonusAdminState
    MAX-ACCESS      read-write
    STATUS          current
    DESCRIPTION     
            "Media Profile capability state for G711"
    DEFVAL          { enabled }
    ::= { sonusMediaProfileEntry 21 }

sonusMediaProfileCapabilityT38 OBJECT-TYPE
    SYNTAX          SonusAdminState
    MAX-ACCESS      read-write
    STATUS          current
    DESCRIPTION     
            "Media Profile capability state for T38"
    DEFVAL          { enabled }
    ::= { sonusMediaProfileEntry 22 }

sonusGsmRedundancyTable OBJECT-TYPE
    SYNTAX          SEQUENCE OF SonusGsmRedundancyEntry
    MAX-ACCESS      not-accessible
    STATUS          current
    DESCRIPTION     
            "Table of GSM (AMR GANC mode) redundancy settings. Maximum 4 entries allowed in this
             table representing 4 codec modes in the Active Codec Set (ACS)"
    ::= { sonusDspResourcesMIBObjects 10 }

sonusGsmRedundancyEntry OBJECT-TYPE
    SYNTAX          SonusGsmRedundancyEntry
    MAX-ACCESS      not-accessible
    STATUS          current
    DESCRIPTION     
            "GSM (AMR GANC mode) redundancy configuration associated with each codec mode in ACS"
    INDEX           { sonusGsmRedundancyIndex }
    ::= { sonusGsmRedundancyTable 1 }

SonusGsmRedundancyEntry ::=
    SEQUENCE {
        sonusGsmRedundancyRowStatus     RowStatus,
        sonusGsmRedundancyIndex         Integer32,
        sonusGsmRedundancyCodecMode     Integer32,
        sonusGsmRedundancyPktRed        Integer32,
        sonusGsmRedundancyPktLossThreshold  Integer32,
        sonusGsmRedundancyPktLossHysteresis   Integer32
    }

sonusGsmRedundancyRowStatus OBJECT-TYPE
    SYNTAX          RowStatus
    MAX-ACCESS      read-write
    STATUS          current
    DESCRIPTION     
            "This object is used to create, delete, or modify a row in this table."
    ::= { sonusGsmRedundancyEntry 1 }

sonusGsmRedundancyIndex OBJECT-TYPE
    SYNTAX          Integer32 (1..4)
    MAX-ACCESS      read-only
    STATUS          current
    DESCRIPTION     
            "Index into the GSM Redundancy Profile table"
    ::= { sonusGsmRedundancyEntry 2 }

sonusGsmRedundancyCodecMode OBJECT-TYPE
    SYNTAX          Integer32 (1..4)
    MAX-ACCESS      read-write
    STATUS          current
    DESCRIPTION     
            "AMR Codec Mode used by this Profile"
    DEFVAL          { 1 }
    ::= { sonusGsmRedundancyEntry 3 }

sonusGsmRedundancyPktRed OBJECT-TYPE
    SYNTAX          Integer32 (0..2)
    MAX-ACCESS      read-write
    STATUS          current
    DESCRIPTION     
            "Packet Redundancy (0,1,2) associated with the Codec Mode(sonusGsmRedundancyCodecMode), 0
             indicates Redundancy is disabled for AMR GANC mode"
    DEFVAL          { 0 }
    ::= { sonusGsmRedundancyEntry 4 }

sonusGsmRedundancyPktLossThreshold OBJECT-TYPE
    SYNTAX          Integer32 (0..63)
    MAX-ACCESS      read-write
    STATUS          current
    DESCRIPTION     
            "Packet Loss Threshold value associated with the Codec Mode(sonusGsmRedundancyCodecMode),
             expressed in number of AMR frames, only apply if Redundancy value (sonusGsmRedundancyPktRed)
             is non-zero; This value is a percentage of the total AMR frames in PacketLossEvaluationInteval
             (sonusPadAdmnPacketLossEvalInterval) and is used to calculate the frame loss ratio for AMR 
             codecs"
    DEFVAL          { 15 }
    ::= { sonusGsmRedundancyEntry 5 }

sonusGsmRedundancyPktLossHysteresis OBJECT-TYPE
    SYNTAX          Integer32 (0..15)
    MAX-ACCESS      read-write
    STATUS          current
    DESCRIPTION     
            "Packet Loss Hysteresis value associated with the Codec Mode(sonusGsmRedundancyCodecMode),
             expressed in number of AMR frames, only apply if Redundancy value (sonusGsmRedundancyPktRed)
             is non-zero; This value is a percentage of the total AMR frames in PacketLossEvaluationInteval
             (sonusPadAdmnPacketLossEvalInterval) and is used to calculate the frame loss ratio for AMR 
             codecs"
    DEFVAL          { 2 }
    ::= { sonusGsmRedundancyEntry 6 }

sonusPadMIBNotifications OBJECT IDENTIFIER
    ::= { sonusDspResourcesMIB 2 }

sonusPadMIBNotificationsPrefix OBJECT IDENTIFIER
    ::= { sonusPadMIBNotifications 0 }

sonusPadMIBNotificationsObjects OBJECT IDENTIFIER
    ::= { sonusPadMIBNotifications 1 }

sonusPadThresholdType OBJECT-TYPE
    SYNTAX          INTEGER { g729AB(1), tone(2), g7231(3), g726(4), 
                        universalcompression(5) }
    MAX-ACCESS      read-only
    STATUS          current
    DESCRIPTION     
            "Type of resource usage that caused a threshold crossing trap"
    ::= { sonusPadMIBNotificationsObjects 1 }

sonusPadThresholdState OBJECT-TYPE
    SYNTAX          INTEGER { off(1), on(2) }
    MAX-ACCESS      read-only
    STATUS          current
    DESCRIPTION     
            "State of threshold, indicates whether threshold is on or off"
    ::= { sonusPadMIBNotificationsObjects 2 }

sonusPadThresholdNotification NOTIFICATION-TYPE
    OBJECTS         { sonusShelfIndex, sonusPadThresholdType, 
                      sonusPadThresholdState, sonusEventDescription, 
                      sonusEventClass, sonusEventLevel, sonusSequenceId, 
                      sonusEventTime }
    STATUS          current
    DESCRIPTION     
            "Generated when a PAD resource usage has gone above the threshold value.
             The type indicates the type reseource."
    ::= { sonusPadMIBNotificationsPrefix 1 }

sonusPadPacketOutageThresholdExceededNotification NOTIFICATION-TYPE
    OBJECTS         { sonusShelfIndex, sonusSlotIndex, 
                      sonusDspSlotStatPacketOutageTotal, 
                      sonusEventDescription, sonusEventClass, 
                      sonusEventLevel, sonusSequenceId, sonusEventTime }
    STATUS          current
    DESCRIPTION     
            "Generated after a packet outage exceeds a configured threshold 
             for a VoIP call on the specified shelf and slot."
    ::= { sonusPadMIBNotificationsPrefix 2 }

sonusPadPacketOutageThresholdClearedNotification NOTIFICATION-TYPE
    OBJECTS         { sonusShelfIndex, sonusSlotIndex, 
                      sonusDspSlotStatPacketOutageInterval, 
                      sonusEventDescription, sonusEventClass, 
                      sonusEventLevel, sonusSequenceId, sonusEventTime }
    STATUS          current
    DESCRIPTION     
            "Generated 10 seconds after the last packet outage exceeds a 
             configured threshold for a VoIP call on the specified shelf and slot."
    ::= { sonusPadMIBNotificationsPrefix 3 }

sonusPadDspFailureNotification NOTIFICATION-TYPE
    OBJECTS         { sonusShelfIndex, sonusSlotIndex, 
                      sonusDspAdmnDspIndex, sonusEventDescription, 
                      sonusEventClass, sonusEventLevel, sonusSequenceId, 
                      sonusEventTime }
    STATUS          current
    DESCRIPTION     
            "Generated after a DSP has not responded to consecutive DSP stat
             commands."
    ::= { sonusPadMIBNotificationsPrefix 4 }

sonusPadThresholdPerSlotNotification NOTIFICATION-TYPE
    OBJECTS         { sonusShelfIndex, sonusSlotIndex, 
                      sonusPadThresholdType, sonusPadThresholdState, 
                      sonusEventDescription, sonusEventClass, 
                      sonusEventLevel, sonusSequenceId, sonusEventTime }
    STATUS          current
    DESCRIPTION     
            "Generated when a PAD resource usage of a slot exceeds a configured the threshold value.
             The type indicates the type reseource."
    ::= { sonusPadMIBNotificationsPrefix 5 }

sonusDspActDeActFailureNotification NOTIFICATION-TYPE
    OBJECTS         { sonusShelfIndex, sonusSlotIndex, 
                      sonusDspAdmnDspIndex, sonusEventDescription, 
                      sonusEventClass, sonusEventLevel, sonusSequenceId, 
                      sonusEventTime }
    STATUS          current
    DESCRIPTION     
            "Generated when DSP resources could not be activated or deactivated.
             This typically indicates a resource was not cleaned up."
    ::= { sonusPadMIBNotificationsPrefix 6 }

sonusPadDspChecksumFailure NOTIFICATION-TYPE
    OBJECTS         { sonusShelfIndex, sonusSlotIndex, 
                      sonusDspAdmnDspIndex, sonusPadAdmnChecksumAction, 
                      sonusEventDescription, sonusEventClass, 
                      sonusEventLevel, sonusSequenceId, sonusEventTime }
    STATUS          current
    DESCRIPTION     
            "Generated after a DSP has detected a checksum failure."
    ::= { sonusPadMIBNotificationsPrefix 7 }

sonusPadDspChecksumErrorRepaired NOTIFICATION-TYPE
    OBJECTS         { sonusShelfIndex, sonusSlotIndex, 
                      sonusDspAdmnDspIndex, sonusEventDescription, 
                      sonusEventClass, sonusEventLevel, sonusSequenceId, 
                      sonusEventTime }
    STATUS          current
    DESCRIPTION     
            "Generated after a DSP has detected a checksum failure and repaired the error successfully."
    ::= { sonusPadMIBNotificationsPrefix 8 }

sonusPadDspChecksumErrorRepairFailed NOTIFICATION-TYPE
    OBJECTS         { sonusShelfIndex, sonusSlotIndex, 
                      sonusDspAdmnDspIndex, sonusEventDescription, 
                      sonusEventClass, sonusEventLevel, sonusSequenceId, 
                      sonusEventTime }
    STATUS          current
    DESCRIPTION     
            "Generated after a DSP has detected a checksum failure and the error could not be repaired."
    ::= { sonusPadMIBNotificationsPrefix 9 }

END -- end of module SONUS-DSP-RESOURCES-MIB.
