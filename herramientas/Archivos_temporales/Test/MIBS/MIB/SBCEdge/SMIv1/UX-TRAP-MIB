--
-- This SMIv1 module has been generated by smidump 0.2-cvs. Do not edit.
--

UX-TRAP-MIB DEFINITIONS ::= BEGIN

IMPORTS
    TRAP-TYPE
        FROM RFC-1215
    Counter, IpAddress
        FROM RFC1155-SMI
    enterprises
        FROM SNMPv2-SMI
    uxAlarmActiveCancelType, uxAlarmActiveCategory, 
    uxAlarmActiveClrEvtID, uxAlarmActiveClrEvtSubID, 
    uxAlarmActiveCondition, uxAlarmActiveCount, uxAlarmActiveDecodeKey, 
    uxAlarmActiveDescription, uxAlarmActiveFirstOccur, 
    uxAlarmActiveHardWareID, uxAlarmActiveHighestSeverityAlarm, 
    uxAlarmActiveID, uxAlarmActiveIndex, uxAlarmActiveLastOccur, 
    uxAlarmActiveSeverity, uxAlarmActiveSourceInstance, 
    uxAlarmActiveState, uxAlarmActiveSubID, uxAlarmConfigIndex
        FROM UX-OBJECTS-MIB;

ux OBJECT IDENTIFIER
    ::= { enterprises 177 15 }

-- ux MODULE-IDENTITY
--     LAST-UPDATED    "201807241735Z"
--     ORGANIZATION    
--             "Ribbon Communications"
--     CONTACT-INFO    
--             "Ribbon Service
--              E-mail: TAC_VA@rbbn.com"
--     DESCRIPTION     
--             "The MIB module for Ribbon Communications SBC Edge entities. 
--              This MIB module describes the enterprise traps for the SBC Edge."
--     ::= { enterprises 177 15 }


net OBJECT IDENTIFIER
    ::= { enterprises 177 }

uxObjects OBJECT IDENTIFIER
    ::= { enterprises 177 15 1 }

uxTraps OBJECT IDENTIFIER
    ::= { enterprises 177 15 2 }

uxAlmADcachingfailed TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Failed to cache attributes from AD in memory. Suggested action - try again later. This alarm will be cleared by event AD caching successful."
    ::= 65537

uxAlmOnlineADqueryfailed TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Failed to execute AD query. Suggested action - confirm that AD is network reachable, check the AD configuration as well as AD access credentials."
    ::= 65538

uxAlmUserloggedin TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "New user 'username' logged in from 'ip address'."
    ::= 65540

uxAlmUserloginfailed TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "User 'username' login failed from 'ip' at 'time'. This alarm will be cleared by event User logged in."
    ::= 65541

uxAlmADUnreachable TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Either AD is network unreachable, or the AD credentials are invalid. This alarm will be cleared by 'AD Reachable' event."
    ::= 65542

uxAlmADReachable TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Active directory is now reachable."
    ::= 65543

uxAlmADcachingsuccessful TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "AD caching was successful."
    ::= 65544

uxAlmADbackupfailed TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Failed to backup cached values from AD to storage device. Either the storage device is not present, or it is full. Contact Ribbon Service for further assistance."
    ::= 65545

uxAlmADsuccessfullybackedup TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Successful backup of cached values from AD to storage device."
    ::= 65546

uxAlmADcachetruncated TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "AD Cache is truncated, AD cache results have exceeded the maximum cache size. Consider caching only the required attributes. If the query is not found in cache, Online query will be performed, while affecting performance."
    ::= 65547

uxAlmRADIUSServerUnreachable TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Either the RADIUS server is network unreachable, the configuration is incorrect, or due to service impacting change.  Suggested action - check shared secret, listening port, RADIUS server IP. This alarm will be cleared by 'RADIUS Reachable' event."
    ::= 65548

uxAlmRADIUSReachable TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "RADIUS server is online."
    ::= 65549

uxAlmCDRloggingfailed TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "SBC Edge failed to send CDR to RADIUS based accounting server. Either the server is network unreachable, or the configuration is incorrect.  Suggested action - check shared secret, listening port, RADIUS server IP."
    ::= 65550

uxAlmCDRbackupfailed TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "SBC Edge failed to backup CDR in local file. Either running with low disk space or CDR backup maximum limit is crossed. Suggested action - Free up the disk space or save the CDR Queued file for future reference."
    ::= 65551

uxAlmUserpasswordchangedsuccessfully TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Password changed successfully by 'username' from 'ip address'."
    ::= 65553

uxAlmUserpasswordchangefailed TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Password change attempted by 'username' from 'ip address' failed."
    ::= 65554

uxAlmUseraccountdisabled TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Account has been disabled by 'username' from 'ip address'."
    ::= 65555

uxAlmUseraccountactivated TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Account has been activated by 'username' from 'ip address'."
    ::= 65556

uxAlmGlobalsecurityoptionschanged TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Global security options changed."
    ::= 65557

uxAlmUserloginblocked TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "User attempting to log in from 'ip' blocked due to excessive incorrect login attempts."
    ::= 65558

uxAlmUserloginunblocked TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "User login is unblocked."
    ::= 65559

uxAlmUserpasswordexpired TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Password has expired. User 'username' logging in from 'ip' password is expired."
    ::= 65560

uxAlmADMaximumThreadsExceeded TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "AD has reached maximum threads. Please inform your service representative."
    ::= 65561

uxAlmADcachingtimedout TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Timed out caching attributes due to lack of response from AD. Suggested action - try again later. The SBC will attempt to load the last successful cache from backup."
    ::= 65562

uxAlmADCacheEncryptionFailed TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "AD Cache encryption failed. Cache will not be saved."
    ::= 65563

uxAlmADCacheEncryptionSuccessful TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "AD Cache encryption successful."
    ::= 65564

uxAlmInvalidCardIDEEPROMData TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "A Card was detected with invalid Card ID EEPROM (failed CRC-CCITT check). Suggested action - provide the entire alarm message including the numbers at the end to Ribbon Service for further assistance."
    ::= 131073

uxAlmCardHealthCheckFailed TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "During Line Card activation, a Card Fault was detected after power was applied to the card. The Card will remain out-of-service.  Suggested action - reboot system. If issue persists, contact Ribbon Service with the alarm information."
    ::= 131074

uxAlmCardnotSupported TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "A Card was detected which can be identified, but the SBC Edge software is unable to support. The Card will remain out-of-service. Suggested action - reboot system. If issue persists, contact Ribbon Service with the alarm information."
    ::= 131075

uxAlmPowerSupplyinputfailure TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "A Power supply module has indicated a failure of input power. The SBC Edge has lost Power Supply redundancy. Suggested action - Verify that the power cable is connected and that the PS is functioning properly."
    ::= 131076

uxAlmPowerSupplyinputrestored TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "A Power Supply module has indicated that input power has been restored. This event clears the 'Power Supply Input Failure' Alarm."
    ::= 131077

uxAlmPowerSupplyoutputfailure TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "A Power Supply module has indicated a failure of output power. The SBC Edge has lost Power Supply redundancy. Suggested action - Verify that the PS is functioning properly."
    ::= 131078

uxAlmSingleFanfailure TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Check the System tab to find the Fan ID of the failed fan. Contact Ribbon Service with this information."
    ::= 131079

uxAlmMultipleFanFailures TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Check the System tab to find the Fan ID's of the failed fans. Contact Ribbon Service with this information."
    ::= 131080

uxAlmSystemTemperatureWarm TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "The temperature sensors have indicated that the system is running warm (55 degrees C threshold)."
    ::= 131081

uxAlmSystemTemperatureWarmCleared TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "The temperature sensors have indicated that the system is no longer running warm (55 degrees C threshold). This event clears the 'System Temperature Warm' Alarm."
    ::= 131082

uxAlmSystemTemperatureHot TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "The temperature sensors have indicated that system is running hot (65 degrees C threshold)."
    ::= 131083

uxAlmSystemTemperatureHotCleared TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "The temperature sensors have indicated that the system is no longer running hot (65 degrees C threshold). This event clears the 'System Temperature Hot' Alarm."
    ::= 131084

uxAlmLicensesexpired TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "License of the node has expired, all the licensed features would fail to work. Contact Ribbon Enterprise Sales."
    ::= 196609

uxAlmLicenseexpiresin2weeks TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "License of the node will expire in 2 weeks."
    ::= 196610

uxAlmNewLicenseapplied TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "New License is applied on the node."
    ::= 196611

uxAlmFailedtoApplyLicense TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Either an invalid key is used, or the license key applies to a different node, or the license key expiry is past the present date. Contact Ribbon Sales to obtain a new license."
    ::= 196612

uxAlmFailedtoacquirelicense TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "License(s) for 'license type' has been exhausted or is not licensed."
    ::= 196613

uxAlmLicensedDS1portsexceedsinstalledports TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "The alarm is generated when the license key applied has more DS1 ports licensed than are installed in the system. The number of BRI ports installed will get activated. As a fix, obtain a license with correct number of DS1 ports."
    ::= 196614

uxAlmLicensedBRIportsexceedsinstalledports TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "The alarm is generated when the license key applied has more BRI ports licensed than are installed in the system. The number of BRI ports installed will get activated. As a fix, obtain a license with correct number of BRI ports."
    ::= 196615

uxAlmLicensedFXSportsexceedsinstalledports TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "The alarm is generated when the license key applied has more FXS ports licensed than are installed in the system. The number of FXS ports installed will get activated. As a fix, obtain a license with correct number of FXS ports."
    ::= 196616

uxAlmLicensedFXOportsexceedsinstalledports TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "The alarm is generated when the license key applied has more FXO ports licensed than are installed in the system. The number of FXO ports installed will get activated. As a fix, obtain a license with correct number of FXO ports."
    ::= 196617

uxAlmFailedtogetkeyforLicensegeneration TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Failed to get key for license generation."
    ::= 196618

uxAlmLicensedSIPSignalingSessionsexceedssystemcapability TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "The alarm is generated when the license key applied has more SIP Signaling Sessions licensed than the system is capable of. Extra licenses will not be used. As a fix, obtain a license with correct number of SIP Signaling Sessions."
    ::= 196619

uxAlmLicensedSIPRegistrationsexceedssystemcapability TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "The alarm is generated when the license key applied has more SIP Registrations licensed than the system is capable of. Extra licenses will not be used. As a fix, obtain a license with correct number of SIP Registrations."
    ::= 196620

uxAlmLicensedSIPMediaSessionsexceedssystemcapability TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "The alarm is generated when the license key applied has more SIP Media Sessions licensed than the system is capable of. Extra licenses will not be used. As a fix, obtain a license with correct number of SIP Media Sessions."
    ::= 196621

uxAlmLicensedProxyLocalSRTPMediaSessionsexceedssystemcapability TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "The alarm is generated when the license key applied has more SIP Proxy Encrypted Media Sessions licensed than the system is capable of. Extra licenses will not be used. As a fix, obtain a license with correct number of SIP Media Sessions."
    ::= 196622

uxAlmLicensedRTPProxysessionsexceedsystemcapability TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "SIP RTP Proxy Sessions of 'number' licenses exceeds the capability of the system of 'number' licenses. As a fix, obtain a license with correct number of SIP RTP Proxy Sessions."
    ::= 196623

uxAlmLicensedVideosessionsexceedsystemcapability TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "SIP Video Sessions of 'number' licenses exceeds the capability of the system of 'number' licenses. As a fix, obtain a license with correct number of SIP Video Sessions."
    ::= 196624

uxAlmLicensedHighCapacity250sessionsexceedsystemcapability TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "SIP High Capacity (250+) Sessions of 'number' licenses exceeds the capability of the system of 'number' licenses. As a fix, obtain a license with correct number of SIP High Capacity Sessions."
    ::= 196625

uxAlmSIPHighCapacity250Licenserequired TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "The SIP Signal Sessions of 'number' licenses exceeds the SIP High Capability (250+) Sessions of 'number' licenses. As a fix, obtain a license with correct number of SIP High Capacity Sessions."
    ::= 196626

uxAlmASMUnreachable TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "ASM system can not be reached, system is down. Check whether the ASM is rebooting."
    ::= 327681

uxAlmClearASMUnreachable TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Clears alarm 'ASM Unreachable'."
    ::= 327682

uxAlmASMFailureRecovered TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "ASM system was previously unreachable, but has come up. This alarm doesn't autoclear so the user can investigate the cause, but the system should be working correctly now."
    ::= 327683

uxAlmASMServicesNotRunning TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "ASM services are not running, calls through the ASM cannot be placed."
    ::= 327684

uxAlmClearASMServicesNotRunning TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Clears alarm 'ASM Services Not Running'."
    ::= 327685

uxAlmASMServicesRestarted TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "ASM Services was previously stopped, but has started. This alarm doesn't autoclear so the user can investigate the cause, but ASM Services should be working correctly now."
    ::= 327686

uxAlmASMServiceRestartFailed TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "The system attempted to restart a failed service on the ASM, service did not start successfully. User interaction is required."
    ::= 327687

uxAlmASMSystemStarted TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "This event is set when the SBA communication system is first established, and usually indicates that the Application Solution Module (ASM) has finished booting. It should come up at system startup, it may come again if the ASM hardware is rebooted."
    ::= 327688

uxAlmASMSystemShuttingdown TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "A planned or deliberate shut down is taking place on the Application Solution Module (ASM)."
    ::= 327689

uxAlmEthernetLinkDown TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Ethernet port specified has lost link. Source Instance: Eth0/Eth1 via SBA Monitor."
    ::= 327690

uxAlmEthernetLinkUp TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Ethernet port specific has recovered link. "
    ::= 327691

uxAlmASMSBCIPSubnetMismatch TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "The ASM and SBC Edge IP interfaces are in different subnets and cannot communicate."
    ::= 327692

uxAlmASMSBCIPSubnetMatch TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "The ASM and SBC Edge IP interfaces are in the same subnet and can now communicate."
    ::= 327693

uxAlmASMQoESQLdatabaseisunreachable TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "The QoE database is unreachable from ASM, make sure Skype for Business Server or Lync Server 2013 is deployed and Monitoring database is running"
    ::= 327694

uxAlmClearASMQoESQLdatabaseisunreachable TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "The QoE database is now reachable from ASM."
    ::= 327695

uxAlmASMfailedtostoreQoEinformation TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Failed to store the QoE information from ASM."
    ::= 327696

uxAlmASMSBCCACUpdatefailed TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "The ASM hasn't been able to apply the CAC update."
    ::= 327697

uxAlmASMSBCCACUpdateapplied TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "ASM-SBC CAC Update applied."
    ::= 327698

uxAlmThiscopyofASMOperatingSystemisnotgenuine TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "ASM Windows Server is not able to activate as genuine Microsoft product."
    ::= 327699

uxAlmASMdriveNFSmountfailure TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "NFS mounting of ASM drive failed, make sure ASM module is up and NFS service is running on the ASM module"
    ::= 327700

uxAlmClearASMdriveNFSmountfailure TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "ASM hard drive is NFS mounted and available."
    ::= 327701

uxAlmASMOperatingSystemSuccessfullyActivated TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "ASM Windows Server is activate as genuine Microsoft product."
    ::= 327702

uxAlmASMIPaddressconflict TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "The current ASM IP 'IP address' is in use by a 'Device' ('MAC address'), Change the 'Device' IP 'Is PowerCycle required' and retry"
    ::= 327703

uxAlmClearASMIPaddressconflict TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "ASM IP address conflict cleared."
    ::= 327704

uxAlmASMEthernetPortDown TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "ASM Ethernet Port have been detected down"
    ::= 327705

uxAlmClearASMEthernetPortDown TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "ASM Ethernet Port have been detected down is cleared."
    ::= 327706

uxAlmActiveCCEMaintenanceMode TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Cloud Connector Edition entered Maintenance mode due to 'Update Type'"
    ::= 327707

uxAlmClearActiveCCEMaintenanceMode TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Cloud Connector Edition exited maintenance mode."
    ::= 327708

uxAlmCCEWindowsProductKeyismissing TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Cloud Connector Edition Windows Product Key is missing."
    ::= 327709

uxAlmClearCCEWindowsProductKeyismissingorfailedtoactivate TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Cloud Connector Edition Windows Product Key has been found."
    ::= 327710

uxAlmCCEWindowsProductfailedtoactivate TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Cloud Connector Edition Windows Product failed to activate"
    ::= 327711

uxAlmASMandSBCFirmwaremismatch TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "ASM('SbcComms version') and SBC('SBC version') firmware version does not match"
    ::= 327712

uxAlmClearASMandSBCFirmwaremismatch TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "ASM and SBC firmware version does not match is cleared."
    ::= 327713

uxAlmFailedtoincreasetheCCEMediationVMressource TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "From the ASM Hyper-V Manager, assign 9 vCPU to the CCE Mediation Server VM."
    ::= 327714

uxAlmConfigurationchangeoccurredonActionSet TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Action set modified 'id'."
    ::= 458753

uxAlmConfigurationchangeoccurredonNormalizationTable TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "There is a normalization table number/name that should be printed with this event."
    ::= 458754

uxAlmConfigurationchangeoccurredonRouteTable TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Routing table modified 'id'."
    ::= 458755

uxAlmConfigurationchangeoccurredonTransformationTables TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Transformation table modified 'id'."
    ::= 458756

uxAlmRoutetemporarilydisabled TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Route temporarily disabled due to signaling group(s) down."
    ::= 458757

uxAlmRouteenabled TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Route enabled as the signaling group is up."
    ::= 458758

uxAlmACallexceededthelimitfornumberofdestinations TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Maximum(8) call forks exceeded, no more forks for this destination"
    ::= 458759

uxAlmCallforkingusedwithnoforkinglicense TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Call forking used with no forking license."
    ::= 458760

uxAlmInvocationofInvokeActionSetexceededthemaximumnestinglimit TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Maximum(10) nested InvokeActionSet exceeded."
    ::= 458761

uxAlmConfigurationchangeoccurredonCallbackTables TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Callback table 'id' modified."
    ::= 458762

uxAlmChannelisinservice TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Channel is up and is in service. This clears the 'Channel out of service' alarm."
    ::= 524289

uxAlmChannelisoutofservice TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Channel Out Of Service Alarm. This alarm is automatically cleared when Channel is in service."
    ::= 524290

uxAlmEmergencyCallAttempted TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Emergency Call is attempted from Calling Number, Calling Extension, Caller IP address."
    ::= 524291

uxAlmEmergencyCallCompleted TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Emergency Call completed. The alarm will be cleared after expiry time in emergency status table."
    ::= 524292

uxAlmQoEReportNotSentDuetoRTCPMediaList TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "QoE Report for the Signaling Group not sent. To enable QoE report for this Signaling Group, check the Media List associated with the SG and set RTCP Mode to RTCP-XR."
    ::= 524293

uxAlmCallTransferfailedduetocallnotbeinginDSPmode TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "The call is not in DSP mode - hence the call transfer could not be honored. Set Agent Type as Access Mode to pass through the SIP REFER."
    ::= 524294

uxAlmCallAttemptfailedduetoMediaModemismatch TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "The call failed due to Media Mode mismatch across SG and Call Route configuration."
    ::= 524295

uxAlmSGDrained TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "SG set to Drain Mode, all channels are idle"
    ::= 524296

uxAlmNonEmergencyCallPreemptedduetoanEmergencyCallAttempt TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Non-Emergency Call Preempted due to an Emergency Call Attempt."
    ::= 524297

uxAlmLicensedSIPMediaSessioncountreached TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Number of licensed SIP Media Sessions has been reached."
    ::= 524298

uxAlmLicensedProxyLocalSRTPcountreached TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Number of licensed Proxy Local SRTP has been reached."
    ::= 524299

uxAlmNoAMRWidebandlicense TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "AMR Wideband call attempted but not licensed."
    ::= 524300

uxAlmMaximumCallDurationExceeded TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Maximum call duration exceeded for call and call has been disconnected."
    ::= 524301

uxAlmSIPServerNotResponding TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "SIP server has failed to respond and has been taken out of service. This alarm will be cleared by the event 'SIP server became responsive'."
    ::= 589825

uxAlmSignalingGroupTakenoutofService TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "All servers in SG have failed. This alarm will be cleared by 'SIP Signaling group enabled' event."
    ::= 589826

uxAlmSignalingGroupDisabled TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Configuration action has changed this Signaling Group from Enabled to Disabled."
    ::= 589827

uxAlmSIPTLSServerHandshakeFailure TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "TLS server handshake failed with alert code. Action: Refer to Error Alerts in RFC 5246 for the problem."
    ::= 589828

uxAlmSIPTLSHandshakeInactivityTimeoutFailure TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Handshake failed due to no response from peer within specified timeout. Action: Increase the Handshake Inactivity Timeout in TLS Profile."
    ::= 589829

uxAlmConfiguredPortNumberMismatch TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Discrepancy of an FQDN/Port configured in the SipServer object that is different than the DNS SRV lookup. A DNS SRV record can return the port number for the selected protocol. The DNS SRV port value will take priority over the configured port."
    ::= 589830

uxAlmSIPServerBecameResponsive TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "SIP server came up."
    ::= 589831

uxAlmSIPclusterwentdown TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "SIP cluster went down. This is due to all the servers in the clusters being unresponsive. This alarm will be cleared by the event 'SIP Cluster Enabled'. "
    ::= 589832

uxAlmSIPClusterEnabled TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "SIP cluster enabled."
    ::= 589833

uxAlmSIPSignalingGroupEnabled TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "SIP Signaling group enabled."
    ::= 589834

uxAlmSIPSignalingGroupDNSFailure TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Failed to resolve the FQDN entries in the SIP Signaling Group. Suggested action - confirm the FQDNs, and confirm DNS access."
    ::= 589835

uxAlmSIPSignalingGroupFQDNResolved TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Successfully resolved the FQDN of the SIP Signaling group."
    ::= 589836

uxAlmSIPServerDNSFailure TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Failed to resolve the SIP server FQDN entries in the SIP Server table. Suggested action - check the FQDN syntax."
    ::= 589837

uxAlmSIPServerFQDNResolved TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "SIP Server config FQDN resolved."
    ::= 589838

uxAlmSIPCallSessionDNSFailure TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Failed to resolve an FQDN with DNS server during a SIP call session."
    ::= 589839

uxAlmAcquiringLicenseforRegisterFailed TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Failed to acquire license from License Manager"
    ::= 589840

uxAlmSessionorOtherResourceLeak TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "SIP performs self-check for leaks. Please enable logging for sip and issue 'show resources' command."
    ::= 589841

uxAlmFailedtoBindtoNetworkInterface TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Failed to bind to network interface due to dynamic IP address not available."
    ::= 589842

uxAlmSuccessfullyBoundtoNetworkInterface TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Successfully bound to network interface. DHCP lease renewed."
    ::= 589843

uxAlmSIPRegisterServerNotResponding TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "SIP Register server has failed to respond. This alarm will be cleared by the event 'SIP Register server became responsive'."
    ::= 589844

uxAlmSIPRegisterServerBecameResponsive TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "SIP Register server came up."
    ::= 589845

uxAlmRegistrationNotValidReceivedstalefalse TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Stale=false/Registration no longer valid due to Incorrect Credentials."
    ::= 589846

uxAlmConfigChangeforSIPEndpointThatReceivedstalefalse TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Config has changed, clear StaleIsFalse Alarm."
    ::= 589847

uxAlmQoENotifyMessageResponseWasNotSuccessful TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "QoE Notify Message received a no response or a failed response. This alarm will be cleared by the event 'QoE Notify Message received a successful response'."
    ::= 589848

uxAlmQoENotifyMessageResponseWasSuccessful TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "QoE Notify Message received a successful response."
    ::= 589849

uxAlmSystemOverloadDetected TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "System processing is overloaded"
    ::= 589850

uxAlmSystemOverloadCleared TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "System processing  resumes normal operation, overload cleared"
    ::= 589851

uxAlmMaximumNumberofSIPSessionsReached TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "The maximum number of SIP sessions (calls/register/subscribe) has been reached on the signaling group. Increase the number of SIP Channels for the signaling group."
    ::= 589852

uxAlmMaximumNumberofSIPSessionsAlarmCleared TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "SIP sessions per signaling group is under the maximum limit"
    ::= 589853

uxAlmErrorresolvingSRVrecord TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Failed to execute SRV record query.  Suggested action - confirm that DNS server network is reachable, check SRV and DNS server configuration."
    ::= 589854

uxAlmSRVrecordresolved TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "DNS server returned valid SRV record(s)."
    ::= 589855

uxAlmSIPTLSHandshakeNegotiationStartFailure TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "'server' handshake failed to start with invalid certificate; 'connection ID', 'port ID'. Action: confirm that both signed Ribbon SBC Edge Certificate and Trusted CA Certificate exist."
    ::= 589856

uxAlmSIPTLSHandshakeNegotiationStartSuccessful TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Handshake response was started with valid certificate on local and remote gateway. This event clears the 'SIP-TLS Handshake Negotiation Start Failure' alarm. "
    ::= 589857

uxAlmMaximumsupportedSIPSGsreached TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "SIP signaling group Count Reached maximum Supported Limit. "
    ::= 589858

uxAlmMaximumsupportedSIPSGscleared TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "SIP signaling group Count is under the maximum Supported"
    ::= 589859

uxAlmMaximumnonSIPCallSessionsreached TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Number of SIP Non Call Sessions is over the system capacity"
    ::= 589860

uxAlmMaximumnonSIPCallSessionscleared TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Number of SIP Non Call Sessions is under the system capacity"
    ::= 589861

uxAlmMaximumSIPCallSessionsreached TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Number of SIP Call Sessions is over the system capacity"
    ::= 589862

uxAlmMaximumSIPCallSessionscleared TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Number of SIP Call Sessions is under the system capacity"
    ::= 589863

uxAlmBroadsoftSIPCallrerouted TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Broadsoft SIP Call re-routed"
    ::= 589864

uxAlmBroadsoftSIPCallReroutedcleared TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Broadsoft SIP call re-routed cleared"
    ::= 589865

uxAlmSIPSGListenProtocolandSIPServerHostProtocolmismatch TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Verify that the Listen Ports and Protocols for the SG match those in the Server Table"
    ::= 589866

uxAlmConfigurationErrorSIPSGandServerProtocolMismatch TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Verify that the Listen Ports and Protocols for the SG match those in the Server Table"
    ::= 589867

uxAlmSIPTLSClientHandshakeFailure TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "TLS client handshake failed with alert code. Action: Refer to Error Alerts in RFC 5246 for the problem."
    ::= 589868

uxAlmSIPTLSHandshakeInactivityTimeoutCleared TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Handshake response was received within specified timeout. This event clears the 'SIP-TLS Handshake Inactivity Timeout Failure' alarm. "
    ::= 589869

uxAlmSIPTLSServerHandshakeFailureCleared TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Handshake failure error alert condition was cleared. This event clears the 'SIP-TLS Server Handshake Failure' alarm. "
    ::= 589870

uxAlmSIPTLSClientHandshakeFailureCleared TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Handshake failure error alert condition was cleared. This event clears the 'SIP-TLS Client Handshake Failure' alarm. "
    ::= 589871

uxAlmSkypeLyncPresenceServerResponseFailure TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "A Presence Publish Request has been sent to the configured Lync Presence Front End and has received no response or a failed response."
    ::= 589872

uxAlmSkypeLyncPresenceServerResponseFailureCleared TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "A presence server that previously was unreachable has successfully sent a message that the SBC has received. "
    ::= 589873

uxAlmSIPRequestfromUntrustedIP TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "An INVITE message was received from a host without a matching Federated IP"
    ::= 589874

uxAlmSIPRequestfromUntrustedIPCleared TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Source IP is added to the list of federated IP Addresses."
    ::= 589875

uxAlmReSyncmessagereceivedonSGnotselectedforAutoConfigtask TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Check Auto Configuration Task settings and verify that the Signalling Group selected is correct."
    ::= 589876

uxAlmMaximumNumberofSkypeLyncPresenceSessionsReached TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "The maximum number of 500 concurrent SIP Publish sessions for Presence has been reached. Skype/Lync Presence processing will be suspended until the number of concurrent sessions drops below 500 limit. "
    ::= 589877

uxAlmMaximumNumberofS4BPresencePublishSessionsAlarmCleared TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "SIP Publish sessions for S4B Presence is under the maximum limit"
    ::= 589878

uxAlmEnableMonitoringonSkypePresenceServerforbetterreliability TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Enable Monitoring on Skype Presence Server for better reliability."
    ::= 589879

uxAlmMonitoringonSkypePresenceServerhasbeenenabled TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Monitoring on Skype Presence Server has been enabled."
    ::= 589880

uxAlmTheSIPVoiceQualityServerConnectionisBroken TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Suggested Action: Verifying the IP, Port, Protocol, and Certificate (if TLS) are Correct."
    ::= 589881

uxAlmTheSIPVoiceQualityServerConnectionisResumed TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "The SIP Voice Quality Server Connection is Resumed."
    ::= 589882

uxAlmTheVoiceQualityNotifyRejectedbytheSIPVoiceQualityServer TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Suggested Action: Examining the Notify Response Code and the Reason Header (if Included) to Understand Why it was Rejected."
    ::= 589883

uxAlmTheVoiceQualityNotifyAcceptbyTheSIPVoiceQualityServer TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "The Voice Quality Notify has been Accept by The SIP Voice Quality Server."
    ::= 589884

uxAlmFailedtoResolvetheFQDNoftheSIPVoiceQualityServer TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Failed to Resolve FQDN of the SIP Voice Quality Server. Suggested action - confirm the DNS access and FQDN."
    ::= 589885

uxAlmtheSIPVoiceQualityServerFQDNhasbeenResolved TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "the SIP Voice Quality Server FQDN has been Resolved."
    ::= 589886

uxAlmConfiguredRegistrationLimitreached TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Configured Registration Limit reached. New SIP Registrations will be rejected until the number of registered users drops below maximum number of users configured for the Registrar."
    ::= 589887

uxAlmConfiguredRegistrationLimitCleared TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Configured Registration Limit Cleared."
    ::= 589888

uxAlmDChanneldown TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "The D-channel(layer 2) is out of service."
    ::= 655361

uxAlmDChannelup TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "The D-channel(layer 2) is in service. "
    ::= 655362

uxAlmCallreleasedduetochannelrestartbyfarend TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Call released as the ISDN channel has been restarted by far end."
    ::= 655363

uxAlmPortdisabledbyoperator TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Port is placed Out of Service by operator."
    ::= 720897

uxAlmPortenabledbyoperator TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Port is placed back in Service by operator."
    ::= 720898

uxAlmDS1LoopbackEnter TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "The physical layer is in loopback state."
    ::= 720899

uxAlmDS1LoopbackExit TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "The physical layer is out of loopback state."
    ::= 720900

uxAlmRedAlarmLossofSignal TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "The physical layer has detected a RED (LOS) alarm."
    ::= 720901

uxAlmRedAlarmLossofSignalcleared TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "The physical layer RED alarm (LOS) is cleared."
    ::= 720902

uxAlmRedAlarmLossofFrame TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "The physical layer has detected a Red (LOF) alarm."
    ::= 720903

uxAlmRedAlarmLossofFramecleared TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "The physical layer RED alarm (LOF) is cleared."
    ::= 720904

uxAlmBlueAlarm TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "The physical layer has detected a BLUE alarm."
    ::= 720905

uxAlmBlueAlarmCleared TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "The physical layer BLUE alarm is cleared."
    ::= 720906

uxAlmYellowAlarm TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "The physical layer has detected a YELLOW alarm"
    ::= 720907

uxAlmYellowAlarmCleared TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "The physical layer YELLOW alarm is cleared."
    ::= 720908

uxAlmPortdisabledasportnotfoundonDS1 TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Port is now marked as disabled because the corresponding port was not present on the DS1 physical hardware."
    ::= 720909

uxAlmClockrecoveryswitchedtoportconfiguredassecondary TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "System has switched over to secondary clock recovery port as primary is lost."
    ::= 720910

uxAlmClockrecoveryswitchovertosecondaryportcleared TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Secondary clock recovery alarm is being cleared as primary clock is recovered."
    ::= 720911

uxAlmClockrecoveryswitchedtofreerunclock TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "System has switched over to QF free-run clock as both primary/secondary recovery clocks are invalid."
    ::= 720912

uxAlmClockrecoveryswitchovertofreerunclockcleared TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Free-run clock recovery alarm is being cleared as primary clock is recovered."
    ::= 720913

uxAlmLinecardnotdetected TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Line card not detected."
    ::= 720914

uxAlmLinecarddetected TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Line card is detected."
    ::= 720915

uxAlmPortdisabledforrelaypassthroughstateactivation TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Port is now marked as disabled for activated relay passthrough state."
    ::= 720916

uxAlmPortenabledforrelayonlinestateactivation TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Port is now marked as enabled for activated relay online state."
    ::= 720917

uxAlmLayer1down TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "The physical layer has detected layer 1 down due to state conditions that results in nonoperational state of the BRI port."
    ::= 720918

uxAlmLayer1up TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "The physical layer 1 down alarm is cleared with operational state of the BRI port."
    ::= 720919

uxAlmPortdisabledasportnotfoundonanalogcard TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Port is now marked as disabled because the corresponding port was not present on the analog physical hardware."
    ::= 720920

uxAlmPortsdisabledforrelaypassthrustatechgonanalogrelaycards TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Ports are now marked as disabled for activated relay passthrough state on analog FXS/FXO card pair."
    ::= 720921

uxAlmPortsenabledforrelayonlinestatechangeonanalogrelaycardpairs TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Ports are now marked as enabled for activated relay passthrough state on analog FXS/FXO card pair."
    ::= 720922

uxAlmPortstatusdowndetected TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Line down condition detected due to no battery."
    ::= 720923

uxAlmPortstatusup TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Line down condition is cleared."
    ::= 720924

uxAlmPortdisabledasportnotfoundonBRI TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Port is now marked as disabled because the corresponding port was not present on the BRI physical hardware."
    ::= 720925

uxAlmSystemnotoperational TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "System not operational because DSP cannot be initialized. Contact Ribbon Service with the information in this alarm."
    ::= 720926

uxAlmDS1syncfailure TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "DS1 sync failure could be due to mismatching line configuration. Suggested Action: Disable 'Admin State' of unused ports to avoid performance impact."
    ::= 720927

uxAlmDS1syncfailurecleared TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "DS1 sync failure cleared."
    ::= 720928

uxAlmDSPnotcomingup TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "DSP board 'board type' could not be brought up. If the DSP does not come up, contact Ribbon Service with the information in this alarm."
    ::= 786433

uxAlmDSPreset TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "This alarm will be generated if a DSP encounters a fatal error condition and has to be reinitialized."
    ::= 786434

uxAlmDSPCardisUP TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "This event will clear the 'DSP not coming up' and 'DSP reset' alarms."
    ::= 786435

uxAlmDSPeventfailure TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Call related command on Connection ID 'value' failed wtih error code 'value'."
    ::= 786436

uxAlmRTPRTCPPortRangeInvalid TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "This alarm is generated if a RTP/RTCP port range is found to be invalid. This condition should be resolved by reconfiguring the RTP/RTCP Port Range under Media System Configuration."
    ::= 786437

uxAlmRTPRTCPPortRangeInvalidCleared TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "This event will clear the 'RTP/RTCP Port Range Invalid' alarm."
    ::= 786438

uxAlmMSCMediaStreamModeMismatch TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "This alarm is generated when there is a mismatch in media stream mode of the two call legs. Suggested Action: Match 'Audio/Fax Stream Mode' settings and clear alarm."
    ::= 786439

uxAlmMusicOnHoldfailedduetoimproperlyconfiguredsource TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Music-On-Hold enabled; source is not properly configured. If source is set to File: upload a file, disable music on hold or switch source to an FXS port"
    ::= 786440

uxAlmFailedtoAllocateRTPports TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "This alarm is generated if we exceed the configured number of RTP/RTCP port pairs. This condition should be resolved by increasing the 'Number of Port Pairs' in Media System Configuration."
    ::= 786441

uxAlmVirtDSPeventfailure TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Virt DSP Command Failure: Conf='conf' Type='type' Error='error'"
    ::= 786442

uxAlmMSCDTLSServerHandshakeFailure TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "DTLS server handshake failed with alert code. Action: Refer to Error Alerts in RFC 5246 for the problem."
    ::= 786443

uxAlmMSCDTLSServerHandshakeFailureCleared TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Handshake failure error alert condition was cleared. This event clears the 'MSC-DTLS Server Handshake Failure' alarm. "
    ::= 786444

uxAlmMSCDTLSHandshakeInactivityTimeoutFailure TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "DTLS handshake failed due to no response from peer within specified timeout. Action: Increase the Handshake Inactivity Timeout in DTLS Profile."
    ::= 786445

uxAlmMSCDTLSHandshakeInactivityTimeoutCleared TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Handshake response was received within specified timeout. This event clears the 'MSC-DTLS Handshake Inactivity Timeout Failure' alarm. "
    ::= 786446

uxAlmMSCDTLSHandshakeNegotiationStartFailure TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "'server' handshake failed to start with invalid certificate; 'connection ID', 'port ID'. Action: confirm that both signed Ribbon SBC Edge Certificate and Trusted CA Certificate exist."
    ::= 786447

uxAlmMSCDTLSHandshakeNegotiationStartSuccessful TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "DTLS Handshake response was started with valid certificate on local and remote gateway. This event clears the 'MSC-DTLS Handshake Negotiation Start Failure' alarm. "
    ::= 786448

uxAlmMSCDTLSClientHandshakeFailure TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "DTLS client handshake failed with alert code. Action: Refer to Error Alerts in RFC 5246 for the problem."
    ::= 786449

uxAlmMSCDTLSClientHandshakeFailureCleared TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Handshake failure error alert condition was cleared. This event clears the 'MSC-DTLS Client Handshake Failure' alarm. "
    ::= 786450

uxAlmTLSOwnServerCertificatewillExpire TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "CommonName: 'name' StartDate: 'startdate' EndDate: 'enddata' will expire in a window time. Action: Generate, Export CSR and Import a new signed certificate."
    ::= 851969

uxAlmTLSOwnServerCertificatehasExpired TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "CommonName: 'name' StartDate: 'startdate' EndDate: 'enddata' has expired. Action: Generate, Export CSR and Import a new signed certificate."
    ::= 851970

uxAlmTLSOwnServerCertificateismissing TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "This Server certificate is found to be missing or has failed validations. Suggested Action. Generate, Export CSR and Import a new signed certificate."
    ::= 851971

uxAlmTLSSelfSignCertificateGenerationFailed TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Failed to create a default self signed certificate on the system."
    ::= 851972

uxAlmNewandValidTLSOwnServerCertificateDetected TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Imported and validated common name: 'name' StartDate: 'start date' EndDate: 'end date'. This event clears the Server Certificate Expiring, Expired and Missing alarms."
    ::= 851973

uxAlmTLSTrustedCertificateAuthoritywillExpire TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "CommonName: 'name' StartDate: 'start date' EndDate: 'end date' will expire in a window time. Action: Obtain and Import a new valid certificate from the CA vendor."
    ::= 851974

uxAlmTLSTrustedCertificateAuthorityhasExpired TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "'CommonName: 'name' StartDate: 'start date' EndDate: 'end date' has expired. Action: Obtain and Import a new valid certificate from the CA vendor."
    ::= 851975

uxAlmTLSTrustedCertificateAuthoritywasDeleted TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "The Trusted Certificate Authority is successfully deleted due to the expired or expiring soon validity status."
    ::= 851976

uxAlmTLSOwnServerCertificateExpiryNotice TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "CommonName: 'name' StartDate: 'start date' EndDate: 'end date' will expire in a window time. Action: Obtain and Import a new valid certificate from the CA vendor."
    ::= 851977

uxAlmTLSTrustedCertificateAuthorityExpiryNotice TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "CommonName: 'name' StartDate: 'start date' EndDate: 'end date' has expired. Action: Obtain and Import a new valid certificate from the CA vendor."
    ::= 851978

uxAlmInvalidSessionforattemptedrealtimeconnection TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "If a web-client tries to open a realtime monitor connection with invalid session ID, BMP will generate this alarm."
    ::= 917505

uxAlmBMPTLSHandshakeAlertFailure TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "This alarm will be generated if TLS Connection failed with an Alert. The connection associated with a TLS Connection ID is aborted."
    ::= 917506

uxAlmBMPTLSHandshakeInactivityTimeoutFailure TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "This alarm will be generated if there was long period of inactivity during exchange of handshake messages for an associated TLS Connection ID."
    ::= 917507

uxAlmInterfaceoperdown TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Occurs when an Ethernet port (of ports 1, 2, 3 and 4) is operationally down (e.g. cable unplugged, mismatched speed/duplexity settings) and if administrative state is enabled. Is generated only on the SBC 2000."
    ::= 983041

uxAlmInterfaceoperup TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Is generated when an Ethernet port (of ports 1, 2, 3 and 4) becomes operationally up. This event automatically clears the 'Interface oper down' alarm."
    ::= 983042

uxAlmInterfaceadminup TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Is generated when the administrative state of the Logical Interface is configured to be enabled. Is applicable to SBC 2000 and SWe Lite platforms only."
    ::= 983043

uxAlmInterfaceadmindown TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Is generated when the administrative state of the Logical Interface is configured to be disabled. Is applicable to SBC 2000 and SWe Lite platforms only. "
    ::= 983044

uxAlmAdminPortoperdown TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Is generated when the Admin Port is operationally down (e.g. cable unplugged, mismatched duplex/speed settings). Is applicable to the SBC 2000 only."
    ::= 983045

uxAlmAdminPortoperup TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Is generated with the port becomes operational after being in an *Admin port oper down* state. Is applicable to the SBC 2000 only"
    ::= 983046

uxAlmPortoperdown TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "This event is generated when the port is operationally down. It is generated for the SBC 1000 only."
    ::= 983047

uxAlmRIPlicensenotenabled TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            " RIP feature license is not enabled."
    ::= 983048

uxAlmOSPFlicensenotenabled TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            " OSPF feature license is not enabled."
    ::= 983049

uxAlmLinkMonitorPeerDown TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Connection to the monitored host or gateway is down."
    ::= 983050

uxAlmLinkMonitorPeerReady TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Connection to the monitored host or gateway is established."
    ::= 983051

uxAlmTunnelconnectiondisabledbyoperator TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Tunnel connection is placed Out of Service by operator."
    ::= 983052

uxAlmTunnelconnectionenabledbyoperator TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Tunnel connection is placed back in Service by operator."
    ::= 983053

uxAlmTunnellinklost TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Tunnel lost communication with the peer. This alarm will be cleared by event 'Tunnel link restored'."
    ::= 983054

uxAlmTunnellinkrestored TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Tunnel is successfully established with the peer"
    ::= 983055

uxAlmIPseclicensenotenabled TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "IPsec feature license is not enabled."
    ::= 983056

uxAlmNegotiatedDuplexityHalf TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Port negotiated duplexity is half. This degrades the performance."
    ::= 983057

uxAlmNegotiatedDuplexityFull TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Port negotiated duplexity is back to full."
    ::= 983058

uxAlmPreferredlinkdown TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "This event is generated when the preferred link is down."
    ::= 983059

uxAlmPreferredlinkready TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "This event is generated when the the preferred link is ready for service. This event automatically clears the 'preferred Link down' alarm."
    ::= 983060

uxAlmTunnelnotificationfailure TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Tunnel negotiation failed. Suggested Action: Look up the 'Failure Reason' attribute details for the Source in the IPsec Tunnel Table."
    ::= 983061

uxAlmTunnellocalsubnetsarenonnegotiable TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Local subnets 'subnets' failed negotiation as a result of peer config mismatch."
    ::= 983062

uxAlmTunnelremotesubnetsarenonnegotiable TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Remote subnets 'subnets' failed negotiation as a result of peer config mismatch."
    ::= 983063

uxAlmPortStateLearning TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "MSTP port is in learning state."
    ::= 983064

uxAlmPortStateForwarding TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "MSTP port is in forwarding state."
    ::= 983065

uxAlmPortStateDiscarding TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "MSTP port is in discarding state."
    ::= 983066

uxAlmPacketCaptureStarted TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Packet capture has started."
    ::= 983067

uxAlmPacketCaptureStopped TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Packet capture has stopped due to 'reason'."
    ::= 983068

uxAlmDuplicateIPv6addressdetected TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "The indicated IPv6 address has been detected as a duplicate address."
    ::= 983069

uxAlmIPaddressconfigured TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "This event is generated when an IP address is configured on the node."
    ::= 983070

uxAlmIPaddressremoved TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "This event is generated when an IP address is removed from the node."
    ::= 983071

uxAlmLinkfailoverdetected TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Link failover detected, the indicated Ethernet port became active."
    ::= 983072

uxAlmMACaddresseshavechanged TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Some MAC addresses have changed since the last time the system was up. It is recommended to log into console as 'netconfig' user and remap the interfaces as desired."
    ::= 983073

uxAlmDomainNameEmpty TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Domain Name for Split DNS should not be empty."
    ::= 983074

uxAlmApplicationServicerestarted TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "An SBC Edge Application service was restarted. Contact Ribbon Service with the information in this alarm and any core files present. These can be found in Diagnostics->Restart Report under the 'Core Files' tab."
    ::= 1048577

uxAlmActivepartitionswitched TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "System detected a problem during previous boot cycle, active partition has switched automatically. Suggested action - backup the configuration and re-apply the upgrade to the currently inactive partition."
    ::= 1048578

uxAlmFailedtomountpartition TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Mounting failed for partition 'number'."
    ::= 1048579

uxAlmFailedtosetactivepartition TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Failed to set active partition. Contact Ribbon Service with the information in this alarm."
    ::= 1048580

uxAlmAttempttorepairbootparametermismatchfailed TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Attempt to auto repair boot parmeters failed. Contact Ribbon Service with the information in this alarm."
    ::= 1048581

uxAlmBootparametermismatchdetected TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Boot parameter mismatch was detected.Attempting to auto repair."
    ::= 1048582

uxAlmFailedPoweronmemoryselftest TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Power-on self test failure."
    ::= 1048583

uxAlmFailedPoweronCoreSwitchtest TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Power-on self test failure."
    ::= 1048584

uxAlmFailedPoweronSecondarySwitchtest TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Power-on self test failure."
    ::= 1048585

uxAlmFailedPoweronexternalQuadPHYtest TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Power-on self test failure."
    ::= 1048586

uxAlmFailedPoweronexternalSinglePHYtest TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Power-on self test failure."
    ::= 1048587

uxAlmFailedPoweronCPUPHYtest TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Power-on self test failure."
    ::= 1048588

uxAlmFailedPoweronTSItest TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Power-on self test failure."
    ::= 1048589

uxAlmFailedPoweroninternal5PortPHYtest TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Power-on self test failure."
    ::= 1048590

uxAlmSystemUpAfterPlannedRestart TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "System up after planned restart."
    ::= 1048591

uxAlmSystemUpAfterUnplannedRestart TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "System up after unplanned restart."
    ::= 1048592

uxAlmEnteredpasswordrecoverymode TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "SBC has entered password recovery mode."
    ::= 1048593

uxAlmExitedpasswordrecoverymode TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "SBC has exited password recovery mode."
    ::= 1048594

uxAlmFailedtomountUSBstoragedevice TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "SBC discovered USB storage. SBC can mount flash drives formatted with FAT32 file system only."
    ::= 1048595

uxAlmUSBstoragedeviceconnected TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "USB storge device is connected."
    ::= 1048596

uxAlmUSBstoragedevicedisconnected TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "USB storge device is disconnected. This alarm will be cleared when USB drive is connected."
    ::= 1048597

uxAlmCriticalapplicationcrash TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "A critical SBC Edge application has crashed, and the system will be restarted. Contact Ribbon Service with the information in this alarm and any core files present. These can be found in Diagnostics->Restart Report under the 'Core Files' tab."
    ::= 1048598

uxAlmOlderfirmwaredetected TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "A USB firmware update is available. To perform upgrade, please first load SW release v4.1.1"
    ::= 1048599

uxAlmAutoConfigurationsuccessful TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Auto Configuration successful after receiving SIP NOTIFY message."
    ::= 1048600

uxAlmAutoConfigurationfailed TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Failed to perform Auto Configuration after receiving SIP NOTIFY message."
    ::= 1048601

uxAlmSoftwareUpdateinprogress TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Current SIP NOTIFY message cannot be processed as software update is in progress"
    ::= 1048602

uxAlmNodeReboot TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Node Reboot requested by user 'Username' from 'IP address'."
    ::= 1048603

uxAlmFactoryDefault TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Full factory default requested by user 'Username' from 'IP address'."
    ::= 1048604

uxAlmInvalidSystemMemory TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Unexpected memory size for virtual CPU detected. Please consult documentation for memory requirement."
    ::= 1048605

uxAlmResetButtonFactoryDefault TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Full factory default requested via hardware reset button."
    ::= 1048606

uxAlmNoresponse TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "No response to seizure."
    ::= 1114113

uxAlmRemoteenddidnotbackoffinglare TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Remote end did not back off in glare."
    ::= 1114114

uxAlmWinkexpecteddidnotarrive TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Wink expected, did not arrive."
    ::= 1114115

uxAlmNodialtone TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Event of off-hook did not produce dial tone as expected."
    ::= 1114116

uxAlmCASsignalinggroupdisabled TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "CAS signaling group is disabled."
    ::= 1114117

uxAlmCASlicensenotenabled TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Call attempted but CAS feature is not enabled. This alarm is cleared by CAS license enabled event."
    ::= 1114118

uxAlmCASlicenseenabled TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "License manager notify CAS that license is enabled."
    ::= 1114119

uxAlmWinkReceived TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Wink failure had occurred, but wink is received now."
    ::= 1114120

uxAlmDialToneReceived TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "No Dial Tone was received, but Dial Tone is received now."
    ::= 1114121

uxAlmResponseReceived TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "No Response to seizure was received, but Response is received now."
    ::= 1114122

uxAlmInvalidcharactersincallingnumber TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Invalid character(s) removed, correct issue and delete warning."
    ::= 1114123

uxAlmInvalidcharactersincallednumber TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Invalid character(s) removed, correct issue and delete warning."
    ::= 1114124

uxAlmCASsignalinggroupenabled TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "CAS signaling group enabled."
    ::= 1114125

uxAlmCASR2CDBiterror TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "CAS-R2 CD-Bits are mismatched on the span, this alarm is cleared when all channels match."
    ::= 1114126

uxAlmCASR2CDBiterrorclear TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "CAS-R2 CD-Bits now match on this span for all channels."
    ::= 1114127

uxAlmNetworkGlareoccured TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Network glare occured on this interface."
    ::= 1114128

uxAlmConfigvalidationfailure TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Config validation failure during startup. Please check the configuration."
    ::= 1179649

uxAlmNewerConfigLoaded TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Configuration loaded from newer release than currently running release."
    ::= 1179650

uxAlmPassworddecryptionfailed TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Password decryption failed on configuration import operation."
    ::= 1179651

uxAlmPartialFactoryDefault TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Partial 'factory default or configuration import' requested by 'Username' from 'IP address'."
    ::= 1179652

uxAlmConfigurationRestore TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Configuration restore requested by 'Username' from 'IP address'."
    ::= 1179653

uxAlmSGChannelUsageexceededTCAthreshold TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Signaling Group channel usage exceeded configured TCA threshold."
    ::= 1245185

uxAlmSGChannelUsagebelowTCAthreshold TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Signaling Group channel usage fell below configured TCA threshold."
    ::= 1245186

uxAlmSIPCallLicenseUsageexceededTCAthreshold TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "SIP Call license usage exceeded configured TCA threshold."
    ::= 1245187

uxAlmSIPCallLicenseUsagebelowTCAthreshold TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "SIP Call license usage fell below configured TCA threshold."
    ::= 1245188

uxAlmSIPRegistrationUsageexceededTCAthreshold TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "SIP Registration usage exceeded configured TCA threshold."
    ::= 1245189

uxAlmSIPRegistrationUsagebelowTCAthreshold TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "SIP Registration usage fell below configured TCA threshold."
    ::= 1245190

uxAlmDSPUsageexceededTCAthreshold TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "DSP usage exceeded configured TCA threshold."
    ::= 1245191

uxAlmDSPUsagebelowTCAthreshold TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "DSP usage fell below configured TCA threshold."
    ::= 1245192

uxAlmCPUUsageexceededTCAthreshold TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "CPU usage exceeded configured TCA threshold."
    ::= 1245193

uxAlmCPUUsagebelowTCAthreshold TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "CPU usage fell below configured TCA threshold."
    ::= 1245194

uxAlmMemoryUsageexceededTCAthreshold TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Memory usage exceeded configured TCA threshold."
    ::= 1245195

uxAlmMemoryUsagebelowTCAthreshold TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Memory usage fell below configured TCA threshold."
    ::= 1245196

uxAlmFileDescriptorUsageexceededTCAthreshold TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "File Descriptor Usage exceeded TCA threshold."
    ::= 1245197

uxAlmFileDescriptorUsagebelowTCAthreshold TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "File Descriptor Usage fell below TCA threshold."
    ::= 1245198

uxAlmCPUloadaverageinpast1minuteexceededTCAthreshold TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "CPU load average in past 1 minute exceeded TCA threshold."
    ::= 1245199

uxAlmCPUloadaverageinpast1minutefellbelowTCAthreshold TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "CPU load average in past 1 minute fell below TCA threshold."
    ::= 1245200

uxAlmCPUloadaverageinpast5minutesexceededTCAthreshold TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "CPU load average in past 5 minutes exceeded TCA threshold."
    ::= 1245201

uxAlmCPUloadaverageinpast5minutesfellbelowTCAthreshold TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "CPU load average in past 5 minutes fell below TCA threshold."
    ::= 1245202

uxAlmCPUloadaverageinpast15minutesexceededTCAthreshold TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "CPU load average in past 15 minutes exceeded TCA threshold."
    ::= 1245203

uxAlmCPUloadaverageinpast15minutesfellbelowTCAthreshold TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "CPU load average in past 15 minutes fell below TCA threshold."
    ::= 1245204

uxAlmTemporarypartitionusageexceededTCAthreshold TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Temporary partition usage exceeded TCA threshold."
    ::= 1245205

uxAlmTemporarypartitionusagefellbelowTCAthreshold TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Temporary partition usage fell below TCA threshold."
    ::= 1245206

uxAlmLoggingpartitionusageexceededTCAthreshold TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Logging partition usage exceeded TCA threshold."
    ::= 1245207

uxAlmLoggingpartitionusagefellbelowTCAthreshold TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "Logging partition usage fell below TCA threshold."
    ::= 1245208

uxAlmFailedtoresolveFQDN TRAP-TYPE
    ENTERPRISE      uxTraps
    VARIABLES       { uxAlarmActiveIndex, uxAlarmConfigIndex, 
                      uxAlarmActiveID, uxAlarmActiveSubID, 
                      uxAlarmActiveCondition, uxAlarmActiveSeverity, 
                      uxAlarmActiveCategory, uxAlarmActiveCancelType, 
                      uxAlarmActiveDecodeKey, uxAlarmActiveCount, 
                      uxAlarmActiveState, uxAlarmActiveSourceInstance, 
                      uxAlarmActiveFirstOccur, uxAlarmActiveLastOccur, 
                      uxAlarmActiveClrEvtID, uxAlarmActiveClrEvtSubID, 
                      uxAlarmActiveDescription, 
                      uxAlarmActiveHighestSeverityAlarm, 
                      uxAlarmActiveHardWareID }
--     STATUS          mandatory
    DESCRIPTION     
            "Failed to resolve IP address. Ensure that FQDN and DNS server is configured properly."
    ::= 1310721

uxAlmFQDNresolved TRAP-TYPE
    ENTERPRISE      uxTraps
    VARIABLES       { uxAlarmActiveIndex, uxAlarmConfigIndex, 
                      uxAlarmActiveID, uxAlarmActiveSubID, 
                      uxAlarmActiveCondition, uxAlarmActiveCategory, 
                      uxAlarmActiveDecodeKey, 
                      uxAlarmActiveSourceInstance, 
                      uxAlarmActiveDescription }
--     STATUS          mandatory
    DESCRIPTION     
            "IP address successfully resolved."
    ::= 1310722

END -- end of module UX-TRAP-MIB.
