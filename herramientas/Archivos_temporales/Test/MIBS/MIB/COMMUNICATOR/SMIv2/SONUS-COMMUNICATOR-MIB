--
-- This SMIv2 module has been generated by smidump 0.2-cvs. Do not edit.
--

SONUS-COMMUNICATOR-MIB DEFINITIONS ::= BEGIN

IMPORTS
    MODULE-IDENTITY, NOTIFICATION-TYPE, OBJECT-TYPE
        FROM SNMPv2-SMI
    DisplayString
        FROM SNMPv2-TC
    sonusEventClass, sonusEventDescription, sonusEventLevel, 
    sonusEventTime
        FROM SONUS-COMMON-MIB
    sonusHostID
        FROM SONUS-HOST-MIB
    sonusServicesMIBs
        FROM SONUS-SMI;

sonusCommunicatorMIB MODULE-IDENTITY
    LAST-UPDATED    "201506160000Z"
    ORGANIZATION    
            "Sonus Networks, Inc."
    CONTACT-INFO    
            "   Customer Support    
             Sonus Networks, Inc.
             250 Apollo Drive
             Chelmsford, MA 01824
             USA
             
             Tel: 978-614-8100
             Fax: 978-614-8609"
    DESCRIPTION     
            "The MIB Module for Sonus Communicator Management."
    ::= { sonusServicesMIBs 21 }


sonusCommMIBObjects OBJECT IDENTIFIER
    ::= { sonusCommunicatorMIB 1 }

sonusCommMIBNotifications OBJECT IDENTIFIER
    ::= { sonusCommMIBObjects 1 }

sonusCommMIBNotificationsPrefix OBJECT IDENTIFIER
    ::= { sonusCommMIBNotifications 0 }

sonusCommMIBNotificationsObjects OBJECT IDENTIFIER
    ::= { sonusCommMIBNotifications 1 }

sonusCommProcMgmtMIBObjects OBJECT IDENTIFIER
    ::= { sonusCommunicatorMIB 2 }

sonusCommProcMgmtMIBNotifications OBJECT IDENTIFIER
    ::= { sonusCommProcMgmtMIBObjects 1 }

sonusCommProcMgmtMIBNotificationsPrefix OBJECT IDENTIFIER
    ::= { sonusCommProcMgmtMIBNotifications 0 }

sonusCommProcMgmtMIBNotificationsObjects OBJECT IDENTIFIER
    ::= { sonusCommProcMgmtMIBNotifications 1 }

sonusCommProcMgmtProcessName OBJECT-TYPE
    SYNTAX          DisplayString (SIZE(0..50))
    MAX-ACCESS      read-only
    STATUS          current
    DESCRIPTION     
            "This object defines the process name."
    ::= { sonusCommProcMgmtMIBNotificationsObjects 1 }

sonusCommChassisStartupNotification NOTIFICATION-TYPE
    OBJECTS         { sonusEventTime, sonusEventDescription, 
                      sonusEventClass, sonusEventLevel, sonusHostID }
    STATUS          current
    DESCRIPTION     
            "The Sonus Communicator Chassis has started."
    ::= { sonusCommMIBNotificationsPrefix 1 }

sonusCommChassisTestNotification NOTIFICATION-TYPE
    OBJECTS         { sonusEventTime, sonusEventDescription, 
                      sonusEventClass, sonusEventLevel, sonusHostID }
    STATUS          current
    DESCRIPTION     
            "Chassis Test Trap."
    ::= { sonusCommMIBNotificationsPrefix 2 }

sonusCommChassisCriticalTestNotification NOTIFICATION-TYPE
    OBJECTS         { sonusEventTime, sonusEventDescription, 
                      sonusEventClass, sonusEventLevel, sonusHostID }
    STATUS          current
    DESCRIPTION     
            "Test Trap with CRITICAL severity."
    ::= { sonusCommMIBNotificationsPrefix 3 }

sonusCommChassisMajorTestNotification NOTIFICATION-TYPE
    OBJECTS         { sonusEventTime, sonusEventDescription, 
                      sonusEventClass, sonusEventLevel, sonusHostID }
    STATUS          current
    DESCRIPTION     
            "Test Trap with MAJOR severity.."
    ::= { sonusCommMIBNotificationsPrefix 4 }

sonusCommChassisMinorTestNotification NOTIFICATION-TYPE
    OBJECTS         { sonusEventTime, sonusEventDescription, 
                      sonusEventClass, sonusEventLevel, sonusHostID }
    STATUS          current
    DESCRIPTION     
            "Test Trap with MINOR severity."
    ::= { sonusCommMIBNotificationsPrefix 5 }

sonusCommChassisWarnTestNotification NOTIFICATION-TYPE
    OBJECTS         { sonusEventTime, sonusEventDescription, 
                      sonusEventClass, sonusEventLevel, sonusHostID }
    STATUS          current
    DESCRIPTION     
            "Test Trap with WARN severity"
    ::= { sonusCommMIBNotificationsPrefix 6 }

sonusCommChassisClearTestNotification NOTIFICATION-TYPE
    OBJECTS         { sonusEventTime, sonusEventDescription, 
                      sonusEventClass, sonusEventLevel, sonusHostID }
    STATUS          current
    DESCRIPTION     
            "Test Trap with CLEARING severity"
    ::= { sonusCommMIBNotificationsPrefix 7 }

sonusHostPMStatsFileGenerationFailedNotification NOTIFICATION-TYPE
    OBJECTS         { sonusEventTime, sonusEventDescription, 
                      sonusEventClass, sonusEventLevel, sonusHostID }
    STATUS          current
    DESCRIPTION     
            "Generation of Performace Statistics tar file failed.  Detailed message is specified in sonusEventDescription."
    ::= { sonusCommMIBNotificationsPrefix 8 }

sonusCommProcMgmtProcessRestartedNotification NOTIFICATION-TYPE
    OBJECTS         { sonusEventTime, sonusEventDescription, 
                      sonusEventClass, sonusEventLevel, 
                      sonusCommProcMgmtProcessName, sonusHostID }
    STATUS          current
    DESCRIPTION     
            "The process specified by sonusCommProcMgmtProcessName has been restarted by Process Management.  This will occur when Process Management's status request has failed a specified number of times."
    ::= { sonusCommProcMgmtMIBNotificationsPrefix 1 }

sonusCommProcMgmtProcessRestartFailureNotification NOTIFICATION-TYPE
    OBJECTS         { sonusEventTime, sonusEventDescription, 
                      sonusEventClass, sonusEventLevel, 
                      sonusCommProcMgmtProcessName, sonusHostID }
    STATUS          current
    DESCRIPTION     
            "An attempt to restart the process specified by sonusCommProcMgmtProcessName by Process Management has failed."
    ::= { sonusCommProcMgmtMIBNotificationsPrefix 2 }

sonusCommProcMgmtGiveUpRestartNotification NOTIFICATION-TYPE
    OBJECTS         { sonusEventTime, sonusEventDescription, 
                      sonusEventClass, sonusEventLevel, 
                      sonusCommProcMgmtProcessName, sonusHostID }
    STATUS          current
    DESCRIPTION     
            "Process Management has given up attempting to restart the specified process.  This will occur after Process Management has failed to restart the process a specified number of times over a specified time interval."
    ::= { sonusCommProcMgmtMIBNotificationsPrefix 3 }

END -- end of module SONUS-COMMUNICATOR-MIB.
