--
-- This SMIv1 module has been generated by smidump 0.2-cvs. Do not edit.
--

SONUS-SOFTSWITCH-ENUME-MIB DEFINITIONS ::= BEGIN

IMPORTS
    TRAP-TYPE
        FROM RFC-1215
    sonusEventClass, sonusEventDescription, sonusEventLevel, 
    sonusEventTime
        FROM SONUS-COMMON-MIB
    sonusServicesMIBs
        FROM SONUS-SMI;

sonusSoftSwitchEnumeMIB OBJECT IDENTIFIER
    ::= { sonusServicesMIBs 32 }

-- sonusSoftSwitchEnumeMIB MODULE-IDENTITY
--     LAST-UPDATED    "201008040000Z"
--     ORGANIZATION    
--             "Sonus Networks, Inc."
--     CONTACT-INFO    
--             "   Customer Support    
--              Sonus Networks, Inc.
--              7 Tech Park Dr
--              Westford, MA 01886
--              USA
--              
--              Tel: 978-614-8100
--              Fax: 978-614-8609"
--     DESCRIPTION     
--             "The MIB Module for SoftSwitch Enume Management."
--     ::= { sonusServicesMIBs 32 }


sonusSoftSwitchEnumeMIBObjects OBJECT IDENTIFIER
    ::= { sonusSoftSwitchEnumeMIB 1 }

sonusSoftSwitchEnumeMIBNotifications OBJECT IDENTIFIER
    ::= { sonusSoftSwitchEnumeMIB 2 }

sonusSoftSwitchEnumeMIBNotificationsPrefix OBJECT IDENTIFIER
    ::= { sonusSoftSwitchEnumeMIBNotifications 0 }

sonusSoftSwitchEnumeMIBNotificationsObjects OBJECT IDENTIFIER
    ::= { sonusSoftSwitchEnumeMIBNotifications 1 }

sonusSoftSwitchEnumeDownNotification TRAP-TYPE
    ENTERPRISE      sonusSoftSwitchEnumeMIBNotifications
    VARIABLES       { sonusEventDescription, sonusEventClass, 
                      sonusEventLevel, sonusEventTime }
--     STATUS          mandatory
    DESCRIPTION     
            "Enume is down"
    ::= 1

sonusSoftSwitchEnumeUpNotification TRAP-TYPE
    ENTERPRISE      sonusSoftSwitchEnumeMIBNotifications
    VARIABLES       { sonusEventDescription, sonusEventClass, 
                      sonusEventLevel, sonusEventTime }
--     STATUS          mandatory
    DESCRIPTION     
            "Enume is up"
    ::= 2

END -- end of module SONUS-SOFTSWITCH-ENUME-MIB.
