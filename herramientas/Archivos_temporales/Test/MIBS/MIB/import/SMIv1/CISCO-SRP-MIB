--
-- This SMIv1 module has been generated by smidump 0.2-cvs. Do not edit.
--

CISCO-SRP-MIB DEFINITIONS ::= BEGIN

IMPORTS
    ciscoExperiment
        FROM CISCO-SMI
    CounterBasedGauge64
        FROM HCNUM-TC
    OBJECT-TYPE
        FROM RFC-1212
    TRAP-TYPE
        FROM RFC-1215
    Counter
        FROM RFC1155-SMI
    ifIndex
        FROM RFC1213-MIB
    MacAddress, TimeStamp, TruthValue
        FROM SNMPv2-TC;

ciscosrpMIB OBJECT IDENTIFIER
    ::= { ciscoExperiment 60 }

-- ciscosrpMIB MODULE-IDENTITY
--     LAST-UPDATED    "200103280000Z"
--     ORGANIZATION    
--             "Cisco Systems, Inc."
--     CONTACT-INFO    
--             "       Cisco Systems
--              Customer Service
--              
--              Postal: 170 W Tasman Drive
--              San Jose, CA 95134
--              USA 
--              
--              Tel:  +1 800 553-NETS 
--              
--              E-mail: cs-dpt@cisco.com"
--     DESCRIPTION     
--             "The MIB module to describe objects for Spatial Reuse
--              Protocol (SRP) interface layer."
--     REVISION        "200103280000Z"
--     DESCRIPTION     
--             "Second version of this MIB module.
--              srpErrorsCountersCurrentTable and
--              srpErrorsCountersIntervalTable have been deprecated
--              and replaced with srpErrCntCurrentTable and
--              srpErrCntIntervalTable. 
--              The srpMACCountersTable has been deprecated."
--     REVISION        "200004170000Z"
--     DESCRIPTION     
--             "Initial version of this MIB module."
--     ::= { ciscoExperiment 60 }


InterfaceSide ::=
    INTEGER { sideA(1), sideB(2) }

-- InterfaceSide ::= TEXTUAL-CONVENTION
--     STATUS          mandatory
--     DESCRIPTION     
--             "An indication of the side of the interface. 
--              An SRP ring is composed of two fiber rings: Outer
--              and Inner. Outer ring traffic flows clockwise.
--              Inner ring traffic flows counter-clockwise.
--              The side of a node with Outer ring receive fiber
--              is identified as side A, the side of a node with
--              Inner ring receive fiber is identified as B.
--              Side A must be connected to side B.
--              The SRP protocol operates by sending data traffic
--              in one direction known as downstream and it's
--              corresponding control information in the opposite
--              direction known as upstream."
--     SYNTAX          INTEGER
--                       { sideA(1), sideB(2) }

IpsMode ::=
    INTEGER { noRequest(1), waitToRestore(2), manualSwitch(3), 
                        signalDegrade(4), signalFail(5), forcedSwitch(6) }

-- IpsMode ::= TEXTUAL-CONVENTION
--     STATUS          mandatory
--     DESCRIPTION     
--             "An Intelligent Protection Switching mode.
--              
--              An SRP ring provides redundancy and protection from a failed
--              node or a link/fiber cut through the use of IPS modes that are
--              automatic or operator/user-configured.  Automatic IPS modes
--              take effect when the ring detects an event, a fiber cut, or a
--              node failure and remain in effect until the wait-to-restore
--              value expires.  As the protection requests travel around the
--              ring, the protection hierarchy is applied.  All modes are
--              signalled on the IPS messaging channel. If an node or fiber
--              facility failure is detected, traffic going toward or coming
--              from the failure direction is wrapped (looped) back to go in
--              opposite direction on the other ring.  The wrap around takes
--              place on the nodes adjacent to the failure.  This way the
--              traffic is re-routed from the failed span.
--              
--              The ISP modes starting from the highest to the lowest level
--              in the IPS protection hierarchy are:
--              
--              'forcedSwitch' -
--                   an operator-configured mode which causes a high-priority
--                   protection switch wrap on each end of a specified span.
--              'signalFail' -
--                   an automatically-detected mode which causes a protection
--                   switch wrap on a span when a media signal failure is
--                   detected.
--              'signalDegrade' -
--                   an automatically-detected mode which causes protection
--                   switch wraps on a span when a media signal degrade is
--                   detected due to excessive Bit Error Rate.
--              'manualSwitch' -
--                   an operator-configured mode which causes a low-prioority
--                   protection switch wrap on each end of a specified span.
--              'waitToRestore' -
--                   an automatically-invoked mode which results in a waiting
--                   period after the working channel meets the restoration
--                   criteria after a signal fail or signal degrade condition
--                   disappears to prevent protection switch oscilation.
--              'normal' -
--                   a mode which can be configured by an operator, and/or is
--                   in effect when no other mode has been automatically
--                   detected/invoked."
--     SYNTAX          INTEGER
--                       { noRequest(1), waitToRestore(2), 
--                         manualSwitch(3), signalDegrade(4), 
--                         signalFail(5), forcedSwitch(6) }

-- PerfCurrentCount64 ::= TEXTUAL-CONVENTION
--     STATUS          mandatory
--     DESCRIPTION     
--             "A counter associated with a
--              performance measurement in a current 15
--              minute measurement interval. The value
--              of this counter starts from zero and is
--              increased when associated events occur,
--              until the end of the 15 minute interval.
--              At that time the value of the counter is
--              stored in the first 15 minute history
--              interval, and the CurrentCount is
--              restarted at zero. In the
--              case where the agent has no valid data
--              available for the current interval the
--              corresponding object instance is not
--              available and upon a retrieval request
--              a corresponding error message shall be
--              returned to indicate that this instance
--              does not exist (for example, a noSuchInstance
--              for SNMPv2 GET operation)."
--     SYNTAX          CounterBasedGauge64

-- PerfIntervalCount64 ::= TEXTUAL-CONVENTION
--     STATUS          mandatory
--     DESCRIPTION     
--             "A counter associated with a
--              performance measurement in a previous
--              15 minute measurement interval. In the
--              case where the agent has no valid data
--              available for a particular interval the
--              corresponding object instance is not
--              available and upon a retrieval request
--              a corresponding error message shall be
--              returned to indicate that this instance
--              does not exist (for example, a noSuchInstance
--              for SNMPv2 GET operation).
--              In a system supporting
--              a history of n intervals with
--              IntervalCount(1) and IntervalCount(n) the
--              most and least recent intervals
--              respectively, the following applies at
--              the end of a 15 minute interval:
--              - discard the value of IntervalCount(n)
--              - the value of IntervalCount(i) becomes that
--                of IntervalCount(i-1) for n >= i > 1
--              - the value of IntervalCount(1) becomes that
--                of CurrentCount
--              - the TotalCount, if supported, is adjusted."
--     SYNTAX          CounterBasedGauge64

srpMAC OBJECT IDENTIFIER
    ::= { ciscosrpMIB 1 }

srpIfTable OBJECT-TYPE
    SYNTAX          SEQUENCE OF SrpIfEntry
    ACCESS          not-accessible
    STATUS          mandatory
    DESCRIPTION     
            "The SRP interface table."
    ::= { srpMAC 1 }

srpIfEntry OBJECT-TYPE
    SYNTAX          SrpIfEntry
    ACCESS          not-accessible
    STATUS          mandatory
    DESCRIPTION     
            "There exists one such entry for every interface
             in the ifTable which has an ifType of SRP interface (151)
             Each of these entries are indexed by the value
             of ifIndex as defined in RFC2233."
    INDEX           { ifIndex }
    ::= { srpIfTable 1 }

SrpIfEntry ::=
    SEQUENCE {
        srpMACAddress                   MacAddress,
        srpPriorityThreshold            INTEGER,
        srpNodesOnTheRing               INTEGER,
        srpIpsState                     INTEGER,
        srpIpsLockedOut                 TruthValue,
        srpIpsWaitToRestoreTimer        INTEGER,
        srpIfTimeElapsed                INTEGER,
        srpIfValidIntervals             INTEGER
    }

srpMACAddress OBJECT-TYPE
    SYNTAX          MacAddress
    ACCESS          read-only
    STATUS          mandatory
    DESCRIPTION     
            "The MAC's 48-bit individual MAC address."
    ::= { srpIfEntry 1 }

srpPriorityThreshold OBJECT-TYPE
    SYNTAX          INTEGER (0..7)
    ACCESS          read-write
    STATUS          mandatory
    DESCRIPTION     
            "The priority threshold value to be compared against
             the 3 bits of priority contained in each packet's SRP
             header. If a packet's priority is greater or equal to
             this threshold, that packet should be placed in the
             high priority transmit or transit queue. If a packet's
             priority is less than this threshold, it should be
             placed in the low priority transmit or transit queue.
             
             Since there are only two types of priority
             queues (High Priority and Low Priority) a packet
             is treated as either low or high priority once it is 
             on the ring. Each node determines the threshold
             value for classifying what is considered a high
             priority packet and what is considered a low priority
             packet."
    ::= { srpIfEntry 2 }

srpNodesOnTheRing OBJECT-TYPE
    SYNTAX          INTEGER (0..128)
    ACCESS          read-only
    STATUS          mandatory
    DESCRIPTION     
            "The number of nodes in the SRP ring.
             When interface is down the value is 0."
    ::= { srpIfEntry 3 }

srpIpsState OBJECT-TYPE
    SYNTAX          INTEGER { idle(1), passThrough(2), wrapped(3) }
    ACCESS          read-only
    STATUS          mandatory
    DESCRIPTION     
            "Each node in the Intelligent Protection Switching (IPS)
             is one of the following states.
             Idle - In this mode the node is ready to perform protection
             and it sends to both neighboring nodes idle IPS messages,
             which include self in the source address field
             {0, SELF, 0, S}.
             
             PassThrough - Node participate in a protection switch by
             passing the wrapped traffic and long path signalling through
             itself. This state is entered based on received IPS messages.
             
             Wrapped - Node participate in a protection switch with a wrap
             present. This state is entered based on protection request
                   issued locally or based on received IPS messages.
             
             When interface is down the value for IPS state
             is passThrough."
    ::= { srpIfEntry 4 }

srpIpsLockedOut OBJECT-TYPE
    SYNTAX          TruthValue
    ACCESS          read-write
    STATUS          mandatory
    DESCRIPTION     
            "The boolean flag to indicate node
             LockedOut of protection state. If it's true than
             Intelligent Protection Swiching is disabled and
             the node will not wrap on either side of the interface."
    ::= { srpIfEntry 5 }

srpIpsWaitToRestoreTimer OBJECT-TYPE
    SYNTAX          INTEGER (10..600)
    ACCESS          read-write
    STATUS          mandatory
    DESCRIPTION     
            "Indicates the length of time in seconds,
             to remain in the wrap state, after the cause
             of a wrap is removed. This mechanism prevents
             protection switch oscillations. Default value is 60 sec."
    ::= { srpIfEntry 6 }

srpIfTimeElapsed OBJECT-TYPE
    SYNTAX          INTEGER (1..900)
    ACCESS          read-only
    STATUS          mandatory
    DESCRIPTION     
            "The number of seconds, including partial seconds,
             that have elapsed since the beginning of the current
             measurement interval as described in RFC 2493.
             If, for some reason, such as an
             adjustment in the system's time-of-day clock, the
             current interval exceeds the maximum value, the
             agent will return the maximum value."
    ::= { srpIfEntry 7 }

srpIfValidIntervals OBJECT-TYPE
    SYNTAX          INTEGER (0..96)
    ACCESS          read-only
    STATUS          mandatory
    DESCRIPTION     
            "The number of previous 15-minute
             measurement intervals
             for which data was collected.
             A SRP interface must be capable
             of supporting at least n intervals.
             The minimum value of n is 4.
             The default of n is 32.
             The maximum value of n is 96.
             The value will be <n> unless the measurement was
             (re-)started within the last (<n>*15) minutes, in which
             case the value will be the number of complete 15
             minute intervals for which the agent has at least
             some data. In certain cases (e.g., in the case
             where the agent is a proxy) it is possible that some
             intervals are unavailable.  In this case, this
             interval is the maximum interval number for
             which data is available. "
    ::= { srpIfEntry 8 }

srpMACSideTable OBJECT-TYPE
    SYNTAX          SEQUENCE OF SrpMACSideEntry
    ACCESS          not-accessible
    STATUS          mandatory
    DESCRIPTION     
            "A table of information about the sides of SRP interfaces."
    ::= { srpMAC 2 }

srpMACSideEntry OBJECT-TYPE
    SYNTAX          SrpMACSideEntry
    ACCESS          not-accessible
    STATUS          mandatory
    DESCRIPTION     
            "A list of information specific to a particular
             side of a particular SRP interface."
    INDEX           { ifIndex, srpMACInterfaceSide }
    ::= { srpMACSideTable 1 }

SrpMACSideEntry ::=
    SEQUENCE {
        srpMACInterfaceSide             InterfaceSide,
        srpMACNeighborAddress           MacAddress,
        srpMACSideWrapped               TruthValue,
        srpMACIpsMgmtRequestedMode      IpsMode,
        srpMACIpsAutoDetectMode         IpsMode,
        srpMACIpsRemoteMode             IpsMode,
        srpMACIpsRemoteType             INTEGER,
        srpMACIpsActiveMode             IpsMode,
        srpMACIpsWrapCounter            Counter,
        srpMACIpsLastWrapTimeStamp      TimeStamp,
        srpMACIpsLastUnWrapTimeStamp    TimeStamp,
        srpMACClockSourceMode           INTEGER,
        srpMACTopologyTimer             INTEGER
    }

srpMACInterfaceSide OBJECT-TYPE
    SYNTAX          InterfaceSide
    ACCESS          not-accessible
    STATUS          mandatory
    DESCRIPTION     
            "An indication of the side of the interface for which
             this row contains information."
    ::= { srpMACSideEntry 1 }

srpMACNeighborAddress OBJECT-TYPE
    SYNTAX          MacAddress
    ACCESS          read-only
    STATUS          mandatory
    DESCRIPTION     
            "The MAC's neighbor's 48-bit individual
             MAC address."
    ::= { srpMACSideEntry 2 }

srpMACSideWrapped OBJECT-TYPE
    SYNTAX          TruthValue
    ACCESS          read-only
    STATUS          mandatory
    DESCRIPTION     
            "The boolean flag to indicate the node's wrapped state."
    ::= { srpMACSideEntry 3 }

srpMACIpsMgmtRequestedMode OBJECT-TYPE
    SYNTAX          IpsMode
    ACCESS          read-write
    STATUS          mandatory
    DESCRIPTION     
            "The IPS mode requested by management for the local node
             that can affect the srpMACIpsActiveMode state  
             of the SRP node, according to the set of rules describing IPS 
             protocol. This variable value is one from the following subset
             (noRequest, manualSwitch, forcedSwitch)."
    ::= { srpMACSideEntry 4 }

srpMACIpsAutoDetectMode OBJECT-TYPE
    SYNTAX          IpsMode
    ACCESS          read-only
    STATUS          mandatory
    DESCRIPTION     
            "The current IPS mode as automatically detected 
             by the the local node that can affect
             the srpMACIpsActiveMode state of the SRP node,
             according to the set of rules describing IPS protocol.
             This variable value is one from the following subset
             (SignalFail, SignalDegrade, WaitToRestore)."
    ::= { srpMACSideEntry 5 }

srpMACIpsRemoteMode OBJECT-TYPE
    SYNTAX          IpsMode
    ACCESS          read-only
    STATUS          mandatory
    DESCRIPTION     
            "The IPS mode indicated in IPS messages being received by
             the local node from other nodes on the ring,
             that can affect the srpMACIpsActiveMode state  
             of the SRP node, according to the set of rules describing IPS 
             protocol."
    ::= { srpMACSideEntry 6 }

srpMACIpsRemoteType OBJECT-TYPE
    SYNTAX          INTEGER { shortPath(1), longPath(2) }
    ACCESS          read-only
    STATUS          mandatory
    DESCRIPTION     
            "Indicates if srpMACIpsRemoteMode object value
             belongs to the adjacent node in the case of the shortPath
             or belongs to the non-adjacent node in the case
             of the longPath."
    ::= { srpMACSideEntry 7 }

srpMACIpsActiveMode OBJECT-TYPE
    SYNTAX          IpsMode
    ACCESS          read-only
    STATUS          mandatory
    DESCRIPTION     
            "The currently active IPS mode
             for the local node, which can be changed based on
             combined effect of the following variables:
                srpMACIpsMgmtRequestedMode,
                srpMACIpsAutoDetectMode,
                srpMACIpsRemoteMode, and
                srpMACIpsRemoteType
             according to the set of rules describing IPS protocol."
    ::= { srpMACSideEntry 8 }

srpMACIpsWrapCounter OBJECT-TYPE
    SYNTAX          Counter
    ACCESS          read-only
    STATUS          mandatory
    DESCRIPTION     
            "The number of transition from unwrap  
             to wrap state."
    ::= { srpMACSideEntry 9 }

srpMACIpsLastWrapTimeStamp OBJECT-TYPE
    SYNTAX          TimeStamp
    ACCESS          read-only
    STATUS          mandatory
    DESCRIPTION     
            "The value of sysUpTime for the last wrap."
    ::= { srpMACSideEntry 10 }

srpMACIpsLastUnWrapTimeStamp OBJECT-TYPE
    SYNTAX          TimeStamp
    ACCESS          read-only
    STATUS          mandatory
    DESCRIPTION     
            "The value of sysUpTime for the last unwrap."
    ::= { srpMACSideEntry 11 }

srpMACClockSourceMode OBJECT-TYPE
    SYNTAX          INTEGER { internal(1), line(2) }
    ACCESS          read-write
    STATUS          mandatory
    DESCRIPTION     
            "Indicates the mode of the SRP interface clock source.
             
             Internal - mode specifies the clock source as internal, and   
             is used when connecting between two routers over a dark fiber
             or over WDM system.
             The internal mode is used as a default value.
             
             Line -  mode specifies the clock source as line, and is used
             when connecting a router to SONET/SDH ADM."
    ::= { srpMACSideEntry 12 }

srpMACTopologyTimer OBJECT-TYPE
    SYNTAX          INTEGER (1..600)
    ACCESS          read-write
    STATUS          mandatory
    DESCRIPTION     
            "Indicates the topology-timer on a SRP ring, how frequently
             topology discovery messages are sent around ring to identify
             the nodes. Toplogy discovery is always on. 
             The default value is 10 seconds."
    ::= { srpMACSideEntry 13 }

srpRingTopologyMapTable OBJECT-TYPE
    SYNTAX          SEQUENCE OF SrpRingTopologyMapEntry
    ACCESS          not-accessible
    STATUS          mandatory
    DESCRIPTION     
            "A list of SRP ring topology map entries."
    ::= { srpMAC 3 }

srpRingTopologyMapEntry OBJECT-TYPE
    SYNTAX          SrpRingTopologyMapEntry
    ACCESS          not-accessible
    STATUS          mandatory
    DESCRIPTION     
            "A MAC entry containing information
             specific to a particular node on the ring."
    INDEX           { ifIndex, srpNodeHopsNumber }
    ::= { srpRingTopologyMapTable 1 }

SrpRingTopologyMapEntry ::=
    SEQUENCE {
        srpNodeHopsNumber               Gauge,
        srpNodeMACAddress               MacAddress,
        srpNodeWrapped                  TruthValue,
        srpNodeName                     DisplayString
    }

srpNodeHopsNumber OBJECT-TYPE
    SYNTAX          Gauge (0..128)
    ACCESS          not-accessible
    STATUS          mandatory
    DESCRIPTION     
            "A value, between 0 and (srpNodesOnTheRing - 1), used
             to identify the particular node which is the number
             of hops around the ring (clock-wise) away from
             the local node."
    ::= { srpRingTopologyMapEntry 1 }

srpNodeMACAddress OBJECT-TYPE
    SYNTAX          MacAddress
    ACCESS          read-only
    STATUS          mandatory
    DESCRIPTION     
            "The node MAC's 48-bit individual MAC address."
    ::= { srpRingTopologyMapEntry 2 }

srpNodeWrapped OBJECT-TYPE
    SYNTAX          TruthValue
    ACCESS          read-only
    STATUS          mandatory
    DESCRIPTION     
            "Indicates in general if the node is wrapped
             without specifying on which side."
    ::= { srpRingTopologyMapEntry 3 }

srpNodeName OBJECT-TYPE
    SYNTAX          DisplayString (SIZE(0..255))
    ACCESS          read-only
    STATUS          mandatory
    DESCRIPTION     
            "The node name reported by the SRP protocol.
             If the name is not known then this field is left blank."
    ::= { srpRingTopologyMapEntry 4 }

srpMACCountersTable OBJECT-TYPE
    SYNTAX          SEQUENCE OF SrpMACCountersEntry
    ACCESS          not-accessible
    STATUS          deprecated
    DESCRIPTION     
            "The MAC layer traffic Counters table."
    ::= { srpMAC 6 }

srpMACCountersEntry OBJECT-TYPE
    SYNTAX          SrpMACCountersEntry
    ACCESS          not-accessible
    STATUS          deprecated
    DESCRIPTION     
            "A packet counting and packet reject capability for a
             source and/or destination address on a 
             particular SRP interface."
    INDEX           { ifIndex }
    ::= { srpMACCountersTable 1 }

SrpMACCountersEntry ::=
    SEQUENCE {
        srpMACCountPktsBySourceFlag     TruthValue,
        srpMACCountPktsBySourceAddress  MacAddress,
        srpMACSourceDiscontTimeStamp    TimeStamp,
--         srpMACCountPktsBySource         Counter64,
        srpMACCountPktsByDestinationFlag TruthValue,
        srpMACCountPktsByDestAddress    MacAddress,
        srpMACDestDiscontTimeStamp      TimeStamp,
--         srpMACCountPktsByDest           Counter64,
        srpMACRejectPktsBySourceFlag    TruthValue,
        srpMACRejectPktsBySourceAddress MacAddress,
        srpMACRejectPktsByDestFlag      TruthValue,
        srpMACRejectPktsByDestAddress   MacAddress
    }

srpMACCountPktsBySourceFlag OBJECT-TYPE
    SYNTAX          TruthValue
    ACCESS          read-write
    STATUS          deprecated
    DESCRIPTION     
            "Indicates that packets are to be counted
             for a particular source address."
    ::= { srpMACCountersEntry 1 }

srpMACCountPktsBySourceAddress OBJECT-TYPE
    SYNTAX          MacAddress
    ACCESS          read-write
    STATUS          deprecated
    DESCRIPTION     
            "Indicates the particular source address for which packets
             are to be counted when the corresponding instance of
             srpMACCountPktsBySourceFlag has the value 'true'."
    ::= { srpMACCountersEntry 2 }

srpMACSourceDiscontTimeStamp OBJECT-TYPE
    SYNTAX          TimeStamp
    ACCESS          read-only
    STATUS          deprecated
    DESCRIPTION     
            "The value of sysUpTime on the most recent occasion when
             there was a change in the value of the corresponding
             instances of either srpMACCountPktsBySourceAddress
             or srpMACCountPktsBySourceFlag."
    ::= { srpMACCountersEntry 3 }

-- srpMACCountPktsBySource OBJECT-TYPE
--     SYNTAX          Counter64
--     ACCESS          read-only
--     STATUS          deprecated
--     DESCRIPTION     
--             "Counter for the number of packets received
--              from a particular source node's MAC address.
--              Discontinuities in the value of this counter can occur
--              at re-initialization of the management system, and at
--              other times as indicated by the value of
--              srpMACSourceDiscontTimeStamp."
--     ::= { srpMACCountersEntry 4 }

srpMACCountPktsByDestinationFlag OBJECT-TYPE
    SYNTAX          TruthValue
    ACCESS          read-write
    STATUS          deprecated
    DESCRIPTION     
            "Indicates that packets are to be counted
             for a particular destination address."
    ::= { srpMACCountersEntry 5 }

srpMACCountPktsByDestAddress OBJECT-TYPE
    SYNTAX          MacAddress
    ACCESS          read-write
    STATUS          deprecated
    DESCRIPTION     
            "Indicates the particular destination address for which 
             packets are to be counted when the corresponding instance 
             of srpMACCountPktsByDestinationFlag
             has the value 'true'."
    ::= { srpMACCountersEntry 6 }

srpMACDestDiscontTimeStamp OBJECT-TYPE
    SYNTAX          TimeStamp
    ACCESS          read-only
    STATUS          deprecated
    DESCRIPTION     
            "The value of sysUpTime on the most recent occasion when
             there was a change in the value of the corresponding
             instances of either srpMACCountPktsByDestAddress 
             or srpMACCountPktsByDestinationFlag."
    ::= { srpMACCountersEntry 7 }

-- srpMACCountPktsByDest OBJECT-TYPE
--     SYNTAX          Counter64
--     ACCESS          read-only
--     STATUS          deprecated
--     DESCRIPTION     
--             "Counter for the number of packets send
--              to a particular destination node's MAC address.
--              Discontinuities in the value of this counter can occur
--              at re-initialization of the management system, and at
--              other times as indicated by the value of
--              srpMACDestDiscontTimeStamp."
--     ::= { srpMACCountersEntry 8 }

srpMACRejectPktsBySourceFlag OBJECT-TYPE
    SYNTAX          TruthValue
    ACCESS          read-write
    STATUS          deprecated
    DESCRIPTION     
            "Indicates that packets are to be rejected
             for a particular source address."
    ::= { srpMACCountersEntry 9 }

srpMACRejectPktsBySourceAddress OBJECT-TYPE
    SYNTAX          MacAddress
    ACCESS          read-write
    STATUS          deprecated
    DESCRIPTION     
            "Indicates the particular source address for which
             packets are to rejected when the corresponding
             instance of srpMACRejectPktsBySourceFlag
             has the value 'true'."
    ::= { srpMACCountersEntry 10 }

srpMACRejectPktsByDestFlag OBJECT-TYPE
    SYNTAX          TruthValue
    ACCESS          read-write
    STATUS          deprecated
    DESCRIPTION     
            "Indicates that packets are to be rejected
             for a particular destination address."
    ::= { srpMACCountersEntry 11 }

srpMACRejectPktsByDestAddress OBJECT-TYPE
    SYNTAX          MacAddress
    ACCESS          read-write
    STATUS          deprecated
    DESCRIPTION     
            "Indicates the particular destination address for which
             packets are to rejected when the corresponding
             instance of srpMACRejectPktsByDestFlag
             has the value 'true'."
    ::= { srpMACCountersEntry 12 }

srpRingCounters OBJECT IDENTIFIER
    ::= { ciscosrpMIB 2 }

srpRingCountersCurrentTable OBJECT-TYPE
    SYNTAX          SEQUENCE OF SrpRingCountersCurrentEntry
    ACCESS          not-accessible
    STATUS          mandatory
    DESCRIPTION     
            "The Physical medium dependent layer
             Current counters table."
    ::= { srpRingCounters 1 }

srpRingCountersCurrentEntry OBJECT-TYPE
    SYNTAX          SrpRingCountersCurrentEntry
    ACCESS          not-accessible
    STATUS          mandatory
    DESCRIPTION     
            "Packets and octets statistics for the current interval
             for the Physical medium dependent layer of a particular
             side of a particular SRP interface. The corresponding
             instance of srpIfTimeElapsed indicates the number
             of seconds which have elapsed so far
             in the current interval."
    INDEX           { ifIndex, srpRingInterfaceSide }
    ::= { srpRingCountersCurrentTable 1 }

SrpRingCountersCurrentEntry ::=
    SEQUENCE {
        srpRingInterfaceSide            InterfaceSide
--         srpRingCurUcastLowPriPktsIn     CounterBasedGauge64,
--         srpRingCurUcastLowPriOctetsIn   CounterBasedGauge64,
--         srpRingCurMcastLowPriPktsIn     CounterBasedGauge64,
--         srpRingCurMcastLowPriOctetsIn   CounterBasedGauge64,
--         srpRingCurUcastHighPriPktsIn    CounterBasedGauge64,
--         srpRingCurUcastHighPriOctetsIn  CounterBasedGauge64,
--         srpRingCurMcastHighPriPktsIn    CounterBasedGauge64,
--         srpRingCurMcastHighPriOctetsIn  CounterBasedGauge64,
--         srpRingCurUcastLowPriPktsOut    CounterBasedGauge64,
--         srpRingCurUcastLowPriOctetsOut  CounterBasedGauge64,
--         srpRingCurMcastLowPriPktsOut    CounterBasedGauge64,
--         srpRingCurMcastLowPriOctetsOut  CounterBasedGauge64,
--         srpRingCurUcastHighPriPktsOut   CounterBasedGauge64,
--         srpRingCurUcastHighPriOctetsOut CounterBasedGauge64,
--         srpRingCurMcastHighPriPktsOut   CounterBasedGauge64,
--         srpRingCurMcastHighPriOctetsOut CounterBasedGauge64
    }

srpRingInterfaceSide OBJECT-TYPE
    SYNTAX          InterfaceSide
    ACCESS          not-accessible
    STATUS          mandatory
    DESCRIPTION     
            "An indication of the side of the interface for which
             this row contains information."
    ::= { srpRingCountersCurrentEntry 1 }

-- srpRingCurUcastLowPriPktsIn OBJECT-TYPE
--     SYNTAX          CounterBasedGauge64
--     ACCESS          read-only
--     STATUS          mandatory
--     DESCRIPTION     
--             "The counter associated with the number of low priority 
--              unicast packets received from
--              the Physical medium dependent layer
--              in the current 15 minute interval."
--     ::= { srpRingCountersCurrentEntry 2 }

-- srpRingCurUcastLowPriOctetsIn OBJECT-TYPE
--     SYNTAX          CounterBasedGauge64
--     ACCESS          read-only
--     STATUS          mandatory
--     DESCRIPTION     
--             "The counter associated with the number of low priority 
--              unicast octets received from
--              the Physical medium dependent layer
--              in the current 15minute interval."
--     ::= { srpRingCountersCurrentEntry 3 }

-- srpRingCurMcastLowPriPktsIn OBJECT-TYPE
--     SYNTAX          CounterBasedGauge64
--     ACCESS          read-only
--     STATUS          mandatory
--     DESCRIPTION     
--             "The counter associated with the number of low priority 
--              multicast packets received from
--              the Physical medium dependent layer
--              in the current 15 minute interval."
--     ::= { srpRingCountersCurrentEntry 4 }

-- srpRingCurMcastLowPriOctetsIn OBJECT-TYPE
--     SYNTAX          CounterBasedGauge64
--     ACCESS          read-only
--     STATUS          mandatory
--     DESCRIPTION     
--             "The counter associated with the number of low priority 
--              multicast octets received from
--              the Physical medium dependent layer
--              in the current 15 minute interval."
--     ::= { srpRingCountersCurrentEntry 5 }

-- srpRingCurUcastHighPriPktsIn OBJECT-TYPE
--     SYNTAX          CounterBasedGauge64
--     ACCESS          read-only
--     STATUS          mandatory
--     DESCRIPTION     
--             "The counter associated with the number of high priority 
--              unicast packets received from
--              the Physical medium dependent layer
--              in the current 15 minute interval."
--     ::= { srpRingCountersCurrentEntry 6 }

-- srpRingCurUcastHighPriOctetsIn OBJECT-TYPE
--     SYNTAX          CounterBasedGauge64
--     ACCESS          read-only
--     STATUS          mandatory
--     DESCRIPTION     
--             "The counter associated with the number of high priority 
--              unicast octets received from
--              the Physical medium dependent layer
--              in the current 15 minute interval."
--     ::= { srpRingCountersCurrentEntry 7 }

-- srpRingCurMcastHighPriPktsIn OBJECT-TYPE
--     SYNTAX          CounterBasedGauge64
--     ACCESS          read-only
--     STATUS          mandatory
--     DESCRIPTION     
--             "The counter associated with the number of high priority 
--              multicast packets received from
--              the Physical medium dependent layer
--              in the current 15 minute interval."
--     ::= { srpRingCountersCurrentEntry 8 }

-- srpRingCurMcastHighPriOctetsIn OBJECT-TYPE
--     SYNTAX          CounterBasedGauge64
--     ACCESS          read-only
--     STATUS          mandatory
--     DESCRIPTION     
--             "The counter associated with the number of high priority 
--              multicast octets received from
--              the Physical medium dependent layer
--              in the current 15 minute interval."
--     ::= { srpRingCountersCurrentEntry 9 }

-- srpRingCurUcastLowPriPktsOut OBJECT-TYPE
--     SYNTAX          CounterBasedGauge64
--     ACCESS          read-only
--     STATUS          mandatory
--     DESCRIPTION     
--             "The counter associated with the number of low priority
--              unicast packets going to the Physical medium dependent 
--              layer in the current 15 minute interval."
--     ::= { srpRingCountersCurrentEntry 10 }

-- srpRingCurUcastLowPriOctetsOut OBJECT-TYPE
--     SYNTAX          CounterBasedGauge64
--     ACCESS          read-only
--     STATUS          mandatory
--     DESCRIPTION     
--             "The counter associated with the number of low priority 
--              unicast octets going to the Physical medium dependent 
--              layer in the current 15 minute interval."
--     ::= { srpRingCountersCurrentEntry 11 }

-- srpRingCurMcastLowPriPktsOut OBJECT-TYPE
--     SYNTAX          CounterBasedGauge64
--     ACCESS          read-only
--     STATUS          mandatory
--     DESCRIPTION     
--             "The counter associated with the number of low priority 
--              multicast packets going to the Physical medium dependent 
--              layer in the current 15 minute interval."
--     ::= { srpRingCountersCurrentEntry 12 }

-- srpRingCurMcastLowPriOctetsOut OBJECT-TYPE
--     SYNTAX          CounterBasedGauge64
--     ACCESS          read-only
--     STATUS          mandatory
--     DESCRIPTION     
--             "The counter associated with the number of low priority 
--              multicast octets going to the Physical medium dependent 
--              layer in the current 15 minute interval."
--     ::= { srpRingCountersCurrentEntry 13 }

-- srpRingCurUcastHighPriPktsOut OBJECT-TYPE
--     SYNTAX          CounterBasedGauge64
--     ACCESS          read-only
--     STATUS          mandatory
--     DESCRIPTION     
--             "The counter associated with the number of high priority 
--              unicast packets going to the Physical medium dependent 
--              layer in the current 15 minute interval."
--     ::= { srpRingCountersCurrentEntry 14 }

-- srpRingCurUcastHighPriOctetsOut OBJECT-TYPE
--     SYNTAX          CounterBasedGauge64
--     ACCESS          read-only
--     STATUS          mandatory
--     DESCRIPTION     
--             "The counter associated with the number of high priority 
--              unicast octets going to the Physical medium dependent 
--              layer in the current 15 minute interval."
--     ::= { srpRingCountersCurrentEntry 15 }

-- srpRingCurMcastHighPriPktsOut OBJECT-TYPE
--     SYNTAX          CounterBasedGauge64
--     ACCESS          read-only
--     STATUS          mandatory
--     DESCRIPTION     
--             "The counter associated with the number of high priority
--              multicast packets going to the Physical medium dependent 
--              layer in the current 15 minute interval."
--     ::= { srpRingCountersCurrentEntry 16 }

-- srpRingCurMcastHighPriOctetsOut OBJECT-TYPE
--     SYNTAX          CounterBasedGauge64
--     ACCESS          read-only
--     STATUS          mandatory
--     DESCRIPTION     
--             "The counter associated with the number of high priority
--              multicast octets going to the Physical medium dependent 
--              layer in the current 15 minute interval."
--     ::= { srpRingCountersCurrentEntry 17 }

srpRingCountersIntervalTable OBJECT-TYPE
    SYNTAX          SEQUENCE OF SrpRingCountersIntervalEntry
    ACCESS          not-accessible
    STATUS          mandatory
    DESCRIPTION     
            "The Physical medium dependent layer
             Interval counters table."
    ::= { srpRingCounters 2 }

srpRingCountersIntervalEntry OBJECT-TYPE
    SYNTAX          SrpRingCountersIntervalEntry
    ACCESS          not-accessible
    STATUS          mandatory
    DESCRIPTION     
            "Packets and octets statistics collected
             for a particular interval
             for the Physical medium dependent layer of a particular
             side of a particular SRP interface.
             The number of 15-minute intervals is between 1 and 96, 
             identifies the intervals for which the set of
             and statistics is available."
    INDEX           { ifIndex, srpRingIntInterfaceSide, srpRingIntNumber }
    ::= { srpRingCountersIntervalTable 1 }

SrpRingCountersIntervalEntry ::=
    SEQUENCE {
        srpRingIntInterfaceSide         InterfaceSide,
        srpRingIntNumber                INTEGER,
        srpRingIntWrapCounter           Counter
--         srpRingIntUcastLowPriPktsIn     CounterBasedGauge64,
--         srpRingIntUcastLowPriOctetsIn   CounterBasedGauge64,
--         srpRingIntMcastLowPriPktsIn     CounterBasedGauge64,
--         srpRingIntMcastLowPriOctetsIn   CounterBasedGauge64,
--         srpRingIntUcastHighPriPktsIn    CounterBasedGauge64,
--         srpRingIntUcastHighPriOctetsIn  CounterBasedGauge64,
--         srpRingIntMcastHighPriPktsIn    CounterBasedGauge64,
--         srpRingIntMcastHighPriOctetsIn  CounterBasedGauge64,
--         srpRingIntUcastLowPriPktsOut    CounterBasedGauge64,
--         srpRingIntUcastLowPriOctetsOut  CounterBasedGauge64,
--         srpRingIntMcastLowPriPktsOut    CounterBasedGauge64,
--         srpRingIntMcastLowPriOctetsOut  CounterBasedGauge64,
--         srpRingIntUcastHighPriPktsOut   CounterBasedGauge64,
--         srpRingIntUcastHighPriOctetsOut CounterBasedGauge64,
--         srpRingIntMcastHighPriPktsOut   CounterBasedGauge64,
--         srpRingIntMcastHighPriOctetsOut CounterBasedGauge64
    }

srpRingIntInterfaceSide OBJECT-TYPE
    SYNTAX          InterfaceSide
    ACCESS          not-accessible
    STATUS          mandatory
    DESCRIPTION     
            "An indication of the side of the interface for which
             this row contains information."
    ::= { srpRingCountersIntervalEntry 1 }

srpRingIntNumber OBJECT-TYPE
    SYNTAX          INTEGER (1..96)
    ACCESS          not-accessible
    STATUS          mandatory
    DESCRIPTION     
            "A number between 1 and 96, which identifies the
             intervals for which the set of statistics is available.
             The interval identified by 1 is the most recently
             completed 15 minute interval,
             and interval identified by N is the interval
             immediately preceding the one identified by N-1."
    ::= { srpRingCountersIntervalEntry 2 }

srpRingIntWrapCounter OBJECT-TYPE
    SYNTAX          Counter
    ACCESS          read-only
    STATUS          mandatory
    DESCRIPTION     
            "The counter counts the number of
             transition from unwrap to wrap state
             for the last <N> intervals described by
             the srpRingIntNumber variable."
    ::= { srpRingCountersIntervalEntry 3 }

-- srpRingIntUcastLowPriPktsIn OBJECT-TYPE
--     SYNTAX          CounterBasedGauge64
--     ACCESS          read-only
--     STATUS          mandatory
--     DESCRIPTION     
--             "The counter associated with the number of low priority 
--              unicast packets received from the Physical medium dependent 
--              layer in a particular 15-minute interval
--              in the past 24 hours."
--     ::= { srpRingCountersIntervalEntry 4 }

-- srpRingIntUcastLowPriOctetsIn OBJECT-TYPE
--     SYNTAX          CounterBasedGauge64
--     ACCESS          read-only
--     STATUS          mandatory
--     DESCRIPTION     
--             "The counter associated with the number of low priority
--              unicast octets received from the Physical medium dependent
--              layer in a particular 15-minute interval
--              in the past 24 hours."
--     ::= { srpRingCountersIntervalEntry 5 }

-- srpRingIntMcastLowPriPktsIn OBJECT-TYPE
--     SYNTAX          CounterBasedGauge64
--     ACCESS          read-only
--     STATUS          mandatory
--     DESCRIPTION     
--             "The counter associated with the number of low priority
--              multicast packets received from the Physical medium dependent
--              layer in a particular 15-minute interval
--              in the past 24 hours."
--     ::= { srpRingCountersIntervalEntry 6 }

-- srpRingIntMcastLowPriOctetsIn OBJECT-TYPE
--     SYNTAX          CounterBasedGauge64
--     ACCESS          read-only
--     STATUS          mandatory
--     DESCRIPTION     
--             "The counter associated with the number of low priority
--              multicast octets  received from the Physical medium dependent
--              layer in a particular 15-minute interval
--              in the past 24 hours."
--     ::= { srpRingCountersIntervalEntry 7 }

-- srpRingIntUcastHighPriPktsIn OBJECT-TYPE
--     SYNTAX          CounterBasedGauge64
--     ACCESS          read-only
--     STATUS          mandatory
--     DESCRIPTION     
--             "The counter associated with the number of high priority
--              unicast packets received from the Physical medium dependent
--              layer in a particular 15-minute interval
--              in the past 24 hours."
--     ::= { srpRingCountersIntervalEntry 8 }

-- srpRingIntUcastHighPriOctetsIn OBJECT-TYPE
--     SYNTAX          CounterBasedGauge64
--     ACCESS          read-only
--     STATUS          mandatory
--     DESCRIPTION     
--             "The counter associated with the number of high priority
--              unicast octets received from the Physical medium dependent
--              layer in a particular 15-minute interval
--              in the past 24 hours."
--     ::= { srpRingCountersIntervalEntry 9 }

-- srpRingIntMcastHighPriPktsIn OBJECT-TYPE
--     SYNTAX          CounterBasedGauge64
--     ACCESS          read-only
--     STATUS          mandatory
--     DESCRIPTION     
--             "The counter associated with the number of high priority
--              multicast packets received from the Physical medium dependent
--              layer in a particular 15-minute interval
--              in the past 24 hours."
--     ::= { srpRingCountersIntervalEntry 10 }

-- srpRingIntMcastHighPriOctetsIn OBJECT-TYPE
--     SYNTAX          CounterBasedGauge64
--     ACCESS          read-only
--     STATUS          mandatory
--     DESCRIPTION     
--             "The counter associated with the number of high priority
--              multicast octets received from the Physical medium dependent
--              layer in a particular 15-minute interval
--              in the past 24 hours."
--     ::= { srpRingCountersIntervalEntry 11 }

-- srpRingIntUcastLowPriPktsOut OBJECT-TYPE
--     SYNTAX          CounterBasedGauge64
--     ACCESS          read-only
--     STATUS          mandatory
--     DESCRIPTION     
--             "The counter associated with the number of low priority
--              unicast packets going to the Physical medium dependent layer
--              in a particular 15-minute interval in the past 24 hours."
--     ::= { srpRingCountersIntervalEntry 12 }

-- srpRingIntUcastLowPriOctetsOut OBJECT-TYPE
--     SYNTAX          CounterBasedGauge64
--     ACCESS          read-only
--     STATUS          mandatory
--     DESCRIPTION     
--             "The counter associated with the number of low priority 
--              unicast octets going to the Physical medium dependent layer
--              in a particular 15-minute interval in the past 24 hours."
--     ::= { srpRingCountersIntervalEntry 13 }

-- srpRingIntMcastLowPriPktsOut OBJECT-TYPE
--     SYNTAX          CounterBasedGauge64
--     ACCESS          read-only
--     STATUS          mandatory
--     DESCRIPTION     
--             "The counter associated with the number of low priority 
--              multicast packets going to the Physical medium dependent layer
--              in a particular 15-minute interval in the past 24 hours."
--     ::= { srpRingCountersIntervalEntry 14 }

-- srpRingIntMcastLowPriOctetsOut OBJECT-TYPE
--     SYNTAX          CounterBasedGauge64
--     ACCESS          read-only
--     STATUS          mandatory
--     DESCRIPTION     
--             "The counter associated with the number of low priority 
--              multicast octets going to the Physical medium dependent layer
--              in a particular 15-minute interval in the past 24 hours."
--     ::= { srpRingCountersIntervalEntry 15 }

-- srpRingIntUcastHighPriPktsOut OBJECT-TYPE
--     SYNTAX          CounterBasedGauge64
--     ACCESS          read-only
--     STATUS          mandatory
--     DESCRIPTION     
--             "The counter associated with the number of high priority 
--              unicast packets going to the Physical medium dependent layer
--              in a particular 15-minute interval in the past 24 hours."
--     ::= { srpRingCountersIntervalEntry 16 }

-- srpRingIntUcastHighPriOctetsOut OBJECT-TYPE
--     SYNTAX          CounterBasedGauge64
--     ACCESS          read-only
--     STATUS          mandatory
--     DESCRIPTION     
--             "The counter associated with the number of high priority 
--              unicast octets going to the Physical medium dependent layer
--              in a particular 15-minute interval in the past 24 hours."
--     ::= { srpRingCountersIntervalEntry 17 }

-- srpRingIntMcastHighPriPktsOut OBJECT-TYPE
--     SYNTAX          CounterBasedGauge64
--     ACCESS          read-only
--     STATUS          mandatory
--     DESCRIPTION     
--             "The counter associated with the number of high priority
--              multicast packets going to the Physical medium dependent layer
--              in a particular 15-minute interval in the past 24 hours."
--     ::= { srpRingCountersIntervalEntry 18 }

-- srpRingIntMcastHighPriOctetsOut OBJECT-TYPE
--     SYNTAX          CounterBasedGauge64
--     ACCESS          read-only
--     STATUS          mandatory
--     DESCRIPTION     
--             "The counter associated with the number of high priority
--              multicast octets going to the Physical medium dependent layer
--              in a particular 15-minute interval in the past 24 hours."
--     ::= { srpRingCountersIntervalEntry 19 }

srpHostCounters OBJECT IDENTIFIER
    ::= { ciscosrpMIB 3 }

srpHostCountersCurrentTable OBJECT-TYPE
    SYNTAX          SEQUENCE OF SrpHostCountersCurrentEntry
    ACCESS          not-accessible
    STATUS          mandatory
    DESCRIPTION     
            "The Higher Layer Current counters table."
    ::= { srpHostCounters 1 }

srpHostCountersCurrentEntry OBJECT-TYPE
    SYNTAX          SrpHostCountersCurrentEntry
    ACCESS          not-accessible
    STATUS          mandatory
    DESCRIPTION     
            "Packets and octets statistics for the current interval
             for the Higher Layer of a particular
             side of a particular SRP interface. The corresponding
             instance of srpIfTimeElapsed indicates the number
             of seconds which have elapsed so far
             in the current interval."
    INDEX           { ifIndex, srpHostInterfaceSide }
    ::= { srpHostCountersCurrentTable 1 }

SrpHostCountersCurrentEntry ::=
    SEQUENCE {
        srpHostInterfaceSide            InterfaceSide
--         srpHostCurUcastLowPriPktsIn     CounterBasedGauge64,
--         srpHostCurUcastLowPriOctetsIn   CounterBasedGauge64,
--         srpHostCurMcastLowPriPktsIn     CounterBasedGauge64,
--         srpHostCurMcastLowPriOctetsIn   CounterBasedGauge64,
--         srpHostCurUcastHighPriPktsIn    CounterBasedGauge64,
--         srpHostCurUcastHighPriOctetsIn  CounterBasedGauge64,
--         srpHostCurMcastHighPriPktsIn    CounterBasedGauge64,
--         srpHostCurMcastHighPriOctetsIn  CounterBasedGauge64,
--         srpHostCurUcastLowPriPktsOut    CounterBasedGauge64,
--         srpHostCurUcastLowPriOctetsOut  CounterBasedGauge64,
--         srpHostCurMcastLowPriPktsOut    CounterBasedGauge64,
--         srpHostCurMcastLowPriOctetsOut  CounterBasedGauge64,
--         srpHostCurUcastHighPriPktsOut   CounterBasedGauge64,
--         srpHostCurUcastHighPriOctetsOut CounterBasedGauge64,
--         srpHostCurMcastHighPriPktsOut   CounterBasedGauge64,
--         srpHostCurMcastHighPriOctetsOut CounterBasedGauge64
    }

srpHostInterfaceSide OBJECT-TYPE
    SYNTAX          InterfaceSide
    ACCESS          not-accessible
    STATUS          mandatory
    DESCRIPTION     
            "An indication of the side of the interface for which
             this row contains information."
    ::= { srpHostCountersCurrentEntry 1 }

-- srpHostCurUcastLowPriPktsIn OBJECT-TYPE
--     SYNTAX          CounterBasedGauge64
--     ACCESS          read-only
--     STATUS          mandatory
--     DESCRIPTION     
--             "The counter associated with the number of total
--              unicast packets received from the Higher Layer
--              in the current 15 minute interval."
--     ::= { srpHostCountersCurrentEntry 2 }

-- srpHostCurUcastLowPriOctetsIn OBJECT-TYPE
--     SYNTAX          CounterBasedGauge64
--     ACCESS          read-only
--     STATUS          mandatory
--     DESCRIPTION     
--             "The counter associated with the number of total
--              unicast octets received from the Higher Layer
--              in the current 15 minute interval."
--     ::= { srpHostCountersCurrentEntry 3 }

-- srpHostCurMcastLowPriPktsIn OBJECT-TYPE
--     SYNTAX          CounterBasedGauge64
--     ACCESS          read-only
--     STATUS          mandatory
--     DESCRIPTION     
--             "The counter associated with the number of total
--              multicast packets received from the Higher Layer
--              in the current 15 minute interval."
--     ::= { srpHostCountersCurrentEntry 4 }

-- srpHostCurMcastLowPriOctetsIn OBJECT-TYPE
--     SYNTAX          CounterBasedGauge64
--     ACCESS          read-only
--     STATUS          mandatory
--     DESCRIPTION     
--             "The counter associated with the number of total
--              multicast octets received from the Higher Layer
--              in the current 15 minute interval."
--     ::= { srpHostCountersCurrentEntry 5 }

-- srpHostCurUcastHighPriPktsIn OBJECT-TYPE
--     SYNTAX          CounterBasedGauge64
--     ACCESS          read-only
--     STATUS          mandatory
--     DESCRIPTION     
--             "The counter associated with the number of high priority
--              unicast packets received from the Higher Layer
--              in the current 15 minute interval."
--     ::= { srpHostCountersCurrentEntry 6 }

-- srpHostCurUcastHighPriOctetsIn OBJECT-TYPE
--     SYNTAX          CounterBasedGauge64
--     ACCESS          read-only
--     STATUS          mandatory
--     DESCRIPTION     
--             "The counter associated with the number of high priority
--              unicast octets received from the Higher Layer
--              in the current 15 minute interval."
--     ::= { srpHostCountersCurrentEntry 7 }

-- srpHostCurMcastHighPriPktsIn OBJECT-TYPE
--     SYNTAX          CounterBasedGauge64
--     ACCESS          read-only
--     STATUS          mandatory
--     DESCRIPTION     
--             "The counter associated with the number of high priority
--              multicast packets received from the Higher Layer
--              in the current 15 minute interval."
--     ::= { srpHostCountersCurrentEntry 8 }

-- srpHostCurMcastHighPriOctetsIn OBJECT-TYPE
--     SYNTAX          CounterBasedGauge64
--     ACCESS          read-only
--     STATUS          mandatory
--     DESCRIPTION     
--             "The counter associated with the number of high priority
--              multicast octets received from the Higher Layer
--              in the current 15 minute interval."
--     ::= { srpHostCountersCurrentEntry 9 }

-- srpHostCurUcastLowPriPktsOut OBJECT-TYPE
--     SYNTAX          CounterBasedGauge64
--     ACCESS          read-only
--     STATUS          mandatory
--     DESCRIPTION     
--             "The counter associated with the number of total
--              unicast packets going to the Higher Layer
--              in the current 15 minute interval."
--     ::= { srpHostCountersCurrentEntry 10 }

-- srpHostCurUcastLowPriOctetsOut OBJECT-TYPE
--     SYNTAX          CounterBasedGauge64
--     ACCESS          read-only
--     STATUS          mandatory
--     DESCRIPTION     
--             "The counter associated with the number of total
--              unicast octets going to the Higher Layer
--              in the current 15 minute interval."
--     ::= { srpHostCountersCurrentEntry 11 }

-- srpHostCurMcastLowPriPktsOut OBJECT-TYPE
--     SYNTAX          CounterBasedGauge64
--     ACCESS          read-only
--     STATUS          mandatory
--     DESCRIPTION     
--             "The counter associated with the number of total
--              multicast packets going to the Higher Layer
--              in the current 15 minute interval."
--     ::= { srpHostCountersCurrentEntry 12 }

-- srpHostCurMcastLowPriOctetsOut OBJECT-TYPE
--     SYNTAX          CounterBasedGauge64
--     ACCESS          read-only
--     STATUS          mandatory
--     DESCRIPTION     
--             "The counter associated with the number of total
--              multicast octets going to the Higher Layer
--              in the current 15 minute interval."
--     ::= { srpHostCountersCurrentEntry 13 }

-- srpHostCurUcastHighPriPktsOut OBJECT-TYPE
--     SYNTAX          CounterBasedGauge64
--     ACCESS          read-only
--     STATUS          mandatory
--     DESCRIPTION     
--             "The counter associated with the number of high priority
--              unicast packets going to the Higher Layer
--              in the current 15 minute interval."
--     ::= { srpHostCountersCurrentEntry 14 }

-- srpHostCurUcastHighPriOctetsOut OBJECT-TYPE
--     SYNTAX          CounterBasedGauge64
--     ACCESS          read-only
--     STATUS          mandatory
--     DESCRIPTION     
--             "The counter associated with the number of high priority
--              unicast octets going to from the Higher Layer
--              in the current 15 minute interval."
--     ::= { srpHostCountersCurrentEntry 15 }

-- srpHostCurMcastHighPriPktsOut OBJECT-TYPE
--     SYNTAX          CounterBasedGauge64
--     ACCESS          read-only
--     STATUS          mandatory
--     DESCRIPTION     
--             "The counter associated with the number of high priority
--              multicast packets going to the Higher Layer
--              in the current 15 minute interval."
--     ::= { srpHostCountersCurrentEntry 16 }

-- srpHostCurMcastHighPriOctetsOut OBJECT-TYPE
--     SYNTAX          CounterBasedGauge64
--     ACCESS          read-only
--     STATUS          mandatory
--     DESCRIPTION     
--             "The counter associated with the number of high priority
--              multicast octets going to the Higher Layer
--              in the current 15 minute interval."
--     ::= { srpHostCountersCurrentEntry 17 }

srpHostCountersIntervalTable OBJECT-TYPE
    SYNTAX          SEQUENCE OF SrpHostCountersIntervalEntry
    ACCESS          not-accessible
    STATUS          mandatory
    DESCRIPTION     
            "The Higher Layer Interval counters table."
    ::= { srpHostCounters 2 }

srpHostCountersIntervalEntry OBJECT-TYPE
    SYNTAX          SrpHostCountersIntervalEntry
    ACCESS          not-accessible
    STATUS          mandatory
    DESCRIPTION     
            "Packets and octets statistics collected for a
             particular interval for the Higher Layer
             of a particular side of a particular SRP interface.
             The number of 15-minute intervals is between 1 and 96, and
             identifies the intervals for which the set of
             statistics is available."
    INDEX           { ifIndex, srpHostIntInterfaceSide, srpHostIntNumber }
    ::= { srpHostCountersIntervalTable 1 }

SrpHostCountersIntervalEntry ::=
    SEQUENCE {
        srpHostIntInterfaceSide         InterfaceSide,
        srpHostIntNumber                INTEGER
--         srpHostIntUcastLowPriPktsIn     CounterBasedGauge64,
--         srpHostIntUcastLowPriOctetsIn   CounterBasedGauge64,
--         srpHostIntMcastLowPriPktsIn     CounterBasedGauge64,
--         srpHostIntMcastLowPriOctetsIn   CounterBasedGauge64,
--         srpHostIntUcastHighPriPktsIn    CounterBasedGauge64,
--         srpHostIntUcastHighPriOctetsIn  CounterBasedGauge64,
--         srpHostIntMcastHighPriPktsIn    CounterBasedGauge64,
--         srpHostIntMcastHighPriOctetsIn  CounterBasedGauge64,
--         srpHostIntUcastLowPriPktsOut    CounterBasedGauge64,
--         srpHostIntUcastLowPriOctetsOut  CounterBasedGauge64,
--         srpHostIntMcastLowPriPktsOut    CounterBasedGauge64,
--         srpHostIntMcastLowPriOctetsOut  CounterBasedGauge64,
--         srpHostIntUcastHighPriPktsOut   CounterBasedGauge64,
--         srpHostIntUcastHighPriOctetsOut CounterBasedGauge64,
--         srpHostIntMcastHighPriPktsOut   CounterBasedGauge64,
--         srpHostIntMcastHighPriOctetsOut CounterBasedGauge64
    }

srpHostIntInterfaceSide OBJECT-TYPE
    SYNTAX          InterfaceSide
    ACCESS          not-accessible
    STATUS          mandatory
    DESCRIPTION     
            "An indication of the side of the interface for which
             this row contains information."
    ::= { srpHostCountersIntervalEntry 1 }

srpHostIntNumber OBJECT-TYPE
    SYNTAX          INTEGER (1..96)
    ACCESS          not-accessible
    STATUS          mandatory
    DESCRIPTION     
            "A number between 1 and 96, which identifies the
             interval for which the set od statistics is available.
             The interval identified by 1 is the most recently
             completed 15 minute interval,
             and interval identified by N is the interval
             immediately preceding the one identified by N-1."
    ::= { srpHostCountersIntervalEntry 2 }

-- srpHostIntUcastLowPriPktsIn OBJECT-TYPE
--     SYNTAX          CounterBasedGauge64
--     ACCESS          read-only
--     STATUS          mandatory
--     DESCRIPTION     
--             "The counter associated with the number of total
--              unicast packets received from the Higher Layer
--              in a particular 15-minute interval in the past 24 hours."
--     ::= { srpHostCountersIntervalEntry 3 }

-- srpHostIntUcastLowPriOctetsIn OBJECT-TYPE
--     SYNTAX          CounterBasedGauge64
--     ACCESS          read-only
--     STATUS          mandatory
--     DESCRIPTION     
--             "The counter associated with the number of total
--              unicast octets received from the Higher Layer
--              in a particular 15-minute interval in the past 24 hours."
--     ::= { srpHostCountersIntervalEntry 4 }

-- srpHostIntMcastLowPriPktsIn OBJECT-TYPE
--     SYNTAX          CounterBasedGauge64
--     ACCESS          read-only
--     STATUS          mandatory
--     DESCRIPTION     
--             "The counter associated with the number of total
--              multicast packets received from the Higher Layer
--              in a particular 15-minute interval in the past 24 hours."
--     ::= { srpHostCountersIntervalEntry 5 }

-- srpHostIntMcastLowPriOctetsIn OBJECT-TYPE
--     SYNTAX          CounterBasedGauge64
--     ACCESS          read-only
--     STATUS          mandatory
--     DESCRIPTION     
--             "The counter associated with the number of total
--              multicast octets received from the Higher Layer
--              in a particular 15-minute interval in the past 24 hours."
--     ::= { srpHostCountersIntervalEntry 6 }

-- srpHostIntUcastHighPriPktsIn OBJECT-TYPE
--     SYNTAX          CounterBasedGauge64
--     ACCESS          read-only
--     STATUS          mandatory
--     DESCRIPTION     
--             "The counter associated with the number of high priority
--              unicast packets received from the Higher Layer
--              in a particular 15-minute interval in the past 24 hours."
--     ::= { srpHostCountersIntervalEntry 7 }

-- srpHostIntUcastHighPriOctetsIn OBJECT-TYPE
--     SYNTAX          CounterBasedGauge64
--     ACCESS          read-only
--     STATUS          mandatory
--     DESCRIPTION     
--             "The counter associated with the number of high priority
--              unicast octets received from from the Higher Layer
--              in a particular 15-minute interval in the past 24 hours."
--     ::= { srpHostCountersIntervalEntry 8 }

-- srpHostIntMcastHighPriPktsIn OBJECT-TYPE
--     SYNTAX          CounterBasedGauge64
--     ACCESS          read-only
--     STATUS          mandatory
--     DESCRIPTION     
--             "The counter associated with the number of high priority
--              multicast packets received from the Higher Layer
--              in a particular 15-minute interval in the past 24 hours."
--     ::= { srpHostCountersIntervalEntry 9 }

-- srpHostIntMcastHighPriOctetsIn OBJECT-TYPE
--     SYNTAX          CounterBasedGauge64
--     ACCESS          read-only
--     STATUS          mandatory
--     DESCRIPTION     
--             "The counter associated with the number of high priority
--              multicast octets received from the Higher Layer
--              in a particular 15-minute interval in the past 24 hours."
--     ::= { srpHostCountersIntervalEntry 10 }

-- srpHostIntUcastLowPriPktsOut OBJECT-TYPE
--     SYNTAX          CounterBasedGauge64
--     ACCESS          read-only
--     STATUS          mandatory
--     DESCRIPTION     
--             "The counter associated with the number of total
--              unicast packets going to the Higher Layer
--              in a particular 15-minute interval in the past 24 hours."
--     ::= { srpHostCountersIntervalEntry 11 }

-- srpHostIntUcastLowPriOctetsOut OBJECT-TYPE
--     SYNTAX          CounterBasedGauge64
--     ACCESS          read-only
--     STATUS          mandatory
--     DESCRIPTION     
--             "The counter associated with the number of total
--              unicast octets going to the Higher Layer
--              in a particular 15-minute interval in the past 24 hours."
--     ::= { srpHostCountersIntervalEntry 12 }

-- srpHostIntMcastLowPriPktsOut OBJECT-TYPE
--     SYNTAX          CounterBasedGauge64
--     ACCESS          read-only
--     STATUS          mandatory
--     DESCRIPTION     
--             "The counter associated with the number of total
--              multicast packets going to the Higher Layer
--              in a particular 15-minute interval in the past 24 hours."
--     ::= { srpHostCountersIntervalEntry 13 }

-- srpHostIntMcastLowPriOctetsOut OBJECT-TYPE
--     SYNTAX          CounterBasedGauge64
--     ACCESS          read-only
--     STATUS          mandatory
--     DESCRIPTION     
--             "The counter associated with the number of total
--              multicast octets going to the Higher Layer
--              in a particular 15-minute interval in the past 24 hours."
--     ::= { srpHostCountersIntervalEntry 14 }

-- srpHostIntUcastHighPriPktsOut OBJECT-TYPE
--     SYNTAX          CounterBasedGauge64
--     ACCESS          read-only
--     STATUS          mandatory
--     DESCRIPTION     
--             "The counter associated with the number of high priority
--              unicast packets going to the Higher Layer
--              in a particular 15-minute interval in the past 24 hours."
--     ::= { srpHostCountersIntervalEntry 15 }

-- srpHostIntUcastHighPriOctetsOut OBJECT-TYPE
--     SYNTAX          CounterBasedGauge64
--     ACCESS          read-only
--     STATUS          mandatory
--     DESCRIPTION     
--             "The counter associated with the number of high priority
--              unicast octets going to the Higher Layer
--              in a particular 15-minute interval in the past 24 hours."
--     ::= { srpHostCountersIntervalEntry 16 }

-- srpHostIntMcastHighPriPktsOut OBJECT-TYPE
--     SYNTAX          CounterBasedGauge64
--     ACCESS          read-only
--     STATUS          mandatory
--     DESCRIPTION     
--             "The counter associated with the number of high priority
--              multicast packets going to the Higher Layer
--              in a particular 15-minute interval in the past 24 hours."
--     ::= { srpHostCountersIntervalEntry 17 }

-- srpHostIntMcastHighPriOctetsOut OBJECT-TYPE
--     SYNTAX          CounterBasedGauge64
--     ACCESS          read-only
--     STATUS          mandatory
--     DESCRIPTION     
--             "The counter associated with the number of high priority
--              multicast octets going to the Higher Layer
--              in a particular 15-minute interval in the past 24 hours."
--     ::= { srpHostCountersIntervalEntry 18 }

srpErrorsCounters OBJECT IDENTIFIER
    ::= { ciscosrpMIB 4 }

srpErrorsCountersCurrentTable OBJECT-TYPE
    SYNTAX          SEQUENCE OF SrpErrorsCountersCurrentEntry
    ACCESS          not-accessible
    STATUS          deprecated
    DESCRIPTION     
            "The SRP Errors Current counters table."
    ::= { srpErrorsCounters 1 }

srpErrorsCountersCurrentEntry OBJECT-TYPE
    SYNTAX          SrpErrorsCountersCurrentEntry
    ACCESS          not-accessible
    STATUS          deprecated
    DESCRIPTION     
            "Errors statistics for the current interval
             of a particular side of a particular SRP interface.
             The corresponding instance of srpIfTimeElapsed
             indicates the number of seconds which have
             elapsed so far in the current interval."
    INDEX           { ifIndex, srpErrorsInterfaceSide }
    ::= { srpErrorsCountersCurrentTable 1 }

SrpErrorsCountersCurrentEntry ::=
    SEQUENCE {
        srpErrorsInterfaceSide          InterfaceSide
--         srpRingCurRxErrorsDataParity    CounterBasedGauge64,
--         srpRingCurRxErrorsShortPackets  CounterBasedGauge64,
--         srpRingCurRxErrorsGiantPackets  CounterBasedGauge64,
--         srpRingCurRxErrorsSideBadPackets CounterBasedGauge64,
--         srpRingCurRxErrorsCRC           CounterBasedGauge64,
--         srpHostCurRxErrorsDataParity    CounterBasedGauge64,
--         srpHostCurRxErrorsShortPackets  CounterBasedGauge64,
--         srpHostCurRxErrorsGiantPackets  CounterBasedGauge64,
--         srpHostCurRxErrorsSideBadPackets CounterBasedGauge64
    }

srpErrorsInterfaceSide OBJECT-TYPE
    SYNTAX          InterfaceSide
    ACCESS          not-accessible
    STATUS          deprecated
    DESCRIPTION     
            "An indication of the side of the interface for which
             this row contains information."
    ::= { srpErrorsCountersCurrentEntry 1 }

-- srpRingCurRxErrorsDataParity OBJECT-TYPE
--     SYNTAX          CounterBasedGauge64
--     ACCESS          read-only
--     STATUS          deprecated
--     DESCRIPTION     
--             "The counter associated with the  
--              number of data parity errors,
--              received from the Physical medium dependent layer 
--              in the current 15 minute interval."
--     ::= { srpErrorsCountersCurrentEntry 2 }

-- srpRingCurRxErrorsShortPackets OBJECT-TYPE
--     SYNTAX          CounterBasedGauge64
--     ACCESS          read-only
--     STATUS          deprecated
--     DESCRIPTION     
--             "The counter associated with the  
--              number of short packets,
--              received from the Physical medium dependent layer
--              in the current 15 minute interval.
--              A short packet is 16 octets or less."
--     ::= { srpErrorsCountersCurrentEntry 3 }

-- srpRingCurRxErrorsGiantPackets OBJECT-TYPE
--     SYNTAX          CounterBasedGauge64
--     ACCESS          read-only
--     STATUS          deprecated
--     DESCRIPTION     
--             "The counter associated with the  
--              number of giant packets,
--              received from the Physical medium dependent layer
--              in the current 15 minute interval.
--              A giant packet is larger than max size MTU,
--              which is 9216 octets."
--     ::= { srpErrorsCountersCurrentEntry 4 }

-- srpRingCurRxErrorsSideBadPackets OBJECT-TYPE
--     SYNTAX          CounterBasedGauge64
--     ACCESS          read-only
--     STATUS          deprecated
--     DESCRIPTION     
--             "The counter associated with the current 
--              number of bad packets,
--              received from the Physical medium dependent layer
--              in the current 15 minute interval.
--              A bad packet is an empty packet with a valid
--              Start-Of-Packet signal causing an incorrect CRC."
--     ::= { srpErrorsCountersCurrentEntry 5 }

-- srpRingCurRxErrorsCRC OBJECT-TYPE
--     SYNTAX          CounterBasedGauge64
--     ACCESS          read-only
--     STATUS          deprecated
--     DESCRIPTION     
--             "The counter associated with the current 
--              number of packets with CRC errors,
--              received from the Physical medium dependent layer
--              in the current 15 minute interval."
--     ::= { srpErrorsCountersCurrentEntry 6 }

-- srpHostCurRxErrorsDataParity OBJECT-TYPE
--     SYNTAX          CounterBasedGauge64
--     ACCESS          read-only
--     STATUS          deprecated
--     DESCRIPTION     
--             "The counter associated with the current 
--              number of data parity errors, 
--              received from the Higher Layer
--              in the current 15 minute interval."
--     ::= { srpErrorsCountersCurrentEntry 7 }

-- srpHostCurRxErrorsShortPackets OBJECT-TYPE
--     SYNTAX          CounterBasedGauge64
--     ACCESS          read-only
--     STATUS          deprecated
--     DESCRIPTION     
--             "The counter associated with the current 
--              number of short packets, 
--              received from the Higher Layer
--              in the current 15 minute interval."
--     ::= { srpErrorsCountersCurrentEntry 8 }

-- srpHostCurRxErrorsGiantPackets OBJECT-TYPE
--     SYNTAX          CounterBasedGauge64
--     ACCESS          read-only
--     STATUS          deprecated
--     DESCRIPTION     
--             "The counter associated with the current 
--              number of giant packets, 
--              received from the Higher Layer
--              in the current 15 minute interval."
--     ::= { srpErrorsCountersCurrentEntry 9 }

-- srpHostCurRxErrorsSideBadPackets OBJECT-TYPE
--     SYNTAX          CounterBasedGauge64
--     ACCESS          read-only
--     STATUS          deprecated
--     DESCRIPTION     
--             "The counter associated with the current 
--              number of bad packets, 
--              received from the Higher Layer
--              in the current 15 minute interval."
--     ::= { srpErrorsCountersCurrentEntry 10 }

srpErrorsCountersIntervalTable OBJECT-TYPE
    SYNTAX          SEQUENCE OF SrpErrorsCountersIntervalEntry
    ACCESS          not-accessible
    STATUS          deprecated
    DESCRIPTION     
            "The SRP Errors Interval counters table."
    ::= { srpErrorsCounters 2 }

srpErrorsCountersIntervalEntry OBJECT-TYPE
    SYNTAX          SrpErrorsCountersIntervalEntry
    ACCESS          not-accessible
    STATUS          deprecated
    DESCRIPTION     
            "Error statistics collected for a particular interval
             of a particular side of a particular SRP interface.
             The number of 15-minute intervals is between 1 and 96, and
             identifies the intervals for which the set of
             statistics is available."
    INDEX           { ifIndex, srpErrorsIntervalInterfaceSide, 
                      srpErrorsIntervalNumber }
    ::= { srpErrorsCountersIntervalTable 1 }

SrpErrorsCountersIntervalEntry ::=
    SEQUENCE {
        srpErrorsIntervalInterfaceSide  InterfaceSide,
        srpErrorsIntervalNumber         INTEGER
--         srpRingIntRxErrorsDataParity    CounterBasedGauge64,
--         srpRingIntRxErrorsShortPackets  CounterBasedGauge64,
--         srpRingIntRxErrorsGiantPackets  CounterBasedGauge64,
--         srpRingIntRxErrorsSideBadPackets CounterBasedGauge64,
--         srpRingIntRxErrorsCRC           CounterBasedGauge64,
--         srpHostIntRxErrorsDataParity    CounterBasedGauge64,
--         srpHostIntRxErrorsShortPackets  CounterBasedGauge64,
--         srpHostIntRxErrorsGiantPackets  CounterBasedGauge64,
--         srpHostIntRxErrorsSideBadPackets CounterBasedGauge64
    }

srpErrorsIntervalInterfaceSide OBJECT-TYPE
    SYNTAX          InterfaceSide
    ACCESS          not-accessible
    STATUS          deprecated
    DESCRIPTION     
            "An indication of the side of the interface for which
             this row contains information."
    ::= { srpErrorsCountersIntervalEntry 1 }

srpErrorsIntervalNumber OBJECT-TYPE
    SYNTAX          INTEGER (1..96)
    ACCESS          not-accessible
    STATUS          deprecated
    DESCRIPTION     
            "A number between 1 and 96, which identifies the
             interval for which the set od statistics is available.
             The interval identified by 1 is the most recently
             completed 15 minute interval,
             and interval identified by N is the interval
             immediately preceding the one identified by N-1."
    ::= { srpErrorsCountersIntervalEntry 2 }

-- srpRingIntRxErrorsDataParity OBJECT-TYPE
--     SYNTAX          CounterBasedGauge64
--     ACCESS          read-only
--     STATUS          deprecated
--     DESCRIPTION     
--             "The counter associated with the interval 
--              number of data parity errors,
--              received from the Layer 1 Physical medium 
--              in a particular 15-minute interval in the past 24 hours."
--     ::= { srpErrorsCountersIntervalEntry 3 }

-- srpRingIntRxErrorsShortPackets OBJECT-TYPE
--     SYNTAX          CounterBasedGauge64
--     ACCESS          read-only
--     STATUS          deprecated
--     DESCRIPTION     
--             "The counter associated with the interval 
--              number of short packets,
--              received from the Layer 1 Physical medium
--              in a particular 15-minute interval in the past 24 hours."
--     ::= { srpErrorsCountersIntervalEntry 4 }

-- srpRingIntRxErrorsGiantPackets OBJECT-TYPE
--     SYNTAX          CounterBasedGauge64
--     ACCESS          read-only
--     STATUS          deprecated
--     DESCRIPTION     
--             "The counter associated with the interval 
--              number of giant packets,
--              received from the Layer 1 Physical medium
--              in a particular 15-minute interval in the past 24 hours."
--     ::= { srpErrorsCountersIntervalEntry 5 }

-- srpRingIntRxErrorsSideBadPackets OBJECT-TYPE
--     SYNTAX          CounterBasedGauge64
--     ACCESS          read-only
--     STATUS          deprecated
--     DESCRIPTION     
--             "The counter associated with the interval 
--              number of bad packets,
--              received from the Layer 1 Physical medium
--              in a particular 15-minute interval in the past 24 hours."
--     ::= { srpErrorsCountersIntervalEntry 6 }

-- srpRingIntRxErrorsCRC OBJECT-TYPE
--     SYNTAX          CounterBasedGauge64
--     ACCESS          read-only
--     STATUS          deprecated
--     DESCRIPTION     
--             "The counter associated with the interval 
--              number of packets with CRC errors,
--              received from the Layer 1 Physical medium
--              in a particular 15-minute interval in the past 24 hours."
--     ::= { srpErrorsCountersIntervalEntry 7 }

-- srpHostIntRxErrorsDataParity OBJECT-TYPE
--     SYNTAX          CounterBasedGauge64
--     ACCESS          read-only
--     STATUS          deprecated
--     DESCRIPTION     
--             "The counter associated with the interval 
--              number of data parity errors, 
--              received from the higher layer 
--              in a particular 15-minute interval in the past 24 hours."
--     ::= { srpErrorsCountersIntervalEntry 8 }

-- srpHostIntRxErrorsShortPackets OBJECT-TYPE
--     SYNTAX          CounterBasedGauge64
--     ACCESS          read-only
--     STATUS          deprecated
--     DESCRIPTION     
--             "The counter associated with the interval 
--              number of short packets, 
--              received from the higher layer 
--              in a particular 15-minute interval in the past 24 hours."
--     ::= { srpErrorsCountersIntervalEntry 9 }

-- srpHostIntRxErrorsGiantPackets OBJECT-TYPE
--     SYNTAX          CounterBasedGauge64
--     ACCESS          read-only
--     STATUS          deprecated
--     DESCRIPTION     
--             "The counter associated with the interval 
--              number of giant packets, 
--              received from the higher layer 
--              in a particular 15-minute interval in the past 24 hours."
--     ::= { srpErrorsCountersIntervalEntry 10 }

-- srpHostIntRxErrorsSideBadPackets OBJECT-TYPE
--     SYNTAX          CounterBasedGauge64
--     ACCESS          read-only
--     STATUS          deprecated
--     DESCRIPTION     
--             "The counter associated with the interval 
--              number of bad packets, 
--              received from the higher layer 
--              in a particular 15-minute interval in the past 24 hours."
--     ::= { srpErrorsCountersIntervalEntry 11 }

srpErrCntCurrTable OBJECT-TYPE
    SYNTAX          SEQUENCE OF SrpErrCntCurrEntry
    ACCESS          not-accessible
    STATUS          mandatory
    DESCRIPTION     
            "The SRP Errors Current counters table."
    ::= { srpErrorsCounters 3 }

srpErrCntCurrEntry OBJECT-TYPE
    SYNTAX          SrpErrCntCurrEntry
    ACCESS          not-accessible
    STATUS          mandatory
    DESCRIPTION     
            "Errors statistics for the current interval
             of a particular side of a particular SRP interface.
             The corresponding instance of srpIfTimeElapsed
             indicates the number of seconds which have
             elapsed so far in the current interval."
    INDEX           { ifIndex, srpErrCntCurrInterfaceSide }
    ::= { srpErrCntCurrTable 1 }

SrpErrCntCurrEntry ::=
    SEQUENCE {
        srpErrCntCurrInterfaceSide      InterfaceSide
--         srpErrCntCurrRingRxTtlExpPkts   PerfCurrentCount64,
--         srpErrCntCurrRingRxShortPkts    PerfCurrentCount64,
--         srpErrCntCurrRingRxGiantPkts    PerfCurrentCount64,
--         srpErrCntCurrRingRxAbortPkts    PerfCurrentCount64,
--         srpErrCntCurrRingRxCRC          PerfCurrentCount64,
--         srpErrCntCurrHostRxDiscardPkts  PerfCurrentCount64,
--         srpErrCntCurrHostRxShortPkts    PerfCurrentCount64,
--         srpErrCntCurrHostRxGiantPkts    PerfCurrentCount64
    }

srpErrCntCurrInterfaceSide OBJECT-TYPE
    SYNTAX          InterfaceSide
    ACCESS          not-accessible
    STATUS          mandatory
    DESCRIPTION     
            "An indication of the side of the interface for which
             this row contains information."
    ::= { srpErrCntCurrEntry 1 }

-- srpErrCntCurrRingRxTtlExpPkts OBJECT-TYPE
--     SYNTAX          PerfCurrentCount64
--     ACCESS          read-only
--     STATUS          mandatory
--     DESCRIPTION     
--             "The counter associated with the
--              number of packets discarded due to TTL expiry,
--              received from the Physical medium dependent layer
--              in the current 15 minute interval."
--     ::= { srpErrCntCurrEntry 2 }

-- srpErrCntCurrRingRxShortPkts OBJECT-TYPE
--     SYNTAX          PerfCurrentCount64
--     ACCESS          read-only
--     STATUS          mandatory
--     DESCRIPTION     
--             "The counter associated with the
--              number of short packets,
--              received from the Physical medium dependent layer
--              in the current 15 minute interval.
--              A short packet is 16 octets or less."
--     ::= { srpErrCntCurrEntry 3 }

-- srpErrCntCurrRingRxGiantPkts OBJECT-TYPE
--     SYNTAX          PerfCurrentCount64
--     ACCESS          read-only
--     STATUS          mandatory
--     DESCRIPTION     
--             "The counter associated with the
--              number of giant packets,
--              received from the Physical medium dependent layer
--              in the current 15 minute interval.
--              A giant packet is larger than max size packet,
--              which is 9216 octets."
--     ::= { srpErrCntCurrEntry 4 }

-- srpErrCntCurrRingRxAbortPkts OBJECT-TYPE
--     SYNTAX          PerfCurrentCount64
--     ACCESS          read-only
--     STATUS          mandatory
--     DESCRIPTION     
--             "The counter associated with the current
--              number of aborted packets,
--              received from the Physical medium dependent layer
--              in the current 15 minute interval.
--              Aborted packets are packets that have
--              been aborted by an abort sequence code."
--     ::= { srpErrCntCurrEntry 5 }

-- srpErrCntCurrRingRxCRC OBJECT-TYPE
--     SYNTAX          PerfCurrentCount64
--     ACCESS          read-only
--     STATUS          mandatory
--     DESCRIPTION     
--             "The counter associated with the current
--              number of packets with CRC errors,
--              received from the Physical medium dependent layer
--              in the current 15 minute interval."
--     ::= { srpErrCntCurrEntry 6 }

-- srpErrCntCurrHostRxDiscardPkts OBJECT-TYPE
--     SYNTAX          PerfCurrentCount64
--     ACCESS          read-only
--     STATUS          mandatory
--     DESCRIPTION     
--             "The counter associated with the current
--              number of packets which were prevented from
--              being delivered to the Higher Layer because
--              of a resource limitation,
--              in the current 15 minute interval."
--     ::= { srpErrCntCurrEntry 7 }

-- srpErrCntCurrHostRxShortPkts OBJECT-TYPE
--     SYNTAX          PerfCurrentCount64
--     ACCESS          read-only
--     STATUS          mandatory
--     DESCRIPTION     
--             "The counter associated with the current
--              number of packets which were prevented from
--              being delivered to the Higher Layer because
--              of being too short,
--              in the current 15 minute interval."
--     ::= { srpErrCntCurrEntry 8 }

-- srpErrCntCurrHostRxGiantPkts OBJECT-TYPE
--     SYNTAX          PerfCurrentCount64
--     ACCESS          read-only
--     STATUS          mandatory
--     DESCRIPTION     
--             "The counter associated with the current
--              number of packets discarded because of being
--              too big for the higher layer,
--              in the current 15 minute interval."
--     ::= { srpErrCntCurrEntry 9 }

srpErrCntIntTable OBJECT-TYPE
    SYNTAX          SEQUENCE OF SrpErrCntIntEntry
    ACCESS          not-accessible
    STATUS          mandatory
    DESCRIPTION     
            "The SRP Errors Interval counters table."
    ::= { srpErrorsCounters 4 }

srpErrCntIntEntry OBJECT-TYPE
    SYNTAX          SrpErrCntIntEntry
    ACCESS          not-accessible
    STATUS          mandatory
    DESCRIPTION     
            "Error statistics collected for a particular interval
             of a particular side of a particular SRP interface.
             The number of 15-minute intervals is between 1 and 96, and
             identifies the intervals for which the set of
             statistics is available. The value of srpIfValidIntervals 
             indicates how many intervals are currently available."
    INDEX           { ifIndex, srpErrCntIntInterfaceSide, 
                      srpErrCntIntNumber }
    ::= { srpErrCntIntTable 1 }

SrpErrCntIntEntry ::=
    SEQUENCE {
        srpErrCntIntInterfaceSide       InterfaceSide,
        srpErrCntIntNumber              INTEGER
--         srpErrCntIntRingRxTtlExpPkts    PerfIntervalCount64,
--         srpErrCntIntRingRxShortPkts     PerfIntervalCount64,
--         srpErrCntIntRingRxGiantPkts     PerfIntervalCount64,
--         srpErrCntIntRingRxAbortPkts     PerfIntervalCount64,
--         srpErrCntIntRingRxCRC           PerfIntervalCount64,
--         srpErrCntIntHostRxDiscardPkts   PerfIntervalCount64,
--         srpErrCntIntHostRxShortPkts     PerfIntervalCount64,
--         srpErrCntIntHostRxGiantPkts     PerfIntervalCount64
    }

srpErrCntIntInterfaceSide OBJECT-TYPE
    SYNTAX          InterfaceSide
    ACCESS          not-accessible
    STATUS          mandatory
    DESCRIPTION     
            "An indication of the side of the interface for which
             this row contains information."
    ::= { srpErrCntIntEntry 1 }

srpErrCntIntNumber OBJECT-TYPE
    SYNTAX          INTEGER (1..96)
    ACCESS          not-accessible
    STATUS          mandatory
    DESCRIPTION     
            "A number between 1 and 96, which identifies the
             interval for which the set od statistics is available.
             The interval identified by 1 is the most recently
             completed 15 minute interval,
             and interval identified by N is the interval
             immediately preceding the one identified by N-1."
    ::= { srpErrCntIntEntry 2 }

-- srpErrCntIntRingRxTtlExpPkts OBJECT-TYPE
--     SYNTAX          PerfIntervalCount64
--     ACCESS          read-only
--     STATUS          mandatory
--     DESCRIPTION     
--             "The counter associated with the interval
--              number of expired packets,
--              received from the Layer 1 Physical medium
--              in a particular 15-minute interval in the past 24 hours."
--     ::= { srpErrCntIntEntry 3 }

-- srpErrCntIntRingRxShortPkts OBJECT-TYPE
--     SYNTAX          PerfIntervalCount64
--     ACCESS          read-only
--     STATUS          mandatory
--     DESCRIPTION     
--             "The counter associated with the interval
--              number of short packets,
--              received from the Layer 1 Physical medium
--              in a particular 15-minute interval in the past 24 hours."
--     ::= { srpErrCntIntEntry 4 }

-- srpErrCntIntRingRxGiantPkts OBJECT-TYPE
--     SYNTAX          PerfIntervalCount64
--     ACCESS          read-only
--     STATUS          mandatory
--     DESCRIPTION     
--             "The counter associated with the interval
--              number of giant packets,
--              received from the Layer 1 Physical medium
--              in a particular 15-minute interval in the past 24 hours."
--     ::= { srpErrCntIntEntry 5 }

-- srpErrCntIntRingRxAbortPkts OBJECT-TYPE
--     SYNTAX          PerfIntervalCount64
--     ACCESS          read-only
--     STATUS          mandatory
--     DESCRIPTION     
--             "The counter associated with the interval
--              number of aborted packets,
--              received from the Layer 1 Physical medium
--              in a particular 15-minute interval in the past 24 hours."
--     ::= { srpErrCntIntEntry 6 }

-- srpErrCntIntRingRxCRC OBJECT-TYPE
--     SYNTAX          PerfIntervalCount64
--     ACCESS          read-only
--     STATUS          mandatory
--     DESCRIPTION     
--             "The counter associated with the interval
--              number of packets with CRC errors,
--              received from the Layer 1 Physical medium
--              in a particular 15-minute interval in the past 24 hours."
--     ::= { srpErrCntIntEntry 7 }

-- srpErrCntIntHostRxDiscardPkts OBJECT-TYPE
--     SYNTAX          PerfIntervalCount64
--     ACCESS          read-only
--     STATUS          mandatory
--     DESCRIPTION     
--             "The counter associated with the interval
--              number of packets discarded due to resource limitations,
--              received from the Layer 1 Physical medium
--              in a particular 15-minute interval in the past 24 hours."
--     ::= { srpErrCntIntEntry 8 }

-- srpErrCntIntHostRxShortPkts OBJECT-TYPE
--     SYNTAX          PerfIntervalCount64
--     ACCESS          read-only
--     STATUS          mandatory
--     DESCRIPTION     
--             "The counter associated with the interval
--              number of packets discarded because of being
--              too short for the higher layer,
--              in a particular 15-minute interval in the past 24 hours."
--     ::= { srpErrCntIntEntry 9 }

-- srpErrCntIntHostRxGiantPkts OBJECT-TYPE
--     SYNTAX          PerfIntervalCount64
--     ACCESS          read-only
--     STATUS          mandatory
--     DESCRIPTION     
--             "The counter associated with the interval
--              number of packets discarded because of being
--              too big for the higher layer,
--              in a particular 15-minute interval in the past 24 hours."
--     ::= { srpErrCntIntEntry 10 }

srpTrapsNotificationsPrefix OBJECT IDENTIFIER
    ::= { ciscosrpMIB 5 }

srpTrapsNotifications OBJECT IDENTIFIER
    ::= { srpTrapsNotificationsPrefix 0 }

srpConformance OBJECT IDENTIFIER
    ::= { ciscosrpMIB 6 }

srpGroups OBJECT IDENTIFIER
    ::= { srpConformance 1 }

srpCompliances OBJECT IDENTIFIER
    ::= { srpConformance 2 }

srpTrapRingWrapped TRAP-TYPE
    ENTERPRISE      srpTrapsNotificationsPrefix
    VARIABLES       { ifIndex, srpIpsState, srpMACIpsAutoDetectMode, 
                      srpMACIpsRemoteMode, srpMACIpsRemoteType, 
                      srpMACIpsActiveMode, srpMACIpsWrapCounter, 
                      srpMACIpsLastWrapTimeStamp, 
                      srpMACIpsLastUnWrapTimeStamp }
--     STATUS          mandatory
    DESCRIPTION     
            "An srpTrapRingWrapped notification is sent
             when the value of an instance of
             srpMACIpsWrapCounter increments."
    ::= 1

srpTrapRingRestored TRAP-TYPE
    ENTERPRISE      srpTrapsNotificationsPrefix
    VARIABLES       { ifIndex, srpIpsState, srpMACIpsAutoDetectMode, 
                      srpMACIpsRemoteMode, srpMACIpsRemoteType, 
                      srpMACIpsActiveMode, srpMACIpsWrapCounter, 
                      srpMACIpsLastWrapTimeStamp, 
                      srpMACIpsLastUnWrapTimeStamp }
--     STATUS          mandatory
    DESCRIPTION     
            "An srpTrapRingRestored notification is sent
             when the value of an instance of
             rpMACIpsLastUnWrapTimeStamp is changed."
    ::= 2

srpIfGroup OBJECT IDENTIFIER
    ::= { srpGroups 1 }

-- srpIfGroup OBJECT-GROUP
--     OBJECTS         { srpMACAddress, srpPriorityThreshold, 
--                       srpNodesOnTheRing, srpIpsState, srpIpsLockedOut, 
--                       srpIpsWaitToRestoreTimer, srpIfTimeElapsed, 
--                       srpIfValidIntervals }
--     STATUS          mandatory
--     DESCRIPTION     
--             "A collection of objects providing information
--              independent from a particular side A or B and is
--              applicable to all SRP interfaces."
--     ::= { srpGroups 1 }

srpMACSideGroup OBJECT IDENTIFIER
    ::= { srpGroups 2 }

-- srpMACSideGroup OBJECT-GROUP
--     OBJECTS         { srpMACNeighborAddress, srpMACSideWrapped, 
--                       srpMACIpsMgmtRequestedMode, 
--                       srpMACIpsAutoDetectMode, srpMACIpsRemoteMode, 
--                       srpMACIpsRemoteType, srpMACIpsActiveMode, 
--                       srpMACIpsWrapCounter, 
--                       srpMACIpsLastWrapTimeStamp, 
--                       srpMACIpsLastUnWrapTimeStamp, 
--                       srpMACClockSourceMode, srpMACTopologyTimer }
--     STATUS          mandatory
--     DESCRIPTION     
--             "A collection of objects providing information
--              dependent from a particular side A or B and is
--              specific to MAC and IPS (Intelligent protection
--              Switching)."
--     ::= { srpGroups 2 }

srpRingTopologyMapGroup OBJECT IDENTIFIER
    ::= { srpGroups 3 }

-- srpRingTopologyMapGroup OBJECT-GROUP
--     OBJECTS         { srpNodeMACAddress, srpNodeWrapped, srpNodeName }
--     STATUS          mandatory
--     DESCRIPTION     
--             "A collection of objects providing information
--              on the ring topology and nodes status."
--     ::= { srpGroups 3 }

srpMACCountersGroup OBJECT IDENTIFIER
    ::= { srpGroups 4 }

-- srpMACCountersGroup OBJECT-GROUP
--     OBJECTS         { srpMACCountPktsBySourceFlag, 
--                       srpMACCountPktsBySourceAddress, 
--                       srpMACSourceDiscontTimeStamp, 
--                       srpMACCountPktsBySource, 
--                       srpMACCountPktsByDestinationFlag, 
--                       srpMACCountPktsByDestAddress, 
--                       srpMACDestDiscontTimeStamp, 
--                       srpMACCountPktsByDest, 
--                       srpMACRejectPktsBySourceFlag, 
--                       srpMACRejectPktsBySourceAddress, 
--                       srpMACRejectPktsByDestFlag, 
--                       srpMACRejectPktsByDestAddress }
--     STATUS          deprecated
--     DESCRIPTION     
--             "A collection of objects providing information
--              about packets received or rejected by
--              a particular source or destination address."
--     ::= { srpGroups 4 }

srpRingCountersCurrentGroup OBJECT IDENTIFIER
    ::= { srpGroups 5 }

-- srpRingCountersCurrentGroup OBJECT-GROUP
--     OBJECTS         { srpRingCurUcastLowPriPktsIn, 
--                       srpRingCurUcastLowPriOctetsIn, 
--                       srpRingCurMcastLowPriPktsIn, 
--                       srpRingCurMcastLowPriOctetsIn, 
--                       srpRingCurUcastHighPriPktsIn, 
--                       srpRingCurUcastHighPriOctetsIn, 
--                       srpRingCurMcastHighPriPktsIn, 
--                       srpRingCurMcastHighPriOctetsIn, 
--                       srpRingCurUcastLowPriPktsOut, 
--                       srpRingCurUcastLowPriOctetsOut, 
--                       srpRingCurMcastLowPriPktsOut, 
--                       srpRingCurMcastLowPriOctetsOut, 
--                       srpRingCurUcastHighPriPktsOut, 
--                       srpRingCurUcastHighPriOctetsOut, 
--                       srpRingCurMcastHighPriPktsOut, 
--                       srpRingCurMcastHighPriOctetsOut }
--     STATUS          mandatory
--     DESCRIPTION     
--             "A collection of objects providing information
--              about unicast or multicast packets and octets
--              coming from the ring to a particular node
--              in the current 15 minute interval."
--     ::= { srpGroups 5 }

srpRingCountersIntervalGroup OBJECT IDENTIFIER
    ::= { srpGroups 6 }

-- srpRingCountersIntervalGroup OBJECT-GROUP
--     OBJECTS         { srpRingIntWrapCounter, 
--                       srpRingIntUcastLowPriPktsIn, 
--                       srpRingIntUcastLowPriOctetsIn, 
--                       srpRingIntMcastLowPriPktsIn, 
--                       srpRingIntMcastLowPriOctetsIn, 
--                       srpRingIntUcastHighPriPktsIn, 
--                       srpRingIntUcastHighPriOctetsIn, 
--                       srpRingIntMcastHighPriPktsIn, 
--                       srpRingIntMcastHighPriOctetsIn, 
--                       srpRingIntUcastLowPriPktsOut, 
--                       srpRingIntUcastLowPriOctetsOut, 
--                       srpRingIntMcastLowPriPktsOut, 
--                       srpRingIntMcastLowPriOctetsOut, 
--                       srpRingIntUcastHighPriPktsOut, 
--                       srpRingIntUcastHighPriOctetsOut, 
--                       srpRingIntMcastHighPriPktsOut, 
--                       srpRingIntMcastHighPriOctetsOut }
--     STATUS          mandatory
--     DESCRIPTION     
--             "A collection of objects providing information
--              about uni or multicast packets and octets
--              coming from the ring to a particular node
--              in a particular 15-minute interval
--              in the past 24 hours."
--     ::= { srpGroups 6 }

srpHostCountersCurrentGroup OBJECT IDENTIFIER
    ::= { srpGroups 7 }

-- srpHostCountersCurrentGroup OBJECT-GROUP
--     OBJECTS         { srpHostCurUcastLowPriPktsIn, 
--                       srpHostCurUcastLowPriOctetsIn, 
--                       srpHostCurMcastLowPriPktsIn, 
--                       srpHostCurMcastLowPriOctetsIn, 
--                       srpHostCurUcastHighPriPktsIn, 
--                       srpHostCurUcastHighPriOctetsIn, 
--                       srpHostCurMcastHighPriPktsIn, 
--                       srpHostCurMcastHighPriOctetsIn, 
--                       srpHostCurUcastLowPriPktsOut, 
--                       srpHostCurUcastLowPriOctetsOut, 
--                       srpHostCurMcastLowPriPktsOut, 
--                       srpHostCurMcastLowPriOctetsOut, 
--                       srpHostCurUcastHighPriPktsOut, 
--                       srpHostCurUcastHighPriOctetsOut, 
--                       srpHostCurMcastHighPriPktsOut, 
--                       srpHostCurMcastHighPriOctetsOut }
--     STATUS          mandatory
--     DESCRIPTION     
--             "A collection of objects providing information
--              about uni or multicast packets and octets
--              coming from the host to a particular node
--              in the current 15 minute interval."
--     ::= { srpGroups 7 }

srpHostCountersIntervalGroup OBJECT IDENTIFIER
    ::= { srpGroups 8 }

-- srpHostCountersIntervalGroup OBJECT-GROUP
--     OBJECTS         { srpHostIntUcastLowPriPktsIn, 
--                       srpHostIntUcastLowPriOctetsIn, 
--                       srpHostIntMcastLowPriPktsIn, 
--                       srpHostIntMcastLowPriOctetsIn, 
--                       srpHostIntUcastHighPriPktsIn, 
--                       srpHostIntUcastHighPriOctetsIn, 
--                       srpHostIntMcastHighPriPktsIn, 
--                       srpHostIntMcastHighPriOctetsIn, 
--                       srpHostIntUcastLowPriPktsOut, 
--                       srpHostIntUcastLowPriOctetsOut, 
--                       srpHostIntMcastLowPriPktsOut, 
--                       srpHostIntMcastLowPriOctetsOut, 
--                       srpHostIntUcastHighPriPktsOut, 
--                       srpHostIntUcastHighPriOctetsOut, 
--                       srpHostIntMcastHighPriPktsOut, 
--                       srpHostIntMcastHighPriOctetsOut }
--     STATUS          mandatory
--     DESCRIPTION     
--             "A collection of objects providing information
--              about uni or multicast packets and octets
--              coming from the host to a particular node
--              in a particular 15-minute interval
--              in the past 24 hours."
--     ::= { srpGroups 8 }

srpErrorsCountersCurrentGroup OBJECT IDENTIFIER
    ::= { srpGroups 9 }

-- srpErrorsCountersCurrentGroup OBJECT-GROUP
--     OBJECTS         { srpRingCurRxErrorsDataParity, 
--                       srpRingCurRxErrorsShortPackets, 
--                       srpRingCurRxErrorsGiantPackets, 
--                       srpRingCurRxErrorsSideBadPackets, 
--                       srpRingCurRxErrorsCRC, 
--                       srpHostCurRxErrorsDataParity, 
--                       srpHostCurRxErrorsShortPackets, 
--                       srpHostCurRxErrorsGiantPackets, 
--                       srpHostCurRxErrorsSideBadPackets }
--     STATUS          deprecated
--     DESCRIPTION     
--             "A collection of objects providing information
--              about errors coming from the ring 
--              to a particular node
--              in the current 15 minute interval."
--     ::= { srpGroups 9 }

srpErrorsCountersIntervalGroup OBJECT IDENTIFIER
    ::= { srpGroups 10 }

-- srpErrorsCountersIntervalGroup OBJECT-GROUP
--     OBJECTS         { srpRingIntRxErrorsDataParity, 
--                       srpRingIntRxErrorsShortPackets, 
--                       srpRingIntRxErrorsGiantPackets, 
--                       srpRingIntRxErrorsSideBadPackets, 
--                       srpRingIntRxErrorsCRC, 
--                       srpHostIntRxErrorsDataParity, 
--                       srpHostIntRxErrorsShortPackets, 
--                       srpHostIntRxErrorsGiantPackets, 
--                       srpHostIntRxErrorsSideBadPackets }
--     STATUS          deprecated
--     DESCRIPTION     
--             "A collection of objects providing information
--              about errors coming from the higher layer  
--              to a particular interface
--              in the current 15 minute interval."
--     ::= { srpGroups 10 }

srpErrCntCurrGroup OBJECT IDENTIFIER
    ::= { srpGroups 11 }

-- srpErrCntCurrGroup OBJECT-GROUP
--     OBJECTS         { srpErrCntCurrRingRxTtlExpPkts, 
--                       srpErrCntCurrRingRxShortPkts, 
--                       srpErrCntCurrRingRxGiantPkts, 
--                       srpErrCntCurrRingRxAbortPkts, 
--                       srpErrCntCurrRingRxCRC, 
--                       srpErrCntCurrHostRxDiscardPkts, 
--                       srpErrCntCurrHostRxShortPkts, 
--                       srpErrCntCurrHostRxGiantPkts }
--     STATUS          mandatory
--     DESCRIPTION     
--             "A collection of objects providing information
--              about received errors,
--              in the current 15 minute interval."
--     ::= { srpGroups 11 }

srpErrCntIntGroup OBJECT IDENTIFIER
    ::= { srpGroups 12 }

-- srpErrCntIntGroup OBJECT-GROUP
--     OBJECTS         { srpErrCntIntRingRxTtlExpPkts, 
--                       srpErrCntIntRingRxShortPkts, 
--                       srpErrCntIntRingRxGiantPkts, 
--                       srpErrCntIntRingRxAbortPkts, 
--                       srpErrCntIntRingRxCRC, 
--                       srpErrCntIntHostRxDiscardPkts, 
--                       srpErrCntIntHostRxShortPkts, 
--                       srpErrCntIntHostRxGiantPkts }
--     STATUS          mandatory
--     DESCRIPTION     
--             "A collection of objects providing information
--              about received errors,
--              in a particular 15-minute interval
--              in the past 24 hours."
--     ::= { srpGroups 12 }

srpNotificationsGroup OBJECT IDENTIFIER
    ::= { srpGroups 13 }

-- srpNotificationsGroup NOTIFICATION-GROUP
--     NOTIFICATIONS   { srpTrapRingWrapped, srpTrapRingRestored }
--     STATUS          mandatory
--     DESCRIPTION     
--             "The collection of notifications used to indicate
--              wrapped and unwrapped node state information."
--     ::= { srpGroups 13 }

srpCompliance OBJECT IDENTIFIER
    ::= { srpCompliances 1 }

-- srpCompliance MODULE-COMPLIANCE
--     STATUS          mandatory
--     DESCRIPTION     
--             "The compliance statement for this MIB."

--     MODULE          -- -- this module

--         MANDATORY-GROUPS    { srpIfGroup, srpMACSideGroup, 
--                       srpRingTopologyMapGroup }

--     ::= { srpCompliances 1 }

END -- end of module CISCO-SRP-MIB.
