--
-- This SMIv1 module has been generated by smidump 0.2-cvs. Do not edit.
--

SONUS-TCAP-CLIENT-SERVICES-MIB DEFINITIONS ::= BEGIN

IMPORTS
    OBJECT-TYPE
        FROM RFC-1212
    RowStatus
        FROM SNMPv2-TC
    sonusServicesMIBs
        FROM SONUS-SMI
    PointCode, SonusName
        FROM SONUS-TC;

sonusTcapClientServicesMIB OBJECT IDENTIFIER
    ::= { sonusServicesMIBs 4 }

-- sonusTcapClientServicesMIB MODULE-IDENTITY
--     LAST-UPDATED    "200703280000Z"
--     ORGANIZATION    
--             "Sonus Networks, Inc."
--     CONTACT-INFO    
--             "   Customer Support    
--              Sonus Networks, Inc.
--              7 Technology Park Drive
--              Westford, MA 01886
--              USA
--              
--              Tel: 978-614-8100
--              Fax: 978-614-8609"
--     DESCRIPTION     
--             "The MIB Module for TCAP Client Services Management."
--     REVISION        "200010240000Z"
--     DESCRIPTION     
--             "This MIB was obsoleted because TCAP services have been removed from the GSX."
--     ::= { sonusServicesMIBs 4 }


sonusTcapClientServicesMIBObjects OBJECT IDENTIFIER
    ::= { sonusTcapClientServicesMIB 1 }

sonusScpAdmn OBJECT IDENTIFIER
    ::= { sonusTcapClientServicesMIBObjects 1 }

sonusScpAdmnNextIndex OBJECT-TYPE
    SYNTAX          INTEGER
    ACCESS          read-only
    STATUS          obsolete
    DESCRIPTION     
            "The next valid index to use when creating an entry in
             the sonusScpAdmnTable."
    ::= { sonusScpAdmn 1 }

sonusScpAdmnTable OBJECT-TYPE
    SYNTAX          SEQUENCE OF SonusScpAdmnEntry
    ACCESS          not-accessible
    STATUS          obsolete
    DESCRIPTION     
            "This table contains information about each SCP configured to 
             provide a particular TCAP application service. A management 
             			entity may create rows for SCP that are anticipated to provide
             			services in the future."
    ::= { sonusScpAdmn 2 }

sonusScpAdmnEntry OBJECT-TYPE
    SYNTAX          SonusScpAdmnEntry
    ACCESS          not-accessible
    STATUS          obsolete
    DESCRIPTION     
            "This table describes the SCPs' configurations that GSX9000 
             node has access to their services."
    INDEX           { sonusScpAdmnIndex }
    ::= { sonusScpAdmnTable 1 }

SonusScpAdmnEntry ::=
    SEQUENCE {
        sonusScpAdmnIndex               INTEGER,
        sonusScpAdmnName                SonusName,
        sonusScpAdmnCarrier             DisplayString,
        sonusScpAdmnNode                DisplayString,
        sonusScpAdmnPc                  PointCode,
        sonusScpAdmnSsn                 INTEGER,
        sonusScpAdmnTimeout             INTEGER,
        sonusScpAdmnType                INTEGER,
        sonusScpAdmnProtocol            INTEGER,
        sonusScpAdmnState               INTEGER,
        sonusScpAdmnRowStatus           RowStatus
    }

sonusScpAdmnIndex OBJECT-TYPE
    SYNTAX          INTEGER
    ACCESS          read-only
    STATUS          obsolete
    DESCRIPTION     
            "A unique value for each SCP that is between 1 and maximum
             allowed"
    ::= { sonusScpAdmnEntry 1 }

sonusScpAdmnName OBJECT-TYPE
    SYNTAX          SonusName
    ACCESS          read-write
    STATUS          obsolete
    DESCRIPTION     
            "The name of the SCP."
    ::= { sonusScpAdmnEntry 2 }

sonusScpAdmnCarrier OBJECT-TYPE
    SYNTAX          DisplayString (SIZE(1..23))
    ACCESS          read-write
    STATUS          obsolete
    DESCRIPTION     
            "The name of the carrier using this SCP. "
    ::= { sonusScpAdmnEntry 3 }

sonusScpAdmnNode OBJECT-TYPE
    SYNTAX          DisplayString (SIZE(1..23))
    ACCESS          read-write
    STATUS          obsolete
    DESCRIPTION     
            "The name of the SS7 Node connecting to this SCP. "
    ::= { sonusScpAdmnEntry 4 }

sonusScpAdmnPc OBJECT-TYPE
    SYNTAX          PointCode
    ACCESS          read-write
    STATUS          obsolete
    DESCRIPTION     
            "The point code of this SCP"
    ::= { sonusScpAdmnEntry 5 }

sonusScpAdmnSsn OBJECT-TYPE
    SYNTAX          INTEGER
    ACCESS          read-write
    STATUS          obsolete
    DESCRIPTION     
            "The subsystem number of this SCP service"
    ::= { sonusScpAdmnEntry 6 }

sonusScpAdmnTimeout OBJECT-TYPE
    SYNTAX          INTEGER
    ACCESS          read-write
    STATUS          obsolete
    DESCRIPTION     
            "The timeout value of this SCP service"
    ::= { sonusScpAdmnEntry 7 }

sonusScpAdmnType OBJECT-TYPE
    SYNTAX          INTEGER { tollfree(1), lnp(2), credit(3), authen(4) }
    ACCESS          read-write
    STATUS          obsolete
    DESCRIPTION     
            "The type of service of this SCP"
    ::= { sonusScpAdmnEntry 8 }

sonusScpAdmnProtocol OBJECT-TYPE
    SYNTAX          INTEGER { none(1), ain(2), inap(3) }
    ACCESS          read-write
    STATUS          obsolete
    DESCRIPTION     
            "The encoding/decoding protocol on top of TCAP"
    DEFVAL          { none }
    ::= { sonusScpAdmnEntry 9 }

sonusScpAdmnState OBJECT-TYPE
    SYNTAX          INTEGER { disabled(1), enabled(2) }
    ACCESS          read-write
    STATUS          obsolete
    DESCRIPTION     
            "The configured state of the SCP."
    DEFVAL          { disabled }
    ::= { sonusScpAdmnEntry 10 }

sonusScpAdmnRowStatus OBJECT-TYPE
    SYNTAX          RowStatus
    ACCESS          read-write
    STATUS          obsolete
    DESCRIPTION     
            ""
    ::= { sonusScpAdmnEntry 11 }

sonusScpStatTable OBJECT-TYPE
    SYNTAX          SEQUENCE OF SonusScpStatEntry
    ACCESS          not-accessible
    STATUS          obsolete
    DESCRIPTION     
            "This table contains status information about each SCP"
    ::= { sonusTcapClientServicesMIBObjects 2 }

sonusScpStatEntry OBJECT-TYPE
    SYNTAX          SonusScpStatEntry
    ACCESS          not-accessible
    STATUS          obsolete
    DESCRIPTION     
            "This table describes the SCP stat"
    INDEX           { sonusScpStatIndex }
    ::= { sonusScpStatTable 1 }

SonusScpStatEntry ::=
    SEQUENCE {
        sonusScpStatIndex               INTEGER,
        sonusScpStatQueryNum            INTEGER,
        sonusScpStatQueryFailed         INTEGER
    }

sonusScpStatIndex OBJECT-TYPE
    SYNTAX          INTEGER
    ACCESS          read-only
    STATUS          obsolete
    DESCRIPTION     
            "Identifies the SCP"
    ::= { sonusScpStatEntry 1 }

sonusScpStatQueryNum OBJECT-TYPE
    SYNTAX          INTEGER
    ACCESS          read-only
    STATUS          obsolete
    DESCRIPTION     
            "The total number of queries performed at the moment"
    ::= { sonusScpStatEntry 2 }

sonusScpStatQueryFailed OBJECT-TYPE
    SYNTAX          INTEGER
    ACCESS          read-only
    STATUS          obsolete
    DESCRIPTION     
            "The total number of queries failed at the moment"
    ::= { sonusScpStatEntry 3 }

END -- end of module SONUS-TCAP-CLIENT-SERVICES-MIB.
