--
-- This SMIv1 module has been generated by smidump 0.2-cvs. Do not edit.
--

SONUS-SOFTSWITCH-MIB DEFINITIONS ::= BEGIN

IMPORTS
    OBJECT-TYPE
        FROM RFC-1212
    TRAP-TYPE
        FROM RFC-1215
    sonusEventClass, sonusEventDescription, sonusEventLevel, 
    sonusEventTime
        FROM SONUS-COMMON-MIB
    sonusSystemMIBs
        FROM SONUS-SMI
    SonusSoftSwitchDbOperationFailureReason, SonusTMIdentifier
        FROM SONUS-SOFTSWITCH-TC
    SonusSystemName
        FROM SONUS-TC;

sonusSoftSwitchMIB OBJECT IDENTIFIER
    ::= { sonusSystemMIBs 4 }

-- sonusSoftSwitchMIB MODULE-IDENTITY
--     LAST-UPDATED    "200004230000Z"
--     ORGANIZATION    
--             "Sonus Networks, Inc."
--     CONTACT-INFO    
--             "   Customer Support    
--              Sonus Networks, Inc.
--              250 Apollo Drive
--              Chelmsford, MA 01824
--              USA
--              
--              Tel: 978-614-8100
--              Fax: 978-614-8609"
--     DESCRIPTION     
--             "The MIB Module for SoftSwitch Management."
--     ::= { sonusSystemMIBs 4 }


sonusSoftSwitchMIBObjects OBJECT IDENTIFIER
    ::= { sonusSoftSwitchMIB 1 }

sonusSoftSwitchMIBNotifications OBJECT IDENTIFIER
    ::= { sonusSoftSwitchMIB 2 }

sonusSoftSwitchMIBNotificationsPrefix OBJECT IDENTIFIER
    ::= { sonusSoftSwitchMIBNotifications 0 }

sonusSoftSwitchMIBNotificationsObjects OBJECT IDENTIFIER
    ::= { sonusSoftSwitchMIBNotifications 1 }

sonusSoftSwitchServerName OBJECT-TYPE
    SYNTAX          SonusSystemName
    ACCESS          read-only
    STATUS          mandatory
    DESCRIPTION     
            "Name of the SoftSwitch server."
    ::= { sonusSoftSwitchMIBNotificationsObjects 1 }

sonusSoftSwitchClientName OBJECT-TYPE
    SYNTAX          SonusSystemName
    ACCESS          read-only
    STATUS          mandatory
    DESCRIPTION     
            "Name of the SoftSwitch client, usually a gateway."
    ::= { sonusSoftSwitchMIBNotificationsObjects 2 }

sonusSoftSwitchDbOperationFailureReason OBJECT-TYPE
    SYNTAX          SonusSoftSwitchDbOperationFailureReason
    ACCESS          read-only
    STATUS          mandatory
    DESCRIPTION     
            "DB operation failure reason."
    ::= { sonusSoftSwitchMIBNotificationsObjects 3 }

sonusSoftSwitchTMIdentifier1 OBJECT-TYPE
    SYNTAX          SonusTMIdentifier
    ACCESS          read-only
    STATUS          mandatory
    DESCRIPTION     
            "Identifies the control. For Destination and Origination element type this is the national number. For Trunkgroup type, it is the trunkgroup identifier"
    ::= { sonusSoftSwitchMIBNotificationsObjects 4 }

sonusSoftSwitchTMIdentifier2 OBJECT-TYPE
    SYNTAX          SonusTMIdentifier
    ACCESS          read-only
    STATUS          mandatory
    DESCRIPTION     
            "Identifies the control.  For Destination and Origination element type this is the country code. For Trunkgroup type it is the gateway identifier. "
    ::= { sonusSoftSwitchMIBNotificationsObjects 5 }

sonusSoftSwitchTMElementType OBJECT-TYPE
    SYNTAX          INTEGER { destination(1), trunkgroup(2), 
                        origination(3), routingLabel(4) }
    ACCESS          read-only
    STATUS          mandatory
    DESCRIPTION     
            "Type of element on which this traffic management control operates."
    ::= { sonusSoftSwitchMIBNotificationsObjects 6 }

sonusSoftSwitchTMProvControlType OBJECT-TYPE
    SYNTAX          INTEGER { unknown(0), canf(1), cantdr(2), skipdr(3), 
                        skipar(4), dialeddestination(5), 
                        translateddestination(6), cantar(7), strdr(8), 
                        strar(9), irrdr(10), sirrdr(11), orrdr(12), 
                        sorrdr(13), rralternate(14), irrar(15), 
                        sirrar(16), orrar(17), sorrar(18), 
                        origination(19), finalCallingNumber(20), 
                        finalDestination(21), 
                        contractorBasedOrigination(22), 
                        cdDNBasedDestination(23) }
    ACCESS          read-only
    STATUS          mandatory
    DESCRIPTION     
            "Type of control provisioned."
    ::= { sonusSoftSwitchMIBNotificationsObjects 7 }

sonusSoftSwitchTMAppliedControlType OBJECT-TYPE
    SYNTAX          INTEGER { dialeddestination(1), 
                        translateddestination(2), origination(3), 
                        finalCallingNumber(4), finalDestination(5), 
                        contractorBasedOrigination(6), 
                        cdDNBasedDestination(7) }
    ACCESS          read-only
    STATUS          mandatory
    DESCRIPTION     
            "Type of control applied."
    ::= { sonusSoftSwitchMIBNotificationsObjects 8 }

sonusSoftSwitchTMAddressNature OBJECT-TYPE
    SYNTAX          INTEGER { unknown(0), national(1), international(2), 
                        nochange(3), subscriber(4), networkspecific(5), 
                        natureunknown(6), subscriberoperator(7), 
                        nationaloperator(8), internationaloperator(9), 
                        testcode(10), nonumberoprequested(11), 
                        nonumbercutthrough(12), nature950(13), 
                        anicallingpartysubscriber(14), 
                        aninotavailable(15), anicallingpartynational(16), 
                        anicalledpartysubscriber(17), 
                        anicalledpartynonumber(18), 
                        anicalledpartynational(19), ss7reserved(20), 
                        nationalnotrestricted(21), 
                        nationalrestricted(22), 
                        internationalnotrestricted(23), 
                        internationalrestricted(24), 
                        partialcallinglineid(126), all(255) }
    ACCESS          read-only
    STATUS          mandatory
    DESCRIPTION     
            "Specifies whether the call was national,international or any other type like network specific."
    ::= { sonusSoftSwitchMIBNotificationsObjects 9 }

sonusSoftSwitchUpNotification TRAP-TYPE
    ENTERPRISE      sonusSoftSwitchMIBNotifications
    VARIABLES       { sonusEventDescription, sonusEventClass, 
                      sonusEventLevel, sonusEventTime }
--     STATUS          mandatory
    DESCRIPTION     
            "SoftSwitch is up."
    ::= 1

sonusSoftSwitchDownNotification TRAP-TYPE
    ENTERPRISE      sonusSoftSwitchMIBNotifications
    VARIABLES       { sonusEventDescription, sonusEventClass, 
                      sonusEventLevel, sonusEventTime }
--     STATUS          mandatory
    DESCRIPTION     
            "SoftSwitch is down."
    ::= 2

sonusSoftSwitchThreadCountConfigChangeNotification TRAP-TYPE
    ENTERPRISE      sonusSoftSwitchMIBNotifications
    VARIABLES       { sonusEventDescription, sonusEventClass, 
                      sonusEventLevel, sonusEventTime }
--     STATUS          deprecated
    DESCRIPTION     
            "SoftSwitch's total thread count have been changed."
    ::= 3

sonusSoftSwitchThreadCountConfigOutOfRangeErrorNotification TRAP-TYPE
    ENTERPRISE      sonusSoftSwitchMIBNotifications
    VARIABLES       { sonusEventDescription, sonusEventClass, 
                      sonusEventLevel, sonusEventTime }
--     STATUS          deprecated
    DESCRIPTION     
            "SoftSwitch is down."
    ::= 4

sonusSoftSwitchThreadCountConfigOutOfRangeErrorCleanupNotification TRAP-TYPE
    ENTERPRISE      sonusSoftSwitchMIBNotifications
    VARIABLES       { sonusEventDescription, sonusEventClass, 
                      sonusEventLevel, sonusEventTime }
--     STATUS          deprecated
    DESCRIPTION     
            "SoftSwitch is up."
    ::= 5

sonusSoftSwitchCPSLicensingThresholdMajor TRAP-TYPE
    ENTERPRISE      sonusSoftSwitchMIBNotifications
    VARIABLES       { sonusEventDescription, sonusEventClass, 
                      sonusEventLevel, sonusEventTime }
--     STATUS          mandatory
    DESCRIPTION     
            "The PSX process CPS licensing threshold has reached or exceeded major threshold."
    ::= 6

sonusSoftSwitchCPSLicensingThresholdCritical TRAP-TYPE
    ENTERPRISE      sonusSoftSwitchMIBNotifications
    VARIABLES       { sonusEventDescription, sonusEventClass, 
                      sonusEventLevel, sonusEventTime }
--     STATUS          mandatory
    DESCRIPTION     
            "The PSX process CPS licensing threshold has reached or exceeded critical threshold."
    ::= 7

sonusSoftSwitchCPSLicenseGracePeriod TRAP-TYPE
    ENTERPRISE      sonusSoftSwitchMIBNotifications
    VARIABLES       { sonusEventDescription, sonusEventClass, 
                      sonusEventLevel, sonusEventTime }
--     STATUS          mandatory
    DESCRIPTION     
            "PSX CPS Base License is  unavailable and a grace period of 90 days is provided."
    ::= 8

sonusSoftSwitchCPSLicenseUnavailable TRAP-TYPE
    ENTERPRISE      sonusSoftSwitchMIBNotifications
    VARIABLES       { sonusEventDescription, sonusEventClass, 
                      sonusEventLevel, sonusEventTime }
--     STATUS          mandatory
    DESCRIPTION     
            "PSX CPS Base License is  unavailable and calls will be dropped."
    ::= 9

sonusSoftSwitchSwitchToDomainLockedLicensingFailedNotification TRAP-TYPE
    ENTERPRISE      sonusSoftSwitchMIBNotifications
    VARIABLES       { sonusEventDescription, sonusEventClass, 
                      sonusEventLevel, sonusEventTime }
--     STATUS          mandatory
    DESCRIPTION     
            "PSX Switching to domain locked licensing is failed."
    ::= 10

END -- end of module SONUS-SOFTSWITCH-MIB.
