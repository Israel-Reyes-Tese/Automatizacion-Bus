--
-- This SMIv2 module has been generated by smidump 0.2-cvs. Do not edit.
--

SONUS-SOFTSWITCH-SSA-MIB DEFINITIONS ::= BEGIN

IMPORTS
    Counter32, Gauge32, Integer32, MODULE-IDENTITY, NOTIFICATION-TYPE, 
    OBJECT-TYPE, TimeTicks
        FROM SNMPv2-SMI
    sonusEventClass, sonusEventDescription, sonusEventLevel, 
    sonusEventTime
        FROM SONUS-COMMON-MIB
    sonusServicesMIBs
        FROM SONUS-SMI
    SonusName
        FROM SONUS-TC;

sonusSoftSwitchSsaMIB OBJECT IDENTIFIER
    ::= { sonusServicesMIBs 45 }

sonusSoftSwitchSsaMIBObjects OBJECT IDENTIFIER
    ::= { sonusSoftSwitchSsaMIB 1 }

sonusSoftSwitchSsaStatistics OBJECT IDENTIFIER
    ::= { sonusSoftSwitchSsaMIBObjects 1 }

sonusSoftSwitchOutboundLicenseCounters OBJECT IDENTIFIER
    ::= { sonusSoftSwitchSsaStatistics 1 }

sonusSoftSwitchOutboundLicenseTable OBJECT-TYPE
    SYNTAX          SEQUENCE OF SonusSoftSwitchOutboundLicenseEntry
    MAX-ACCESS      not-accessible
    STATUS          current
    DESCRIPTION     
            "Count Feature or on/off license enabled for the node"
    ::= { sonusSoftSwitchOutboundLicenseCounters 1 }

sonusSoftSwitchOutboundLicenseEntry OBJECT-TYPE
    SYNTAX          SonusSoftSwitchOutboundLicenseEntry
    MAX-ACCESS      not-accessible
    STATUS          current
    DESCRIPTION     
            "An entry in the Outbound License table "
    INDEX           { sonusSoftSwitchOutboundLicenseName }
    ::= { sonusSoftSwitchOutboundLicenseTable 1 }

SonusSoftSwitchOutboundLicenseEntry ::=
    SEQUENCE {
        sonusSoftSwitchOutboundLicenseName  SonusName,
        sonusSoftSwitchOutboundLicenseUsageLimit        Gauge32
    }

sonusSoftSwitchOutboundLicenseName OBJECT-TYPE
    SYNTAX          SonusName
    MAX-ACCESS      read-only
    STATUS          current
    DESCRIPTION     
            "FeatureId (or SKU) for which usage limit is specified."
    ::= { sonusSoftSwitchOutboundLicenseEntry 1 }

sonusSoftSwitchOutboundLicenseUsageLimit OBJECT-TYPE
    SYNTAX          Gauge32
    MAX-ACCESS      read-only
    STATUS          current
    DESCRIPTION     
            "Provisioned total BASE Count for the license on the node"
    ::= { sonusSoftSwitchOutboundLicenseEntry 2 }

sonusSoftSwitchSsaMIBNotifications OBJECT IDENTIFIER
    ::= { sonusSoftSwitchSsaMIB 2 }

sonusSoftSwitchSsaMIBNotificationsPrefix OBJECT IDENTIFIER
    ::= { sonusSoftSwitchSsaMIBNotifications 0 }

sonusSoftSwitchSsmgrExitNotification NOTIFICATION-TYPE
    OBJECTS         { sonusEventDescription, sonusEventClass, 
                      sonusEventLevel, sonusEventTime }
    STATUS          current
    DESCRIPTION     
            "The 'ssmgr' process is exited."
    ::= { sonusSoftSwitchSsaMIBNotificationsPrefix 1 }

END -- end of module SONUS-SOFTSWITCH-SSA-MIB.
