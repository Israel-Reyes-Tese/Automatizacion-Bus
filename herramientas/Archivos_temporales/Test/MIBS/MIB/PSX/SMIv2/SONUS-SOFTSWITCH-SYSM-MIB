--
-- This SMIv2 module has been generated by smidump 0.2-cvs. Do not edit.
--

SONUS-SOFTSWITCH-SYSM-MIB DEFINITIONS ::= BEGIN

IMPORTS
    Counter32, Gauge32, Integer32, MODULE-IDENTITY, NOTIFICATION-TYPE, 
    OBJECT-TYPE
        FROM SNMPv2-SMI
    sonusEventClass, sonusEventDescription, sonusEventLevel, 
    sonusEventTime
        FROM SONUS-COMMON-MIB
    sonusServicesMIBs
        FROM SONUS-SMI;

sonusSoftSwitchSystemManagerMIB MODULE-IDENTITY
    LAST-UPDATED    "200205030000Z"
    ORGANIZATION    
            "Sonus Networks, Inc."
    CONTACT-INFO    
            " Customer Support
             Sonus Networks, Inc.
             250 Apollo Drive
             Chelmsford, MA 01824
             USA
             Tel: 978-614-8100
             Fax: 978-614-8609"
    DESCRIPTION     
            "The MIB Module for SoftSwitch System Manager."
    ::= { sonusServicesMIBs 44 }


sonusSoftSwitchSystemManagerMIBObjects OBJECT IDENTIFIER
    ::= { sonusSoftSwitchSystemManagerMIB 1 }

sonusSoftSwitchSysmMIBNotifications OBJECT IDENTIFIER
    ::= { sonusSoftSwitchSystemManagerMIB 2 }

sonusSoftSwitchSysmMIBNotificationsPrefix OBJECT IDENTIFIER
    ::= { sonusSoftSwitchSysmMIBNotifications 0 }

sonusSoftSwitchSysmMIBNotificationsObjects OBJECT IDENTIFIER
    ::= { sonusSoftSwitchSysmMIBNotifications 1 }

sonusSoftSwitchSysmUpNotification NOTIFICATION-TYPE
    OBJECTS         { sonusEventDescription, sonusEventClass, 
                      sonusEventLevel, sonusEventTime }
    STATUS          current
    DESCRIPTION     
            "SoftSwitch SYSM is up."
    ::= { sonusSoftSwitchSysmMIBNotificationsPrefix 1 }

sonusSoftSwitchSysmDownNotification NOTIFICATION-TYPE
    OBJECTS         { sonusEventDescription, sonusEventClass, 
                      sonusEventLevel, sonusEventTime }
    STATUS          current
    DESCRIPTION     
            "SoftSwitch SYSM is down."
    ::= { sonusSoftSwitchSysmMIBNotificationsPrefix 2 }

END -- end of module SONUS-SOFTSWITCH-SYSM-MIB.
