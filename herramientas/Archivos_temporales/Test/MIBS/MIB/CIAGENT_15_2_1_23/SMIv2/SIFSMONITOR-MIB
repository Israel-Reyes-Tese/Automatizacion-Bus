--
-- This SMIv2 module has been generated by smidump 0.2-cvs. Do not edit.
--

SIFSMONITOR-MIB DEFINITIONS ::= BEGIN

IMPORTS
    snmpResearchMIBs
        FROM SNMP-RESEARCH-MIB
    Integer32, MODULE-IDENTITY, NOTIFICATION-TYPE, OBJECT-TYPE
        FROM SNMPv2-SMI
    DisplayString, RowStatus, TruthValue
        FROM SNMPv2-TC;

siFsMonitor MODULE-IDENTITY
    LAST-UPDATED    "199906091645Z"
    ORGANIZATION    
            "SNMP Research"
    CONTACT-INFO    
            "Postal:  SNMP Research
             3001 Kimberlin Heights Rd.
             Knoxville, TN 37920-9716
             USA
             
             Tel:     +1 423 579 3311
             Fax:     +1 423 579 6565
             E-mail:  info@int.snmp.com
             WWW:     http://www.int.snmp.com"
    DESCRIPTION     
            "A set of objects for monitoring filesystem utilization"
    ::= { iso 3 6 1 4 1 99 12 39 }


siFsMonObjects OBJECT IDENTIFIER
    ::= { siFsMonitor 1 }

siFsMonGlobalPollInterval OBJECT-TYPE
    SYNTAX          Integer32
    MAX-ACCESS      read-write
    STATUS          current
    DESCRIPTION     
            "The period, in seconds, when the filesystems should be 
             checked to see if any exceed the threshold.  A value of
             0 indicates not to poll based on this value."
    ::= { siFsMonObjects 1 }

siFsMonGlobalPollNow OBJECT-TYPE
    SYNTAX          TruthValue
    MAX-ACCESS      read-write
    STATUS          current
    DESCRIPTION     
            "Setting this object to true(1) will cause the filesystems 
             to be checked to see if they exceed a threshold. The primary
             purpose of this variable is for use with the disman schedule
             MIB."
    ::= { siFsMonObjects 2 }

siFsMonitorTable OBJECT-TYPE
    SYNTAX          SEQUENCE OF SiFsMonitorEntry
    MAX-ACCESS      not-accessible
    STATUS          current
    DESCRIPTION     
            "A table to configure which filesystems are to be monitored."
    ::= { siFsMonObjects 10 }

siFsMonitorEntry OBJECT-TYPE
    SYNTAX          SiFsMonitorEntry
    MAX-ACCESS      not-accessible
    STATUS          current
    DESCRIPTION     
            "An entry in the siFsMonitorTable."
    INDEX           { siFsMonIndex }
    ::= { siFsMonitorTable 1 }

SiFsMonitorEntry ::=
    SEQUENCE {
        siFsMonIndex                    Integer32,
        siFsMonName                     DisplayString,
        siFsMonDescr                    DisplayString,
        siFsMonThreshold                Integer32,
        siFsMonSeverity                 INTEGER,
        siFsMonCurrentUtilization       Integer32,
        siFsMonTrapWhenAboveThreshold   TruthValue,
        siFsMonTrapWhenBelowThreshold   TruthValue,
        siFsMonCommandWhenAboveThreshold DisplayString,
        siFsMonPollInterval             Integer32,
        siFsMonPollNow                  TruthValue,
        siFsMonOwner                    DisplayString,
        siFsMonRowStatus                RowStatus
    }

siFsMonIndex OBJECT-TYPE
    SYNTAX          Integer32 (1..2147483647)
    MAX-ACCESS      not-accessible
    STATUS          current
    DESCRIPTION     
            "A numeric index for the siFsMonitorTable."
    ::= { siFsMonitorEntry 1 }

siFsMonName OBJECT-TYPE
    SYNTAX          DisplayString
    MAX-ACCESS      read-create
    STATUS          current
    DESCRIPTION     
            "The name of the filesystem to be monitored."
    ::= { siFsMonitorEntry 2 }

siFsMonDescr OBJECT-TYPE
    SYNTAX          DisplayString
    MAX-ACCESS      read-create
    STATUS          current
    DESCRIPTION     
            "A textual description of this entry."
    ::= { siFsMonitorEntry 3 }

siFsMonThreshold OBJECT-TYPE
    SYNTAX          Integer32
    MAX-ACCESS      read-create
    STATUS          current
    DESCRIPTION     
            "The percentage full at which an event will be triggered."
    ::= { siFsMonitorEntry 4 }

siFsMonSeverity OBJECT-TYPE
    SYNTAX          INTEGER { warning(1), critical(2) }
    MAX-ACCESS      read-create
    STATUS          current
    DESCRIPTION     
            "The severity determines which trap will be sent when the
             threshold is exceeded."
    ::= { siFsMonitorEntry 6 }

siFsMonCurrentUtilization OBJECT-TYPE
    SYNTAX          Integer32
    MAX-ACCESS      read-only
    STATUS          current
    DESCRIPTION     
            "The percentage of disk space currently in use on 
             this filesystem."
    ::= { siFsMonitorEntry 7 }

siFsMonTrapWhenAboveThreshold OBJECT-TYPE
    SYNTAX          TruthValue
    MAX-ACCESS      read-create
    STATUS          current
    DESCRIPTION     
            "This value determines if a trap should be sent when the
             threshold is exceeded."
    ::= { siFsMonitorEntry 8 }

siFsMonTrapWhenBelowThreshold OBJECT-TYPE
    SYNTAX          TruthValue
    MAX-ACCESS      read-create
    STATUS          current
    DESCRIPTION     
            "This value determines if a trap should be sent when the
             filesystem utilization falls below the threshold."
    ::= { siFsMonitorEntry 10 }

siFsMonCommandWhenAboveThreshold OBJECT-TYPE
    SYNTAX          DisplayString
    MAX-ACCESS      read-create
    STATUS          current
    DESCRIPTION     
            "A command to execute when the threshold is exceeded. A
             zero-length octet string indicates that no command will
             be executed."
    ::= { siFsMonitorEntry 12 }

siFsMonPollInterval OBJECT-TYPE
    SYNTAX          Integer32
    MAX-ACCESS      read-create
    STATUS          current
    DESCRIPTION     
            "The period, in seconds, when this filesystem should be  
             checked to see if it exceeds the threshold. A value of
             0 indicates not to poll based on this value."
    ::= { siFsMonitorEntry 16 }

siFsMonPollNow OBJECT-TYPE
    SYNTAX          TruthValue
    MAX-ACCESS      read-create
    STATUS          current
    DESCRIPTION     
            "Setting this object to true(1) will cause this filesystem
             to be checked to see if it exceeds a threshold. The primary
             purpose of this variable is for use with the disman schedule
             MIB."
    ::= { siFsMonitorEntry 17 }

siFsMonOwner OBJECT-TYPE
    SYNTAX          DisplayString
    MAX-ACCESS      read-create
    STATUS          current
    DESCRIPTION     
            "The entity that configured this entry and is
             therefore using the resources assigned to it."
    ::= { siFsMonitorEntry 27 }

siFsMonRowStatus OBJECT-TYPE
    SYNTAX          RowStatus
    MAX-ACCESS      read-create
    STATUS          current
    DESCRIPTION     
            "A RowStatus object for the filesystem monitor table."
    ::= { siFsMonitorEntry 28 }

siFsTable OBJECT-TYPE
    SYNTAX          SEQUENCE OF SiFsEntry
    MAX-ACCESS      not-accessible
    STATUS          current
    DESCRIPTION     
            "The filesystem table"
    ::= { siFsMonObjects 11 }

siFsEntry OBJECT-TYPE
    SYNTAX          SiFsEntry
    MAX-ACCESS      not-accessible
    STATUS          current
    DESCRIPTION     
            "An entry in the filesystem table."
    INDEX           { siFsIndex }
    ::= { siFsTable 1 }

SiFsEntry ::=
    SEQUENCE {
        siFsIndex                       Integer32,
        siFsFilesystem                  DisplayString,
        siFsMountPoint                  DisplayString,
        siFsSize                        Integer32,
        siFsUsed                        Integer32,
        siFsAvail                       Integer32,
        siFsCapacity                    Integer32
    }

siFsIndex OBJECT-TYPE
    SYNTAX          Integer32 (1..2147483647)
    MAX-ACCESS      not-accessible
    STATUS          current
    DESCRIPTION     
            "A numeric index for the filesystem table."
    ::= { siFsEntry 1 }

siFsFilesystem OBJECT-TYPE
    SYNTAX          DisplayString
    MAX-ACCESS      read-only
    STATUS          current
    DESCRIPTION     
            "The filesystem name."
    ::= { siFsEntry 2 }

siFsMountPoint OBJECT-TYPE
    SYNTAX          DisplayString
    MAX-ACCESS      read-only
    STATUS          current
    DESCRIPTION     
            "The filesystem mount point."
    ::= { siFsEntry 3 }

siFsSize OBJECT-TYPE
    SYNTAX          Integer32
    MAX-ACCESS      read-only
    STATUS          current
    DESCRIPTION     
            "The total space allocated in the file system."
    ::= { siFsEntry 4 }

siFsUsed OBJECT-TYPE
    SYNTAX          Integer32
    MAX-ACCESS      read-only
    STATUS          current
    DESCRIPTION     
            "The amount of space allocated to existing files."
    ::= { siFsEntry 5 }

siFsAvail OBJECT-TYPE
    SYNTAX          Integer32
    MAX-ACCESS      read-only
    STATUS          current
    DESCRIPTION     
            "The total amount of space available for the
             creation of new files by unpriviledged users."
    ::= { siFsEntry 6 }

siFsCapacity OBJECT-TYPE
    SYNTAX          Integer32
    MAX-ACCESS      read-only
    STATUS          current
    DESCRIPTION     
            "the percentage of normally available
             space that is currently allocated to all
             files on the file system."
    ::= { siFsEntry 7 }

siFsExceptionsTable OBJECT-TYPE
    SYNTAX          SEQUENCE OF SiFsExceptionsEntry
    MAX-ACCESS      not-accessible
    STATUS          current
    DESCRIPTION     
            "A table of filesystems which are currently above the
             threshold."
    ::= { siFsMonObjects 12 }

siFsExceptionsEntry OBJECT-TYPE
    SYNTAX          SiFsExceptionsEntry
    MAX-ACCESS      not-accessible
    STATUS          current
    DESCRIPTION     
            "An entry in the siFsExceptionsTable."
    INDEX           { siFsMonIndex }
    ::= { siFsExceptionsTable 1 }

SiFsExceptionsEntry ::=
    SEQUENCE {
        siFsExceptionName               DisplayString,
        siFsExceptionThreshold          Integer32,
        siFsExceptionCurrentValue       Integer32
    }

siFsExceptionName OBJECT-TYPE
    SYNTAX          DisplayString
    MAX-ACCESS      read-only
    STATUS          current
    DESCRIPTION     
            "The filesystem name."
    ::= { siFsExceptionsEntry 1 }

siFsExceptionThreshold OBJECT-TYPE
    SYNTAX          Integer32
    MAX-ACCESS      read-only
    STATUS          current
    DESCRIPTION     
            "The threshold which has been exceeded."
    ::= { siFsExceptionsEntry 2 }

siFsExceptionCurrentValue OBJECT-TYPE
    SYNTAX          Integer32
    MAX-ACCESS      read-only
    STATUS          current
    DESCRIPTION     
            "The current percent utilization of the filesystem."
    ::= { siFsExceptionsEntry 3 }

siFsMonNotifications OBJECT IDENTIFIER
    ::= { siFsMonitor 2 }

siFsAboveWarningThreshold NOTIFICATION-TYPE
    OBJECTS         { siFsMonName, siFsMonThreshold, 
                      siFsMonCurrentUtilization }
    STATUS          current
    DESCRIPTION     
            "A trap indicating that the threshold was exceeded in a
             row where the severity is set to warning."
    ::= { siFsMonNotifications 1 }

siFsAboveCriticalThreshold NOTIFICATION-TYPE
    OBJECTS         { siFsMonName, siFsMonThreshold, 
                      siFsMonCurrentUtilization }
    STATUS          current
    DESCRIPTION     
            "A trap indicating that the threshold was exceeded in a
             row where the severity is set to critical."
    ::= { siFsMonNotifications 2 }

siFsBelowWarningThreshold NOTIFICATION-TYPE
    OBJECTS         { siFsMonName, siFsMonThreshold, 
                      siFsMonCurrentUtilization }
    STATUS          current
    DESCRIPTION     
            "A trap indicating that the percent utilization has dropped
             back below the threshold in a row where the severity is set 
             to warning."
    ::= { siFsMonNotifications 3 }

siFsBelowCriticalThreshold NOTIFICATION-TYPE
    OBJECTS         { siFsMonName, siFsMonThreshold, 
                      siFsMonCurrentUtilization }
    STATUS          current
    DESCRIPTION     
            "A trap indicating that the percent utilization has dropped
             back below the threshold in a row where the severity is set 
             to critical."
    ::= { siFsMonNotifications 4 }

END -- end of module SIFSMONITOR-MIB.
