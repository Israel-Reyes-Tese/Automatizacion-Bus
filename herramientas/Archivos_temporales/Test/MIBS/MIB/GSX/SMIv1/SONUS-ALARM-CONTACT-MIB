--
-- This SMIv1 module has been generated by smidump 0.2-cvs. Do not edit.
--

SONUS-ALARM-CONTACT-MIB DEFINITIONS ::= BEGIN

IMPORTS
    OBJECT-TYPE
        FROM RFC-1212
    TRAP-TYPE
        FROM RFC-1215
    sonusEventClass, sonusEventDescription, sonusEventLevel, 
    sonusEventTime, sonusSequenceId, sonusShelfIndex
        FROM SONUS-COMMON-MIB
    sonusSystemMIBs
        FROM SONUS-SMI
    SonusAdminState, SonusBoolean, SonusShelfIndex
        FROM SONUS-TC;

sonusAlarmManagerMIB OBJECT IDENTIFIER
    ::= { sonusSystemMIBs 6 }

-- sonusAlarmManagerMIB MODULE-IDENTITY
--     LAST-UPDATED    "200703280000Z"
--     ORGANIZATION    
--             "Sonus Networks, Inc."
--     CONTACT-INFO    
--             "   Customer Support    
--              Sonus Networks, Inc.
--              7 Technology Park Drive
--              Westford, MA 01886
--              USA
--              
--              Tel: 978-614-8100
--              Fax: 978-614-8609"
--     DESCRIPTION     
--             "The MIB Module for Physical Alarm Contacts management."
--     ::= { sonusSystemMIBs 6 }


sonusAlarmManagerMIBObjects OBJECT IDENTIFIER
    ::= { sonusAlarmManagerMIB 1 }

sonusAlarmOutAdmnTable OBJECT-TYPE
    SYNTAX          SEQUENCE OF SonusAlarmOutAdmnEntry
    ACCESS          not-accessible
    STATUS          mandatory
    DESCRIPTION     
            "  "
    ::= { sonusAlarmManagerMIBObjects 1 }

sonusAlarmOutAdmnEntry OBJECT-TYPE
    SYNTAX          SonusAlarmOutAdmnEntry
    ACCESS          not-accessible
    STATUS          mandatory
    DESCRIPTION     
            "  "
    INDEX           { sonusAlarmOutAdmnShelfIndex, 
                      sonusAlarmOutAdmnRelayIndex }
    ::= { sonusAlarmOutAdmnTable 1 }

SonusAlarmOutAdmnEntry ::=
    SEQUENCE {
        sonusAlarmOutAdmnShelfIndex     SonusShelfIndex,
        sonusAlarmOutAdmnRelayIndex     INTEGER,
        sonusAlarmOutAdmnOperState      SonusAdminState,
        sonusAlarmOutAdmnValue          INTEGER,
        sonusAlarmOutAdmnSense          INTEGER,
        sonusAlarmOutAdmnStartDelay     INTEGER,
        sonusAlarmOutAdmnCutoff         INTEGER
    }

sonusAlarmOutAdmnShelfIndex OBJECT-TYPE
    SYNTAX          SonusShelfIndex
    ACCESS          read-only
    STATUS          mandatory
    DESCRIPTION     
            " Identifies the target shelf within the node. "
    ::= { sonusAlarmOutAdmnEntry 1 }

sonusAlarmOutAdmnRelayIndex OBJECT-TYPE
    SYNTAX          INTEGER { shelfpwr-1(1), critical-2(2), major-3(3), 
                        minor-4(4), user-5(5), user-6(6) }
    ACCESS          read-only
    STATUS          mandatory
    DESCRIPTION     
            " Identifies the target outbound relay within the shelf. "
    ::= { sonusAlarmOutAdmnEntry 2 }

sonusAlarmOutAdmnOperState OBJECT-TYPE
    SYNTAX          SonusAdminState
    ACCESS          read-write
    STATUS          mandatory
    DESCRIPTION     
            " If enabled, the relay will respond to system events by opening and closing.
             
             If disabled, then it will be left in the default state of 'Clear',  
             where clear is relative to the 'sense' assigned to the relay. The default
             sense is Normal, which means a closed relay is considered in the alarm state."
    DEFVAL          { enabled }
    ::= { sonusAlarmOutAdmnEntry 3 }

sonusAlarmOutAdmnValue OBJECT-TYPE
    SYNTAX          INTEGER { clear(1), alarm(2) }
    ACCESS          read-write
    STATUS          mandatory
    DESCRIPTION     
            " Default value for the relays, either ALARM or CLEAR.
             
             Alarm contact five can be manually reconfigured. Alarm Contacts 1 thru 4  
             	  have a fixed default state of CLEAR, and cannot be manually reconfigured"
    DEFVAL          { clear }
    ::= { sonusAlarmOutAdmnEntry 4 }

sonusAlarmOutAdmnSense OBJECT-TYPE
    SYNTAX          INTEGER { normal(1), inverted(2) }
    ACCESS          read-write
    STATUS          mandatory
    DESCRIPTION     
            " Select NORMAL   if a CLOSED relay indicates an alarm condition.
             Select INVERTED if an OPEN  relay indicates an alarm condition."
    DEFVAL          { normal }
    ::= { sonusAlarmOutAdmnEntry 5 }

sonusAlarmOutAdmnStartDelay OBJECT-TYPE
    SYNTAX          INTEGER (0..300)
    ACCESS          read-write
    STATUS          mandatory
    DESCRIPTION     
            " Start Delay will hold the outbound relays in reset for the time period(seconds) specified.
             This is intended to mitigate nuisance alarms when a shelf is first started. "
    DEFVAL          { 120 }
    ::= { sonusAlarmOutAdmnEntry 6 }

sonusAlarmOutAdmnCutoff OBJECT-TYPE
    SYNTAX          INTEGER { true(1), false(2) }
    ACCESS          read-write
    STATUS          mandatory
    DESCRIPTION     
            " Cutoff will cause the outbound relay selected to be set to its 
             alarm clear state, relative to the relay 'sense' setting. This 
             allows the customer to disable an alarm after it has been set 
             by some system event. Cutoff is a one shot event, which does not 
             inhibit future additional alarms on that relay from occuring.
             
             Alarm Relays DO NOT automatically clear, and must be cleared 
             manually with this feature."
    DEFVAL          { false }
    ::= { sonusAlarmOutAdmnEntry 7 }

sonusAlarmOutStatTable OBJECT-TYPE
    SYNTAX          SEQUENCE OF SonusAlarmOutStatEntry
    ACCESS          not-accessible
    STATUS          mandatory
    DESCRIPTION     
            "  This table describes the current status of the outbound alarm relays "
    ::= { sonusAlarmManagerMIBObjects 2 }

sonusAlarmOutStatEntry OBJECT-TYPE
    SYNTAX          SonusAlarmOutStatEntry
    ACCESS          not-accessible
    STATUS          mandatory
    DESCRIPTION     
            "  "
    INDEX           { sonusAlarmOutStatShelfIndex, 
                      sonusAlarmOutStatRelayIndex }
    ::= { sonusAlarmOutStatTable 1 }

SonusAlarmOutStatEntry ::=
    SEQUENCE {
        sonusAlarmOutStatShelfIndex     SonusShelfIndex,
        sonusAlarmOutStatRelayIndex     INTEGER,
        sonusAlarmOutStatStatus         INTEGER,
        sonusAlarmOutStatStartDelay     SonusBoolean
    }

sonusAlarmOutStatShelfIndex OBJECT-TYPE
    SYNTAX          SonusShelfIndex
    ACCESS          read-only
    STATUS          mandatory
    DESCRIPTION     
            "  "
    ::= { sonusAlarmOutStatEntry 1 }

sonusAlarmOutStatRelayIndex OBJECT-TYPE
    SYNTAX          INTEGER { shelfpwr-1(1), critical-2(2), major-3(3), 
                        minor-4(4), user-5(5), user-6(6) }
    ACCESS          read-only
    STATUS          mandatory
    DESCRIPTION     
            "  "
    ::= { sonusAlarmOutStatEntry 2 }

sonusAlarmOutStatStatus OBJECT-TYPE
    SYNTAX          INTEGER { clear(1), alarm(2) }
    ACCESS          read-only
    STATUS          mandatory
    DESCRIPTION     
            " Indicates the operational status of the alarm relay contacts."
    ::= { sonusAlarmOutStatEntry 3 }

sonusAlarmOutStatStartDelay OBJECT-TYPE
    SYNTAX          SonusBoolean
    ACCESS          read-only
    STATUS          mandatory
    DESCRIPTION     
            " TRUE if the alarm contact is in Start Delay, FALSE otherwise.
             
             Start Delay is a programmable time period that when the Shelf boots, 
             alarm events will NOT trigger the corresponding alarm contact.
             
             It is intended to mitigate nuisance alarms when a shelf is first started."
    ::= { sonusAlarmOutStatEntry 4 }

sonusAlarmInStatTable OBJECT-TYPE
    SYNTAX          SEQUENCE OF SonusAlarmInStatEntry
    ACCESS          not-accessible
    STATUS          mandatory
    DESCRIPTION     
            "  This table describes the current status of the inbound alarm ports "
    ::= { sonusAlarmManagerMIBObjects 3 }

sonusAlarmInStatEntry OBJECT-TYPE
    SYNTAX          SonusAlarmInStatEntry
    ACCESS          not-accessible
    STATUS          mandatory
    DESCRIPTION     
            "  "
    INDEX           { sonusAlarmInStatShelfIndex, sonusAlarmInStatPort }
    ::= { sonusAlarmInStatTable 1 }

SonusAlarmInStatEntry ::=
    SEQUENCE {
        sonusAlarmInStatShelfIndex      SonusShelfIndex,
        sonusAlarmInStatPort            INTEGER,
        sonusAlarmInStatStatus          INTEGER
    }

sonusAlarmInStatShelfIndex OBJECT-TYPE
    SYNTAX          SonusShelfIndex
    ACCESS          read-only
    STATUS          mandatory
    DESCRIPTION     
            "  "
    ::= { sonusAlarmInStatEntry 1 }

sonusAlarmInStatPort OBJECT-TYPE
    SYNTAX          INTEGER (1..5)
    ACCESS          read-only
    STATUS          mandatory
    DESCRIPTION     
            "  "
    ::= { sonusAlarmInStatEntry 2 }

sonusAlarmInStatStatus OBJECT-TYPE
    SYNTAX          INTEGER { open(1), closed(2) }
    ACCESS          read-only
    STATUS          mandatory
    DESCRIPTION     
            " Indicates the operational status of the inbound alarm contacts."
    ::= { sonusAlarmInStatEntry 3 }

sonusAlarmManagerMIBNotifications OBJECT IDENTIFIER
    ::= { sonusAlarmManagerMIB 2 }

sonusAlarmManagerMIBNotificationsPrefix OBJECT IDENTIFIER
    ::= { sonusAlarmManagerMIBNotifications 0 }

sonusAlarmManagerMIBNotificationsObjects OBJECT IDENTIFIER
    ::= { sonusAlarmManagerMIBNotifications 1 }

sonusAlarmPortIndex OBJECT-TYPE
    SYNTAX          INTEGER
    ACCESS          read-only
    STATUS          mandatory
    DESCRIPTION     
            "Alarm IN port which has changed state."
    ::= { sonusAlarmManagerMIBNotificationsObjects 1 }

sonusAlarmPortState OBJECT-TYPE
    SYNTAX          INTEGER { open(1), closed(2) }
    ACCESS          read-only
    STATUS          mandatory
    DESCRIPTION     
            "The current state of the inbound alarm port. "
    ::= { sonusAlarmManagerMIBNotificationsObjects 2 }

sonusAlarmManagerInboundNotification TRAP-TYPE
    ENTERPRISE      sonusAlarmManagerMIBNotifications
    VARIABLES       { sonusShelfIndex, sonusAlarmPortIndex, 
                      sonusAlarmPortState, sonusEventDescription, 
                      sonusEventClass, sonusEventLevel, sonusSequenceId, 
                      sonusEventTime }
--     STATUS          mandatory
    DESCRIPTION     
            "This trap indicates that a change of state has occured on the inbound alarm port"
    ::= 1

END -- end of module SONUS-ALARM-CONTACT-MIB.
