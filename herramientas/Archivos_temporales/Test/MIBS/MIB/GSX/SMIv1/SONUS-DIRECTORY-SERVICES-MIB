--
-- This SMIv1 module has been generated by smidump 0.2-cvs. Do not edit.
--

SONUS-DIRECTORY-SERVICES-MIB DEFINITIONS ::= BEGIN

IMPORTS
    OBJECT-TYPE
        FROM RFC-1212
    TRAP-TYPE
        FROM RFC-1215
    RowStatus
        FROM SNMPv2-TC
    sonusEventClass, sonusEventDescription, sonusEventLevel, 
    sonusEventTime, sonusPortIndex, sonusSequenceId, sonusShelfIndex, 
    sonusSlotIndex
        FROM SONUS-COMMON-MIB
    sonusServicesMIBs
        FROM SONUS-SMI
    SonusName, SonusSlotIndex
        FROM SONUS-TC;

sonusDirectoryServicesMIB OBJECT IDENTIFIER
    ::= { sonusServicesMIBs 1 }

-- sonusDirectoryServicesMIB MODULE-IDENTITY
--     LAST-UPDATED    "200910300000Z"
--     ORGANIZATION    
--             "Sonus Networks, Inc."
--     CONTACT-INFO    
--             "   Customer Support    
--              Sonus Networks, Inc.
--              7 Technology Park Drive
--              Westford, MA 01886
--              USA
--              
--              Tel: 978-614-8100
--              Fax: 978-614-8609"
--     DESCRIPTION     
--             "The MIB Module for Directory Services Management."
--     ::= { sonusServicesMIBs 1 }


sonusDirectoryServicesMIBObjects OBJECT IDENTIFIER
    ::= { sonusDirectoryServicesMIB 1 }

sonusRouteObjects OBJECT IDENTIFIER
    ::= { sonusDirectoryServicesMIBObjects 1 }

sonusRouteNameObjects OBJECT IDENTIFIER
    ::= { sonusRouteObjects 1 }

sonusDsRouteNameNextIndex OBJECT-TYPE
    SYNTAX          INTEGER
    ACCESS          read-only
    STATUS          mandatory
    DESCRIPTION     
            "The next valid index to use when creating a new sonusDsRouteNameEntry"
    ::= { sonusRouteNameObjects 1 }

sonusDsRouteNameTable OBJECT-TYPE
    SYNTAX          SEQUENCE OF SonusDsRouteNameEntry
    ACCESS          not-accessible
    STATUS          mandatory
    DESCRIPTION     
            "Each route name can be associated with up to 4 routes.
             Each route is comprised of 3 elements, namely the
             gateway name, gateway's trunk group name and the trunk
             group's attributes.  The routes are ordered in terms
             of preferences."
    ::= { sonusRouteNameObjects 2 }

sonusDsRouteNameEntry OBJECT-TYPE
    SYNTAX          SonusDsRouteNameEntry
    ACCESS          not-accessible
    STATUS          mandatory
    DESCRIPTION     
            "A route name entry containing the following 
             configuration objects.  "
    INDEX           { sonusDsNameRouteTableIndex, sonusDsRouteNameIndex }
    ::= { sonusDsRouteNameTable 1 }

SonusDsRouteNameEntry ::=
    SEQUENCE {
        sonusDsNameRouteTableIndex      INTEGER,
        sonusDsRouteNameIndex           INTEGER,
        sonusDsRouteName                DisplayString,
        sonusDsRoute1TgName             DisplayString,
        sonusDsRoute2TgName             DisplayString,
        sonusDsRoute3TgName             DisplayString,
        sonusDsRoute4TgName             DisplayString,
        sonusDsRouteNameAdminState      INTEGER,
        sonusDsRouteNameRowStatus       RowStatus,
        sonusDsSignalingTonePackageId   INTEGER
    }

sonusDsNameRouteTableIndex OBJECT-TYPE
    SYNTAX          INTEGER
    ACCESS          read-only
    STATUS          mandatory
    DESCRIPTION     
            "A unique value for a route table entry."
    ::= { sonusDsRouteNameEntry 1 }

sonusDsRouteNameIndex OBJECT-TYPE
    SYNTAX          INTEGER
    ACCESS          read-only
    STATUS          mandatory
    DESCRIPTION     
            "A unique value for each Route Name entry."
    ::= { sonusDsRouteNameEntry 2 }

sonusDsRouteName OBJECT-TYPE
    SYNTAX          DisplayString (SIZE(0..23))
    ACCESS          read-write
    STATUS          mandatory
    DESCRIPTION     
            "Destination Route name for the following routes."
    ::= { sonusDsRouteNameEntry 3 }

sonusDsRoute1TgName OBJECT-TYPE
    SYNTAX          DisplayString (SIZE(0..23))
    ACCESS          read-write
    STATUS          mandatory
    DESCRIPTION     
            "Route1's trunk group name"
    ::= { sonusDsRouteNameEntry 4 }

sonusDsRoute2TgName OBJECT-TYPE
    SYNTAX          DisplayString (SIZE(0..23))
    ACCESS          read-write
    STATUS          mandatory
    DESCRIPTION     
            "Route2's trunk group name"
    ::= { sonusDsRouteNameEntry 5 }

sonusDsRoute3TgName OBJECT-TYPE
    SYNTAX          DisplayString (SIZE(0..23))
    ACCESS          read-write
    STATUS          mandatory
    DESCRIPTION     
            "Route3's trunk group name"
    ::= { sonusDsRouteNameEntry 6 }

sonusDsRoute4TgName OBJECT-TYPE
    SYNTAX          DisplayString (SIZE(0..23))
    ACCESS          read-write
    STATUS          mandatory
    DESCRIPTION     
            "Route4's trunk group name"
    ::= { sonusDsRouteNameEntry 7 }

sonusDsRouteNameAdminState OBJECT-TYPE
    SYNTAX          INTEGER { disabled(1), enabled(2) }
    ACCESS          read-write
    STATUS          mandatory
    DESCRIPTION     
            "The requested state of the given route name."
    DEFVAL          { disabled }
    ::= { sonusDsRouteNameEntry 8 }

sonusDsRouteNameRowStatus OBJECT-TYPE
    SYNTAX          RowStatus
    ACCESS          read-write
    STATUS          mandatory
    DESCRIPTION     
            "This is for SNMP use."
    ::= { sonusDsRouteNameEntry 9 }

sonusDsSignalingTonePackageId OBJECT-TYPE
    SYNTAX          INTEGER (0..65535)
    ACCESS          read-write
    STATUS          mandatory
    DESCRIPTION     
            "Local Ring Back Tone configuration: This is Tone
             Package Id that is configured for each tone package"
    ::= { sonusDsRouteNameEntry 10 }

sonusRouteTableObjects OBJECT IDENTIFIER
    ::= { sonusRouteObjects 2 }

sonusDsRouteTableNextIndex OBJECT-TYPE
    SYNTAX          INTEGER
    ACCESS          read-only
    STATUS          mandatory
    DESCRIPTION     
            "The next valid index to use when creating a new sonusDsRouteTableEntry"
    ::= { sonusRouteTableObjects 1 }

sonusDsRouteTable OBJECT-TYPE
    SYNTAX          SEQUENCE OF SonusDsRouteTableEntry
    ACCESS          not-accessible
    STATUS          mandatory
    DESCRIPTION     
            "Characteristicss of a route table."
    ::= { sonusRouteTableObjects 2 }

sonusDsRouteTableEntry OBJECT-TYPE
    SYNTAX          SonusDsRouteTableEntry
    ACCESS          not-accessible
    STATUS          mandatory
    DESCRIPTION     
            "A route table entry containing the following 
             configuration objects.  "
    INDEX           { sonusDsRouteTableIndex }
    ::= { sonusDsRouteTable 1 }

SonusDsRouteTableEntry ::=
    SEQUENCE {
        sonusDsRouteTableIndex          INTEGER,
        sonusDsRouteTableName           SonusName,
        sonusDsRouteTableType           INTEGER,
        sonusDsMaxDigits                INTEGER,
        sonusDsMaxRoutes                INTEGER,
        sonusDsTableCountryCode         DisplayString,
        sonusDsRouteTableAdminState     INTEGER,
        sonusDsRouteTableRowStatus      RowStatus
    }

sonusDsRouteTableIndex OBJECT-TYPE
    SYNTAX          INTEGER
    ACCESS          read-only
    STATUS          mandatory
    DESCRIPTION     
            "A unique value for each route table entry. "
    ::= { sonusDsRouteTableEntry 1 }

sonusDsRouteTableName OBJECT-TYPE
    SYNTAX          SonusName
    ACCESS          read-write
    STATUS          mandatory
    DESCRIPTION     
            "The name of this route table"
    ::= { sonusDsRouteTableEntry 2 }

sonusDsRouteTableType OBJECT-TYPE
    SYNTAX          INTEGER { local(1), remote(2) }
    ACCESS          read-write
    STATUS          mandatory
    DESCRIPTION     
            "Route table type specifies the format of the route table."
    DEFVAL          { local }
    ::= { sonusDsRouteTableEntry 3 }

sonusDsMaxDigits OBJECT-TYPE
    SYNTAX          INTEGER (1..12)
    ACCESS          read-write
    STATUS          mandatory
    DESCRIPTION     
            "A maximum of digits that is used for the look-up."
    DEFVAL          { 12 }
    ::= { sonusDsRouteTableEntry 4 }

sonusDsMaxRoutes OBJECT-TYPE
    SYNTAX          INTEGER (1..4)
    ACCESS          read-write
    STATUS          mandatory
    DESCRIPTION     
            "A maximum of 4 routes are allowed per route name
             entry in the route table."
    DEFVAL          { 4 }
    ::= { sonusDsRouteTableEntry 5 }

sonusDsTableCountryCode OBJECT-TYPE
    SYNTAX          DisplayString (SIZE(1..3))
    ACCESS          read-write
    STATUS          mandatory
    DESCRIPTION     
            "Country code portion of phone number address entry "
    ::= { sonusDsRouteTableEntry 6 }

sonusDsRouteTableAdminState OBJECT-TYPE
    SYNTAX          INTEGER { disabled(1), enabled(2) }
    ACCESS          read-write
    STATUS          mandatory
    DESCRIPTION     
            "The requested state of the given route table."
    DEFVAL          { disabled }
    ::= { sonusDsRouteTableEntry 7 }

sonusDsRouteTableRowStatus OBJECT-TYPE
    SYNTAX          RowStatus
    ACCESS          read-write
    STATUS          mandatory
    DESCRIPTION     
            "This is for SNMP use."
    ::= { sonusDsRouteTableEntry 8 }

sonusRouteAddressObjects OBJECT IDENTIFIER
    ::= { sonusRouteObjects 3 }

sonusDsAddressRouteTable OBJECT-TYPE
    SYNTAX          SEQUENCE OF SonusDsAddressRouteEntry
    ACCESS          not-accessible
    STATUS          mandatory
    DESCRIPTION     
            "Each phone number has a corresponding route name in a specific
             route table."
    ::= { sonusRouteAddressObjects 1 }

sonusDsAddressRouteEntry OBJECT-TYPE
    SYNTAX          SonusDsAddressRouteEntry
    ACCESS          not-accessible
    STATUS          mandatory
    DESCRIPTION     
            "A Route address entry containing the following 
             configuration objects.  "
    INDEX           { sonusDsAddressRouteTableIndex, 
                      sonusDsAddressRouteIndex }
    ::= { sonusDsAddressRouteTable 1 }

SonusDsAddressRouteEntry ::=
    SEQUENCE {
        sonusDsAddressRouteTableIndex   INTEGER,
        sonusDsAddressRouteIndex        INTEGER,
        sonusDsAddressCountryCode       DisplayString,
        sonusDsAddress                  DisplayString,
        sonusDsAddressRouteName         DisplayString,
        sonusDsAddressRouteAdminState   INTEGER,
        sonusDsAddressRouteRowStatus    RowStatus
    }

sonusDsAddressRouteTableIndex OBJECT-TYPE
    SYNTAX          INTEGER
    ACCESS          read-only
    STATUS          mandatory
    DESCRIPTION     
            "A unique route table entry. "
    ::= { sonusDsAddressRouteEntry 1 }

sonusDsAddressRouteIndex OBJECT-TYPE
    SYNTAX          INTEGER
    ACCESS          read-only
    STATUS          mandatory
    DESCRIPTION     
            "A unique value for each phone number address entry. "
    ::= { sonusDsAddressRouteEntry 2 }

sonusDsAddressCountryCode OBJECT-TYPE
    SYNTAX          DisplayString (SIZE(0..3))
    ACCESS          read-write
    STATUS          mandatory
    DESCRIPTION     
            "Country code portion of phone number address entry "
    ::= { sonusDsAddressRouteEntry 3 }

sonusDsAddress OBJECT-TYPE
    SYNTAX          DisplayString (SIZE(1..12))
    ACCESS          read-write
    STATUS          mandatory
    DESCRIPTION     
            "Phone number address entry "
    ::= { sonusDsAddressRouteEntry 4 }

sonusDsAddressRouteName OBJECT-TYPE
    SYNTAX          DisplayString (SIZE(0..23))
    ACCESS          read-write
    STATUS          mandatory
    DESCRIPTION     
            "Route Name for this phone number. "
    ::= { sonusDsAddressRouteEntry 5 }

sonusDsAddressRouteAdminState OBJECT-TYPE
    SYNTAX          INTEGER { disabled(1), enabled(2) }
    ACCESS          read-write
    STATUS          mandatory
    DESCRIPTION     
            "The requested state of the given route table."
    DEFVAL          { disabled }
    ::= { sonusDsAddressRouteEntry 6 }

sonusDsAddressRouteRowStatus OBJECT-TYPE
    SYNTAX          RowStatus
    ACCESS          read-write
    STATUS          mandatory
    DESCRIPTION     
            "This is for SNMP use."
    ::= { sonusDsAddressRouteEntry 7 }

sonusDestinationTrunkObjects OBJECT IDENTIFIER
    ::= { sonusRouteObjects 4 }

sonusDsDestTgNextIndex OBJECT-TYPE
    SYNTAX          INTEGER
    ACCESS          read-only
    STATUS          mandatory
    DESCRIPTION     
            "The next valid index to use when creating a new sonusDsDestTgEntry"
    ::= { sonusDestinationTrunkObjects 1 }

sonusDsDestTgTable OBJECT-TYPE
    SYNTAX          SEQUENCE OF SonusDsDestTgEntry
    ACCESS          not-accessible
    STATUS          mandatory
    DESCRIPTION     
            "Each Destination Trunk group has both a set of trunk group
             attributes and a corresponding gateway name"
    ::= { sonusDestinationTrunkObjects 2 }

sonusDsDestTgEntry OBJECT-TYPE
    SYNTAX          SonusDsDestTgEntry
    ACCESS          not-accessible
    STATUS          mandatory
    DESCRIPTION     
            "A destination trunk group entry containing the following 
             configuration objects.  "
    INDEX           { sonusDsDestTgIndex }
    ::= { sonusDsDestTgTable 1 }

SonusDsDestTgEntry ::=
    SEQUENCE {
        sonusDsDestTgIndex              INTEGER,
        sonusDsDestTgName               SonusName,
        sonusDsDestTrunk                INTEGER,
        sonusDsDestTgSignaling          INTEGER,
        sonusDsDestGwName               DisplayString,
        sonusDsDestCarrier              DisplayString,
        sonusDsDestTgAdminState         INTEGER,
        sonusDsDestTgRowStatus          RowStatus
    }

sonusDsDestTgIndex OBJECT-TYPE
    SYNTAX          INTEGER
    ACCESS          read-only
    STATUS          mandatory
    DESCRIPTION     
            "A unique value for each destination trunk group entry. "
    ::= { sonusDsDestTgEntry 1 }

sonusDsDestTgName OBJECT-TYPE
    SYNTAX          SonusName
    ACCESS          read-write
    STATUS          mandatory
    DESCRIPTION     
            "The name of this destination trunk group"
    ::= { sonusDsDestTgEntry 2 }

sonusDsDestTrunk OBJECT-TYPE
    SYNTAX          INTEGER { unres(1), res(2) }
    ACCESS          read-write
    STATUS          mandatory
    DESCRIPTION     
            "Bearer transfer rate attribute of this trunk group. Unrestricted is 64KB
             and restricted is 56KB.  "
    ::= { sonusDsDestTgEntry 3 }

sonusDsDestTgSignaling OBJECT-TYPE
    SYNTAX          INTEGER { isup(1), isdn(2), cas(3) }
    ACCESS          read-write
    STATUS          mandatory
    DESCRIPTION     
            "Signaling protocol attribute of this trunk group.  "
    ::= { sonusDsDestTgEntry 4 }

sonusDsDestGwName OBJECT-TYPE
    SYNTAX          DisplayString (SIZE(0..23))
    ACCESS          read-write
    STATUS          mandatory
    DESCRIPTION     
            "The name of the gateway that is assigned to this destination trunk 
             group. "
    ::= { sonusDsDestTgEntry 5 }

sonusDsDestCarrier OBJECT-TYPE
    SYNTAX          DisplayString (SIZE(0..23))
    ACCESS          read-write
    STATUS          mandatory
    DESCRIPTION     
            "The name of the carrier that is assigned to this destination trunk 
             group. "
    ::= { sonusDsDestTgEntry 6 }

sonusDsDestTgAdminState OBJECT-TYPE
    SYNTAX          INTEGER { disabled(1), enabled(2) }
    ACCESS          read-write
    STATUS          mandatory
    DESCRIPTION     
            "The requested state of the given route table."
    DEFVAL          { disabled }
    ::= { sonusDsDestTgEntry 7 }

sonusDsDestTgRowStatus OBJECT-TYPE
    SYNTAX          RowStatus
    ACCESS          read-write
    STATUS          mandatory
    DESCRIPTION     
            "This is for SNMP use."
    ::= { sonusDsDestTgEntry 8 }

sonusRouteStatusObjects OBJECT IDENTIFIER
    ::= { sonusRouteObjects 5 }

sonusUnknownRoutes OBJECT-TYPE
    SYNTAX          INTEGER
    ACCESS          read-write
    STATUS          mandatory
    DESCRIPTION     
            "Number of unresolved directory service route look up since
             the last reset."
    ::= { sonusRouteStatusObjects 1 }

sonusDirectoryConfigObjects OBJECT IDENTIFIER
    ::= { sonusDirectoryServicesMIBObjects 2 }

sonusDsCountryCode OBJECT-TYPE
    SYNTAX          DisplayString (SIZE(1..3))
    ACCESS          read-write
    STATUS          mandatory
    DESCRIPTION     
            "Country code for this gateway."
    ::= { sonusDirectoryConfigObjects 1 }

sonusDsMaxRemoteTg OBJECT-TYPE
    SYNTAX          INTEGER (1..5000)
    ACCESS          read-write
    STATUS          mandatory
    DESCRIPTION     
            "Maximum allowable destination or remote trunk groups per gateway."
    DEFVAL          { 5000 }
    ::= { sonusDirectoryConfigObjects 2 }

sonusDsMaxRouteNames OBJECT-TYPE
    SYNTAX          INTEGER (1..20000)
    ACCESS          read-write
    STATUS          mandatory
    DESCRIPTION     
            "Maximum allowable routenames per route table."
    DEFVAL          { 20000 }
    ::= { sonusDirectoryConfigObjects 3 }

sonusDsAccess OBJECT-TYPE
    SYNTAX          INTEGER { internal(1), external(2), local(3), 
                        hybrid(4), fallback(5) }
    ACCESS          read-write
    STATUS          mandatory
    DESCRIPTION     
            "Directory services access for policy query:
             internal - lab use only
             external - PSX based
             local    - GSX based."
    DEFVAL          { external }
    ::= { sonusDirectoryConfigObjects 4 }

sonusDsMaxTables OBJECT-TYPE
    SYNTAX          INTEGER (1..12)
    ACCESS          read-write
    STATUS          mandatory
    DESCRIPTION     
            "Maximum route table for this gateway."
    DEFVAL          { 6 }
    ::= { sonusDirectoryConfigObjects 5 }

sonusDsMaxAddresses OBJECT-TYPE
    SYNTAX          INTEGER (1..10000)
    ACCESS          read-write
    STATUS          mandatory
    DESCRIPTION     
            "Maximum address routes per route table for this gateway."
    DEFVAL          { 10000 }
    ::= { sonusDirectoryConfigObjects 6 }

sonusDsMaxTollFreePrefixes OBJECT-TYPE
    SYNTAX          INTEGER (1..100)
    ACCESS          read-write
    STATUS          mandatory
    DESCRIPTION     
            "Maximum toll free prefixes for this gateway."
    DEFVAL          { 100 }
    ::= { sonusDirectoryConfigObjects 7 }

sonusDsLevel1ScriptCacheSize OBJECT-TYPE
    SYNTAX          INTEGER (8..2048)
    ACCESS          read-write
    STATUS          mandatory
    DESCRIPTION     
            "Level 1 script cache size is in units of 1024 bytes. Level 1 cache size should be larger
             than Level 2 cache size. "
    DEFVAL          { 1024 }
    ::= { sonusDirectoryConfigObjects 8 }

sonusDsLevel2ScriptCacheSize OBJECT-TYPE
    SYNTAX          INTEGER (8..1024)
    ACCESS          read-write
    STATUS          mandatory
    DESCRIPTION     
            "Level 2 script cache size is in units of 1024 bytes. Level 1 cache size should be larger
             than Level 2 cache size. "
    DEFVAL          { 256 }
    ::= { sonusDirectoryConfigObjects 9 }

sonusDsTimeOutDuration OBJECT-TYPE
    SYNTAX          INTEGER (0..3600)
    ACCESS          read-write
    STATUS          mandatory
    DESCRIPTION     
            " DS Timeout Duration timer "
    DEFVAL          { 60 }
    ::= { sonusDirectoryConfigObjects 10 }

sonusDsAutoRevertTimer OBJECT-TYPE
    SYNTAX          INTEGER (0..3600)
    ACCESS          read-write
    STATUS          mandatory
    DESCRIPTION     
            " Auto revert timer "
    DEFVAL          { 60 }
    ::= { sonusDirectoryConfigObjects 11 }

sonusDsAccessSwitchback OBJECT-TYPE
    SYNTAX          INTEGER { manual(1), automatic(2) }
    ACCESS          read-write
    STATUS          mandatory
    DESCRIPTION     
            "Directory services access : Switchback manual/automatic"
    DEFVAL          { manual }
    ::= { sonusDirectoryConfigObjects 12 }

sonusDsAccessSwitchOperState OBJECT-TYPE
    SYNTAX          INTEGER { external(1), local(2) }
    ACCESS          read-write
    STATUS          mandatory
    DESCRIPTION     
            "Directory services access : Switchback Mode"
    DEFVAL          { external }
    ::= { sonusDirectoryConfigObjects 13 }

sonusDsReQueryPolicyServer OBJECT-TYPE
    SYNTAX          INTEGER { disabled(1), enabled(2) }
    ACCESS          read-write
    STATUS          mandatory
    DESCRIPTION     
            "If flag is set, Policy server is requeried
             (in 8.0 only PSX can be requeried)
             "
    DEFVAL          { disabled }
    ::= { sonusDirectoryConfigObjects 14 }

sonusTollFreeObjects OBJECT IDENTIFIER
    ::= { sonusDirectoryServicesMIBObjects 3 }

sonusDsTollFreeNpaTable OBJECT-TYPE
    SYNTAX          SEQUENCE OF SonusDsTollFreeNpaEntry
    ACCESS          not-accessible
    STATUS          mandatory
    DESCRIPTION     
            "This is a table containing a list of toll free NPAs for
             look up in the SCP."
    ::= { sonusTollFreeObjects 1 }

sonusDsTollFreeNpaEntry OBJECT-TYPE
    SYNTAX          SonusDsTollFreeNpaEntry
    ACCESS          not-accessible
    STATUS          mandatory
    DESCRIPTION     
            "Each entry lists a toll free NPA"
    INDEX           { sonusDsTollFreeNpaIndex }
    ::= { sonusDsTollFreeNpaTable 1 }

SonusDsTollFreeNpaEntry ::=
    SEQUENCE {
        sonusDsTollFreeNpaIndex         INTEGER,
        sonusDsTollFreeNpaNumber        DisplayString,
        sonusDsTollFreeNpaAdminState    INTEGER,
        sonusDsTollFreeNpaRowStatus     RowStatus
    }

sonusDsTollFreeNpaIndex OBJECT-TYPE
    SYNTAX          INTEGER
    ACCESS          read-only
    STATUS          mandatory
    DESCRIPTION     
            "A unique value for each route server between 1 and maximum 
             allowed. "
    ::= { sonusDsTollFreeNpaEntry 1 }

sonusDsTollFreeNpaNumber OBJECT-TYPE
    SYNTAX          DisplayString (SIZE(1..4))
    ACCESS          read-write
    STATUS          mandatory
    DESCRIPTION     
            "This is NPA or toll free prefix."
    ::= { sonusDsTollFreeNpaEntry 2 }

sonusDsTollFreeNpaAdminState OBJECT-TYPE
    SYNTAX          INTEGER { disabled(1), enabled(2) }
    ACCESS          read-write
    STATUS          mandatory
    DESCRIPTION     
            "Allow administrator to disable or enable the use of this NPA for a look up."
    DEFVAL          { disabled }
    ::= { sonusDsTollFreeNpaEntry 3 }

sonusDsTollFreeNpaRowStatus OBJECT-TYPE
    SYNTAX          RowStatus
    ACCESS          read-write
    STATUS          mandatory
    DESCRIPTION     
            "This is for SNMP use."
    ::= { sonusDsTollFreeNpaEntry 4 }

sonusScriptCacheObjects OBJECT IDENTIFIER
    ::= { sonusDirectoryServicesMIBObjects 4 }

sonusScriptCacheStatusTable OBJECT-TYPE
    SYNTAX          SEQUENCE OF SonusScriptCacheStatusEntry
    ACCESS          not-accessible
    STATUS          mandatory
    DESCRIPTION     
            "This table contains status information of script caching.
             Level1 cache is located in slot 1 & slot 2 (MNS).
             Level2 cache is located in any other slots (CNS)."
    ::= { sonusScriptCacheObjects 1 }

sonusScriptCacheStatusEntry OBJECT-TYPE
    SYNTAX          SonusScriptCacheStatusEntry
    ACCESS          not-accessible
    STATUS          mandatory
    DESCRIPTION     
            "Each entry describes the current server cache status."
    INDEX           { sonusScriptCacheStatusIndex }
    ::= { sonusScriptCacheStatusTable 1 }

SonusScriptCacheStatusEntry ::=
    SEQUENCE {
        sonusScriptCacheStatusIndex     SonusSlotIndex,
        sonusScriptCacheSizeAllowed     INTEGER,
        sonusScriptCacheOccupied        INTEGER,
        sonusScriptCacheInUse           INTEGER,
        sonusScriptCacheType            INTEGER
    }

sonusScriptCacheStatusIndex OBJECT-TYPE
    SYNTAX          SonusSlotIndex
    ACCESS          read-only
    STATUS          mandatory
    DESCRIPTION     
            "Chassis slot value between 1 and 16."
    ::= { sonusScriptCacheStatusEntry 1 }

sonusScriptCacheSizeAllowed OBJECT-TYPE
    SYNTAX          INTEGER
    ACCESS          read-only
    STATUS          mandatory
    DESCRIPTION     
            "Current script cache size in bytes allowed for caching scripts."
    ::= { sonusScriptCacheStatusEntry 2 }

sonusScriptCacheOccupied OBJECT-TYPE
    SYNTAX          INTEGER
    ACCESS          read-only
    STATUS          mandatory
    DESCRIPTION     
            "Current bytes of cache occupied by loaded scripts."
    ::= { sonusScriptCacheStatusEntry 3 }

sonusScriptCacheInUse OBJECT-TYPE
    SYNTAX          INTEGER
    ACCESS          read-only
    STATUS          mandatory
    DESCRIPTION     
            "Current bytes that are in use and cannot be removed to accept another script for caching."
    ::= { sonusScriptCacheStatusEntry 4 }

sonusScriptCacheType OBJECT-TYPE
    SYNTAX          INTEGER { level1(1), level2(2) }
    ACCESS          read-only
    STATUS          mandatory
    DESCRIPTION     
            "Type of script cache."
    ::= { sonusScriptCacheStatusEntry 5 }

sonusDirectoryServicesStatusObjects OBJECT IDENTIFIER
    ::= { sonusDirectoryServicesMIBObjects 5 }

sonusDsStatusOperState OBJECT-TYPE
    SYNTAX          INTEGER { external(1), local(2), hybrid(3) }
    ACCESS          read-write
    STATUS          mandatory
    DESCRIPTION     
            "Directory services operational state"
    DEFVAL          { external }
    ::= { sonusDirectoryServicesStatusObjects 1 }

sonusDirectoryServiceMIBNotifications OBJECT IDENTIFIER
    ::= { sonusDirectoryServicesMIB 2 }

sonusDirectoryServiceMIBNotificationsPrefix OBJECT IDENTIFIER
    ::= { sonusDirectoryServiceMIBNotifications 0 }

sonusDirectoryServiceMMIBNotificationsObjects OBJECT IDENTIFIER
    ::= { sonusDirectoryServiceMIBNotifications 1 }

sonusDirectoryServiceStateNotification TRAP-TYPE
    ENTERPRISE      sonusDirectoryServiceMIBNotifications
    VARIABLES       { sonusDsStatusOperState, sonusEventDescription, 
                      sonusEventClass, sonusEventLevel, sonusSequenceId, 
                      sonusEventTime }
--     STATUS          mandatory
    DESCRIPTION     
            "This trap indicates a change in DS operational state"
    ::= 1

END -- end of module SONUS-DIRECTORY-SERVICES-MIB.
