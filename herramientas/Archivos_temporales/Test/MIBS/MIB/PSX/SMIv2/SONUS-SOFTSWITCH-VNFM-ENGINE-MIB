--
-- This SMIv2 module has been generated by smidump 0.2-cvs. Do not edit.
--

SONUS-SOFTSWITCH-VNFM-ENGINE-MIB DEFINITIONS ::= BEGIN

IMPORTS
    Integer32, MODULE-IDENTITY, NOTIFICATION-TYPE, OBJECT-TYPE
        FROM SNMPv2-SMI
    sonusEventClass, sonusEventDescription, sonusEventLevel, 
    sonusEventTime
        FROM SONUS-COMMON-MIB
    sonusServicesMIBs
        FROM SONUS-SMI;

sonusSoftSwitchVNFMEngineMIB MODULE-IDENTITY
    LAST-UPDATED    "201806010000Z"
    ORGANIZATION    
            "Sonus Networks, Inc."
    CONTACT-INFO    
            "   Customer Support    
             Sonus Networks, Inc.
             250 Apollo Drive
             Chelmsford, MA 01824
             USA
             
             Tel: 978-614-8100
             Fax: 978-614-8609"
    DESCRIPTION     
            "The MIB Module for SoftSwitch VNFM Engine Management."
    ::= { sonusServicesMIBs 46 }


sonusSoftSwitchVNFMEngineMIBObjects OBJECT IDENTIFIER
    ::= { sonusSoftSwitchVNFMEngineMIB 1 }

sonusSoftSwitchVNFMEngineMIBNotifications OBJECT IDENTIFIER
    ::= { sonusSoftSwitchVNFMEngineMIB 2 }

sonusSoftSwitchVNFMEngineMIBNotificationsPrefix OBJECT IDENTIFIER
    ::= { sonusSoftSwitchVNFMEngineMIBNotifications 0 }

sonusSoftSwitchVnfmUpNotification NOTIFICATION-TYPE
    OBJECTS         { sonusEventDescription, sonusEventClass, 
                      sonusEventLevel, sonusEventTime }
    STATUS          current
    DESCRIPTION     
            "SoftSwitch VNFM Engine is up."
    ::= { sonusSoftSwitchVNFMEngineMIBNotificationsPrefix 1 }

sonusSoftSwitchVnfmDownNotification NOTIFICATION-TYPE
    OBJECTS         { sonusEventDescription, sonusEventClass, 
                      sonusEventLevel, sonusEventTime }
    STATUS          current
    DESCRIPTION     
            "SoftSwitch VNFM Engine is down."
    ::= { sonusSoftSwitchVNFMEngineMIBNotificationsPrefix 2 }

sonusSoftSwitchVnfmHeartbeatLostNotification NOTIFICATION-TYPE
    OBJECTS         { sonusEventDescription, sonusEventClass, 
                      sonusEventLevel, sonusEventTime }
    STATUS          current
    DESCRIPTION     
            "SoftSwitch VNFM Engine lost heartbeat to VNFM."
    ::= { sonusSoftSwitchVNFMEngineMIBNotificationsPrefix 3 }

sonusSoftSwitchVnfmHeartbeatRecoveredNotification NOTIFICATION-TYPE
    OBJECTS         { sonusEventDescription, sonusEventClass, 
                      sonusEventLevel, sonusEventTime }
    STATUS          current
    DESCRIPTION     
            "SoftSwitch VNFM Engine recovered heartbeat to VNFM."
    ::= { sonusSoftSwitchVNFMEngineMIBNotificationsPrefix 4 }

END -- end of module SONUS-SOFTSWITCH-VNFM-ENGINE-MIB.
