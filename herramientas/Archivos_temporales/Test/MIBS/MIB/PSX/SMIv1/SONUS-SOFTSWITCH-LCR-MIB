--
-- This SMIv1 module has been generated by smidump 0.2-cvs. Do not edit.
--

SONUS-SOFTSWITCH-LCR-MIB DEFINITIONS ::= BEGIN

IMPORTS
    TRAP-TYPE
        FROM RFC-1215
    sonusEventClass, sonusEventDescription, sonusEventLevel, 
    sonusEventTime
        FROM SONUS-COMMON-MIB
    sonusServicesMIBs
        FROM SONUS-SMI;

sonusSoftSwitchLcrMIB OBJECT IDENTIFIER
    ::= { sonusServicesMIBs 40 }

-- sonusSoftSwitchLcrMIB MODULE-IDENTITY
--     LAST-UPDATED    "200205030000Z"
--     ORGANIZATION    
--             "Sonus Networks, Inc."
--     CONTACT-INFO    
--             "   Customer Support    
--              Sonus Networks, Inc.
--              4 Technology Park Drive 
--              Westford, MA 01886
--              USA
--              
--              Tel: 978-614-8100
--              Fax: 978-614-8609"
--     DESCRIPTION     
--             "The MIB Module for SoftSwitch Database Replication Management."
--     ::= { sonusServicesMIBs 40 }


sonusSoftSwitchLcrMIBObjects OBJECT IDENTIFIER
    ::= { sonusSoftSwitchLcrMIB 1 }

sonusSoftSwitchLcrMIBNotifications OBJECT IDENTIFIER
    ::= { sonusSoftSwitchLcrMIB 2 }

sonusSoftSwitchLcrMIBNotificationsPrefix OBJECT IDENTIFIER
    ::= { sonusSoftSwitchLcrMIBNotifications 0 }

sonusSoftSwitchLcrMIBNotificationsObjects OBJECT IDENTIFIER
    ::= { sonusSoftSwitchLcrMIBNotifications 1 }

sonusSoftSwitchLcrKpiLoadFailedNotification TRAP-TYPE
    ENTERPRISE      sonusSoftSwitchLcrMIBNotifications
    VARIABLES       { sonusEventDescription, sonusEventClass, 
                      sonusEventLevel, sonusEventTime }
--     STATUS          mandatory
    DESCRIPTION     
            "The KPI loader tool encounters an error while loading."
    ::= 1

sonusSoftSwitchLcrKpiRetrievalFailedNotification TRAP-TYPE
    ENTERPRISE      sonusSoftSwitchLcrMIBNotifications
    VARIABLES       { sonusEventDescription, sonusEventClass, 
                      sonusEventLevel, sonusEventTime }
--     STATUS          mandatory
    DESCRIPTION     
            "The NetScore KPI pull utilities encounter an error."
    ::= 2

sonusSoftSwitchLcrCountryCapLoadFailedNotification TRAP-TYPE
    ENTERPRISE      sonusSoftSwitchLcrMIBNotifications
    VARIABLES       { sonusEventDescription, sonusEventClass, 
                      sonusEventLevel, sonusEventTime }
--     STATUS          mandatory
    DESCRIPTION     
            "Country Cap file load failed."
    ::= 3

sonusSoftSwitchLcrCountryCapRetrievalFailedNotification TRAP-TYPE
    ENTERPRISE      sonusSoftSwitchLcrMIBNotifications
    VARIABLES       { sonusEventDescription, sonusEventClass, 
                      sonusEventLevel, sonusEventTime }
--     STATUS          mandatory
    DESCRIPTION     
            "Country Cap file retrieval failed."
    ::= 4

sonusSoftSwitchLcrCountryCapReachedNotification TRAP-TYPE
    ENTERPRISE      sonusSoftSwitchLcrMIBNotifications
    VARIABLES       { sonusEventDescription, sonusEventClass, 
                      sonusEventLevel, sonusEventTime }
--     STATUS          mandatory
    DESCRIPTION     
            "Country Cap limit reached or exceeded."
    ::= 5

END -- end of module SONUS-SOFTSWITCH-LCR-MIB.
