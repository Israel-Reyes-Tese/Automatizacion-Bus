--
-- This SMIv2 module has been generated by smidump 0.2-cvs. Do not edit.
--

SONUS-SOFTSWITCH-DBREP-MIB DEFINITIONS ::= BEGIN

IMPORTS
    InetAddress, InetAddressType
        FROM INET-ADDRESS-MIB
    IpAddress, MODULE-IDENTITY, NOTIFICATION-TYPE, OBJECT-TYPE
        FROM SNMPv2-SMI
    sonusEventClass, sonusEventDescription, sonusEventLevel, 
    sonusEventTime
        FROM SONUS-COMMON-MIB
    sonusServicesMIBs
        FROM SONUS-SMI;

sonusSoftSwitchDbrepMIB MODULE-IDENTITY
    LAST-UPDATED    "200205030000Z"
    ORGANIZATION    
            "Sonus Networks, Inc."
    CONTACT-INFO    
            "   Customer Support    
             Sonus Networks, Inc.
             250 Apollo Drive
             Chelmsford, MA 01824
             USA
             
             Tel: 978-614-8100
             Fax: 978-614-8609"
    DESCRIPTION     
            "The MIB Module for SoftSwitch Database Replication Management."
    ::= { sonusServicesMIBs 16 }


sonusSoftSwitchDbrepMIBObjects OBJECT IDENTIFIER
    ::= { sonusSoftSwitchDbrepMIB 1 }

sonusSoftSwitchDbrepMIBNotifications OBJECT IDENTIFIER
    ::= { sonusSoftSwitchDbrepMIB 2 }

sonusSoftSwitchDbrepMIBNotificationsPrefix OBJECT IDENTIFIER
    ::= { sonusSoftSwitchDbrepMIBNotifications 0 }

sonusSoftSwitchDbrepMIBNotificationsObjects OBJECT IDENTIFIER
    ::= { sonusSoftSwitchDbrepMIBNotifications 1 }

sonusSoftSwitchDbrepPeerIp OBJECT-TYPE
    SYNTAX          IpAddress
    MAX-ACCESS      read-only
    STATUS          deprecated
    DESCRIPTION     
            "The IP address of the remote peer."
    ::= { sonusSoftSwitchDbrepMIBNotificationsObjects 1 }

sonusSoftSwitchDbrepPeerExtendedIpType OBJECT-TYPE
    SYNTAX          InetAddressType
    MAX-ACCESS      read-only
    STATUS          current
    DESCRIPTION     
            "The IP address type of the remote peer."
    ::= { sonusSoftSwitchDbrepMIBNotificationsObjects 2 }

sonusSoftSwitchDbrepPeerExtendedIp OBJECT-TYPE
    SYNTAX          InetAddress
    MAX-ACCESS      read-only
    STATUS          current
    DESCRIPTION     
            "The IP address of the remote peer."
    ::= { sonusSoftSwitchDbrepMIBNotificationsObjects 3 }

sonusSoftSwitchDbrepUpNotification NOTIFICATION-TYPE
    OBJECTS         { sonusEventDescription, sonusEventClass, 
                      sonusEventLevel, sonusEventTime }
    STATUS          current
    DESCRIPTION     
            "Dbrep daemon up"
    ::= { sonusSoftSwitchDbrepMIBNotificationsPrefix 1 }

sonusSoftSwitchDbrepDownNotification NOTIFICATION-TYPE
    OBJECTS         { sonusEventDescription, sonusEventClass, 
                      sonusEventLevel, sonusEventTime }
    STATUS          current
    DESCRIPTION     
            "Dbrep daemon down"
    ::= { sonusSoftSwitchDbrepMIBNotificationsPrefix 2 }

sonusSoftSwitchDbrepConnectionUpNotification NOTIFICATION-TYPE
    OBJECTS         { sonusEventDescription, sonusEventClass, 
                      sonusEventLevel, sonusEventTime, 
                      sonusSoftSwitchDbrepPeerIp }
    STATUS          deprecated
    DESCRIPTION     
            "Dbrep connection establised"
    ::= { sonusSoftSwitchDbrepMIBNotificationsPrefix 3 }

sonusSoftSwitchDbrepConnectionDownNotification NOTIFICATION-TYPE
    OBJECTS         { sonusEventDescription, sonusEventClass, 
                      sonusEventLevel, sonusEventTime, 
                      sonusSoftSwitchDbrepPeerIp }
    STATUS          deprecated
    DESCRIPTION     
            "Dbrep connection severed"
    ::= { sonusSoftSwitchDbrepMIBNotificationsPrefix 4 }

sonusSoftSwitchDbrepConnectionAttemptNotification NOTIFICATION-TYPE
    OBJECTS         { sonusEventDescription, sonusEventClass, 
                      sonusEventLevel, sonusEventTime, 
                      sonusSoftSwitchDbrepPeerIp }
    STATUS          deprecated
    DESCRIPTION     
            "Dbrep attempt to connect to remote peer"
    ::= { sonusSoftSwitchDbrepMIBNotificationsPrefix 5 }

sonusSoftSwitchDbrepDbErrorNotification NOTIFICATION-TYPE
    OBJECTS         { sonusEventDescription, sonusEventClass, 
                      sonusEventLevel, sonusEventTime }
    STATUS          current
    DESCRIPTION     
            "Dbrep failure while attempting a DB operation"
    ::= { sonusSoftSwitchDbrepMIBNotificationsPrefix 6 }

sonusSoftSwitchDbrepLagThresholdExceededNotification NOTIFICATION-TYPE
    OBJECTS         { sonusEventDescription, sonusEventClass, 
                      sonusEventLevel, sonusEventTime, 
                      sonusSoftSwitchDbrepPeerIp }
    STATUS          deprecated
    DESCRIPTION     
            "Dbrep Lag Threshold was exceeded"
    ::= { sonusSoftSwitchDbrepMIBNotificationsPrefix 7 }

sonusExtendedSoftSwitchDbrepConnectionUpNotification NOTIFICATION-TYPE
    OBJECTS         { sonusEventDescription, sonusEventClass, 
                      sonusEventLevel, sonusEventTime, 
                      sonusSoftSwitchDbrepPeerExtendedIpType, 
                      sonusSoftSwitchDbrepPeerExtendedIp }
    STATUS          current
    DESCRIPTION     
            "Dbrep connection establised"
    ::= { sonusSoftSwitchDbrepMIBNotificationsPrefix 8 }

sonusExtendedSoftSwitchDbrepConnectionDownNotification NOTIFICATION-TYPE
    OBJECTS         { sonusEventDescription, sonusEventClass, 
                      sonusEventLevel, sonusEventTime, 
                      sonusSoftSwitchDbrepPeerExtendedIpType, 
                      sonusSoftSwitchDbrepPeerExtendedIp }
    STATUS          current
    DESCRIPTION     
            "Dbrep connection severed"
    ::= { sonusSoftSwitchDbrepMIBNotificationsPrefix 9 }

sonusExtendedSoftSwitchDbrepConnectionAttemptNotification NOTIFICATION-TYPE
    OBJECTS         { sonusEventDescription, sonusEventClass, 
                      sonusEventLevel, sonusEventTime, 
                      sonusSoftSwitchDbrepPeerExtendedIpType, 
                      sonusSoftSwitchDbrepPeerExtendedIp }
    STATUS          current
    DESCRIPTION     
            "Dbrep attempt to connect to remote peer"
    ::= { sonusSoftSwitchDbrepMIBNotificationsPrefix 10 }

sonusExtendedSoftSwitchDbrepLagThresholdExceededNotification NOTIFICATION-TYPE
    OBJECTS         { sonusEventDescription, sonusEventClass, 
                      sonusEventLevel, sonusEventTime, 
                      sonusSoftSwitchDbrepPeerExtendedIpType, 
                      sonusSoftSwitchDbrepPeerExtendedIp }
    STATUS          current
    DESCRIPTION     
            "Dbrep Lag Threshold was exceeded"
    ::= { sonusSoftSwitchDbrepMIBNotificationsPrefix 11 }

END -- end of module SONUS-SOFTSWITCH-DBREP-MIB.
