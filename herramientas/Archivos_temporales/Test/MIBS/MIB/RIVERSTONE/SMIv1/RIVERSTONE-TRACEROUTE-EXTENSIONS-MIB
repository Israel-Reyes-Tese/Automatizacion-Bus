--
-- This SMIv1 module has been generated by smidump 0.2-cvs. Do not edit.
--

RIVERSTONE-TRACEROUTE-EXTENSIONS-MIB DEFINITIONS ::= BEGIN

IMPORTS
    traceRouteCtlOwnerIndex, traceRouteCtlTestName, 
    traceRouteProbeHistoryHopIndex, traceRouteProbeHistoryIndex, 
    traceRouteProbeHistoryProbeIndex
        FROM DISMAN-TRACEROUTE-MIB
    VlanId
        FROM Q-BRIDGE-MIB
    OBJECT-TYPE
        FROM RFC-1212
    riverstoneMibs
        FROM RIVERSTONE-SMI-MIB
    MacAddress
        FROM SNMPv2-TC;

rsTraceRouteExtensionsMIB OBJECT IDENTIFIER
    ::= { riverstoneMibs 56 }

-- rsTraceRouteExtensionsMIB MODULE-IDENTITY
--     LAST-UPDATED    "200210110000Z"
--     ORGANIZATION    
--             "Riverstone Networks, Inc"
--     CONTACT-INFO    
--             "Riverstone Networks
--              Customer Service
--              
--              Postal:
--              Riverstone Networks, Inc
--              5200 Great America Parkway
--              Santa Clara CA 95054 USA
--              
--              PHONE:+1 408.878.6500
--              EMAIL: nms-eng@riverstonenet.com
--              WEB: http://www.riverstonenet.com"
--     DESCRIPTION     
--             "This module extends the traceRouteMIB defined in RFC2925."
--     REVISION        "200210110000Z"
--     DESCRIPTION     
--             "Initial version of Riverstone extensions to the traceRouteMIB."
--     ::= { riverstoneMibs 56 }


rsTraceRouteObjects OBJECT IDENTIFIER
    ::= { rsTraceRouteExtensionsMIB 1 }

rsTraceRouteEtherOamCtlTable OBJECT-TYPE
    SYNTAX          SEQUENCE OF RsTraceRouteEtherOamCtlEntry
    ACCESS          not-accessible
    STATUS          mandatory
    DESCRIPTION     
            "Extends the traceRoute  Control Table for providing, via SNMP,
             the capability of performing trace path  operations at 
             a remote host by L2 MAC address.
             
             Restrictions:
             
             Following objects of traceRouteCtlEntry are not used when
             traceRouteCtlType is of rsTraceRouteEthernetOAM.
             
             traceRouteCtlTargetAddress,
             traceRouteCtlTargetAddressType,
             traceRouteCtlPort,
             traceRouteCtlDontFragment,
             traceRouteCtlInitialTtl,
             
             traceRouteCtlSourceAddressType,
             traceRouteCtlSourceAddress,
             traceRouteCtlByPassRouteTable,
             traceRouteCtlDSField
             
             traceRouteCtlIfIndex will only takes values 
             When its  ifType value is any one of these
             
             ethernetCsmacd(6),
             propMultiplexor(54)
             
             traceRouteCtlMiscOptions can take RS CLI option
             'detailed'. If specified the traceroute does fetch
             details like Switch Name, System Name, Version.
             
             "
    ::= { rsTraceRouteObjects 5 }

rsTraceRouteEtherOamCtlEntry OBJECT-TYPE
    SYNTAX          RsTraceRouteEtherOamCtlEntry
    ACCESS          not-accessible
    STATUS          mandatory
    DESCRIPTION     
            "Defines an entry in the rsTraceRouteEtherOamCtlTable. 
             Both indexes are defined in RFC2925.
             "
    INDEX           { traceRouteCtlOwnerIndex, traceRouteCtlTestName }
    ::= { rsTraceRouteEtherOamCtlTable 1 }

RsTraceRouteEtherOamCtlEntry ::=
    SEQUENCE {
        rsTraceRouteEtherOamCtlTargetAddress    MacAddress,
        rsTraceRouteEtherOamCtlVlanId   VlanId,
        rsTraceRouteEtherOamCtlPriority Gauge
    }

rsTraceRouteEtherOamCtlTargetAddress OBJECT-TYPE
    SYNTAX          MacAddress
    ACCESS          read-write
    STATUS          mandatory
    DESCRIPTION     
            "Specifies the host L2 MAC address to be used at a remote host for
             performing a traceRoute operation. A value for this object MUST be
             set prior to transitioning its corresponding traceRouteCtlEntry to
             active(1) via  traceRouteCtlRowStatus. 
             
             This object essentially replaces traceRouteCtlTargetAddressType and 
             traceRouteCtrTArgetAddress in traceRouteCtrlTable. 
             "
    ::= { rsTraceRouteEtherOamCtlEntry 1 }

rsTraceRouteEtherOamCtlVlanId OBJECT-TYPE
    SYNTAX          VlanId
    ACCESS          read-write
    STATUS          mandatory
    DESCRIPTION     
            "A 12-bit VLAN ID used in the VLAN Tag header of traceRoute
             frame. Its value range  from 1 to 4095 as defined in 
             IEEE 802.1Q VLAN-ID "
    ::= { rsTraceRouteEtherOamCtlEntry 2 }

rsTraceRouteEtherOamCtlPriority OBJECT-TYPE
    SYNTAX          Gauge (0..7)
    ACCESS          read-write
    STATUS          mandatory
    DESCRIPTION     
            "802.1p priority value"
    ::= { rsTraceRouteEtherOamCtlEntry 3 }

rsTraceRouteEtherOamHistoryTable OBJECT-TYPE
    SYNTAX          SEQUENCE OF RsTraceRouteEtherOamHistoryEntry
    ACCESS          not-accessible
    STATUS          mandatory
    DESCRIPTION     
            "Extends the traceRouteProbeHistoryTable  for providing, via SNMP,
             the capability of performing trace path  operations at 
             a remote host by L2 MAC address.
             
             Restrictions:
             
             Following objects of traceRouteProbeHistoryEntry are not used when
             traceRouteCtlType is of rsTraceRouteEthernetOAM.
             traceRouteProbeHistoryHAddrType,
             traceRouteProbeHistoryHAddr,
             "
    ::= { rsTraceRouteObjects 10 }

rsTraceRouteEtherOamHistoryEntry OBJECT-TYPE
    SYNTAX          RsTraceRouteEtherOamHistoryEntry
    ACCESS          not-accessible
    STATUS          mandatory
    DESCRIPTION     
            "Defines an entry in the rsTraceRouteEtherOamHistoryTable. 
             Both indexes are defined in RFC2925.
             "
    INDEX           { traceRouteCtlOwnerIndex, traceRouteCtlTestName, 
                      traceRouteProbeHistoryIndex, 
                      traceRouteProbeHistoryHopIndex, 
                      traceRouteProbeHistoryProbeIndex }
    ::= { rsTraceRouteEtherOamHistoryTable 1 }

RsTraceRouteEtherOamHistoryEntry ::=
    SEQUENCE {
        rsTraceRouteEtherOamHistoryTargetAddress        MacAddress
    }

rsTraceRouteEtherOamHistoryTargetAddress OBJECT-TYPE
    SYNTAX          MacAddress
    ACCESS          read-only
    STATUS          mandatory
    DESCRIPTION     
            "Specifies the host L2 MAC address at a hop. 
             This object essentially replaces traceRouteHistoryTargetAddressType and 
             traceRouteCtrTArgetAddress in traceRouteCtrlTable. 
             "
    ::= { rsTraceRouteEtherOamHistoryEntry 1 }

rsTraceRouteConformance OBJECT IDENTIFIER
    ::= { rsTraceRouteExtensionsMIB 2 }

rsTraceRouteCompliances OBJECT IDENTIFIER
    ::= { rsTraceRouteConformance 1 }

rsTraceRouteGroups OBJECT IDENTIFIER
    ::= { rsTraceRouteConformance 2 }

rsTraceRouteTypes OBJECT IDENTIFIER
    ::= { rsTraceRouteExtensionsMIB 3 }

rsTraceRouteEthernetOam OBJECT IDENTIFIER
    ::= { rsTraceRouteTypes 5 }

rsTraceRouteEtherOamCtlGroup OBJECT IDENTIFIER
    ::= { rsTraceRouteGroups 5 }

-- rsTraceRouteEtherOamCtlGroup OBJECT-GROUP
--     OBJECTS         { rsTraceRouteEtherOamCtlTargetAddress, 
--                       rsTraceRouteEtherOamCtlVlanId, 
--                       rsTraceRouteEtherOamCtlPriority }
--     STATUS          mandatory
--     DESCRIPTION     
--             "The group of objects that are needed for Ethernet OAM traceRoute."
--     ::= { rsTraceRouteGroups 5 }

rsTraceRouteEtherOamHistoryGroup OBJECT IDENTIFIER
    ::= { rsTraceRouteGroups 10 }

-- rsTraceRouteEtherOamHistoryGroup OBJECT-GROUP
--     OBJECTS         { rsTraceRouteEtherOamHistoryTargetAddress }
--     STATUS          mandatory
--     DESCRIPTION     
--             "The group of objects that are needed for Ethernet OAM
--              traceRoute history."
--     ::= { rsTraceRouteGroups 10 }

rsTraceRouteCompliance OBJECT IDENTIFIER
    ::= { rsTraceRouteCompliances 1 }

-- rsTraceRouteCompliance MODULE-COMPLIANCE
--     STATUS          mandatory
--     DESCRIPTION     
--             "The compliance statement for RIVERSTONE-PING-EXTENSIONS-MIB."

--     MODULE          -- -- this module

--         MANDATORY-GROUPS    { rsTraceRouteEtherOamCtlGroup, 
--                       rsTraceRouteEtherOamHistoryGroup }

--     ::= { rsTraceRouteCompliances 1 }

END -- end of module RIVERSTONE-TRACEROUTE-EXTENSIONS-MIB.
