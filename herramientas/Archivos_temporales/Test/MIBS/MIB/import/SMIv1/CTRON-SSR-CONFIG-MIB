--
-- This SMIv1 module has been generated by smidump 0.2-cvs. Do not edit.
--

CTRON-SSR-CONFIG-MIB DEFINITIONS ::= BEGIN

IMPORTS
    ssrMibs
        FROM CTRON-SSR-SMI-MIB
    OBJECT-TYPE
        FROM RFC-1212
    IpAddress
        FROM RFC1155-SMI
    DisplayString, TruthValue
        FROM SNMPv2-TC;

ssrConfigMIB OBJECT IDENTIFIER
    ::= { ssrMibs 230 }

-- ssrConfigMIB MODULE-IDENTITY
--     LAST-UPDATED    "200006270000Z"
--     ORGANIZATION    
--             "Cabletron Systems, Inc"
--     CONTACT-INFO    
--             "Riverstone Networks, Inc
--              5200 Great America Parkway
--              Santa Clara, CA 95054
--              (408) 878-6500
--              nms-eng@riverstonenet.com
--              http://www.riverstonenet.com"
--     DESCRIPTION     
--             "This mib module defines an SNMP API to manage SmartSwitch 
--              Router configuration files and system images"
--     REVISION        "200006270000Z"
--     DESCRIPTION     
--             "Revision #3. Update contact information for Riverstone Networks as this mib
--              is found on the Riverstione RS product line as well as Enterasys SSR product line."
--     REVISION        "200002200000Z"
--     DESCRIPTION     
--             "Revision #2. add two objects to obtain current prom and firmware version."
--     REVISION        "199808170000Z"
--     DESCRIPTION     
--             "Revision #1. Provide startup configuration file retrieval, 
--              startup log and append new commands."
--     ::= { ssrMibs 230 }


SSRErrorCode ::=
    INTEGER { noStatus(1), timeout(2), networkError(3), noSpace(4), 
                        invalidConfig(5), commandCompleted(6), 
                        internalError(7), tftpServerError(8) }

-- SSRErrorCode ::= TEXTUAL-CONVENTION
--     STATUS          mandatory
--     DESCRIPTION     
--             "A unique value, greater than zero defining the operation
--              completion status."
--     SYNTAX          INTEGER
--                       { noStatus(1), timeout(2), networkError(3), 
--                         noSpace(4), invalidConfig(5), 
--                         commandCompleted(6), internalError(7), 
--                         tftpServerError(8) }

configConformance OBJECT IDENTIFIER
    ::= { ssrConfigMIB 3 }

configCompliances OBJECT IDENTIFIER
    ::= { configConformance 1 }

configGroups OBJECT IDENTIFIER
    ::= { configConformance 2 }

cfgGroup OBJECT IDENTIFIER
    ::= { ssrMibs 231 }

cfgTransferOp OBJECT-TYPE
    SYNTAX          INTEGER { noop(1), sendConfigToAgent(2), 
                        receiveConfigFromAgent(3), 
                        receiveBootlogFromAgent(4) }
    ACCESS          read-write
    STATUS          mandatory
    DESCRIPTION     
            "Tranfer operation to be performed. Configuration
             files are ASCII NVT text files describing the operation of the shelf.
             Send operations use tftp to transfer a file from the manager to agent.
             Receive operations use tftp to transfer the file from the agent to the 
             manager. Default value is no operation or noop."
    ::= { cfgGroup 1 }

cfgManagerAddress OBJECT-TYPE
    SYNTAX          IpAddress
    ACCESS          read-write
    STATUS          mandatory
    DESCRIPTION     
            "The IPv4 address of the Manager to be used by the agent for
             for cfgTransferOp operations. Default value is 0.0.0.0. Address must be 
             a unicast address that is reachable from the agent and no firewalls/acls 
             preventing tftp datagrams from being transferred."
    ::= { cfgGroup 2 }

cfgFileName OBJECT-TYPE
    SYNTAX          DisplayString
    ACCESS          read-write
    STATUS          mandatory
    DESCRIPTION     
            "The file name to be retrieved from the tftp server at 
             host cfgManagerAddress or to be written to. Default value is blank. 
             Length of filename string must not exceed 255 alpha-numeric characters, 
             no spaces in filenames."
    ::= { cfgGroup 3 }

cfgActivateTransfer OBJECT-TYPE
    SYNTAX          TruthValue
    ACCESS          read-write
    STATUS          mandatory
    DESCRIPTION     
            "Activate the file transfer operation with a value of True(1) or 
             stop it with False(2). Poll cfgTransferStatus for current status. 
             Default value is False. cfgFileName, cfgManagerAddress and cfgTransferOp
             must be valid prior to setting this object to True. This object is equivalent to
             the CLI command: copy tftp-server to startup if cfgRequestOp == sendConfig"
    ::= { cfgGroup 4 }

cfgTransferStatus OBJECT-TYPE
    SYNTAX          INTEGER { idle(1), sending(2), receiving(3), 
                        transferComplete(4), error(5) }
    ACCESS          read-only
    STATUS          mandatory
    DESCRIPTION     
            "The current status of the transfer task. Default state is idle. 
             sending indicates a file transfer (agent->mgr) in progress. 
             receiving indicates sending a file from Manager to agent. 
             transferComplete indicates a successful transfer. error indicates
             a failed transfer. See cfgLastError to diagnose why the transfer failed."
    ::= { cfgGroup 5 }

cfgActivateFile OBJECT-TYPE
    SYNTAX          TruthValue
    ACCESS          read-write
    STATUS          mandatory
    DESCRIPTION     
            "Once a transfer to the SmartSwitchRouter is complete, Set this object
             to True to activate the new configuration.
             If activateConfigFile operation was successful, this object performs
             the CLI equivalent to these commands: negate all existing commands,
             copy scratchpad to active, copy scratchpad to startup"
    ::= { cfgGroup 6 }

cfgLastError OBJECT-TYPE
    SYNTAX          SSRErrorCode
    ACCESS          read-only
    STATUS          mandatory
    DESCRIPTION     
            "A reason code for the last transfer operation. Poll this value
             when doing sets against cfgMakeActive for config files obtain status."
    ::= { cfgGroup 7 }

cfgLastErrorReason OBJECT-TYPE
    SYNTAX          DisplayString
    ACCESS          read-only
    STATUS          mandatory
    DESCRIPTION     
            "A string representation of cfgLastError which may contain addtional details."
    ::= { cfgGroup 8 }

cfgActiveImageVersion OBJECT-TYPE
    SYNTAX          DisplayString
    ACCESS          read-only
    STATUS          mandatory
    DESCRIPTION     
            "The Version string of the current image executing on this control module. This
             is the same description as the system show version command. example:  1.1.0.0"
    ::= { cfgGroup 9 }

cfgActiveImageBootLocation OBJECT-TYPE
    SYNTAX          DisplayString
    ACCESS          read-only
    STATUS          mandatory
    DESCRIPTION     
            "The URL location string from whence the current image was loaded. 
             example:  slot0:boot/ssr8.tar.gz/"
    ::= { cfgGroup 10 }

configGroup10 OBJECT IDENTIFIER
    ::= { configGroups 1 }

-- configGroup10 OBJECT-GROUP
--     OBJECTS         { cfgTransferOp, cfgManagerAddress, cfgFileName, 
--                       cfgActivateTransfer, cfgTransferStatus, 
--                       cfgActivateFile, cfgLastError, 
--                       cfgLastErrorReason }
--     STATUS          deprecated
--     DESCRIPTION     
--             "The collection of objects which are used to represent version 1.0
--              file transfer operations in the SmartSwitch Router."
--     ::= { configGroups 1 }

configGroup20 OBJECT IDENTIFIER
    ::= { configGroups 2 }

-- configGroup20 OBJECT-GROUP
--     OBJECTS         { cfgTransferOp, cfgManagerAddress, cfgFileName, 
--                       cfgActivateTransfer, cfgTransferStatus, 
--                       cfgActivateFile, cfgLastError, 
--                       cfgLastErrorReason, cfgActiveImageVersion, 
--                       cfgActiveImageBootLocation }
--     STATUS          mandatory
--     DESCRIPTION     
--             "The collection of objects which are used to represent version 2.0
--              configuration operations in the SmartSwitch Router version."
--     ::= { configGroups 2 }

configCompliance OBJECT IDENTIFIER
    ::= { configCompliances 1 }

-- configCompliance MODULE-COMPLIANCE
--     STATUS          obsolete
--     DESCRIPTION     
--             "The compliance statement for SNMP entities which implement
--              the SmartSwitch Router Config Management MIB."

--     MODULE          -- -- this module

--         MANDATORY-GROUPS    { configGroup10 }

--     ::= { configCompliances 1 }

configCompliance2 OBJECT IDENTIFIER
    ::= { configCompliances 2 }

-- configCompliance2 MODULE-COMPLIANCE
--     STATUS          mandatory
--     DESCRIPTION     
--             "The compliance statement for SNMP entities which implement
--              the SmartSwitch Router Config Management MIB."

--     MODULE          -- -- this module

--         MANDATORY-GROUPS    { configGroup20 }

--     ::= { configCompliances 2 }

END -- end of module CTRON-SSR-CONFIG-MIB.
