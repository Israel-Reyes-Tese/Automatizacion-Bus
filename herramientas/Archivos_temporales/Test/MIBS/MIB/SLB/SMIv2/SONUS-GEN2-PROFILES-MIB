--
-- This SMIv2 module has been generated by smidump 0.2-cvs. Do not edit.
--

SONUS-GEN2-PROFILES-MIB DEFINITIONS ::= BEGIN

IMPORTS
    Counter32, Counter64, Gauge32, Integer32, IpAddress, MODULE-IDENTITY, 
    OBJECT-TYPE, Unsigned32
        FROM SNMPv2-SMI
    DateAndTime, RowStatus, TEXTUAL-CONVENTION, TruthValue
        FROM SNMPv2-TC
    sonusCommonSoftwarePlatformServicesMIBs
        FROM SONUS-SMI;

sonusGen2ProfilesMIB MODULE-IDENTITY
    LAST-UPDATED    "201212310000Z"
    ORGANIZATION    
            "Ribbon Communications, Inc."
    CONTACT-INFO    
            "Customer Support        
             Ribbon Communications, Inc. 
             4 Technology Park Drive 
             Westford, MA 01886      
             USA                     
                                     
             Tel: 978-614-8100       
             Fax: 978-614-8609"
    DESCRIPTION     
            "The MIB Module for Characteristic Management."
    REVISION        "201212310000Z"
    DESCRIPTION     
            "Auto generated MIB."
    ::= { sonusCommonSoftwarePlatformServicesMIBs 11 }


String ::= TEXTUAL-CONVENTION
    DISPLAY-HINT    "1t"
    STATUS          current
    DESCRIPTION     
            "xs:string"
    SYNTAX          OCTET STRING

SonusNodeCoreDumpCountLimitType ::= TEXTUAL-CONVENTION
    STATUS          current
    DESCRIPTION     
            "
             Number of coredumps allowed on harddisk per process. Minimum 1, Maximum 10.
             "
    SYNTAX          Integer32 (1..10)

SonusNodeCoreDumpLevelType ::= TEXTUAL-CONVENTION
    STATUS          current
    DESCRIPTION     
            ""
    SYNTAX          INTEGER { disabled(1), normal(2), sensitive(3) }

SonusNodeCoreDumpSpaceLimitType ::= TEXTUAL-CONVENTION
    STATUS          current
    DESCRIPTION     
            "
             Coredump disk space limit in GigaBytes. Minimum 1, Maximum 20.
             "
    SYNTAX          Integer32 (1..20)

sonusProfiles OBJECT IDENTIFIER
    ::= { sonusGen2ProfilesMIB 1 }

sonusProfilesSystem OBJECT IDENTIFIER
    ::= { sonusProfiles 1 }

sonusProfilesSystemCoredumpProfileTable OBJECT-TYPE
    SYNTAX          SEQUENCE OF SonusProfilesSystemCoredumpProfileEntry
    MAX-ACCESS      not-accessible
    STATUS          obsolete
    DESCRIPTION     
            "
             Coredump settings applicable to server(s)
             "
    ::= { sonusProfilesSystem 1 }

sonusProfilesSystemCoredumpProfileEntry OBJECT-TYPE
    SYNTAX          SonusProfilesSystemCoredumpProfileEntry
    MAX-ACCESS      not-accessible
    STATUS          obsolete
    DESCRIPTION     
            ""
    INDEX           { sonusProfilesSystemCoredumpProfileName }
    ::= { sonusProfilesSystemCoredumpProfileTable 1 }

SonusProfilesSystemCoredumpProfileEntry ::=
    SEQUENCE {
        sonusProfilesSystemCoredumpProfileName      String,
        sonusProfilesSystemCoredumpProfileCoredumpLevel               SonusNodeCoreDumpLevelType,
        sonusProfilesSystemCoredumpProfileCoredumpPath              String,
        sonusProfilesSystemCoredumpProfileCoredumpSpaceLimit                    SonusNodeCoreDumpSpaceLimitType,
        sonusProfilesSystemCoredumpProfileCoredumpCountLimit                    SonusNodeCoreDumpCountLimitType,
        sonusProfilesSystemCoredumpProfileRowstatus           RowStatus
    }

sonusProfilesSystemCoredumpProfileName OBJECT-TYPE
    SYNTAX          String (SIZE(0..23))
    MAX-ACCESS      not-accessible
    STATUS          obsolete
    DESCRIPTION     
            "
             The name of the profile.
             "
    ::= { sonusProfilesSystemCoredumpProfileEntry 1 }

sonusProfilesSystemCoredumpProfileCoredumpLevel OBJECT-TYPE
    SYNTAX          SonusNodeCoreDumpLevelType
    MAX-ACCESS      read-create
    STATUS          obsolete
    DESCRIPTION     
            "
             Sensitivity level for coredumping.
             "
    DEFVAL          { normal }
    ::= { sonusProfilesSystemCoredumpProfileEntry 2 }

sonusProfilesSystemCoredumpProfileCoredumpPath OBJECT-TYPE
    SYNTAX          String (SIZE(0..255))
    MAX-ACCESS      read-create
    STATUS          obsolete
    DESCRIPTION     
            "
             The path of the coredump.
             "
    ::= { sonusProfilesSystemCoredumpProfileEntry 3 }

sonusProfilesSystemCoredumpProfileCoredumpSpaceLimit OBJECT-TYPE
    SYNTAX          SonusNodeCoreDumpSpaceLimitType
    MAX-ACCESS      read-create
    STATUS          obsolete
    DESCRIPTION     
            "
             Coredump disk space limit per server (in GigaBytes).
             "
    DEFVAL          { 6 }
    ::= { sonusProfilesSystemCoredumpProfileEntry 4 }

sonusProfilesSystemCoredumpProfileCoredumpCountLimit OBJECT-TYPE
    SYNTAX          SonusNodeCoreDumpCountLimitType
    MAX-ACCESS      read-create
    STATUS          obsolete
    DESCRIPTION     
            "
             Number of coredumps allowed on disk (per process).
             "
    DEFVAL          { 3 }
    ::= { sonusProfilesSystemCoredumpProfileEntry 5 }

sonusProfilesSystemCoredumpProfileRowstatus OBJECT-TYPE
    SYNTAX          RowStatus
    MAX-ACCESS      read-create
    STATUS          obsolete
    DESCRIPTION     
            ""
    ::= { sonusProfilesSystemCoredumpProfileEntry 6 }

END -- end of module SONUS-GEN2-PROFILES-MIB.
