--
-- This SMIv2 module has been generated by smidump 0.2-cvs. Do not edit.
--

RIVERSTONE-PING-EXTENSIONS-MIB DEFINITIONS ::= BEGIN

IMPORTS
    AtmVcIdentifier, AtmVpIdentifier
        FROM ATM-TC-MIB
    pingCtlOwnerIndex, pingCtlTestName
        FROM DISMAN-PING-MIB
    VlanId
        FROM Q-BRIDGE-MIB
    riverstoneMibs
        FROM RIVERSTONE-SMI-MIB
    MODULE-COMPLIANCE, OBJECT-GROUP
        FROM SNMPv2-CONF
    Integer32, MODULE-IDENTITY, OBJECT-IDENTITY, OBJECT-TYPE, Unsigned32
        FROM SNMPv2-SMI
    MacAddress, TEXTUAL-CONVENTION
        FROM SNMPv2-TC;

rsPingExtensionsMIB MODULE-IDENTITY
    LAST-UPDATED    "200210090000Z"
    ORGANIZATION    
            "Riverstone Networks, Inc"
    CONTACT-INFO    
            "Riverstone Networks
             Customer Service
             
             Postal:
             Riverstone Networks, Inc
             5200 Great America Parkway
             Santa Clara CA 95054 USA
             
             PHONE:+1 408.878.6500
             EMAIL: nms-eng@riverstonenet.com
             WEB: http://www.riverstonenet.com"
    DESCRIPTION     
            "This module extends the pingMIB defined in RFC2925."
    REVISION        "200210090000Z"
    DESCRIPTION     
            "Add ping extension for ethernet OAM."
    REVISION        "200204160000Z"
    DESCRIPTION     
            "Initial version of Riverstone extensions to the pingMIB. 
             ATM OAM ping is the first extension."
    ::= { riverstoneMibs 55 }


RsAtmFlowLevel ::= TEXTUAL-CONVENTION
    STATUS          current
    DESCRIPTION     
            "Indicate different ATM flow levels. The level VPI (F4)
             indicates the flow is switched by VPI by the network nodes, 
             The level VCI (F5) indicates the flow is switched by VPI
             and VCI."
    SYNTAX          INTEGER { none(0), f4(4), f5(5) }

RsAtmOamFlowType ::= TEXTUAL-CONVENTION
    STATUS          current
    DESCRIPTION     
            "Indicates different ATM OAM loopback flow types. An OAM 
             loopback can either be segment or endToEnd. A segment 
             	flow covers part of the circuit. Only network nodes receive 
             segment flows. A segment flow cannot end at a Customer 
             	Premises Equipment (CPE). An endToEnd flow indicates 
             	the end of a circuit. It is from a network node or a CPE 
             	to a far point, another CPE."
    SYNTAX          INTEGER { none(0), segment(3), endToEnd(4) }

RsAtmOamLocationID ::= TEXTUAL-CONVENTION
    STATUS          current
    DESCRIPTION     
            "Indicate a location ID, which can be configured on
             each ATM switch to identify it."
    SYNTAX          OCTET STRING (SIZE(0..16))

rsPingObjects OBJECT IDENTIFIER
    ::= { rsPingExtensionsMIB 1 }

rsPingAtmCtlTable OBJECT-TYPE
    SYNTAX          SEQUENCE OF RsPingAtmCtlEntry
    MAX-ACCESS      not-accessible
    STATUS          current
    DESCRIPTION     
            "Extends the ping Control Table for providing, via SNMP,
             the capability of performing ping operations at 
             a remote host."
    ::= { rsPingObjects 1 }

rsPingAtmCtlEntry OBJECT-TYPE
    SYNTAX          RsPingAtmCtlEntry
    MAX-ACCESS      not-accessible
    STATUS          current
    DESCRIPTION     
            "Defines an entry in the rsPingCtlTable.  The first index
             element pingCtlOwnerIndex isdefined in RFC2925.
             The second index pingCtlTestName is also defined in RFC2925."
    INDEX           { pingCtlOwnerIndex, pingCtlTestName }
    ::= { rsPingAtmCtlTable 1 }

RsPingAtmCtlEntry ::=
    SEQUENCE {
        rsPingAtmCtlPort                Unsigned32,
        rsPingAtmCtlVpi                 AtmVpIdentifier,
        rsPingAtmCtlVci                 AtmVcIdentifier,
        rsPingAtmCtlFlowType            RsAtmOamFlowType,
        rsPingAtmCtlLocationID          RsAtmOamLocationID
    }

rsPingAtmCtlPort OBJECT-TYPE
    SYNTAX          Unsigned32
    MAX-ACCESS      read-create
    STATUS          current
    DESCRIPTION     
            "This indicates the system port of the virtual circuit 
             that the OAM loopback cells would go out."
    DEFVAL          { 0 }
    ::= { rsPingAtmCtlEntry 1 }

rsPingAtmCtlVpi OBJECT-TYPE
    SYNTAX          AtmVpIdentifier
    MAX-ACCESS      read-create
    STATUS          current
    DESCRIPTION     
            "This indicates the VPI of the virtual circuit
             that the OAM loopback cells would go out."
    DEFVAL          { 1 }
    ::= { rsPingAtmCtlEntry 2 }

rsPingAtmCtlVci OBJECT-TYPE
    SYNTAX          AtmVcIdentifier
    MAX-ACCESS      read-create
    STATUS          current
    DESCRIPTION     
            "This indicates the VCI of the virtual circuit
             that the OAM loopback cells would go out. 
             If this circuit is switched by VPI(F4), this 
             object would only take in 3 or 4 for segment or 
             endToTnd respectively to indicate its flow type."
    DEFVAL          { 3 }
    ::= { rsPingAtmCtlEntry 3 }

rsPingAtmCtlFlowType OBJECT-TYPE
    SYNTAX          RsAtmOamFlowType
    MAX-ACCESS      read-create
    STATUS          current
    DESCRIPTION     
            "This indicates to the switch to send ATM OAM 
             segment loopback or endToEnd loopback cells. 
             This object only applies when the flow level 
             is F5. For F4 circuit, set the VCI to 3 for 
             	segment and 4 for endToEnd."
    DEFVAL          { none }
    ::= { rsPingAtmCtlEntry 4 }

rsPingAtmCtlLocationID OBJECT-TYPE
    SYNTAX          RsAtmOamLocationID
    MAX-ACCESS      read-create
    STATUS          current
    DESCRIPTION     
            "This object only applies if the flow type is
             segment. Use this object to identify which ATM
             network node in the circuit would the segment 
             loopback occur. The default value of all 1s
             	indicate the end of the circuit. For segment
             	flows, this is the last network node. For endToEnd
             	flows, this is the CPE."
    DEFVAL          { "ffffffffffffffff" }
    ::= { rsPingAtmCtlEntry 5 }

rsPingEtherOamCtlTable OBJECT-TYPE
    SYNTAX          SEQUENCE OF RsPingEtherOamCtlEntry
    MAX-ACCESS      not-accessible
    STATUS          current
    DESCRIPTION     
            "Extends the ping Control Table for providing, via SNMP,
             the capability of performing ping operations at 
             a remote host by L2 MAC address.
             
             Restrictions:
             
             Following objects of pingCtlEntry are not used when
             pingCtlType is of rsPingEthernetOAM.
             
             pingCtlTargetAddress,
             pingCtlTargetAddressType,
             pingCtlSourceAddressType,
             pingCtlSourceAddress,
             pingCtlByPassRouteTable,
             pingCtlDSField
             
             pingCtlIfIndex will only takes values 
             When its  ifType value is any one of these
             
             ethernetCsmacd(6),
             propMultiplexor(54)
             
             "
    ::= { rsPingObjects 5 }

rsPingEtherOamCtlEntry OBJECT-TYPE
    SYNTAX          RsPingEtherOamCtlEntry
    MAX-ACCESS      not-accessible
    STATUS          current
    DESCRIPTION     
            "Defines an entry in the rsPingEtherOamCtlTable. 
             Both indexes are defined in RFC2925.
             "
    INDEX           { pingCtlOwnerIndex, pingCtlTestName }
    ::= { rsPingEtherOamCtlTable 1 }

RsPingEtherOamCtlEntry ::=
    SEQUENCE {
        rsPingEtherOamCtlTargetAddress  MacAddress,
        rsPingEtherOamCtlVlanId         VlanId,
        rsPingEtherOamCtlPriority       Unsigned32
    }

rsPingEtherOamCtlTargetAddress OBJECT-TYPE
    SYNTAX          MacAddress
    MAX-ACCESS      read-create
    STATUS          current
    DESCRIPTION     
            "Specifies the host L2 MAC address to be used at a remote host for
             performing a ping operation. A value for this object MUST be
             set prior to transitioning its corresponding pingCtlEntry to
             active(1) via  pingCtlRowStatus. 
             
             This object essentially replaces pingCtlTargetAddressType and 
             pingCtrTArgetAddress in pingCtrlTable. 
             "
    ::= { rsPingEtherOamCtlEntry 1 }

rsPingEtherOamCtlVlanId OBJECT-TYPE
    SYNTAX          VlanId
    MAX-ACCESS      read-create
    STATUS          current
    DESCRIPTION     
            "A 12-bit VLAN ID used in the VLAN Tag header of ping
             frame. Its value range  from 1 to 4095 as defined in 
             IEEE 802.1Q VLAN-ID "
    ::= { rsPingEtherOamCtlEntry 2 }

rsPingEtherOamCtlPriority OBJECT-TYPE
    SYNTAX          Unsigned32 (0..7)
    MAX-ACCESS      read-create
    STATUS          current
    DESCRIPTION     
            "802.1p priority value"
    ::= { rsPingEtherOamCtlEntry 3 }

rsPingConformance OBJECT IDENTIFIER
    ::= { rsPingExtensionsMIB 2 }

rsPingCompliances OBJECT IDENTIFIER
    ::= { rsPingConformance 1 }

rsPingGroups OBJECT IDENTIFIER
    ::= { rsPingConformance 2 }

rsPingTypes OBJECT IDENTIFIER
    ::= { rsPingExtensionsMIB 3 }

rsPingAtmOamLoopback OBJECT-IDENTITY
    STATUS          current
    DESCRIPTION     
            "Indicates that an implementation is using ATM OAM loopback."
    ::= { rsPingTypes 1 }

rsPingEtherOam OBJECT-IDENTITY
    STATUS          current
    DESCRIPTION     
            "Indicates that an implementation is using Ethernet OAM to
             find round trip time to remote host by L2 MAC address"
    ::= { rsPingTypes 5 }

rsPingAtmCtlGroup OBJECT-GROUP
    OBJECTS         { rsPingAtmCtlPort, rsPingAtmCtlVpi, rsPingAtmCtlVci, 
                      rsPingAtmCtlFlowType, rsPingAtmCtlLocationID }
    STATUS          current
    DESCRIPTION     
            "The group of objects that are needed for ATM OAM ping."
    ::= { rsPingGroups 1 }

rsPingEtherOamCtlGroup OBJECT-GROUP
    OBJECTS         { rsPingEtherOamCtlTargetAddress, 
                      rsPingEtherOamCtlVlanId, rsPingEtherOamCtlPriority }
    STATUS          current
    DESCRIPTION     
            "The group of objects that are needed for Ethernet OAM ping."
    ::= { rsPingGroups 5 }

rsPingCompliance MODULE-COMPLIANCE
    STATUS          current
    DESCRIPTION     
            "The compliance statement for RIVERSTONE-PING-EXTENSIONS-MIB."

    MODULE          -- this module

        MANDATORY-GROUPS    { rsPingAtmCtlGroup, rsPingEtherOamCtlGroup }

    ::= { rsPingCompliances 1 }

END -- end of module RIVERSTONE-PING-EXTENSIONS-MIB.
