--
-- This SMIv1 module has been generated by smidump 0.2-cvs. Do not edit.
--

CISCO-SMI DEFINITIONS ::= BEGIN

IMPORTS
    enterprises
        FROM SNMPv2-SMI;

cisco OBJECT IDENTIFIER
    ::= { enterprises 9 }

-- cisco MODULE-IDENTITY
--     LAST-UPDATED    "200001110000Z"
--     ORGANIZATION    
--             "Cisco Systems, Inc."
--     CONTACT-INFO    
--             "	Cisco Systems
--              Customer Service
--              
--              Postal: 170 West Tasman Drive
--              San Jose, CA  95134
--              USA
--              
--              Tel: +1 800 553-NETS
--              
--              E-mail: cs-snmp@cisco.com"
--     DESCRIPTION     
--             "The Structure of Management Information for the
--              Cisco enterprise."
--     REVISION        "200001110000Z"
--     DESCRIPTION     
--             "Added ciscoPolicy, ciscoPolicyAuto, ciscoPIB, and
--              ciscoPibToMib."
--     REVISION        "199704090000Z"
--     DESCRIPTION     
--             "Added ciscoPartnerProducts to generate sysObjectID
--              for partner platforms"
--     REVISION        "199505160000Z"
--     DESCRIPTION     
--             "New oid assignments for Cisco REPEATER MIB and others."
--     REVISION        "199404262000Z"
--     DESCRIPTION     
--             "Initial version of this MIB module."
--     ::= { enterprises 9 }


ciscoProducts OBJECT IDENTIFIER
    ::= { cisco 1 }

local OBJECT IDENTIFIER
    ::= { cisco 2 }

temporary OBJECT IDENTIFIER
    ::= { cisco 3 }

pakmon OBJECT IDENTIFIER
    ::= { cisco 4 }

workgroup OBJECT IDENTIFIER
    ::= { cisco 5 }

otherEnterprises OBJECT IDENTIFIER
    ::= { cisco 6 }

ciscoAgentCapability OBJECT IDENTIFIER
    ::= { cisco 7 }

ciscoConfig OBJECT IDENTIFIER
    ::= { cisco 8 }

ciscoMgmt OBJECT IDENTIFIER
    ::= { cisco 9 }

ciscoExperiment OBJECT IDENTIFIER
    ::= { cisco 10 }

ciscoAdmin OBJECT IDENTIFIER
    ::= { cisco 11 }

ciscoProxy OBJECT IDENTIFIER
    ::= { ciscoAdmin 1 }

ciscoPartyProxy OBJECT IDENTIFIER
    ::= { ciscoProxy 1 }

ciscoContextProxy OBJECT IDENTIFIER
    ::= { ciscoProxy 2 }

ciscoRptrGroupObjectID OBJECT IDENTIFIER
    ::= { ciscoAdmin 2 }

ciscoUnknownRptrGroup OBJECT IDENTIFIER
    ::= { ciscoRptrGroupObjectID 1 }

cisco2505RptrGroup OBJECT IDENTIFIER
    ::= { ciscoRptrGroupObjectID 2 }

cisco2507RptrGroup OBJECT IDENTIFIER
    ::= { ciscoRptrGroupObjectID 3 }

cisco2516RptrGroup OBJECT IDENTIFIER
    ::= { ciscoRptrGroupObjectID 4 }

ciscoWsx5020RptrGroup OBJECT IDENTIFIER
    ::= { ciscoRptrGroupObjectID 5 }

ciscoChipSets OBJECT IDENTIFIER
    ::= { ciscoAdmin 3 }

ciscoChipSetSaint1 OBJECT IDENTIFIER
    ::= { ciscoChipSets 1 }

ciscoChipSetSaint2 OBJECT IDENTIFIER
    ::= { ciscoChipSets 2 }

ciscoChipSetSaint3 OBJECT IDENTIFIER
    ::= { ciscoChipSets 3 }

ciscoChipSetSaint4 OBJECT IDENTIFIER
    ::= { ciscoChipSets 4 }

ciscoModules OBJECT IDENTIFIER
    ::= { cisco 12 }

lightstream OBJECT IDENTIFIER
    ::= { cisco 13 }

ciscoworks OBJECT IDENTIFIER
    ::= { cisco 14 }

newport OBJECT IDENTIFIER
    ::= { cisco 15 }

ciscoPartnerProducts OBJECT IDENTIFIER
    ::= { cisco 16 }

ciscoPolicy OBJECT IDENTIFIER
    ::= { cisco 17 }

ciscoPIB OBJECT IDENTIFIER
    ::= { ciscoPolicy 2 }

ciscoPolicyAuto OBJECT IDENTIFIER
    ::= { cisco 18 }

ciscoPibToMib OBJECT IDENTIFIER
    ::= { ciscoPolicyAuto 2 }

END -- end of module CISCO-SMI.
