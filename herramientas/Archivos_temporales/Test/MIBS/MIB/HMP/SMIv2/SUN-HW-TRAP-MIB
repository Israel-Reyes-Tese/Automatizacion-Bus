--
-- This SMIv2 module has been generated by smidump 0.2-cvs. Do not edit.
--

SUN-HW-TRAP-MIB DEFINITIONS ::= BEGIN

IMPORTS
    NOTIFICATION-GROUP, OBJECT-GROUP
        FROM SNMPv2-CONF
    Integer32, MODULE-IDENTITY, NOTIFICATION-TYPE, OBJECT-TYPE, 
    enterprises
        FROM SNMPv2-SMI
    DisplayString, RowPointer, TEXTUAL-CONVENTION
        FROM SNMPv2-TC;

sunHwTrapMIB MODULE-IDENTITY
    LAST-UPDATED    "200803170000Z"
    ORGANIZATION    
            "Sun Microsystems, Inc."
    CONTACT-INFO    
            "Sun Microsystems, Inc.
             4150 Network Circle
             Santa Clara, CA 95054
             
             1-800-555-9SUN or
             1-650-960-1300
             
             http://www.sun.com
             or contact your local support representative"
    DESCRIPTION     
            "Copyright 2008 Sun Microsystems, Inc.  All rights reserved.
             Use is subject to license terms.
             
             The SUN-HW-TRAP-MIB describes the hardware related
             notifications/traps that may be generated by Sun systems"
    REVISION        "200803170000Z"
    DESCRIPTION     
            "Version: 2.0
             Released with ILOM version 3.0"
    REVISION        "200702060000Z"
    DESCRIPTION     
            "Version: 1.0"
    ::= { ilom 103 }


SunHwTrapThresholdTypeTC ::= TEXTUAL-CONVENTION
    STATUS          current
    DESCRIPTION     
            "Describes whether a threshold is an upper threshold or
             a lower threshold"
    SYNTAX          INTEGER { upper(1), lower(2), unknown(3) }

SunHwTrapSeverityTC ::= TEXTUAL-CONVENTION
    STATUS          current
    DESCRIPTION     
            "Describes the severity levels that a trap can take."
    SYNTAX          INTEGER { other(1), fatal(2), critical(3), 
                        nonCritical(4), ok(5) }

SunHwTrapHAStateTC ::= TEXTUAL-CONVENTION
    STATUS          current
    DESCRIPTION     
            "Describes the states that a high availability system can take."
    SYNTAX          INTEGER { other(1), initializing(2), standalone(3), 
                        standby(4), master(5) }

SunHwTrapHardDriveStatesTC ::= TEXTUAL-CONVENTION
    STATUS          current
    DESCRIPTION     
            "Describes the states a hard drive can be in when hard drive status
             is reported."
    SYNTAX          INTEGER { other(1), present(2), fault(3), 
                        predictiveFailure(4), hotSpare(5), 
                        consistencyCheckInProgress(6), 
                        inCriticalArray(7), inFailedArray(8), 
                        rebuildInProgress(9), rebuildAborted(10) }

SunHwTrapDisableReasonsTC ::= TEXTUAL-CONVENTION
    STATUS          current
    DESCRIPTION     
            "Describes the reasons that a component is disabled."
    SYNTAX          INTEGER { unknown(1), faultOrError(2), 
                        configuration(3) }

SunHwTrapFloatingPointValueTC ::= TEXTUAL-CONVENTION
    DISPLAY-HINT    "255a"
    STATUS          current
    DESCRIPTION     
            "A floating point number converted to a string
             in decimal notation of the form [-]mmm.dd"
    SYNTAX          OCTET STRING (SIZE(0..255))

sun OBJECT IDENTIFIER
    ::= { enterprises 42 }

products OBJECT IDENTIFIER
    ::= { sun 2 }

ilom OBJECT IDENTIFIER
    ::= { products 175 }

sunHwTrapObjects OBJECT IDENTIFIER
    ::= { sunHwTrapMIB 1 }

sunHwTraps OBJECT IDENTIFIER
    ::= { sunHwTrapMIB 2 }

sunHwTrapPrefix OBJECT IDENTIFIER
    ::= { sunHwTraps 0 }

sunHwTrapData OBJECT IDENTIFIER
    ::= { sunHwTraps 1 }

sunHwTrapSystemIdentifier OBJECT-TYPE
    SYNTAX          DisplayString
    MAX-ACCESS      accessible-for-notify
    STATUS          current
    DESCRIPTION     
            "A text string used to identify the source of the trap. Typically
             this is the host name."
    ::= { sunHwTrapData 1 }

sunHwTrapComponentName OBJECT-TYPE
    SYNTAX          DisplayString
    MAX-ACCESS      accessible-for-notify
    STATUS          current
    DESCRIPTION     
            "The name of the component which is the source of the trap."
    ::= { sunHwTrapData 2 }

sunHwTrapThresholdType OBJECT-TYPE
    SYNTAX          SunHwTrapThresholdTypeTC
    MAX-ACCESS      accessible-for-notify
    STATUS          current
    DESCRIPTION     
            "Identifies the threshold type that the sensor is reporting on."
    ::= { sunHwTrapData 3 }

sunHwTrapThresholdValue OBJECT-TYPE
    SYNTAX          SunHwTrapFloatingPointValueTC
    MAX-ACCESS      accessible-for-notify
    STATUS          current
    DESCRIPTION     
            "The threshold setting that has been crossed."
    ::= { sunHwTrapData 4 }

sunHwTrapSensorValue OBJECT-TYPE
    SYNTAX          SunHwTrapFloatingPointValueTC
    MAX-ACCESS      accessible-for-notify
    STATUS          current
    DESCRIPTION     
            "The threshold sensor's reading at the time the trap was generated."
    ::= { sunHwTrapData 5 }

sunHwTrapSuspectComponentName OBJECT-TYPE
    SYNTAX          DisplayString
    MAX-ACCESS      accessible-for-notify
    STATUS          current
    DESCRIPTION     
            "Contains the name of a component that is suspected of causing
             a fault."
    ::= { sunHwTrapData 6 }

sunHwTrapFaultClass OBJECT-TYPE
    SYNTAX          DisplayString
    MAX-ACCESS      accessible-for-notify
    STATUS          current
    DESCRIPTION     
            "The class represents a hierarchical classification string indicating
             the type of problem detected, as reported by the fault management
             subsystem, such as, for instance the Solaris fault manager.
             Information on the Solaris fault manager can be found at
             http://www.opensolaris.org/os/community/fm.
             
             This object will have a value of NULL if the system doesn't
             support this information."
    REFERENCE       
            "SUN-FM-MIB.sunFmFaultEventClass
             http://www.opensolaris.org/os/community/fm/mib/sun-fm-mib.mib"
    ::= { sunHwTrapData 7 }

sunHwTrapFaultCertainty OBJECT-TYPE
    SYNTAX          Integer32 (0..100)
    MAX-ACCESS      accessible-for-notify
    STATUS          current
    DESCRIPTION     
            "The percentage likelihood that the component is the source
             of the problem. This object will have a value of 0 if the
             system doesn't support this information."
    ::= { sunHwTrapData 8 }

sunHwTrapAdditionalInfo OBJECT-TYPE
    SYNTAX          DisplayString
    MAX-ACCESS      accessible-for-notify
    STATUS          current
    DESCRIPTION     
            "An optional textual description which provides additional
             information relevant to this notification."
    ::= { sunHwTrapData 9 }

sunHwTrapAssocObjectId OBJECT-TYPE
    SYNTAX          RowPointer
    MAX-ACCESS      accessible-for-notify
    STATUS          current
    DESCRIPTION     
            "The object in the entPhysicalTable to which this notification applies.
             The value is the name of the instance of the first accessible columnar
             object in the entPhysicalTable conceptual row. If no association exists
             or the association cannot be determined, this object will have a value
             of 0.0."
    ::= { sunHwTrapData 10 }

sunHwTrapNewHAState OBJECT-TYPE
    SYNTAX          SunHwTrapHAStateTC
    MAX-ACCESS      accessible-for-notify
    STATUS          current
    DESCRIPTION     
            "This object provides the new value of the high availability state
             after a high availability state change has occurred."
    ::= { sunHwTrapData 11 }

sunHwTrapOldHAState OBJECT-TYPE
    SYNTAX          SunHwTrapHAStateTC
    MAX-ACCESS      accessible-for-notify
    STATUS          current
    DESCRIPTION     
            "This object provides the old value of the high availability state
             after a high availability state change has occurred."
    ::= { sunHwTrapData 12 }

sunHwTrapSeverity OBJECT-TYPE
    SYNTAX          SunHwTrapSeverityTC
    MAX-ACCESS      accessible-for-notify
    STATUS          current
    DESCRIPTION     
            "An indication of the severity of the notfication."
    ::= { sunHwTrapData 13 }

sunHwTrapChassisId OBJECT-TYPE
    SYNTAX          DisplayString
    MAX-ACCESS      accessible-for-notify
    STATUS          current
    DESCRIPTION     
            "A text string containing the chassis serial number. When combined
             with the sunHwTrapProductName, it unambiguously identifies the
             system. If the source of the trap is a blade, the text string will
             contain the chassis serial number and the blade serial number, in
             the following format <chassis-serial-number::blade-serial-number>"
    ::= { sunHwTrapData 14 }

sunHwTrapProductName OBJECT-TYPE
    SYNTAX          DisplayString
    MAX-ACCESS      accessible-for-notify
    STATUS          current
    DESCRIPTION     
            "A text string containing the product name. When combined with the
             sunHwTrapChassisId, it unambiguously identifies the system. If the
             source of the trap is a blade, the text string will contain the
             chassis product name and the blade product name, in the following
             format <chassis-name>::<blade-name>"
    ::= { sunHwTrapData 15 }

sunHwTrapHardDriveState OBJECT-TYPE
    SYNTAX          SunHwTrapHardDriveStatesTC
    MAX-ACCESS      accessible-for-notify
    STATUS          current
    DESCRIPTION     
            "The states a hard drive can be in when hard drive status
             is reported."
    ::= { sunHwTrapData 16 }

sunHwTrapFaultMessageID OBJECT-TYPE
    SYNTAX          DisplayString
    MAX-ACCESS      accessible-for-notify
    STATUS          current
    DESCRIPTION     
            "The message ID that can be used to get additional information about
             the problem from Sun's knowledge article database. This object will
             have a value of NULL if the system doesn't support this
             information."
    ::= { sunHwTrapData 17 }

sunHwTrapFaultUUID OBJECT-TYPE
    SYNTAX          DisplayString
    MAX-ACCESS      accessible-for-notify
    STATUS          current
    DESCRIPTION     
            "The universal unique identifier that was assigned to this fault. This
             object will have a value of NULL if the system doesn't support this
             information."
    ::= { sunHwTrapData 18 }

sunHwTrapDisableReason OBJECT-TYPE
    SYNTAX          SunHwTrapDisableReasonsTC
    MAX-ACCESS      accessible-for-notify
    STATUS          current
    DESCRIPTION     
            "An indication as to why the component was disabled."
    ::= { sunHwTrapData 19 }

sunHwTrapTestMessage OBJECT-TYPE
    SYNTAX          DisplayString
    MAX-ACCESS      accessible-for-notify
    STATUS          current
    DESCRIPTION     
            "This is a test trap"
    ::= { sunHwTrapData 20 }

sunHwTrapConformances OBJECT IDENTIFIER
    ::= { sunHwTrapMIB 3 }

sunHwTrapCompliances OBJECT IDENTIFIER
    ::= { sunHwTrapConformances 1 }

sunHwTrapGroups OBJECT IDENTIFIER
    ::= { sunHwTrapConformances 2 }

sunHwTrapObjectGroups OBJECT IDENTIFIER
    ::= { sunHwTrapGroups 1 }

sunHwTrapNotifGroups OBJECT IDENTIFIER
    ::= { sunHwTrapGroups 2 }

sunHwTrapVoltageFatalThresholdExceeded NOTIFICATION-TYPE
    OBJECTS         { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
    STATUS          current
    DESCRIPTION     
            "A voltage sensor has reported that its value has gone above an upper
             fatal threshold setting or below a lower fatal threshold setting.
             The sunHwTrapThresholdType object indicates whether the threshold was
             an upper or lower."
    ::= { sunHwTrapPrefix 1 }

sunHwTrapVoltageFatalThresholdDeasserted NOTIFICATION-TYPE
    OBJECTS         { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
    STATUS          current
    DESCRIPTION     
            "A voltage sensor has reported that its value has gone below an upper
             fatal threshold setting or above a lower fatal threshold setting.
             The sunHwTrapThresholdType object indicates whether the threshold was
             an upper or lower."
    ::= { sunHwTrapPrefix 2 }

sunHwTrapVoltageCritThresholdExceeded NOTIFICATION-TYPE
    OBJECTS         { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
    STATUS          current
    DESCRIPTION     
            "A voltage sensor has reported that its value has gone above an upper
             critical threshold setting or below a lower critical threshold setting.
             The sunHwTrapThresholdType object indicates whether the threshold was
             an upper or lower."
    ::= { sunHwTrapPrefix 3 }

sunHwTrapVoltageCritThresholdDeasserted NOTIFICATION-TYPE
    OBJECTS         { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
    STATUS          current
    DESCRIPTION     
            "A voltage sensor has reported that its value has gone below an upper
             critical threshold setting or above a lower critical threshold setting.
             The sunHwTrapThresholdType object indicates whether the threshold was
             an upper or lower."
    ::= { sunHwTrapPrefix 4 }

sunHwTrapVoltageNonCritThresholdExceeded NOTIFICATION-TYPE
    OBJECTS         { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
    STATUS          current
    DESCRIPTION     
            "A voltage sensor has reported that its value has gone above an upper
             non-critical threshold setting or below a lower non-critical threshold
             setting. The sunHwTrapThresholdType object indicates whether the threshold
             was an upper or lower."
    ::= { sunHwTrapPrefix 5 }

sunHwTrapVoltageOk NOTIFICATION-TYPE
    OBJECTS         { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
    STATUS          current
    DESCRIPTION     
            "A voltage sensor has reported that its value is in the normal
             operating range."
    ::= { sunHwTrapPrefix 6 }

sunHwTrapTempFatalThresholdExceeded NOTIFICATION-TYPE
    OBJECTS         { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
    STATUS          current
    DESCRIPTION     
            "A temperature sensor has reported that its value has gone above an upper
             fatal threshold setting or below a lower fatal threshold setting.
             The sunHwTrapThresholdType object indicates whether the threshold was
             an upper or lower."
    ::= { sunHwTrapPrefix 7 }

sunHwTrapTempFatalThresholdDeasserted NOTIFICATION-TYPE
    OBJECTS         { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
    STATUS          current
    DESCRIPTION     
            "A temperature sensor has reported that its value has gone below an
             upper fatal threshold setting or above a lower fatal threshold setting.
             The sunHwTrapThresholdType object indicates whether the threshold was
             an upper or lower."
    ::= { sunHwTrapPrefix 8 }

sunHwTrapTempCritThresholdExceeded NOTIFICATION-TYPE
    OBJECTS         { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
    STATUS          current
    DESCRIPTION     
            "A temperature sensor has reported that its value has gone above an
             upper critical threshold setting or below a lower critical threshold
             setting. The sunHwTrapThresholdType object indicates whether the
             threshold was an upper or lower."
    ::= { sunHwTrapPrefix 9 }

sunHwTrapTempCritThresholdDeasserted NOTIFICATION-TYPE
    OBJECTS         { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
    STATUS          current
    DESCRIPTION     
            "A temperature sensor has reported that its value has gone below an
             upper critical threshold setting or above a lower critical threshold
             setting. The sunHwTrapThresholdType object indicates whether the
             threshold was an upper or lower."
    ::= { sunHwTrapPrefix 10 }

sunHwTrapTempNonCritThresholdExceeded NOTIFICATION-TYPE
    OBJECTS         { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
    STATUS          current
    DESCRIPTION     
            "A temperature sensor has reported that its value has gone above an
             upper non-critical threshold setting or below a lower non-critical
             threshold setting. The sunHwTrapThresholdType object indicates whether
             the threshold was an upper or lower."
    ::= { sunHwTrapPrefix 11 }

sunHwTrapTempOk NOTIFICATION-TYPE
    OBJECTS         { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
    STATUS          current
    DESCRIPTION     
            "A temperature sensor has reported that its value is in the normal
             operating range."
    ::= { sunHwTrapPrefix 12 }

sunHwTrapElectricalCurrentFatalThresholdExceeded NOTIFICATION-TYPE
    OBJECTS         { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
    STATUS          current
    DESCRIPTION     
            "An electrical current sensor has reported that its value has gone above
             an upper fatal threshold setting or below a lower fatal threshold
             setting. The sunHwTrapThresholdType object indicates whether the
             threshold was an upper or lower."
    ::= { sunHwTrapPrefix 13 }

sunHwTrapElectricalCurrentFatalThresholdDeasserted NOTIFICATION-TYPE
    OBJECTS         { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
    STATUS          current
    DESCRIPTION     
            "An electrical current sensor has reported that its value has gone below
             an upper fatal threshold setting or above a lower fatal threshold
             setting. The sunHwTrapThresholdType object indicates whether the
             threshold was an upper or lower."
    ::= { sunHwTrapPrefix 14 }

sunHwTrapElectricalCurrentCritThresholdExceeded NOTIFICATION-TYPE
    OBJECTS         { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
    STATUS          current
    DESCRIPTION     
            "An electrical current sensor has reported that its value has gone above
             an upper critical threshold setting or below a lower critical threshold
             setting. The sunHwTrapThresholdType object indicates whether the
             threshold was an upper or lower."
    ::= { sunHwTrapPrefix 15 }

sunHwTrapElectricalCurrentCritThresholdDeasserted NOTIFICATION-TYPE
    OBJECTS         { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
    STATUS          current
    DESCRIPTION     
            "An electrical current sensor has reported that its value has gone below
             an upper critical threshold setting or above a lower critical threshold
             setting. The sunHwTrapThresholdType object indicates whether the
             threshold was an upper or lower."
    ::= { sunHwTrapPrefix 16 }

sunHwTrapElectricalCurrentNonCritThresholdExceeded NOTIFICATION-TYPE
    OBJECTS         { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
    STATUS          current
    DESCRIPTION     
            "An electrical current sensor has reported that its value has gone above
             an upper non-critical threshold setting or below a lower non-critical
             threshold setting. The sunHwTrapThresholdType object indicates whether
             the threshold was an upper or lower."
    ::= { sunHwTrapPrefix 17 }

sunHwTrapElectricalCurrentOk NOTIFICATION-TYPE
    OBJECTS         { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
    STATUS          current
    DESCRIPTION     
            "An electrical current sensor has reported that its value is in
             the normal operating range."
    ::= { sunHwTrapPrefix 18 }

sunHwTrapFanSpeedFatalThresholdExceeded NOTIFICATION-TYPE
    OBJECTS         { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
    STATUS          current
    DESCRIPTION     
            "A fan speed sensor has reported that its value has gone above an upper
             fatal threshold setting or below a lower fatal threshold setting.
             The sunHwTrapThresholdType object indicates whether the threshold was
             an upper or lower."
    ::= { sunHwTrapPrefix 19 }

sunHwTrapFanSpeedFatalThresholdDeasserted NOTIFICATION-TYPE
    OBJECTS         { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
    STATUS          current
    DESCRIPTION     
            "A fan speed sensor has reported that its value has gone below an upper
             fatal threshold setting or above a lower fatal threshold setting.
             The sunHwTrapThresholdType object indicates whether the threshold was
             an upper or lower."
    ::= { sunHwTrapPrefix 20 }

sunHwTrapFanSpeedCritThresholdExceeded NOTIFICATION-TYPE
    OBJECTS         { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
    STATUS          current
    DESCRIPTION     
            "A fan speed sensor has reported that its value has gone above an upper
             critical threshold setting or below a lower critical threshold setting.
             The sunHwTrapThresholdType object indicates whether the threshold was
             an upper or lower."
    ::= { sunHwTrapPrefix 21 }

sunHwTrapFanSpeedCritThresholdDeasserted NOTIFICATION-TYPE
    OBJECTS         { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
    STATUS          current
    DESCRIPTION     
            "A fan speed sensor has reported that its value has gone below an upper
             critical threshold setting or above a lower critical threshold setting.
             The sunHwTrapThresholdType object indicates whether the threshold was
             an upper or lower."
    ::= { sunHwTrapPrefix 22 }

sunHwTrapFanSpeedNonCritThresholdExceeded NOTIFICATION-TYPE
    OBJECTS         { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
    STATUS          current
    DESCRIPTION     
            "A fan speed sensor has reported that its value has gone above an upper
             non-critical threshold setting or below a lower non-critical threshold
             setting. The sunHwTrapThresholdType object indicates whether the
             threshold was an upper or lower."
    ::= { sunHwTrapPrefix 23 }

sunHwTrapFanSpeedOk NOTIFICATION-TYPE
    OBJECTS         { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
    STATUS          current
    DESCRIPTION     
            "A fan speed sensor has reported that its value is in
             the normal operating range."
    ::= { sunHwTrapPrefix 24 }

sunHwTrapSensorFatalThresholdExceeded NOTIFICATION-TYPE
    OBJECTS         { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
    STATUS          current
    DESCRIPTION     
            "A sensor has reported that its value has gone above an upper fatal
             threshold setting or below a lower fatal threshold setting. The 
             generic 'sensor' trap is generated when the SNMP agent does not
             recognize the component type. The sunHwTrapThresholdType object
             indicates whether the threshold was an upper or lower."
    ::= { sunHwTrapPrefix 25 }

sunHwTrapSensorFatalThresholdDeasserted NOTIFICATION-TYPE
    OBJECTS         { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
    STATUS          current
    DESCRIPTION     
            "A sensor has reported that its value has gone below an upper fatal
             threshold setting or above a lower fatal threshold setting. The
             generic 'sensor' trap is generated when the SNMP agent does not
             recognize the component type. The sunHwTrapThresholdType object
             indicates whether the threshold was an upper or lower."
    ::= { sunHwTrapPrefix 26 }

sunHwTrapSensorCritThresholdExceeded NOTIFICATION-TYPE
    OBJECTS         { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
    STATUS          current
    DESCRIPTION     
            "A sensor has reported that its value has gone above an upper critical
             threshold setting or below a lower critical threshold setting. The 
             generic 'sensor' trap is generated when the SNMP agent does not
             recognize the component type. The sunHwTrapThresholdType object
             indicates whether the threshold was an upper or lower."
    ::= { sunHwTrapPrefix 27 }

sunHwTrapSensorCritThresholdDeasserted NOTIFICATION-TYPE
    OBJECTS         { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
    STATUS          current
    DESCRIPTION     
            "A sensor has reported that its value has gone below an upper critical
             threshold setting or above a lower critical threshold setting. The
             generic 'sensor' trap is generated when the SNMP agent does not
             recognize the component type. The sunHwTrapThresholdType object
             indicates whether the threshold was an upper or lower."
    ::= { sunHwTrapPrefix 28 }

sunHwTrapSensorNonCritThresholdExceeded NOTIFICATION-TYPE
    OBJECTS         { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
    STATUS          current
    DESCRIPTION     
            "A sensor has reported that its value has gone above an upper
             non-critical threshold setting or below a lower non-critical threshold
             setting. The generic 'sensor' trap is generated when the SNMP agent
             does not recognize the component type. The sunHwTrapThresholdType
             object indicates whether the threshold was an upper or lower."
    ::= { sunHwTrapPrefix 29 }

sunHwTrapSensorThresholdOk NOTIFICATION-TYPE
    OBJECTS         { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
    STATUS          current
    DESCRIPTION     
            "A sensor has reported that its value is in the normal operating range.
             The generic 'sensor' trap is generated when the SNMP agent does not
             recognize the component type."
    ::= { sunHwTrapPrefix 30 }

sunHwTrapPowerSupplyFault NOTIFICATION-TYPE
    OBJECTS         { sunHwTrapSystemIdentifier, sunHwTrapChassisId, 
                      sunHwTrapProductName, 
                      sunHwTrapSuspectComponentName, sunHwTrapFaultClass, 
                      sunHwTrapFaultCertainty, sunHwTrapFaultMessageID, 
                      sunHwTrapFaultUUID, sunHwTrapAssocObjectId, 
                      sunHwTrapAdditionalInfo }
    STATUS          current
    DESCRIPTION     
            "A power supply component is suspected of causing a fault."
    ::= { sunHwTrapPrefix 31 }

sunHwTrapPowerSupplyError NOTIFICATION-TYPE
    OBJECTS         { sunHwTrapSystemIdentifier, sunHwTrapChassisId, 
                      sunHwTrapProductName, sunHwTrapComponentName, 
                      sunHwTrapAdditionalInfo, sunHwTrapAssocObjectId }
    STATUS          current
    DESCRIPTION     
            "A power supply sensor has detected an error."
    ::= { sunHwTrapPrefix 32 }

sunHwTrapPowerSupplyOk NOTIFICATION-TYPE
    OBJECTS         { sunHwTrapSystemIdentifier, sunHwTrapChassisId, 
                      sunHwTrapProductName, sunHwTrapComponentName, 
                      sunHwTrapAdditionalInfo, sunHwTrapAssocObjectId }
    STATUS          current
    DESCRIPTION     
            "A power supply sensor has returned to its normal state."
    ::= { sunHwTrapPrefix 33 }

sunHwTrapFanFault NOTIFICATION-TYPE
    OBJECTS         { sunHwTrapSystemIdentifier, sunHwTrapChassisId, 
                      sunHwTrapProductName, 
                      sunHwTrapSuspectComponentName, sunHwTrapFaultClass, 
                      sunHwTrapFaultCertainty, sunHwTrapFaultMessageID, 
                      sunHwTrapFaultUUID, sunHwTrapAssocObjectId, 
                      sunHwTrapAdditionalInfo }
    STATUS          current
    DESCRIPTION     
            "A fan component is suspected of causing a fault."
    ::= { sunHwTrapPrefix 34 }

sunHwTrapFanError NOTIFICATION-TYPE
    OBJECTS         { sunHwTrapSystemIdentifier, sunHwTrapChassisId, 
                      sunHwTrapProductName, sunHwTrapComponentName, 
                      sunHwTrapAdditionalInfo, sunHwTrapAssocObjectId }
    STATUS          current
    DESCRIPTION     
            "A fan sensor has detected an error."
    ::= { sunHwTrapPrefix 35 }

sunHwTrapFanOk NOTIFICATION-TYPE
    OBJECTS         { sunHwTrapSystemIdentifier, sunHwTrapChassisId, 
                      sunHwTrapProductName, sunHwTrapComponentName, 
                      sunHwTrapAdditionalInfo, sunHwTrapAssocObjectId }
    STATUS          current
    DESCRIPTION     
            "A fan sensor has returned to its normal state."
    ::= { sunHwTrapPrefix 36 }

sunHwTrapProcessorFault NOTIFICATION-TYPE
    OBJECTS         { sunHwTrapSystemIdentifier, sunHwTrapChassisId, 
                      sunHwTrapProductName, 
                      sunHwTrapSuspectComponentName, sunHwTrapFaultClass, 
                      sunHwTrapFaultCertainty, sunHwTrapFaultMessageID, 
                      sunHwTrapFaultUUID, sunHwTrapAssocObjectId, 
                      sunHwTrapAdditionalInfo }
    STATUS          current
    DESCRIPTION     
            "A processor component is suspected of causing a fault."
    ::= { sunHwTrapPrefix 37 }

sunHwTrapProcessorError NOTIFICATION-TYPE
    OBJECTS         { sunHwTrapSystemIdentifier, sunHwTrapChassisId, 
                      sunHwTrapProductName, sunHwTrapComponentName, 
                      sunHwTrapAdditionalInfo, sunHwTrapAssocObjectId }
    STATUS          current
    DESCRIPTION     
            "A processor sensor has detected an error."
    ::= { sunHwTrapPrefix 38 }

sunHwTrapProcessorOk NOTIFICATION-TYPE
    OBJECTS         { sunHwTrapSystemIdentifier, sunHwTrapChassisId, 
                      sunHwTrapProductName, sunHwTrapComponentName, 
                      sunHwTrapAdditionalInfo, sunHwTrapAssocObjectId }
    STATUS          current
    DESCRIPTION     
            "A processor sensor has returned to its normal state."
    ::= { sunHwTrapPrefix 39 }

sunHwTrapMemoryFault NOTIFICATION-TYPE
    OBJECTS         { sunHwTrapSystemIdentifier, sunHwTrapChassisId, 
                      sunHwTrapProductName, 
                      sunHwTrapSuspectComponentName, sunHwTrapFaultClass, 
                      sunHwTrapFaultCertainty, sunHwTrapFaultMessageID, 
                      sunHwTrapFaultUUID, sunHwTrapAssocObjectId, 
                      sunHwTrapAdditionalInfo }
    STATUS          current
    DESCRIPTION     
            "A memory component is suspected of causing a fault."
    ::= { sunHwTrapPrefix 40 }

sunHwTrapMemoryError NOTIFICATION-TYPE
    OBJECTS         { sunHwTrapSystemIdentifier, sunHwTrapChassisId, 
                      sunHwTrapProductName, sunHwTrapComponentName, 
                      sunHwTrapAdditionalInfo, sunHwTrapAssocObjectId }
    STATUS          current
    DESCRIPTION     
            "A memory sensor has detected an error."
    ::= { sunHwTrapPrefix 41 }

sunHwTrapMemoryOk NOTIFICATION-TYPE
    OBJECTS         { sunHwTrapSystemIdentifier, sunHwTrapChassisId, 
                      sunHwTrapProductName, sunHwTrapComponentName, 
                      sunHwTrapAdditionalInfo, sunHwTrapAssocObjectId }
    STATUS          current
    DESCRIPTION     
            "A memory sensor has returned to its normal state."
    ::= { sunHwTrapPrefix 42 }

sunHwTrapHardDriveFault NOTIFICATION-TYPE
    OBJECTS         { sunHwTrapSystemIdentifier, sunHwTrapChassisId, 
                      sunHwTrapProductName, 
                      sunHwTrapSuspectComponentName, sunHwTrapFaultClass, 
                      sunHwTrapFaultCertainty, sunHwTrapFaultMessageID, 
                      sunHwTrapFaultUUID, sunHwTrapAssocObjectId, 
                      sunHwTrapAdditionalInfo }
    STATUS          current
    DESCRIPTION     
            "A hard drive component is suspected of causing a fault."
    ::= { sunHwTrapPrefix 43 }

sunHwTrapHardDriveError NOTIFICATION-TYPE
    OBJECTS         { sunHwTrapSystemIdentifier, sunHwTrapChassisId, 
                      sunHwTrapProductName, sunHwTrapComponentName, 
                      sunHwTrapAdditionalInfo, sunHwTrapAssocObjectId }
    STATUS          current
    DESCRIPTION     
            "A hard drive sensor has detected an error."
    ::= { sunHwTrapPrefix 44 }

sunHwTrapHardDriveOk NOTIFICATION-TYPE
    OBJECTS         { sunHwTrapSystemIdentifier, sunHwTrapChassisId, 
                      sunHwTrapProductName, sunHwTrapComponentName, 
                      sunHwTrapAdditionalInfo, sunHwTrapAssocObjectId }
    STATUS          current
    DESCRIPTION     
            "A hard drive sensor has returned to its normal state."
    ::= { sunHwTrapPrefix 45 }

sunHwTrapIOFault NOTIFICATION-TYPE
    OBJECTS         { sunHwTrapSystemIdentifier, sunHwTrapChassisId, 
                      sunHwTrapProductName, 
                      sunHwTrapSuspectComponentName, sunHwTrapFaultClass, 
                      sunHwTrapFaultCertainty, sunHwTrapFaultMessageID, 
                      sunHwTrapFaultUUID, sunHwTrapAssocObjectId, 
                      sunHwTrapAdditionalInfo }
    STATUS          current
    DESCRIPTION     
            "A component in the IO subsystem is suspected of causing a fault."
    ::= { sunHwTrapPrefix 46 }

sunHwTrapIOError NOTIFICATION-TYPE
    OBJECTS         { sunHwTrapSystemIdentifier, sunHwTrapChassisId, 
                      sunHwTrapProductName, sunHwTrapComponentName, 
                      sunHwTrapAdditionalInfo, sunHwTrapAssocObjectId }
    STATUS          current
    DESCRIPTION     
            "An IO sensor has detected an error."
    ::= { sunHwTrapPrefix 47 }

sunHwTrapIOOk NOTIFICATION-TYPE
    OBJECTS         { sunHwTrapSystemIdentifier, sunHwTrapChassisId, 
                      sunHwTrapProductName, sunHwTrapComponentName, 
                      sunHwTrapAdditionalInfo, sunHwTrapAssocObjectId }
    STATUS          current
    DESCRIPTION     
            "An IO sensor has returned to its normal state."
    ::= { sunHwTrapPrefix 48 }

sunHwTrapSlotOrConnectorFault NOTIFICATION-TYPE
    OBJECTS         { sunHwTrapSystemIdentifier, sunHwTrapChassisId, 
                      sunHwTrapProductName, 
                      sunHwTrapSuspectComponentName, sunHwTrapFaultClass, 
                      sunHwTrapFaultCertainty, sunHwTrapFaultMessageID, 
                      sunHwTrapFaultUUID, sunHwTrapAssocObjectId, 
                      sunHwTrapAdditionalInfo }
    STATUS          current
    DESCRIPTION     
            "A slot or connector component is suspected of causing a fault."
    ::= { sunHwTrapPrefix 49 }

sunHwTrapSlotOrConnectorError NOTIFICATION-TYPE
    OBJECTS         { sunHwTrapSystemIdentifier, sunHwTrapChassisId, 
                      sunHwTrapProductName, sunHwTrapComponentName, 
                      sunHwTrapAdditionalInfo, sunHwTrapAssocObjectId }
    STATUS          current
    DESCRIPTION     
            "A sensor associated with a slot or connector has detected an error."
    ::= { sunHwTrapPrefix 50 }

sunHwTrapSlotOrConnectorOk NOTIFICATION-TYPE
    OBJECTS         { sunHwTrapSystemIdentifier, sunHwTrapChassisId, 
                      sunHwTrapProductName, sunHwTrapComponentName, 
                      sunHwTrapAdditionalInfo, sunHwTrapAssocObjectId }
    STATUS          current
    DESCRIPTION     
            "A sensor associated with a slot or connector has returned
             to its normal state."
    ::= { sunHwTrapPrefix 51 }

sunHwTrapComponentFault NOTIFICATION-TYPE
    OBJECTS         { sunHwTrapSystemIdentifier, sunHwTrapChassisId, 
                      sunHwTrapProductName, 
                      sunHwTrapSuspectComponentName, sunHwTrapFaultClass, 
                      sunHwTrapFaultCertainty, sunHwTrapFaultMessageID, 
                      sunHwTrapFaultUUID, sunHwTrapAssocObjectId, 
                      sunHwTrapAdditionalInfo }
    STATUS          current
    DESCRIPTION     
            "A component is suspected of causing a fault. This generic 'component'
             trap is generated when the SNMP agent does not recognize the component
             type."
    ::= { sunHwTrapPrefix 52 }

sunHwTrapComponentError NOTIFICATION-TYPE
    OBJECTS         { sunHwTrapSystemIdentifier, sunHwTrapChassisId, 
                      sunHwTrapProductName, sunHwTrapComponentName, 
                      sunHwTrapAdditionalInfo, sunHwTrapAssocObjectId }
    STATUS          current
    DESCRIPTION     
            "A sensor has detected an error. This generic 'component' trap is
             generated when the SNMP agent does not recognize the component type."
    ::= { sunHwTrapPrefix 53 }

sunHwTrapComponentOk NOTIFICATION-TYPE
    OBJECTS         { sunHwTrapSystemIdentifier, sunHwTrapChassisId, 
                      sunHwTrapProductName, sunHwTrapComponentName, 
                      sunHwTrapAdditionalInfo, sunHwTrapAssocObjectId }
    STATUS          current
    DESCRIPTION     
            "A sensor has returned to its normal state. This generic 'component'
             trap is generated when the SNMP agent does not recognize the component
             type."
    ::= { sunHwTrapPrefix 54 }

sunHwTrapFruInserted NOTIFICATION-TYPE
    OBJECTS         { sunHwTrapSystemIdentifier, sunHwTrapChassisId, 
                      sunHwTrapProductName, sunHwTrapComponentName, 
                      sunHwTrapAssocObjectId }
    STATUS          current
    DESCRIPTION     
            "A field replaceable unit has been inserted into the system."
    ::= { sunHwTrapPrefix 55 }

sunHwTrapFruRemoved NOTIFICATION-TYPE
    OBJECTS         { sunHwTrapSystemIdentifier, sunHwTrapChassisId, 
                      sunHwTrapProductName, sunHwTrapComponentName, 
                      sunHwTrapAssocObjectId }
    STATUS          current
    DESCRIPTION     
            "A field replaceable unit has been removed from the system."
    ::= { sunHwTrapPrefix 56 }

sunHwTrapComponentDisabled NOTIFICATION-TYPE
    OBJECTS         { sunHwTrapSystemIdentifier, sunHwTrapChassisId, 
                      sunHwTrapProductName, sunHwTrapComponentName, 
                      sunHwTrapDisableReason, sunHwTrapAdditionalInfo, 
                      sunHwTrapAssocObjectId }
    STATUS          current
    DESCRIPTION     
            "The component operational state has changed or is changing
             to disabled."
    ::= { sunHwTrapPrefix 57 }

sunHwTrapComponentEnabled NOTIFICATION-TYPE
    OBJECTS         { sunHwTrapSystemIdentifier, sunHwTrapChassisId, 
                      sunHwTrapProductName, sunHwTrapComponentName, 
                      sunHwTrapAdditionalInfo, sunHwTrapAssocObjectId }
    STATUS          current
    DESCRIPTION     
            "The component operational state has changed or is changing
             to enabled."
    ::= { sunHwTrapPrefix 58 }

sunHwTrapPreOSError NOTIFICATION-TYPE
    OBJECTS         { sunHwTrapSystemIdentifier, sunHwTrapChassisId, 
                      sunHwTrapProductName, sunHwTrapAdditionalInfo }
    STATUS          current
    DESCRIPTION     
            "An error has been detected in the period before the operating
             system has taken control of the system."
    ::= { sunHwTrapPrefix 59 }

sunHwTrapHAStateChange NOTIFICATION-TYPE
    OBJECTS         { sunHwTrapSystemIdentifier, sunHwTrapChassisId, 
                      sunHwTrapProductName, sunHwTrapNewHAState, 
                      sunHwTrapOldHAState, sunHwTrapAdditionalInfo }
    STATUS          current
    DESCRIPTION     
            "The high availability component identified by sunHwTrapSystemIdentifier
             has changed state."
    ::= { sunHwTrapPrefix 60 }

sunHwTrapSecurityIntrusion NOTIFICATION-TYPE
    OBJECTS         { sunHwTrapSystemIdentifier, sunHwTrapChassisId, 
                      sunHwTrapProductName, sunHwTrapAdditionalInfo }
    STATUS          current
    DESCRIPTION     
            "An intrusion sensor has detected that someone may have physically
             tampered with the system."
    ::= { sunHwTrapPrefix 61 }

sunHwTrapHardDriveStatus NOTIFICATION-TYPE
    OBJECTS         { sunHwTrapSystemIdentifier, sunHwTrapChassisId, 
                      sunHwTrapProductName, sunHwTrapComponentName, 
                      sunHwTrapHardDriveState }
    STATUS          current
    DESCRIPTION     
            "The hard drive identified by sunHwTrapComponentName has changed state."
    ::= { sunHwTrapPrefix 62 }

sunHwTrapTestTrap NOTIFICATION-TYPE
    OBJECTS         { sunHwTrapSystemIdentifier, sunHwTrapChassisId, 
                      sunHwTrapProductName, sunHwTrapTestMessage }
    STATUS          current
    DESCRIPTION     
            "This is a test trap"
    ::= { sunHwTrapPrefix 63 }

sunHwTrapPowerSupplyFaultCleared NOTIFICATION-TYPE
    OBJECTS         { sunHwTrapSystemIdentifier, sunHwTrapChassisId, 
                      sunHwTrapProductName, sunHwTrapComponentName, 
                      sunHwTrapAssocObjectId, sunHwTrapAdditionalInfo }
    STATUS          current
    DESCRIPTION     
            "A power supply component fault has been cleared."
    ::= { sunHwTrapPrefix 64 }

sunHwTrapFanFaultCleared NOTIFICATION-TYPE
    OBJECTS         { sunHwTrapSystemIdentifier, sunHwTrapChassisId, 
                      sunHwTrapProductName, sunHwTrapComponentName, 
                      sunHwTrapAssocObjectId, sunHwTrapAdditionalInfo }
    STATUS          current
    DESCRIPTION     
            "A fan component fault has been cleared."
    ::= { sunHwTrapPrefix 65 }

sunHwTrapProcessorFaultCleared NOTIFICATION-TYPE
    OBJECTS         { sunHwTrapSystemIdentifier, sunHwTrapChassisId, 
                      sunHwTrapProductName, sunHwTrapComponentName, 
                      sunHwTrapAssocObjectId, sunHwTrapAdditionalInfo }
    STATUS          current
    DESCRIPTION     
            "A processor component fault has been cleared."
    ::= { sunHwTrapPrefix 66 }

sunHwTrapMemoryFaultCleared NOTIFICATION-TYPE
    OBJECTS         { sunHwTrapSystemIdentifier, sunHwTrapChassisId, 
                      sunHwTrapProductName, sunHwTrapComponentName, 
                      sunHwTrapAssocObjectId, sunHwTrapAdditionalInfo }
    STATUS          current
    DESCRIPTION     
            "A memory component fault has been cleared."
    ::= { sunHwTrapPrefix 67 }

sunHwTrapHardDriveFaultCleared NOTIFICATION-TYPE
    OBJECTS         { sunHwTrapSystemIdentifier, sunHwTrapChassisId, 
                      sunHwTrapProductName, sunHwTrapComponentName, 
                      sunHwTrapAssocObjectId, sunHwTrapAdditionalInfo }
    STATUS          current
    DESCRIPTION     
            "A hard drive component fault has been cleared."
    ::= { sunHwTrapPrefix 68 }

sunHwTrapIOFaultCleared NOTIFICATION-TYPE
    OBJECTS         { sunHwTrapSystemIdentifier, sunHwTrapChassisId, 
                      sunHwTrapProductName, sunHwTrapComponentName, 
                      sunHwTrapAssocObjectId, sunHwTrapAdditionalInfo }
    STATUS          current
    DESCRIPTION     
            "An IO subsystem component fault has been cleared."
    ::= { sunHwTrapPrefix 69 }

sunHwTrapSlotOrConnectorFaultCleared NOTIFICATION-TYPE
    OBJECTS         { sunHwTrapSystemIdentifier, sunHwTrapChassisId, 
                      sunHwTrapProductName, sunHwTrapComponentName, 
                      sunHwTrapAssocObjectId, sunHwTrapAdditionalInfo }
    STATUS          current
    DESCRIPTION     
            "A slot or connector component fault has been cleared."
    ::= { sunHwTrapPrefix 70 }

sunHwTrapComponentFaultCleared NOTIFICATION-TYPE
    OBJECTS         { sunHwTrapSystemIdentifier, sunHwTrapChassisId, 
                      sunHwTrapProductName, sunHwTrapComponentName, 
                      sunHwTrapAssocObjectId, sunHwTrapAdditionalInfo }
    STATUS          current
    DESCRIPTION     
            "A component fault has been cleared. This generic 'component'
             trap is generated when the SNMP agent does not recognize the component
             type."
    ::= { sunHwTrapPrefix 71 }

sunHwTrapNotificationObjectGroup OBJECT-GROUP
    OBJECTS         { sunHwTrapSystemIdentifier, sunHwTrapComponentName, 
                      sunHwTrapThresholdType, sunHwTrapThresholdValue, 
                      sunHwTrapSensorValue, 
                      sunHwTrapSuspectComponentName, sunHwTrapFaultClass, 
                      sunHwTrapFaultCertainty, sunHwTrapAdditionalInfo, 
                      sunHwTrapAssocObjectId, sunHwTrapNewHAState, 
                      sunHwTrapOldHAState, sunHwTrapSeverity, 
                      sunHwTrapChassisId, sunHwTrapProductName, 
                      sunHwTrapHardDriveState, sunHwTrapFaultMessageID, 
                      sunHwTrapFaultUUID, sunHwTrapDisableReason, 
                      sunHwTrapTestMessage }
    STATUS          current
    DESCRIPTION     
            "The collection of objects used in notifications."
    ::= { sunHwTrapObjectGroups 2 }

sunHwTrapNotificationsGroup NOTIFICATION-GROUP
    NOTIFICATIONS   { sunHwTrapVoltageFatalThresholdExceeded, 
                      sunHwTrapVoltageFatalThresholdDeasserted, 
                      sunHwTrapVoltageCritThresholdExceeded, 
                      sunHwTrapVoltageCritThresholdDeasserted, 
                      sunHwTrapVoltageNonCritThresholdExceeded, 
                      sunHwTrapVoltageOk, 
                      sunHwTrapTempFatalThresholdExceeded, 
                      sunHwTrapTempFatalThresholdDeasserted, 
                      sunHwTrapTempCritThresholdExceeded, 
                      sunHwTrapTempCritThresholdDeasserted, 
                      sunHwTrapTempNonCritThresholdExceeded, 
                      sunHwTrapTempOk, 
                      sunHwTrapElectricalCurrentFatalThresholdExceeded, 
                      sunHwTrapElectricalCurrentFatalThresholdDeasserted, 
                      sunHwTrapElectricalCurrentCritThresholdExceeded, 
                      sunHwTrapElectricalCurrentCritThresholdDeasserted, 
                      sunHwTrapElectricalCurrentNonCritThresholdExceeded, 
                      sunHwTrapElectricalCurrentOk, 
                      sunHwTrapFanSpeedFatalThresholdExceeded, 
                      sunHwTrapFanSpeedFatalThresholdDeasserted, 
                      sunHwTrapFanSpeedCritThresholdExceeded, 
                      sunHwTrapFanSpeedCritThresholdDeasserted, 
                      sunHwTrapFanSpeedNonCritThresholdExceeded, 
                      sunHwTrapFanSpeedOk, 
                      sunHwTrapSensorFatalThresholdExceeded, 
                      sunHwTrapSensorFatalThresholdDeasserted, 
                      sunHwTrapSensorCritThresholdExceeded, 
                      sunHwTrapSensorCritThresholdDeasserted, 
                      sunHwTrapSensorNonCritThresholdExceeded, 
                      sunHwTrapSensorThresholdOk, 
                      sunHwTrapPowerSupplyFault, 
                      sunHwTrapPowerSupplyFaultCleared, 
                      sunHwTrapPowerSupplyError, sunHwTrapPowerSupplyOk, 
                      sunHwTrapFanFault, sunHwTrapFanFaultCleared, 
                      sunHwTrapFanError, sunHwTrapFanOk, 
                      sunHwTrapProcessorFault, 
                      sunHwTrapProcessorFaultCleared, 
                      sunHwTrapProcessorError, sunHwTrapProcessorOk, 
                      sunHwTrapMemoryFault, sunHwTrapMemoryFaultCleared, 
                      sunHwTrapMemoryError, sunHwTrapMemoryOk, 
                      sunHwTrapHardDriveFault, 
                      sunHwTrapHardDriveFaultCleared, 
                      sunHwTrapHardDriveError, sunHwTrapHardDriveOk, 
                      sunHwTrapIOFault, sunHwTrapIOFaultCleared, 
                      sunHwTrapIOError, sunHwTrapIOOk, 
                      sunHwTrapSlotOrConnectorFault, 
                      sunHwTrapSlotOrConnectorFaultCleared, 
                      sunHwTrapSlotOrConnectorError, 
                      sunHwTrapSlotOrConnectorOk, 
                      sunHwTrapComponentFault, 
                      sunHwTrapComponentFaultCleared, 
                      sunHwTrapComponentError, sunHwTrapComponentOk, 
                      sunHwTrapFruInserted, sunHwTrapFruRemoved, 
                      sunHwTrapComponentDisabled, 
                      sunHwTrapComponentEnabled, sunHwTrapPreOSError, 
                      sunHwTrapHAStateChange, sunHwTrapSecurityIntrusion, 
                      sunHwTrapHardDriveStatus, sunHwTrapTestTrap }
    STATUS          current
    DESCRIPTION     
            "The collection of notifications used to indicate faults, errors,
             and other conditions related to HW components in the system."
    ::= { sunHwTrapNotifGroups 1 }

END -- end of module SUN-HW-TRAP-MIB.
