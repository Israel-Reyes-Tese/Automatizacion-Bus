--
-- This SMIv1 module has been generated by smidump 0.2-cvs. Do not edit.
--

DOTHILL-SANNET-U320-MIB DEFINITIONS ::= BEGIN

IMPORTS
    OBJECT-TYPE
        FROM RFC-1212
    TRAP-TYPE
        FROM RFC-1215
    Counter
        FROM RFC1155-SMI
    enterprises
        FROM SNMPv2-SMI;

sannetU320 OBJECT IDENTIFIER
    ::= { dothill 3320 }

-- sannetU320 MODULE-IDENTITY
--     LAST-UPDATED    "200511142300Z"
--     ORGANIZATION    
--             "Dot Hill Systems Corp."
--     CONTACT-INFO    
--             "
--              Postal:  Dot Hill Systems Corp.
--                       6305 El Camino Real
--                       Carlsbad, CA 92009
--              
--                       Email: support@dothill.com
--              
--                       Phone: 760-931-5500
--                       "
--     DESCRIPTION     
--             "Dot Hill SANNET II MIB"
--     REVISION        "200511142300Z"
--     DESCRIPTION     
--             "Initial Revision FW 414B"
--     ::= { dothill 3320 }


dothill OBJECT IDENTIFIER
    ::= { enterprises 2294 }

snCtlrEventV2 OBJECT IDENTIFIER
    ::= { sannetU320 0 }

snRAIDU320 OBJECT IDENTIFIER
    ::= { sannetU320 1 }

extInterface OBJECT IDENTIFIER
    ::= { snRAIDU320 1 }

ctlrConfiguration OBJECT IDENTIFIER
    ::= { extInterface 1 }

sysInformation OBJECT IDENTIFIER
    ::= { ctlrConfiguration 1 }

cpuType OBJECT-TYPE
    SYNTAX          OCTET STRING
    ACCESS          read-only
    STATUS          mandatory
    DESCRIPTION     
            "CPU type on RAID controller"
    ::= { sysInformation 1 }

cacheSize OBJECT-TYPE
    SYNTAX          INTEGER
    ACCESS          read-only
    STATUS          mandatory
    DESCRIPTION     
            "Cache size on RAID controller, in MB"
    ::= { sysInformation 2 }

memoryType OBJECT-TYPE
    SYNTAX          INTEGER
    ACCESS          read-only
    STATUS          mandatory
    DESCRIPTION     
            "Cache memory type on RAID controller
             0: FPG, 1: EDO, 2: SDRAM, 3: ECC SDRAM"
    ::= { sysInformation 3 }

fwMajorVersion OBJECT-TYPE
    SYNTAX          INTEGER
    ACCESS          read-only
    STATUS          mandatory
    DESCRIPTION     
            "Firmware major version"
    ::= { sysInformation 4 }

fwMinorVersion OBJECT-TYPE
    SYNTAX          INTEGER
    ACCESS          read-only
    STATUS          mandatory
    DESCRIPTION     
            "Firmware minor version"
    ::= { sysInformation 5 }

fwEngineerVersion OBJECT-TYPE
    SYNTAX          INTEGER
    ACCESS          read-only
    STATUS          mandatory
    DESCRIPTION     
            "Firmware engineer version"
    ::= { sysInformation 6 }

brMajorVersion OBJECT-TYPE
    SYNTAX          INTEGER
    ACCESS          read-only
    STATUS          mandatory
    DESCRIPTION     
            "Bootrecord major version"
    ::= { sysInformation 7 }

brMinorVersion OBJECT-TYPE
    SYNTAX          INTEGER
    ACCESS          read-only
    STATUS          mandatory
    DESCRIPTION     
            "Bootrecord minor version"
    ::= { sysInformation 8 }

brEngineerVersion OBJECT-TYPE
    SYNTAX          INTEGER
    ACCESS          read-only
    STATUS          mandatory
    DESCRIPTION     
            "Bootrecord engineer version"
    ::= { sysInformation 9 }

serialNum OBJECT-TYPE
    SYNTAX          INTEGER
    ACCESS          read-only
    STATUS          mandatory
    DESCRIPTION     
            "Serial number"
    ::= { sysInformation 10 }

ctlrName OBJECT-TYPE
    SYNTAX          OCTET STRING
    ACCESS          read-write
    STATUS          mandatory
    DESCRIPTION     
            "Controller name"
    ::= { sysInformation 11 }

ctlrCfgModeFlags OBJECT-TYPE
    SYNTAX          INTEGER
    ACCESS          read-write
    STATUS          mandatory
    DESCRIPTION     
            "Controller configuration mode flags
             BIT 0 : Write Back Status (RW)
             		0: Disabled, 1: Enabled.
             BIT 1 : Motor Spin Up (RW)
             		0: Disabled, 1: Enabled.
             BIT 2 : Power Up SCSI Reset (RW)
             		0: Disabled, 1: Enabled.
             BIT 8 : Battery Backup Supported (RO)
             		0: Not Supported, 1: Supported.
             BIT 9 : Battery Backup Present (RO)
             		0: Absent, 1: Present.
             BIT 12 : ECC Function
             		0: Disabled, 1: Enabled
             BIT 15 : JBOD Mode (RW) - This should be ignored if
             		JBOD Mode Supported is not set.
             		0: Disabled, 1: Enabled.
             BIT 16 : LUN Assignment by SCSI ID (RO)
             		0: Not Supported, 1: Supported.
             BIT 17 : Support SCSI LUN > 0  (RO)
             BIT 18 : Spanning Logical Drive Support
             		0: Not Supported, 1: Supported.
             BIT 19 : JBOD Mode Supported (RO)
             		0: Not Supported, 1: Supported.
             BIT 20 -- BIT 32 : Reserved."
    ::= { sysInformation 12 }

privateLogoString OBJECT-TYPE
    SYNTAX          OCTET STRING
    ACCESS          read-only
    STATUS          mandatory
    DESCRIPTION     
            "Private logo string"
    ::= { sysInformation 13 }

privateLogoVendor OBJECT-TYPE
    SYNTAX          OCTET STRING
    ACCESS          read-only
    STATUS          mandatory
    DESCRIPTION     
            "Private logo vendor string"
    ::= { sysInformation 14 }

privateLogoModel OBJECT-TYPE
    SYNTAX          OCTET STRING
    ACCESS          read-only
    STATUS          mandatory
    DESCRIPTION     
            "Private logo model string"
    ::= { sysInformation 15 }

ctlrUniqueID OBJECT-TYPE
    SYNTAX          OCTET STRING
    ACCESS          read-write
    STATUS          mandatory
    DESCRIPTION     
            "Controller unique identifier"
    ::= { sysInformation 16 }

cachingParams OBJECT IDENTIFIER
    ::= { ctlrConfiguration 2 }

cacheModeFlags OBJECT-TYPE
    SYNTAX          INTEGER
    ACCESS          read-only
    STATUS          mandatory
    DESCRIPTION     
            "Caching mode flags
             BIT 0 : Write Back Status (RW)
             		0: Disabled, 1: Enabled.
             BIT 1 : Read Ahead Disable (RW)
             		0: Enabled, 1: Disabled.
             BIT 2 : Enable/Disable keeping LD/LV
             		off-line after controller initialization
             		if cached write data was lost (RW)
             		0: Disabled, 1: Enabled.
             BIT 3 -- BIT 7 : Reserved (Set to 0).
             BIT 8 : Cache Optimization Option (RW)
             		0: Small/Random I/Os, 1: Large/Sequential I/Os
             BIT 9 -- BIT 15 : Reserved (Set to 0).
             BIT 16 -- BIT 18 : Periodic Cache Sync Period (RW)
             		For interpretation of values, reference
             		Periodic Cache Sync Period Value
             		Cross-Reference List.
             BIT 19 -- BIT 21 : Cache Flush Initiation
             		Threshold (RW)
             		For interpretation of values, reference
             		Cache Flush Initiation Threshold Valid
             		Cross-Reference List.
             BIT 22 -- BIT 25 : Cache Flush Termination
             		Threshold (RW)
             		For interpretation of values, reference
             		Cache Flush Termination Threshold Valid
             		Cross-Reference List.
             BIT 26 -- BIT 31 : Reserved (Set to 0)."
    ::= { cachingParams 1 }

cacheBlkSizeIdx OBJECT-TYPE
    SYNTAX          INTEGER
    ACCESS          read-only
    STATUS          mandatory
    DESCRIPTION     
            "Cache block size index
             BIT 0 -- BIT 3 : Cache Block Size Index
                 Block Size (bytes) = 512 * 2 ** (Block Size Index)
             BIT 4 -- BIT 7 : Reserved (Set to 0)."
    ::= { cachingParams 2 }

cacheTotal OBJECT-TYPE
    SYNTAX          INTEGER
    ACCESS          read-only
    STATUS          mandatory
    DESCRIPTION     
            "Total number of cache blocks"
    ::= { cachingParams 3 }

cacheDirty OBJECT-TYPE
    SYNTAX          INTEGER
    ACCESS          read-only
    STATUS          mandatory
    DESCRIPTION     
            "Number of dirty cache blocks"
    ::= { cachingParams 4 }

diskArrayParams OBJECT IDENTIFIER
    ::= { ctlrConfiguration 3 }

maxRebPriorityIdx OBJECT-TYPE
    SYNTAX          INTEGER
    ACCESS          read-only
    STATUS          mandatory
    DESCRIPTION     
            "Maximum supported rebuild priority index
             0: Low, 1: Normal, 2: Improved, 3: High"
    ::= { diskArrayParams 1 }

minRebPriorityIdx OBJECT-TYPE
    SYNTAX          INTEGER
    ACCESS          read-only
    STATUS          mandatory
    DESCRIPTION     
            "Minimum supported rebuild priority index
             0: Low, 1: Normal, 2: Improved, 3: High"
    ::= { diskArrayParams 2 }

defRebPriorityIdx OBJECT-TYPE
    SYNTAX          INTEGER
    ACCESS          read-only
    STATUS          mandatory
    DESCRIPTION     
            "Default rebuild priority index
             0: Low, 1: Normal, 2: Improved, 3: High"
    ::= { diskArrayParams 3 }

curRebPriorityIdx OBJECT-TYPE
    SYNTAX          INTEGER
    ACCESS          read-only
    STATUS          mandatory
    DESCRIPTION     
            "Current rebuild priority index
             0: Low, 1: Normal, 2: Improved, 3: High"
    ::= { diskArrayParams 4 }

writeVerifyModeFlags OBJECT-TYPE
    SYNTAX          INTEGER
    ACCESS          read-only
    STATUS          mandatory
    DESCRIPTION     
            "Write-verify mode flags
             BIT 0 : Write-Verify on Normal Writes (RW)
             		0: Disabled, 1: Enabled.
             BIT 1 : Write-Verify on Initialization Writes (RW)
             		0: Disabled, 1: Enabled.
             BIT 2 : Write-Verify on Rebuild Writes (RW)
             		0: Disabled, 1: Enabled.
             BIT 3 -- BIT 7 : Reserved (Set to 0)."
    ::= { diskArrayParams 5 }

hostSideParams OBJECT IDENTIFIER
    ::= { ctlrConfiguration 4 }

maxQueuedIOCnt OBJECT-TYPE
    SYNTAX          INTEGER
    ACCESS          read-only
    STATUS          mandatory
    DESCRIPTION     
            "Maximum supported host queued I/O count
             == N (> 0) ==> Count = 2 ** ( N - 1 )."
    ::= { hostSideParams 1 }

minQueuedIOCnt OBJECT-TYPE
    SYNTAX          INTEGER
    ACCESS          read-only
    STATUS          mandatory
    DESCRIPTION     
            "Minimum supported host queued I/O count
             == N (> 0) ==> Count = 2 ** ( N - 1 )."
    ::= { hostSideParams 2 }

defQueuedIOCnt OBJECT-TYPE
    SYNTAX          INTEGER
    ACCESS          read-only
    STATUS          mandatory
    DESCRIPTION     
            "Default host queued I/O count
             == N (> 0) ==> Count = 2 ** ( N - 1 )."
    ::= { hostSideParams 3 }

curQueuedIOCnt OBJECT-TYPE
    SYNTAX          INTEGER
    ACCESS          read-only
    STATUS          mandatory
    DESCRIPTION     
            "Current host queued I/O count
             == 0 - Automatically Computed.
             == N (> 0) ==> Count = 2 ** ( N - 1 )."
    ::= { hostSideParams 4 }

maxLunNum OBJECT-TYPE
    SYNTAX          INTEGER
    ACCESS          read-only
    STATUS          mandatory
    DESCRIPTION     
            "Maximum LUNs per host SCSI ID(SCSI-to-SCSI only)
             == N ==> LUNs = 2 ** ( N - 1 )"
    ::= { hostSideParams 5 }

minLunNum OBJECT-TYPE
    SYNTAX          INTEGER
    ACCESS          read-only
    STATUS          mandatory
    DESCRIPTION     
            "Minimum LUNs per host SCSI ID(SCSI-to-SCSI only)
             == N ==> LUNs = 2 ** ( N - 1 )"
    ::= { hostSideParams 6 }

defLunNum OBJECT-TYPE
    SYNTAX          INTEGER
    ACCESS          read-only
    STATUS          mandatory
    DESCRIPTION     
            "Default LUNs per host SCSI ID(SCSI-to-SCSI only)
             == N ==> LUNs = 2 ** ( N - 1 )"
    ::= { hostSideParams 7 }

curLunNum OBJECT-TYPE
    SYNTAX          INTEGER
    ACCESS          read-only
    STATUS          mandatory
    DESCRIPTION     
            "Current LUNs per host SCSI ID(SCSI-to-SCSI only)
             == N ==> LUNs = 2 ** ( N - 1 )"
    ::= { hostSideParams 8 }

driveSideParams OBJECT IDENTIFIER
    ::= { ctlrConfiguration 5 }

modeFlags OBJECT-TYPE
    SYNTAX          INTEGER
    ACCESS          read-only
    STATUS          mandatory
    DESCRIPTION     
            "mode flags of drive-side interface parameters
             BIT 0 : Motor Spin Up (RW)
             		0: Disabled, 1: Enabled.
             BIT 1 : Power Up SCSI Reset (RW)
             		0: Disabled, 1: Enabled.
             BIT 2 -- BIT 15 : Reserved (Set to 0)
             BITS 16-17: Drive Failure Prediction (SMART) Mode:
             			== 0 - Disabled.
             			== 1 - Detect only.
             			== 2 - Clone drive and keep drive cloned.
             			== 3 - Clone drive and replace when cloning complete.
             BIT 18 : Auto Assign Global Spare Drive (RW)
             		0: Disabled, 1: Enabled.
             BIT 19 -- BIT 31 : Reserved (Set to 0)"
    ::= { driveSideParams 1 }

maxAccessDelayTime OBJECT-TYPE
    SYNTAX          INTEGER
    ACCESS          read-only
    STATUS          mandatory
    DESCRIPTION     
            "Maximum time to delay prior to first disk access(in 5 seconds unit)
             == N ==> Delay = N * 5 seconds."
    ::= { driveSideParams 2 }

minAccessDelayTime OBJECT-TYPE
    SYNTAX          INTEGER
    ACCESS          read-only
    STATUS          mandatory
    DESCRIPTION     
            "Minimum time to delay prior to first disk access(in 5 seconds unit)
             == N ==> Delay = N * 5 seconds."
    ::= { driveSideParams 3 }

defAccessDelayTime OBJECT-TYPE
    SYNTAX          INTEGER
    ACCESS          read-only
    STATUS          mandatory
    DESCRIPTION     
            "Default time to delay prior to first disk access(in 5 seconds unit)
             == N ==> Delay = N * 5 seconds."
    ::= { driveSideParams 4 }

curAccessDelayTime OBJECT-TYPE
    SYNTAX          INTEGER
    ACCESS          read-only
    STATUS          mandatory
    DESCRIPTION     
            "Current time to delay prior to first disk access(in 5 seconds unit)
             == 0 ==> No Delay.
             == N ==> Delay = N * 5 seconds."
    ::= { driveSideParams 5 }

maxTagCnt OBJECT-TYPE
    SYNTAX          INTEGER
    ACCESS          read-only
    STATUS          mandatory
    DESCRIPTION     
            "Maximum drive-side SCSI tags per drive(Tags = 2**(N-1))"
    ::= { driveSideParams 6 }

minTagCnt OBJECT-TYPE
    SYNTAX          INTEGER
    ACCESS          read-only
    STATUS          mandatory
    DESCRIPTION     
            "Minimum drive-side SCSI tags per drive(Tags = 2**(N-1))"
    ::= { driveSideParams 7 }

defTagCnt OBJECT-TYPE
    SYNTAX          INTEGER
    ACCESS          read-only
    STATUS          mandatory
    DESCRIPTION     
            "Default drive-side SCSI tags per drive(Tags = 2**(N-1))"
    ::= { driveSideParams 8 }

curTagCnt OBJECT-TYPE
    SYNTAX          INTEGER
    ACCESS          read-only
    STATUS          mandatory
    DESCRIPTION     
            "Current  drive-side SCSI tags per drive(Tags = 2**(N-1), 0: Disabled)"
    ::= { driveSideParams 9 }

defIOTimeout OBJECT-TYPE
    SYNTAX          INTEGER
    ACCESS          read-only
    STATUS          mandatory
    DESCRIPTION     
            "Default drive-side SCSI I/O timeout(in 10ms units)"
    ::= { driveSideParams 10 }

curIOTimeout OBJECT-TYPE
    SYNTAX          INTEGER
    ACCESS          read-only
    STATUS          mandatory
    DESCRIPTION     
            "Current drive-side SCSI I/O timeout(in 10ms units)"
    ::= { driveSideParams 11 }

defDrvChkPeriod OBJECT-TYPE
    SYNTAX          INTEGER
    ACCESS          read-only
    STATUS          mandatory
    DESCRIPTION     
            "Default drive-side SCSI drive check period(10ms units)"
    ::= { driveSideParams 12 }

curDrvChkPeriod OBJECT-TYPE
    SYNTAX          INTEGER
    ACCESS          read-only
    STATUS          mandatory
    DESCRIPTION     
            "Current drive-side SCSI drive check period(10ms units)"
    ::= { driveSideParams 13 }

defSaftePollingPeriod OBJECT-TYPE
    SYNTAX          INTEGER
    ACCESS          read-only
    STATUS          mandatory
    DESCRIPTION     
            "Default SAFTE polling period(10ms units)"
    ::= { driveSideParams 14 }

curSaftePollingPeriod OBJECT-TYPE
    SYNTAX          INTEGER
    ACCESS          read-only
    STATUS          mandatory
    DESCRIPTION     
            "Current SAFTE polling period(10ms units)"
    ::= { driveSideParams 15 }

defAutoDetectPeriod OBJECT-TYPE
    SYNTAX          INTEGER
    ACCESS          read-only
    STATUS          mandatory
    DESCRIPTION     
            "Default auto-detect failed drive swaped check period(10ms units)"
    ::= { driveSideParams 16 }

curAutoDetectPeriod OBJECT-TYPE
    SYNTAX          INTEGER
    ACCESS          read-only
    STATUS          mandatory
    DESCRIPTION     
            "Current auto-detect failed drive swaped check period(10ms units)"
    ::= { driveSideParams 17 }

redundantParams OBJECT IDENTIFIER
    ::= { ctlrConfiguration 6 }

redCtlrCfg OBJECT-TYPE
    SYNTAX          INTEGER
    ACCESS          read-only
    STATUS          mandatory
    DESCRIPTION     
            "Redundant controller configuration
             For Reading:
               BITS 0 -- 1:
             		== 0xff - RC Functionality Not Supported.
             		== 0 - RC Functionality Disabled.
             		== 1 - RC Functionality Enabled as Primary.
             		== 2 - RC Functionality Enabled as Secondary.
             		== 3 - RC Functionality Enabled in Autoconfigure Mode.
               BITS 2 -- 6 : Reserved.
               BIT 7 : State of Controller Location Signal Support:
             			0: Not supported, 1: Supported.
             For Writing:
             	    == 0 - Disable Redundant Controller Functionality.
             	    == 1 - Enable RC Functionality and set role to Primary.
             	    == 2 - Enable RC Functionality and set role to Primary.
             	    == 3 - Enable RC Functionality and automatically select role.
             	    == 0x81 - Deassert Reset (WO).
             	    == 0xc1 - Simulate Primary Controller Failure (WO).
             	    == 0xc2 - Simulate Secondary Controller	Failure (WO).
             	    == 0xc3 - Force secondary controller to	kill primary controller Failure (WO).
             	    == 0xc4 - Force primary controller to kill secondary controller Failure (WO)."
    ::= { redundantParams 1 }

redCtlrModeFlags OBJECT-TYPE
    SYNTAX          INTEGER
    ACCESS          read-only
    STATUS          mandatory
    DESCRIPTION     
            "Redundant controller mode flags
             BIT 0 : Cache Synchronization (RW)
             	      0 : Cache NOT Synchronized, 1 : Cache Synchronized
             BIT 1 : Host Channel Failover Mode (RW)
             	      0 : Shared host bus, 1 : Independent host bus
             BIT 2 : Local/Remote Redundant Mode (RW)
             	      0 : Local Redundant, 1 : Remote Redundant
             BITS 2-14 : Reserved.
             BIT 15 : Secondary RS-232 Port Status (RW)
             	      0 : Port Disabled, 1 : Port Enabled"
    ::= { redundantParams 2 }

redCtlrCommType OBJECT-TYPE
    SYNTAX          INTEGER
    ACCESS          read-only
    STATUS          mandatory
    DESCRIPTION     
            "Redundant controller communication channel type
             == 0 - RS-232
             == 1 - SCSI/Fibre Channel"
    ::= { redundantParams 3 }

redCtlrStatus OBJECT-TYPE
    SYNTAX          INTEGER
    ACCESS          read-only
    STATUS          mandatory
    DESCRIPTION     
            "Redundant controller status
             BIT 0 -- BIT 5 : Current Status
             				== 0 - Inactive.
             			    == 1 - Scanning.
             			    == 0x11 - Detected.
             			    == 0x12 - Enabled.
             				== 0x3f - Controller Failed.
             BIT 6 : Original Controller Role (prior to first controller failure):
             		0: Primary, 1: Secondary.
             BIT 7 : Current Controller Role
             		0: Primary, 1: Secondary."
    ::= { redundantParams 4 }

ldTable OBJECT-TYPE
    SYNTAX          SEQUENCE OF LdEntry
    ACCESS          not-accessible
    STATUS          mandatory
    DESCRIPTION     
            "Logical drive table"
    ::= { extInterface 2 }

ldEntry OBJECT-TYPE
    SYNTAX          LdEntry
    ACCESS          not-accessible
    STATUS          mandatory
    DESCRIPTION     
            "Logical drive entry"
    INDEX           { ldIndex }
    ::= { ldTable 1 }

LdEntry ::=
    SEQUENCE {
        ldIndex                         Gauge,
        ldID                            OCTET STRING,
        ldSize                          INTEGER,
        ldBlkSizeIdx                    INTEGER,
        ldOpModes                       INTEGER,
        ldStatus                        INTEGER,
        ldState                         INTEGER,
        ldTotalDrvCnt                   INTEGER,
        ldOnlineDrvCnt                  INTEGER,
        ldSpareDrvCnt                   INTEGER,
        ldFailedDrvCnt                  INTEGER
    }

ldIndex OBJECT-TYPE
    SYNTAX          Gauge
    ACCESS          not-accessible
    STATUS          mandatory
    DESCRIPTION     
            "Logical drive index"
    ::= { ldEntry 1 }

ldID OBJECT-TYPE
    SYNTAX          OCTET STRING
    ACCESS          read-only
    STATUS          mandatory
    DESCRIPTION     
            "Logical drive identifier"
    ::= { ldEntry 2 }

ldSize OBJECT-TYPE
    SYNTAX          INTEGER
    ACCESS          read-only
    STATUS          mandatory
    DESCRIPTION     
            "Logical drive size, in Blocks"
    ::= { ldEntry 3 }

ldBlkSizeIdx OBJECT-TYPE
    SYNTAX          INTEGER
    ACCESS          read-only
    STATUS          mandatory
    DESCRIPTION     
            "Block Size = (Block Size Index) Power of 2"
    ::= { ldEntry 4 }

ldOpModes OBJECT-TYPE
    SYNTAX          INTEGER
    ACCESS          read-write
    STATUS          mandatory
    DESCRIPTION     
            "Logical drive operating modes
             BITS 0-3 : RAID Level (RO):
             		  0 : Single Drive
             		  1 : NON-RAID
             		  2 : RAID 0
             		  3 : RAID 1
             		  4 : RAID 3
             		  5 : RAID 4
             		  6 : RAID 5
             		  0xf: NOT DEFINED
             BITS 4-6 : Reserved (Set to 0).
             BIT 7 : Logical Drive Assignment (R/W):
             		  If CLEAR, Logical Drive is assigned to Primary Controller.
             		  If SET, Logical Drive is assigned to Secondary Controller."
    ::= { ldEntry 5 }

ldStatus OBJECT-TYPE
    SYNTAX          INTEGER
    ACCESS          read-only
    STATUS          mandatory
    DESCRIPTION     
            "Logical drive status
             BITS 0-2 : Status Code (RO):
             		  0 : Good
             		  1 : Rebuilding
             		  2 : Initializing
             		  3 : Degraded
             		  4 : Dead
             		  5 : Invalid
             		  6 : Incomplete
             		  7 : Drive Missing
             BITS 3-6 : Reserved.
             BITS 7 : Logical Drive Off-line (RW)."
    ::= { ldEntry 6 }

ldState OBJECT-TYPE
    SYNTAX          INTEGER
    ACCESS          read-only
    STATUS          mandatory
    DESCRIPTION     
            "Logical drive state
             BIT 0 : If SET, in process of rebuilding
             		(degraded mode) or checking/updating
             		Logical Drive Parity (LD is 'good').
             BIT 1 : If SET, in process of expanding Logical Drive.
             BIT 2 : If SET, in process of adding SCSI drives
             		to Logical Drive.
             BIT 3-5: Reserved.
             BIT 6 : If SET, add SCSI drives operation is paused.
             BIT 7 : Reserved."
    ::= { ldEntry 7 }

ldTotalDrvCnt OBJECT-TYPE
    SYNTAX          INTEGER
    ACCESS          read-only
    STATUS          mandatory
    DESCRIPTION     
            "Total hard drive count on logical drive"
    ::= { ldEntry 8 }

ldOnlineDrvCnt OBJECT-TYPE
    SYNTAX          INTEGER
    ACCESS          read-only
    STATUS          mandatory
    DESCRIPTION     
            "On-Line hard drvie count on logical drive"
    ::= { ldEntry 9 }

ldSpareDrvCnt OBJECT-TYPE
    SYNTAX          INTEGER
    ACCESS          read-only
    STATUS          mandatory
    DESCRIPTION     
            "Spare hard drive count on logical drive"
    ::= { ldEntry 10 }

ldFailedDrvCnt OBJECT-TYPE
    SYNTAX          INTEGER
    ACCESS          read-only
    STATUS          mandatory
    DESCRIPTION     
            "Failed hard drive count on logical drive"
    ::= { ldEntry 11 }

lvTable OBJECT-TYPE
    SYNTAX          SEQUENCE OF LvEntry
    ACCESS          not-accessible
    STATUS          mandatory
    DESCRIPTION     
            "Logical volume table"
    ::= { extInterface 3 }

lvEntry OBJECT-TYPE
    SYNTAX          LvEntry
    ACCESS          not-accessible
    STATUS          mandatory
    DESCRIPTION     
            "Logical volume entry"
    INDEX           { lvIndex }
    ::= { lvTable 1 }

LvEntry ::=
    SEQUENCE {
        lvIndex                         Gauge,
        lvID                            OCTET STRING,
        lvSize                          INTEGER,
        lvBlkSizeIdx                    INTEGER,
        lvOpModes                       INTEGER,
        lvLdCount                       INTEGER,
        lvLdList                        OCTET STRING
    }

lvIndex OBJECT-TYPE
    SYNTAX          Gauge
    ACCESS          not-accessible
    STATUS          mandatory
    DESCRIPTION     
            "Logical volume index"
    ::= { lvEntry 1 }

lvID OBJECT-TYPE
    SYNTAX          OCTET STRING
    ACCESS          read-only
    STATUS          mandatory
    DESCRIPTION     
            "Logical volume identifier"
    ::= { lvEntry 2 }

lvSize OBJECT-TYPE
    SYNTAX          INTEGER
    ACCESS          read-only
    STATUS          mandatory
    DESCRIPTION     
            "Logical volume size, in Blocks"
    ::= { lvEntry 3 }

lvBlkSizeIdx OBJECT-TYPE
    SYNTAX          INTEGER
    ACCESS          read-only
    STATUS          mandatory
    DESCRIPTION     
            "Block Size = (Block Size Index) Power of 2"
    ::= { lvEntry 4 }

lvOpModes OBJECT-TYPE
    SYNTAX          INTEGER
    ACCESS          read-write
    STATUS          mandatory
    DESCRIPTION     
            "Logical volume operating modes
             BITS 0-6 : Reserved (Set to 0).
             BIT 7 : Logical Volume Assignment (R/W):
             	    If CLEAR, Logical Volume is assigned to Primary Controller.
             		If SET, Logical Volume is assigned to Secondary Controller."
    ::= { lvEntry 5 }

lvLdCount OBJECT-TYPE
    SYNTAX          INTEGER
    ACCESS          read-only
    STATUS          mandatory
    DESCRIPTION     
            "Logical drive counts in this logical volume"
    ::= { lvEntry 6 }

lvLdList OBJECT-TYPE
    SYNTAX          OCTET STRING
    ACCESS          read-only
    STATUS          mandatory
    DESCRIPTION     
            "Logical drive identifiers list in this logical volume"
    ::= { lvEntry 7 }

partTable OBJECT-TYPE
    SYNTAX          SEQUENCE OF PartEntry
    ACCESS          not-accessible
    STATUS          mandatory
    DESCRIPTION     
            "Partition table"
    ::= { extInterface 4 }

partEntry OBJECT-TYPE
    SYNTAX          PartEntry
    ACCESS          not-accessible
    STATUS          mandatory
    DESCRIPTION     
            "Partition entry"
    INDEX           { partIndex }
    ::= { partTable 1 }

PartEntry ::=
    SEQUENCE {
        partIndex                       Gauge,
        partLdLvID                      OCTET STRING,
        partOffset                      INTEGER,
        partSize                        INTEGER
    }

partIndex OBJECT-TYPE
    SYNTAX          Gauge
    ACCESS          not-accessible
    STATUS          mandatory
    DESCRIPTION     
            "Partition index"
    ::= { partEntry 1 }

partLdLvID OBJECT-TYPE
    SYNTAX          OCTET STRING
    ACCESS          read-only
    STATUS          mandatory
    DESCRIPTION     
            "Logical drive/Logical volume identifier"
    ::= { partEntry 2 }

partOffset OBJECT-TYPE
    SYNTAX          INTEGER
    ACCESS          read-only
    STATUS          mandatory
    DESCRIPTION     
            "Partition base offset"
    ::= { partEntry 3 }

partSize OBJECT-TYPE
    SYNTAX          INTEGER
    ACCESS          read-only
    STATUS          mandatory
    DESCRIPTION     
            "Partition size, in Blocks"
    ::= { partEntry 4 }

lunTable OBJECT-TYPE
    SYNTAX          SEQUENCE OF LunEntry
    ACCESS          not-accessible
    STATUS          mandatory
    DESCRIPTION     
            "LUN table"
    ::= { extInterface 5 }

lunEntry OBJECT-TYPE
    SYNTAX          LunEntry
    ACCESS          not-accessible
    STATUS          mandatory
    DESCRIPTION     
            "LUN entry"
    INDEX           { lunIndex }
    ::= { lunTable 1 }

LunEntry ::=
    SEQUENCE {
        lunIndex                        Gauge,
        lunChl                          INTEGER,
        lunID                           INTEGER,
        lunNum                          INTEGER,
        lunLdLvID                       OCTET STRING,
        lunPartIdx                      INTEGER
    }

lunIndex OBJECT-TYPE
    SYNTAX          Gauge
    ACCESS          not-accessible
    STATUS          mandatory
    DESCRIPTION     
            "LUN index"
    ::= { lunEntry 1 }

lunChl OBJECT-TYPE
    SYNTAX          INTEGER
    ACCESS          read-only
    STATUS          mandatory
    DESCRIPTION     
            "Logical host channel number"
    ::= { lunEntry 2 }

lunID OBJECT-TYPE
    SYNTAX          INTEGER
    ACCESS          read-only
    STATUS          mandatory
    DESCRIPTION     
            "Host-side SCSI ID"
    ::= { lunEntry 3 }

lunNum OBJECT-TYPE
    SYNTAX          INTEGER
    ACCESS          read-only
    STATUS          mandatory
    DESCRIPTION     
            "Host-side SCSI LUN"
    ::= { lunEntry 4 }

lunLdLvID OBJECT-TYPE
    SYNTAX          OCTET STRING
    ACCESS          read-only
    STATUS          mandatory
    DESCRIPTION     
            "Logical drive/Logical volume identifier"
    ::= { lunEntry 5 }

lunPartIdx OBJECT-TYPE
    SYNTAX          INTEGER
    ACCESS          read-only
    STATUS          mandatory
    DESCRIPTION     
            "Partition index of logical drive or logical volume"
    ::= { lunEntry 6 }

hddTable OBJECT-TYPE
    SYNTAX          SEQUENCE OF HddEntry
    ACCESS          not-accessible
    STATUS          mandatory
    DESCRIPTION     
            "Hard disk drive table"
    ::= { extInterface 6 }

hddEntry OBJECT-TYPE
    SYNTAX          HddEntry
    ACCESS          not-accessible
    STATUS          mandatory
    DESCRIPTION     
            "Hard disk drive entry"
    INDEX           { hddIndex }
    ::= { hddTable 1 }

HddEntry ::=
    SEQUENCE {
        hddIndex                        Gauge,
        hddLogChlNum                    INTEGER,
        hddPhyChlNum                    INTEGER,
        hddScsiId                       INTEGER,
        hddScsiLun                      INTEGER,
        hddLdId                         OCTET STRING,
        hddSize                         INTEGER,
        hddBlkSizeIdx                   INTEGER,
        hddSpeed                        INTEGER,
        hddDataWidth                    INTEGER,
        hddStatus                       INTEGER,
        hddState                        INTEGER,
        hddSlotNum                      INTEGER,
        hddResvSpace                    INTEGER,
        hddModelStr                     OCTET STRING,
        hddFwRevStr                     OCTET STRING,
        hddSerialNum                    OCTET STRING
    }

hddIndex OBJECT-TYPE
    SYNTAX          Gauge
    ACCESS          not-accessible
    STATUS          mandatory
    DESCRIPTION     
            "Hard disk drive index"
    ::= { hddEntry 1 }

hddLogChlNum OBJECT-TYPE
    SYNTAX          INTEGER
    ACCESS          read-only
    STATUS          mandatory
    DESCRIPTION     
            "Logical channel number to which hard disk drive is connected"
    ::= { hddEntry 2 }

hddPhyChlNum OBJECT-TYPE
    SYNTAX          INTEGER
    ACCESS          read-only
    STATUS          mandatory
    DESCRIPTION     
            "Physical channel number to which hard disk drive is connected"
    ::= { hddEntry 3 }

hddScsiId OBJECT-TYPE
    SYNTAX          INTEGER
    ACCESS          read-only
    STATUS          mandatory
    DESCRIPTION     
            "SCSI ID of hard disk drive"
    ::= { hddEntry 4 }

hddScsiLun OBJECT-TYPE
    SYNTAX          INTEGER
    ACCESS          read-only
    STATUS          mandatory
    DESCRIPTION     
            "SCSI Lun of hard disk drive"
    ::= { hddEntry 5 }

hddLdId OBJECT-TYPE
    SYNTAX          OCTET STRING
    ACCESS          read-only
    STATUS          mandatory
    DESCRIPTION     
            "Logical drive ID to which hard disk drive is belonged
             0 : If Drive Status == Spare Drive, then drive is Global Spare.
             Otherwise, indicates drive does not currently belong to any logical drive."
    ::= { hddEntry 6 }

hddSize OBJECT-TYPE
    SYNTAX          INTEGER
    ACCESS          read-only
    STATUS          mandatory
    DESCRIPTION     
            "Hard disk drive size, in Blocks"
    ::= { hddEntry 7 }

hddBlkSizeIdx OBJECT-TYPE
    SYNTAX          INTEGER
    ACCESS          read-only
    STATUS          mandatory
    DESCRIPTION     
            "Block Size = (Block Size Index) Power of 2"
    ::= { hddEntry 8 }

hddSpeed OBJECT-TYPE
    SYNTAX          INTEGER
    ACCESS          read-only
    STATUS          mandatory
    DESCRIPTION     
            "Hard disk drive data transfer speed, in ns"
    ::= { hddEntry 9 }

hddDataWidth OBJECT-TYPE
    SYNTAX          INTEGER
    ACCESS          read-only
    STATUS          mandatory
    DESCRIPTION     
            "Hard disk drive data transfer width
             0: Narrow 1: Wide"
    ::= { hddEntry 10 }

hddStatus OBJECT-TYPE
    SYNTAX          INTEGER
    ACCESS          read-only
    STATUS          mandatory
    DESCRIPTION     
            "Hard disk drive status
             0 : New Drive
             1 : On-Line Drive
             2 : Used Drive
             3 : Spare Drive
             4 : Drive Initialization in Progress
             5 : Drive Rebuild in Progress
             6 : Add Drive to Logical Drive in Progress
             9 : Global Spare Drive
             0x11 : Drive is in process of Cloning another Drive
             0x12 : Drive is a valid Clone of another Drive
             0x13 : Drive is in process of Copying from another Drive
             		(for Copy/Replace LD Expansion function)
             0x3f : Drive Absent
             0x8x: SCSI Device (Type x)
             0xfc : Missing Global Spare Drive
             0xfd : Missing Spare Drive
             0xfe : Missing Drive
             0xff : Failed Drive"
    ::= { hddEntry 11 }

hddState OBJECT-TYPE
    SYNTAX          INTEGER
    ACCESS          read-only
    STATUS          mandatory
    DESCRIPTION     
            "Hard disk drive state
             BITS 0 -- 6: Reserved.
             BIT 7: Drive off-line (RW)."
    ::= { hddEntry 12 }

hddSlotNum OBJECT-TYPE
    SYNTAX          INTEGER
    ACCESS          read-only
    STATUS          mandatory
    DESCRIPTION     
            "Hard disk drive slot number, 0: N/A"
    ::= { hddEntry 13 }

hddResvSpace OBJECT-TYPE
    SYNTAX          INTEGER
    ACCESS          read-only
    STATUS          mandatory
    DESCRIPTION     
            "Hard disk drive reserved space
             Drive Reserved Space Size (64KB units). When set,
             the index into the 'Valid Value List' should
             be passed in rather than the size itself.
             This will trigger a format or unformat
             operation (depending on the direction of the
             change) is performed on the drive reserved
             space. Note that it is an error to try and
             change a the size of the reserved space
             without unformatting first or to try and
             unformat a drive that has been configured as
             a LD member or as a spare/clone."
    ::= { hddEntry 14 }

hddModelStr OBJECT-TYPE
    SYNTAX          OCTET STRING
    ACCESS          read-only
    STATUS          mandatory
    DESCRIPTION     
            "Hard disk drive model string"
    ::= { hddEntry 15 }

hddFwRevStr OBJECT-TYPE
    SYNTAX          OCTET STRING
    ACCESS          read-only
    STATUS          mandatory
    DESCRIPTION     
            "Hard disk drive firmware revision string"
    ::= { hddEntry 16 }

hddSerialNum OBJECT-TYPE
    SYNTAX          OCTET STRING
    ACCESS          read-only
    STATUS          mandatory
    DESCRIPTION     
            "Hard disk drive serial number"
    ::= { hddEntry 17 }

chlTable OBJECT-TYPE
    SYNTAX          SEQUENCE OF ChlEntry
    ACCESS          not-accessible
    STATUS          mandatory
    DESCRIPTION     
            "SCSI/Fibre channel table"
    ::= { extInterface 7 }

chlEntry OBJECT-TYPE
    SYNTAX          ChlEntry
    ACCESS          not-accessible
    STATUS          mandatory
    DESCRIPTION     
            "SCSI/Fibre channel entry"
    INDEX           { chlIndex }
    ::= { chlTable 1 }

ChlEntry ::=
    SEQUENCE {
        chlIndex                        Gauge,
        chlLogChlNum                    INTEGER,
        chlPhyChlNum                    INTEGER,
        chlType                         INTEGER,
        chlChipType                     INTEGER,
        chlMaxSupId                     INTEGER,
        chlMaxSupLun                    INTEGER,
        chlMode                         INTEGER,
        chlScsiIdBitmap                 INTEGER,
        chlFibreIdBase                  INTEGER,
        chlHostIdBitmap                 INTEGER,
        chlDrvPid                       INTEGER,
        chlDrvSid                       INTEGER,
        chlMaxTxPeriod                  INTEGER,
        chlMinTxPeriod                  INTEGER,
        chlDefTxPeriod                  INTEGER,
        chlCurTxPeriod                  INTEGER,
        chlMaxTxWidth                   INTEGER,
        chlMinTxWidth                   INTEGER,
        chlDefTxWidth                   INTEGER,
        chlCurTxWidth                   INTEGER,
        chlMaxTagCnt                    INTEGER,
        chlDefTagCnt                    INTEGER
    }

chlIndex OBJECT-TYPE
    SYNTAX          Gauge
    ACCESS          not-accessible
    STATUS          mandatory
    DESCRIPTION     
            "SCSI/Fibre channel index"
    ::= { chlEntry 1 }

chlLogChlNum OBJECT-TYPE
    SYNTAX          INTEGER
    ACCESS          read-only
    STATUS          mandatory
    DESCRIPTION     
            "Logical channel number"
    ::= { chlEntry 2 }

chlPhyChlNum OBJECT-TYPE
    SYNTAX          INTEGER
    ACCESS          read-only
    STATUS          mandatory
    DESCRIPTION     
            "Physical channel number"
    ::= { chlEntry 3 }

chlType OBJECT-TYPE
    SYNTAX          INTEGER
    ACCESS          read-only
    STATUS          mandatory
    DESCRIPTION     
            "Channel type
             0 : SCSI
             1 : PCI
             2 : FIBRE
             3 : Parallel-IDE
             	4 : SATA
             0x11 : Network-IO - LAN
             0x40 : Fixed Redundant Communication Channel
             Others : not defined"
    ::= { chlEntry 4 }

chlChipType OBJECT-TYPE
    SYNTAX          INTEGER
    ACCESS          read-only
    STATUS          mandatory
    DESCRIPTION     
            "Channel interface chip type"
    ::= { chlEntry 5 }

chlMaxSupId OBJECT-TYPE
    SYNTAX          INTEGER
    ACCESS          read-only
    STATUS          mandatory
    DESCRIPTION     
            "Max supported SCSI id"
    ::= { chlEntry 6 }

chlMaxSupLun OBJECT-TYPE
    SYNTAX          INTEGER
    ACCESS          read-only
    STATUS          mandatory
    DESCRIPTION     
            "Max supported SCSI lun per id"
    ::= { chlEntry 7 }

chlMode OBJECT-TYPE
    SYNTAX          INTEGER
    ACCESS          read-only
    STATUS          mandatory
    DESCRIPTION     
            "Channel mode flags
             BIT 0 : Channel Mode (RW)
             		0: Drive Mode, 1: Host Mode (or dedicated RCC).
             BIT 1 : Channel SCSI Termination (SCSI Only) (RW)
             		0: Disabled, 1: Enabled.
             BIT 2 : SCSI Parity (SCSI Only) (RW)
             		0: Disabled, 1: Enabled.
             BIT 3 : Support LUN > 0 (RW)
             		0: Disabled, 1: Enabled.
             BIT 8 : Supports Redundant Channel Communication (RO)
             		0: Does NOT support, 1: Does support.
             BIT 9 : Redundant Controller Communication Enable (RW)
             	    Note that if RCC is enabled on host-mode
             	    channels, then the channel is a dedicated
             	    RCC channel. If it is enabled on drive-mode
             	    channels, then RCC transactions are multiplexed
             	    with standard drive-side IOs on the channel.
             		0: Disabled, 1: Enabled.
             BIT 12 : 'Shelf' Status Input (SCSI Only) (RW)
             		0: Disabled, 1: Enabled.
             BIT 13 : 'Swap' Status Input (SCSI Only) (RW)
             		0: Disabled, 1: Enabled.
             BIT 14 : 'Drive Failure' Status Output (SCSI Only) (RW)
             		0: Disabled, 1: Enabled.
             BIT 15 : Reserved."
    ::= { chlEntry 8 }

chlScsiIdBitmap OBJECT-TYPE
    SYNTAX          INTEGER
    ACCESS          read-only
    STATUS          mandatory
    DESCRIPTION     
            "SCSI host/drive channel id bitmap
             BITS 0-15 : Primary Controller SCSI ID Bitmap
             BITS 16-31 : Secondary Controller SCSI ID Bitmap"
    ::= { chlEntry 9 }

chlFibreIdBase OBJECT-TYPE
    SYNTAX          INTEGER
    ACCESS          read-only
    STATUS          mandatory
    DESCRIPTION     
            "Fibre host channel id base in units of 0x10.
             Note that this is ignored for SCSI channels"
    ::= { chlEntry 10 }

chlHostIdBitmap OBJECT-TYPE
    SYNTAX          INTEGER
    ACCESS          read-only
    STATUS          mandatory
    DESCRIPTION     
            "SCSI/Fibre host channel id bitmap
             BITS 0-15 : Primary Controller SCSI ID Bitmap
             BITS 16-31 : Secondary Controller SCSI ID Bitmap"
    ::= { chlEntry 11 }

chlDrvPid OBJECT-TYPE
    SYNTAX          INTEGER
    ACCESS          read-only
    STATUS          mandatory
    DESCRIPTION     
            "Primary controller SCSI/Fibre drive channel id
             Note: For Fibre Drive Channels, if == 0x7f
             		then ID will be negotiated."
    ::= { chlEntry 12 }

chlDrvSid OBJECT-TYPE
    SYNTAX          INTEGER
    ACCESS          read-only
    STATUS          mandatory
    DESCRIPTION     
            "Secondary controller SCSI/Fibre drive channel id
             Note: For Fibre Drive Channels, if == 0x7f
             		then ID will be negotiated. If == 0xff,
             		then Fibre loop not initialized."
    ::= { chlEntry 13 }

chlMaxTxPeriod OBJECT-TYPE
    SYNTAX          INTEGER
    ACCESS          read-only
    STATUS          mandatory
    DESCRIPTION     
            "Maximum synchronized transfer period
             (SCSI: 4 ns units, 0 : Async; Fibre: 1/32 ns units)"
    ::= { chlEntry 14 }

chlMinTxPeriod OBJECT-TYPE
    SYNTAX          INTEGER
    ACCESS          read-only
    STATUS          mandatory
    DESCRIPTION     
            "Minimum synchronized transfer period
             (SCSI: 4 ns units, 0 : Async; Fibre: 1/32 ns units)"
    ::= { chlEntry 15 }

chlDefTxPeriod OBJECT-TYPE
    SYNTAX          INTEGER
    ACCESS          read-only
    STATUS          mandatory
    DESCRIPTION     
            "Default synchronized transfer period
             (SCSI: 4 ns units, 0 : Async; Fibre: 1/32 ns units, 0 - Auto-negotiate)"
    ::= { chlEntry 16 }

chlCurTxPeriod OBJECT-TYPE
    SYNTAX          INTEGER
    ACCESS          read-only
    STATUS          mandatory
    DESCRIPTION     
            "Current synchronized transfer period
             (SCSI: 4 ns units, 0 : Async; Fibre: 1/32 ns units)"
    ::= { chlEntry 17 }

chlMaxTxWidth OBJECT-TYPE
    SYNTAX          INTEGER
    ACCESS          read-only
    STATUS          mandatory
    DESCRIPTION     
            "Maximum synchronized transfer width index(SCSI only)
             (Index - 0:Narrow, 1:Wide)"
    ::= { chlEntry 18 }

chlMinTxWidth OBJECT-TYPE
    SYNTAX          INTEGER
    ACCESS          read-only
    STATUS          mandatory
    DESCRIPTION     
            "Minimum synchronized transfer width index(SCSI only)
             (Index - 0:Narrow, 1:Wide)"
    ::= { chlEntry 19 }

chlDefTxWidth OBJECT-TYPE
    SYNTAX          INTEGER
    ACCESS          read-only
    STATUS          mandatory
    DESCRIPTION     
            "Default synchronized transfer width index(SCSI only)
             (Index - 0:Narrow, 1:Wide)"
    ::= { chlEntry 20 }

chlCurTxWidth OBJECT-TYPE
    SYNTAX          INTEGER
    ACCESS          read-only
    STATUS          mandatory
    DESCRIPTION     
            "Current synchronized transfer width index(SCSI only)
             (Index - 0:Narrow, 1:Wide)"
    ::= { chlEntry 21 }

chlMaxTagCnt OBJECT-TYPE
    SYNTAX          INTEGER
    ACCESS          read-only
    STATUS          mandatory
    DESCRIPTION     
            "Maximum tag count"
    ::= { chlEntry 22 }

chlDefTagCnt OBJECT-TYPE
    SYNTAX          INTEGER
    ACCESS          read-only
    STATUS          mandatory
    DESCRIPTION     
            "Default tag count"
    ::= { chlEntry 23 }

luTable OBJECT-TYPE
    SYNTAX          SEQUENCE OF LuEntry
    ACCESS          not-accessible
    STATUS          mandatory
    DESCRIPTION     
            "Logical unit table"
    ::= { extInterface 8 }

luEntry OBJECT-TYPE
    SYNTAX          LuEntry
    ACCESS          not-accessible
    STATUS          mandatory
    DESCRIPTION     
            "Logical unit entry"
    INDEX           { luIndex }
    ::= { luTable 1 }

LuEntry ::=
    SEQUENCE {
        luIndex                         Gauge,
        luDescriptor                    INTEGER,
        luClassCode                     INTEGER,
        luTypeCode                      INTEGER,
        luVendorID                      OCTET STRING,
        luIDString                      OCTET STRING,
        luHWRev                         OCTET STRING,
        luSWRev                         OCTET STRING,
        luChlNum                        INTEGER,
        luIDNum                         INTEGER
    }

luIndex OBJECT-TYPE
    SYNTAX          Gauge
    ACCESS          not-accessible
    STATUS          mandatory
    DESCRIPTION     
            "Logical unit index"
    ::= { luEntry 1 }

luDescriptor OBJECT-TYPE
    SYNTAX          INTEGER
    ACCESS          read-only
    STATUS          mandatory
    DESCRIPTION     
            "Logical unit descriptor"
    ::= { luEntry 2 }

luClassCode OBJECT-TYPE
    SYNTAX          INTEGER
    ACCESS          read-only
    STATUS          mandatory
    DESCRIPTION     
            "Logical unit class code
             1 - Enclosure Unit: Manages Power supplies, fans, temperature, UPS', and
              	 drive slot states.
             2 - 0xfff: Reserved.
             0x1000 - 0xffff: Vendor specific."
    ::= { luEntry 3 }

luTypeCode OBJECT-TYPE
    SYNTAX          INTEGER
    ACCESS          read-only
    STATUS          mandatory
    DESCRIPTION     
            "Logical unit type code
             1 - SAF-TE Management Device.
             2 - Controller Peripheral Device.
             3 - Customable I2C Peripheral Device.
             4 - SES Management Device.
             5 - 0xfff: Reserved.
             0x1000 - 0xffff: Vendor specific."
    ::= { luEntry 4 }

luVendorID OBJECT-TYPE
    SYNTAX          OCTET STRING
    ACCESS          read-only
    STATUS          mandatory
    DESCRIPTION     
            "Logical unit vendor ID string"
    ::= { luEntry 5 }

luIDString OBJECT-TYPE
    SYNTAX          OCTET STRING
    ACCESS          read-only
    STATUS          mandatory
    DESCRIPTION     
            "Logical unit ID string"
    ::= { luEntry 6 }

luHWRev OBJECT-TYPE
    SYNTAX          OCTET STRING
    ACCESS          read-only
    STATUS          mandatory
    DESCRIPTION     
            "Logical unit hardware revision string"
    ::= { luEntry 7 }

luSWRev OBJECT-TYPE
    SYNTAX          OCTET STRING
    ACCESS          read-only
    STATUS          mandatory
    DESCRIPTION     
            "Logical unit software revision string"
    ::= { luEntry 8 }

luChlNum OBJECT-TYPE
    SYNTAX          INTEGER
    ACCESS          read-only
    STATUS          mandatory
    DESCRIPTION     
            "Channel number to which logical unit is connected"
    ::= { luEntry 9 }

luIDNum OBJECT-TYPE
    SYNTAX          INTEGER
    ACCESS          read-only
    STATUS          mandatory
    DESCRIPTION     
            "ID number for logical unit"
    ::= { luEntry 10 }

luDevTable OBJECT-TYPE
    SYNTAX          SEQUENCE OF LuDevEntry
    ACCESS          not-accessible
    STATUS          mandatory
    DESCRIPTION     
            "Logical unit device table"
    ::= { extInterface 9 }

luDevEntry OBJECT-TYPE
    SYNTAX          LuDevEntry
    ACCESS          not-accessible
    STATUS          mandatory
    DESCRIPTION     
            "Logical unit device entry"
    INDEX           { lguDevTabIdx }
    ::= { luDevTable 1 }

LuDevEntry ::=
    SEQUENCE {
        lguDevTabIdx                    Gauge,
        lguDescriptor                   INTEGER,
        lguClassCode                    INTEGER,
        lguTypeCode                     INTEGER,
        luDevDescriptor                 INTEGER,
        luDevTypeCode                   INTEGER,
        luDevIndex                      INTEGER,
        luDevDescription                OCTET STRING,
        luDevValue                      INTEGER,
        luDevValueUnit                  INTEGER,
        luDevChlNum                     INTEGER,
        luDevIDNum                      INTEGER,
        luDevStatus                     INTEGER
    }

lguDevTabIdx OBJECT-TYPE
    SYNTAX          Gauge
    ACCESS          not-accessible
    STATUS          mandatory
    DESCRIPTION     
            "Logical unit device table index"
    ::= { luDevEntry 1 }

lguDescriptor OBJECT-TYPE
    SYNTAX          INTEGER
    ACCESS          read-only
    STATUS          mandatory
    DESCRIPTION     
            "Logical unit descriptor"
    ::= { luDevEntry 2 }

lguClassCode OBJECT-TYPE
    SYNTAX          INTEGER
    ACCESS          read-only
    STATUS          mandatory
    DESCRIPTION     
            "Logical unit class code
             1 - Enclosure Unit: Manages Power supplies, fans, temperature, UPS', and
              	 drive slot states.
             2 - 0xfff: Reserved.
             0x1000 - 0xffff: Vendor specific."
    ::= { luDevEntry 3 }

lguTypeCode OBJECT-TYPE
    SYNTAX          INTEGER
    ACCESS          read-only
    STATUS          mandatory
    DESCRIPTION     
            "Logical unit type code
             1 - SAF-TE Management Device.
             2 - Controller Peripheral Device.
             3 - Customable I2C Peripheral Device.
             4 - SES Management Device.
             5 - 0xfff: Reserved.
             0x1000 - 0xffff: Vendor specific."
    ::= { luDevEntry 4 }

luDevDescriptor OBJECT-TYPE
    SYNTAX          INTEGER
    ACCESS          read-only
    STATUS          mandatory
    DESCRIPTION     
            "Logical unit device descriptor"
    ::= { luDevEntry 5 }

luDevTypeCode OBJECT-TYPE
    SYNTAX          INTEGER
    ACCESS          read-only
    STATUS          mandatory
    DESCRIPTION     
            "Logical unit device type code
             Enclosure Unit Device Types:
             	1 - Power supply.
             	2 - Fan.
             	3 - Temperature sensor.
             	4 - UPS.
             	5 - Voltage sensors.
             	6 - Current sensors.
             	8 - Temperature Out-of-Range Flags.
             	9 - Door.
             	0xa - Speaker.
             	0xb - Battery-backup battery.
             	0x11 - Slot states."
    ::= { luDevEntry 6 }

luDevIndex OBJECT-TYPE
    SYNTAX          INTEGER
    ACCESS          read-only
    STATUS          mandatory
    DESCRIPTION     
            "Logical unit device index
             Can be used to identify device position.
             If == 0, Index Not Available. For SAF-TE Logical
             Units, this index corresponds to one greater than
             the index of the device as presented in the
             'Read Enclosure Status' data."
    ::= { luDevEntry 7 }

luDevDescription OBJECT-TYPE
    SYNTAX          OCTET STRING
    ACCESS          read-only
    STATUS          mandatory
    DESCRIPTION     
            "Logical unit device description string"
    ::= { luDevEntry 8 }

luDevValue OBJECT-TYPE
    SYNTAX          INTEGER
    ACCESS          read-only
    STATUS          mandatory
    DESCRIPTION     
            "Logical unit device value"
    ::= { luDevEntry 9 }

luDevValueUnit OBJECT-TYPE
    SYNTAX          INTEGER
    ACCESS          read-only
    STATUS          mandatory
    DESCRIPTION     
            "Logical unit device value unit
             Fan: in RPM
             Voltage Sensor: in Millivolt
             Current Sensor: in Milliamps
             Temperature Sensor: in 1/1000 Degreeds C(Absolut value)"
    ::= { luDevEntry 10 }

luDevChlNum OBJECT-TYPE
    SYNTAX          INTEGER
    ACCESS          read-only
    STATUS          mandatory
    DESCRIPTION     
            "Logical unit device(device slot) channel number"
    ::= { luDevEntry 11 }

luDevIDNum OBJECT-TYPE
    SYNTAX          INTEGER
    ACCESS          read-only
    STATUS          mandatory
    DESCRIPTION     
            "Logical unit device(device slot) id number"
    ::= { luDevEntry 12 }

luDevStatus OBJECT-TYPE
    SYNTAX          INTEGER
    ACCESS          read-only
    STATUS          mandatory
    DESCRIPTION     
            "Logical unit device status flags
             Power Supply:
             	BIT 0 - CLEAR:	Power supply functioning normally.
             			SET:	Power supply malfunctioning.
             	BITS 1-5 - Reserved (Set to 0).
             	BIT 6 - CLEAR:	Power supply is ON.
             			SET:	Power supply is OFF.
             	BIT 7 - CLEAR:	Power supply IS present.
             			SET:	Power supply is NOT present.
             	== 0xff - Status unknown.
             Fan:
             	BIT 0 - CLEAR:	Fan functioning normally.
             			SET:	Fan malfunctioning.
             	BITS 1-5 - Reserved (Set to 0).
             	BIT 6 - CLEAR:	Fan is ON.
             			SET:	Fan is OFF.
             	BIT 7 - CLEAR:	Fan IS present.
             			SET:	Fan is NOT present.
             	== 0xff - Status unknown.
             Temperature Sensor:
             	BIT 0 - CLEAR:	Temp. sensor functioning normally.
             			SET:	Temp. sensor malfunctioning.
             	BIT 1 - 3: If == 0, Temp. within safe range.
             			   If == 2, Cold Temp. Warning.
             			   If == 3, Hot Temp. Warning.
             			   If == 4, Cold Temp. Limit Exceeded.
             			   If == 5, Hot Temp. Limit Exceeded.
             	BIT 6 - CLEAR:	Temp. Sensor is Activated.
             			SET:	Temp. Sensor is NOT Activated.
             	BIT 7 - CLEAR:	Temperature sensor IS present.
             			SET:	Temperature sensor is NOT present.
             	== 0xff - Status unknown.
             UPS:
             	BIT 0 - CLEAR:	Unit functioning normally.
             			SET:	Unit malfunctioning.
             	BIT 1 - CLEAR:	AC Power present.
             			SET:	AC Power NOT present.
             	BIT 2 - 3: If == 0, battery fully charged.
             			   If == 1, battery not fully charged.
             			   If == 2, battery charge critically low.
             			   If == 3, battery completely drained.
             	BITS 4-5 - Reserved (Set to 0).
             	BIT 6 - CLEAR:	UPS is ON.
             			SET:	UPS is OFF.
             	BIT 7 - CLEAR:	UPS IS present.
             			SET:	UPS is NOT present.
             	== 0xff - Status unknown.
             Battery:
             	BIT 0 - CLEAR:	Battery functioning normally.
             			SET:	Battery malfunctioning.
             	BIT 1 - CLEAR:	Battery charging OFF (or trickle).
             			SET:	Battery charging ON.
             	BIT 2 - 3: If == 0, battery fully charged.
             			   If == 1, battery not fully charged.
             			   If == 2, battery charge critically low.
             			   If == 3, battery completely drained.
             	BITS 4-5 - Reserved (Set to 0).
             	BIT 6 - CLEAR:	Battery-backup is enabled.
             			SET:	Battery-backup is disabled.
             	BIT 7 - CLEAR:	Battery IS present.
             			SET:	Battery is NOT present.
             	== 0xff - Status unknown.
             Voltage Sensor:
             	BIT 0 - CLEAR:	Voltage sensor functioning normally.
             			SET:	Voltage sensor malfunctioning.
             	BIT 1 - 3: Current Voltage Sensor State:
             			   If == 0, Voltage within acceptable range.
             			   If == 2, Low Voltage Warning.
             			   If == 3, High Voltage Warning.
             			   If == 4, Low Voltage Limit Exceeded.
             			   If == 5, High Voltage Limit Exceeded.
             	BIT 4 - 5: Reserved.
             	BIT 6 - CLEAR:	Voltage Sensor is Activated.
             			SET:	Voltage Sensor is NOT Activated.
             	BIT 7 - CLEAR:	Voltage sensor IS present.
             			SET:	Voltage sensor is NOT present.
             	== 0xff - Voltage Sensor Status unknown.
             Current Sensor:
             	BIT 0 - CLEAR:	Current sensor functioning normally.
             			SET:	Current sensor malfunctioning.
             	BIT 1 - 3: Current Current Sensor State:
             				If == 0, Current within acceptable range.
             				If == 3, Over Current Warning.
             				If == 5, Over Current Limit Exceeded.
             	BIT 4 - 5: Reserved.
             	BIT 6 - CLEAR:	Current Sensor is Activated.
             			SET:	Current Sensor is NOT Activated.
             	BIT 7 - CLEAR:	Current sensor IS present.
             			SET:	Current sensor is NOT present.
             	== 0xff - Current Sensor Status unknown.
             Door:
             	BIT 0 - CLEAR:	Door OK.
             			SET:	Door, door lock, or door sensor	malfunctioning.
             	BIT 1 - CLEAR:	Door is shut.
             			SET:	Door is open.
             	BITS 2-5 - Reserved (Set to 0).
             	BIT 6 - CLEAR:	Door lock engaged.
             			SET:	Door lock NOT engaged.
             	BIT 7 - CLEAR:	Door IS present.
             			SET:	Door is NOT present.
             	== 0xff - Status unknown.
             Speaker:
             	BIT 0 - CLEAR:	Speaker functioning normally.
             			SET:	Speaker malfunctioning.
             	BITS 1-5 - Reserved (Set to 0).
             	BIT 6 - CLEAR:	Speaker is ON.
             			SET:	Speaker is OFF.
             	BIT 7 - CLEAR:	Speaker IS present.
             			SET:	Speaker is NOT present.
             	== 0xff - Status unknown.
             Slot:
             	BIT 0 - CLEAR:	Slot sense circuitry functioning normally.
             			SET:	Slot sense circuitry malfunctioning.
             	BIT 1 - CLEAR:	Device in slot has not been marked
             					'needing replacement' or a replacement
             					drive has been inserted.
             			SET:	Device in slot has been marked BAD
             					and is awaiting replacement.
             	BIT 2 - CLEAR:	Slot is activated so that drive can	be accessed.
             			SET:	Slot NOT activated.
             	BITS 3-5 - Reserved (Set to 0).
             	BIT 6 - CLEAR:	Slot is NOT ready for insertion/removal.
             			SET:	Slot is ready for insertion/removal.
             	BIT 7 - CLEAR:	Device inserted in slot.
             			SET:	Slot is empty.
             	== 0xff - Status unknown."
    ::= { luDevEntry 13 }

extLunTable OBJECT-TYPE
    SYNTAX          SEQUENCE OF ExtLunEntry
    ACCESS          not-accessible
    STATUS          mandatory
    DESCRIPTION     
            "Extended LUN table"
    ::= { extInterface 10 }

extLunEntry OBJECT-TYPE
    SYNTAX          ExtLunEntry
    ACCESS          not-accessible
    STATUS          mandatory
    DESCRIPTION     
            "Extended LUN entry"
    INDEX           { extLunIndex }
    ::= { extLunTable 1 }

ExtLunEntry ::=
    SEQUENCE {
        extLunIndex                     Gauge,
        extLunGroupName                 OCTET STRING,
        extLunHostIDWWN                 OCTET STRING,
        extLunHostIDMask                OCTET STRING,
        extLunFilterType                OCTET STRING,
        extLunAccessMode                OCTET STRING,
        extLunChl                       INTEGER,
        extLunID                        INTEGER,
        extLunNum                       INTEGER,
        extLunLdLvID                    OCTET STRING,
        extLunPartIdx                   INTEGER
    }

extLunIndex OBJECT-TYPE
    SYNTAX          Gauge
    ACCESS          not-accessible
    STATUS          mandatory
    DESCRIPTION     
            "Extended LUN index"
    ::= { extLunEntry 1 }

extLunGroupName OBJECT-TYPE
    SYNTAX          OCTET STRING
    ACCESS          read-only
    STATUS          mandatory
    DESCRIPTION     
            "Name of this extended LUN definition"
    ::= { extLunEntry 2 }

extLunHostIDWWN OBJECT-TYPE
    SYNTAX          OCTET STRING
    ACCESS          read-only
    STATUS          mandatory
    DESCRIPTION     
            "Host-ID/WWN of this exteded LUN definition"
    ::= { extLunEntry 3 }

extLunHostIDMask OBJECT-TYPE
    SYNTAX          OCTET STRING
    ACCESS          read-only
    STATUS          mandatory
    DESCRIPTION     
            "Host-ID/WWN mask of this extended LUN definition"
    ::= { extLunEntry 4 }

extLunFilterType OBJECT-TYPE
    SYNTAX          OCTET STRING
    ACCESS          read-only
    STATUS          mandatory
    DESCRIPTION     
            "Filtering type of this extended LUN definition"
    ::= { extLunEntry 5 }

extLunAccessMode OBJECT-TYPE
    SYNTAX          OCTET STRING
    ACCESS          read-only
    STATUS          mandatory
    DESCRIPTION     
            "Access mode of this extended LUN definition"
    ::= { extLunEntry 6 }

extLunChl OBJECT-TYPE
    SYNTAX          INTEGER
    ACCESS          read-only
    STATUS          mandatory
    DESCRIPTION     
            "Logical host channel number"
    ::= { extLunEntry 7 }

extLunID OBJECT-TYPE
    SYNTAX          INTEGER
    ACCESS          read-only
    STATUS          mandatory
    DESCRIPTION     
            "Host-side SCSI ID"
    ::= { extLunEntry 8 }

extLunNum OBJECT-TYPE
    SYNTAX          INTEGER
    ACCESS          read-only
    STATUS          mandatory
    DESCRIPTION     
            "Host-side SCSI LUN"
    ::= { extLunEntry 9 }

extLunLdLvID OBJECT-TYPE
    SYNTAX          OCTET STRING
    ACCESS          read-only
    STATUS          mandatory
    DESCRIPTION     
            "Logical drive/Logical volume identifier"
    ::= { extLunEntry 10 }

extLunPartIdx OBJECT-TYPE
    SYNTAX          INTEGER
    ACCESS          read-only
    STATUS          mandatory
    DESCRIPTION     
            "Partition index of logical drive or logical volume"
    ::= { extLunEntry 11 }

eventLog OBJECT IDENTIFIER
    ::= { extInterface 11 }

allEvtTable OBJECT-TYPE
    SYNTAX          SEQUENCE OF AllEvtEntry
    ACCESS          not-accessible
    STATUS          mandatory
    DESCRIPTION     
            "All event table"
    ::= { eventLog 1 }

allEvtEntry OBJECT-TYPE
    SYNTAX          AllEvtEntry
    ACCESS          not-accessible
    STATUS          mandatory
    DESCRIPTION     
            "All event entry"
    INDEX           { evtTableIdx }
    ::= { allEvtTable 1 }

AllEvtEntry ::=
    SEQUENCE {
        evtTableIdx                     Gauge,
        evtSource                       OCTET STRING,
        evtSeverity                     OCTET STRING,
        evtIndex                        INTEGER,
        evtType                         OCTET STRING,
        evtCode                         OCTET STRING,
        evtTime                         OCTET STRING
    }

evtTableIdx OBJECT-TYPE
    SYNTAX          Gauge
    ACCESS          not-accessible
    STATUS          mandatory
    DESCRIPTION     
            "Event table index"
    ::= { allEvtEntry 1 }

evtSource OBJECT-TYPE
    SYNTAX          OCTET STRING
    ACCESS          read-only
    STATUS          mandatory
    DESCRIPTION     
            "Event source"
    ::= { allEvtEntry 2 }

evtSeverity OBJECT-TYPE
    SYNTAX          OCTET STRING
    ACCESS          read-only
    STATUS          mandatory
    DESCRIPTION     
            "Event severity"
    ::= { allEvtEntry 3 }

evtIndex OBJECT-TYPE
    SYNTAX          INTEGER
    ACCESS          read-only
    STATUS          mandatory
    DESCRIPTION     
            "Event index"
    ::= { allEvtEntry 4 }

evtType OBJECT-TYPE
    SYNTAX          OCTET STRING
    ACCESS          read-only
    STATUS          mandatory
    DESCRIPTION     
            "Event type"
    ::= { allEvtEntry 5 }

evtCode OBJECT-TYPE
    SYNTAX          OCTET STRING
    ACCESS          read-only
    STATUS          mandatory
    DESCRIPTION     
            "Event code"
    ::= { allEvtEntry 6 }

evtTime OBJECT-TYPE
    SYNTAX          OCTET STRING
    ACCESS          read-only
    STATUS          mandatory
    DESCRIPTION     
            "Event time"
    ::= { allEvtEntry 7 }

ctlrEvtTable OBJECT-TYPE
    SYNTAX          SEQUENCE OF CtlrEvtEntry
    ACCESS          not-accessible
    STATUS          mandatory
    DESCRIPTION     
            "Controller event table"
    ::= { eventLog 2 }

ctlrEvtEntry OBJECT-TYPE
    SYNTAX          CtlrEvtEntry
    ACCESS          not-accessible
    STATUS          mandatory
    DESCRIPTION     
            "Controller event entry"
    INDEX           { cevtTableIdx }
    ::= { ctlrEvtTable 1 }

CtlrEvtEntry ::=
    SEQUENCE {
        cevtTableIdx                    Gauge,
        cevtSource                      OCTET STRING,
        cevtSeverity                    OCTET STRING,
        cevtIndex                       INTEGER,
        cevtType                        OCTET STRING,
        cevtCode                        OCTET STRING,
        cevtTime                        OCTET STRING
    }

cevtTableIdx OBJECT-TYPE
    SYNTAX          Gauge
    ACCESS          not-accessible
    STATUS          mandatory
    DESCRIPTION     
            "Event table index"
    ::= { ctlrEvtEntry 1 }

cevtSource OBJECT-TYPE
    SYNTAX          OCTET STRING
    ACCESS          read-only
    STATUS          mandatory
    DESCRIPTION     
            "Event source"
    ::= { ctlrEvtEntry 2 }

cevtSeverity OBJECT-TYPE
    SYNTAX          OCTET STRING
    ACCESS          read-only
    STATUS          mandatory
    DESCRIPTION     
            "Event severity"
    ::= { ctlrEvtEntry 3 }

cevtIndex OBJECT-TYPE
    SYNTAX          INTEGER
    ACCESS          read-only
    STATUS          mandatory
    DESCRIPTION     
            "Event index"
    ::= { ctlrEvtEntry 4 }

cevtType OBJECT-TYPE
    SYNTAX          OCTET STRING
    ACCESS          read-only
    STATUS          mandatory
    DESCRIPTION     
            "Event type"
    ::= { ctlrEvtEntry 5 }

cevtCode OBJECT-TYPE
    SYNTAX          OCTET STRING
    ACCESS          read-only
    STATUS          mandatory
    DESCRIPTION     
            "Event code"
    ::= { ctlrEvtEntry 6 }

cevtTime OBJECT-TYPE
    SYNTAX          OCTET STRING
    ACCESS          read-only
    STATUS          mandatory
    DESCRIPTION     
            "Event time"
    ::= { ctlrEvtEntry 7 }

drvEvtTable OBJECT-TYPE
    SYNTAX          SEQUENCE OF DrvEvtEntry
    ACCESS          not-accessible
    STATUS          mandatory
    DESCRIPTION     
            "Drive interface event table"
    ::= { eventLog 3 }

drvEvtEntry OBJECT-TYPE
    SYNTAX          DrvEvtEntry
    ACCESS          not-accessible
    STATUS          mandatory
    DESCRIPTION     
            "Drive event entry"
    INDEX           { evtTableIdx }
    ::= { drvEvtTable 1 }

DrvEvtEntry ::=
    SEQUENCE {
        devtTableIdx                    Gauge,
        devtSource                      OCTET STRING,
        devtSeverity                    OCTET STRING,
        devtIndex                       INTEGER,
        devtType                        OCTET STRING,
        devtCode                        OCTET STRING,
        evtLdID                         OCTET STRING,
        evtLogChl                       INTEGER,
        evtID                           INTEGER,
        evtLun                          INTEGER,
        devtTime                        OCTET STRING
    }

devtTableIdx OBJECT-TYPE
    SYNTAX          Gauge
    ACCESS          not-accessible
    STATUS          mandatory
    DESCRIPTION     
            "Event table index"
    ::= { drvEvtEntry 1 }

devtSource OBJECT-TYPE
    SYNTAX          OCTET STRING
    ACCESS          read-only
    STATUS          mandatory
    DESCRIPTION     
            "Event source"
    ::= { drvEvtEntry 2 }

devtSeverity OBJECT-TYPE
    SYNTAX          OCTET STRING
    ACCESS          read-only
    STATUS          mandatory
    DESCRIPTION     
            "Event severity"
    ::= { drvEvtEntry 3 }

devtIndex OBJECT-TYPE
    SYNTAX          INTEGER
    ACCESS          read-only
    STATUS          mandatory
    DESCRIPTION     
            "Event index"
    ::= { drvEvtEntry 4 }

devtType OBJECT-TYPE
    SYNTAX          OCTET STRING
    ACCESS          read-only
    STATUS          mandatory
    DESCRIPTION     
            "Event type"
    ::= { drvEvtEntry 5 }

devtCode OBJECT-TYPE
    SYNTAX          OCTET STRING
    ACCESS          read-only
    STATUS          mandatory
    DESCRIPTION     
            "Event code"
    ::= { drvEvtEntry 6 }

evtLdID OBJECT-TYPE
    SYNTAX          OCTET STRING
    ACCESS          read-only
    STATUS          mandatory
    DESCRIPTION     
            "Logical drive ID"
    ::= { drvEvtEntry 7 }

evtLogChl OBJECT-TYPE
    SYNTAX          INTEGER
    ACCESS          read-only
    STATUS          mandatory
    DESCRIPTION     
            "Logical channel number"
    ::= { drvEvtEntry 8 }

evtID OBJECT-TYPE
    SYNTAX          INTEGER
    ACCESS          read-only
    STATUS          mandatory
    DESCRIPTION     
            "Node SCSI ID"
    ::= { drvEvtEntry 9 }

evtLun OBJECT-TYPE
    SYNTAX          INTEGER
    ACCESS          read-only
    STATUS          mandatory
    DESCRIPTION     
            "SCSI LUN"
    ::= { drvEvtEntry 10 }

devtTime OBJECT-TYPE
    SYNTAX          OCTET STRING
    ACCESS          read-only
    STATUS          mandatory
    DESCRIPTION     
            "Event time"
    ::= { drvEvtEntry 11 }

hostEvtTable OBJECT-TYPE
    SYNTAX          SEQUENCE OF HostEvtEntry
    ACCESS          not-accessible
    STATUS          mandatory
    DESCRIPTION     
            "Host interface event table"
    ::= { eventLog 4 }

hostEvtEntry OBJECT-TYPE
    SYNTAX          HostEvtEntry
    ACCESS          not-accessible
    STATUS          mandatory
    DESCRIPTION     
            "Host interface event entry"
    INDEX           { evtTableIdx }
    ::= { hostEvtTable 1 }

HostEvtEntry ::=
    SEQUENCE {
        hevtTableIdx                    Gauge,
        hevtSource                      OCTET STRING,
        hevtSeverity                    OCTET STRING,
        hevtIndex                       INTEGER,
        hevtType                        OCTET STRING,
        hevtCode                        OCTET STRING,
        evtChl                          INTEGER,
        hevtID                          INTEGER,
        hevtLun                         INTEGER,
        hevtTime                        OCTET STRING
    }

hevtTableIdx OBJECT-TYPE
    SYNTAX          Gauge
    ACCESS          not-accessible
    STATUS          mandatory
    DESCRIPTION     
            "Event table index"
    ::= { hostEvtEntry 1 }

hevtSource OBJECT-TYPE
    SYNTAX          OCTET STRING
    ACCESS          read-only
    STATUS          mandatory
    DESCRIPTION     
            "Event source"
    ::= { hostEvtEntry 2 }

hevtSeverity OBJECT-TYPE
    SYNTAX          OCTET STRING
    ACCESS          read-only
    STATUS          mandatory
    DESCRIPTION     
            "Event severity"
    ::= { hostEvtEntry 3 }

hevtIndex OBJECT-TYPE
    SYNTAX          INTEGER
    ACCESS          read-only
    STATUS          mandatory
    DESCRIPTION     
            "Event index"
    ::= { hostEvtEntry 4 }

hevtType OBJECT-TYPE
    SYNTAX          OCTET STRING
    ACCESS          read-only
    STATUS          mandatory
    DESCRIPTION     
            "Event type"
    ::= { hostEvtEntry 5 }

hevtCode OBJECT-TYPE
    SYNTAX          OCTET STRING
    ACCESS          read-only
    STATUS          mandatory
    DESCRIPTION     
            "Event code"
    ::= { hostEvtEntry 6 }

evtChl OBJECT-TYPE
    SYNTAX          INTEGER
    ACCESS          read-only
    STATUS          mandatory
    DESCRIPTION     
            "Host SCSI channel number"
    ::= { hostEvtEntry 7 }

hevtID OBJECT-TYPE
    SYNTAX          INTEGER
    ACCESS          read-only
    STATUS          mandatory
    DESCRIPTION     
            "Host SCSI ID"
    ::= { hostEvtEntry 8 }

hevtLun OBJECT-TYPE
    SYNTAX          INTEGER
    ACCESS          read-only
    STATUS          mandatory
    DESCRIPTION     
            "Host SCSI LUN"
    ::= { hostEvtEntry 9 }

hevtTime OBJECT-TYPE
    SYNTAX          OCTET STRING
    ACCESS          read-only
    STATUS          mandatory
    DESCRIPTION     
            "Event time"
    ::= { hostEvtEntry 10 }

ldEvtTable OBJECT-TYPE
    SYNTAX          SEQUENCE OF LdEvtEntry
    ACCESS          not-accessible
    STATUS          mandatory
    DESCRIPTION     
            "Logical drive event table"
    ::= { eventLog 5 }

ldEvtEntry OBJECT-TYPE
    SYNTAX          LdEvtEntry
    ACCESS          not-accessible
    STATUS          mandatory
    DESCRIPTION     
            "Logical drive event entry"
    INDEX           { evtTableIdx }
    ::= { ldEvtTable 1 }

LdEvtEntry ::=
    SEQUENCE {
        ldevtTableIdx                   Gauge,
        ldevtSource                     OCTET STRING,
        ldevtSeverity                   OCTET STRING,
        ldevtIndex                      INTEGER,
        ldevtType                       OCTET STRING,
        ldevtCode                       OCTET STRING,
        ldevtLdID                       OCTET STRING,
        evtFailedChl                    INTEGER,
        evtFailedID                     INTEGER,
        evtFailedLun                    INTEGER,
        ldevtTime                       OCTET STRING
    }

ldevtTableIdx OBJECT-TYPE
    SYNTAX          Gauge
    ACCESS          not-accessible
    STATUS          mandatory
    DESCRIPTION     
            "Event table index"
    ::= { ldEvtEntry 1 }

ldevtSource OBJECT-TYPE
    SYNTAX          OCTET STRING
    ACCESS          read-only
    STATUS          mandatory
    DESCRIPTION     
            "Event source"
    ::= { ldEvtEntry 2 }

ldevtSeverity OBJECT-TYPE
    SYNTAX          OCTET STRING
    ACCESS          read-only
    STATUS          mandatory
    DESCRIPTION     
            "Event severity"
    ::= { ldEvtEntry 3 }

ldevtIndex OBJECT-TYPE
    SYNTAX          INTEGER
    ACCESS          read-only
    STATUS          mandatory
    DESCRIPTION     
            "Event index"
    ::= { ldEvtEntry 4 }

ldevtType OBJECT-TYPE
    SYNTAX          OCTET STRING
    ACCESS          read-only
    STATUS          mandatory
    DESCRIPTION     
            "Event type"
    ::= { ldEvtEntry 5 }

ldevtCode OBJECT-TYPE
    SYNTAX          OCTET STRING
    ACCESS          read-only
    STATUS          mandatory
    DESCRIPTION     
            "Event code"
    ::= { ldEvtEntry 6 }

ldevtLdID OBJECT-TYPE
    SYNTAX          OCTET STRING
    ACCESS          read-only
    STATUS          mandatory
    DESCRIPTION     
            "Logical drive ID"
    ::= { ldEvtEntry 7 }

evtFailedChl OBJECT-TYPE
    SYNTAX          INTEGER
    ACCESS          read-only
    STATUS          mandatory
    DESCRIPTION     
            "Logical channel number of the failed hard drive"
    ::= { ldEvtEntry 8 }

evtFailedID OBJECT-TYPE
    SYNTAX          INTEGER
    ACCESS          read-only
    STATUS          mandatory
    DESCRIPTION     
            "SCSI ID of the failed hard drive"
    ::= { ldEvtEntry 9 }

evtFailedLun OBJECT-TYPE
    SYNTAX          INTEGER
    ACCESS          read-only
    STATUS          mandatory
    DESCRIPTION     
            "SCSI LUN of the failed hard drive"
    ::= { ldEvtEntry 10 }

ldevtTime OBJECT-TYPE
    SYNTAX          OCTET STRING
    ACCESS          read-only
    STATUS          mandatory
    DESCRIPTION     
            "Event time"
    ::= { ldEvtEntry 11 }

gtEvtTable OBJECT-TYPE
    SYNTAX          SEQUENCE OF GtEvtEntry
    ACCESS          not-accessible
    STATUS          mandatory
    DESCRIPTION     
            "Generalized target event table"
    ::= { eventLog 6 }

gtEvtEntry OBJECT-TYPE
    SYNTAX          GtEvtEntry
    ACCESS          not-accessible
    STATUS          mandatory
    DESCRIPTION     
            "Generalized target event entry"
    INDEX           { evtTableIdx }
    ::= { gtEvtTable 1 }

GtEvtEntry ::=
    SEQUENCE {
        gtevtTableIdx                   Gauge,
        gtevtSource                     OCTET STRING,
        gtevtSeverity                   OCTET STRING,
        gtevtIndex                      INTEGER,
        gtevtType                       OCTET STRING,
        evtLuDesc                       INTEGER,
        evtLuDevDesc                    INTEGER,
        evtLuClass                      INTEGER,
        evtLuSubclass                   INTEGER,
        gtevtCode                       OCTET STRING,
        evtLuDevType                    OCTET STRING,
        evtLuDevIdx                     INTEGER,
        evtEncChl                       INTEGER,
        evtEncID                        INTEGER,
        evtEncLun                       INTEGER,
        gtevtTime                       OCTET STRING
    }

gtevtTableIdx OBJECT-TYPE
    SYNTAX          Gauge
    ACCESS          not-accessible
    STATUS          mandatory
    DESCRIPTION     
            "Event table index"
    ::= { gtEvtEntry 1 }

gtevtSource OBJECT-TYPE
    SYNTAX          OCTET STRING
    ACCESS          read-only
    STATUS          mandatory
    DESCRIPTION     
            "Event source"
    ::= { gtEvtEntry 2 }

gtevtSeverity OBJECT-TYPE
    SYNTAX          OCTET STRING
    ACCESS          read-only
    STATUS          mandatory
    DESCRIPTION     
            "Event severity"
    ::= { gtEvtEntry 3 }

gtevtIndex OBJECT-TYPE
    SYNTAX          INTEGER
    ACCESS          read-only
    STATUS          mandatory
    DESCRIPTION     
            "Event index"
    ::= { gtEvtEntry 4 }

gtevtType OBJECT-TYPE
    SYNTAX          OCTET STRING
    ACCESS          read-only
    STATUS          mandatory
    DESCRIPTION     
            "Event type"
    ::= { gtEvtEntry 5 }

evtLuDesc OBJECT-TYPE
    SYNTAX          INTEGER
    ACCESS          read-only
    STATUS          mandatory
    DESCRIPTION     
            "Logical unit descriptor"
    ::= { gtEvtEntry 6 }

evtLuDevDesc OBJECT-TYPE
    SYNTAX          INTEGER
    ACCESS          read-only
    STATUS          mandatory
    DESCRIPTION     
            "Logical unit device descriptor"
    ::= { gtEvtEntry 7 }

evtLuClass OBJECT-TYPE
    SYNTAX          INTEGER
    ACCESS          read-only
    STATUS          mandatory
    DESCRIPTION     
            "Logical unit class code"
    ::= { gtEvtEntry 8 }

evtLuSubclass OBJECT-TYPE
    SYNTAX          INTEGER
    ACCESS          read-only
    STATUS          mandatory
    DESCRIPTION     
            "Logical unit subclass code"
    ::= { gtEvtEntry 9 }

gtevtCode OBJECT-TYPE
    SYNTAX          OCTET STRING
    ACCESS          read-only
    STATUS          mandatory
    DESCRIPTION     
            "Event code"
    ::= { gtEvtEntry 10 }

evtLuDevType OBJECT-TYPE
    SYNTAX          OCTET STRING
    ACCESS          read-only
    STATUS          mandatory
    DESCRIPTION     
            "Logical unit device type"
    ::= { gtEvtEntry 11 }

evtLuDevIdx OBJECT-TYPE
    SYNTAX          INTEGER
    ACCESS          read-only
    STATUS          mandatory
    DESCRIPTION     
            "Logical unit device index"
    ::= { gtEvtEntry 12 }

evtEncChl OBJECT-TYPE
    SYNTAX          INTEGER
    ACCESS          read-only
    STATUS          mandatory
    DESCRIPTION     
            "Enclosure(SAF-TE/SES) unit SCSI channel number"
    ::= { gtEvtEntry 13 }

evtEncID OBJECT-TYPE
    SYNTAX          INTEGER
    ACCESS          read-only
    STATUS          mandatory
    DESCRIPTION     
            "Enclosure(SAF-TE/SES) unit SCSI ID"
    ::= { gtEvtEntry 14 }

evtEncLun OBJECT-TYPE
    SYNTAX          INTEGER
    ACCESS          read-only
    STATUS          mandatory
    DESCRIPTION     
            "Enclosure(SAF-TE/SES) unit SCSI LUN"
    ::= { gtEvtEntry 15 }

gtevtTime OBJECT-TYPE
    SYNTAX          OCTET STRING
    ACCESS          read-only
    STATUS          mandatory
    DESCRIPTION     
            "Event time"
    ::= { gtEvtEntry 16 }

snMgm OBJECT IDENTIFIER
    ::= { snRAIDU320 2 }

snNpc OBJECT IDENTIFIER
    ::= { snMgm 3 }

snSnmpTrap OBJECT IDENTIFIER
    ::= { snNpc 1 }

snEventText OBJECT-TYPE
    SYNTAX          OCTET STRING
    ACCESS          read-only
    STATUS          mandatory
    DESCRIPTION     
            "The description of the event"
    ::= { snSnmpTrap 1 }

snCtlrEventU320 TRAP-TYPE
    ENTERPRISE      sannetU320
    VARIABLES       { snEventText }
--     STATUS          mandatory
    DESCRIPTION     
            "There is a controller event occurred"
    ::= 1

END -- end of module DOTHILL-SANNET-U320-MIB.
