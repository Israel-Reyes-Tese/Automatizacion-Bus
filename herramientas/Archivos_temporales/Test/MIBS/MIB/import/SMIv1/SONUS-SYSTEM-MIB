--
-- This SMIv1 module has been generated by smidump 0.2-cvs. Do not edit.
--

SONUS-SYSTEM-MIB DEFINITIONS ::= BEGIN

IMPORTS
    OBJECT-TYPE
        FROM RFC-1212
    Counter, Gauge, IpAddress
        FROM RFC1155-SMI
    DateAndTime, RowStatus, TruthValue
        FROM SNMPv2-TC
    sonusCommonSoftwarePlatformServicesMIBs
        FROM SONUS-SMI;

sonusSystemMIB OBJECT IDENTIFIER
    ::= { sonusCommonSoftwarePlatformServicesMIBs 5 }

-- sonusSystemMIB MODULE-IDENTITY
--     LAST-UPDATED    "201603230000Z"
--     ORGANIZATION    
--             "Ribbon Communications, Inc."
--     CONTACT-INFO    
--             "Customer Support        
--              Ribbon Communications, Inc. 
--              4 Technology Park Drive 
--              Westford, MA 01886      
--              USA                     
--                                      
--              Tel: 978-614-8100       
--              Fax: 978-614-8609"
--     DESCRIPTION     
--             "The MIB Module for Node Management."
--     REVISION        "201603230000Z"
--     DESCRIPTION     
--             "Auto generated MIB."
--     ::= { sonusCommonSoftwarePlatformServicesMIBs 5 }


Short ::=
    INTEGER (-32768..32767)

-- Short ::= TEXTUAL-CONVENTION
--     DISPLAY-HINT    "d"
--     STATUS          mandatory
--     DESCRIPTION     
--             "xs:short"
--     SYNTAX          INTEGER (-32768..32767)

UnsignedShort ::=
    Gauge (0..65535)

-- UnsignedShort ::= TEXTUAL-CONVENTION
--     DISPLAY-HINT    "d"
--     STATUS          mandatory
--     DESCRIPTION     
--             "xs:unsignedShort"
--     SYNTAX          Gauge (0..65535)

ConfdString ::=
    OCTET STRING

-- ConfdString ::= TEXTUAL-CONVENTION
--     DISPLAY-HINT    "1t"
--     STATUS          mandatory
--     DESCRIPTION     
--             "xs: and confd: types mapped to strings"
--     SYNTAX          OCTET STRING

String ::=
    OCTET STRING

-- String ::= TEXTUAL-CONVENTION
--     DISPLAY-HINT    "1t"
--     STATUS          mandatory
--     DESCRIPTION     
--             "xs:string"
--     SYNTAX          OCTET STRING

HexList ::=
    OCTET STRING

-- HexList ::= TEXTUAL-CONVENTION
--     DISPLAY-HINT    "1x:"
--     STATUS          mandatory
--     DESCRIPTION     
--             "confd:hexList"
--     SYNTAX          OCTET STRING

SonusBlockCountType ::=
    Gauge (5..256000)

-- SonusBlockCountType ::= TEXTUAL-CONVENTION
--     STATUS          mandatory
--     DESCRIPTION     
--             "
--              The blockCount type.  Range 5 to 256000 
--              "
--     SYNTAX          Gauge (5..256000)

AlphaNumericRestrictionType ::=
    Gauge (0..16)

-- AlphaNumericRestrictionType ::= TEXTUAL-CONVENTION
--     STATUS          mandatory
--     DESCRIPTION     
--             "
--              The minimum number of characters in a particular class.
--              Enter value in range of 0-16
--              "
--     SYNTAX          Gauge (0..16)

SonusCoreDumpType ::=
    INTEGER { full(0), partial(1) }

-- SonusCoreDumpType ::= TEXTUAL-CONVENTION
--     STATUS          mandatory
--     DESCRIPTION     
--             "
--              Full or partial core dump process set.
--              "
--     SYNTAX          INTEGER
--                       { full(0), partial(1) }

SonusNodeStatMgmtStatusType ::=
    INTEGER { manageable(1), softwareUpgradeInProgress(2), 
                        softwareUpgradeFailed(3) }

-- SonusNodeStatMgmtStatusType ::= TEXTUAL-CONVENTION
--     STATUS          mandatory
--     DESCRIPTION     
--             ""
--     SYNTAX          INTEGER
--                       { manageable(1), softwareUpgradeInProgress(2), 
--                         softwareUpgradeFailed(3) }

SonusNodeUpgradeType ::=
    INTEGER { normal(1), forced(2) }

-- SonusNodeUpgradeType ::= TEXTUAL-CONVENTION
--     STATUS          mandatory
--     DESCRIPTION     
--             ""
--     SYNTAX          INTEGER
--                       { normal(1), forced(2) }

PasswordHashType ::=
    OCTET STRING (SIZE(0..128))

-- PasswordHashType ::= TEXTUAL-CONVENTION
--     DISPLAY-HINT    "1t"
--     STATUS          mandatory
--     DESCRIPTION     
--             ""
--     SYNTAX          OCTET STRING (SIZE(0..128))

SonusPasswordExpiryWarningPeriodType ::=
    Gauge (3..14)

-- SonusPasswordExpiryWarningPeriodType ::= TEXTUAL-CONVENTION
--     STATUS          mandatory
--     DESCRIPTION     
--             "
--              Password expiry warning period in days.
--              Enter value in range of 3-14
--              "
--     SYNTAX          Gauge (3..14)

SonusRevisionType ::=
    INTEGER (-32768..32767)

-- SonusRevisionType ::= TEXTUAL-CONVENTION
--     DISPLAY-HINT    "d"
--     STATUS          mandatory
--     DESCRIPTION     
--             ""
--     SYNTAX          INTEGER (-32768..32767)

OutOfMemoryCoredumpThresholdValueType ::=
    INTEGER (75..91)

-- OutOfMemoryCoredumpThresholdValueType ::= TEXTUAL-CONVENTION
--     STATUS          mandatory
--     DESCRIPTION     
--             "
--              Enter 'disabled' or a value in the range of (75..91)
--              "
--     SYNTAX          INTEGER (75..91)

SonusAccountAgingPeriodType ::=
    Gauge (30..180)

-- SonusAccountAgingPeriodType ::= TEXTUAL-CONVENTION
--     STATUS          mandatory
--     DESCRIPTION     
--             "
--              Account aging period in days.
--              Enter value in range of 30-180
--              "
--     SYNTAX          Gauge (30..180)

SonusNodeSrvrLastRestartReasonType ::=
    INTEGER { unknown(1), systemRestart(2), systemSoftReset(3), 
                        serverRestart(4), serverSoftReset(5), 
                        switchover(6), processAbnormalTermination(7), 
                        softwareUpgradeOrRevert(8), 
                        managementPortDown(9) }

-- SonusNodeSrvrLastRestartReasonType ::= TEXTUAL-CONVENTION
--     STATUS          mandatory
--     DESCRIPTION     
--             ""
--     SYNTAX          INTEGER
--                       { unknown(1), systemRestart(2), 
--                         systemSoftReset(3), serverRestart(4), 
--                         serverSoftReset(5), switchover(6), 
--                         processAbnormalTermination(7), 
--                         softwareUpgradeOrRevert(8), 
--                         managementPortDown(9) }

SonusPersonalityType ::=
    INTEGER { isbc(1), ssbc(2), msbc(3), mrfp(4), slb(5) }

-- SonusPersonalityType ::= TEXTUAL-CONVENTION
--     STATUS          mandatory
--     DESCRIPTION     
--             "personality type of the server"
--     SYNTAX          INTEGER
--                       { isbc(1), ssbc(2), msbc(3), mrfp(4), slb(5) }

SonusSyncStatusType ::=
    INTEGER { unknown(0), inSync(1), outOfSync(2), inProgress(3), 
                        notApplicable(4) }

-- SonusSyncStatusType ::= TEXTUAL-CONVENTION
--     STATUS          mandatory
--     DESCRIPTION     
--             ""
--     SYNTAX          INTEGER
--                       { unknown(0), inSync(1), outOfSync(2), 
--                         inProgress(3), notApplicable(4) }

SonusDspSlotIndex ::=
    Gauge (1..4)

-- SonusDspSlotIndex ::= TEXTUAL-CONVENTION
--     STATUS          mandatory
--     DESCRIPTION     
--             "
--              The index for a DSP slot.
--              "
--     SYNTAX          Gauge (1..4)

SonusNodeSrvrPktPortSpeed ::=
    INTEGER { speed1Gbps(0), speed10Gbps(1) }

-- SonusNodeSrvrPktPortSpeed ::= TEXTUAL-CONVENTION
--     STATUS          mandatory
--     DESCRIPTION     
--             "
--              Packet port speed setting
--              "
--     SYNTAX          INTEGER
--                       { speed1Gbps(0), speed10Gbps(1) }

ExternalAuthenticationType ::=
    INTEGER { radius(1), ldap(2) }

-- ExternalAuthenticationType ::= TEXTUAL-CONVENTION
--     STATUS          mandatory
--     DESCRIPTION     
--             ""
--     SYNTAX          INTEGER
--                       { radius(1), ldap(2) }

OutOfMemoryCoredumpThresholdDisabledType ::=
    OCTET STRING

-- OutOfMemoryCoredumpThresholdDisabledType ::= TEXTUAL-CONVENTION
--     DISPLAY-HINT    "1t"
--     STATUS          mandatory
--     DESCRIPTION     
--             "
--              Enter 'disabled' or a value in the range of (75..91)
--              "
--     SYNTAX          OCTET STRING

SonusNodeSrvrRole ::=
    INTEGER { primary(1), secondary(2) }

-- SonusNodeSrvrRole ::= TEXTUAL-CONVENTION
--     STATUS          mandatory
--     DESCRIPTION     
--             ""
--     SYNTAX          INTEGER
--                       { primary(1), secondary(2) }

DaughterBoardOperationalStatus ::=
    INTEGER { enabled(1), disabled(2), dryup(3), locked(4), loading(5), 
                        failed(6) }

-- DaughterBoardOperationalStatus ::= TEXTUAL-CONVENTION
--     STATUS          mandatory
--     DESCRIPTION     
--             ""
--     SYNTAX          INTEGER
--                       { enabled(1), disabled(2), dryup(3), locked(4), 
--                         loading(5), failed(6) }

FailedPasswordAttemptType ::=
    INTEGER (1..10)

-- FailedPasswordAttemptType ::= TEXTUAL-CONVENTION
--     STATUS          mandatory
--     DESCRIPTION     
--             "
--              Allowed wrong password attempts.
--              Enter value in range of 1-10
--              "
--     SYNTAX          INTEGER (1..10)

MacAddressStatusType ::=
    INTEGER { free(1), used(2) }

-- MacAddressStatusType ::= TEXTUAL-CONVENTION
--     STATUS          mandatory
--     DESCRIPTION     
--             "
--              Status of MAC address in macAddressStatus table .
--              "
--     SYNTAX          INTEGER
--                       { free(1), used(2) }

OutOfMemoryCoredumpThresholdType ::=
    OCTET STRING

-- OutOfMemoryCoredumpThresholdType ::= TEXTUAL-CONVENTION
--     DISPLAY-HINT    "1t"
--     STATUS          mandatory
--     DESCRIPTION     
--             "
--              The threshold for taking coredumps when memory utilization increases
--              "
--     SYNTAX          OCTET STRING

SonusDspDryupTime ::=
    Gauge (0..60)

-- SonusDspDryupTime ::= TEXTUAL-CONVENTION
--     STATUS          mandatory
--     DESCRIPTION     
--             "
--              Dryup time limits for DSPs in minutes.
--              "
--     SYNTAX          Gauge (0..60)

SonusLeaderElectType ::=
    INTEGER { currentValue(0), standard(1), enhanced(2) }

-- SonusLeaderElectType ::= TEXTUAL-CONVENTION
--     STATUS          mandatory
--     DESCRIPTION     
--             "
--              Leader election enumeration. CurrentValue indicates no change required for this parameter.
--              "
--     SYNTAX          INTEGER
--                       { currentValue(0), standard(1), enhanced(2) }

SonusNodeVersionCheckType ::=
    INTEGER { perform(1), skip(2) }

-- SonusNodeVersionCheckType ::= TEXTUAL-CONVENTION
--     STATUS          mandatory
--     DESCRIPTION     
--             ""
--     SYNTAX          INTEGER
--                       { perform(1), skip(2) }

SonusOSAccountAgingPeriodType ::=
    Gauge (7..712)

-- SonusOSAccountAgingPeriodType ::= TEXTUAL-CONVENTION
--     STATUS          mandatory
--     DESCRIPTION     
--             "
--              Account aging period in days.
--              Enter value in range of 7-712
--              "
--     SYNTAX          Gauge (7..712)

AccountUnlockTime ::=
    INTEGER (30..5400)

-- AccountUnlockTime ::= TEXTUAL-CONVENTION
--     STATUS          mandatory
--     DESCRIPTION     
--             "
--              Auto unlock time value (in secs).
--              Enter value in range of 30-5400
--              "
--     SYNTAX          INTEGER (30..5400)

SonusBondMonitorType ::=
    INTEGER { currentValue(0), direct-connect(1), network-connect(2) }

-- SonusBondMonitorType ::= TEXTUAL-CONVENTION
--     STATUS          mandatory
--     DESCRIPTION     
--             "
--              Bond port monitoring  enumeration. CurrentValue indicates no change required for this parameter.
--              "
--     SYNTAX          INTEGER
--                       { currentValue(0), direct-connect(1), 
--                         network-connect(2) }

SonusNodeCeLicenseStatusType ::=
    INTEGER { dualCe(1), singleCe(2) }

-- SonusNodeCeLicenseStatusType ::= TEXTUAL-CONVENTION
--     STATUS          mandatory
--     DESCRIPTION     
--             ""
--     SYNTAX          INTEGER
--                       { dualCe(1), singleCe(2) }

SonusNodeSwitchoverType ::=
    INTEGER { normal(1), forced(2) }

-- SonusNodeSwitchoverType ::= TEXTUAL-CONVENTION
--     STATUS          mandatory
--     DESCRIPTION     
--             ""
--     SYNTAX          INTEGER
--                       { normal(1), forced(2) }

SonusSystemHaModeType ::=
    INTEGER { haMode1to1(1), haModeNto1(2) }

-- SonusSystemHaModeType ::= TEXTUAL-CONVENTION
--     STATUS          mandatory
--     DESCRIPTION     
--             "
--              SBC HA mode type.
--              "
--     SYNTAX          INTEGER
--                       { haMode1to1(1), haModeNto1(2) }

SonusGratuitousArpOpcodeType ::=
    INTEGER { request(1), reply(2) }

-- SonusGratuitousArpOpcodeType ::= TEXTUAL-CONVENTION
--     STATUS          mandatory
--     DESCRIPTION     
--             "
--              Enter value  1-request or 2-reply
--              "
--     SYNTAX          INTEGER
--                       { request(1), reply(2) }

SonusNodeServerLiveSoftwareUpgradeStatusType ::=
    INTEGER { none(1), pendingUpgrade(2), upgrading(3), upgraded(4), 
                        pendingRevert(5), reverting(6), reverted(7), 
                        revertingOnError(8), committed(9) }

-- SonusNodeServerLiveSoftwareUpgradeStatusType ::= TEXTUAL-CONVENTION
--     STATUS          mandatory
--     DESCRIPTION     
--             ""
--     SYNTAX          INTEGER
--                       { none(1), pendingUpgrade(2), upgrading(3), 
--                         upgraded(4), pendingRevert(5), reverting(6), 
--                         reverted(7), revertingOnError(8), 
--                         committed(9) }

SonusNodeSrvrAdmnActionType ::=
    INTEGER { dryUp(1), force(2), undefined(3) }

-- SonusNodeSrvrAdmnActionType ::= TEXTUAL-CONVENTION
--     STATUS          mandatory
--     DESCRIPTION     
--             ""
--     SYNTAX          INTEGER
--                       { dryUp(1), force(2), undefined(3) }

SonusNodeSrvrStatSwVersionType ::=
    OCTET STRING (SIZE(0..255))

-- SonusNodeSrvrStatSwVersionType ::= TEXTUAL-CONVENTION
--     DISPLAY-HINT    "1t"
--     STATUS          mandatory
--     DESCRIPTION     
--             ""
--     SYNTAX          OCTET STRING (SIZE(0..255))

SonusId ::=
    INTEGER { all(1), activeConfigAndActivePolicy(2), 
                        activeAndStandbyPolicy(3) }

-- SonusId ::= TEXTUAL-CONVENTION
--     STATUS          mandatory
--     DESCRIPTION     
--             ""
--     SYNTAX          INTEGER
--                       { all(1), activeConfigAndActivePolicy(2), 
--                         activeAndStandbyPolicy(3) }

CoredumpCountLimitType ::=
    Gauge (1..10)

-- CoredumpCountLimitType ::= TEXTUAL-CONVENTION
--     DISPLAY-HINT    "d"
--     STATUS          mandatory
--     DESCRIPTION     
--             "
--              Number of out of memory coredumps allowed on a node. Minimum 1, Maximum 10.
--              "
--     SYNTAX          Gauge (1..10)

MinDiffWithOldPasswdType ::=
    Gauge (1..8)

-- MinDiffWithOldPasswdType ::= TEXTUAL-CONVENTION
--     STATUS          mandatory
--     DESCRIPTION     
--             "
--              The minimum difference between the new and old password.
--              Enter value in range of 1-8
--              "
--     SYNTAX          Gauge (1..8)

PasswordType ::=
    OCTET STRING (SIZE(0..32))

-- PasswordType ::= TEXTUAL-CONVENTION
--     DISPLAY-HINT    "1t"
--     STATUS          mandatory
--     DESCRIPTION     
--             ""
--     SYNTAX          OCTET STRING (SIZE(0..32))

SonusMaxSessionsType ::=
    INTEGER (1..5)

-- SonusMaxSessionsType ::= TEXTUAL-CONVENTION
--     STATUS          mandatory
--     DESCRIPTION     
--             "
--              Enter value in range of 1-5
--              "
--     SYNTAX          INTEGER (1..5)

SonusNodeShelfStatSerialNumberType ::=
    OCTET STRING (SIZE(0..255))

-- SonusNodeShelfStatSerialNumberType ::= TEXTUAL-CONVENTION
--     DISPLAY-HINT    "1t"
--     STATUS          mandatory
--     DESCRIPTION     
--             ""
--     SYNTAX          OCTET STRING (SIZE(0..255))

SonusNodeSrvrAdmnDryupLimitType ::=
    INTEGER (0..65535)

-- SonusNodeSrvrAdmnDryupLimitType ::= TEXTUAL-CONVENTION
--     STATUS          mandatory
--     DESCRIPTION     
--             ""
--     SYNTAX          INTEGER (0..65535)

SonusNodeSrvrStatPartNumType ::=
    OCTET STRING (SIZE(0..255))

-- SonusNodeSrvrStatPartNumType ::= TEXTUAL-CONVENTION
--     DISPLAY-HINT    "1t"
--     STATUS          mandatory
--     DESCRIPTION     
--             ""
--     SYNTAX          OCTET STRING (SIZE(0..255))

SonusNodeSrvrSyncStatusType ::=
    INTEGER { syncInProgress(1), syncCompleted(2), unprotected(3), 
                        unprotectedRunningStandby(4) }

-- SonusNodeSrvrSyncStatusType ::= TEXTUAL-CONVENTION
--     STATUS          mandatory
--     DESCRIPTION     
--             ""
--     SYNTAX          INTEGER
--                       { syncInProgress(1), syncCompleted(2), 
--                         unprotected(3), unprotectedRunningStandby(4) }

SonusNodeSyncStatusType ::=
    INTEGER { synchronizingSource(1), synchronizingDestination(2), 
                        synchronized(3), unprotected(4), unknown(5), 
                        standyRepartitionInprogress(6), 
                        forceSwitchoverforRepartition(7), 
                        preParingforForcedSwitchover(8) }

-- SonusNodeSyncStatusType ::= TEXTUAL-CONVENTION
--     STATUS          mandatory
--     DESCRIPTION     
--             ""
--     SYNTAX          INTEGER
--                       { synchronizingSource(1), 
--                         synchronizingDestination(2), synchronized(3), 
--                         unprotected(4), unknown(5), 
--                         standyRepartitionInprogress(6), 
--                         forceSwitchoverforRepartition(7), 
--                         preParingforForcedSwitchover(8) }

BannerString ::=
    OCTET STRING (SIZE(0..1600))

-- BannerString ::= TEXTUAL-CONVENTION
--     DISPLAY-HINT    "1t"
--     STATUS          mandatory
--     DESCRIPTION     
--             "
--              This data type is used to model textual information taken
--              from the NVT ASCII character set.  This type is similar to
--              SonusLongName, but can be null.  It is a replacement for
--              xs:string and xsd:string, since all strings must have a
--              maxLength specified.
--              "
--     SYNTAX          OCTET STRING (SIZE(0..1600))

LicenseBundleString ::=
    OCTET STRING (SIZE(0..12288))

-- LicenseBundleString ::= TEXTUAL-CONVENTION
--     DISPLAY-HINT    "1t"
--     STATUS          mandatory
--     DESCRIPTION     
--             ""
--     SYNTAX          OCTET STRING (SIZE(0..12288))

OperationType ::=
    INTEGER { lock(1), unlock(2) }

-- OperationType ::= TEXTUAL-CONVENTION
--     STATUS          mandatory
--     DESCRIPTION     
--             ""
--     SYNTAX          INTEGER
--                       { lock(1), unlock(2) }

SonusDspDisableCleanupType ::=
    INTEGER { graceful(1), forced(2) }

-- SonusDspDisableCleanupType ::= TEXTUAL-CONVENTION
--     STATUS          mandatory
--     DESCRIPTION     
--             ""
--     SYNTAX          INTEGER
--                       { graceful(1), forced(2) }

SonusNodeDiskStatusType ::=
    INTEGER { online(1), missing(2), failed(3), unknown(4) }

-- SonusNodeDiskStatusType ::= TEXTUAL-CONVENTION
--     STATUS          mandatory
--     DESCRIPTION     
--             ""
--     SYNTAX          INTEGER
--                       { online(1), missing(2), failed(3), unknown(4) }

SonusNodeSrvrStatMfgDateType ::=
    OCTET STRING (SIZE(0..255))

-- SonusNodeSrvrStatMfgDateType ::= TEXTUAL-CONVENTION
--     DISPLAY-HINT    "1t"
--     STATUS          mandatory
--     DESCRIPTION     
--             ""
--     SYNTAX          OCTET STRING (SIZE(0..255))

SonusConfigSyncStatus ::=
    INTEGER { success(1), failure(2) }

-- SonusConfigSyncStatus ::= TEXTUAL-CONVENTION
--     STATUS          mandatory
--     DESCRIPTION     
--             ""
--     SYNTAX          INTEGER
--                       { success(1), failure(2) }

SonusAdSearchResult ::=
    INTEGER { notFound(0), found(1) }

-- SonusAdSearchResult ::= TEXTUAL-CONVENTION
--     STATUS          mandatory
--     DESCRIPTION     
--             ""
--     SYNTAX          INTEGER
--                       { notFound(0), found(1) }

SonusDetailedStatusType ::=
    OCTET STRING (SIZE(0..4096))

-- SonusDetailedStatusType ::= TEXTUAL-CONVENTION
--     DISPLAY-HINT    "1t"
--     STATUS          mandatory
--     DESCRIPTION     
--             ""
--     SYNTAX          OCTET STRING (SIZE(0..4096))

SonusNodeIntegrityCheckType ::=
    INTEGER { perform(1), skip(2) }

-- SonusNodeIntegrityCheckType ::= TEXTUAL-CONVENTION
--     STATUS          mandatory
--     DESCRIPTION     
--             ""
--     SYNTAX          INTEGER
--                       { perform(1), skip(2) }

SonusSessionType ::=
    INTEGER (1..32)

-- SonusSessionType ::= TEXTUAL-CONVENTION
--     STATUS          mandatory
--     DESCRIPTION     
--             "
--              The number of management session.
--              Enter value in range of 1-32
--              "
--     SYNTAX          INTEGER (1..32)

SonusSshMaxAuthTriesType ::=
    INTEGER (2..6)

-- SonusSshMaxAuthTriesType ::= TEXTUAL-CONVENTION
--     STATUS          mandatory
--     DESCRIPTION     
--             "
--              Enter value in range of 2-6
--              "
--     SYNTAX          INTEGER (2..6)

SonusTimeIntervalType ::=
    Gauge (5..60)

-- SonusTimeIntervalType ::= TEXTUAL-CONVENTION
--     STATUS          mandatory
--     DESCRIPTION     
--             "
--              This type defines the range of the timer interval in minutes
--              that can be used by the configuration management for activities
--              such as to measure the statistics of certain resources.
--              "
--     SYNTAX          Gauge (5..60)

SonusMaxCountTypeUnlimited ::=
    OCTET STRING

-- SonusMaxCountTypeUnlimited ::= TEXTUAL-CONVENTION
--     DISPLAY-HINT    "1t"
--     STATUS          mandatory
--     DESCRIPTION     
--             "
--              Enter 'unlimited' or value in range of (2..1000000).
--              "
--     SYNTAX          OCTET STRING

SonusNodeLiveSoftwareUpgradeReasonType ::=
    INTEGER { none(0), successfulCompletion(1), initTimeout(2), 
                        userInitiated(3), fileUnavailable(4), timeout(5), 
                        unexpectedSwitchover(6), internalError(7), 
                        failedToRemoveOldPackage(8), 
                        failedToInstallNewPackage(9), 
                        failedToStartApplication(10), userReset(11) }

-- SonusNodeLiveSoftwareUpgradeReasonType ::= TEXTUAL-CONVENTION
--     STATUS          mandatory
--     DESCRIPTION     
--             ""
--     SYNTAX          INTEGER
--                       { none(0), successfulCompletion(1), 
--                         initTimeout(2), userInitiated(3), 
--                         fileUnavailable(4), timeout(5), 
--                         unexpectedSwitchover(6), internalError(7), 
--                         failedToRemoveOldPackage(8), 
--                         failedToInstallNewPackage(9), 
--                         failedToStartApplication(10), userReset(11) }

SonusNodeLiveSoftwareUpgradeStatusType ::=
    INTEGER { idle(1), upgradingStandby(2), upgradingActive(3), 
                        restartingStandby(4), upgradeDone(5), 
                        revertingStandby(6), revertingActive(7), 
                        revertDone(8), upgradeStopped(9), 
                        validatingCmd(10), reverting(11), 
                        standbyModelChange(12), activeModelChange(13), 
                        standbyRevertModelChange(14), 
                        activeRevertModelChange(15), 
                        waitRedundSyncComplete(16), upgrading(17) }

-- SonusNodeLiveSoftwareUpgradeStatusType ::= TEXTUAL-CONVENTION
--     STATUS          mandatory
--     DESCRIPTION     
--             ""
--     SYNTAX          INTEGER
--                       { idle(1), upgradingStandby(2), 
--                         upgradingActive(3), restartingStandby(4), 
--                         upgradeDone(5), revertingStandby(6), 
--                         revertingActive(7), revertDone(8), 
--                         upgradeStopped(9), validatingCmd(10), 
--                         reverting(11), standbyModelChange(12), 
--                         activeModelChange(13), 
--                         standbyRevertModelChange(14), 
--                         activeRevertModelChange(15), 
--                         waitRedundSyncComplete(16), upgrading(17) }

SonusNodeSrvrStatPartNumRevType ::=
    OCTET STRING (SIZE(0..255))

-- SonusNodeSrvrStatPartNumRevType ::= TEXTUAL-CONVENTION
--     DISPLAY-HINT    "1t"
--     STATUS          mandatory
--     DESCRIPTION     
--             ""
--     SYNTAX          OCTET STRING (SIZE(0..255))

SonusSearchResponseString ::=
    OCTET STRING (SIZE(0..128))

-- SonusSearchResponseString ::= TEXTUAL-CONVENTION
--     DISPLAY-HINT    "1t"
--     STATUS          mandatory
--     DESCRIPTION     
--             "
--              "
--     SYNTAX          OCTET STRING (SIZE(0..128))

SonusDspMismatchAction ::=
    INTEGER { preserveRedundancy(1), preserveCapacity(2) }

-- SonusDspMismatchAction ::= TEXTUAL-CONVENTION
--     STATUS          mandatory
--     DESCRIPTION     
--             ""
--     SYNTAX          INTEGER
--                       { preserveRedundancy(1), preserveCapacity(2) }

ConfigModeType ::=
    INTEGER { oam(0), managed-vm(1), direct-single(2), sbc(3) }

-- ConfigModeType ::= TEXTUAL-CONVENTION
--     STATUS          mandatory
--     DESCRIPTION     
--             ""
--     SYNTAX          INTEGER
--                       { oam(0), managed-vm(1), direct-single(2), 
--                         sbc(3) }

MaxRepeatCountType ::=
    Gauge (3..16)

-- MaxRepeatCountType ::= TEXTUAL-CONVENTION
--     STATUS          mandatory
--     DESCRIPTION     
--             "
--              The maximum number of consecutive repeating character.
--              Enter value in range of 3-16
--              "
--     SYNTAX          Gauge (3..16)

MinPasswordLengthType ::=
    Gauge (8..24)

-- MinPasswordLengthType ::= TEXTUAL-CONVENTION
--     STATUS          mandatory
--     DESCRIPTION     
--             "
--              The minimum number of characters in a password.
--              Enter value in range of 8-24
--              "
--     SYNTAX          Gauge (8..24)

SonusAllowOldVersionType ::=
    INTEGER { yes(1), no(2) }

-- SonusAllowOldVersionType ::= TEXTUAL-CONVENTION
--     STATUS          mandatory
--     DESCRIPTION     
--             ""
--     SYNTAX          INTEGER
--                       { yes(1), no(2) }

SonusMaxCountType ::=
    OCTET STRING

-- SonusMaxCountType ::= TEXTUAL-CONVENTION
--     DISPLAY-HINT    "1t"
--     STATUS          mandatory
--     DESCRIPTION     
--             "
--              The maximum license count allowed
--              "
--     SYNTAX          OCTET STRING

SonusMinCountType ::=
    Gauge (1..256000)

-- SonusMinCountType ::= TEXTUAL-CONVENTION
--     STATUS          mandatory
--     DESCRIPTION     
--             "
--              The mininum license count allowed.  Range 1 to 256000
--              "
--     SYNTAX          Gauge (1..256000)

SonusPasswordAgingPeriodType ::=
    Gauge (1..365)

-- SonusPasswordAgingPeriodType ::= TEXTUAL-CONVENTION
--     STATUS          mandatory
--     DESCRIPTION     
--             "
--              Password validity period in days.
--              Enter value in range of 1-365
--              "
--     SYNTAX          Gauge (1..365)

SonusMaxCountTypeVal ::=
    INTEGER (2..1000000)

-- SonusMaxCountTypeVal ::= TEXTUAL-CONVENTION
--     STATUS          mandatory
--     DESCRIPTION     
--             "
--              Enter 'unlimited' or value in range of (2..1000000).
--              "
--     SYNTAX          INTEGER (2..1000000)

SonusConfigStoreType ::=
    INTEGER { ems(1), swift(2) }

-- SonusConfigStoreType ::= TEXTUAL-CONVENTION
--     STATUS          mandatory
--     DESCRIPTION     
--             "Defines the type of external cloud object store service used for configuration file save/retrieve"
--     SYNTAX          INTEGER
--                       { ems(1), swift(2) }

SonusNodeSrvrStatModeType ::=
    INTEGER { unknown(1), standby(2), active(3), switchoverPending(4) }

-- SonusNodeSrvrStatModeType ::= TEXTUAL-CONVENTION
--     STATUS          mandatory
--     DESCRIPTION     
--             ""
--     SYNTAX          INTEGER
--                       { unknown(1), standby(2), active(3), 
--                         switchoverPending(4) }

SonusNodeSrvrStatUserNameType ::=
    OCTET STRING (SIZE(0..255))

-- SonusNodeSrvrStatUserNameType ::= TEXTUAL-CONVENTION
--     DISPLAY-HINT    "1t"
--     STATUS          mandatory
--     DESCRIPTION     
--             ""
--     SYNTAX          OCTET STRING (SIZE(0..255))

SonusNodeSrvrStatViewNameType ::=
    OCTET STRING (SIZE(0..255))

-- SonusNodeSrvrStatViewNameType ::= TEXTUAL-CONVENTION
--     DISPLAY-HINT    "1t"
--     STATUS          mandatory
--     DESCRIPTION     
--             ""
--     SYNTAX          OCTET STRING (SIZE(0..255))

SonusNumberOfPastIntervalsType ::=
    Gauge (1..12)

-- SonusNumberOfPastIntervalsType ::= TEXTUAL-CONVENTION
--     STATUS          mandatory
--     DESCRIPTION     
--             "
--              This type defines the range of the number of past interval
--              that can be configured for retrieving the statistics data.
--              "
--     SYNTAX          Gauge (1..12)

SonusSystemIdleTimeoutType ::=
    INTEGER (1..120)

-- SonusSystemIdleTimeoutType ::= TEXTUAL-CONVENTION
--     STATUS          mandatory
--     DESCRIPTION     
--             "
--              Timeout is in minutes from 1 to 120.
--              "
--     SYNTAX          INTEGER (1..120)

BfdIpAddress ::=
    OCTET STRING (SIZE(0..128))

-- BfdIpAddress ::= TEXTUAL-CONVENTION
--     DISPLAY-HINT    "1t"
--     STATUS          mandatory
--     DESCRIPTION     
--             ""
--     SYNTAX          OCTET STRING (SIZE(0..128))

BfdSessionState ::=
    OCTET STRING (SIZE(0..10))

-- BfdSessionState ::= TEXTUAL-CONVENTION
--     DISPLAY-HINT    "1t"
--     STATUS          mandatory
--     DESCRIPTION     
--             ""
--     SYNTAX          OCTET STRING (SIZE(0..10))

DiskNumberType ::=
    Gauge (0..3)

-- DiskNumberType ::= TEXTUAL-CONVENTION
--     STATUS          mandatory
--     DESCRIPTION     
--             "
--              The index for a disk, 0 through 3.
--              "
--     SYNTAX          Gauge (0..3)

PasswordHistoryDepthType ::=
    Gauge (0..24)

-- PasswordHistoryDepthType ::= TEXTUAL-CONVENTION
--     STATUS          mandatory
--     DESCRIPTION     
--             "
--              The number of passwords to be stored in history.
--              Enter value in range of 0-24
--              "
--     SYNTAX          Gauge (0..24)

RaidDiskNumberType ::=
    Gauge (0..1)

-- RaidDiskNumberType ::= TEXTUAL-CONVENTION
--     STATUS          mandatory
--     DESCRIPTION     
--             "
--              The index for a disk (0 or 1).
--              "
--     SYNTAX          Gauge (0..1)

SonusLicenseAdminStateType ::=
    INTEGER { disabled(1), enabled(2) }

-- SonusLicenseAdminStateType ::= TEXTUAL-CONVENTION
--     STATUS          mandatory
--     DESCRIPTION     
--             "Admin state of a license"
--     SYNTAX          INTEGER
--                       { disabled(1), enabled(2) }

SonusNodeUpgradeStateResetType ::=
    INTEGER { normal(1), forced(2) }

-- SonusNodeUpgradeStateResetType ::= TEXTUAL-CONVENTION
--     STATUS          mandatory
--     DESCRIPTION     
--             ""
--     SYNTAX          INTEGER
--                       { normal(1), forced(2) }

SonusSystemManagementIpVersionType ::=
    INTEGER { ipv4(1), ipv6(2) }

-- SonusSystemManagementIpVersionType ::= TEXTUAL-CONVENTION
--     STATUS          mandatory
--     DESCRIPTION     
--             ""
--     SYNTAX          INTEGER
--                       { ipv4(1), ipv6(2) }

SonusAdAttributeIndex ::=
    INTEGER { adAttribute1(251), adAttribute2(252), adAttribute3(253), 
                        adAttribute4(254), adAttribute5(255), 
                        adAttribute6(256), adAttribute7(257), 
                        adAttribute8(258), adAttribute9(259), 
                        adAttribute10(260), adAttribute11(261), 
                        adAttribute12(262), adAttribute13(263), 
                        adAttribute14(264), adAttribute15(265), 
                        adAttribute16(266), adAttribute17(267), 
                        adAttribute18(268), adAttribute19(269), 
                        adAttribute20(270), adAttribute21(271), 
                        adAttribute22(272), adAttribute23(273), 
                        adAttribute24(274), adAttribute25(275), 
                        adAttribute26(276), adAttribute27(277), 
                        adAttribute28(278), adAttribute29(279), 
                        adAttribute30(280), adAttribute31(281), 
                        adAttribute32(282) }

-- SonusAdAttributeIndex ::= TEXTUAL-CONVENTION
--     STATUS          mandatory
--     DESCRIPTION     
--             ""
--     SYNTAX          INTEGER
--                       { adAttribute1(251), adAttribute2(252), 
--                         adAttribute3(253), adAttribute4(254), 
--                         adAttribute5(255), adAttribute6(256), 
--                         adAttribute7(257), adAttribute8(258), 
--                         adAttribute9(259), adAttribute10(260), 
--                         adAttribute11(261), adAttribute12(262), 
--                         adAttribute13(263), adAttribute14(264), 
--                         adAttribute15(265), adAttribute16(266), 
--                         adAttribute17(267), adAttribute18(268), 
--                         adAttribute19(269), adAttribute20(270), 
--                         adAttribute21(271), adAttribute22(272), 
--                         adAttribute23(273), adAttribute24(274), 
--                         adAttribute25(275), adAttribute26(276), 
--                         adAttribute27(277), adAttribute28(278), 
--                         adAttribute29(279), adAttribute30(280), 
--                         adAttribute31(281), adAttribute32(282) }

SonusFacKeyElement ::=
    INTEGER { callingParty(4), calledParty(5), callId(6), sourceIp(7), 
                        callingNcalledId(8) }

-- SonusFacKeyElement ::= TEXTUAL-CONVENTION
--     STATUS          mandatory
--     DESCRIPTION     
--             ""
--     SYNTAX          INTEGER
--                       { callingParty(4), calledParty(5), callId(6), 
--                         sourceIp(7), callingNcalledId(8) }

NumberOfProcessesToCoredumpType ::=
    INTEGER (1..5)

-- NumberOfProcessesToCoredumpType ::= TEXTUAL-CONVENTION
--     STATUS          mandatory
--     DESCRIPTION     
--             "
--              The number of processes to take a core dump of when memory utilization is high
--              "
--     SYNTAX          INTEGER (1..5)

SonusNodeSrvrHwType ::=
    OCTET STRING (SIZE(0..255))

-- SonusNodeSrvrHwType ::= TEXTUAL-CONVENTION
--     DISPLAY-HINT    "1t"
--     STATUS          mandatory
--     DESCRIPTION     
--             ""
--     SYNTAX          OCTET STRING (SIZE(0..255))

SonusNodeSrvrStatSerialNumType ::=
    OCTET STRING (SIZE(0..255))

-- SonusNodeSrvrStatSerialNumType ::= TEXTUAL-CONVENTION
--     DISPLAY-HINT    "1t"
--     STATUS          mandatory
--     DESCRIPTION     
--             ""
--     SYNTAX          OCTET STRING (SIZE(0..255))

SonusAccountRemovalPeriodType ::=
    Gauge (60..360)

-- SonusAccountRemovalPeriodType ::= TEXTUAL-CONVENTION
--     STATUS          mandatory
--     DESCRIPTION     
--             "
--              Account removal period in days.
--              Enter value in range of 60-360
--              "
--     SYNTAX          Gauge (60..360)

SonusLicenseServerPriorityType ::=
    INTEGER (1..4)

-- SonusLicenseServerPriorityType ::= TEXTUAL-CONVENTION
--     STATUS          mandatory
--     DESCRIPTION     
--             "Priority. Range 1 to 4"
--     SYNTAX          INTEGER (1..4)

SonusFacThreshold ::=
    INTEGER (0..999)

-- SonusFacThreshold ::= TEXTUAL-CONVENTION
--     DISPLAY-HINT    "d"
--     STATUS          mandatory
--     DESCRIPTION     
--             "Threshold range for SBC Fault Avalanche Detection and Control.  Range 0 to 999"
--     SYNTAX          INTEGER (0..999)

SonusLicenseModeType ::=
    INTEGER { nodeLocked(0), domain(3) }

-- SonusLicenseModeType ::= TEXTUAL-CONVENTION
--     STATUS          mandatory
--     DESCRIPTION     
--             "
--              The License mode
--              "
--     SYNTAX          INTEGER
--                       { nodeLocked(0), domain(3) }

SonusNodeCeRunTimeModeType ::=
    INTEGER { dualCe(1), singleCe(2) }

-- SonusNodeCeRunTimeModeType ::= TEXTUAL-CONVENTION
--     STATUS          mandatory
--     DESCRIPTION     
--             ""
--     SYNTAX          INTEGER
--                       { dualCe(1), singleCe(2) }

SonusNodeSrvrStatFlashVersionType ::=
    OCTET STRING (SIZE(0..255))

-- SonusNodeSrvrStatFlashVersionType ::= TEXTUAL-CONVENTION
--     DISPLAY-HINT    "1t"
--     STATUS          mandatory
--     DESCRIPTION     
--             ""
--     SYNTAX          OCTET STRING (SIZE(0..255))

SonusSearchString ::=
    OCTET STRING (SIZE(0..128))

-- SonusSearchString ::= TEXTUAL-CONVENTION
--     DISPLAY-HINT    "1t"
--     STATUS          mandatory
--     DESCRIPTION     
--             "
--              Input Search String.
--              "
--     SYNTAX          OCTET STRING (SIZE(0..128))

SonusFacTimeOut ::=
    INTEGER (15..60)

-- SonusFacTimeOut ::= TEXTUAL-CONVENTION
--     DISPLAY-HINT    "d"
--     STATUS          mandatory
--     DESCRIPTION     
--             "Global configurable for the fault record aging timeout.  Range 15 to 60 Min."
--     SYNTAX          INTEGER (15..60)

SonusAdSyncStatusType ::=
    INTEGER { neverSynced(0), syncInProgress(1), syncCompleted(2), 
                        syncFailed(3), syncAccepted(4), syncRejected(5) }

-- SonusAdSyncStatusType ::= TEXTUAL-CONVENTION
--     STATUS          mandatory
--     DESCRIPTION     
--             ""
--     SYNTAX          INTEGER
--                       { neverSynced(0), syncInProgress(1), 
--                         syncCompleted(2), syncFailed(3), 
--                         syncAccepted(4), syncRejected(5) }

sonusSystem OBJECT IDENTIFIER
    ::= { sonusSystemMIB 1 }

sonusSystemLicenseStatus OBJECT IDENTIFIER
    ::= { sonusSystem 1 }

sonusSystemLicenseStatusCemode OBJECT-TYPE
    SYNTAX          SonusNodeCeLicenseStatusType
    ACCESS          read-only
    STATUS          mandatory
    DESCRIPTION     
            "
             This is the current CE license state.
             "
    ::= { sonusSystemLicenseStatus 1 }

sonusSystemSoftwareUpgradeStatus OBJECT IDENTIFIER
    ::= { sonusSystem 2 }

sonusSystemSoftwareUpgradeStatusState OBJECT-TYPE
    SYNTAX          SonusNodeLiveSoftwareUpgradeStatusType
    ACCESS          read-only
    STATUS          mandatory
    DESCRIPTION     
            "
             This is the current LSWU state.
             "
    ::= { sonusSystemSoftwareUpgradeStatus 1 }

sonusSystemSoftwareUpgradeStatusPreviousState OBJECT-TYPE
    SYNTAX          SonusNodeLiveSoftwareUpgradeStatusType
    ACCESS          read-only
    STATUS          mandatory
    DESCRIPTION     
            "
             This is the previous LSWU state.
             "
    ::= { sonusSystemSoftwareUpgradeStatus 2 }

sonusSystemSoftwareUpgradeStatusUpgradeStartTime OBJECT-TYPE
    SYNTAX          String (SIZE(0..255))
    ACCESS          read-only
    STATUS          mandatory
    DESCRIPTION     
            "
             Indicates when the live software upgrade started.
             "
    ::= { sonusSystemSoftwareUpgradeStatus 3 }

sonusSystemSoftwareUpgradeStatusRevertStartTime OBJECT-TYPE
    SYNTAX          String (SIZE(0..255))
    ACCESS          read-only
    STATUS          deprecated
    DESCRIPTION     
            "
             Indicates when the live software upgrade started.
             "
    ::= { sonusSystemSoftwareUpgradeStatus 4 }

sonusSystemSoftwareUpgradeStatusPackage OBJECT-TYPE
    SYNTAX          String (SIZE(0..255))
    ACCESS          read-only
    STATUS          mandatory
    DESCRIPTION     
            "
             Name of the new package.
             "
    ::= { sonusSystemSoftwareUpgradeStatus 5 }

sonusSystemSoftwareUpgradeStatusRpmName OBJECT-TYPE
    SYNTAX          String (SIZE(0..255))
    ACCESS          read-only
    STATUS          deprecated
    DESCRIPTION     
            "
             Name of the new rpm used for upgrade.
             "
    ::= { sonusSystemSoftwareUpgradeStatus 6 }

sonusSystemSoftwareUpgradeStatusUpgradeScript OBJECT-TYPE
    SYNTAX          String (SIZE(0..255))
    ACCESS          read-only
    STATUS          deprecated
    DESCRIPTION     
            "
             Script to run to perform upgrade.
             "
    ::= { sonusSystemSoftwareUpgradeStatus 8 }

sonusSystemSoftwareUpgradeStatusRevertScript OBJECT-TYPE
    SYNTAX          String (SIZE(0..255))
    ACCESS          read-only
    STATUS          deprecated
    DESCRIPTION     
            "
             Script to run to perform revert in case upgrade fails.
             "
    ::= { sonusSystemSoftwareUpgradeStatus 9 }

sonusSystemSoftwareUpgradeStatusReason OBJECT-TYPE
    SYNTAX          SonusNodeLiveSoftwareUpgradeReasonType
    ACCESS          read-only
    STATUS          mandatory
    DESCRIPTION     
            "
             Indicates the exit reason for failure of the last software upgrade.
             "
    ::= { sonusSystemSoftwareUpgradeStatus 10 }

sonusSystemSoftwareUpgradeStatusCemodeAtStart OBJECT-TYPE
    SYNTAX          SonusNodeCeRunTimeModeType
    ACCESS          read-only
    STATUS          deprecated
    DESCRIPTION     
            "
             CE mode when upgrade started (single/dual).
             "
    ::= { sonusSystemSoftwareUpgradeStatus 11 }

sonusSystemSoftwareUpgradeStatusOldRelease OBJECT-TYPE
    SYNTAX          String (SIZE(0..255))
    ACCESS          read-only
    STATUS          mandatory
    DESCRIPTION     
            "
             Software release that was running before upgrade started.
             "
    ::= { sonusSystemSoftwareUpgradeStatus 12 }

sonusSystemSoftwareUpgradeStatusNewRelease OBJECT-TYPE
    SYNTAX          String (SIZE(0..255))
    ACCESS          read-only
    STATUS          mandatory
    DESCRIPTION     
            "
             Software release to which the upgrade is performed.
             "
    ::= { sonusSystemSoftwareUpgradeStatus 13 }

sonusSystemSoftwareUpgradeStatusActiveCeAtStart OBJECT-TYPE
    SYNTAX          String (SIZE(0..255))
    ACCESS          read-only
    STATUS          deprecated
    DESCRIPTION     
            "
             Active CE name when the upgrade started.
             "
    ::= { sonusSystemSoftwareUpgradeStatus 14 }

sonusSystemSoftwareUpgradeStatusModelChange OBJECT-TYPE
    SYNTAX          TruthValue
    ACCESS          read-only
    STATUS          deprecated
    DESCRIPTION     
            "
             Inidicates if the process model changed as part of this upgrade.
             "
    ::= { sonusSystemSoftwareUpgradeStatus 15 }

sonusSystemSoftwareUpgradeStatusPrimaryUpgradeStatus OBJECT-TYPE
    SYNTAX          SonusNodeServerLiveSoftwareUpgradeStatusType
    ACCESS          read-only
    STATUS          mandatory
    DESCRIPTION     
            "
             Indicates the current status of the primary server.
             "
    ::= { sonusSystemSoftwareUpgradeStatus 16 }

sonusSystemSoftwareUpgradeStatusSecondaryUpgradeStatus OBJECT-TYPE
    SYNTAX          SonusNodeServerLiveSoftwareUpgradeStatusType
    ACCESS          read-only
    STATUS          mandatory
    DESCRIPTION     
            "
             Indicates the current status of the secondary server.
             "
    ::= { sonusSystemSoftwareUpgradeStatus 17 }

sonusSystemSoftwareUpgradeStatusUpgradeCompleteTime OBJECT-TYPE
    SYNTAX          String (SIZE(0..255))
    ACCESS          read-only
    STATUS          mandatory
    DESCRIPTION     
            "
             Indicates when the live software upgrade completed.
             "
    ::= { sonusSystemSoftwareUpgradeStatus 18 }

sonusSystemAdminTable OBJECT-TYPE
    SYNTAX          SEQUENCE OF SonusSystemAdminEntry
    ACCESS          not-accessible
    STATUS          obsolete
    DESCRIPTION     
            "
             Basic configuration (name, location, etc) for the system.
             "
    ::= { sonusSystem 3 }

sonusSystemAdminEntry OBJECT-TYPE
    SYNTAX          SonusSystemAdminEntry
    ACCESS          not-accessible
    STATUS          obsolete
    DESCRIPTION     
            ""
    INDEX           { sonusSystemAdminName }
    ::= { sonusSystemAdminTable 1 }

SonusSystemAdminEntry ::=
    SEQUENCE {
        sonusSystemAdminName            String,
        sonusSystemAdminLocation        String,
        sonusSystemAdminContact         String,
        sonusSystemAdminCliIdleTimeout  SonusSystemIdleTimeoutType,
        sonusSystemAdminLocalAuthenticationEnabled          TruthValue,
        sonusSystemAdminExternalAuthenticationEnabled             TruthValue,
        sonusSystemAdminStandbyServerState  INTEGER,
        sonusSystemAdminUtilMonitorStatsInterval        SonusTimeIntervalType,
        sonusSystemAdminUtilMonitorStatsNumOfPastInterval                 SonusNumberOfPastIntervalsType,
        sonusSystemAdminManagementIpVersion   SonusSystemManagementIpVersionType,
        sonusSystemAdminAuditLogState   INTEGER,
        sonusSystemAdminCliSessions     SonusSessionType,
        sonusSystemAdminNetconfSessions SonusSessionType,
        sonusSystemAdminPasswordRulesMinimumLength          MinPasswordLengthType,
        sonusSystemAdminPasswordRulesMinimumNumberOfUppercaseChars                          AlphaNumericRestrictionType,
        sonusSystemAdminPasswordRulesMinimumNumberOfLowercaseChars                          AlphaNumericRestrictionType,
        sonusSystemAdminPasswordRulesMinimumNumberOfDigits                  AlphaNumericRestrictionType,
        sonusSystemAdminPasswordRulesMinimumNumberOfOtherChars                      AlphaNumericRestrictionType,
        sonusSystemAdminPasswordRulesPasswordHistoryDepth                 PasswordHistoryDepthType,
        sonusSystemAdminPasswordRulesMaximumRepeatingCharsCount                       MaxRepeatCountType,
        sonusSystemAdminCliSetWarningSupport    INTEGER,
        sonusSystemAdminRowstatus       RowStatus,
        sonusSystemAdminActualSystemName String,
        sonusSystemAdminClusterId       String,
        sonusSystemAdminDefaultAccountLocalOnly       TruthValue,
        sonusSystemAdminExternalAuthenticationType          ExternalAuthenticationType
    }

sonusSystemAdminName OBJECT-TYPE
    SYNTAX          String (SIZE(0..255))
    ACCESS          not-accessible
    STATUS          obsolete
    DESCRIPTION     
            "
             Name of the system.
             "
    ::= { sonusSystemAdminEntry 1 }

sonusSystemAdminLocation OBJECT-TYPE
    SYNTAX          String (SIZE(0..255))
    ACCESS          read-write
    STATUS          obsolete
    DESCRIPTION     
            "
             Physical location of the system.
             "
    ::= { sonusSystemAdminEntry 2 }

sonusSystemAdminContact OBJECT-TYPE
    SYNTAX          String (SIZE(0..255))
    ACCESS          read-write
    STATUS          obsolete
    DESCRIPTION     
            "
             Contact information of the system.
             "
    ::= { sonusSystemAdminEntry 3 }

sonusSystemAdminCliIdleTimeout OBJECT-TYPE
    SYNTAX          SonusSystemIdleTimeoutType
    ACCESS          read-write
    STATUS          obsolete
    DESCRIPTION     
            "
             This is the time before the CLI session will be diconnected.
             "
    DEFVAL          { 30 }
    ::= { sonusSystemAdminEntry 4 }

sonusSystemAdminLocalAuthenticationEnabled OBJECT-TYPE
    SYNTAX          TruthValue
    ACCESS          read-write
    STATUS          obsolete
    DESCRIPTION     
            "
             The confd cli user information stored locally can be used for authentication.
             "
    ::= { sonusSystemAdminEntry 5 }

sonusSystemAdminExternalAuthenticationEnabled OBJECT-TYPE
    SYNTAX          TruthValue
    ACCESS          read-write
    STATUS          obsolete
    DESCRIPTION     
            "
             The type of external authentication to use
             "
    ::= { sonusSystemAdminEntry 6 }

sonusSystemAdminStandbyServerState OBJECT-TYPE
    SYNTAX          INTEGER { disabled(1), enabled(2) }
    ACCESS          read-write
    STATUS          obsolete
    DESCRIPTION     
            "
             Standby server state indicates if to bring up or not the standby server.
             "
    ::= { sonusSystemAdminEntry 9 }

sonusSystemAdminUtilMonitorStatsInterval OBJECT-TYPE
    SYNTAX          SonusTimeIntervalType
    ACCESS          read-write
    STATUS          obsolete
    DESCRIPTION     
            "
             The time interval for system resource monitoring statistics.
             "
    DEFVAL          { 15 }
    ::= { sonusSystemAdminEntry 10 }

sonusSystemAdminUtilMonitorStatsNumOfPastInterval OBJECT-TYPE
    SYNTAX          SonusNumberOfPastIntervalsType
    ACCESS          read-write
    STATUS          obsolete
    DESCRIPTION     
            "
             The number of past intervals saved for system resource monitoring statistics.
             "
    DEFVAL          { 4 }
    ::= { sonusSystemAdminEntry 11 }

sonusSystemAdminManagementIpVersion OBJECT-TYPE
    SYNTAX          SonusSystemManagementIpVersionType
    ACCESS          read-write
    STATUS          obsolete
    DESCRIPTION     
            "
             This is the IP version used by the management application. The management application
             will only accept packets using either IPV4 or IPV6 over the managemnt port.
             "
    DEFVAL          { ipv4 }
    ::= { sonusSystemAdminEntry 12 }

sonusSystemAdminAuditLogState OBJECT-TYPE
    SYNTAX          INTEGER { disabled(1), enabled(2) }
    ACCESS          read-write
    STATUS          obsolete
    DESCRIPTION     
            "
             This enables/disable the management audit log.
             "
    ::= { sonusSystemAdminEntry 13 }

sonusSystemAdminCliSessions OBJECT-TYPE
    SYNTAX          SonusSessionType
    ACCESS          read-write
    STATUS          obsolete
    DESCRIPTION     
            "
             The number of active cli sessions allowed.
             "
    DEFVAL          { 16 }
    ::= { sonusSystemAdminEntry 14 }

sonusSystemAdminNetconfSessions OBJECT-TYPE
    SYNTAX          SonusSessionType
    ACCESS          read-write
    STATUS          obsolete
    DESCRIPTION     
            "
             The number of active netconf sessions allowed.
             "
    DEFVAL          { 8 }
    ::= { sonusSystemAdminEntry 15 }

sonusSystemAdminPasswordRulesMinimumLength OBJECT-TYPE
    SYNTAX          MinPasswordLengthType
    ACCESS          read-write
    STATUS          obsolete
    DESCRIPTION     
            "
             Minimum number of characters that should be present in the password.
             "
    DEFVAL          { 8 }
    ::= { sonusSystemAdminEntry 16 }

sonusSystemAdminPasswordRulesMinimumNumberOfUppercaseChars OBJECT-TYPE
    SYNTAX          AlphaNumericRestrictionType
    ACCESS          read-write
    STATUS          obsolete
    DESCRIPTION     
            "
             Minimum number of upper case characters that should be present in the password.
             "
    DEFVAL          { 1 }
    ::= { sonusSystemAdminEntry 17 }

sonusSystemAdminPasswordRulesMinimumNumberOfLowercaseChars OBJECT-TYPE
    SYNTAX          AlphaNumericRestrictionType
    ACCESS          read-write
    STATUS          obsolete
    DESCRIPTION     
            "
             Minimum number of lower case characters that should be present in the password.
             "
    DEFVAL          { 1 }
    ::= { sonusSystemAdminEntry 18 }

sonusSystemAdminPasswordRulesMinimumNumberOfDigits OBJECT-TYPE
    SYNTAX          AlphaNumericRestrictionType
    ACCESS          read-write
    STATUS          obsolete
    DESCRIPTION     
            "
             Minimum number of digits that should be present in the password.
             "
    DEFVAL          { 1 }
    ::= { sonusSystemAdminEntry 19 }

sonusSystemAdminPasswordRulesMinimumNumberOfOtherChars OBJECT-TYPE
    SYNTAX          AlphaNumericRestrictionType
    ACCESS          read-write
    STATUS          obsolete
    DESCRIPTION     
            "
             Minimum number of non-alpha-numeric characters that should be present in the password.
             "
    DEFVAL          { 1 }
    ::= { sonusSystemAdminEntry 20 }

sonusSystemAdminPasswordRulesPasswordHistoryDepth OBJECT-TYPE
    SYNTAX          PasswordHistoryDepthType
    ACCESS          read-write
    STATUS          obsolete
    DESCRIPTION     
            "
             The number of latest passwords that should be prevented from re-use.
             "
    DEFVAL          { 4 }
    ::= { sonusSystemAdminEntry 21 }

sonusSystemAdminPasswordRulesMaximumRepeatingCharsCount OBJECT-TYPE
    SYNTAX          MaxRepeatCountType
    ACCESS          read-write
    STATUS          obsolete
    DESCRIPTION     
            "
             Maximum number of consecutive repeatation for any character in the password.
             "
    DEFVAL          { 3 }
    ::= { sonusSystemAdminEntry 22 }

sonusSystemAdminCliSetWarningSupport OBJECT-TYPE
    SYNTAX          INTEGER { disabled(1), enabled(2) }
    ACCESS          read-write
    STATUS          obsolete
    DESCRIPTION     
            "
             Setting to enable/disable warning prompts configured for the set command. This
             setting does not modify warnings generated with the request command.
             "
    ::= { sonusSystemAdminEntry 23 }

sonusSystemAdminRowstatus OBJECT-TYPE
    SYNTAX          RowStatus
    ACCESS          read-write
    STATUS          obsolete
    DESCRIPTION     
            ""
    ::= { sonusSystemAdminEntry 24 }

sonusSystemAdminActualSystemName OBJECT-TYPE
    SYNTAX          String (SIZE(0..255))
    ACCESS          read-only
    STATUS          obsolete
    DESCRIPTION     
            "
             System Name given by user as user/metadata
             "
    ::= { sonusSystemAdminEntry 25 }

sonusSystemAdminClusterId OBJECT-TYPE
    SYNTAX          String (SIZE(0..255))
    ACCESS          read-only
    STATUS          obsolete
    DESCRIPTION     
            "
             clusterID instance given in userdata
             "
    ::= { sonusSystemAdminEntry 26 }

sonusSystemAdminDefaultAccountLocalOnly OBJECT-TYPE
    SYNTAX          TruthValue
    ACCESS          read-write
    STATUS          obsolete
    DESCRIPTION     
            "
             Default confd cli user admin can only have local authentication.
             "
    ::= { sonusSystemAdminEntry 27 }

sonusSystemAdminExternalAuthenticationType OBJECT-TYPE
    SYNTAX          ExternalAuthenticationType
    ACCESS          read-write
    STATUS          obsolete
    DESCRIPTION     
            "
             The confd cli user information stored on remote Radius server used for authentication.
             "
    DEFVAL          { radius }
    ::= { sonusSystemAdminEntry 28 }

sonusSystemApplicationsTable OBJECT-TYPE
    SYNTAX          SEQUENCE OF SonusSystemApplicationsEntry
    ACCESS          not-accessible
    STATUS          obsolete
    DESCRIPTION     
            "
             The applications deployed on the system.
             "
    ::= { sonusSystem 4 }

sonusSystemApplicationsEntry OBJECT-TYPE
    SYNTAX          SonusSystemApplicationsEntry
    ACCESS          not-accessible
    STATUS          obsolete
    DESCRIPTION     
            ""
    INDEX           { sonusSystemApplicationsName }
    ::= { sonusSystemApplicationsTable 1 }

SonusSystemApplicationsEntry ::=
    SEQUENCE {
        sonusSystemApplicationsName     String,
        sonusSystemApplicationsPath     String,
        sonusSystemApplicationsRowstatus RowStatus
    }

sonusSystemApplicationsName OBJECT-TYPE
    SYNTAX          String (SIZE(0..23))
    ACCESS          not-accessible
    STATUS          obsolete
    DESCRIPTION     
            "
             The name of the application.
             "
    ::= { sonusSystemApplicationsEntry 1 }

sonusSystemApplicationsPath OBJECT-TYPE
    SYNTAX          String (SIZE(0..255))
    ACCESS          read-write
    STATUS          obsolete
    DESCRIPTION     
            "
             The path of the application.
             "
    ::= { sonusSystemApplicationsEntry 2 }

sonusSystemApplicationsRowstatus OBJECT-TYPE
    SYNTAX          RowStatus
    ACCESS          read-write
    STATUS          obsolete
    DESCRIPTION     
            ""
    ::= { sonusSystemApplicationsEntry 3 }

sonusSystemHardDiskStatusTable OBJECT-TYPE
    SYNTAX          SEQUENCE OF SonusSystemHardDiskStatusEntry
    ACCESS          not-accessible
    STATUS          mandatory
    DESCRIPTION     
            "
             Hard disk status on the server(s).
             "
    ::= { sonusSystem 5 }

sonusSystemHardDiskStatusEntry OBJECT-TYPE
    SYNTAX          SonusSystemHardDiskStatusEntry
    ACCESS          not-accessible
    STATUS          mandatory
    DESCRIPTION     
            ""
    INDEX           { sonusSystemHardDiskStatusServerName, 
                      sonusSystemHardDiskStatusDiskNumber }
    ::= { sonusSystemHardDiskStatusTable 1 }

SonusSystemHardDiskStatusEntry ::=
    SEQUENCE {
        sonusSystemHardDiskStatusServerName   String,
        sonusSystemHardDiskStatusDiskNumber   DiskNumberType,
        sonusSystemHardDiskStatusPresent TruthValue,
        sonusSystemHardDiskStatusProductId  String,
        sonusSystemHardDiskStatusRevision String,
        sonusSystemHardDiskStatusCapacity String,
        sonusSystemHardDiskStatusDiskStatus   SonusNodeDiskStatusType,
        sonusSystemHardDiskStatusSyncStatus   SonusNodeSyncStatusType,
        sonusSystemHardDiskStatusSyncCompletion       String,
        sonusSystemHardDiskStatusHealthTest   String,
        sonusSystemHardDiskStatusDiskLifeRemaining          String
    }

sonusSystemHardDiskStatusServerName OBJECT-TYPE
    SYNTAX          String (SIZE(0..255))
    ACCESS          not-accessible
    STATUS          mandatory
    DESCRIPTION     
            "
             Identifies the server.
             "
    ::= { sonusSystemHardDiskStatusEntry 1 }

sonusSystemHardDiskStatusDiskNumber OBJECT-TYPE
    SYNTAX          DiskNumberType
    ACCESS          not-accessible
    STATUS          mandatory
    DESCRIPTION     
            "
             Hard disk number (typically 0 through 3)
             "
    ::= { sonusSystemHardDiskStatusEntry 2 }

sonusSystemHardDiskStatusPresent OBJECT-TYPE
    SYNTAX          TruthValue
    ACCESS          read-only
    STATUS          mandatory
    DESCRIPTION     
            "
             Indicates if the hard disk exists.
             "
    ::= { sonusSystemHardDiskStatusEntry 3 }

sonusSystemHardDiskStatusProductId OBJECT-TYPE
    SYNTAX          String (SIZE(0..255))
    ACCESS          read-only
    STATUS          mandatory
    DESCRIPTION     
            "
             Product ID of the hard disk as assigned by vendor
             "
    ::= { sonusSystemHardDiskStatusEntry 4 }

sonusSystemHardDiskStatusRevision OBJECT-TYPE
    SYNTAX          String (SIZE(0..23))
    ACCESS          read-only
    STATUS          mandatory
    DESCRIPTION     
            "
             Revision of the hard disk as assigned by vendor
             "
    ::= { sonusSystemHardDiskStatusEntry 5 }

sonusSystemHardDiskStatusCapacity OBJECT-TYPE
    SYNTAX          String (SIZE(0..23))
    ACCESS          read-only
    STATUS          mandatory
    DESCRIPTION     
            "
             Capacity of the disk
             "
    ::= { sonusSystemHardDiskStatusEntry 6 }

sonusSystemHardDiskStatusDiskStatus OBJECT-TYPE
    SYNTAX          SonusNodeDiskStatusType
    ACCESS          read-only
    STATUS          mandatory
    DESCRIPTION     
            "
             Harddisk status that indicates if the disk is online/failed
             "
    ::= { sonusSystemHardDiskStatusEntry 7 }

sonusSystemHardDiskStatusSyncStatus OBJECT-TYPE
    SYNTAX          SonusNodeSyncStatusType
    ACCESS          read-only
    STATUS          obsolete
    DESCRIPTION     
            "
             RAID synchrinization status
             "
    ::= { sonusSystemHardDiskStatusEntry 8 }

sonusSystemHardDiskStatusSyncCompletion OBJECT-TYPE
    SYNTAX          String (SIZE(0..23))
    ACCESS          read-only
    STATUS          obsolete
    DESCRIPTION     
            "
             Indicates hard disk sync completion percentage
             "
    ::= { sonusSystemHardDiskStatusEntry 9 }

sonusSystemHardDiskStatusHealthTest OBJECT-TYPE
    SYNTAX          String (SIZE(0..255))
    ACCESS          read-only
    STATUS          mandatory
    DESCRIPTION     
            "
             Pass or Fail indicating the overall health of the device.
             "
    ::= { sonusSystemHardDiskStatusEntry 10 }

sonusSystemHardDiskStatusDiskLifeRemaining OBJECT-TYPE
    SYNTAX          String (SIZE(0..23))
    ACCESS          read-only
    STATUS          mandatory
    DESCRIPTION     
            "
             A calculated percentage estimating the life remaining of the device or N/A if not supported by the device.
             "
    ::= { sonusSystemHardDiskStatusEntry 11 }

sonusSystemHardDiskUsageTable OBJECT-TYPE
    SYNTAX          SEQUENCE OF SonusSystemHardDiskUsageEntry
    ACCESS          not-accessible
    STATUS          mandatory
    DESCRIPTION     
            "
             Hard disk status on the server(s).
             "
    ::= { sonusSystem 6 }

sonusSystemHardDiskUsageEntry OBJECT-TYPE
    SYNTAX          SonusSystemHardDiskUsageEntry
    ACCESS          not-accessible
    STATUS          mandatory
    DESCRIPTION     
            ""
    INDEX           { sonusSystemHardDiskUsageServerName, 
                      sonusSystemHardDiskUsagePartition }
    ::= { sonusSystemHardDiskUsageTable 1 }

SonusSystemHardDiskUsageEntry ::=
    SEQUENCE {
        sonusSystemHardDiskUsageServerName  String,
        sonusSystemHardDiskUsagePartition String,
        sonusSystemHardDiskUsageTotalDiskSpace      String,
        sonusSystemHardDiskUsageFreeDiskSpace     String,
        sonusSystemHardDiskUsageUsedDiskSpace     String,
        sonusSystemHardDiskUsageRole    SonusNodeSrvrRole,
        sonusSystemHardDiskUsageSyncStatus  SonusNodeSyncStatusType,
        sonusSystemHardDiskUsageSyncCompletion      String
    }

sonusSystemHardDiskUsageServerName OBJECT-TYPE
    SYNTAX          String (SIZE(0..255))
    ACCESS          not-accessible
    STATUS          mandatory
    DESCRIPTION     
            "
             Identifies the server.
             "
    ::= { sonusSystemHardDiskUsageEntry 1 }

sonusSystemHardDiskUsagePartition OBJECT-TYPE
    SYNTAX          String (SIZE(0..255))
    ACCESS          not-accessible
    STATUS          mandatory
    DESCRIPTION     
            "
             Name of the hard disk partition
             "
    ::= { sonusSystemHardDiskUsageEntry 2 }

sonusSystemHardDiskUsageTotalDiskSpace OBJECT-TYPE
    SYNTAX          String (SIZE(0..23))
    ACCESS          read-only
    STATUS          mandatory
    DESCRIPTION     
            "
             Capacity of the disk (KBytes)
             "
    ::= { sonusSystemHardDiskUsageEntry 3 }

sonusSystemHardDiskUsageFreeDiskSpace OBJECT-TYPE
    SYNTAX          String (SIZE(0..23))
    ACCESS          read-only
    STATUS          mandatory
    DESCRIPTION     
            "
             Indicates free hard disk space (KBytes)
             "
    ::= { sonusSystemHardDiskUsageEntry 4 }

sonusSystemHardDiskUsageUsedDiskSpace OBJECT-TYPE
    SYNTAX          String (SIZE(0..23))
    ACCESS          read-only
    STATUS          mandatory
    DESCRIPTION     
            "
             Indicates used hard disk (%)
             "
    ::= { sonusSystemHardDiskUsageEntry 5 }

sonusSystemHardDiskUsageRole OBJECT-TYPE
    SYNTAX          SonusNodeSrvrRole
    ACCESS          read-only
    STATUS          mandatory
    DESCRIPTION     
            "
             Role of the server for the indicated partition
             "
    ::= { sonusSystemHardDiskUsageEntry 6 }

sonusSystemHardDiskUsageSyncStatus OBJECT-TYPE
    SYNTAX          SonusNodeSyncStatusType
    ACCESS          read-only
    STATUS          mandatory
    DESCRIPTION     
            "
             Partition's synchronization status with peer server
             "
    ::= { sonusSystemHardDiskUsageEntry 7 }

sonusSystemHardDiskUsageSyncCompletion OBJECT-TYPE
    SYNTAX          String (SIZE(0..23))
    ACCESS          read-only
    STATUS          mandatory
    DESCRIPTION     
            "
             Indicates partition's sync completion percentage
             "
    ::= { sonusSystemHardDiskUsageEntry 8 }

sonusSystemFanStatusTable OBJECT-TYPE
    SYNTAX          SEQUENCE OF SonusSystemFanStatusEntry
    ACCESS          not-accessible
    STATUS          mandatory
    DESCRIPTION     
            "
             Fan status on the server(s).
             "
    ::= { sonusSystem 7 }

sonusSystemFanStatusEntry OBJECT-TYPE
    SYNTAX          SonusSystemFanStatusEntry
    ACCESS          not-accessible
    STATUS          mandatory
    DESCRIPTION     
            ""
    INDEX           { sonusSystemFanStatusServerName, 
                      sonusSystemFanStatusFanId }
    ::= { sonusSystemFanStatusTable 1 }

SonusSystemFanStatusEntry ::=
    SEQUENCE {
        sonusSystemFanStatusServerName  String,
        sonusSystemFanStatusFanId       String,
        sonusSystemFanStatusSpeed       String
    }

sonusSystemFanStatusServerName OBJECT-TYPE
    SYNTAX          String (SIZE(0..255))
    ACCESS          not-accessible
    STATUS          mandatory
    DESCRIPTION     
            "
             Identifies the server.
             "
    ::= { sonusSystemFanStatusEntry 1 }

sonusSystemFanStatusFanId OBJECT-TYPE
    SYNTAX          String (SIZE(0..255))
    ACCESS          not-accessible
    STATUS          mandatory
    DESCRIPTION     
            "
             The name of the fan (usually /FT0/F0/ /FT0/F1/ etc).
             "
    ::= { sonusSystemFanStatusEntry 2 }

sonusSystemFanStatusSpeed OBJECT-TYPE
    SYNTAX          String (SIZE(0..23))
    ACCESS          read-only
    STATUS          mandatory
    DESCRIPTION     
            "
             Indicates the fan speed in RPM.
             "
    ::= { sonusSystemFanStatusEntry 3 }

sonusSystemPowerSupplyStatusTable OBJECT-TYPE
    SYNTAX          SEQUENCE OF SonusSystemPowerSupplyStatusEntry
    ACCESS          not-accessible
    STATUS          mandatory
    DESCRIPTION     
            "
             Power consumption/state of the server.
             "
    ::= { sonusSystem 8 }

sonusSystemPowerSupplyStatusEntry OBJECT-TYPE
    SYNTAX          SonusSystemPowerSupplyStatusEntry
    ACCESS          not-accessible
    STATUS          mandatory
    DESCRIPTION     
            ""
    INDEX           { sonusSystemPowerSupplyStatusServerName, 
                      sonusSystemPowerSupplyStatusPowerSupplyId }
    ::= { sonusSystemPowerSupplyStatusTable 1 }

SonusSystemPowerSupplyStatusEntry ::=
    SEQUENCE {
        sonusSystemPowerSupplyStatusServerName      String,
        sonusSystemPowerSupplyStatusPowerSupplyId         String,
        sonusSystemPowerSupplyStatusPresent   TruthValue,
        sonusSystemPowerSupplyStatusProductName       String,
        sonusSystemPowerSupplyStatusSerialNum     SonusNodeSrvrStatSerialNumType,
        sonusSystemPowerSupplyStatusPartNum   SonusNodeSrvrStatPartNumType,
        sonusSystemPowerSupplyStatusManufactureDate           SonusNodeSrvrStatMfgDateType,
        sonusSystemPowerSupplyStatusInputPower      String,
        sonusSystemPowerSupplyStatusInputVoltage        String,
        sonusSystemPowerSupplyStatusInputCurrent        String,
        sonusSystemPowerSupplyStatusOutputPower       String,
        sonusSystemPowerSupplyStatusOutputVoltage         String,
        sonusSystemPowerSupplyStatusOutputCurrent         String,
        sonusSystemPowerSupplyStatusAmbientTemperature              String,
        sonusSystemPowerSupplyStatusFanSpeed    String,
        sonusSystemPowerSupplyStatusPowerFault      TruthValue,
        sonusSystemPowerSupplyStatusVoltageFault        TruthValue,
        sonusSystemPowerSupplyStatusCurrentFault        TruthValue,
        sonusSystemPowerSupplyStatusFanFault    TruthValue,
        sonusSystemPowerSupplyStatusTemperatureFault            TruthValue
    }

sonusSystemPowerSupplyStatusServerName OBJECT-TYPE
    SYNTAX          String (SIZE(0..255))
    ACCESS          not-accessible
    STATUS          mandatory
    DESCRIPTION     
            "
             Identifies the server.
             "
    ::= { sonusSystemPowerSupplyStatusEntry 1 }

sonusSystemPowerSupplyStatusPowerSupplyId OBJECT-TYPE
    SYNTAX          String (SIZE(0..23))
    ACCESS          not-accessible
    STATUS          mandatory
    DESCRIPTION     
            "
             The name of the power supply (/SYS/VPS)
             "
    ::= { sonusSystemPowerSupplyStatusEntry 2 }

sonusSystemPowerSupplyStatusPresent OBJECT-TYPE
    SYNTAX          TruthValue
    ACCESS          read-only
    STATUS          mandatory
    DESCRIPTION     
            "
             Indicates if the module is present or not.
             "
    ::= { sonusSystemPowerSupplyStatusEntry 3 }

sonusSystemPowerSupplyStatusProductName OBJECT-TYPE
    SYNTAX          String (SIZE(0..255))
    ACCESS          read-only
    STATUS          mandatory
    DESCRIPTION     
            "
             Identifies the name (as given by manufacturer) of power supply module.
             "
    ::= { sonusSystemPowerSupplyStatusEntry 4 }

sonusSystemPowerSupplyStatusSerialNum OBJECT-TYPE
    SYNTAX          SonusNodeSrvrStatSerialNumType
    ACCESS          read-only
    STATUS          mandatory
    DESCRIPTION     
            "
             Identifies the serial number of the power supply module.  This is the
             serial number assigned to the server module at manufacture.
             "
    ::= { sonusSystemPowerSupplyStatusEntry 5 }

sonusSystemPowerSupplyStatusPartNum OBJECT-TYPE
    SYNTAX          SonusNodeSrvrStatPartNumType
    ACCESS          read-only
    STATUS          mandatory
    DESCRIPTION     
            "
             Identifies the part number of the module.  This is the
             part number assigned to the module at manufacture.
             "
    ::= { sonusSystemPowerSupplyStatusEntry 6 }

sonusSystemPowerSupplyStatusManufactureDate OBJECT-TYPE
    SYNTAX          SonusNodeSrvrStatMfgDateType
    ACCESS          read-only
    STATUS          obsolete
    DESCRIPTION     
            "
             The date this power supply module was manufactured.
             "
    ::= { sonusSystemPowerSupplyStatusEntry 7 }

sonusSystemPowerSupplyStatusInputPower OBJECT-TYPE
    SYNTAX          String (SIZE(0..23))
    ACCESS          read-only
    STATUS          obsolete
    DESCRIPTION     
            "
             Indicates input power in watts.
             "
    ::= { sonusSystemPowerSupplyStatusEntry 8 }

sonusSystemPowerSupplyStatusInputVoltage OBJECT-TYPE
    SYNTAX          String (SIZE(0..23))
    ACCESS          read-only
    STATUS          obsolete
    DESCRIPTION     
            "
             Indicates input volatge.
             "
    ::= { sonusSystemPowerSupplyStatusEntry 9 }

sonusSystemPowerSupplyStatusInputCurrent OBJECT-TYPE
    SYNTAX          String (SIZE(0..23))
    ACCESS          read-only
    STATUS          obsolete
    DESCRIPTION     
            "
             Indicates input current.
             "
    ::= { sonusSystemPowerSupplyStatusEntry 10 }

sonusSystemPowerSupplyStatusOutputPower OBJECT-TYPE
    SYNTAX          String (SIZE(0..23))
    ACCESS          read-only
    STATUS          obsolete
    DESCRIPTION     
            "
             Indicates output power in watts.
             "
    ::= { sonusSystemPowerSupplyStatusEntry 11 }

sonusSystemPowerSupplyStatusOutputVoltage OBJECT-TYPE
    SYNTAX          String (SIZE(0..23))
    ACCESS          read-only
    STATUS          obsolete
    DESCRIPTION     
            "
             Indicates output volatge.
             "
    ::= { sonusSystemPowerSupplyStatusEntry 12 }

sonusSystemPowerSupplyStatusOutputCurrent OBJECT-TYPE
    SYNTAX          String (SIZE(0..23))
    ACCESS          read-only
    STATUS          obsolete
    DESCRIPTION     
            "
             Indicates output current.
             "
    ::= { sonusSystemPowerSupplyStatusEntry 13 }

sonusSystemPowerSupplyStatusAmbientTemperature OBJECT-TYPE
    SYNTAX          String (SIZE(0..23))
    ACCESS          read-only
    STATUS          obsolete
    DESCRIPTION     
            "
             Indicates ambient temperature of the power supply unit.
             "
    ::= { sonusSystemPowerSupplyStatusEntry 14 }

sonusSystemPowerSupplyStatusFanSpeed OBJECT-TYPE
    SYNTAX          String (SIZE(0..23))
    ACCESS          read-only
    STATUS          obsolete
    DESCRIPTION     
            "
             Indicates the fan speed in RPM.
             "
    ::= { sonusSystemPowerSupplyStatusEntry 15 }

sonusSystemPowerSupplyStatusPowerFault OBJECT-TYPE
    SYNTAX          TruthValue
    ACCESS          read-only
    STATUS          mandatory
    DESCRIPTION     
            "
             Indicates if there is power fault.
             "
    ::= { sonusSystemPowerSupplyStatusEntry 16 }

sonusSystemPowerSupplyStatusVoltageFault OBJECT-TYPE
    SYNTAX          TruthValue
    ACCESS          read-only
    STATUS          mandatory
    DESCRIPTION     
            "
             Indicates if there is voltage fault.
             "
    ::= { sonusSystemPowerSupplyStatusEntry 17 }

sonusSystemPowerSupplyStatusCurrentFault OBJECT-TYPE
    SYNTAX          TruthValue
    ACCESS          read-only
    STATUS          obsolete
    DESCRIPTION     
            "
             Indicates if there is current fault.
             "
    ::= { sonusSystemPowerSupplyStatusEntry 18 }

sonusSystemPowerSupplyStatusFanFault OBJECT-TYPE
    SYNTAX          TruthValue
    ACCESS          read-only
    STATUS          obsolete
    DESCRIPTION     
            "
             Indicates if there is fan fault.
             "
    ::= { sonusSystemPowerSupplyStatusEntry 19 }

sonusSystemPowerSupplyStatusTemperatureFault OBJECT-TYPE
    SYNTAX          TruthValue
    ACCESS          read-only
    STATUS          obsolete
    DESCRIPTION     
            "
             Indicates if there is temperature fault.
             "
    ::= { sonusSystemPowerSupplyStatusEntry 20 }

sonusSystemFileTransferStatusTable OBJECT-TYPE
    SYNTAX          SEQUENCE OF SonusSystemFileTransferStatusEntry
    ACCESS          not-accessible
    STATUS          obsolete
    DESCRIPTION     
            "
             File transfer status on the system.
             "
    ::= { sonusSystem 9 }

sonusSystemFileTransferStatusEntry OBJECT-TYPE
    SYNTAX          SonusSystemFileTransferStatusEntry
    ACCESS          not-accessible
    STATUS          obsolete
    DESCRIPTION     
            ""
    INDEX           { sonusSystemFileTransferStatusServerName, 
                      sonusSystemFileTransferStatusFileName }
    ::= { sonusSystemFileTransferStatusTable 1 }

SonusSystemFileTransferStatusEntry ::=
    SEQUENCE {
        sonusSystemFileTransferStatusServerName       String,
        sonusSystemFileTransferStatusFileName     String,
        sonusSystemFileTransferStatusSource   String,
        sonusSystemFileTransferStatusStartTime      String,
        sonusSystemFileTransferStatusCompletion       String,
        sonusSystemFileTransferStatusStatus   String
    }

sonusSystemFileTransferStatusServerName OBJECT-TYPE
    SYNTAX          String (SIZE(0..255))
    ACCESS          not-accessible
    STATUS          obsolete
    DESCRIPTION     
            "
             Identifies the server.
             "
    ::= { sonusSystemFileTransferStatusEntry 1 }

sonusSystemFileTransferStatusFileName OBJECT-TYPE
    SYNTAX          String (SIZE(0..255))
    ACCESS          not-accessible
    STATUS          obsolete
    DESCRIPTION     
            "
             Identifies the file.
             "
    ::= { sonusSystemFileTransferStatusEntry 2 }

sonusSystemFileTransferStatusSource OBJECT-TYPE
    SYNTAX          String (SIZE(0..255))
    ACCESS          read-only
    STATUS          obsolete
    DESCRIPTION     
            "
             Identifies the source from where getting this file.
             "
    ::= { sonusSystemFileTransferStatusEntry 3 }

sonusSystemFileTransferStatusStartTime OBJECT-TYPE
    SYNTAX          String (SIZE(0..255))
    ACCESS          read-only
    STATUS          obsolete
    DESCRIPTION     
            "
             Indicates when the file transfer started.
             "
    ::= { sonusSystemFileTransferStatusEntry 4 }

sonusSystemFileTransferStatusCompletion OBJECT-TYPE
    SYNTAX          String (SIZE(0..23))
    ACCESS          read-only
    STATUS          obsolete
    DESCRIPTION     
            "
             Percentage completion so far.
             "
    ::= { sonusSystemFileTransferStatusEntry 5 }

sonusSystemFileTransferStatusStatus OBJECT-TYPE
    SYNTAX          String (SIZE(0..255))
    ACCESS          read-only
    STATUS          obsolete
    DESCRIPTION     
            "
             Status of the transfer, success/failure reason.
             "
    ::= { sonusSystemFileTransferStatusEntry 6 }

sonusSystemSyncStatusTable OBJECT-TYPE
    SYNTAX          SEQUENCE OF SonusSystemSyncStatusEntry
    ACCESS          not-accessible
    STATUS          mandatory
    DESCRIPTION     
            "
             The system server synchronization status table, describes data synchronization state of various items.
             "
    ::= { sonusSystem 10 }

sonusSystemSyncStatusEntry OBJECT-TYPE
    SYNTAX          SonusSystemSyncStatusEntry
    ACCESS          not-accessible
    STATUS          mandatory
    DESCRIPTION     
            ""
    INDEX           { sonusSystemSyncStatusSyncModule }
    ::= { sonusSystemSyncStatusTable 1 }

SonusSystemSyncStatusEntry ::=
    SEQUENCE {
        sonusSystemSyncStatusSyncModule String,
        sonusSystemSyncStatusStatus     SonusNodeSrvrSyncStatusType
    }

sonusSystemSyncStatusSyncModule OBJECT-TYPE
    SYNTAX          String (SIZE(0..255))
    ACCESS          not-accessible
    STATUS          mandatory
    DESCRIPTION     
            "
             Identifies the syncronization item.
             "
    ::= { sonusSystemSyncStatusEntry 1 }

sonusSystemSyncStatusStatus OBJECT-TYPE
    SYNTAX          SonusNodeSrvrSyncStatusType
    ACCESS          read-only
    STATUS          mandatory
    DESCRIPTION     
            "
             Indicates the inter-CE data synchronization state.
             "
    ::= { sonusSystemSyncStatusEntry 2 }

sonusSystemServerStatusTable OBJECT-TYPE
    SYNTAX          SEQUENCE OF SonusSystemServerStatusEntry
    ACCESS          not-accessible
    STATUS          mandatory
    DESCRIPTION     
            "
             The system server status table describes the status of the
             server module.
             "
    ::= { sonusSystem 12 }

sonusSystemServerStatusEntry OBJECT-TYPE
    SYNTAX          SonusSystemServerStatusEntry
    ACCESS          not-accessible
    STATUS          mandatory
    DESCRIPTION     
            ""
    INDEX           { sonusSystemServerStatusName }
    ::= { sonusSystemServerStatusTable 1 }

SonusSystemServerStatusEntry ::=
    SEQUENCE {
        sonusSystemServerStatusName     String,
        sonusSystemServerStatusHwType   SonusNodeSrvrHwType,
        sonusSystemServerStatusSerialNum SonusNodeSrvrStatSerialNumType,
        sonusSystemServerStatusPartNum  SonusNodeSrvrStatPartNumType,
        sonusSystemServerStatusManufactureDate      SonusNodeSrvrStatMfgDateType,
        sonusSystemServerStatusPlatformVersion      SonusNodeSrvrStatSwVersionType,
        sonusSystemServerStatusApplicationVersion         SonusNodeSrvrStatSwVersionType,
        sonusSystemServerStatusMgmtRedundancyRole         SonusNodeSrvrStatModeType,
        sonusSystemServerStatusUpTime   String,
        sonusSystemServerStatusApplicationUpTime        String,
        sonusSystemServerStatusLastRestartReason        SonusNodeSrvrLastRestartReasonType,
        sonusSystemServerStatusSyncStatus SonusNodeSrvrSyncStatusType,
        sonusSystemServerStatusDaughterBoardPresent           TruthValue,
        sonusSystemServerStatusCurrentTime  String,
        sonusSystemServerStatusPktPortSpeed   SonusNodeSrvrPktPortSpeed,
        sonusSystemServerStatusActualCeName   String,
        sonusSystemServerStatusHwSubType SonusNodeSrvrHwType,
        sonusSystemServerStatusFingerprint  String
    }

sonusSystemServerStatusName OBJECT-TYPE
    SYNTAX          String (SIZE(0..255))
    ACCESS          not-accessible
    STATUS          mandatory
    DESCRIPTION     
            "
             Identifies the server.
             "
    ::= { sonusSystemServerStatusEntry 1 }

sonusSystemServerStatusHwType OBJECT-TYPE
    SYNTAX          SonusNodeSrvrHwType
    ACCESS          read-only
    STATUS          mandatory
    DESCRIPTION     
            "
             Identifies the type of server module the indexed slot has been
             configured to accept.  Server modules other than this type are
             rejected by the System Manager.
             "
    ::= { sonusSystemServerStatusEntry 2 }

sonusSystemServerStatusSerialNum OBJECT-TYPE
    SYNTAX          SonusNodeSrvrStatSerialNumType
    ACCESS          read-only
    STATUS          mandatory
    DESCRIPTION     
            "
             Identifies the serial number of the server module.  This is the
             serial number assigned to the server module at manufacture.
             "
    ::= { sonusSystemServerStatusEntry 3 }

sonusSystemServerStatusPartNum OBJECT-TYPE
    SYNTAX          SonusNodeSrvrStatPartNumType
    ACCESS          read-only
    STATUS          mandatory
    DESCRIPTION     
            "
             Identifies the part number of the module.  This is the
             part number assigned to the module at manufacture.
             "
    ::= { sonusSystemServerStatusEntry 4 }

sonusSystemServerStatusManufactureDate OBJECT-TYPE
    SYNTAX          SonusNodeSrvrStatMfgDateType
    ACCESS          read-only
    STATUS          obsolete
    DESCRIPTION     
            "
             The date this server module assembly was manufactured.
             "
    ::= { sonusSystemServerStatusEntry 5 }

sonusSystemServerStatusPlatformVersion OBJECT-TYPE
    SYNTAX          SonusNodeSrvrStatSwVersionType
    ACCESS          read-only
    STATUS          mandatory
    DESCRIPTION     
            "
             Indicates the platform version currently running on server.
             "
    ::= { sonusSystemServerStatusEntry 6 }

sonusSystemServerStatusApplicationVersion OBJECT-TYPE
    SYNTAX          SonusNodeSrvrStatSwVersionType
    ACCESS          read-only
    STATUS          mandatory
    DESCRIPTION     
            "
             Indicates the application version currently running on server.
             "
    ::= { sonusSystemServerStatusEntry 7 }

sonusSystemServerStatusMgmtRedundancyRole OBJECT-TYPE
    SYNTAX          SonusNodeSrvrStatModeType
    ACCESS          read-only
    STATUS          mandatory
    DESCRIPTION     
            "
             Indicates the redundancy role of the server (for management entities)
             "
    ::= { sonusSystemServerStatusEntry 8 }

sonusSystemServerStatusUpTime OBJECT-TYPE
    SYNTAX          String (SIZE(0..255))
    ACCESS          read-only
    STATUS          mandatory
    DESCRIPTION     
            "
             Indicates the server module uptime in days/hours/minutes/sec.
             "
    ::= { sonusSystemServerStatusEntry 9 }

sonusSystemServerStatusApplicationUpTime OBJECT-TYPE
    SYNTAX          String (SIZE(0..255))
    ACCESS          read-only
    STATUS          mandatory
    DESCRIPTION     
            "
             Indicates the application uptime on the server in days/hours/minutes/sec.
             "
    ::= { sonusSystemServerStatusEntry 10 }

sonusSystemServerStatusLastRestartReason OBJECT-TYPE
    SYNTAX          SonusNodeSrvrLastRestartReasonType
    ACCESS          read-only
    STATUS          mandatory
    DESCRIPTION     
            "
             Indicates the reason for last restart of the server.
             "
    ::= { sonusSystemServerStatusEntry 11 }

sonusSystemServerStatusSyncStatus OBJECT-TYPE
    SYNTAX          SonusNodeSrvrSyncStatusType
    ACCESS          read-only
    STATUS          mandatory
    DESCRIPTION     
            "
             Indicates the inter-CE data synchronization state.
             "
    ::= { sonusSystemServerStatusEntry 12 }

sonusSystemServerStatusDaughterBoardPresent OBJECT-TYPE
    SYNTAX          TruthValue
    ACCESS          read-only
    STATUS          mandatory
    DESCRIPTION     
            "
             Indicates if the daughter board exists.
             "
    ::= { sonusSystemServerStatusEntry 13 }

sonusSystemServerStatusCurrentTime OBJECT-TYPE
    SYNTAX          String (SIZE(0..255))
    ACCESS          read-only
    STATUS          mandatory
    DESCRIPTION     
            "
             Indicates the current system time.
             "
    ::= { sonusSystemServerStatusEntry 14 }

sonusSystemServerStatusPktPortSpeed OBJECT-TYPE
    SYNTAX          SonusNodeSrvrPktPortSpeed
    ACCESS          read-only
    STATUS          mandatory
    DESCRIPTION     
            "
             Packet port speed setting.
             "
    ::= { sonusSystemServerStatusEntry 15 }

sonusSystemServerStatusActualCeName OBJECT-TYPE
    SYNTAX          String (SIZE(0..255))
    ACCESS          read-only
    STATUS          mandatory
    DESCRIPTION     
            "
             Identifies the given/actual server.
             "
    ::= { sonusSystemServerStatusEntry 16 }

sonusSystemServerStatusHwSubType OBJECT-TYPE
    SYNTAX          SonusNodeSrvrHwType
    ACCESS          read-only
    STATUS          mandatory
    DESCRIPTION     
            "
             Identifies the type of server module the indexed slot has been
             configured to accept.  Server modules other than this type are
             rejected by the System Manager.
             "
    ::= { sonusSystemServerStatusEntry 17 }

sonusSystemServerStatusFingerprint OBJECT-TYPE
    SYNTAX          String (SIZE(0..255))
    ACCESS          read-only
    STATUS          mandatory
    DESCRIPTION     
            "
             The licensing fingerprint for the node
             "
    ::= { sonusSystemServerStatusEntry 18 }

sonusSystemDaughterBoardStatusTable OBJECT-TYPE
    SYNTAX          SEQUENCE OF SonusSystemDaughterBoardStatusEntry
    ACCESS          not-accessible
    STATUS          obsolete
    DESCRIPTION     
            "
             Indicates the daughter board status on the server.
             "
    ::= { sonusSystem 13 }

sonusSystemDaughterBoardStatusEntry OBJECT-TYPE
    SYNTAX          SonusSystemDaughterBoardStatusEntry
    ACCESS          not-accessible
    STATUS          obsolete
    DESCRIPTION     
            ""
    INDEX           { sonusSystemDaughterBoardStatusServerName, 
                      sonusSystemDaughterBoardStatusSlot }
    ::= { sonusSystemDaughterBoardStatusTable 1 }

SonusSystemDaughterBoardStatusEntry ::=
    SEQUENCE {
        sonusSystemDaughterBoardStatusServerName        String,
        sonusSystemDaughterBoardStatusDaughterBoardId             String,
        sonusSystemDaughterBoardStatusPresent     TruthValue,
        sonusSystemDaughterBoardStatusProductName         String,
        sonusSystemDaughterBoardStatusSerialNum       SonusNodeSrvrStatSerialNumType,
        sonusSystemDaughterBoardStatusPartNum     SonusNodeSrvrStatPartNumType,
        sonusSystemDaughterBoardStatusSlot  SonusDspSlotIndex,
        sonusSystemDaughterBoardStatusOperationalStatus               DaughterBoardOperationalStatus,
        sonusSystemDaughterBoardStatusLogicalId       SonusDspSlotIndex,
        sonusSystemDaughterBoardStatusImageLoadFailureCount                   Gauge,
        sonusSystemDaughterBoardStatusFpgaVersion         String
    }

sonusSystemDaughterBoardStatusServerName OBJECT-TYPE
    SYNTAX          String (SIZE(0..255))
    ACCESS          not-accessible
    STATUS          obsolete
    DESCRIPTION     
            "
             Identifies the server.
             "
    ::= { sonusSystemDaughterBoardStatusEntry 1 }

sonusSystemDaughterBoardStatusDaughterBoardId OBJECT-TYPE
    SYNTAX          String (SIZE(0..23))
    ACCESS          read-only
    STATUS          obsolete
    DESCRIPTION     
            "
             The name of the daughter board.
             "
    ::= { sonusSystemDaughterBoardStatusEntry 2 }

sonusSystemDaughterBoardStatusPresent OBJECT-TYPE
    SYNTAX          TruthValue
    ACCESS          read-only
    STATUS          obsolete
    DESCRIPTION     
            "
             Indicates if the module is present or not.
             "
    ::= { sonusSystemDaughterBoardStatusEntry 3 }

sonusSystemDaughterBoardStatusProductName OBJECT-TYPE
    SYNTAX          String (SIZE(0..255))
    ACCESS          read-only
    STATUS          obsolete
    DESCRIPTION     
            "
             Identifies the name (as given by manufacturer) of the module.
             "
    ::= { sonusSystemDaughterBoardStatusEntry 4 }

sonusSystemDaughterBoardStatusSerialNum OBJECT-TYPE
    SYNTAX          SonusNodeSrvrStatSerialNumType
    ACCESS          read-only
    STATUS          obsolete
    DESCRIPTION     
            "
             Identifies the serial number of the daughter board module.  This is the
             serial number assigned to the server module at manufacture.
             "
    ::= { sonusSystemDaughterBoardStatusEntry 5 }

sonusSystemDaughterBoardStatusPartNum OBJECT-TYPE
    SYNTAX          SonusNodeSrvrStatPartNumType
    ACCESS          read-only
    STATUS          obsolete
    DESCRIPTION     
            "
             Identifies the part number of the module.  This is the
             part number assigned to the module at manufacture.
             "
    ::= { sonusSystemDaughterBoardStatusEntry 6 }

sonusSystemDaughterBoardStatusSlot OBJECT-TYPE
    SYNTAX          SonusDspSlotIndex
    ACCESS          not-accessible
    STATUS          obsolete
    DESCRIPTION     
            "
             Identifies the slot associated with the DSP board.
             "
    ::= { sonusSystemDaughterBoardStatusEntry 7 }

sonusSystemDaughterBoardStatusOperationalStatus OBJECT-TYPE
    SYNTAX          DaughterBoardOperationalStatus
    ACCESS          read-only
    STATUS          obsolete
    DESCRIPTION     
            "
             Identifies the operational state of the board.
             "
    ::= { sonusSystemDaughterBoardStatusEntry 8 }

sonusSystemDaughterBoardStatusLogicalId OBJECT-TYPE
    SYNTAX          SonusDspSlotIndex
    ACCESS          read-only
    STATUS          obsolete
    DESCRIPTION     
            "
             Identifies the logical id of the slot.
             "
    ::= { sonusSystemDaughterBoardStatusEntry 9 }

sonusSystemDaughterBoardStatusImageLoadFailureCount OBJECT-TYPE
    SYNTAX          Gauge
    ACCESS          read-only
    STATUS          obsolete
    DESCRIPTION     
            "
             Indicates daughter board image load failure count since last successful attempt.
             "
    ::= { sonusSystemDaughterBoardStatusEntry 10 }

sonusSystemDaughterBoardStatusFpgaVersion OBJECT-TYPE
    SYNTAX          String (SIZE(0..255))
    ACCESS          read-only
    STATUS          obsolete
    DESCRIPTION     
            "
             FPGA version of slot.
             "
    ::= { sonusSystemDaughterBoardStatusEntry 11 }

sonusSystemServerSoftwareUpgradeStatusTable OBJECT-TYPE
    SYNTAX          SEQUENCE OF SonusSystemServerSoftwareUpgradeStatusEntry
    ACCESS          not-accessible
    STATUS          mandatory
    DESCRIPTION     
            "
             The system server software upgrade status table describes the status of the
             server software upgrade module.
             "
    ::= { sonusSystem 14 }

sonusSystemServerSoftwareUpgradeStatusEntry OBJECT-TYPE
    SYNTAX          SonusSystemServerSoftwareUpgradeStatusEntry
    ACCESS          not-accessible
    STATUS          mandatory
    DESCRIPTION     
            ""
    INDEX           { sonusSystemServerSoftwareUpgradeStatusName }
    ::= { sonusSystemServerSoftwareUpgradeStatusTable 1 }

SonusSystemServerSoftwareUpgradeStatusEntry ::=
    SEQUENCE {
        sonusSystemServerSoftwareUpgradeStatusName          String,
        sonusSystemServerSoftwareUpgradeStatusUpgradeStatus                   SonusNodeServerLiveSoftwareUpgradeStatusType
    }

sonusSystemServerSoftwareUpgradeStatusName OBJECT-TYPE
    SYNTAX          String (SIZE(0..255))
    ACCESS          not-accessible
    STATUS          mandatory
    DESCRIPTION     
            "
             Identifies the server.
             "
    ::= { sonusSystemServerSoftwareUpgradeStatusEntry 1 }

sonusSystemServerSoftwareUpgradeStatusUpgradeStatus OBJECT-TYPE
    SYNTAX          SonusNodeServerLiveSoftwareUpgradeStatusType
    ACCESS          read-only
    STATUS          mandatory
    DESCRIPTION     
            "
             Indicates the current status of the server.
             "
    ::= { sonusSystemServerSoftwareUpgradeStatusEntry 2 }

sonusSystemLicenseInfoTable OBJECT-TYPE
    SYNTAX          SEQUENCE OF SonusSystemLicenseInfoEntry
    ACCESS          not-accessible
    STATUS          mandatory
    DESCRIPTION     
            "
             The license status for registered license features.
             "
    ::= { sonusSystem 15 }

sonusSystemLicenseInfoEntry OBJECT-TYPE
    SYNTAX          SonusSystemLicenseInfoEntry
    ACCESS          not-accessible
    STATUS          mandatory
    DESCRIPTION     
            ""
    INDEX           { sonusSystemLicenseInfoFeatureName, 
                      sonusSystemLicenseInfoLicenseId }
    ::= { sonusSystemLicenseInfoTable 1 }

SonusSystemLicenseInfoEntry ::=
    SEQUENCE {
        sonusSystemLicenseInfoFeatureName String,
        sonusSystemLicenseInfoLicenseId String,
        sonusSystemLicenseInfoExpirationDate    String,
        sonusSystemLicenseInfoUsageLimit INTEGER,
        sonusSystemLicenseInfoSource    String,
        sonusSystemLicenseInfoInUse     INTEGER
    }

sonusSystemLicenseInfoFeatureName OBJECT-TYPE
    SYNTAX          String (SIZE(0..255))
    ACCESS          not-accessible
    STATUS          mandatory
    DESCRIPTION     
            "
             This object indicates the feature name
             "
    ::= { sonusSystemLicenseInfoEntry 1 }

sonusSystemLicenseInfoLicenseId OBJECT-TYPE
    SYNTAX          String (SIZE(0..64))
    ACCESS          not-accessible
    STATUS          mandatory
    DESCRIPTION     
            "
             This object indicates the license Id.
             "
    ::= { sonusSystemLicenseInfoEntry 2 }

sonusSystemLicenseInfoExpirationDate OBJECT-TYPE
    SYNTAX          String (SIZE(0..255))
    ACCESS          read-only
    STATUS          mandatory
    DESCRIPTION     
            "
             This object indicates the licence expiry date for a feature.
             "
    ::= { sonusSystemLicenseInfoEntry 3 }

sonusSystemLicenseInfoUsageLimit OBJECT-TYPE
    SYNTAX          INTEGER
    ACCESS          read-only
    STATUS          mandatory
    DESCRIPTION     
            "
             This object indicates the usageLimit of a feature.
             "
    ::= { sonusSystemLicenseInfoEntry 4 }

sonusSystemLicenseInfoSource OBJECT-TYPE
    SYNTAX          String (SIZE(0..255))
    ACCESS          read-only
    STATUS          mandatory
    DESCRIPTION     
            "
             Indicates where the licenses is located: nodeLocked or domain
             "
    ::= { sonusSystemLicenseInfoEntry 5 }

sonusSystemLicenseInfoInUse OBJECT-TYPE
    SYNTAX          INTEGER
    ACCESS          read-only
    STATUS          mandatory
    DESCRIPTION     
            "
             Indicates the number of licenses used by the application
             "
    ::= { sonusSystemLicenseInfoEntry 6 }

sonusSystemBaseMacAddressTable OBJECT-TYPE
    SYNTAX          SEQUENCE OF SonusSystemBaseMacAddressEntry
    ACCESS          not-accessible
    STATUS          mandatory
    DESCRIPTION     
            "
             Displays base MAC address of servers
             "
    ::= { sonusSystem 16 }

sonusSystemBaseMacAddressEntry OBJECT-TYPE
    SYNTAX          SonusSystemBaseMacAddressEntry
    ACCESS          not-accessible
    STATUS          mandatory
    DESCRIPTION     
            ""
    INDEX           { IMPLIED sonusSystemBaseMacAddressServerName }
    ::= { sonusSystemBaseMacAddressTable 1 }

SonusSystemBaseMacAddressEntry ::=
    SEQUENCE {
        sonusSystemBaseMacAddressServerName   String,
        sonusSystemBaseMacAddressAssignedBaseAddress            HexList,
        sonusSystemBaseMacAddressCurrentBaseAddress           HexList,
        sonusSystemBaseMacAddressActiveBaseAddress          HexList
    }

sonusSystemBaseMacAddressServerName OBJECT-TYPE
    SYNTAX          String (SIZE(0..255))
    ACCESS          not-accessible
    STATUS          mandatory
    DESCRIPTION     
            "
             Name of server.
             "
    ::= { sonusSystemBaseMacAddressEntry 1 }

sonusSystemBaseMacAddressAssignedBaseAddress OBJECT-TYPE
    SYNTAX          HexList (SIZE(6))
    ACCESS          read-only
    STATUS          mandatory
    DESCRIPTION     
            "
             MAC address base assigned to this server
             "
    ::= { sonusSystemBaseMacAddressEntry 2 }

sonusSystemBaseMacAddressCurrentBaseAddress OBJECT-TYPE
    SYNTAX          HexList (SIZE(6))
    ACCESS          read-only
    STATUS          obsolete
    DESCRIPTION     
            "
             MAC address base assigned to this server at this time
             "
    ::= { sonusSystemBaseMacAddressEntry 3 }

sonusSystemBaseMacAddressActiveBaseAddress OBJECT-TYPE
    SYNTAX          HexList (SIZE(6))
    ACCESS          read-only
    STATUS          mandatory
    DESCRIPTION     
            "
             MAC address base assigned to the active server
             "
    ::= { sonusSystemBaseMacAddressEntry 4 }

sonusSystemCpuUtilCurrentStatisticsTable OBJECT-TYPE
    SYNTAX          SEQUENCE OF SonusSystemCpuUtilCurrentStatisticsEntry
    ACCESS          not-accessible
    STATUS          mandatory
    DESCRIPTION     
            "
             The CPU utilization for the current
             interval period.
             "
    ::= { sonusSystem 17 }

sonusSystemCpuUtilCurrentStatisticsEntry OBJECT-TYPE
    SYNTAX          SonusSystemCpuUtilCurrentStatisticsEntry
    ACCESS          not-accessible
    STATUS          mandatory
    DESCRIPTION     
            ""
    INDEX           { sonusSystemCpuUtilCurrentStatisticsCeName, 
                      sonusSystemCpuUtilCurrentStatisticsCpu }
    ::= { sonusSystemCpuUtilCurrentStatisticsTable 1 }

SonusSystemCpuUtilCurrentStatisticsEntry ::=
    SEQUENCE {
        sonusSystemCpuUtilCurrentStatisticsCeName         String,
        sonusSystemCpuUtilCurrentStatisticsCpu      Gauge,
        sonusSystemCpuUtilCurrentStatisticsAverage          Gauge,
        sonusSystemCpuUtilCurrentStatisticsHigh       Gauge,
        sonusSystemCpuUtilCurrentStatisticsLow      Gauge
    }

sonusSystemCpuUtilCurrentStatisticsCeName OBJECT-TYPE
    SYNTAX          String (SIZE(0..255))
    ACCESS          not-accessible
    STATUS          mandatory
    DESCRIPTION     
            "
             This object indicates the configured CE name.
             "
    ::= { sonusSystemCpuUtilCurrentStatisticsEntry 1 }

sonusSystemCpuUtilCurrentStatisticsCpu OBJECT-TYPE
    SYNTAX          Gauge
    ACCESS          not-accessible
    STATUS          mandatory
    DESCRIPTION     
            "
             The cpu number.
             "
    ::= { sonusSystemCpuUtilCurrentStatisticsEntry 2 }

sonusSystemCpuUtilCurrentStatisticsAverage OBJECT-TYPE
    SYNTAX          Gauge
    ACCESS          read-only
    STATUS          mandatory
    DESCRIPTION     
            "
             The average cpu % utilization for this interval.
             "
    ::= { sonusSystemCpuUtilCurrentStatisticsEntry 3 }

sonusSystemCpuUtilCurrentStatisticsHigh OBJECT-TYPE
    SYNTAX          Gauge
    ACCESS          read-only
    STATUS          mandatory
    DESCRIPTION     
            "
             The high cpu % utilization for this interval.
             "
    ::= { sonusSystemCpuUtilCurrentStatisticsEntry 4 }

sonusSystemCpuUtilCurrentStatisticsLow OBJECT-TYPE
    SYNTAX          Gauge
    ACCESS          read-only
    STATUS          mandatory
    DESCRIPTION     
            "
             The low cpu % utilization for this interval.
             "
    ::= { sonusSystemCpuUtilCurrentStatisticsEntry 5 }

sonusSystemCpuUtilIntervalStatisticsTable OBJECT-TYPE
    SYNTAX          SEQUENCE OF SonusSystemCpuUtilIntervalStatisticsEntry
    ACCESS          not-accessible
    STATUS          mandatory
    DESCRIPTION     
            "
             The CPU utilization for the
             'n' number of intervals.
             "
    ::= { sonusSystem 18 }

sonusSystemCpuUtilIntervalStatisticsEntry OBJECT-TYPE
    SYNTAX          SonusSystemCpuUtilIntervalStatisticsEntry
    ACCESS          not-accessible
    STATUS          mandatory
    DESCRIPTION     
            ""
    INDEX           { sonusSystemCpuUtilIntervalStatisticsNumber, 
                      sonusSystemCpuUtilIntervalStatisticsCeName, 
                      sonusSystemCpuUtilIntervalStatisticsCpu }
    ::= { sonusSystemCpuUtilIntervalStatisticsTable 1 }

SonusSystemCpuUtilIntervalStatisticsEntry ::=
    SEQUENCE {
        sonusSystemCpuUtilIntervalStatisticsNumber          Gauge,
        sonusSystemCpuUtilIntervalStatisticsCeName          String,
        sonusSystemCpuUtilIntervalStatisticsCpu       Gauge,
        sonusSystemCpuUtilIntervalStatisticsIntervalValid                 INTEGER,
        sonusSystemCpuUtilIntervalStatisticsTime        Gauge,
        sonusSystemCpuUtilIntervalStatisticsAverage           Gauge,
        sonusSystemCpuUtilIntervalStatisticsHigh        Gauge,
        sonusSystemCpuUtilIntervalStatisticsLow       Gauge
    }

sonusSystemCpuUtilIntervalStatisticsNumber OBJECT-TYPE
    SYNTAX          Gauge
    ACCESS          not-accessible
    STATUS          mandatory
    DESCRIPTION     
            "
             A sequence number which identifies the
             interval for which the set of statistics is required.
             The interval N identifies the recently completed interval,
             Interval N is identifed by the last sequence value and N-( number of intervals)
             is the earlest completed interval.
             "
    ::= { sonusSystemCpuUtilIntervalStatisticsEntry 1 }

sonusSystemCpuUtilIntervalStatisticsCeName OBJECT-TYPE
    SYNTAX          String (SIZE(0..255))
    ACCESS          not-accessible
    STATUS          mandatory
    DESCRIPTION     
            "
             This object indicates the configured CE name.
             "
    ::= { sonusSystemCpuUtilIntervalStatisticsEntry 2 }

sonusSystemCpuUtilIntervalStatisticsCpu OBJECT-TYPE
    SYNTAX          Gauge
    ACCESS          not-accessible
    STATUS          mandatory
    DESCRIPTION     
            "
             The cpu number.
             "
    ::= { sonusSystemCpuUtilIntervalStatisticsEntry 3 }

sonusSystemCpuUtilIntervalStatisticsIntervalValid OBJECT-TYPE
    SYNTAX          INTEGER { true(1), false(2) }
    ACCESS          read-only
    STATUS          mandatory
    DESCRIPTION     
            "
             The member indicating the validity of the interval.
             "
    ::= { sonusSystemCpuUtilIntervalStatisticsEntry 4 }

sonusSystemCpuUtilIntervalStatisticsTime OBJECT-TYPE
    SYNTAX          Gauge
    ACCESS          read-only
    STATUS          mandatory
    DESCRIPTION     
            "
             The system up time when the interval statisitic is collected.
             "
    ::= { sonusSystemCpuUtilIntervalStatisticsEntry 5 }

sonusSystemCpuUtilIntervalStatisticsAverage OBJECT-TYPE
    SYNTAX          Gauge
    ACCESS          read-only
    STATUS          mandatory
    DESCRIPTION     
            "
             The average cpu % utilization for this interval.
             "
    ::= { sonusSystemCpuUtilIntervalStatisticsEntry 6 }

sonusSystemCpuUtilIntervalStatisticsHigh OBJECT-TYPE
    SYNTAX          Gauge
    ACCESS          read-only
    STATUS          mandatory
    DESCRIPTION     
            "
             The high cpu % utilization for this interval.
             "
    ::= { sonusSystemCpuUtilIntervalStatisticsEntry 7 }

sonusSystemCpuUtilIntervalStatisticsLow OBJECT-TYPE
    SYNTAX          Gauge
    ACCESS          read-only
    STATUS          mandatory
    DESCRIPTION     
            "
             The low cpu % utilization for this interval.
             "
    ::= { sonusSystemCpuUtilIntervalStatisticsEntry 8 }

sonusSystemMemoryUtilCurrentStatisticsTable OBJECT-TYPE
    SYNTAX          SEQUENCE OF SonusSystemMemoryUtilCurrentStatisticsEntry
    ACCESS          not-accessible
    STATUS          mandatory
    DESCRIPTION     
            "
             The memory utilization for the current
             interval period.
             "
    ::= { sonusSystem 19 }

sonusSystemMemoryUtilCurrentStatisticsEntry OBJECT-TYPE
    SYNTAX          SonusSystemMemoryUtilCurrentStatisticsEntry
    ACCESS          not-accessible
    STATUS          mandatory
    DESCRIPTION     
            ""
    INDEX           { sonusSystemMemoryUtilCurrentStatisticsCeName }
    ::= { sonusSystemMemoryUtilCurrentStatisticsTable 1 }

SonusSystemMemoryUtilCurrentStatisticsEntry ::=
    SEQUENCE {
        sonusSystemMemoryUtilCurrentStatisticsCeName            String,
        sonusSystemMemoryUtilCurrentStatisticsAverage             Gauge,
        sonusSystemMemoryUtilCurrentStatisticsHigh          Gauge,
        sonusSystemMemoryUtilCurrentStatisticsLow         Gauge,
        sonusSystemMemoryUtilCurrentStatisticsAverageSwap                 Gauge,
        sonusSystemMemoryUtilCurrentStatisticsHighSwap              Gauge,
        sonusSystemMemoryUtilCurrentStatisticsLowSwap             Gauge
    }

sonusSystemMemoryUtilCurrentStatisticsCeName OBJECT-TYPE
    SYNTAX          String (SIZE(0..255))
    ACCESS          not-accessible
    STATUS          mandatory
    DESCRIPTION     
            "
             This object indicates the configured CE name.
             "
    ::= { sonusSystemMemoryUtilCurrentStatisticsEntry 1 }

sonusSystemMemoryUtilCurrentStatisticsAverage OBJECT-TYPE
    SYNTAX          Gauge
    ACCESS          read-only
    STATUS          mandatory
    DESCRIPTION     
            "
             The average memory % utilization for this interval.
             "
    ::= { sonusSystemMemoryUtilCurrentStatisticsEntry 2 }

sonusSystemMemoryUtilCurrentStatisticsHigh OBJECT-TYPE
    SYNTAX          Gauge
    ACCESS          read-only
    STATUS          mandatory
    DESCRIPTION     
            "
             The high memory % utilization for this interval.
             "
    ::= { sonusSystemMemoryUtilCurrentStatisticsEntry 3 }

sonusSystemMemoryUtilCurrentStatisticsLow OBJECT-TYPE
    SYNTAX          Gauge
    ACCESS          read-only
    STATUS          mandatory
    DESCRIPTION     
            "
             The low memory % utilization for this interval.
             "
    ::= { sonusSystemMemoryUtilCurrentStatisticsEntry 4 }

sonusSystemMemoryUtilCurrentStatisticsAverageSwap OBJECT-TYPE
    SYNTAX          Gauge
    ACCESS          read-only
    STATUS          mandatory
    DESCRIPTION     
            "
             The average swap % memory utilization for this interval.
             "
    ::= { sonusSystemMemoryUtilCurrentStatisticsEntry 5 }

sonusSystemMemoryUtilCurrentStatisticsHighSwap OBJECT-TYPE
    SYNTAX          Gauge
    ACCESS          read-only
    STATUS          mandatory
    DESCRIPTION     
            "
             The high swap % memory utilization for this interval.
             "
    ::= { sonusSystemMemoryUtilCurrentStatisticsEntry 6 }

sonusSystemMemoryUtilCurrentStatisticsLowSwap OBJECT-TYPE
    SYNTAX          Gauge
    ACCESS          read-only
    STATUS          mandatory
    DESCRIPTION     
            "
             The low swap memory % utilization for this interval.
             "
    ::= { sonusSystemMemoryUtilCurrentStatisticsEntry 7 }

sonusSystemMemoryUtilIntervalStatisticsTable OBJECT-TYPE
    SYNTAX          SEQUENCE OF SonusSystemMemoryUtilIntervalStatisticsEntry
    ACCESS          not-accessible
    STATUS          mandatory
    DESCRIPTION     
            "
             The memory utilization for the
             'n' number of intervals.
             "
    ::= { sonusSystem 20 }

sonusSystemMemoryUtilIntervalStatisticsEntry OBJECT-TYPE
    SYNTAX          SonusSystemMemoryUtilIntervalStatisticsEntry
    ACCESS          not-accessible
    STATUS          mandatory
    DESCRIPTION     
            ""
    INDEX           { sonusSystemMemoryUtilIntervalStatisticsNumber, 
                      sonusSystemMemoryUtilIntervalStatisticsCeName }
    ::= { sonusSystemMemoryUtilIntervalStatisticsTable 1 }

SonusSystemMemoryUtilIntervalStatisticsEntry ::=
    SEQUENCE {
        sonusSystemMemoryUtilIntervalStatisticsNumber             Gauge,
        sonusSystemMemoryUtilIntervalStatisticsCeName             String,
        sonusSystemMemoryUtilIntervalStatisticsIntervalValid                    INTEGER,
        sonusSystemMemoryUtilIntervalStatisticsTime           Gauge,
        sonusSystemMemoryUtilIntervalStatisticsAverage              Gauge,
        sonusSystemMemoryUtilIntervalStatisticsHigh           Gauge,
        sonusSystemMemoryUtilIntervalStatisticsLow          Gauge,
        sonusSystemMemoryUtilIntervalStatisticsAverageSwap                  Gauge,
        sonusSystemMemoryUtilIntervalStatisticsHighSwap               Gauge,
        sonusSystemMemoryUtilIntervalStatisticsLowSwap              Gauge
    }

sonusSystemMemoryUtilIntervalStatisticsNumber OBJECT-TYPE
    SYNTAX          Gauge
    ACCESS          not-accessible
    STATUS          mandatory
    DESCRIPTION     
            "
             A sequence number which identifies the
             interval for which the set of statistics is required.
             The interval N identifies the recently completed interval,
             Interval N is identifed by the last sequence value and N-( number of intervals)
             is the earlest completed interval.
             "
    ::= { sonusSystemMemoryUtilIntervalStatisticsEntry 1 }

sonusSystemMemoryUtilIntervalStatisticsCeName OBJECT-TYPE
    SYNTAX          String (SIZE(0..255))
    ACCESS          not-accessible
    STATUS          mandatory
    DESCRIPTION     
            "
             This object indicates the configured CE name.
             "
    ::= { sonusSystemMemoryUtilIntervalStatisticsEntry 2 }

sonusSystemMemoryUtilIntervalStatisticsIntervalValid OBJECT-TYPE
    SYNTAX          INTEGER { true(1), false(2) }
    ACCESS          read-only
    STATUS          mandatory
    DESCRIPTION     
            "
             The member indicating the validity of the interval.
             "
    ::= { sonusSystemMemoryUtilIntervalStatisticsEntry 3 }

sonusSystemMemoryUtilIntervalStatisticsTime OBJECT-TYPE
    SYNTAX          Gauge
    ACCESS          read-only
    STATUS          mandatory
    DESCRIPTION     
            "
             The system up time when the interval statisitic is collected.
             "
    ::= { sonusSystemMemoryUtilIntervalStatisticsEntry 4 }

sonusSystemMemoryUtilIntervalStatisticsAverage OBJECT-TYPE
    SYNTAX          Gauge
    ACCESS          read-only
    STATUS          mandatory
    DESCRIPTION     
            "
             The average memory % utilization for this interval.
             "
    ::= { sonusSystemMemoryUtilIntervalStatisticsEntry 5 }

sonusSystemMemoryUtilIntervalStatisticsHigh OBJECT-TYPE
    SYNTAX          Gauge
    ACCESS          read-only
    STATUS          mandatory
    DESCRIPTION     
            "
             The high memory % utilization for this interval.
             "
    ::= { sonusSystemMemoryUtilIntervalStatisticsEntry 6 }

sonusSystemMemoryUtilIntervalStatisticsLow OBJECT-TYPE
    SYNTAX          Gauge
    ACCESS          read-only
    STATUS          mandatory
    DESCRIPTION     
            "
             The low memory % utilization for this interval.
             "
    ::= { sonusSystemMemoryUtilIntervalStatisticsEntry 7 }

sonusSystemMemoryUtilIntervalStatisticsAverageSwap OBJECT-TYPE
    SYNTAX          Gauge
    ACCESS          read-only
    STATUS          mandatory
    DESCRIPTION     
            "
             The average swap memory % utilization for this interval.
             "
    ::= { sonusSystemMemoryUtilIntervalStatisticsEntry 8 }

sonusSystemMemoryUtilIntervalStatisticsHighSwap OBJECT-TYPE
    SYNTAX          Gauge
    ACCESS          read-only
    STATUS          mandatory
    DESCRIPTION     
            "
             The high swap memory % utilization for this interval.
             "
    ::= { sonusSystemMemoryUtilIntervalStatisticsEntry 9 }

sonusSystemMemoryUtilIntervalStatisticsLowSwap OBJECT-TYPE
    SYNTAX          Gauge
    ACCESS          read-only
    STATUS          mandatory
    DESCRIPTION     
            "
             The low swap memory % utilization for this interval.
             "
    ::= { sonusSystemMemoryUtilIntervalStatisticsEntry 10 }

sonusSystemCoredumpListTable OBJECT-TYPE
    SYNTAX          SEQUENCE OF SonusSystemCoredumpListEntry
    ACCESS          not-accessible
    STATUS          mandatory
    DESCRIPTION     
            "
             List of coredumps on the server(s).
             "
    ::= { sonusSystem 21 }

sonusSystemCoredumpListEntry OBJECT-TYPE
    SYNTAX          SonusSystemCoredumpListEntry
    ACCESS          not-accessible
    STATUS          mandatory
    DESCRIPTION     
            ""
    INDEX           { sonusSystemCoredumpListServerName, 
                      sonusSystemCoredumpListIndex }
    ::= { sonusSystemCoredumpListTable 1 }

SonusSystemCoredumpListEntry ::=
    SEQUENCE {
        sonusSystemCoredumpListServerName String,
        sonusSystemCoredumpListIndex    Gauge,
        sonusSystemCoredumpListCoredumpFileName       String,
        sonusSystemCoredumpListSize     String,
        sonusSystemCoredumpListDateAndTime  String,
        sonusSystemCoredumpListNewSinceLastStart        TruthValue
    }

sonusSystemCoredumpListServerName OBJECT-TYPE
    SYNTAX          String (SIZE(0..255))
    ACCESS          not-accessible
    STATUS          mandatory
    DESCRIPTION     
            "
             Identifies the server.
             "
    ::= { sonusSystemCoredumpListEntry 1 }

sonusSystemCoredumpListIndex OBJECT-TYPE
    SYNTAX          Gauge
    ACCESS          not-accessible
    STATUS          mandatory
    DESCRIPTION     
            "
             Index of the coredump file.
             "
    ::= { sonusSystemCoredumpListEntry 2 }

sonusSystemCoredumpListCoredumpFileName OBJECT-TYPE
    SYNTAX          String (SIZE(0..255))
    ACCESS          read-only
    STATUS          mandatory
    DESCRIPTION     
            "
             The file name of the coredump.
             "
    ::= { sonusSystemCoredumpListEntry 3 }

sonusSystemCoredumpListSize OBJECT-TYPE
    SYNTAX          String (SIZE(0..23))
    ACCESS          read-only
    STATUS          mandatory
    DESCRIPTION     
            "
             Indicates size of the coredump(KBytes).
             "
    ::= { sonusSystemCoredumpListEntry 4 }

sonusSystemCoredumpListDateAndTime OBJECT-TYPE
    SYNTAX          String (SIZE(0..255))
    ACCESS          read-only
    STATUS          mandatory
    DESCRIPTION     
            "
             Indicates when the coredump occurred.
             "
    ::= { sonusSystemCoredumpListEntry 5 }

sonusSystemCoredumpListNewSinceLastStart OBJECT-TYPE
    SYNTAX          TruthValue
    ACCESS          read-only
    STATUS          mandatory
    DESCRIPTION     
            "
             Indicates if the it is new since last restart of the application.
             "
    ::= { sonusSystemCoredumpListEntry 6 }

sonusSystemCoredumpSummaryTable OBJECT-TYPE
    SYNTAX          SEQUENCE OF SonusSystemCoredumpSummaryEntry
    ACCESS          not-accessible
    STATUS          mandatory
    DESCRIPTION     
            "
             Summary of coredump files on server(s).
             "
    ::= { sonusSystem 22 }

sonusSystemCoredumpSummaryEntry OBJECT-TYPE
    SYNTAX          SonusSystemCoredumpSummaryEntry
    ACCESS          not-accessible
    STATUS          mandatory
    DESCRIPTION     
            ""
    INDEX           { sonusSystemCoredumpSummaryServerName }
    ::= { sonusSystemCoredumpSummaryTable 1 }

SonusSystemCoredumpSummaryEntry ::=
    SEQUENCE {
        sonusSystemCoredumpSummaryServerName    String,
        sonusSystemCoredumpSummaryCoredumpAndTraceCount               Gauge,
        sonusSystemCoredumpSummaryTotalSize   String
    }

sonusSystemCoredumpSummaryServerName OBJECT-TYPE
    SYNTAX          String (SIZE(0..255))
    ACCESS          not-accessible
    STATUS          mandatory
    DESCRIPTION     
            "
             Identifies the server.
             "
    ::= { sonusSystemCoredumpSummaryEntry 1 }

sonusSystemCoredumpSummaryCoredumpAndTraceCount OBJECT-TYPE
    SYNTAX          Gauge
    ACCESS          read-only
    STATUS          mandatory
    DESCRIPTION     
            "
             Number of coredumps and trace files.
             "
    ::= { sonusSystemCoredumpSummaryEntry 2 }

sonusSystemCoredumpSummaryTotalSize OBJECT-TYPE
    SYNTAX          String (SIZE(0..23))
    ACCESS          read-only
    STATUS          mandatory
    DESCRIPTION     
            "
             Indicates the total size of the coredumps(KBytes).
             "
    ::= { sonusSystemCoredumpSummaryEntry 3 }

sonusSystemSavedConfigListTable OBJECT-TYPE
    SYNTAX          SEQUENCE OF SonusSystemSavedConfigListEntry
    ACCESS          not-accessible
    STATUS          mandatory
    DESCRIPTION     
            "
             List of configurations saved on the system.
             "
    ::= { sonusSystem 23 }

sonusSystemSavedConfigListEntry OBJECT-TYPE
    SYNTAX          SonusSystemSavedConfigListEntry
    ACCESS          not-accessible
    STATUS          mandatory
    DESCRIPTION     
            ""
    INDEX           { sonusSystemSavedConfigListIndex }
    ::= { sonusSystemSavedConfigListTable 1 }

SonusSystemSavedConfigListEntry ::=
    SEQUENCE {
        sonusSystemSavedConfigListIndex Gauge,
        sonusSystemSavedConfigListFileName  String,
        sonusSystemSavedConfigListSize  String,
        sonusSystemSavedConfigListVersion String
    }

sonusSystemSavedConfigListIndex OBJECT-TYPE
    SYNTAX          Gauge
    ACCESS          not-accessible
    STATUS          mandatory
    DESCRIPTION     
            "
             Index of the saved configuration file.
             "
    ::= { sonusSystemSavedConfigListEntry 1 }

sonusSystemSavedConfigListFileName OBJECT-TYPE
    SYNTAX          String (SIZE(0..255))
    ACCESS          read-only
    STATUS          mandatory
    DESCRIPTION     
            "
             The file name of the saved configuration.
             "
    ::= { sonusSystemSavedConfigListEntry 2 }

sonusSystemSavedConfigListSize OBJECT-TYPE
    SYNTAX          String (SIZE(0..23))
    ACCESS          read-only
    STATUS          mandatory
    DESCRIPTION     
            "
             Indicates size of the saved configuration file(KBytes).
             "
    ::= { sonusSystemSavedConfigListEntry 3 }

sonusSystemSavedConfigListVersion OBJECT-TYPE
    SYNTAX          String (SIZE(0..255))
    ACCESS          read-only
    STATUS          mandatory
    DESCRIPTION     
            "
             The software version name of the saved configuration.
             "
    ::= { sonusSystemSavedConfigListEntry 4 }

sonusSystemLedStatusTable OBJECT-TYPE
    SYNTAX          SEQUENCE OF SonusSystemLedStatusEntry
    ACCESS          not-accessible
    STATUS          mandatory
    DESCRIPTION     
            "
             Displays status of various LEDs of the server.
             "
    ::= { sonusSystem 24 }

sonusSystemLedStatusEntry OBJECT-TYPE
    SYNTAX          SonusSystemLedStatusEntry
    ACCESS          not-accessible
    STATUS          mandatory
    DESCRIPTION     
            ""
    INDEX           { sonusSystemLedStatusServerName, 
                      sonusSystemLedStatusLedType }
    ::= { sonusSystemLedStatusTable 1 }

SonusSystemLedStatusEntry ::=
    SEQUENCE {
        sonusSystemLedStatusServerName  String,
        sonusSystemLedStatusLedType     String,
        sonusSystemLedStatusLedState    String,
        sonusSystemLedStatusLedColor    String
    }

sonusSystemLedStatusServerName OBJECT-TYPE
    SYNTAX          String (SIZE(0..255))
    ACCESS          not-accessible
    STATUS          mandatory
    DESCRIPTION     
            "
             Identifies the server.
             "
    ::= { sonusSystemLedStatusEntry 1 }

sonusSystemLedStatusLedType OBJECT-TYPE
    SYNTAX          String (SIZE(0..23))
    ACCESS          not-accessible
    STATUS          mandatory
    DESCRIPTION     
            "
             Indicates the LED type.
             "
    ::= { sonusSystemLedStatusEntry 2 }

sonusSystemLedStatusLedState OBJECT-TYPE
    SYNTAX          String (SIZE(0..23))
    ACCESS          read-only
    STATUS          mandatory
    DESCRIPTION     
            "
             Indicates the LED state.
             "
    ::= { sonusSystemLedStatusEntry 3 }

sonusSystemLedStatusLedColor OBJECT-TYPE
    SYNTAX          String (SIZE(0..23))
    ACCESS          read-only
    STATUS          mandatory
    DESCRIPTION     
            "
             Indicates the LED color.
             "
    ::= { sonusSystemLedStatusEntry 4 }

sonusSystemFileStatisticsStatus OBJECT IDENTIFIER
    ::= { sonusSystem 25 }

-- sonusSystemFileStatisticsStatusID OBJECT-TYPE
--     SYNTAX          Counter64
--     ACCESS          read-only
--     STATUS          mandatory
--     DESCRIPTION     
--             "
--              Identifies the server.
--              "
--     ::= { sonusSystemFileStatisticsStatus 1 }

sonusSystemDaughterBoard2StatusTable OBJECT-TYPE
    SYNTAX          SEQUENCE OF SonusSystemDaughterBoard2StatusEntry
    ACCESS          not-accessible
    STATUS          obsolete
    DESCRIPTION     
            "
             Indicates the daughter board status on the server.
             "
    ::= { sonusSystem 28 }

sonusSystemDaughterBoard2StatusEntry OBJECT-TYPE
    SYNTAX          SonusSystemDaughterBoard2StatusEntry
    ACCESS          not-accessible
    STATUS          obsolete
    DESCRIPTION     
            ""
    INDEX           { sonusSystemDaughterBoard2StatusServerName, 
                      sonusSystemDaughterBoard2StatusSlot }
    ::= { sonusSystemDaughterBoard2StatusTable 1 }

SonusSystemDaughterBoard2StatusEntry ::=
    SEQUENCE {
        sonusSystemDaughterBoard2StatusServerName         String,
        sonusSystemDaughterBoard2StatusDaughterBoardId              String,
        sonusSystemDaughterBoard2StatusPresent      TruthValue,
        sonusSystemDaughterBoard2StatusProductName          String,
        sonusSystemDaughterBoard2StatusSerialNum        SonusNodeSrvrStatSerialNumType,
        sonusSystemDaughterBoard2StatusPartNum      SonusNodeSrvrStatPartNumType,
        sonusSystemDaughterBoard2StatusSlot   SonusDspSlotIndex,
        sonusSystemDaughterBoard2StatusOperationalStatus                DaughterBoardOperationalStatus,
        sonusSystemDaughterBoard2StatusLogicalId        SonusDspSlotIndex,
        sonusSystemDaughterBoard2StatusImageLoadFailureCount                    Gauge,
        sonusSystemDaughterBoard2StatusFpgaVersion          String
    }

sonusSystemDaughterBoard2StatusServerName OBJECT-TYPE
    SYNTAX          String (SIZE(0..255))
    ACCESS          not-accessible
    STATUS          obsolete
    DESCRIPTION     
            "
             Identifies the server.
             "
    ::= { sonusSystemDaughterBoard2StatusEntry 1 }

sonusSystemDaughterBoard2StatusDaughterBoardId OBJECT-TYPE
    SYNTAX          String (SIZE(0..23))
    ACCESS          read-only
    STATUS          obsolete
    DESCRIPTION     
            "
             The name of the daughter board.
             "
    ::= { sonusSystemDaughterBoard2StatusEntry 2 }

sonusSystemDaughterBoard2StatusPresent OBJECT-TYPE
    SYNTAX          TruthValue
    ACCESS          read-only
    STATUS          obsolete
    DESCRIPTION     
            "
             Indicates if the module is present or not.
             "
    ::= { sonusSystemDaughterBoard2StatusEntry 3 }

sonusSystemDaughterBoard2StatusProductName OBJECT-TYPE
    SYNTAX          String (SIZE(0..255))
    ACCESS          read-only
    STATUS          obsolete
    DESCRIPTION     
            "
             Identifies the name (as given by manufacturer) of the module.
             "
    ::= { sonusSystemDaughterBoard2StatusEntry 4 }

sonusSystemDaughterBoard2StatusSerialNum OBJECT-TYPE
    SYNTAX          SonusNodeSrvrStatSerialNumType
    ACCESS          read-only
    STATUS          obsolete
    DESCRIPTION     
            "
             Identifies the serial number of the daughter board module.  This is the
             serial number assigned to the server module at manufacture.
             "
    ::= { sonusSystemDaughterBoard2StatusEntry 5 }

sonusSystemDaughterBoard2StatusPartNum OBJECT-TYPE
    SYNTAX          SonusNodeSrvrStatPartNumType
    ACCESS          read-only
    STATUS          obsolete
    DESCRIPTION     
            "
             Identifies the part number of the module.  This is the
             part number assigned to the module at manufacture.
             "
    ::= { sonusSystemDaughterBoard2StatusEntry 6 }

sonusSystemDaughterBoard2StatusSlot OBJECT-TYPE
    SYNTAX          SonusDspSlotIndex
    ACCESS          not-accessible
    STATUS          obsolete
    DESCRIPTION     
            "
             Identifies the slot associated with the DSP board.
             "
    ::= { sonusSystemDaughterBoard2StatusEntry 7 }

sonusSystemDaughterBoard2StatusOperationalStatus OBJECT-TYPE
    SYNTAX          DaughterBoardOperationalStatus
    ACCESS          read-only
    STATUS          obsolete
    DESCRIPTION     
            "
             Identifies the operational state of the board.
             "
    ::= { sonusSystemDaughterBoard2StatusEntry 8 }

sonusSystemDaughterBoard2StatusLogicalId OBJECT-TYPE
    SYNTAX          SonusDspSlotIndex
    ACCESS          read-only
    STATUS          obsolete
    DESCRIPTION     
            "
             Identifies the logical id of the slot.
             "
    ::= { sonusSystemDaughterBoard2StatusEntry 9 }

sonusSystemDaughterBoard2StatusImageLoadFailureCount OBJECT-TYPE
    SYNTAX          Gauge
    ACCESS          read-only
    STATUS          obsolete
    DESCRIPTION     
            "
             Indicates daughter board image load failure count since last successful attempt.
             "
    ::= { sonusSystemDaughterBoard2StatusEntry 10 }

sonusSystemDaughterBoard2StatusFpgaVersion OBJECT-TYPE
    SYNTAX          String (SIZE(0..255))
    ACCESS          read-only
    STATUS          obsolete
    DESCRIPTION     
            "
             FPGA version of slot.
             "
    ::= { sonusSystemDaughterBoard2StatusEntry 11 }

sonusSystemDaughterBoard3StatusTable OBJECT-TYPE
    SYNTAX          SEQUENCE OF SonusSystemDaughterBoard3StatusEntry
    ACCESS          not-accessible
    STATUS          mandatory
    DESCRIPTION     
            "
             Indicates the daughter board status on the server.
             "
    ::= { sonusSystem 29 }

sonusSystemDaughterBoard3StatusEntry OBJECT-TYPE
    SYNTAX          SonusSystemDaughterBoard3StatusEntry
    ACCESS          not-accessible
    STATUS          mandatory
    DESCRIPTION     
            ""
    INDEX           { sonusSystemDaughterBoard3StatusServerName, 
                      sonusSystemDaughterBoard3StatusSlot }
    ::= { sonusSystemDaughterBoard3StatusTable 1 }

SonusSystemDaughterBoard3StatusEntry ::=
    SEQUENCE {
        sonusSystemDaughterBoard3StatusServerName         String,
        sonusSystemDaughterBoard3StatusDaughterBoardId              String,
        sonusSystemDaughterBoard3StatusPresent      TruthValue,
        sonusSystemDaughterBoard3StatusProductName          String,
        sonusSystemDaughterBoard3StatusSerialNum        SonusNodeSrvrStatSerialNumType,
        sonusSystemDaughterBoard3StatusPartNum      SonusNodeSrvrStatPartNumType,
        sonusSystemDaughterBoard3StatusSlot   SonusDspSlotIndex,
        sonusSystemDaughterBoard3StatusOperationalStatus                DaughterBoardOperationalStatus,
        sonusSystemDaughterBoard3StatusLogicalId        SonusDspSlotIndex,
        sonusSystemDaughterBoard3StatusImageLoadFailureCount                    Gauge,
        sonusSystemDaughterBoard3StatusFpgaVersion          String
    }

sonusSystemDaughterBoard3StatusServerName OBJECT-TYPE
    SYNTAX          String (SIZE(0..255))
    ACCESS          not-accessible
    STATUS          mandatory
    DESCRIPTION     
            "
             Identifies the server.
             "
    ::= { sonusSystemDaughterBoard3StatusEntry 1 }

sonusSystemDaughterBoard3StatusDaughterBoardId OBJECT-TYPE
    SYNTAX          String (SIZE(0..23))
    ACCESS          read-only
    STATUS          mandatory
    DESCRIPTION     
            "
             The name of the daughter board.
             "
    ::= { sonusSystemDaughterBoard3StatusEntry 2 }

sonusSystemDaughterBoard3StatusPresent OBJECT-TYPE
    SYNTAX          TruthValue
    ACCESS          read-only
    STATUS          mandatory
    DESCRIPTION     
            "
             Indicates if the module is present or not.
             "
    ::= { sonusSystemDaughterBoard3StatusEntry 3 }

sonusSystemDaughterBoard3StatusProductName OBJECT-TYPE
    SYNTAX          String (SIZE(0..255))
    ACCESS          read-only
    STATUS          mandatory
    DESCRIPTION     
            "
             Identifies the name (as given by manufacturer) of the module.
             "
    ::= { sonusSystemDaughterBoard3StatusEntry 4 }

sonusSystemDaughterBoard3StatusSerialNum OBJECT-TYPE
    SYNTAX          SonusNodeSrvrStatSerialNumType
    ACCESS          read-only
    STATUS          mandatory
    DESCRIPTION     
            "
             Identifies the serial number of the daughter board module.  This is the
             serial number assigned to the server module at manufacture.
             "
    ::= { sonusSystemDaughterBoard3StatusEntry 5 }

sonusSystemDaughterBoard3StatusPartNum OBJECT-TYPE
    SYNTAX          SonusNodeSrvrStatPartNumType
    ACCESS          read-only
    STATUS          mandatory
    DESCRIPTION     
            "
             Identifies the part number of the module.  This is the
             part number assigned to the module at manufacture.
             "
    ::= { sonusSystemDaughterBoard3StatusEntry 6 }

sonusSystemDaughterBoard3StatusSlot OBJECT-TYPE
    SYNTAX          SonusDspSlotIndex
    ACCESS          not-accessible
    STATUS          mandatory
    DESCRIPTION     
            "
             Identifies the slot associated with the DSP board.
             "
    ::= { sonusSystemDaughterBoard3StatusEntry 7 }

sonusSystemDaughterBoard3StatusOperationalStatus OBJECT-TYPE
    SYNTAX          DaughterBoardOperationalStatus
    ACCESS          read-only
    STATUS          mandatory
    DESCRIPTION     
            "
             Identifies the operational state of the board.
             "
    ::= { sonusSystemDaughterBoard3StatusEntry 8 }

sonusSystemDaughterBoard3StatusLogicalId OBJECT-TYPE
    SYNTAX          SonusDspSlotIndex
    ACCESS          read-only
    STATUS          mandatory
    DESCRIPTION     
            "
             Identifies the logical id of the slot.
             "
    ::= { sonusSystemDaughterBoard3StatusEntry 9 }

sonusSystemDaughterBoard3StatusImageLoadFailureCount OBJECT-TYPE
    SYNTAX          Gauge
    ACCESS          read-only
    STATUS          mandatory
    DESCRIPTION     
            "
             Indicates daughter board image load failure count since last successful attempt.
             "
    ::= { sonusSystemDaughterBoard3StatusEntry 10 }

sonusSystemDaughterBoard3StatusFpgaVersion OBJECT-TYPE
    SYNTAX          String (SIZE(0..255))
    ACCESS          read-only
    STATUS          mandatory
    DESCRIPTION     
            "
             FPGA version of slot.
             "
    ::= { sonusSystemDaughterBoard3StatusEntry 11 }

sonusSystemMacAddressStatusTable OBJECT-TYPE
    SYNTAX          SEQUENCE OF SonusSystemMacAddressStatusEntry
    ACCESS          not-accessible
    STATUS          obsolete
    DESCRIPTION     
            "
             Displays status of MAC address of servers. This table is obsolete.
             "
    ::= { sonusSystem 30 }

sonusSystemMacAddressStatusEntry OBJECT-TYPE
    SYNTAX          SonusSystemMacAddressStatusEntry
    ACCESS          not-accessible
    STATUS          obsolete
    DESCRIPTION     
            ""
    INDEX           { sonusSystemMacAddressStatusServerName, 
                      sonusSystemMacAddressStatusMacAddress }
    ::= { sonusSystemMacAddressStatusTable 1 }

SonusSystemMacAddressStatusEntry ::=
    SEQUENCE {
        sonusSystemMacAddressStatusServerName     String,
        sonusSystemMacAddressStatusMacAddress     String,
        sonusSystemMacAddressStatusStatus MacAddressStatusType,
        sonusSystemMacAddressStatusUsedBy String,
        sonusSystemMacAddressStatusUsedByPort     String
    }

sonusSystemMacAddressStatusServerName OBJECT-TYPE
    SYNTAX          String (SIZE(0..255))
    ACCESS          not-accessible
    STATUS          obsolete
    DESCRIPTION     
            "
             Name of server.
             "
    ::= { sonusSystemMacAddressStatusEntry 1 }

sonusSystemMacAddressStatusMacAddress OBJECT-TYPE
    SYNTAX          String (SIZE(0..255))
    ACCESS          not-accessible
    STATUS          obsolete
    DESCRIPTION     
            "
             Mac address.
             "
    ::= { sonusSystemMacAddressStatusEntry 2 }

sonusSystemMacAddressStatusStatus OBJECT-TYPE
    SYNTAX          MacAddressStatusType
    ACCESS          read-only
    STATUS          obsolete
    DESCRIPTION     
            "
             Status of MAC Address
             "
    ::= { sonusSystemMacAddressStatusEntry 3 }

sonusSystemMacAddressStatusUsedBy OBJECT-TYPE
    SYNTAX          String (SIZE(0..255))
    ACCESS          read-only
    STATUS          obsolete
    DESCRIPTION     
            "
             MAC Address usedBy Server
             "
    ::= { sonusSystemMacAddressStatusEntry 4 }

sonusSystemMacAddressStatusUsedByPort OBJECT-TYPE
    SYNTAX          String (SIZE(0..255))
    ACCESS          read-only
    STATUS          obsolete
    DESCRIPTION     
            "
             MAC Address usedByPort
             "
    ::= { sonusSystemMacAddressStatusEntry 5 }

sonusSystemFipsFSMStateTable OBJECT-TYPE
    SYNTAX          SEQUENCE OF SonusSystemFipsFSMStateEntry
    ACCESS          not-accessible
    STATUS          obsolete
    DESCRIPTION     
            "
             FIPS finite state machine state. This table is obsolete.
             "
    ::= { sonusSystem 31 }

sonusSystemFipsFSMStateEntry OBJECT-TYPE
    SYNTAX          SonusSystemFipsFSMStateEntry
    ACCESS          not-accessible
    STATUS          obsolete
    DESCRIPTION     
            ""
    INDEX           { sonusSystemFipsFSMStateIndx }
    ::= { sonusSystemFipsFSMStateTable 1 }

SonusSystemFipsFSMStateEntry ::=
    SEQUENCE {
        sonusSystemFipsFSMStateIndx     Gauge,
        sonusSystemFipsFSMStateState    String,
        sonusSystemFipsFSMStateTimeStamp String,
        sonusSystemFipsFSMStateIssuer   String,
        sonusSystemFipsFSMStateMessage  String
    }

sonusSystemFipsFSMStateIndx OBJECT-TYPE
    SYNTAX          Gauge
    ACCESS          not-accessible
    STATUS          obsolete
    DESCRIPTION     
            "
             FIPS FSM state.
             "
    ::= { sonusSystemFipsFSMStateEntry 1 }

sonusSystemFipsFSMStateState OBJECT-TYPE
    SYNTAX          String (SIZE(0..255))
    ACCESS          read-only
    STATUS          obsolete
    DESCRIPTION     
            "
             FIPS FSM state.
             "
    ::= { sonusSystemFipsFSMStateEntry 2 }

sonusSystemFipsFSMStateTimeStamp OBJECT-TYPE
    SYNTAX          String (SIZE(0..255))
    ACCESS          read-only
    STATUS          obsolete
    DESCRIPTION     
            "
             FIPS FSM time stamp.
             "
    ::= { sonusSystemFipsFSMStateEntry 3 }

sonusSystemFipsFSMStateIssuer OBJECT-TYPE
    SYNTAX          String (SIZE(0..255))
    ACCESS          read-only
    STATUS          obsolete
    DESCRIPTION     
            "
             FIPS FSM Issuer.
             "
    ::= { sonusSystemFipsFSMStateEntry 4 }

sonusSystemFipsFSMStateMessage OBJECT-TYPE
    SYNTAX          String (SIZE(0..255))
    ACCESS          read-only
    STATUS          obsolete
    DESCRIPTION     
            "
             FIPS FSM message.
             "
    ::= { sonusSystemFipsFSMStateEntry 5 }

sonusSystemDodModeStatusTable OBJECT-TYPE
    SYNTAX          SEQUENCE OF SonusSystemDodModeStatusEntry
    ACCESS          not-accessible
    STATUS          mandatory
    DESCRIPTION     
            "
             DoD mode status
             "
    ::= { sonusSystem 32 }

sonusSystemDodModeStatusEntry OBJECT-TYPE
    SYNTAX          SonusSystemDodModeStatusEntry
    ACCESS          not-accessible
    STATUS          mandatory
    DESCRIPTION     
            ""
    INDEX           { sonusSystemDodModeStatusIndx }
    ::= { sonusSystemDodModeStatusTable 1 }

SonusSystemDodModeStatusEntry ::=
    SEQUENCE {
        sonusSystemDodModeStatusIndx    Gauge,
        sonusSystemDodModeStatusStatus  String
    }

sonusSystemDodModeStatusIndx OBJECT-TYPE
    SYNTAX          Gauge
    ACCESS          not-accessible
    STATUS          mandatory
    DESCRIPTION     
            ""
    ::= { sonusSystemDodModeStatusEntry 1 }

sonusSystemDodModeStatusStatus OBJECT-TYPE
    SYNTAX          String (SIZE(0..255))
    ACCESS          read-only
    STATUS          mandatory
    DESCRIPTION     
            ""
    ::= { sonusSystemDodModeStatusEntry 2 }

sonusSystemFipsFSM2StateTable OBJECT-TYPE
    SYNTAX          SEQUENCE OF SonusSystemFipsFSM2StateEntry
    ACCESS          not-accessible
    STATUS          mandatory
    DESCRIPTION     
            "
             FIPS finite state machine state.
             "
    ::= { sonusSystem 33 }

sonusSystemFipsFSM2StateEntry OBJECT-TYPE
    SYNTAX          SonusSystemFipsFSM2StateEntry
    ACCESS          not-accessible
    STATUS          mandatory
    DESCRIPTION     
            ""
    INDEX           { sonusSystemFipsFSM2StateIndx }
    ::= { sonusSystemFipsFSM2StateTable 1 }

SonusSystemFipsFSM2StateEntry ::=
    SEQUENCE {
        sonusSystemFipsFSM2StateIndx    Gauge,
        sonusSystemFipsFSM2StateState   String,
        sonusSystemFipsFSM2StateTimeStamp String,
        sonusSystemFipsFSM2StateIssuer  String,
        sonusSystemFipsFSM2StateMessage String
    }

sonusSystemFipsFSM2StateIndx OBJECT-TYPE
    SYNTAX          Gauge
    ACCESS          not-accessible
    STATUS          mandatory
    DESCRIPTION     
            "
             FIPS FSM state.
             "
    ::= { sonusSystemFipsFSM2StateEntry 1 }

sonusSystemFipsFSM2StateState OBJECT-TYPE
    SYNTAX          String (SIZE(0..255))
    ACCESS          read-only
    STATUS          mandatory
    DESCRIPTION     
            "
             FIPS FSM state.
             "
    ::= { sonusSystemFipsFSM2StateEntry 2 }

sonusSystemFipsFSM2StateTimeStamp OBJECT-TYPE
    SYNTAX          String (SIZE(0..255))
    ACCESS          read-only
    STATUS          mandatory
    DESCRIPTION     
            "
             FIPS FSM time stamp.
             "
    ::= { sonusSystemFipsFSM2StateEntry 3 }

sonusSystemFipsFSM2StateIssuer OBJECT-TYPE
    SYNTAX          String (SIZE(0..255))
    ACCESS          read-only
    STATUS          mandatory
    DESCRIPTION     
            "
             FIPS FSM Issuer.
             "
    ::= { sonusSystemFipsFSM2StateEntry 4 }

sonusSystemFipsFSM2StateMessage OBJECT-TYPE
    SYNTAX          String (SIZE(0..255))
    ACCESS          read-only
    STATUS          mandatory
    DESCRIPTION     
            "
             FIPS FSM message.
             "
    ::= { sonusSystemFipsFSM2StateEntry 5 }

sonusSystemMacAddress2StatusTable OBJECT-TYPE
    SYNTAX          SEQUENCE OF SonusSystemMacAddress2StatusEntry
    ACCESS          not-accessible
    STATUS          mandatory
    DESCRIPTION     
            "
             Displays status of MAC address of servers
             "
    ::= { sonusSystem 34 }

sonusSystemMacAddress2StatusEntry OBJECT-TYPE
    SYNTAX          SonusSystemMacAddress2StatusEntry
    ACCESS          not-accessible
    STATUS          mandatory
    DESCRIPTION     
            ""
    INDEX           { sonusSystemMacAddress2StatusServerName, 
                      sonusSystemMacAddress2StatusMacAddress }
    ::= { sonusSystemMacAddress2StatusTable 1 }

SonusSystemMacAddress2StatusEntry ::=
    SEQUENCE {
        sonusSystemMacAddress2StatusServerName      String,
        sonusSystemMacAddress2StatusMacAddress      String,
        sonusSystemMacAddress2StatusStatus  MacAddressStatusType,
        sonusSystemMacAddress2StatusUsedBy  String,
        sonusSystemMacAddress2StatusUsedByPort      String
    }

sonusSystemMacAddress2StatusServerName OBJECT-TYPE
    SYNTAX          String (SIZE(0..255))
    ACCESS          not-accessible
    STATUS          mandatory
    DESCRIPTION     
            "
             Name of server.
             "
    ::= { sonusSystemMacAddress2StatusEntry 1 }

sonusSystemMacAddress2StatusMacAddress OBJECT-TYPE
    SYNTAX          String (SIZE(0..255))
    ACCESS          not-accessible
    STATUS          mandatory
    DESCRIPTION     
            "
             Mac address.
             "
    ::= { sonusSystemMacAddress2StatusEntry 2 }

sonusSystemMacAddress2StatusStatus OBJECT-TYPE
    SYNTAX          MacAddressStatusType
    ACCESS          read-only
    STATUS          mandatory
    DESCRIPTION     
            "
             Status of MAC Address
             "
    ::= { sonusSystemMacAddress2StatusEntry 3 }

sonusSystemMacAddress2StatusUsedBy OBJECT-TYPE
    SYNTAX          String (SIZE(0..255))
    ACCESS          read-only
    STATUS          mandatory
    DESCRIPTION     
            "
             MAC Address usedBy Server
             "
    ::= { sonusSystemMacAddress2StatusEntry 4 }

sonusSystemMacAddress2StatusUsedByPort OBJECT-TYPE
    SYNTAX          String (SIZE(0..255))
    ACCESS          read-only
    STATUS          mandatory
    DESCRIPTION     
            "
             MAC Address usedByPort
             "
    ::= { sonusSystemMacAddress2StatusEntry 5 }

sonusSystemSoftwareUpgradeDetailedStatusTable OBJECT-TYPE
    SYNTAX          SEQUENCE OF SonusSystemSoftwareUpgradeDetailedStatusEntry
    ACCESS          not-accessible
    STATUS          mandatory
    DESCRIPTION     
            "
             The system software upgrade detailed status table describes the detailed status of the
             software upgrade module.
             "
    ::= { sonusSystem 35 }

sonusSystemSoftwareUpgradeDetailedStatusEntry OBJECT-TYPE
    SYNTAX          SonusSystemSoftwareUpgradeDetailedStatusEntry
    ACCESS          not-accessible
    STATUS          mandatory
    DESCRIPTION     
            ""
    INDEX           { sonusSystemSoftwareUpgradeDetailedStatusSystemName }
    ::= { sonusSystemSoftwareUpgradeDetailedStatusTable 1 }

SonusSystemSoftwareUpgradeDetailedStatusEntry ::=
    SEQUENCE {
        sonusSystemSoftwareUpgradeDetailedStatusSystemName                  String,
        sonusSystemSoftwareUpgradeDetailedStatusDetailedStatus                      SonusDetailedStatusType
    }

sonusSystemSoftwareUpgradeDetailedStatusSystemName OBJECT-TYPE
    SYNTAX          String (SIZE(0..255))
    ACCESS          not-accessible
    STATUS          mandatory
    DESCRIPTION     
            "
             Identifies the system.
             "
    ::= { sonusSystemSoftwareUpgradeDetailedStatusEntry 1 }

sonusSystemSoftwareUpgradeDetailedStatusDetailedStatus OBJECT-TYPE
    SYNTAX          SonusDetailedStatusType
    ACCESS          read-only
    STATUS          mandatory
    DESCRIPTION     
            "
             Prints the detailed upgrade status.
             "
    ::= { sonusSystemSoftwareUpgradeDetailedStatusEntry 2 }

sonusSystemHaConfigTable OBJECT-TYPE
    SYNTAX          SEQUENCE OF SonusSystemHaConfigEntry
    ACCESS          not-accessible
    STATUS          mandatory
    DESCRIPTION     
            "
             Displays the HA port redundancy configuration.
             "
    ::= { sonusSystem 36 }

sonusSystemHaConfigEntry OBJECT-TYPE
    SYNTAX          SonusSystemHaConfigEntry
    ACCESS          not-accessible
    STATUS          mandatory
    DESCRIPTION     
            ""
    INDEX           { sonusSystemHaConfigServerName }
    ::= { sonusSystemHaConfigTable 1 }

SonusSystemHaConfigEntry ::=
    SEQUENCE {
        sonusSystemHaConfigServerName   String,
        sonusSystemHaConfigLeaderElection SonusLeaderElectType,
        sonusSystemHaConfigBondMonitoring SonusBondMonitorType
    }

sonusSystemHaConfigServerName OBJECT-TYPE
    SYNTAX          String (SIZE(0..255))
    ACCESS          not-accessible
    STATUS          mandatory
    DESCRIPTION     
            "
             Name of server.
             "
    ::= { sonusSystemHaConfigEntry 1 }

sonusSystemHaConfigLeaderElection OBJECT-TYPE
    SYNTAX          SonusLeaderElectType
    ACCESS          read-only
    STATUS          mandatory
    DESCRIPTION     
            "
             Leader Election Algorithm.
             "
    ::= { sonusSystemHaConfigEntry 2 }

sonusSystemHaConfigBondMonitoring OBJECT-TYPE
    SYNTAX          SonusBondMonitorType
    ACCESS          read-only
    STATUS          mandatory
    DESCRIPTION     
            "
             bond device monitoring.
             "
    ::= { sonusSystemHaConfigEntry 3 }

sonusSystemLicenseServerStatusTable OBJECT-TYPE
    SYNTAX          SEQUENCE OF SonusSystemLicenseServerStatusEntry
    ACCESS          not-accessible
    STATUS          mandatory
    DESCRIPTION     
            "
             Status for license servers
             "
    ::= { sonusSystem 37 }

sonusSystemLicenseServerStatusEntry OBJECT-TYPE
    SYNTAX          SonusSystemLicenseServerStatusEntry
    ACCESS          not-accessible
    STATUS          mandatory
    DESCRIPTION     
            ""
    INDEX           { sonusSystemLicenseServerStatusServerName }
    ::= { sonusSystemLicenseServerStatusTable 1 }

SonusSystemLicenseServerStatusEntry ::=
    SEQUENCE {
        sonusSystemLicenseServerStatusServerName        String,
        sonusSystemLicenseServerStatusIsCurrentActive             String,
        sonusSystemLicenseServerStatusRequestMessagesSent                 Counter,
        sonusSystemLicenseServerStatusLicenseGrantMessagesReceived                          Counter,
        sonusSystemLicenseServerStatusLicensePartialGrantMessagesReceived                                 Counter,
        sonusSystemLicenseServerStatusLicenseRejectMessagesReceived                           Counter,
        sonusSystemLicenseServerStatusLicenseErrors           Counter
    }

sonusSystemLicenseServerStatusServerName OBJECT-TYPE
    SYNTAX          String (SIZE(0..23))
    ACCESS          not-accessible
    STATUS          mandatory
    DESCRIPTION     
            "
             The name of the feature
             "
    ::= { sonusSystemLicenseServerStatusEntry 1 }

sonusSystemLicenseServerStatusIsCurrentActive OBJECT-TYPE
    SYNTAX          String (SIZE(0..23))
    ACCESS          read-only
    STATUS          mandatory
    DESCRIPTION     
            "
             This server was the last server that successfully responded to a licenseRequest
             "
    ::= { sonusSystemLicenseServerStatusEntry 2 }

sonusSystemLicenseServerStatusRequestMessagesSent OBJECT-TYPE
    SYNTAX          Counter
    ACCESS          read-only
    STATUS          mandatory
    DESCRIPTION     
            "
             the number of license requests sent
             "
    ::= { sonusSystemLicenseServerStatusEntry 3 }

sonusSystemLicenseServerStatusLicenseGrantMessagesReceived OBJECT-TYPE
    SYNTAX          Counter
    ACCESS          read-only
    STATUS          mandatory
    DESCRIPTION     
            "
             the number of license grant messages receieved
             "
    ::= { sonusSystemLicenseServerStatusEntry 4 }

sonusSystemLicenseServerStatusLicensePartialGrantMessagesReceived OBJECT-TYPE
    SYNTAX          Counter
    ACCESS          read-only
    STATUS          mandatory
    DESCRIPTION     
            "
             the number of partial license grant messages receieved
             "
    ::= { sonusSystemLicenseServerStatusEntry 5 }

sonusSystemLicenseServerStatusLicenseRejectMessagesReceived OBJECT-TYPE
    SYNTAX          Counter
    ACCESS          read-only
    STATUS          mandatory
    DESCRIPTION     
            "
             the number of license reject messages receieved
             "
    ::= { sonusSystemLicenseServerStatusEntry 6 }

sonusSystemLicenseServerStatusLicenseErrors OBJECT-TYPE
    SYNTAX          Counter
    ACCESS          read-only
    STATUS          mandatory
    DESCRIPTION     
            "
             Errors when attempting to make a request (Includes no-response received and possibly other errors)
             "
    ::= { sonusSystemLicenseServerStatusEntry 7 }

sonusSystemLicenseClusterSharedId OBJECT IDENTIFIER
    ::= { sonusSystem 38 }

sonusSystemLicenseClusterSharedIdSharedId OBJECT-TYPE
    SYNTAX          String (SIZE(0..255))
    ACCESS          read-only
    STATUS          mandatory
    DESCRIPTION     
            "
             The shared id.
             "
    ::= { sonusSystemLicenseClusterSharedId 1 }

sonusSystemObjectStoreParameters OBJECT IDENTIFIER
    ::= { sonusSystem 39 }

sonusSystemObjectStoreParametersObjectStoreType OBJECT-TYPE
    SYNTAX          SonusConfigStoreType
    ACCESS          read-only
    STATUS          mandatory
    DESCRIPTION     
            "
             The type of object store service.
             "
    ::= { sonusSystemObjectStoreParameters 1 }

sonusSystemObjectStoreParametersUserName OBJECT-TYPE
    SYNTAX          String (SIZE(0..255))
    ACCESS          read-only
    STATUS          mandatory
    DESCRIPTION     
            "
             The user name credential needed to access the object store service.
             "
    ::= { sonusSystemObjectStoreParameters 2 }

sonusSystemObjectStoreParametersPassword OBJECT-TYPE
    SYNTAX          ConfdString
    ACCESS          read-only
    STATUS          mandatory
    DESCRIPTION     
            "
             The password credential needed to access the object store service.
             "
    ::= { sonusSystemObjectStoreParameters 3 }

sonusSystemObjectStoreParametersUrl OBJECT-TYPE
    SYNTAX          String (SIZE(0..255))
    ACCESS          read-only
    STATUS          mandatory
    DESCRIPTION     
            "
             The url used to access the object store service.
             "
    ::= { sonusSystemObjectStoreParameters 4 }

sonusSystemConfigurator OBJECT IDENTIFIER
    ::= { sonusSystem 41 }

sonusSystemConfiguratorIsConfigurator OBJECT-TYPE
    SYNTAX          TruthValue
    ACCESS          read-only
    STATUS          mandatory
    DESCRIPTION     
            "
             This indicates if the system is the configurator.
             "
    ::= { sonusSystemConfigurator 1 }

sonusSystemLicenseLocalBundleInfoTable OBJECT-TYPE
    SYNTAX          SEQUENCE OF SonusSystemLicenseLocalBundleInfoEntry
    ACCESS          not-accessible
    STATUS          obsolete
    DESCRIPTION     
            "
             Shows information about all the local licenses stored on the box
             "
    ::= { sonusSystem 42 }

sonusSystemLicenseLocalBundleInfoEntry OBJECT-TYPE
    SYNTAX          SonusSystemLicenseLocalBundleInfoEntry
    ACCESS          not-accessible
    STATUS          obsolete
    DESCRIPTION     
            ""
    INDEX           { sonusSystemLicenseLocalBundleInfoBundleName, 
                      sonusSystemLicenseLocalBundleInfoFeatureName }
    ::= { sonusSystemLicenseLocalBundleInfoTable 1 }

SonusSystemLicenseLocalBundleInfoEntry ::=
    SEQUENCE {
        sonusSystemLicenseLocalBundleInfoBundleName           String,
        sonusSystemLicenseLocalBundleInfoFeatureName            String,
        sonusSystemLicenseLocalBundleInfoLicenseId          String,
        sonusSystemLicenseLocalBundleInfoPurchaseOrderId                String,
        sonusSystemLicenseLocalBundleInfoLineId       String,
        sonusSystemLicenseLocalBundleInfoGenerationDate               String,
        sonusSystemLicenseLocalBundleInfoInstallDate            DateAndTime,
        sonusSystemLicenseLocalBundleInfoExpirationDate               String,
        sonusSystemLicenseLocalBundleInfoUsageLimit           INTEGER,
        sonusSystemLicenseLocalBundleInfoFingerPrint1             String,
        sonusSystemLicenseLocalBundleInfoFingerPrint2             String,
        sonusSystemLicenseLocalBundleInfoActiveLicenseMode                  String
    }

sonusSystemLicenseLocalBundleInfoBundleName OBJECT-TYPE
    SYNTAX          String (SIZE(0..23))
    ACCESS          not-accessible
    STATUS          obsolete
    DESCRIPTION     
            "
             The bundle name for the feature
             "
    ::= { sonusSystemLicenseLocalBundleInfoEntry 1 }

sonusSystemLicenseLocalBundleInfoFeatureName OBJECT-TYPE
    SYNTAX          String (SIZE(0..23))
    ACCESS          not-accessible
    STATUS          obsolete
    DESCRIPTION     
            "
             The feature name
             "
    ::= { sonusSystemLicenseLocalBundleInfoEntry 2 }

sonusSystemLicenseLocalBundleInfoLicenseId OBJECT-TYPE
    SYNTAX          String (SIZE(0..23))
    ACCESS          read-only
    STATUS          obsolete
    DESCRIPTION     
            "
             The licenseId
             "
    ::= { sonusSystemLicenseLocalBundleInfoEntry 3 }

sonusSystemLicenseLocalBundleInfoPurchaseOrderId OBJECT-TYPE
    SYNTAX          String (SIZE(0..23))
    ACCESS          read-only
    STATUS          obsolete
    DESCRIPTION     
            "
             The purchase order id
             "
    ::= { sonusSystemLicenseLocalBundleInfoEntry 4 }

sonusSystemLicenseLocalBundleInfoLineId OBJECT-TYPE
    SYNTAX          String (SIZE(0..23))
    ACCESS          read-only
    STATUS          obsolete
    DESCRIPTION     
            "
             The  line id
             "
    ::= { sonusSystemLicenseLocalBundleInfoEntry 5 }

sonusSystemLicenseLocalBundleInfoGenerationDate OBJECT-TYPE
    SYNTAX          String (SIZE(0..255))
    ACCESS          read-only
    STATUS          obsolete
    DESCRIPTION     
            "
             The generation date for this license
             "
    ::= { sonusSystemLicenseLocalBundleInfoEntry 6 }

sonusSystemLicenseLocalBundleInfoInstallDate OBJECT-TYPE
    SYNTAX          DateAndTime
    ACCESS          read-only
    STATUS          obsolete
    DESCRIPTION     
            "
             This date the license was installed
             "
    ::= { sonusSystemLicenseLocalBundleInfoEntry 7 }

sonusSystemLicenseLocalBundleInfoExpirationDate OBJECT-TYPE
    SYNTAX          String (SIZE(0..255))
    ACCESS          read-only
    STATUS          obsolete
    DESCRIPTION     
            "
             The end date for this license
             "
    ::= { sonusSystemLicenseLocalBundleInfoEntry 8 }

sonusSystemLicenseLocalBundleInfoUsageLimit OBJECT-TYPE
    SYNTAX          INTEGER
    ACCESS          read-only
    STATUS          obsolete
    DESCRIPTION     
            "
             The usage limit for this license
             "
    ::= { sonusSystemLicenseLocalBundleInfoEntry 9 }

sonusSystemLicenseLocalBundleInfoFingerPrint1 OBJECT-TYPE
    SYNTAX          String (SIZE(0..255))
    ACCESS          read-only
    STATUS          obsolete
    DESCRIPTION     
            "
             The finger print for one of the nodes
             "
    ::= { sonusSystemLicenseLocalBundleInfoEntry 10 }

sonusSystemLicenseLocalBundleInfoFingerPrint2 OBJECT-TYPE
    SYNTAX          String (SIZE(0..255))
    ACCESS          read-only
    STATUS          obsolete
    DESCRIPTION     
            "
             If an HA license, The finger print for the other node
             "
    ::= { sonusSystemLicenseLocalBundleInfoEntry 11 }

sonusSystemLicenseLocalBundleInfoActiveLicenseMode OBJECT-TYPE
    SYNTAX          String (SIZE(0..255))
    ACCESS          read-only
    STATUS          obsolete
    DESCRIPTION     
            "
             The active licensing mode
             "
    ::= { sonusSystemLicenseLocalBundleInfoEntry 12 }

sonusSystemLicenseLegacyBundleInfoTable OBJECT-TYPE
    SYNTAX          SEQUENCE OF SonusSystemLicenseLegacyBundleInfoEntry
    ACCESS          not-accessible
    STATUS          mandatory
    DESCRIPTION     
            "
             Shows information about all the legacy licenses stored on the box
             "
    ::= { sonusSystem 43 }

sonusSystemLicenseLegacyBundleInfoEntry OBJECT-TYPE
    SYNTAX          SonusSystemLicenseLegacyBundleInfoEntry
    ACCESS          not-accessible
    STATUS          mandatory
    DESCRIPTION     
            ""
    INDEX           { sonusSystemLicenseLegacyBundleInfoBundleName, 
                      sonusSystemLicenseLegacyBundleInfoFeatureName }
    ::= { sonusSystemLicenseLegacyBundleInfoTable 1 }

SonusSystemLicenseLegacyBundleInfoEntry ::=
    SEQUENCE {
        sonusSystemLicenseLegacyBundleInfoBundleName            String,
        sonusSystemLicenseLegacyBundleInfoFeatureName             String,
        sonusSystemLicenseLegacyBundleInfoLicenseId           String,
        sonusSystemLicenseLegacyBundleInfoExpirationDate                String,
        sonusSystemLicenseLegacyBundleInfoUsageLimit            INTEGER,
        sonusSystemLicenseLegacyBundleInfoActiveLicenseMode                   String
    }

sonusSystemLicenseLegacyBundleInfoBundleName OBJECT-TYPE
    SYNTAX          String (SIZE(0..23))
    ACCESS          not-accessible
    STATUS          mandatory
    DESCRIPTION     
            "
             The bundle name for the feature
             "
    ::= { sonusSystemLicenseLegacyBundleInfoEntry 1 }

sonusSystemLicenseLegacyBundleInfoFeatureName OBJECT-TYPE
    SYNTAX          String (SIZE(0..23))
    ACCESS          not-accessible
    STATUS          mandatory
    DESCRIPTION     
            "
             The feature name
             "
    ::= { sonusSystemLicenseLegacyBundleInfoEntry 2 }

sonusSystemLicenseLegacyBundleInfoLicenseId OBJECT-TYPE
    SYNTAX          String (SIZE(0..64))
    ACCESS          read-only
    STATUS          mandatory
    DESCRIPTION     
            "
             The licenseId
             "
    ::= { sonusSystemLicenseLegacyBundleInfoEntry 3 }

sonusSystemLicenseLegacyBundleInfoExpirationDate OBJECT-TYPE
    SYNTAX          String (SIZE(0..255))
    ACCESS          read-only
    STATUS          mandatory
    DESCRIPTION     
            "
             The expiration date for this license
             "
    ::= { sonusSystemLicenseLegacyBundleInfoEntry 4 }

sonusSystemLicenseLegacyBundleInfoUsageLimit OBJECT-TYPE
    SYNTAX          INTEGER
    ACCESS          read-only
    STATUS          mandatory
    DESCRIPTION     
            "
             The count provisioned in this license
             "
    ::= { sonusSystemLicenseLegacyBundleInfoEntry 5 }

sonusSystemLicenseLegacyBundleInfoActiveLicenseMode OBJECT-TYPE
    SYNTAX          String (SIZE(0..255))
    ACCESS          read-only
    STATUS          mandatory
    DESCRIPTION     
            "
             The active licensing mode
             "
    ::= { sonusSystemLicenseLegacyBundleInfoEntry 13 }

sonusSystemLicenseInfoCurrentStatisticsTable OBJECT-TYPE
    SYNTAX          SEQUENCE OF SonusSystemLicenseInfoCurrentStatisticsEntry
    ACCESS          not-accessible
    STATUS          mandatory
    DESCRIPTION     
            "
             The license status for registered license features.
             "
    ::= { sonusSystem 44 }

sonusSystemLicenseInfoCurrentStatisticsEntry OBJECT-TYPE
    SYNTAX          SonusSystemLicenseInfoCurrentStatisticsEntry
    ACCESS          not-accessible
    STATUS          mandatory
    DESCRIPTION     
            ""
    INDEX           { sonusSystemLicenseInfoCurrentStatisticsFeatureName, 
                      sonusSystemLicenseInfoCurrentStatisticsLicenseId }
    ::= { sonusSystemLicenseInfoCurrentStatisticsTable 1 }

SonusSystemLicenseInfoCurrentStatisticsEntry ::=
    SEQUENCE {
        sonusSystemLicenseInfoCurrentStatisticsFeatureName                  String,
        sonusSystemLicenseInfoCurrentStatisticsLicenseId                String,
        sonusSystemLicenseInfoCurrentStatisticsExpirationDate                     String,
        sonusSystemLicenseInfoCurrentStatisticsUsageLimit                 INTEGER,
        sonusSystemLicenseInfoCurrentStatisticsSource             String,
        sonusSystemLicenseInfoCurrentStatisticsInUse            INTEGER
    }

sonusSystemLicenseInfoCurrentStatisticsFeatureName OBJECT-TYPE
    SYNTAX          String (SIZE(0..255))
    ACCESS          not-accessible
    STATUS          mandatory
    DESCRIPTION     
            "
             This object indicates the feature name
             "
    ::= { sonusSystemLicenseInfoCurrentStatisticsEntry 1 }

sonusSystemLicenseInfoCurrentStatisticsLicenseId OBJECT-TYPE
    SYNTAX          String (SIZE(0..64))
    ACCESS          not-accessible
    STATUS          mandatory
    DESCRIPTION     
            "
             This object indicates the license Id.
             "
    ::= { sonusSystemLicenseInfoCurrentStatisticsEntry 2 }

sonusSystemLicenseInfoCurrentStatisticsExpirationDate OBJECT-TYPE
    SYNTAX          String (SIZE(0..255))
    ACCESS          read-only
    STATUS          mandatory
    DESCRIPTION     
            "
             This object indicates the licence expiry date for a feature.
             "
    ::= { sonusSystemLicenseInfoCurrentStatisticsEntry 3 }

sonusSystemLicenseInfoCurrentStatisticsUsageLimit OBJECT-TYPE
    SYNTAX          INTEGER
    ACCESS          read-only
    STATUS          mandatory
    DESCRIPTION     
            "
             This object indicates the usageLimit of a feature.
             "
    ::= { sonusSystemLicenseInfoCurrentStatisticsEntry 4 }

sonusSystemLicenseInfoCurrentStatisticsSource OBJECT-TYPE
    SYNTAX          String (SIZE(0..255))
    ACCESS          read-only
    STATUS          mandatory
    DESCRIPTION     
            "
             Indicates where the licenses is located: nodeLocked or domain
             "
    ::= { sonusSystemLicenseInfoCurrentStatisticsEntry 5 }

sonusSystemLicenseInfoCurrentStatisticsInUse OBJECT-TYPE
    SYNTAX          INTEGER
    ACCESS          read-only
    STATUS          mandatory
    DESCRIPTION     
            "
             Indicates the number of licenses used by the application
             "
    ::= { sonusSystemLicenseInfoCurrentStatisticsEntry 6 }

sonusSystemLicenseInfoIntervalStatisticsTable OBJECT-TYPE
    SYNTAX          SEQUENCE OF SonusSystemLicenseInfoIntervalStatisticsEntry
    ACCESS          not-accessible
    STATUS          mandatory
    DESCRIPTION     
            "
             The license status for registered license features.
             "
    ::= { sonusSystem 45 }

sonusSystemLicenseInfoIntervalStatisticsEntry OBJECT-TYPE
    SYNTAX          SonusSystemLicenseInfoIntervalStatisticsEntry
    ACCESS          not-accessible
    STATUS          mandatory
    DESCRIPTION     
            ""
    INDEX           { 
                      sonusSystemLicenseInfoIntervalStatisticsFeatureName, 
                      sonusSystemLicenseInfoIntervalStatisticsLicenseId }
    ::= { sonusSystemLicenseInfoIntervalStatisticsTable 1 }

SonusSystemLicenseInfoIntervalStatisticsEntry ::=
    SEQUENCE {
        sonusSystemLicenseInfoIntervalStatisticsFeatureName                   String,
        sonusSystemLicenseInfoIntervalStatisticsLicenseId                 String,
        sonusSystemLicenseInfoIntervalStatisticsExpirationDate                      String,
        sonusSystemLicenseInfoIntervalStatisticsUsageLimit                  INTEGER,
        sonusSystemLicenseInfoIntervalStatisticsSource              String,
        sonusSystemLicenseInfoIntervalStatisticsInUse             INTEGER
    }

sonusSystemLicenseInfoIntervalStatisticsFeatureName OBJECT-TYPE
    SYNTAX          String (SIZE(0..255))
    ACCESS          not-accessible
    STATUS          mandatory
    DESCRIPTION     
            "
             This object indicates the feature name
             "
    ::= { sonusSystemLicenseInfoIntervalStatisticsEntry 1 }

sonusSystemLicenseInfoIntervalStatisticsLicenseId OBJECT-TYPE
    SYNTAX          String (SIZE(0..64))
    ACCESS          not-accessible
    STATUS          mandatory
    DESCRIPTION     
            "
             This object indicates the license Id.
             "
    ::= { sonusSystemLicenseInfoIntervalStatisticsEntry 2 }

sonusSystemLicenseInfoIntervalStatisticsExpirationDate OBJECT-TYPE
    SYNTAX          String (SIZE(0..255))
    ACCESS          read-only
    STATUS          mandatory
    DESCRIPTION     
            "
             This object indicates the licence expiry date for a feature.
             "
    ::= { sonusSystemLicenseInfoIntervalStatisticsEntry 3 }

sonusSystemLicenseInfoIntervalStatisticsUsageLimit OBJECT-TYPE
    SYNTAX          INTEGER
    ACCESS          read-only
    STATUS          mandatory
    DESCRIPTION     
            "
             This object indicates the usageLimit of a feature.
             "
    ::= { sonusSystemLicenseInfoIntervalStatisticsEntry 4 }

sonusSystemLicenseInfoIntervalStatisticsSource OBJECT-TYPE
    SYNTAX          String (SIZE(0..255))
    ACCESS          read-only
    STATUS          mandatory
    DESCRIPTION     
            "
             Indicates where the licenses is located: nodeLocked or domain
             "
    ::= { sonusSystemLicenseInfoIntervalStatisticsEntry 5 }

sonusSystemLicenseInfoIntervalStatisticsInUse OBJECT-TYPE
    SYNTAX          INTEGER
    ACCESS          read-only
    STATUS          mandatory
    DESCRIPTION     
            "
             Indicates the number of licenses used by the application
             "
    ::= { sonusSystemLicenseInfoIntervalStatisticsEntry 6 }

sonusSystemLicenseFeatureStatusTable OBJECT-TYPE
    SYNTAX          SEQUENCE OF SonusSystemLicenseFeatureStatusEntry
    ACCESS          not-accessible
    STATUS          mandatory
    DESCRIPTION     
            "
             Status information about each licensed feature
             "
    ::= { sonusSystem 46 }

sonusSystemLicenseFeatureStatusEntry OBJECT-TYPE
    SYNTAX          SonusSystemLicenseFeatureStatusEntry
    ACCESS          not-accessible
    STATUS          mandatory
    DESCRIPTION     
            ""
    INDEX           { sonusSystemLicenseFeatureStatusFeatureName }
    ::= { sonusSystemLicenseFeatureStatusTable 1 }

SonusSystemLicenseFeatureStatusEntry ::=
    SEQUENCE {
        sonusSystemLicenseFeatureStatusFeatureName          String,
        sonusSystemLicenseFeatureStatusLicenseSought            Counter,
        sonusSystemLicenseFeatureStatusLicenseNotReceived                 Counter,
        sonusSystemLicenseFeatureStatusLastUpdateWasLocal                 String,
        sonusSystemLicenseFeatureStatusLicenseInstalled               String,
        sonusSystemLicenseFeatureStatusCurrentLicenseAvailability                         String,
        sonusSystemLicenseFeatureStatusCurrentLicensesTotal                   INTEGER,
        sonusSystemLicenseFeatureStatusCurrentLicensesInUse                   INTEGER,
        sonusSystemLicenseFeatureStatusLicensingStatus              String
    }

sonusSystemLicenseFeatureStatusFeatureName OBJECT-TYPE
    SYNTAX          String (SIZE(0..23))
    ACCESS          not-accessible
    STATUS          mandatory
    DESCRIPTION     
            "
             The name of the feature
             "
    ::= { sonusSystemLicenseFeatureStatusEntry 1 }

sonusSystemLicenseFeatureStatusLicenseSought OBJECT-TYPE
    SYNTAX          Counter
    ACCESS          read-only
    STATUS          mandatory
    DESCRIPTION     
            "
             The number of times a license was sought
             "
    ::= { sonusSystemLicenseFeatureStatusEntry 2 }

sonusSystemLicenseFeatureStatusLicenseNotReceived OBJECT-TYPE
    SYNTAX          Counter
    ACCESS          read-only
    STATUS          mandatory
    DESCRIPTION     
            "
             The number of times a license was not received
             "
    ::= { sonusSystemLicenseFeatureStatusEntry 3 }

sonusSystemLicenseFeatureStatusLastUpdateWasLocal OBJECT-TYPE
    SYNTAX          String (SIZE(0..255))
    ACCESS          read-only
    STATUS          mandatory
    DESCRIPTION     
            "
             Was the last update request performed locally
             "
    ::= { sonusSystemLicenseFeatureStatusEntry 4 }

sonusSystemLicenseFeatureStatusLicenseInstalled OBJECT-TYPE
    SYNTAX          String (SIZE(0..255))
    ACCESS          read-only
    STATUS          mandatory
    DESCRIPTION     
            "
             Displays whether the license is installed or not
             "
    ::= { sonusSystemLicenseFeatureStatusEntry 5 }

sonusSystemLicenseFeatureStatusCurrentLicenseAvailability OBJECT-TYPE
    SYNTAX          String (SIZE(0..255))
    ACCESS          read-only
    STATUS          mandatory
    DESCRIPTION     
            "
             Displays current availability of license
             "
    ::= { sonusSystemLicenseFeatureStatusEntry 6 }

sonusSystemLicenseFeatureStatusCurrentLicensesTotal OBJECT-TYPE
    SYNTAX          INTEGER
    ACCESS          read-only
    STATUS          mandatory
    DESCRIPTION     
            "
             This object indicates usage limit of license
             "
    ::= { sonusSystemLicenseFeatureStatusEntry 7 }

sonusSystemLicenseFeatureStatusCurrentLicensesInUse OBJECT-TYPE
    SYNTAX          INTEGER
    ACCESS          read-only
    STATUS          mandatory
    DESCRIPTION     
            "
             Indicates the number of licenses currently in use
             "
    ::= { sonusSystemLicenseFeatureStatusEntry 8 }

sonusSystemLicenseFeatureStatusLicensingStatus OBJECT-TYPE
    SYNTAX          String (SIZE(0..255))
    ACCESS          read-only
    STATUS          mandatory
    DESCRIPTION     
            "
             Indicates whether Feature or Call addmission is enabled or disabled
             "
    ::= { sonusSystemLicenseFeatureStatusEntry 9 }

sonusSystemLicenseRequiredStatusTable OBJECT-TYPE
    SYNTAX          SEQUENCE OF SonusSystemLicenseRequiredStatusEntry
    ACCESS          not-accessible
    STATUS          mandatory
    DESCRIPTION     
            "
             Status information about licenses acquired by this application
             "
    ::= { sonusSystem 47 }

sonusSystemLicenseRequiredStatusEntry OBJECT-TYPE
    SYNTAX          SonusSystemLicenseRequiredStatusEntry
    ACCESS          not-accessible
    STATUS          mandatory
    DESCRIPTION     
            ""
    INDEX           { sonusSystemLicenseRequiredStatusName, 
                      sonusSystemLicenseRequiredStatusFeatureName }
    ::= { sonusSystemLicenseRequiredStatusTable 1 }

SonusSystemLicenseRequiredStatusEntry ::=
    SEQUENCE {
        sonusSystemLicenseRequiredStatusName    String,
        sonusSystemLicenseRequiredStatusFeatureName           String,
        sonusSystemLicenseRequiredStatusLastAcquiredCount                 Gauge,
        sonusSystemLicenseRequiredStatusLastGoodserverName                  String,
        sonusSystemLicenseRequiredStatusLastAcquiredDate                DateAndTime,
        sonusSystemLicenseRequiredStatusUsingCapacityLicense                    String,
        sonusSystemLicenseRequiredStatusClemency        String,
        sonusSystemLicenseRequiredStatusFailSafeMode            String,
        sonusSystemLicenseRequiredStatusServiceAuthorizationMode                        String
    }

sonusSystemLicenseRequiredStatusName OBJECT-TYPE
    SYNTAX          String (SIZE(0..255))
    ACCESS          not-accessible
    STATUS          mandatory
    DESCRIPTION     
            "
             Identifies the server.
             "
    ::= { sonusSystemLicenseRequiredStatusEntry 1 }

sonusSystemLicenseRequiredStatusFeatureName OBJECT-TYPE
    SYNTAX          String (SIZE(0..23))
    ACCESS          not-accessible
    STATUS          mandatory
    DESCRIPTION     
            "
             The name of the feature
             "
    ::= { sonusSystemLicenseRequiredStatusEntry 2 }

sonusSystemLicenseRequiredStatusLastAcquiredCount OBJECT-TYPE
    SYNTAX          Gauge
    ACCESS          read-only
    STATUS          mandatory
    DESCRIPTION     
            "
             the number of licenses acquired
             "
    ::= { sonusSystemLicenseRequiredStatusEntry 3 }

sonusSystemLicenseRequiredStatusLastGoodserverName OBJECT-TYPE
    SYNTAX          String (SIZE(0..255))
    ACCESS          read-only
    STATUS          mandatory
    DESCRIPTION     
            "
             The name used to reference this server
             "
    ::= { sonusSystemLicenseRequiredStatusEntry 4 }

sonusSystemLicenseRequiredStatusLastAcquiredDate OBJECT-TYPE
    SYNTAX          DateAndTime
    ACCESS          read-only
    STATUS          mandatory
    DESCRIPTION     
            "
             This date the license was installed
             "
    ::= { sonusSystemLicenseRequiredStatusEntry 7 }

sonusSystemLicenseRequiredStatusUsingCapacityLicense OBJECT-TYPE
    SYNTAX          String (SIZE(0..255))
    ACCESS          read-only
    STATUS          mandatory
    DESCRIPTION     
            "
             Was this license obtained using a capacity license
             "
    ::= { sonusSystemLicenseRequiredStatusEntry 8 }

sonusSystemLicenseRequiredStatusClemency OBJECT-TYPE
    SYNTAX          String (SIZE(0..255))
    ACCESS          read-only
    STATUS          mandatory
    DESCRIPTION     
            "
             "
    ::= { sonusSystemLicenseRequiredStatusEntry 9 }

sonusSystemLicenseRequiredStatusFailSafeMode OBJECT-TYPE
    SYNTAX          String (SIZE(0..255))
    ACCESS          read-only
    STATUS          mandatory
    DESCRIPTION     
            "
             "
    ::= { sonusSystemLicenseRequiredStatusEntry 10 }

sonusSystemLicenseRequiredStatusServiceAuthorizationMode OBJECT-TYPE
    SYNTAX          String (SIZE(0..255))
    ACCESS          read-only
    STATUS          mandatory
    DESCRIPTION     
            "
             "
    ::= { sonusSystemLicenseRequiredStatusEntry 11 }

sonusSystemSbcPersonalityStatus OBJECT IDENTIFIER
    ::= { sonusSystem 48 }

sonusSystemSbcPersonalityStatusRole OBJECT-TYPE
    SYNTAX          SonusPersonalityType
    ACCESS          read-only
    STATUS          mandatory
    DESCRIPTION     
            "
             Personality type of this instance.
             "
    ::= { sonusSystemSbcPersonalityStatus 1 }

sonusSystemResetLicenseStats OBJECT IDENTIFIER
    ::= { sonusSystem 49 }

sonusSystemStandbySyncStatusTable OBJECT-TYPE
    SYNTAX          SEQUENCE OF SonusSystemStandbySyncStatusEntry
    ACCESS          not-accessible
    STATUS          mandatory
    DESCRIPTION     
            "
             The standby server synchronization status table.  This table is used for N:1 redundancy where
             a standby server support N active servers.  It describes data synchronization state of various items.
             "
    ::= { sonusSystem 50 }

sonusSystemStandbySyncStatusEntry OBJECT-TYPE
    SYNTAX          SonusSystemStandbySyncStatusEntry
    ACCESS          not-accessible
    STATUS          mandatory
    DESCRIPTION     
            ""
    INDEX           { sonusSystemStandbySyncStatusActiveServerName, 
                      sonusSystemStandbySyncStatusSyncModule }
    ::= { sonusSystemStandbySyncStatusTable 1 }

SonusSystemStandbySyncStatusEntry ::=
    SEQUENCE {
        sonusSystemStandbySyncStatusActiveServerName            String,
        sonusSystemStandbySyncStatusSyncModule      String,
        sonusSystemStandbySyncStatusStatus  SonusNodeSrvrSyncStatusType
    }

sonusSystemStandbySyncStatusActiveServerName OBJECT-TYPE
    SYNTAX          String (SIZE(0..255))
    ACCESS          not-accessible
    STATUS          mandatory
    DESCRIPTION     
            "
             Identifies the active server.
             "
    ::= { sonusSystemStandbySyncStatusEntry 1 }

sonusSystemStandbySyncStatusSyncModule OBJECT-TYPE
    SYNTAX          String (SIZE(0..255))
    ACCESS          not-accessible
    STATUS          mandatory
    DESCRIPTION     
            "
             Identifies the syncronization item.
             "
    ::= { sonusSystemStandbySyncStatusEntry 2 }

sonusSystemStandbySyncStatusStatus OBJECT-TYPE
    SYNTAX          SonusNodeSrvrSyncStatusType
    ACCESS          read-only
    STATUS          mandatory
    DESCRIPTION     
            "
             Indicates the inter-CE data synchronization state.
             "
    ::= { sonusSystemStandbySyncStatusEntry 3 }

sonusSystemRgStatusTable OBJECT-TYPE
    SYNTAX          SEQUENCE OF SonusSystemRgStatusEntry
    ACCESS          not-accessible
    STATUS          mandatory
    DESCRIPTION     
            "
             The system Redundancy Group(RG) status table describes the status of the
             instances in RG.
             "
    ::= { sonusSystem 51 }

sonusSystemRgStatusEntry OBJECT-TYPE
    SYNTAX          SonusSystemRgStatusEntry
    ACCESS          not-accessible
    STATUS          mandatory
    DESCRIPTION     
            ""
    INDEX           { sonusSystemRgStatusInstanceRgName }
    ::= { sonusSystemRgStatusTable 1 }

SonusSystemRgStatusEntry ::=
    SEQUENCE {
        sonusSystemRgStatusInstanceRgName String,
        sonusSystemRgStatusActualCeName String,
        sonusSystemRgStatusAssignedRole SonusNodeSrvrStatModeType,
        sonusSystemRgStatusCurrentRole  String,
        sonusSystemRgStatusNodeId       Gauge,
        sonusSystemRgStatusServiceId    Gauge,
        sonusSystemRgStatusSyncStatus   SonusNodeSrvrSyncStatusType,
        sonusSystemRgStatusUsingMetavarsOf  String,
        sonusSystemRgStatusAppVersion   String
    }

sonusSystemRgStatusInstanceRgName OBJECT-TYPE
    SYNTAX          String (SIZE(0..255))
    ACCESS          not-accessible
    STATUS          mandatory
    DESCRIPTION     
            "
             Identifies the instance.
             "
    ::= { sonusSystemRgStatusEntry 1 }

sonusSystemRgStatusActualCeName OBJECT-TYPE
    SYNTAX          String (SIZE(0..255))
    ACCESS          read-only
    STATUS          mandatory
    DESCRIPTION     
            "
             Identifies the given/actual server.
             "
    ::= { sonusSystemRgStatusEntry 2 }

sonusSystemRgStatusAssignedRole OBJECT-TYPE
    SYNTAX          SonusNodeSrvrStatModeType
    ACCESS          read-only
    STATUS          mandatory
    DESCRIPTION     
            "
             Indicates the assigned redundancy role of the instance.
             "
    ::= { sonusSystemRgStatusEntry 3 }

sonusSystemRgStatusCurrentRole OBJECT-TYPE
    SYNTAX          String (SIZE(0..255))
    ACCESS          read-only
    STATUS          mandatory
    DESCRIPTION     
            "
             Indicates the current redundancy role of the instance.
             "
    ::= { sonusSystemRgStatusEntry 4 }

sonusSystemRgStatusNodeId OBJECT-TYPE
    SYNTAX          Gauge
    ACCESS          read-only
    STATUS          mandatory
    DESCRIPTION     
            "
             Node id of the instance.
             "
    ::= { sonusSystemRgStatusEntry 5 }

sonusSystemRgStatusServiceId OBJECT-TYPE
    SYNTAX          Gauge
    ACCESS          read-only
    STATUS          mandatory
    DESCRIPTION     
            "
             Service id of the instance.
             "
    ::= { sonusSystemRgStatusEntry 6 }

sonusSystemRgStatusSyncStatus OBJECT-TYPE
    SYNTAX          SonusNodeSrvrSyncStatusType
    ACCESS          read-only
    STATUS          mandatory
    DESCRIPTION     
            "
             Indicates synchronization state of the instance.
             "
    ::= { sonusSystemRgStatusEntry 7 }

sonusSystemRgStatusUsingMetavarsOf OBJECT-TYPE
    SYNTAX          String (SIZE(0..255))
    ACCESS          read-only
    STATUS          mandatory
    DESCRIPTION     
            "
             Indicates the Metavariables this instance is using belongs to which stack/instance.
             "
    ::= { sonusSystemRgStatusEntry 8 }

sonusSystemRgStatusAppVersion OBJECT-TYPE
    SYNTAX          String (SIZE(0..255))
    ACCESS          read-only
    STATUS          mandatory
    DESCRIPTION     
            "
             Indicates the version of sbc running on this instance
             "
    ::= { sonusSystemRgStatusEntry 9 }

sonusSystemNiceLicense OBJECT IDENTIFIER
    ::= { sonusSystem 52 }

sonusSystemNiceLicenseIsNiceRecordingAllowed OBJECT-TYPE
    SYNTAX          TruthValue
    ACCESS          read-only
    STATUS          mandatory
    DESCRIPTION     
            "
             if True nice recording is allowed else not.
             "
    ::= { sonusSystemNiceLicense 1 }

sonusSystemGpuStatusTable OBJECT-TYPE
    SYNTAX          SEQUENCE OF SonusSystemGpuStatusEntry
    ACCESS          not-accessible
    STATUS          mandatory
    DESCRIPTION     
            "
             Displays Information of GPUs present in server
             "
    ::= { sonusSystem 53 }

sonusSystemGpuStatusEntry OBJECT-TYPE
    SYNTAX          SonusSystemGpuStatusEntry
    ACCESS          not-accessible
    STATUS          mandatory
    DESCRIPTION     
            ""
    INDEX           { sonusSystemGpuStatusServerName, 
                      sonusSystemGpuStatusGPUNumber }
    ::= { sonusSystemGpuStatusTable 1 }

SonusSystemGpuStatusEntry ::=
    SEQUENCE {
        sonusSystemGpuStatusServerName  String,
        sonusSystemGpuStatusGPUNumber   Gauge,
        sonusSystemGpuStatusMemoryUsage INTEGER,
        sonusSystemGpuStatusCurrentTemperature      INTEGER,
        sonusSystemGpuStatusShutdownTemperature       INTEGER,
        sonusSystemGpuStatusSlowdownTemperature       INTEGER,
        sonusSystemGpuStatusMemoryClockSpeed    INTEGER,
        sonusSystemGpuStatusGraphicsClockSpeed      INTEGER,
        sonusSystemGpuStatusEccErrors   INTEGER,
        sonusSystemGpuStatusCurrentEccMode  String,
        sonusSystemGpuStatusPendingEccMode  String
    }

sonusSystemGpuStatusServerName OBJECT-TYPE
    SYNTAX          String (SIZE(0..255))
    ACCESS          not-accessible
    STATUS          mandatory
    DESCRIPTION     
            "
             Name of server.
             "
    ::= { sonusSystemGpuStatusEntry 1 }

sonusSystemGpuStatusGPUNumber OBJECT-TYPE
    SYNTAX          Gauge
    ACCESS          not-accessible
    STATUS          mandatory
    DESCRIPTION     
            "
             Index of GPU.
             "
    ::= { sonusSystemGpuStatusEntry 2 }

sonusSystemGpuStatusMemoryUsage OBJECT-TYPE
    SYNTAX          INTEGER
    ACCESS          read-only
    STATUS          mandatory
    DESCRIPTION     
            "
             Memory usage of GPU(Percent),  -1 is displayed when no data is available
             "
    ::= { sonusSystemGpuStatusEntry 3 }

sonusSystemGpuStatusCurrentTemperature OBJECT-TYPE
    SYNTAX          INTEGER
    ACCESS          read-only
    STATUS          mandatory
    DESCRIPTION     
            "
             Temperature of GPU in degree celsius, -1 is displayed when no data is available
             "
    ::= { sonusSystemGpuStatusEntry 4 }

sonusSystemGpuStatusShutdownTemperature OBJECT-TYPE
    SYNTAX          INTEGER
    ACCESS          read-only
    STATUS          mandatory
    DESCRIPTION     
            "
             GPU Shutdown Temperature in degree celsius, -1 is displayed when no data is available
             "
    ::= { sonusSystemGpuStatusEntry 5 }

sonusSystemGpuStatusSlowdownTemperature OBJECT-TYPE
    SYNTAX          INTEGER
    ACCESS          read-only
    STATUS          mandatory
    DESCRIPTION     
            "
             GPU Slowdown Temperature in degree celsius, -1 is displayed when no data is available
             "
    ::= { sonusSystemGpuStatusEntry 6 }

sonusSystemGpuStatusMemoryClockSpeed OBJECT-TYPE
    SYNTAX          INTEGER
    ACCESS          read-only
    STATUS          mandatory
    DESCRIPTION     
            "
             Memory clock speed of GPU in degree celsius, -1 is displayed when no data is available
             "
    ::= { sonusSystemGpuStatusEntry 7 }

sonusSystemGpuStatusGraphicsClockSpeed OBJECT-TYPE
    SYNTAX          INTEGER
    ACCESS          read-only
    STATUS          mandatory
    DESCRIPTION     
            "
             Graphics clock speed of GPU in degree celsius, -1 is displayed when no data is available
             "
    ::= { sonusSystemGpuStatusEntry 8 }

sonusSystemGpuStatusEccErrors OBJECT-TYPE
    SYNTAX          INTEGER
    ACCESS          read-only
    STATUS          mandatory
    DESCRIPTION     
            "
             ECC errors, -1 shows no data available
             "
    ::= { sonusSystemGpuStatusEntry 9 }

sonusSystemGpuStatusCurrentEccMode OBJECT-TYPE
    SYNTAX          String (SIZE(0..255))
    ACCESS          read-only
    STATUS          mandatory
    DESCRIPTION     
            "
             Current ECC mode
             "
    ::= { sonusSystemGpuStatusEntry 10 }

sonusSystemGpuStatusPendingEccMode OBJECT-TYPE
    SYNTAX          String (SIZE(0..255))
    ACCESS          read-only
    STATUS          mandatory
    DESCRIPTION     
            "
             Current ECC mode
             "
    ::= { sonusSystemGpuStatusEntry 11 }

sonusSystemPdcsLicense OBJECT IDENTIFIER
    ::= { sonusSystem 54 }

sonusSystemPdcsLicenseIsPDCSAllowed OBJECT-TYPE
    SYNTAX          TruthValue
    ACCESS          read-only
    STATUS          mandatory
    DESCRIPTION     
            "
             if True PDCS license is allowed else not.
             "
    ::= { sonusSystemPdcsLicense 1 }

sonusSystemSbcliLicense OBJECT IDENTIFIER
    ::= { sonusSystem 55 }

sonusSystemSbcliLicenseIsSBCLIAllowed OBJECT-TYPE
    SYNTAX          TruthValue
    ACCESS          read-only
    STATUS          mandatory
    DESCRIPTION     
            "
             if True SBC-LI license is allowed else not.
             "
    ::= { sonusSystemSbcliLicense 1 }

sonusSystemLicenseDomainBundleInfoTable OBJECT-TYPE
    SYNTAX          SEQUENCE OF SonusSystemLicenseDomainBundleInfoEntry
    ACCESS          not-accessible
    STATUS          mandatory
    DESCRIPTION     
            "
             Shows information about all the domain licenses stored on the box
             "
    ::= { sonusSystem 56 }

sonusSystemLicenseDomainBundleInfoEntry OBJECT-TYPE
    SYNTAX          SonusSystemLicenseDomainBundleInfoEntry
    ACCESS          not-accessible
    STATUS          mandatory
    DESCRIPTION     
            ""
    INDEX           { sonusSystemLicenseDomainBundleInfoBundleName, 
                      sonusSystemLicenseDomainBundleInfoFeatureName, 
                      sonusSystemLicenseDomainBundleInfoLineId }
    ::= { sonusSystemLicenseDomainBundleInfoTable 1 }

SonusSystemLicenseDomainBundleInfoEntry ::=
    SEQUENCE {
        sonusSystemLicenseDomainBundleInfoBundleName            String,
        sonusSystemLicenseDomainBundleInfoFeatureName             String,
        sonusSystemLicenseDomainBundleInfoLicenseId           String,
        sonusSystemLicenseDomainBundleInfoPurchaseOrderId                 String,
        sonusSystemLicenseDomainBundleInfoLineId        String,
        sonusSystemLicenseDomainBundleInfoGenerationDate                String,
        sonusSystemLicenseDomainBundleInfoInstallDate             DateAndTime,
        sonusSystemLicenseDomainBundleInfoExpirationDate                String,
        sonusSystemLicenseDomainBundleInfoUsageLimit            INTEGER,
        sonusSystemLicenseDomainBundleInfoActiveLicenseMode                   String
    }

sonusSystemLicenseDomainBundleInfoBundleName OBJECT-TYPE
    SYNTAX          String (SIZE(0..23))
    ACCESS          not-accessible
    STATUS          mandatory
    DESCRIPTION     
            "
             The bundle name for the feature
             "
    ::= { sonusSystemLicenseDomainBundleInfoEntry 1 }

sonusSystemLicenseDomainBundleInfoFeatureName OBJECT-TYPE
    SYNTAX          String (SIZE(0..23))
    ACCESS          not-accessible
    STATUS          mandatory
    DESCRIPTION     
            "
             The feature name
             "
    ::= { sonusSystemLicenseDomainBundleInfoEntry 2 }

sonusSystemLicenseDomainBundleInfoLicenseId OBJECT-TYPE
    SYNTAX          String (SIZE(0..64))
    ACCESS          read-only
    STATUS          obsolete
    DESCRIPTION     
            "
             The licenseId
             "
    ::= { sonusSystemLicenseDomainBundleInfoEntry 3 }

sonusSystemLicenseDomainBundleInfoPurchaseOrderId OBJECT-TYPE
    SYNTAX          String (SIZE(0..23))
    ACCESS          read-only
    STATUS          obsolete
    DESCRIPTION     
            "
             The purchase order id
             "
    ::= { sonusSystemLicenseDomainBundleInfoEntry 4 }

sonusSystemLicenseDomainBundleInfoLineId OBJECT-TYPE
    SYNTAX          String (SIZE(0..64))
    ACCESS          not-accessible
    STATUS          mandatory
    DESCRIPTION     
            "
             The  line id
             "
    ::= { sonusSystemLicenseDomainBundleInfoEntry 5 }

sonusSystemLicenseDomainBundleInfoGenerationDate OBJECT-TYPE
    SYNTAX          String (SIZE(0..255))
    ACCESS          read-only
    STATUS          mandatory
    DESCRIPTION     
            "
             The generation date for this license
             "
    ::= { sonusSystemLicenseDomainBundleInfoEntry 6 }

sonusSystemLicenseDomainBundleInfoInstallDate OBJECT-TYPE
    SYNTAX          DateAndTime
    ACCESS          read-only
    STATUS          mandatory
    DESCRIPTION     
            "
             This date the license was installed
             "
    ::= { sonusSystemLicenseDomainBundleInfoEntry 7 }

sonusSystemLicenseDomainBundleInfoExpirationDate OBJECT-TYPE
    SYNTAX          String (SIZE(0..255))
    ACCESS          read-only
    STATUS          mandatory
    DESCRIPTION     
            "
             The end date for this license
             "
    ::= { sonusSystemLicenseDomainBundleInfoEntry 8 }

sonusSystemLicenseDomainBundleInfoUsageLimit OBJECT-TYPE
    SYNTAX          INTEGER
    ACCESS          read-only
    STATUS          mandatory
    DESCRIPTION     
            "
             The usage limit for this license
             "
    ::= { sonusSystemLicenseDomainBundleInfoEntry 9 }

sonusSystemLicenseDomainBundleInfoActiveLicenseMode OBJECT-TYPE
    SYNTAX          String (SIZE(0..255))
    ACCESS          read-only
    STATUS          mandatory
    DESCRIPTION     
            "
             The active licensing mode
             "
    ::= { sonusSystemLicenseDomainBundleInfoEntry 11 }

sonusSystemLicenseNodeLockedBundleInfoTable OBJECT-TYPE
    SYNTAX          SEQUENCE OF SonusSystemLicenseNodeLockedBundleInfoEntry
    ACCESS          not-accessible
    STATUS          mandatory
    DESCRIPTION     
            "
             Shows information about all the nodeLocked licenses stored on the box
             "
    ::= { sonusSystem 57 }

sonusSystemLicenseNodeLockedBundleInfoEntry OBJECT-TYPE
    SYNTAX          SonusSystemLicenseNodeLockedBundleInfoEntry
    ACCESS          not-accessible
    STATUS          mandatory
    DESCRIPTION     
            ""
    INDEX           { sonusSystemLicenseNodeLockedBundleInfoBundleName, 
                      sonusSystemLicenseNodeLockedBundleInfoFeatureName }
    ::= { sonusSystemLicenseNodeLockedBundleInfoTable 1 }

SonusSystemLicenseNodeLockedBundleInfoEntry ::=
    SEQUENCE {
        sonusSystemLicenseNodeLockedBundleInfoBundleName                String,
        sonusSystemLicenseNodeLockedBundleInfoFeatureName                 String,
        sonusSystemLicenseNodeLockedBundleInfoLicenseId               String,
        sonusSystemLicenseNodeLockedBundleInfoExpirationDate                    String,
        sonusSystemLicenseNodeLockedBundleInfoUsageLimit                INTEGER,
        sonusSystemLicenseNodeLockedBundleInfoActiveLicenseMode                       String
    }

sonusSystemLicenseNodeLockedBundleInfoBundleName OBJECT-TYPE
    SYNTAX          String (SIZE(0..23))
    ACCESS          not-accessible
    STATUS          mandatory
    DESCRIPTION     
            "
             The bundle name for the feature
             "
    ::= { sonusSystemLicenseNodeLockedBundleInfoEntry 1 }

sonusSystemLicenseNodeLockedBundleInfoFeatureName OBJECT-TYPE
    SYNTAX          String (SIZE(0..23))
    ACCESS          not-accessible
    STATUS          mandatory
    DESCRIPTION     
            "
             The feature name
             "
    ::= { sonusSystemLicenseNodeLockedBundleInfoEntry 2 }

sonusSystemLicenseNodeLockedBundleInfoLicenseId OBJECT-TYPE
    SYNTAX          String (SIZE(0..64))
    ACCESS          read-only
    STATUS          mandatory
    DESCRIPTION     
            "
             The licenseId
             "
    ::= { sonusSystemLicenseNodeLockedBundleInfoEntry 3 }

sonusSystemLicenseNodeLockedBundleInfoExpirationDate OBJECT-TYPE
    SYNTAX          String (SIZE(0..255))
    ACCESS          read-only
    STATUS          mandatory
    DESCRIPTION     
            "
             The expiration date for this license
             "
    ::= { sonusSystemLicenseNodeLockedBundleInfoEntry 4 }

sonusSystemLicenseNodeLockedBundleInfoUsageLimit OBJECT-TYPE
    SYNTAX          INTEGER
    ACCESS          read-only
    STATUS          mandatory
    DESCRIPTION     
            "
             The count provisioned in this license
             "
    ::= { sonusSystemLicenseNodeLockedBundleInfoEntry 5 }

sonusSystemLicenseNodeLockedBundleInfoActiveLicenseMode OBJECT-TYPE
    SYNTAX          String (SIZE(0..255))
    ACCESS          read-only
    STATUS          mandatory
    DESCRIPTION     
            "
             The active licensing mode
             "
    ::= { sonusSystemLicenseNodeLockedBundleInfoEntry 13 }

sonusSystemBfdSessionStatsTable OBJECT-TYPE
    SYNTAX          SEQUENCE OF SonusSystemBfdSessionStatsEntry
    ACCESS          not-accessible
    STATUS          mandatory
    DESCRIPTION     
            "
             BFD session status
             "
    ::= { sonusSystem 58 }

sonusSystemBfdSessionStatsEntry OBJECT-TYPE
    SYNTAX          SonusSystemBfdSessionStatsEntry
    ACCESS          not-accessible
    STATUS          mandatory
    DESCRIPTION     
            ""
    INDEX           { sonusSystemBfdSessionStatsSessionId }
    ::= { sonusSystemBfdSessionStatsTable 1 }

SonusSystemBfdSessionStatsEntry ::=
    SEQUENCE {
        sonusSystemBfdSessionStatsSessionId   Gauge,
        sonusSystemBfdSessionStatsRemoteIP  BfdIpAddress,
        sonusSystemBfdSessionStatsLocalIP BfdIpAddress,
        sonusSystemBfdSessionStatsRemotePort    Gauge,
        sonusSystemBfdSessionStatsLocalPort   Gauge,
        sonusSystemBfdSessionStatsLifGroupId    Gauge,
        sonusSystemBfdSessionStatsAddrCntxtId     Gauge,
        sonusSystemBfdSessionStatsLocalDiscr    Gauge,
        sonusSystemBfdSessionStatsRemoteDiscr     Gauge,
        sonusSystemBfdSessionStatsSessionState      BfdSessionState,
        sonusSystemBfdSessionStatsTxPktCount    ConfdString,
        sonusSystemBfdSessionStatsRxPktCount    ConfdString,
        sonusSystemBfdSessionStatsDscp  Gauge,
        sonusSystemBfdSessionStatsLocalDiag   Gauge,
        sonusSystemBfdSessionStatsRemoteMinRxInterval             Gauge,
        sonusSystemBfdSessionStatsDetectTime    Gauge,
        sonusSystemBfdSessionStatsActiveDesiredMinTx            Gauge,
        sonusSystemBfdSessionStatsConnectType     String,
        sonusSystemBfdSessionStatsLinkId Gauge,
        sonusSystemBfdSessionStatsCreationTime      String,
        sonusSystemBfdSessionStatsUpLastTime    String,
        sonusSystemBfdSessionStatsDownLastTime      String
    }

sonusSystemBfdSessionStatsSessionId OBJECT-TYPE
    SYNTAX          Gauge
    ACCESS          not-accessible
    STATUS          mandatory
    DESCRIPTION     
            "
             Session Id
             "
    ::= { sonusSystemBfdSessionStatsEntry 1 }

sonusSystemBfdSessionStatsRemoteIP OBJECT-TYPE
    SYNTAX          BfdIpAddress
    ACCESS          read-only
    STATUS          mandatory
    DESCRIPTION     
            "
             The remote IP address for BFD session.
             "
    ::= { sonusSystemBfdSessionStatsEntry 2 }

sonusSystemBfdSessionStatsLocalIP OBJECT-TYPE
    SYNTAX          BfdIpAddress
    ACCESS          read-only
    STATUS          mandatory
    DESCRIPTION     
            "
             The local IP address for BFD session.
             "
    ::= { sonusSystemBfdSessionStatsEntry 3 }

sonusSystemBfdSessionStatsRemotePort OBJECT-TYPE
    SYNTAX          Gauge
    ACCESS          read-only
    STATUS          mandatory
    DESCRIPTION     
            "
             The remote port for BFD session
             "
    ::= { sonusSystemBfdSessionStatsEntry 4 }

sonusSystemBfdSessionStatsLocalPort OBJECT-TYPE
    SYNTAX          Gauge
    ACCESS          read-only
    STATUS          mandatory
    DESCRIPTION     
            "
             The local port for BFD session
             "
    ::= { sonusSystemBfdSessionStatsEntry 5 }

sonusSystemBfdSessionStatsLifGroupId OBJECT-TYPE
    SYNTAX          Gauge
    ACCESS          read-only
    STATUS          mandatory
    DESCRIPTION     
            "
             The LIF group for BFD session
             "
    ::= { sonusSystemBfdSessionStatsEntry 6 }

sonusSystemBfdSessionStatsAddrCntxtId OBJECT-TYPE
    SYNTAX          Gauge
    ACCESS          read-only
    STATUS          mandatory
    DESCRIPTION     
            "
             The addresscontext id for BFD session
             "
    ::= { sonusSystemBfdSessionStatsEntry 7 }

sonusSystemBfdSessionStatsLocalDiscr OBJECT-TYPE
    SYNTAX          Gauge
    ACCESS          read-only
    STATUS          mandatory
    DESCRIPTION     
            "
             The local discriminator for BFD session
             "
    ::= { sonusSystemBfdSessionStatsEntry 8 }

sonusSystemBfdSessionStatsRemoteDiscr OBJECT-TYPE
    SYNTAX          Gauge
    ACCESS          read-only
    STATUS          mandatory
    DESCRIPTION     
            "
             The remote discriminator for BFD session
             "
    ::= { sonusSystemBfdSessionStatsEntry 9 }

sonusSystemBfdSessionStatsSessionState OBJECT-TYPE
    SYNTAX          BfdSessionState
    ACCESS          read-only
    STATUS          mandatory
    DESCRIPTION     
            "
             The session State for BFD session
             "
    ::= { sonusSystemBfdSessionStatsEntry 10 }

sonusSystemBfdSessionStatsTxPktCount OBJECT-TYPE
    SYNTAX          ConfdString
    ACCESS          read-only
    STATUS          mandatory
    DESCRIPTION     
            "
             Total transmitted packets for BFD session
             "
    ::= { sonusSystemBfdSessionStatsEntry 11 }

sonusSystemBfdSessionStatsRxPktCount OBJECT-TYPE
    SYNTAX          ConfdString
    ACCESS          read-only
    STATUS          mandatory
    DESCRIPTION     
            "
             Total Received packets for BFD session
             "
    ::= { sonusSystemBfdSessionStatsEntry 12 }

sonusSystemBfdSessionStatsDscp OBJECT-TYPE
    SYNTAX          Gauge
    ACCESS          read-only
    STATUS          mandatory
    DESCRIPTION     
            "
             DSCP value for BFD session
             "
    ::= { sonusSystemBfdSessionStatsEntry 13 }

sonusSystemBfdSessionStatsLocalDiag OBJECT-TYPE
    SYNTAX          Gauge
    ACCESS          read-only
    STATUS          mandatory
    DESCRIPTION     
            "
             Diagnostic field for BFD session
             "
    ::= { sonusSystemBfdSessionStatsEntry 14 }

sonusSystemBfdSessionStatsRemoteMinRxInterval OBJECT-TYPE
    SYNTAX          Gauge
    ACCESS          read-only
    STATUS          mandatory
    DESCRIPTION     
            "
             Minimum interval to receive the pkt
             "
    ::= { sonusSystemBfdSessionStatsEntry 15 }

sonusSystemBfdSessionStatsDetectTime OBJECT-TYPE
    SYNTAX          Gauge
    ACCESS          read-only
    STATUS          mandatory
    DESCRIPTION     
            "
             Timeout for session
             "
    ::= { sonusSystemBfdSessionStatsEntry 16 }

sonusSystemBfdSessionStatsActiveDesiredMinTx OBJECT-TYPE
    SYNTAX          Gauge
    ACCESS          read-only
    STATUS          mandatory
    DESCRIPTION     
            "
             Minimum interval to transmit the pkts
             "
    ::= { sonusSystemBfdSessionStatsEntry 17 }

sonusSystemBfdSessionStatsConnectType OBJECT-TYPE
    SYNTAX          String (SIZE(0..255))
    ACCESS          read-only
    STATUS          mandatory
    DESCRIPTION     
            "
             Multihop | SingleHop
             "
    ::= { sonusSystemBfdSessionStatsEntry 18 }

sonusSystemBfdSessionStatsLinkId OBJECT-TYPE
    SYNTAX          Gauge
    ACCESS          read-only
    STATUS          mandatory
    DESCRIPTION     
            "
             Link detection id
             "
    ::= { sonusSystemBfdSessionStatsEntry 19 }

sonusSystemBfdSessionStatsCreationTime OBJECT-TYPE
    SYNTAX          String (SIZE(0..255))
    ACCESS          read-only
    STATUS          mandatory
    DESCRIPTION     
            "
             Session creation time
             "
    ::= { sonusSystemBfdSessionStatsEntry 20 }

sonusSystemBfdSessionStatsUpLastTime OBJECT-TYPE
    SYNTAX          String (SIZE(0..255))
    ACCESS          read-only
    STATUS          mandatory
    DESCRIPTION     
            "
             Up time for session
             "
    ::= { sonusSystemBfdSessionStatsEntry 21 }

sonusSystemBfdSessionStatsDownLastTime OBJECT-TYPE
    SYNTAX          String (SIZE(0..255))
    ACCESS          read-only
    STATUS          mandatory
    DESCRIPTION     
            "
             Down time for session
             "
    ::= { sonusSystemBfdSessionStatsEntry 22 }

END -- end of module SONUS-SYSTEM-MIB.
