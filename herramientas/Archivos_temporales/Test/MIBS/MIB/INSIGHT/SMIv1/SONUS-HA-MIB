--
-- This SMIv1 module has been generated by smidump 0.2-cvs. Do not edit.
--

SONUS-HA-MIB DEFINITIONS ::= BEGIN

IMPORTS
    InetAddress, InetAddressType
        FROM INET-ADDRESS-MIB
    OBJECT-TYPE
        FROM RFC-1212
    TRAP-TYPE
        FROM RFC-1215
    IpAddress
        FROM RFC1155-SMI
    sonusEventClass, sonusEventDescription, sonusEventLevel, 
    sonusEventTime
        FROM SONUS-COMMON-MIB
    sonusHostID
        FROM SONUS-HOST-MIB
    sonusServicesMIBs
        FROM SONUS-SMI;

sonusHAMIB OBJECT IDENTIFIER
    ::= { sonusServicesMIBs 17 }

-- sonusHAMIB MODULE-IDENTITY
--     LAST-UPDATED    "201307200000Z"
--     ORGANIZATION    
--             "Sonus Networks, Inc."
--     CONTACT-INFO    
--             "   Customer Support    
--              Sonus Networks, Inc.
--              250 Apollo Drive
--              Chelmsford, MA 01824
--              USA
--              
--              Tel: 978-614-8100
--              Fax: 978-614-8609"
--     DESCRIPTION     
--             "The MIB Module for Sonus High Availability Management."
--     ::= { sonusServicesMIBs 17 }


SonusHAState ::=
    INTEGER { unknown(0), active(1), active-intent(2), standby(3), 
                        standby-intent(4), standalone(5), suspended(6) }

-- SonusHAState ::= TEXTUAL-CONVENTION
--     STATUS          mandatory
--     DESCRIPTION     
--             "The high availability designation of the host.  This is an operational state."
--     SYNTAX          INTEGER
--                       { unknown(0), active(1), active-intent(2), 
--                         standby(3), standby-intent(4), standalone(5), 
--                         suspended(6) }

sonusHAMIBObjects OBJECT IDENTIFIER
    ::= { sonusHAMIB 1 }

sonusHAMIBNotifications OBJECT IDENTIFIER
    ::= { sonusHAMIB 2 }

sonusHAMIBNotificationsPrefix OBJECT IDENTIFIER
    ::= { sonusHAMIBNotifications 0 }

sonusHAMIBNotificationsObjects OBJECT IDENTIFIER
    ::= { sonusHAMIBNotifications 1 }

sonusHAResource OBJECT-TYPE
    SYNTAX          INTEGER { wellknownIp(1), network(2), disk(3), 
                        database(4) }
    ACCESS          read-only
    STATUS          mandatory
    DESCRIPTION     
            "A resource released by an active system and acquired by a standby system becoming active."
    ::= { sonusHAMIBNotificationsObjects 1 }

sonusHAPrevState OBJECT-TYPE
    SYNTAX          SonusHAState
    ACCESS          read-only
    STATUS          mandatory
    DESCRIPTION     
            "The previous high availability state of this host."
    ::= { sonusHAMIBNotificationsObjects 2 }

sonusHANewState OBJECT-TYPE
    SYNTAX          SonusHAState
    ACCESS          read-only
    STATUS          mandatory
    DESCRIPTION     
            "The new high availability state of this host."
    ::= { sonusHAMIBNotificationsObjects 3 }

sonusHAFailoverReason OBJECT-TYPE
    SYNTAX          INTEGER { unknown(0), user-initiated(1), 
                        oracleFailure(2), multipathFailure(3), 
                        raidFailure(4), processFailure(5) }
    ACCESS          read-write
    STATUS          mandatory
    DESCRIPTION     
            "The reason a failover process was initiated."
    ::= { sonusHAMIBNotificationsObjects 4 }

sonusHACurrentState OBJECT-TYPE
    SYNTAX          SonusHAState
    ACCESS          read-only
    STATUS          mandatory
    DESCRIPTION     
            "The present high availability state of this host."
    ::= { sonusHAMIBNotificationsObjects 5 }

sonusHAPeerIpAddress OBJECT-TYPE
    SYNTAX          IpAddress
    ACCESS          read-write
    STATUS          deprecated
    DESCRIPTION     
            "IP Address of the Softswitch - this is a required parameter."
    ::= { sonusHAMIBNotificationsObjects 6 }

sonusHAPeerExtendedIpAddressType OBJECT-TYPE
    SYNTAX          InetAddressType
    ACCESS          read-write
    STATUS          mandatory
    DESCRIPTION     
            "IP Address type of the Softswitch - this is a required parameter."
    ::= { sonusHAMIBNotificationsObjects 7 }

sonusHAPeerExtendedIpAddress OBJECT-TYPE
    SYNTAX          InetAddress
    ACCESS          read-write
    STATUS          mandatory
    DESCRIPTION     
            "IP Address of the Softswitch - this is a required parameter."
    ::= { sonusHAMIBNotificationsObjects 8 }

sonusHAFailoverInitiatedNotification TRAP-TYPE
    ENTERPRISE      sonusHAMIBNotifications
    VARIABLES       { sonusHAFailoverReason, sonusHostID, 
                      sonusEventDescription, sonusEventClass, 
                      sonusEventLevel, sonusEventTime }
--     STATUS          mandatory
    DESCRIPTION     
            "A failover process has been initiated due to the specified reason."
    ::= 1

sonusHAConnectToPeerFailureNotification TRAP-TYPE
    ENTERPRISE      sonusHAMIBNotifications
    VARIABLES       { sonusHostID, sonusHACurrentState, 
                      sonusHAPeerIpAddress, sonusEventDescription, 
                      sonusEventClass, sonusEventLevel, sonusEventTime }
--     STATUS          deprecated
    DESCRIPTION     
            "Failure to connect to peer."
    ::= 2

sonusHAConnectToPeerSuccessNotification TRAP-TYPE
    ENTERPRISE      sonusHAMIBNotifications
    VARIABLES       { sonusHostID, sonusHAPeerIpAddress, 
                      sonusEventDescription, sonusEventClass, 
                      sonusEventLevel, sonusEventTime }
--     STATUS          deprecated
    DESCRIPTION     
            "Successful connection to peer."
    ::= 3

sonusHAStateChangeNotification TRAP-TYPE
    ENTERPRISE      sonusHAMIBNotifications
    VARIABLES       { sonusHAPrevState, sonusHANewState, sonusHostID, 
                      sonusEventDescription, sonusEventClass, 
                      sonusEventLevel, sonusEventTime }
--     STATUS          mandatory
    DESCRIPTION     
            "The host's high availability state has changed."
    ::= 4

sonusHAResourceAcquireFailureNotification TRAP-TYPE
    ENTERPRISE      sonusHAMIBNotifications
    VARIABLES       { sonusHAResource, sonusHostID, 
                      sonusEventDescription, sonusEventClass, 
                      sonusEventLevel, sonusEventTime }
--     STATUS          mandatory
    DESCRIPTION     
            "The high availability component was unable to acquire the specified resource during a failover procedure."
    ::= 5

sonusHAResourceReleaseFailureNotification TRAP-TYPE
    ENTERPRISE      sonusHAMIBNotifications
    VARIABLES       { sonusHAResource, sonusHostID, 
                      sonusEventDescription, sonusEventClass, 
                      sonusEventLevel, sonusEventTime }
--     STATUS          mandatory
    DESCRIPTION     
            "The high availability component was unable to release the specified resource during a failover procedure."
    ::= 6

sonusHAHeartBeatFailureNotification TRAP-TYPE
    ENTERPRISE      sonusHAMIBNotifications
    VARIABLES       { sonusHostID, sonusEventDescription, 
                      sonusEventClass, sonusEventLevel, sonusEventTime }
--     STATUS          mandatory
    DESCRIPTION     
            "No response was received for a heartbeat request sent to the peer."
    ::= 7

sonusHAConnectToPeerFailureExtendedNotification TRAP-TYPE
    ENTERPRISE      sonusHAMIBNotifications
    VARIABLES       { sonusHostID, sonusHACurrentState, 
                      sonusHAPeerExtendedIpAddressType, 
                      sonusHAPeerExtendedIpAddress, 
                      sonusEventDescription, sonusEventClass, 
                      sonusEventLevel, sonusEventTime }
--     STATUS          mandatory
    DESCRIPTION     
            "Failure to connect to peer."
    ::= 8

sonusHAConnectToPeerSuccessExtendedNotification TRAP-TYPE
    ENTERPRISE      sonusHAMIBNotifications
    VARIABLES       { sonusHostID, sonusHAPeerExtendedIpAddressType, 
                      sonusHAPeerExtendedIpAddress, 
                      sonusEventDescription, sonusEventClass, 
                      sonusEventLevel, sonusEventTime }
--     STATUS          mandatory
    DESCRIPTION     
            "Successful connection to peer."
    ::= 9

END -- end of module SONUS-HA-MIB.
