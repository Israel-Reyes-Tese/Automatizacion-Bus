MIB-EMS-IPASOLINK-VR4-COMMON-MIB DEFINITIONS ::= BEGIN
    
    IMPORTS
        BridgeId
            FROM BRIDGE-MIB
        InterfaceIndex, InterfaceIndexOrZero
            FROM IF-MIB
        Ipv6Address
            FROM IPV6-TC
        OBJECT-TYPE
            FROM RFC-1212
        TRAP-TYPE
            FROM RFC-1215
        Counter, Gauge, IpAddress
            FROM RFC1155-SMI
        enterprises
            FROM SNMPv2-SMI
        DateAndTime, DisplayString, MacAddress, RowStatus, TruthValue
            FROM SNMPv2-TC;
    
    AlarmTypeValue ::=
        INTEGER { invalid(0), communicationsAlarm(1),
                        qualityOfServiceAlarm(2), processingErrorAlarm(3),
                        equipmentAlarm(4), environmentalAlarm(5),
                        integrityViolationAlarm(6),
                        operationalViolationAlarm(7),
                        physicalViolationAlarm(8), securityViolationAlarm(9),
                        timeDomainViolationAlarm(10) }
    
    
    EnableDisableValue ::=
        INTEGER { invalid(0), disable(1), enable(2) }
    
    
    IpeMepId ::=
        INTEGER (1..128)
    
    
    IpeStatsInfo ::=
        INTEGER { invalid(0), validNoMaint(1), validMaint(2),
                        invalidNoMaint(3), invalidMaint(4) }
    
    
    IpeUnsigned64 ::=
        Opaque (SIZE(4..12))
    
    
    IpeVlanIndexOrZero ::=
        INTEGER (0..4094)
    
    
    IpeVlanList ::=
        OCTET STRING (SIZE(512))
    
    
    IpeVlanListOrZero ::=
        OCTET STRING (SIZE(0 | 512))
    
    
    OffOnValue ::=
        INTEGER { invalid(0), off(1), on(2) }
    
    
    ProbableCauseValue ::=
        INTEGER { invalid(0), aIS(1), callSetUpFailure(2), degradedSignal(3),
                        farEndReceiverFailure(4), framingError(5),
                        lossOfFrame(6), lossOfPointer(7), lossOfSignal(8),
                        payloadTypeMismatch(9), transmissionError(10),
                        remoteAlarmInterface(11), excessiveBER(12),
                        pathTraceMismatch(13), unavailable(14),
                        signalLabelMismatch(15), lossOfMultiFrame(16),
                        receiveFailure(17), transmitFailure(18),
                        modulationFailure(19), demodulationFailure(20),
                        broadcastChannelFailure(21),
                        connectionEstablishmentError(22),
                        invalidMessageReceived(23),
                        localNodeTransmissionError(24),
                        remoteNodeTransmissionError(25), routingFailure(26),
                        backplaneFailure(51), dataSetProblem(52),
                        equipmentIdentifierDuplication(53),
                        externalIFDeviceProblem(54), lineCardProblem(55),
                        multiplexerProblem(56), nEIdentifierDuplication(57),
                        powerProblem(58), processorProblem(59),
                        protectionPathFailure(60), receiverFailure(61),
                        replaceableUnitMissing(62),
                        replaceableUnitTypeMismatch(63),
                        synchronizationSourceMismatch(64),
                        terminalProblem(65), timingProblem(66),
                        transmitterFailure(67), trunkCardProblem(68),
                        replaceableUnitProblem(69), realTimeClockFailure(70),
                        antennaFailure(71), batteryChargingFailure(72),
                        diskFailure(73), frequencyHoppingFailure(74),
                        iODeviceError(75), lossOfSynchronisation(76),
                        lossOfRedundancy(77), powerSupplyFailure(78),
                        signalQualityEvaluationFailure(79),
                        tranceiverFailure(80),
                        protectionMechanismFailure(81),
                        protectingResourceFailure(82),
                        airCompressorFailure(101),
                        airConditioningFailure(102), airDryerFailure(103),
                        batteryDischarging(104), batteryFailure(105),
                        commercialPowerFailure(106), coolingFanFailure(107),
                        engineFailure(108), fireDetectorFailure(109),
                        fuseFailure(110), generatorFailure(111),
                        lowBatteryThreshold(112), pumpFailure(113),
                        rectifierFailure(114), rectifierHighVoltage(115),
                        rectifierLowFVoltage(116),
                        ventilationsSystemFailure(117),
                        enclosureDoorOpen(118), explosiveGas(119), fire(120),
                        flood(121), highHumidity(122), highTemperature(123),
                        highWind(124), iceBuildUp(125),
                        intrusionDetection(126), lowFuel(127),
                        lowHumidity(128), lowCablePressure(129),
                        lowTemperatue(130), lowWater(131), smoke(132),
                        toxicGas(133), coolingSystemFailure(134),
                        externalEquipmentFailure(135),
                        externalPointFailure(136),
                        storageCapacityProblem(151), memoryMismatch(152),
                        corruptData(153), outOfCPUCycles(154),
                        sfwrEnvironmentProblem(155),
                        sfwrDownloadFailure(156), lossOfRealTimel(157),
                        applicationSubsystemFailure(158),
                        configurationOrCustomisationError(159),
                        databaseInconsistency(160), fileError(161),
                        outOfMemory(162), softwareError(163),
                        timeoutExpired(164),
                        underlayingResourceUnavailable(165),
                        versionMismatch(166), bandwidthReduced(201),
                        congestion(202), excessiveErrorRate(203),
                        excessiveResponseTime(204),
                        excessiveRetransmissionRate(205),
                        reducedLoggingCapability(206),
                        systemResourcesOverload(207), adapterError(500),
                        applicationSubsystemFailture(501),
                        bandwidthReducedX733(502),
                        callEstablishmentError(503),
                        communicationsProtocolError(504),
                        communicationsSubsystemFailure(505),
                        configurationOrCustomizationError(506),
                        congestionX733(507), coruptData(508),
                        cpuCyclesLimitExceeded(509),
                        dataSetOrModemError(510), degradedSignalX733(511),
                        dteDceInterfaceError(512),
                        enclosureDoorOpenX733(513),
                        equipmentMalfunction(514), excessiveVibration(515),
                        fileErrorX733(516), fireDetected(517),
                        framingErrorX733(518),
                        heatingVentCoolingSystemProblem(519),
                        humidityUnacceptable(520),
                        inputOutputDeviceError(521), inputDeviceError(522),
                        lanError(523), leakDetected(524),
                        localNodeTransmissionErrorX733(525),
                        lossOfFrameX733(526), lossOfSignalX733(527),
                        materialSupplyExhausted(528),
                        multiplexerProblemX733(529), outOfMemoryX733(530),
                        ouputDeviceError(531), performanceDegraded(532),
                        powerProblems(533), pressureUnacceptable(534),
                        processorProblems(535), pumpFailureX733(536),
                        queueSizeExceeded(537), receiveFailureX733(538),
                        receiverFailureX733(539),
                        remoteNodeTransmissionErrorX733(540),
                        resourceAtOrNearingCapacity(541),
                        responseTimeExecessive(542),
                        retransmissionRateExcessive(543),
                        softwareErrorX733(544),
                        softwareProgramAbnormallyTerminated(545),
                        softwareProgramError(546),
                        storageCapacityProblemX733(547),
                        temperatureUnacceptable(548), thresholdCrossed(549),
                        timingProblemX733(550), toxicLeakDetected(551),
                        transmitFailureX733(552), transmiterFailure(553),
                        underlyingResourceUnavailable(554),
                        versionMismatchX733(555), authenticationFailure(600),
                        breachOfConfidentiality(601), cableTamper(602),
                        delayedInformation(603), denialOfService(604),
                        duplicateInformation(605), informationMissing(606),
                        informationModificationDetected(607),
                        informationOutOfSequence(608), keyExpired(609),
                        nonRepudiationFailure(610), outOfHoursActivity(611),
                        outOfService(612), proceduralError(613),
                        unauthorizedAccessAttempt(614),
                        unexpectedInformation(615), other(1024) }
    
    
    ReportNotreportValue ::=
        INTEGER { invalid(0), notReport(1), report(2) }
    
    
    SeverityValue ::=
        INTEGER { cleared(1), indetermine(2), critical(3), major(4),
                        minor(5), warning(6), notReport(7) }
    
    
    UsedNotusedValue ::=
        INTEGER { invalid(0), notUsed(1), used(2) }
    
    
    ValidInvalidValue ::=
        INTEGER { invalid(0), valid(1) }
    
    
    -- 1.3.6.1.4.1.119
    nec OBJECT IDENTIFIER
        ::= { enterprises 119 }
    
    -- 1.3.6.1.4.1.119.2
    nec-mib OBJECT IDENTIFIER
        ::= { nec 2 }
    
    -- 1.3.6.1.4.1.119.2.3
    necProductDepend OBJECT IDENTIFIER
        ::= { nec-mib 3 }
    
    -- 1.3.6.1.4.1.119.2.3.69
    radioEquipment OBJECT IDENTIFIER
        ::= { necProductDepend 69 }
    
    -- 1.3.6.1.4.1.119.2.3.69.203
    commonPnms OBJECT IDENTIFIER
        ::= { radioEquipment 203 }
    
    -- 1.3.6.1.4.1.119.2.3.69.203.513
    ipasolinkVr4 OBJECT IDENTIFIER
        ::= { commonPnms 513 }
    
    -- 1.3.6.1.4.1.119.2.3.69.203.513.501
    pasoNeoIpe-common OBJECT IDENTIFIER
        ::= { ipasolinkVr4 501 }
    
    -- 1.3.6.1.4.1.119.2.3.69.203.513.501.1
    summaryGroup OBJECT IDENTIFIER
        ::= { pasoNeoIpe-common 1 }
    
    -- 1.3.6.1.4.1.119.2.3.69.203.513.501.1.1
    alarmSummaryGroup OBJECT IDENTIFIER
        ::= { summaryGroup 1 }
    
    -- 1.3.6.1.4.1.119.2.3.69.203.513.501.1.1.1
    alarmSummaryCommonInfoTable OBJECT-TYPE
        SYNTAX      SEQUENCE OF AlarmSummaryCommonInfoEntry
        ACCESS      not-accessible
        STATUS      mandatory
        DESCRIPTION
            "Alarm Summary Table.
             Alarm Summary objects represents the maximum severity value of
             raised alarms of the entity."
        ::= { alarmSummaryGroup 1 }
    
    -- 1.3.6.1.4.1.119.2.3.69.203.513.501.1.1.1.1
    alarmSummaryCommonInfoEntry OBJECT-TYPE
        SYNTAX      AlarmSummaryCommonInfoEntry
        ACCESS      not-accessible
        STATUS      mandatory
        DESCRIPTION
            ""
        INDEX       { alarmSummaryCommonInfoNEAddress, alarmSummaryCommonInfoIndex }
        ::= { alarmSummaryCommonInfoTable 1 }
    
    AlarmSummaryCommonInfoEntry ::= SEQUENCE {
        alarmSummaryCommonInfoIndex         INTEGER,
        alarmSummaryCommonInfoNEAddress     IpAddress,
        alarmTotalSummary                   SeverityValue,
        alarmIduSummary                     SeverityValue,
        alarmCtrlSummary                    SeverityValue,
        alarmOduSummary                     SeverityValue,
        alarmAuxInputSummary                SeverityValue,
        alarmPmonTcnSummary                 SeverityValue,
        alarmRmonTcnSummary                 SeverityValue,
        alarmRmonTcnCtrlSummary             SeverityValue
    }
    
    -- 1.3.6.1.4.1.119.2.3.69.203.513.501.1.1.1.1.1
    alarmSummaryCommonInfoIndex OBJECT-TYPE
        SYNTAX      INTEGER (1)
        ACCESS      not-accessible
        STATUS      mandatory
        DESCRIPTION
            "Index of this table"
        ::= { alarmSummaryCommonInfoEntry 1 }
    
    -- 1.3.6.1.4.1.119.2.3.69.203.513.501.1.1.1.1.2
    alarmSummaryCommonInfoNEAddress OBJECT-TYPE
        SYNTAX      IpAddress
        ACCESS      not-accessible
        STATUS      mandatory
        DESCRIPTION
            "reserved"
        ::= { alarmSummaryCommonInfoEntry 2 }
    
    -- 1.3.6.1.4.1.119.2.3.69.203.513.501.1.1.1.1.3
    alarmTotalSummary OBJECT-TYPE
        SYNTAX      SeverityValue
        ACCESS      read-only
        STATUS      mandatory
        DESCRIPTION
            "Total Summary Alarm."
        ::= { alarmSummaryCommonInfoEntry 3 }
    
    -- 1.3.6.1.4.1.119.2.3.69.203.513.501.1.1.1.1.4
    alarmIduSummary OBJECT-TYPE
        SYNTAX      SeverityValue
        ACCESS      read-only
        STATUS      mandatory
        DESCRIPTION
            "IDU Summary Alarm."
        ::= { alarmSummaryCommonInfoEntry 4 }
    
    -- 1.3.6.1.4.1.119.2.3.69.203.513.501.1.1.1.1.5
    alarmCtrlSummary OBJECT-TYPE
        SYNTAX      SeverityValue
        ACCESS      read-only
        STATUS      mandatory
        DESCRIPTION
            "Main Board / Ctrl Card Summary Alarm (including Equipment clock
             alarms)"
        ::= { alarmSummaryCommonInfoEntry 5 }
    
    -- 1.3.6.1.4.1.119.2.3.69.203.513.501.1.1.1.1.6
    alarmOduSummary OBJECT-TYPE
        SYNTAX      SeverityValue
        ACCESS      read-only
        STATUS      mandatory
        DESCRIPTION
            "ODU Summary Alarm."
        ::= { alarmSummaryCommonInfoEntry 6 }
    
    -- 1.3.6.1.4.1.119.2.3.69.203.513.501.1.1.1.1.7
    alarmAuxInputSummary OBJECT-TYPE
        SYNTAX      SeverityValue
        ACCESS      read-only
        STATUS      mandatory
        DESCRIPTION
            "AUX Input Summary Alarm."
        ::= { alarmSummaryCommonInfoEntry 7 }
    
    -- 1.3.6.1.4.1.119.2.3.69.203.513.501.1.1.1.1.8
    alarmPmonTcnSummary OBJECT-TYPE
        SYNTAX      SeverityValue
        ACCESS      read-only
        STATUS      mandatory
        DESCRIPTION
            "PMON TCN Summary Alarm."
        ::= { alarmSummaryCommonInfoEntry 8 }
    
    -- 1.3.6.1.4.1.119.2.3.69.203.513.501.1.1.1.1.9
    alarmRmonTcnSummary OBJECT-TYPE
        SYNTAX      SeverityValue
        ACCESS      read-only
        STATUS      mandatory
        DESCRIPTION
            "RMON TCN Summary Alarm."
        ::= { alarmSummaryCommonInfoEntry 9 }
    
    -- 1.3.6.1.4.1.119.2.3.69.203.513.501.1.1.1.1.10
    alarmRmonTcnCtrlSummary OBJECT-TYPE
        SYNTAX      SeverityValue
        ACCESS      read-only
        STATUS      mandatory
        DESCRIPTION
            "RMON TCN Main Board / Ctrl Card Summary Alarm."
        ::= { alarmSummaryCommonInfoEntry 10 }
    
    -- 1.3.6.1.4.1.119.2.3.69.203.513.501.1.1.2
    alarmSummaryIduGroup OBJECT IDENTIFIER
        ::= { alarmSummaryGroup 2 }
    
    -- 1.3.6.1.4.1.119.2.3.69.203.513.501.1.1.2.1
    alarmSummaryIduSlotInfoTable OBJECT-TYPE
        SYNTAX      SEQUENCE OF AlarmSummaryIduSlotInfoEntry
        ACCESS      not-accessible
        STATUS      mandatory
        DESCRIPTION
            "Alarm Summary per IDU Slot."
        ::= { alarmSummaryIduGroup 1 }
    
    -- 1.3.6.1.4.1.119.2.3.69.203.513.501.1.1.2.1.1
    alarmSummaryIduSlotInfoEntry OBJECT-TYPE
        SYNTAX      AlarmSummaryIduSlotInfoEntry
        ACCESS      not-accessible
        STATUS      mandatory
        DESCRIPTION
            ""
        INDEX       { alarmSummaryIduSlotInfoNEAddress, alarmSummaryIduSlotInfoIndex }
        ::= { alarmSummaryIduSlotInfoTable 1 }
    
    AlarmSummaryIduSlotInfoEntry ::= SEQUENCE {
        alarmSummaryIduSlotInfoIndex        INTEGER,
        alarmSummaryIduSlotInfoNEAddress    IpAddress,
        alarmIduSlotSummary                 SeverityValue
    }
    
    -- 1.3.6.1.4.1.119.2.3.69.203.513.501.1.1.2.1.1.1
    alarmSummaryIduSlotInfoIndex OBJECT-TYPE
        SYNTAX      INTEGER
        ACCESS      not-accessible
        STATUS      mandatory
        DESCRIPTION
            "Index of this table."
        ::= { alarmSummaryIduSlotInfoEntry 1 }
    
    -- 1.3.6.1.4.1.119.2.3.69.203.513.501.1.1.2.1.1.2
    alarmSummaryIduSlotInfoNEAddress OBJECT-TYPE
        SYNTAX      IpAddress
        ACCESS      not-accessible
        STATUS      mandatory
        DESCRIPTION
            "reserved."
        ::= { alarmSummaryIduSlotInfoEntry 2 }
    
    -- 1.3.6.1.4.1.119.2.3.69.203.513.501.1.1.2.1.1.3
    alarmIduSlotSummary OBJECT-TYPE
        SYNTAX      SeverityValue
        ACCESS      read-only
        STATUS      mandatory
        DESCRIPTION
            "IDU Slot Summary Alarm. the maximum severity value of raised
             alarms per slot."
        ::= { alarmSummaryIduSlotInfoEntry 3 }
    
    -- 1.3.6.1.4.1.119.2.3.69.203.513.501.1.1.2.2
    alarmSummaryIduSwGrpInfoTable OBJECT-TYPE
        SYNTAX      SEQUENCE OF AlarmSummaryIduSwGrpInfoEntry
        ACCESS      not-accessible
        STATUS      mandatory
        DESCRIPTION
            "Alarm Summary per MODEM Switch group."
        ::= { alarmSummaryIduGroup 2 }
    
    -- 1.3.6.1.4.1.119.2.3.69.203.513.501.1.1.2.2.1
    alarmSummaryIduSwGrpInfoEntry OBJECT-TYPE
        SYNTAX      AlarmSummaryIduSwGrpInfoEntry
        ACCESS      not-accessible
        STATUS      mandatory
        DESCRIPTION
            ""
        INDEX       { alarmSummaryIduSwGrpInfoNEAddress, alarmSummaryIduSwGrpInfoIndex }
        ::= { alarmSummaryIduSwGrpInfoTable 1 }
    
    AlarmSummaryIduSwGrpInfoEntry ::= SEQUENCE {
        alarmSummaryIduSwGrpInfoIndex       INTEGER,
        alarmSummaryIduSwGrpInfoNEAddress   IpAddress,
        alarmIduSwGrpSummary                SeverityValue
    }
    
    -- 1.3.6.1.4.1.119.2.3.69.203.513.501.1.1.2.2.1.1
    alarmSummaryIduSwGrpInfoIndex OBJECT-TYPE
        SYNTAX      INTEGER
        ACCESS      not-accessible
        STATUS      mandatory
        DESCRIPTION
            "Index of this table."
        ::= { alarmSummaryIduSwGrpInfoEntry 1 }
    
    -- 1.3.6.1.4.1.119.2.3.69.203.513.501.1.1.2.2.1.2
    alarmSummaryIduSwGrpInfoNEAddress OBJECT-TYPE
        SYNTAX      IpAddress
        ACCESS      not-accessible
        STATUS      mandatory
        DESCRIPTION
            "reserved."
        ::= { alarmSummaryIduSwGrpInfoEntry 2 }
    
    -- 1.3.6.1.4.1.119.2.3.69.203.513.501.1.1.2.2.1.3
    alarmIduSwGrpSummary OBJECT-TYPE
        SYNTAX      SeverityValue
        ACCESS      read-only
        STATUS      mandatory
        DESCRIPTION
            "IDU SW Group Summary Alarm. the maximum severity value of raised
             alarms per MODEM Switch group."
        ::= { alarmSummaryIduSwGrpInfoEntry 3 }
    
    -- 1.3.6.1.4.1.119.2.3.69.203.513.501.1.1.3
    alarmSummaryOduInfoTable OBJECT-TYPE
        SYNTAX      SEQUENCE OF AlarmSummaryOduInfoEntry
        ACCESS      not-accessible
        STATUS      mandatory
        DESCRIPTION
            "Alarm Summary per ODU."
        ::= { alarmSummaryGroup 3 }
    
    -- 1.3.6.1.4.1.119.2.3.69.203.513.501.1.1.3.1
    alarmSummaryOduInfoEntry OBJECT-TYPE
        SYNTAX      AlarmSummaryOduInfoEntry
        ACCESS      not-accessible
        STATUS      mandatory
        DESCRIPTION
            ""
        INDEX       { alarmSummaryOduInfoNEAddress, alarmSummaryOduInfoIndex }
        ::= { alarmSummaryOduInfoTable 1 }
    
    AlarmSummaryOduInfoEntry ::= SEQUENCE {
        alarmSummaryOduInfoIndex        INTEGER,
        alarmSummaryOduInfoNEAddress    IpAddress,
        alarmOduEachSummary             SeverityValue
    }
    
    -- 1.3.6.1.4.1.119.2.3.69.203.513.501.1.1.3.1.1
    alarmSummaryOduInfoIndex OBJECT-TYPE
        SYNTAX      INTEGER
        ACCESS      not-accessible
        STATUS      mandatory
        DESCRIPTION
            "Index of this table"
        ::= { alarmSummaryOduInfoEntry 1 }
    
    -- 1.3.6.1.4.1.119.2.3.69.203.513.501.1.1.3.1.2
    alarmSummaryOduInfoNEAddress OBJECT-TYPE
        SYNTAX      IpAddress
        ACCESS      not-accessible
        STATUS      mandatory
        DESCRIPTION
            "reserved"
        ::= { alarmSummaryOduInfoEntry 2 }
    
    -- 1.3.6.1.4.1.119.2.3.69.203.513.501.1.1.3.1.3
    alarmOduEachSummary OBJECT-TYPE
        SYNTAX      SeverityValue
        ACCESS      read-only
        STATUS      mandatory
        DESCRIPTION
            "ODU Each Summary Alarm. the maximum severity value of raised
             alarms per ODU."
        ::= { alarmSummaryOduInfoEntry 3 }
    
    -- 1.3.6.1.4.1.119.2.3.69.203.513.501.1.1.4
    alarmSummaryPmonTcnInfoTable OBJECT-TYPE
        SYNTAX      SEQUENCE OF AlarmSummaryPmonTcnInfoEntry
        ACCESS      not-accessible
        STATUS      mandatory
        DESCRIPTION
            "Alarm Summay of Threshold Crossing Alarms per Slot."
        ::= { alarmSummaryGroup 4 }
    
    -- 1.3.6.1.4.1.119.2.3.69.203.513.501.1.1.4.1
    alarmSummaryPmonTcnInfoEntry OBJECT-TYPE
        SYNTAX      AlarmSummaryPmonTcnInfoEntry
        ACCESS      not-accessible
        STATUS      mandatory
        DESCRIPTION
            ""
        INDEX       { alarmSummaryPmonTcnInfoNEAddress, alarmSummaryPmonTcnInfoIndex }
        ::= { alarmSummaryPmonTcnInfoTable 1 }
    
    AlarmSummaryPmonTcnInfoEntry ::= SEQUENCE {
        alarmSummaryPmonTcnInfoIndex        INTEGER,
        alarmSummaryPmonTcnInfoNEAddress    IpAddress,
        alarmPmonTcnSlotSummary             SeverityValue
    }
    
    -- 1.3.6.1.4.1.119.2.3.69.203.513.501.1.1.4.1.1
    alarmSummaryPmonTcnInfoIndex OBJECT-TYPE
        SYNTAX      INTEGER
        ACCESS      not-accessible
        STATUS      mandatory
        DESCRIPTION
            "Index of this table."
        ::= { alarmSummaryPmonTcnInfoEntry 1 }
    
    -- 1.3.6.1.4.1.119.2.3.69.203.513.501.1.1.4.1.2
    alarmSummaryPmonTcnInfoNEAddress OBJECT-TYPE
        SYNTAX      IpAddress
        ACCESS      not-accessible
        STATUS      mandatory
        DESCRIPTION
            "reserved"
        ::= { alarmSummaryPmonTcnInfoEntry 2 }
    
    -- 1.3.6.1.4.1.119.2.3.69.203.513.501.1.1.4.1.3
    alarmPmonTcnSlotSummary OBJECT-TYPE
        SYNTAX      SeverityValue
        ACCESS      read-only
        STATUS      mandatory
        DESCRIPTION
            "PMON (TCN) Slot Summary Alarm. the maximum severity value of
             raised Threshold Crossing Alarms per slot."
        ::= { alarmSummaryPmonTcnInfoEntry 3 }
    
    -- 1.3.6.1.4.1.119.2.3.69.203.513.501.1.1.5
    alarmSummaryCtrlInfoTable OBJECT-TYPE
        SYNTAX      SEQUENCE OF AlarmSummaryCtrlInfoEntry
        ACCESS      not-accessible
        STATUS      mandatory
        DESCRIPTION
            "Alarm Summary of Main Board or Ctrl Card."
        ::= { alarmSummaryGroup 5 }
    
    -- 1.3.6.1.4.1.119.2.3.69.203.513.501.1.1.5.1
    alarmSummaryCtrlInfoEntry OBJECT-TYPE
        SYNTAX      AlarmSummaryCtrlInfoEntry
        ACCESS      not-accessible
        STATUS      mandatory
        DESCRIPTION
            ""
        INDEX       { alarmSummaryEoamInfoNEAddress, alarmSummaryEoamInfoIndex }
        ::= { alarmSummaryCtrlInfoTable 1 }
    
    AlarmSummaryCtrlInfoEntry ::= SEQUENCE {
        alarmSummaryEoamInfoIndex       INTEGER,
        alarmSummaryEoamInfoNEAddress   IpAddress,
        alarmEoamSummary                SeverityValue,
        alarmRmonEoamSummary            SeverityValue
    }
    
    -- 1.3.6.1.4.1.119.2.3.69.203.513.501.1.1.5.1.1
    alarmSummaryEoamInfoIndex OBJECT-TYPE
        SYNTAX      INTEGER (1)
        ACCESS      not-accessible
        STATUS      mandatory
        DESCRIPTION
            "Index of this table."
        ::= { alarmSummaryCtrlInfoEntry 1 }
    
    -- 1.3.6.1.4.1.119.2.3.69.203.513.501.1.1.5.1.2
    alarmSummaryEoamInfoNEAddress OBJECT-TYPE
        SYNTAX      IpAddress
        ACCESS      not-accessible
        STATUS      mandatory
        DESCRIPTION
            "reserved"
        ::= { alarmSummaryCtrlInfoEntry 2 }
    
    -- 1.3.6.1.4.1.119.2.3.69.203.513.501.1.1.5.1.3
    alarmEoamSummary OBJECT-TYPE
        SYNTAX      SeverityValue
        ACCESS      read-only
        STATUS      mandatory
        DESCRIPTION
            "ETH-OAM including MPLS-TP OAM Summary Alarm. The maximum
             severity value of raised alarms which are related to EtherOAM
             functions."
        ::= { alarmSummaryCtrlInfoEntry 3 }
    
    -- 1.3.6.1.4.1.119.2.3.69.203.513.501.1.1.5.1.4
    alarmRmonEoamSummary OBJECT-TYPE
        SYNTAX      SeverityValue
        ACCESS      read-only
        STATUS      mandatory
        DESCRIPTION
            "RMON ETH-OAM including MPLS-TP OAM Summary Alarm. The maximum
             severity value of raised alarms which are related to EtherOAM
             Threshold Crossing Alarms."
        ::= { alarmSummaryCtrlInfoEntry 4 }
    
    -- 1.3.6.1.4.1.119.2.3.69.203.513.501.1.1.6
    alarmSummaryRmonTcnInfoTable OBJECT-TYPE
        SYNTAX      SEQUENCE OF AlarmSummaryRmonTcnInfoEntry
        ACCESS      not-accessible
        STATUS      mandatory
        DESCRIPTION
            "Alarm summary of RMON Threshold Crossing Alarms per slot."
        ::= { alarmSummaryGroup 6 }
    
    -- 1.3.6.1.4.1.119.2.3.69.203.513.501.1.1.6.1
    alarmSummaryRmonTcnInfoEntry OBJECT-TYPE
        SYNTAX      AlarmSummaryRmonTcnInfoEntry
        ACCESS      not-accessible
        STATUS      mandatory
        DESCRIPTION
            ""
        INDEX       { alarmSummaryRmonTcnInfoNEAddress, alarmSummaryRmonTcnInfoIndex }
        ::= { alarmSummaryRmonTcnInfoTable 1 }
    
    AlarmSummaryRmonTcnInfoEntry ::= SEQUENCE {
        alarmSummaryRmonTcnInfoIndex        INTEGER,
        alarmSummaryRmonTcnInfoNEAddress    IpAddress,
        alarmRmonTcnSlotSummary             SeverityValue
    }
    
    -- 1.3.6.1.4.1.119.2.3.69.203.513.501.1.1.6.1.1
    alarmSummaryRmonTcnInfoIndex OBJECT-TYPE
        SYNTAX      INTEGER
        ACCESS      not-accessible
        STATUS      mandatory
        DESCRIPTION
            "Index of this table."
        ::= { alarmSummaryRmonTcnInfoEntry 1 }
    
    -- 1.3.6.1.4.1.119.2.3.69.203.513.501.1.1.6.1.2
    alarmSummaryRmonTcnInfoNEAddress OBJECT-TYPE
        SYNTAX      IpAddress
        ACCESS      not-accessible
        STATUS      mandatory
        DESCRIPTION
            "reserved."
        ::= { alarmSummaryRmonTcnInfoEntry 2 }
    
    -- 1.3.6.1.4.1.119.2.3.69.203.513.501.1.1.6.1.3
    alarmRmonTcnSlotSummary OBJECT-TYPE
        SYNTAX      SeverityValue
        ACCESS      read-only
        STATUS      mandatory
        DESCRIPTION
            "RMON (TCN) Slot Summary Alarm. The maximum value of raised
             alarms which are related RMON Threshold Crossing Alarm."
        ::= { alarmSummaryRmonTcnInfoEntry 3 }
    
    -- 1.3.6.1.4.1.119.2.3.69.203.513.501.1.2
    maintSummaryGroup OBJECT IDENTIFIER
        ::= { summaryGroup 2 }
    
    -- 1.3.6.1.4.1.119.2.3.69.203.513.501.1.2.1
    maintSummaryCommonInfoTable OBJECT-TYPE
        SYNTAX      SEQUENCE OF MaintSummaryCommonInfoEntry
        ACCESS      not-accessible
        STATUS      mandatory
        DESCRIPTION
            "This table represents the status of maintenance functions."
        ::= { maintSummaryGroup 1 }
    
    -- 1.3.6.1.4.1.119.2.3.69.203.513.501.1.2.1.1
    maintSummaryCommonInfoEntry OBJECT-TYPE
        SYNTAX      MaintSummaryCommonInfoEntry
        ACCESS      not-accessible
        STATUS      mandatory
        DESCRIPTION
            ""
        INDEX       { maintSummaryCommonInfoNEAddress, maintSummaryCommonInfoIndex }
        ::= { maintSummaryCommonInfoTable 1 }
    
    MaintSummaryCommonInfoEntry ::= SEQUENCE {
        maintSummaryCommonInfoIndex         INTEGER,
        maintSummaryCommonInfoNEAddress     IpAddress,
        maintTotalSummary                   OffOnValue
    }
    
    -- 1.3.6.1.4.1.119.2.3.69.203.513.501.1.2.1.1.1
    maintSummaryCommonInfoIndex OBJECT-TYPE
        SYNTAX      INTEGER (1)
        ACCESS      not-accessible
        STATUS      mandatory
        DESCRIPTION
            "Index of this table."
        ::= { maintSummaryCommonInfoEntry 1 }
    
    -- 1.3.6.1.4.1.119.2.3.69.203.513.501.1.2.1.1.2
    maintSummaryCommonInfoNEAddress OBJECT-TYPE
        SYNTAX      IpAddress
        ACCESS      not-accessible
        STATUS      mandatory
        DESCRIPTION
            "reserved"
        ::= { maintSummaryCommonInfoEntry 2 }
    
    -- 1.3.6.1.4.1.119.2.3.69.203.513.501.1.2.1.1.3
    maintTotalSummary OBJECT-TYPE
        SYNTAX      OffOnValue
        ACCESS      read-only
        STATUS      mandatory
        DESCRIPTION
            "Maintenance Total Summary. Represents the status of maintenance
             functions.
             'on' means some maintenance functions are performed on this
             equipment."
        ::= { maintSummaryCommonInfoEntry 3 }
    
    -- 1.3.6.1.4.1.119.2.3.69.203.513.501.2
    trapGroup OBJECT IDENTIFIER
        ::= { pasoNeoIpe-common 2 }
    
    -- 1.3.6.1.4.1.119.2.3.69.203.513.501.2.1
    ipeTrapCommon OBJECT IDENTIFIER
        ::= { trapGroup 1 }
    
    -- 1.3.6.1.4.1.119.2.3.69.203.513.501.2.1.1
    ipeTrapCommonVars OBJECT IDENTIFIER
        ::= { ipeTrapCommon 1 }
    
    -- 1.3.6.1.4.1.119.2.3.69.203.513.501.2.1.1.1
    eventTotalCount OBJECT-TYPE
        SYNTAX      Counter
        ACCESS      read-only
        STATUS      mandatory
        DESCRIPTION
            "The total count of SNMP TRAP/INFORM messages since this
             equipment was booted"
        ::= { ipeTrapCommonVars 1 }
    
    -- 1.3.6.1.4.1.119.2.3.69.203.513.501.2.1.1.2
    eventCount OBJECT-TYPE
        SYNTAX      Counter
        ACCESS      read-only
        STATUS      mandatory
        DESCRIPTION
            "The count of SNMP TRAP/INFORM messages per event type
             (alarm/status/control) since this equipment was booted."
        ::= { ipeTrapCommonVars 2 }
    
    -- 1.3.6.1.4.1.119.2.3.69.203.513.501.2.1.1.3
    eventTime OBJECT-TYPE
        SYNTAX      DateAndTime
        ACCESS      read-only
        STATUS      mandatory
        DESCRIPTION
            "The local date and time when the TRAP/INFORM event occurred."
        ::= { ipeTrapCommonVars 3 }
    
    -- 1.3.6.1.4.1.119.2.3.69.203.513.501.2.1.1.4
    eventType OBJECT-TYPE
        SYNTAX      INTEGER { alarmStateChage(1), statusChange(2),
                        controlEvent(3) }
        ACCESS      read-only
        STATUS      mandatory
        DESCRIPTION
            "The event type of TRAP/INFORM message."
        ::= { ipeTrapCommonVars 4 }
    
    -- 1.3.6.1.4.1.119.2.3.69.203.513.501.2.1.1.5
    eventResourceID OBJECT-TYPE
        SYNTAX      OBJECT IDENTIFIER
        ACCESS      read-only
        STATUS      mandatory
        DESCRIPTION
            "The OBJECT IDENTIFIER of the object which raised the event."
        ::= { ipeTrapCommonVars 5 }
    
    -- 1.3.6.1.4.1.119.2.3.69.203.513.501.2.1.2
    ipeTrapCommonAdditionalVars OBJECT IDENTIFIER
        ::= { ipeTrapCommon 2 }
    
    -- 1.3.6.1.4.1.119.2.3.69.203.513.501.2.1.2.1
    eventAdditionalText1 OBJECT-TYPE
        SYNTAX      DisplayString
        ACCESS      read-only
        STATUS      mandatory
        DESCRIPTION
            "Additional Information about the TRAP/INFORM event."
        ::= { ipeTrapCommonAdditionalVars 1 }
    
    -- 1.3.6.1.4.1.119.2.3.69.203.513.501.2.1.2.2
    eventAdditionalText2 OBJECT-TYPE
        SYNTAX      DisplayString
        ACCESS      read-only
        STATUS      mandatory
        DESCRIPTION
            "Additional Information about the TRAP/INFORM event."
        ::= { ipeTrapCommonAdditionalVars 2 }
    
    -- 1.3.6.1.4.1.119.2.3.69.203.513.501.2.1.2.3
    eventAdditionalText3 OBJECT-TYPE
        SYNTAX      DisplayString
        ACCESS      read-only
        STATUS      mandatory
        DESCRIPTION
            "Additional Information about the TRAP/INFORM event."
        ::= { ipeTrapCommonAdditionalVars 3 }
    
    -- 1.3.6.1.4.1.119.2.3.69.203.513.501.2.1.2.4
    eventAdditionalText4 OBJECT-TYPE
        SYNTAX      DisplayString
        ACCESS      read-only
        STATUS      mandatory
        DESCRIPTION
            "Additional Information about the TRAP/INFORM event."
        ::= { ipeTrapCommonAdditionalVars 4 }
    
    -- 1.3.6.1.4.1.119.2.3.69.203.513.501.2.1.2.5
    eventAdditionalText5 OBJECT-TYPE
        SYNTAX      DisplayString
        ACCESS      read-only
        STATUS      mandatory
        DESCRIPTION
            "Additional Information about the TRAP/INFORM event."
        ::= { ipeTrapCommonAdditionalVars 5 }
    
    -- 1.3.6.1.4.1.119.2.3.69.203.513.501.2.1.3
    ipeTrapAlarmVars OBJECT IDENTIFIER
        ::= { ipeTrapCommon 3 }
    
    -- 1.3.6.1.4.1.119.2.3.69.203.513.501.2.1.3.1
    eventSeverity OBJECT-TYPE
        SYNTAX      SeverityValue
        ACCESS      read-only
        STATUS      mandatory
        DESCRIPTION
            "Severity value of notified alarm event."
        ::= { ipeTrapAlarmVars 1 }
    
    -- 1.3.6.1.4.1.119.2.3.69.203.513.501.2.1.3.2
    eventAlarmType OBJECT-TYPE
        SYNTAX      AlarmTypeValue
        ACCESS      read-only
        STATUS      mandatory
        DESCRIPTION
            "Represents the X.733 based event type value for the alarms."
        ::= { ipeTrapAlarmVars 2 }
    
    -- 1.3.6.1.4.1.119.2.3.69.203.513.501.2.1.3.3
    eventProbableCause OBJECT-TYPE
        SYNTAX      ProbableCauseValue
        ACCESS      read-only
        STATUS      mandatory
        DESCRIPTION
            "Represents the X.733 based probable cause value for the alarms."
        ::= { ipeTrapAlarmVars 3 }
    
    -- 1.3.6.1.4.1.119.2.3.69.203.513.501.2.1.4
    ipeTrapStatusValueVars OBJECT IDENTIFIER
        ::= { ipeTrapCommon 4 }
    
    -- 1.3.6.1.4.1.119.2.3.69.203.513.501.2.1.4.1
    eventStatusValue OBJECT-TYPE
        SYNTAX      INTEGER
        ACCESS      read-only
        STATUS      mandatory
        DESCRIPTION
            "the changed value of status object whose syntax is integer.
             Event object is represented by 'eventResourceID'"
        ::= { ipeTrapStatusValueVars 1 }
    
    -- 1.3.6.1.4.1.119.2.3.69.203.513.501.2.1.4.2
    eventStatusValueDspStr OBJECT-TYPE
        SYNTAX      DisplayString
        ACCESS      read-only
        STATUS      mandatory
        DESCRIPTION
            "the changed value of status object whose syntax is DISPLAY
             STRING. Event object is represented by 'eventResourceID'"
        ::= { ipeTrapStatusValueVars 2 }
    
    -- 1.3.6.1.4.1.119.2.3.69.203.513.501.2.1.4.3
    eventStatusValueOctStr OBJECT-TYPE
        SYNTAX      OCTET STRING (SIZE(0..512 | 32))
        ACCESS      read-only
        STATUS      mandatory
        DESCRIPTION
            "the changed value of status object whose syntax is OCTET STRING.
             Event object is represented by 'eventResourceID'
    
             SYNTAX:  OCTET STRING (SIZE(32..32))
             [iPASOLINK200/400/1000series/EX/iX],
                      OCTET STRING (SIZE(0..512)) [iPASOLINK VR series]"
        ::= { ipeTrapStatusValueVars 3 }
    
    -- 1.3.6.1.4.1.119.2.3.69.203.513.501.2.1.4.4
    eventStatusValueUnsigned32 OBJECT-TYPE
        SYNTAX      Gauge
        ACCESS      read-only
        STATUS      mandatory
        DESCRIPTION
            "the changed value of status object whose syntax is unsigned32.
             Event object is represented by 'eventResourceID'"
        ::= { ipeTrapStatusValueVars 4 }
    
    -- 1.3.6.1.4.1.119.2.3.69.203.513.501.2.1.5
    ipeTrapControlValueVars OBJECT IDENTIFIER
        ::= { ipeTrapCommon 5 }
    
    -- 1.3.6.1.4.1.119.2.3.69.203.513.501.2.1.5.1
    eventControlValue OBJECT-TYPE
        SYNTAX      INTEGER
        ACCESS      read-only
        STATUS      mandatory
        DESCRIPTION
            "the changed value of control event whose syntax is integer32.
             Event object is represented by 'eventResourceID'"
        ::= { ipeTrapControlValueVars 1 }
    
    -- 1.3.6.1.4.1.119.2.3.69.203.513.501.2.1.5.2
    eventControlValueDspStr OBJECT-TYPE
        SYNTAX      DisplayString
        ACCESS      read-only
        STATUS      mandatory
        DESCRIPTION
            "the changed value of control event whose syntax is DISPLAY
             STRING. Event object is represented by 'eventResourceID'"
        ::= { ipeTrapControlValueVars 2 }
    
    -- 1.3.6.1.4.1.119.2.3.69.203.513.501.2.1.5.3
    eventControlValueOctStr OBJECT-TYPE
        SYNTAX      OCTET STRING (SIZE(0..512 | 32))
        ACCESS      read-only
        STATUS      mandatory
        DESCRIPTION
            "the changed value of control event whose syntax is OCTET STRING.
             Event object is represented by 'eventResourceID'
             value range:
             0 - 512 (iPASOLINK VR R5.0 or later),
             32 (others)"
        ::= { ipeTrapControlValueVars 3 }
    
    -- 1.3.6.1.4.1.119.2.3.69.203.513.501.2.1.5.4
    eventControlValueUnsigned32 OBJECT-TYPE
        SYNTAX      Gauge
        ACCESS      read-only
        STATUS      mandatory
        DESCRIPTION
            "the changed value of control event whose syntax is Unsigned32.
             Event object is represented by 'eventResourceID'"
        ::= { ipeTrapControlValueVars 4 }
    
    -- 1.3.6.1.4.1.119.2.3.69.203.513.501.2.1.6
    ipeTrapControlVars OBJECT IDENTIFIER
        ::= { ipeTrapCommon 6 }
    
    -- 1.3.6.1.4.1.119.2.3.69.203.513.501.2.1.6.1
    eventRecordUserName OBJECT-TYPE
        SYNTAX      DisplayString
        ACCESS      read-only
        STATUS      mandatory
        DESCRIPTION
            "the user name who triggered the control event. In SNMPv1/v2
             cases, this object reports 'unknown' unless 'ipeAccessUserName'
             is set within the SNMP SET PDU.
             In SNMPv3 cases, this object reports user name which is specified
             in SET-REQUEST."
        ::= { ipeTrapControlVars 1 }
    
    -- 1.3.6.1.4.1.119.2.3.69.203.513.501.2.1.6.2
    eventRecordAccessType OBJECT-TYPE
        SYNTAX      INTEGER { invalid(0), nms(1), webLct(2), cli(3),
                        internal(4) }
        ACCESS      read-only
        STATUS      mandatory
        DESCRIPTION
            "the access type which triggered the control event. This object
             reports 'nms' unless 'ipeAccessType' is set within the SNMP SET
             PDU. Otherwise this object reports the same value of
             'ipeAccessType'.
             The value ipMplsCli(5) is valid for VR R6.0 or later."
        ::= { ipeTrapControlVars 2 }
    
    -- 1.3.6.1.4.1.119.2.3.69.203.513.501.2.1.6.3
    eventRecordAccessFrom OBJECT-TYPE
        SYNTAX      IpAddress
        ACCESS      read-only
        STATUS      mandatory
        DESCRIPTION
            "the ip address which triggered the control event. The ip address
             is normally recognized by source ip address of SET-REQUEST. But
             when 'ipeAccessFrom' is set in the SET-REQUEST, this object
             reports same value of 'ipeAccessFrom'."
        ::= { ipeTrapControlVars 3 }
    
    -- 1.3.6.1.4.1.119.2.3.69.203.513.501.2.1.6.4
    eventRecordAccessFromV6 OBJECT-TYPE
        SYNTAX      Ipv6Address
        ACCESS      read-only
        STATUS      mandatory
        DESCRIPTION
            "the IPv6 address which triggered the control event. The IPv6
             address is normally recognized by source IPv6 address of
             SET-REQUEST. But when 'ipeAccessFromV6Address' is set in the
             SET-REQUEST, this object reports same value of
             'ipeAccessFromV6Address'."
        ::= { ipeTrapControlVars 4 }
    
    -- 1.3.6.1.4.1.119.2.3.69.203.513.501.2.1.7
    ipeTrapFileDownloadValueVars OBJECT IDENTIFIER
        ::= { ipeTrapCommon 7 }
    
    -- 1.3.6.1.4.1.119.2.3.69.203.513.501.2.1.7.1
    eventDownloadModule OBJECT-TYPE
        SYNTAX      INTEGER
        ACCESS      read-only
        STATUS      mandatory
        DESCRIPTION
            "Represents download module type which triggered download event.
             The type values are same as 'ipeSysOpFileDownloadModule'."
        ::= { ipeTrapFileDownloadValueVars 1 }
    
    -- 1.3.6.1.4.1.119.2.3.69.203.513.501.2.1.7.2
    eventDownloadStatus OBJECT-TYPE
        SYNTAX      INTEGER
        ACCESS      read-only
        STATUS      mandatory
        DESCRIPTION
            "Represents download status. The status values are same as
             'ipeSysOpFileDownloadStatus'."
        ::= { ipeTrapFileDownloadValueVars 2 }
    
    -- 1.3.6.1.4.1.119.2.3.69.203.513.501.2.1.7.3
    eventUpdateDetail OBJECT-TYPE
        SYNTAX      DisplayString
        ACCESS      read-only
        STATUS      mandatory
        DESCRIPTION
            "Represents download file name which is specified by
             'ipeFsUpdateFileDetail'."
        ::= { ipeTrapFileDownloadValueVars 3 }
    
    -- 1.3.6.1.4.1.119.2.3.69.203.513.501.2.1.7.4
    eventUpdateStatus OBJECT-TYPE
        SYNTAX      INTEGER
        ACCESS      read-only
        STATUS      mandatory
        DESCRIPTION
            "Represents download file progress. The value is same as
             'ipeFsUpdateFileStatus'."
        ::= { ipeTrapFileDownloadValueVars 4 }
    
    -- 1.3.6.1.4.1.119.2.3.69.203.513.501.2.3
    ipeTrapItemVar OBJECT IDENTIFIER
        ::= { trapGroup 3 }
    
    -- 1.3.6.1.4.1.119.2.3.69.203.513.501.2.3.1
    ipeAlarmTrapItemVar OBJECT IDENTIFIER
        ::= { ipeTrapItemVar 1 }
    
    -- 1.3.6.1.4.1.119.2.3.69.203.513.501.2.3.2
    ipeStatusTrapItemVar OBJECT IDENTIFIER
        ::= { ipeTrapItemVar 2 }
    
    -- 1.3.6.1.4.1.119.2.3.69.203.513.501.2.3.3
    ipeControlTrapItemVar OBJECT IDENTIFIER
        ::= { ipeTrapItemVar 3 }
    
    -- 1.3.6.1.4.1.119.2.3.69.203.513.501.2.3.4
    ipeFileDownloadTrapItemVar OBJECT IDENTIFIER
        ::= { ipeTrapItemVar 4 }
    
    -- 1.3.6.1.4.1.119.2.3.69.203.513.501.2.4
    ipeEventGroup OBJECT IDENTIFIER
        ::= { trapGroup 4 }
    
    -- 1.3.6.1.4.1.119.2.3.69.203.513.501.2.4.1
    eventTable OBJECT-TYPE
        SYNTAX      SEQUENCE OF EventEntry
        ACCESS      not-accessible
        STATUS      mandatory
        DESCRIPTION
            "This table represents trap counter value of each event type."
        ::= { ipeEventGroup 1 }
    
    -- 1.3.6.1.4.1.119.2.3.69.203.513.501.2.4.1.1
    eventEntry OBJECT-TYPE
        SYNTAX      EventEntry
        ACCESS      not-accessible
        STATUS      mandatory
        DESCRIPTION
            ""
        INDEX       { eventNEAddress, eventIndex }
        ::= { eventTable 1 }
    
    EventEntry ::= SEQUENCE {
        eventIndex          INTEGER,
        eventNEAddress      IpAddress,
        eventDescription    DisplayString,
        eventCounter        Counter,
        eventLastTime       DateAndTime
    }
    
    -- 1.3.6.1.4.1.119.2.3.69.203.513.501.2.4.1.1.1
    eventIndex OBJECT-TYPE
        SYNTAX      INTEGER { alarmStateChage(1), statusChange(2),
                        controlEvent(3) }
        ACCESS      not-accessible
        STATUS      mandatory
        DESCRIPTION
            "Index of this table."
        ::= { eventEntry 1 }
    
    -- 1.3.6.1.4.1.119.2.3.69.203.513.501.2.4.1.1.2
    eventNEAddress OBJECT-TYPE
        SYNTAX      IpAddress
        ACCESS      not-accessible
        STATUS      mandatory
        DESCRIPTION
            "reserved"
        ::= { eventEntry 2 }
    
    -- 1.3.6.1.4.1.119.2.3.69.203.513.501.2.4.1.1.3
    eventDescription OBJECT-TYPE
        SYNTAX      DisplayString
        ACCESS      read-only
        STATUS      mandatory
        DESCRIPTION
            "A textual string information about the event."
        ::= { eventEntry 3 }
    
    -- 1.3.6.1.4.1.119.2.3.69.203.513.501.2.4.1.1.4
    eventCounter OBJECT-TYPE
        SYNTAX      Counter
        ACCESS      read-only
        STATUS      mandatory
        DESCRIPTION
            "The count of SNMP TRAP/INFORM messages per event type
             (alarm/status/control) since this equipment was booted."
        ::= { eventEntry 4 }
    
    -- 1.3.6.1.4.1.119.2.3.69.203.513.501.2.4.1.1.5
    eventLastTime OBJECT-TYPE
        SYNTAX      DateAndTime
        ACCESS      read-only
        STATUS      mandatory
        DESCRIPTION
            "The date and time when this event type was last updated."
        ::= { eventEntry 5 }
    
    -- 1.3.6.1.4.1.119.2.3.69.203.513.501.2.4.2
    eventTypeTable OBJECT-TYPE
        SYNTAX      SEQUENCE OF EventTypeEntry
        ACCESS      not-accessible
        STATUS      mandatory
        DESCRIPTION
            "This table represents event information."
        ::= { ipeEventGroup 2 }
    
    -- 1.3.6.1.4.1.119.2.3.69.203.513.501.2.4.2.1
    eventTypeEntry OBJECT-TYPE
        SYNTAX      EventTypeEntry
        ACCESS      not-accessible
        STATUS      mandatory
        DESCRIPTION
            ""
        INDEX       { eventTypeNEAddress, eventTypeIndex, eventTypeSourceCategory,
                      eventTypeElemId }
        ::= { eventTypeTable 1 }
    
    EventTypeEntry ::= SEQUENCE {
        eventTypeIndex              INTEGER,
        eventTypeSourceCategory     INTEGER,
        eventTypeElemId             INTEGER,
        eventTypeNEAddress          IpAddress,
        eventTypeTrapId             INTEGER,
        eventTypeDescription        DisplayString,
        eventTypeRowStatus          RowStatus
    }
    
    -- 1.3.6.1.4.1.119.2.3.69.203.513.501.2.4.2.1.1
    eventTypeIndex OBJECT-TYPE
        SYNTAX      INTEGER
        ACCESS      not-accessible
        STATUS      mandatory
        DESCRIPTION
            "index of this table. The value is same as 'eventType'."
        ::= { eventTypeEntry 1 }
    
    -- 1.3.6.1.4.1.119.2.3.69.203.513.501.2.4.2.1.2
    eventTypeSourceCategory OBJECT-TYPE
        SYNTAX      INTEGER
        ACCESS      not-accessible
        STATUS      mandatory
        DESCRIPTION
            "Index of this table. This object represents category of
             generator of the event."
        ::= { eventTypeEntry 2 }
    
    -- 1.3.6.1.4.1.119.2.3.69.203.513.501.2.4.2.1.3
    eventTypeElemId OBJECT-TYPE
        SYNTAX      INTEGER
        ACCESS      not-accessible
        STATUS      mandatory
        DESCRIPTION
            "Index of this table. Administrative index value of the event
             which is uniquely identified among the eventTypeSourceCategory."
        ::= { eventTypeEntry 3 }
    
    -- 1.3.6.1.4.1.119.2.3.69.203.513.501.2.4.2.1.4
    eventTypeNEAddress OBJECT-TYPE
        SYNTAX      IpAddress
        ACCESS      not-accessible
        STATUS      mandatory
        DESCRIPTION
            "reserved."
        ::= { eventTypeEntry 4 }
    
    -- 1.3.6.1.4.1.119.2.3.69.203.513.501.2.4.2.1.5
    eventTypeTrapId OBJECT-TYPE
        SYNTAX      INTEGER
        ACCESS      read-only
        STATUS      mandatory
        DESCRIPTION
            "Represents event type id same as eventTypeIndex. This object
             indicates which counter will be incremented when this event
             occurs."
        ::= { eventTypeEntry 5 }
    
    -- 1.3.6.1.4.1.119.2.3.69.203.513.501.2.4.2.1.6
    eventTypeDescription OBJECT-TYPE
        SYNTAX      DisplayString
        ACCESS      read-only
        STATUS      mandatory
        DESCRIPTION
            "A Textual string information about the event."
        ::= { eventTypeEntry 6 }
    
    -- 1.3.6.1.4.1.119.2.3.69.203.513.501.2.4.2.1.7
    eventTypeRowStatus OBJECT-TYPE
        SYNTAX      RowStatus
        ACCESS      read-only
        STATUS      mandatory
        DESCRIPTION
            "RowStatus of this table. This table is created automatically
             when the agent starts, and cannot create or destroy from
             manager."
        ::= { eventTypeEntry 7 }
    
    -- 1.3.6.1.4.1.119.2.3.69.203.513.501.2.5
    ipeTrapStatusGroup OBJECT IDENTIFIER
        ::= { trapGroup 5 }
    
    -- 1.3.6.1.4.1.119.2.3.69.203.513.501.2.5.1
    ipeTrapCounterTable OBJECT-TYPE
        SYNTAX      SEQUENCE OF IpeTrapCounterEntry
        ACCESS      not-accessible
        STATUS      mandatory
        DESCRIPTION
            "This table represents event total count."
        ::= { ipeTrapStatusGroup 1 }
    
    -- 1.3.6.1.4.1.119.2.3.69.203.513.501.2.5.1.1
    ipeTrapCounterEntry OBJECT-TYPE
        SYNTAX      IpeTrapCounterEntry
        ACCESS      not-accessible
        STATUS      mandatory
        DESCRIPTION
            ""
        INDEX       { ipeTrapTotalCounterNEAddress, ipeTrapCounterIndex }
        ::= { ipeTrapCounterTable 1 }
    
    IpeTrapCounterEntry ::= SEQUENCE {
        ipeTrapCounterIndex             INTEGER,
        ipeTrapTotalCounterNEAddress    IpAddress,
        ipeTrapTotalCounter             Counter
    }
    
    -- 1.3.6.1.4.1.119.2.3.69.203.513.501.2.5.1.1.1
    ipeTrapCounterIndex OBJECT-TYPE
        SYNTAX      INTEGER
        ACCESS      not-accessible
        STATUS      mandatory
        DESCRIPTION
            "Index of this table."
        ::= { ipeTrapCounterEntry 1 }
    
    -- 1.3.6.1.4.1.119.2.3.69.203.513.501.2.5.1.1.2
    ipeTrapTotalCounterNEAddress OBJECT-TYPE
        SYNTAX      IpAddress
        ACCESS      not-accessible
        STATUS      mandatory
        DESCRIPTION
            "reserved."
        ::= { ipeTrapCounterEntry 2 }
    
    -- 1.3.6.1.4.1.119.2.3.69.203.513.501.2.5.1.1.3
    ipeTrapTotalCounter OBJECT-TYPE
        SYNTAX      Counter
        ACCESS      read-only
        STATUS      mandatory
        DESCRIPTION
            "represents total counter value which counts all event type of
             TRAP/INFORM messages."
        ::= { ipeTrapCounterEntry 3 }
    
    -- 1.3.6.1.4.1.119.2.3.69.203.513.501.3
    alarmStatusGroup OBJECT IDENTIFIER
        ::= { pasoNeoIpe-common 3 }
    
    -- 1.3.6.1.4.1.119.2.3.69.203.513.501.3.1
    asOduGroup OBJECT IDENTIFIER
        ::= { alarmStatusGroup 1 }
    
    -- 1.3.6.1.4.1.119.2.3.69.203.513.501.3.1.1
    oduGroupTable OBJECT-TYPE
        SYNTAX      SEQUENCE OF OduGroupEntry
        ACCESS      not-accessible
        STATUS      mandatory
        DESCRIPTION
            "This table represents alarm and status information."
        ::= { asOduGroup 1 }
    
    -- 1.3.6.1.4.1.119.2.3.69.203.513.501.3.1.1.1
    oduGroupEntry OBJECT-TYPE
        SYNTAX      OduGroupEntry
        ACCESS      not-accessible
        STATUS      mandatory
        DESCRIPTION
            ""
        INDEX       { oduGroupNEAddress, oduGroupIfIndex }
        ::= { oduGroupTable 1 }
    
    OduGroupEntry ::= SEQUENCE {
        oduGroupIfIndex     InterfaceIndex,
        oduGroupNEAddress   IpAddress,
        oduAlarm            SeverityValue,
        txPowerAlarm        SeverityValue,
        txInputAlarm        SeverityValue,
        rxLevelAlarm        SeverityValue,
        cpuCableOpenAlarm   SeverityValue,
        loRefAlarm          SeverityValue,
        muteStatus          OffOnValue,
        oduPsAlarm          SeverityValue,
        oduPsSetStatus      OffOnValue,
        oduTypeMismatch     SeverityValue,
        oduTotalAlarm       SeverityValue,
        oduGroupMismatch    SeverityValue
    }
    
    -- 1.3.6.1.4.1.119.2.3.69.203.513.501.3.1.1.1.1
    oduGroupIfIndex OBJECT-TYPE
        SYNTAX      InterfaceIndex
        ACCESS      not-accessible
        STATUS      mandatory
        DESCRIPTION
            "Index of this table."
        ::= { oduGroupEntry 1 }
    
    -- 1.3.6.1.4.1.119.2.3.69.203.513.501.3.1.1.1.2
    oduGroupNEAddress OBJECT-TYPE
        SYNTAX      IpAddress
        ACCESS      not-accessible
        STATUS      mandatory
        DESCRIPTION
            "reserved."
        ::= { oduGroupEntry 2 }
    
    -- 1.3.6.1.4.1.119.2.3.69.203.513.501.3.1.1.1.3
    oduAlarm OBJECT-TYPE
        SYNTAX      SeverityValue
        ACCESS      read-only
        STATUS      mandatory
        DESCRIPTION
            "ODU Alarm."
        ::= { oduGroupEntry 3 }
    
    -- 1.3.6.1.4.1.119.2.3.69.203.513.501.3.1.1.1.4
    txPowerAlarm OBJECT-TYPE
        SYNTAX      SeverityValue
        ACCESS      read-only
        STATUS      mandatory
        DESCRIPTION
            "ODU TX Power Alarm."
        ::= { oduGroupEntry 4 }
    
    -- 1.3.6.1.4.1.119.2.3.69.203.513.501.3.1.1.1.5
    txInputAlarm OBJECT-TYPE
        SYNTAX      SeverityValue
        ACCESS      read-only
        STATUS      mandatory
        DESCRIPTION
            "ODU TX Input Alarm."
        ::= { oduGroupEntry 5 }
    
    -- 1.3.6.1.4.1.119.2.3.69.203.513.501.3.1.1.1.6
    rxLevelAlarm OBJECT-TYPE
        SYNTAX      SeverityValue
        ACCESS      read-only
        STATUS      mandatory
        DESCRIPTION
            "ODU RX Level Alarm."
        ::= { oduGroupEntry 6 }
    
    -- 1.3.6.1.4.1.119.2.3.69.203.513.501.3.1.1.1.7
    cpuCableOpenAlarm OBJECT-TYPE
        SYNTAX      SeverityValue
        ACCESS      read-only
        STATUS      mandatory
        DESCRIPTION
            "ODU CPU / Cable Open Alarm."
        ::= { oduGroupEntry 7 }
    
    -- 1.3.6.1.4.1.119.2.3.69.203.513.501.3.1.1.1.8
    loRefAlarm OBJECT-TYPE
        SYNTAX      SeverityValue
        ACCESS      read-only
        STATUS      mandatory
        DESCRIPTION
            "ODU LO REF Alarm"
        ::= { oduGroupEntry 8 }
    
    -- 1.3.6.1.4.1.119.2.3.69.203.513.501.3.1.1.1.9
    muteStatus OBJECT-TYPE
        SYNTAX      OffOnValue
        ACCESS      read-only
        STATUS      mandatory
        DESCRIPTION
            "ODU mute status."
        ::= { oduGroupEntry 9 }
    
    -- 1.3.6.1.4.1.119.2.3.69.203.513.501.3.1.1.1.10
    oduPsAlarm OBJECT-TYPE
        SYNTAX      SeverityValue
        ACCESS      read-only
        STATUS      mandatory
        DESCRIPTION
            "ODU Power Supply Alarm"
        ::= { oduGroupEntry 10 }
    
    -- 1.3.6.1.4.1.119.2.3.69.203.513.501.3.1.1.1.11
    oduPsSetStatus OBJECT-TYPE
        SYNTAX      OffOnValue
        ACCESS      read-only
        STATUS      mandatory
        DESCRIPTION
            "ODU Power Supply Status."
        ::= { oduGroupEntry 11 }
    
    -- 1.3.6.1.4.1.119.2.3.69.203.513.501.3.1.1.1.12
    oduTypeMismatch OBJECT-TYPE
        SYNTAX      SeverityValue
        ACCESS      read-only
        STATUS      mandatory
        DESCRIPTION
            "ODU Type Mismatch Alarm."
        ::= { oduGroupEntry 12 }
    
    -- 1.3.6.1.4.1.119.2.3.69.203.513.501.3.1.1.1.13
    oduTotalAlarm OBJECT-TYPE
        SYNTAX      SeverityValue
        ACCESS      read-only
        STATUS      obsolete
        DESCRIPTION
            "ODU Total Alarm."
        ::= { oduGroupEntry 13 }
    
    -- 1.3.6.1.4.1.119.2.3.69.203.513.501.3.1.1.1.24
    oduGroupMismatch OBJECT-TYPE
        SYNTAX      SeverityValue
        ACCESS      read-only
        STATUS      mandatory
        DESCRIPTION
            "ODU Group Mismatch."
        ::= { oduGroupEntry 24 }
    
    -- 1.3.6.1.4.1.119.2.3.69.203.513.501.3.1.2
    oduSwGroupTable OBJECT-TYPE
        SYNTAX      SEQUENCE OF OduSwGroupEntry
        ACCESS      not-accessible
        STATUS      mandatory
        DESCRIPTION
            "This table represents ODU Switch Group Status."
        ::= { asOduGroup 2 }
    
    -- 1.3.6.1.4.1.119.2.3.69.203.513.501.3.1.2.1
    oduSwGroupEntry OBJECT-TYPE
        SYNTAX      OduSwGroupEntry
        ACCESS      not-accessible
        STATUS      mandatory
        DESCRIPTION
            ""
        INDEX       { oduSwGroupNEAddress, oduSwGroupIfIndex }
        ::= { oduSwGroupTable 1 }
    
    OduSwGroupEntry ::= SEQUENCE {
        oduSwGroupIfIndex           InterfaceIndex,
        oduSwGroupNEAddress         IpAddress,
        txSWStatus                  INTEGER,
        rxSWStatus                  INTEGER,
        txSWLockInStatus            INTEGER,
        txSwReverseReqRecvStatus    INTEGER
    }
    
    -- 1.3.6.1.4.1.119.2.3.69.203.513.501.3.1.2.1.1
    oduSwGroupIfIndex OBJECT-TYPE
        SYNTAX      InterfaceIndex
        ACCESS      not-accessible
        STATUS      mandatory
        DESCRIPTION
            "Index of this table."
        ::= { oduSwGroupEntry 1 }
    
    -- 1.3.6.1.4.1.119.2.3.69.203.513.501.3.1.2.1.2
    oduSwGroupNEAddress OBJECT-TYPE
        SYNTAX      IpAddress
        ACCESS      not-accessible
        STATUS      mandatory
        DESCRIPTION
            "reserved"
        ::= { oduSwGroupEntry 2 }
    
    -- 1.3.6.1.4.1.119.2.3.69.203.513.501.3.1.2.1.3
    txSWStatus OBJECT-TYPE
        SYNTAX      INTEGER { no1(1), no2(2) }
        ACCESS      read-only
        STATUS      mandatory
        DESCRIPTION
            "ODU TX SW Status"
        ::= { oduSwGroupEntry 3 }
    
    -- 1.3.6.1.4.1.119.2.3.69.203.513.501.3.1.2.1.4
    rxSWStatus OBJECT-TYPE
        SYNTAX      INTEGER { no1(1), no2(2) }
        ACCESS      read-only
        STATUS      mandatory
        DESCRIPTION
            "ODU RX SW Status"
        ::= { oduSwGroupEntry 4 }
    
    -- 1.3.6.1.4.1.119.2.3.69.203.513.501.3.1.2.1.5
    txSWLockInStatus OBJECT-TYPE
        SYNTAX      INTEGER { normal(1), lockin(2) }
        ACCESS      read-only
        STATUS      mandatory
        DESCRIPTION
            "MODEM TX SW Lock-in Status"
        ::= { oduSwGroupEntry 5 }
    
    -- 1.3.6.1.4.1.119.2.3.69.203.513.501.3.1.2.1.6
    txSwReverseReqRecvStatus OBJECT-TYPE
        SYNTAX      INTEGER { normal(1), received(2), execute(3) }
        ACCESS      read-only
        STATUS      mandatory
        DESCRIPTION
            "MODEM TX SW Reverse Request Status."
        ::= { oduSwGroupEntry 6 }
    
    -- 1.3.6.1.4.1.119.2.3.69.203.513.501.3.2
    asModemGroup OBJECT IDENTIFIER
        ::= { alarmStatusGroup 2 }
    
    -- 1.3.6.1.4.1.119.2.3.69.203.513.501.3.2.1
    modemGroupTable OBJECT-TYPE
        SYNTAX      SEQUENCE OF ModemGroupEntry
        ACCESS      not-accessible
        STATUS      mandatory
        DESCRIPTION
            "This table represents MODEM Alarm Status information."
        ::= { asModemGroup 1 }
    
    -- 1.3.6.1.4.1.119.2.3.69.203.513.501.3.2.1.1
    modemGroupEntry OBJECT-TYPE
        SYNTAX      ModemGroupEntry
        ACCESS      not-accessible
        STATUS      mandatory
        DESCRIPTION
            ""
        INDEX       { modemGroupNEAddress, modemGroupIfIndex }
        ::= { modemGroupTable 1 }
    
    ModemGroupEntry ::= SEQUENCE {
        modemGroupIfIndex       InterfaceIndex,
        modemGroupNEAddress     IpAddress,
        lof                     SeverityValue,
        frameID                 SeverityValue,
        highBERAlarm            SeverityValue,
        lowBERAlarm             SeverityValue,
        earlyWarningAlarm       SeverityValue,
        modAlarm                SeverityValue,
        ifCableShortAlarm       SeverityValue,
        atpcPowerMode           INTEGER,
        inPhaseStatus           INTEGER,
        amrRangeMismatch        SeverityValue,
        txModulation            INTEGER,
        rxModulation            INTEGER,
        l2SyncLossAlarm         SeverityValue,
        rdiAlarm                SeverityValue,
        uaeAlarm                SeverityValue,
        unlocked                SeverityValue,
        tempAlarm               SeverityValue,
        tdmRangeMismatch        SeverityValue,
        modemPsOff              OffOnValue,
        overheated              SeverityValue
    }
    
    -- 1.3.6.1.4.1.119.2.3.69.203.513.501.3.2.1.1.1
    modemGroupIfIndex OBJECT-TYPE
        SYNTAX      InterfaceIndex
        ACCESS      not-accessible
        STATUS      mandatory
        DESCRIPTION
            "Index of this table"
        ::= { modemGroupEntry 1 }
    
    -- 1.3.6.1.4.1.119.2.3.69.203.513.501.3.2.1.1.2
    modemGroupNEAddress OBJECT-TYPE
        SYNTAX      IpAddress
        ACCESS      not-accessible
        STATUS      mandatory
        DESCRIPTION
            "reserved"
        ::= { modemGroupEntry 2 }
    
    -- 1.3.6.1.4.1.119.2.3.69.203.513.501.3.2.1.1.3
    lof OBJECT-TYPE
        SYNTAX      SeverityValue
        ACCESS      read-only
        STATUS      mandatory
        DESCRIPTION
            "MODEM LOF Alarm"
        ::= { modemGroupEntry 3 }
    
    -- 1.3.6.1.4.1.119.2.3.69.203.513.501.3.2.1.1.4
    frameID OBJECT-TYPE
        SYNTAX      SeverityValue
        ACCESS      read-only
        STATUS      mandatory
        DESCRIPTION
            "MODEM Frame ID Alarm"
        ::= { modemGroupEntry 4 }
    
    -- 1.3.6.1.4.1.119.2.3.69.203.513.501.3.2.1.1.5
    highBERAlarm OBJECT-TYPE
        SYNTAX      SeverityValue
        ACCESS      read-only
        STATUS      mandatory
        DESCRIPTION
            "MODEM High BER Alarm."
        ::= { modemGroupEntry 5 }
    
    -- 1.3.6.1.4.1.119.2.3.69.203.513.501.3.2.1.1.6
    lowBERAlarm OBJECT-TYPE
        SYNTAX      SeverityValue
        ACCESS      read-only
        STATUS      mandatory
        DESCRIPTION
            "MODEM Low BER Alarm."
        ::= { modemGroupEntry 6 }
    
    -- 1.3.6.1.4.1.119.2.3.69.203.513.501.3.2.1.1.7
    earlyWarningAlarm OBJECT-TYPE
        SYNTAX      SeverityValue
        ACCESS      read-only
        STATUS      mandatory
        DESCRIPTION
            "MODEM Early Warning Alarm"
        ::= { modemGroupEntry 7 }
    
    -- 1.3.6.1.4.1.119.2.3.69.203.513.501.3.2.1.1.8
    modAlarm OBJECT-TYPE
        SYNTAX      SeverityValue
        ACCESS      read-only
        STATUS      mandatory
        DESCRIPTION
            "MODEM MOD Alarm"
        ::= { modemGroupEntry 8 }
    
    -- 1.3.6.1.4.1.119.2.3.69.203.513.501.3.2.1.1.9
    ifCableShortAlarm OBJECT-TYPE
        SYNTAX      SeverityValue
        ACCESS      read-only
        STATUS      mandatory
        DESCRIPTION
            "MODEM IF Cable Short Alarm"
        ::= { modemGroupEntry 9 }
    
    -- 1.3.6.1.4.1.119.2.3.69.203.513.501.3.2.1.1.10
    atpcPowerMode OBJECT-TYPE
        SYNTAX      INTEGER { stop(1), active(2) }
        ACCESS      read-only
        STATUS      mandatory
        DESCRIPTION
            "MODEM ATPC Power Mode Status"
        ::= { modemGroupEntry 10 }
    
    -- 1.3.6.1.4.1.119.2.3.69.203.513.501.3.2.1.1.11
    inPhaseStatus OBJECT-TYPE
        SYNTAX      INTEGER { inphase(1), outphase(2) }
        ACCESS      read-only
        STATUS      mandatory
        DESCRIPTION
            "MODEM Inphase Status"
        ::= { modemGroupEntry 11 }
    
    -- 1.3.6.1.4.1.119.2.3.69.203.513.501.3.2.1.1.12
    amrRangeMismatch OBJECT-TYPE
        SYNTAX      SeverityValue
        ACCESS      read-only
        STATUS      obsolete
        DESCRIPTION
            "obsoleted"
        ::= { modemGroupEntry 12 }
    
    -- 1.3.6.1.4.1.119.2.3.69.203.513.501.3.2.1.1.13
    txModulation OBJECT-TYPE
        SYNTAX      INTEGER { invalid(0), qpsk(1), qam16(2), qam32(3),
                        qam64(4), qam128(5), qam256(6), qam512(7),
                        qam1024(8), qam2048(9), qam4096(10) }
        ACCESS      read-only
        STATUS      mandatory
        DESCRIPTION
            "MODEM TX Modulation Status"
        ::= { modemGroupEntry 13 }
    
    -- 1.3.6.1.4.1.119.2.3.69.203.513.501.3.2.1.1.14
    rxModulation OBJECT-TYPE
        SYNTAX      INTEGER { invalid(0), qpsk(1), qam16(2), qam32(3),
                        qam64(4), qam128(5), qam256(6), qam512(7),
                        qam1024(8), qam2048(9), qam4096(10) }
        ACCESS      read-only
        STATUS      mandatory
        DESCRIPTION
            "MODEM RX Modulation Status."
        ::= { modemGroupEntry 14 }
    
    -- 1.3.6.1.4.1.119.2.3.69.203.513.501.3.2.1.1.15
    l2SyncLossAlarm OBJECT-TYPE
        SYNTAX      SeverityValue
        ACCESS      read-only
        STATUS      mandatory
        DESCRIPTION
            "MODEM L2SYNC Loss Alarm."
        ::= { modemGroupEntry 15 }
    
    -- 1.3.6.1.4.1.119.2.3.69.203.513.501.3.2.1.1.16
    rdiAlarm OBJECT-TYPE
        SYNTAX      SeverityValue
        ACCESS      read-only
        STATUS      mandatory
        DESCRIPTION
            "MODEM RDI Alarm"
        ::= { modemGroupEntry 16 }
    
    -- 1.3.6.1.4.1.119.2.3.69.203.513.501.3.2.1.1.17
    uaeAlarm OBJECT-TYPE
        SYNTAX      SeverityValue
        ACCESS      read-only
        STATUS      mandatory
        DESCRIPTION
            "MODEM UAE Alarm"
        ::= { modemGroupEntry 17 }
    
    -- 1.3.6.1.4.1.119.2.3.69.203.513.501.3.2.1.1.18
    unlocked OBJECT-TYPE
        SYNTAX      SeverityValue
        ACCESS      read-only
        STATUS      mandatory
        DESCRIPTION
            "MODEM Unlocked Alarm"
        ::= { modemGroupEntry 18 }
    
    -- 1.3.6.1.4.1.119.2.3.69.203.513.501.3.2.1.1.19
    tempAlarm OBJECT-TYPE
        SYNTAX      SeverityValue
        ACCESS      read-only
        STATUS      obsolete
        DESCRIPTION
            "MODEM Temperature Alarm"
        ::= { modemGroupEntry 19 }
    
    -- 1.3.6.1.4.1.119.2.3.69.203.513.501.3.2.1.1.20
    tdmRangeMismatch OBJECT-TYPE
        SYNTAX      SeverityValue
        ACCESS      read-only
        STATUS      mandatory
        DESCRIPTION
            "MODEM TDM / AMR / AMBR Range Mismatch Alarm"
        ::= { modemGroupEntry 20 }
    
    -- 1.3.6.1.4.1.119.2.3.69.203.513.501.3.2.1.1.21
    modemPsOff OBJECT-TYPE
        SYNTAX      OffOnValue
        ACCESS      read-only
        STATUS      mandatory
        DESCRIPTION
            "MDOEM Power Supply Status"
        ::= { modemGroupEntry 21 }
    
    -- 1.3.6.1.4.1.119.2.3.69.203.513.501.3.2.1.1.22
    overheated OBJECT-TYPE
        SYNTAX      SeverityValue
        ACCESS      read-only
        STATUS      mandatory
        DESCRIPTION
            "MODEM card is overheated."
        ::= { modemGroupEntry 22 }
    
    -- 1.3.6.1.4.1.119.2.3.69.203.513.501.3.2.2
    modemXpicTable OBJECT-TYPE
        SYNTAX      SEQUENCE OF ModemXpicEntry
        ACCESS      not-accessible
        STATUS      mandatory
        DESCRIPTION
            "Represents XPIC Alarm and Status"
        ::= { asModemGroup 2 }
    
    -- 1.3.6.1.4.1.119.2.3.69.203.513.501.3.2.2.1
    modemXpicEntry OBJECT-TYPE
        SYNTAX      ModemXpicEntry
        ACCESS      not-accessible
        STATUS      mandatory
        DESCRIPTION
            ""
        INDEX       { modemXpicNEAddress, modemXpicIfIndex }
        ::= { modemXpicTable 1 }
    
    ModemXpicEntry ::= SEQUENCE {
        modemXpicIfIndex            InterfaceIndex,
        modemXpicNEAddress          IpAddress,
        xIFLevelAlarm               SeverityValue,
        xpicTypeMismatch            SeverityValue,
        xpicPairMuteModeMismatch    SeverityValue
    }
    
    -- 1.3.6.1.4.1.119.2.3.69.203.513.501.3.2.2.1.1
    modemXpicIfIndex OBJECT-TYPE
        SYNTAX      InterfaceIndex
        ACCESS      not-accessible
        STATUS      mandatory
        DESCRIPTION
            "Index of this table"
        ::= { modemXpicEntry 1 }
    
    -- 1.3.6.1.4.1.119.2.3.69.203.513.501.3.2.2.1.2
    modemXpicNEAddress OBJECT-TYPE
        SYNTAX      IpAddress
        ACCESS      not-accessible
        STATUS      mandatory
        DESCRIPTION
            "reserved."
        ::= { modemXpicEntry 2 }
    
    -- 1.3.6.1.4.1.119.2.3.69.203.513.501.3.2.2.1.3
    xIFLevelAlarm OBJECT-TYPE
        SYNTAX      SeverityValue
        ACCESS      read-only
        STATUS      mandatory
        DESCRIPTION
            "MODEM XIF Alarm."
        ::= { modemXpicEntry 3 }
    
    -- 1.3.6.1.4.1.119.2.3.69.203.513.501.3.2.2.1.4
    xpicTypeMismatch OBJECT-TYPE
        SYNTAX      SeverityValue
        ACCESS      read-only
        STATUS      mandatory
        DESCRIPTION
            "MODEM XPIC Mode Mismatch Alarm."
        ::= { modemXpicEntry 4 }
    
    -- 1.3.6.1.4.1.119.2.3.69.203.513.501.3.2.2.1.5
    xpicPairMuteModeMismatch OBJECT-TYPE
        SYNTAX      SeverityValue
        ACCESS      read-only
        STATUS      mandatory
        DESCRIPTION
            "MODEM XPIC Pair Mute Mode Mismatch Alarm."
        ::= { modemXpicEntry 5 }
    
    -- 1.3.6.1.4.1.119.2.3.69.203.513.501.3.2.3
    modemCardTable OBJECT-TYPE
        SYNTAX      SEQUENCE OF ModemCardEntry
        ACCESS      not-accessible
        STATUS      mandatory
        DESCRIPTION
            "Represents MODEM Card Alarm Status."
        ::= { asModemGroup 3 }
    
    -- 1.3.6.1.4.1.119.2.3.69.203.513.501.3.2.3.1
    modemCardEntry OBJECT-TYPE
        SYNTAX      ModemCardEntry
        ACCESS      not-accessible
        STATUS      mandatory
        DESCRIPTION
            ""
        INDEX       { modemCardNEAddress, modemCardIndex }
        ::= { modemCardTable 1 }
    
    ModemCardEntry ::= SEQUENCE {
        modemCardIndex          INTEGER,
        modemCardNEAddress      IpAddress,
        modemComFailAlarm       SeverityValue,
        modemUnequipped         SeverityValue,
        modemAlarm              SeverityValue,
        modemBusErrorTx         SeverityValue,
        modemBusErrorRx         SeverityValue,
        modemTypeMismatch       SeverityValue,
        modemCardOnlineStatus   INTEGER,
        modemCardPsAlarm        SeverityValue
    }
    
    -- 1.3.6.1.4.1.119.2.3.69.203.513.501.3.2.3.1.1
    modemCardIndex OBJECT-TYPE
        SYNTAX      INTEGER
        ACCESS      not-accessible
        STATUS      mandatory
        DESCRIPTION
            "Index of this table."
        ::= { modemCardEntry 1 }
    
    -- 1.3.6.1.4.1.119.2.3.69.203.513.501.3.2.3.1.2
    modemCardNEAddress OBJECT-TYPE
        SYNTAX      IpAddress
        ACCESS      not-accessible
        STATUS      mandatory
        DESCRIPTION
            "reserved"
        ::= { modemCardEntry 2 }
    
    -- 1.3.6.1.4.1.119.2.3.69.203.513.501.3.2.3.1.3
    modemComFailAlarm OBJECT-TYPE
        SYNTAX      SeverityValue
        ACCESS      read-only
        STATUS      mandatory
        DESCRIPTION
            "MODEM Communication FAIL Alarm."
        ::= { modemCardEntry 3 }
    
    -- 1.3.6.1.4.1.119.2.3.69.203.513.501.3.2.3.1.4
    modemUnequipped OBJECT-TYPE
        SYNTAX      SeverityValue
        ACCESS      read-only
        STATUS      mandatory
        DESCRIPTION
            "MODEM Unequipped Alarm."
        ::= { modemCardEntry 4 }
    
    -- 1.3.6.1.4.1.119.2.3.69.203.513.501.3.2.3.1.5
    modemAlarm OBJECT-TYPE
        SYNTAX      SeverityValue
        ACCESS      read-only
        STATUS      mandatory
        DESCRIPTION
            "MODEM Module Alarm."
        ::= { modemCardEntry 5 }
    
    -- 1.3.6.1.4.1.119.2.3.69.203.513.501.3.2.3.1.6
    modemBusErrorTx OBJECT-TYPE
        SYNTAX      SeverityValue
        ACCESS      read-only
        STATUS      mandatory
        DESCRIPTION
            "MODEM Tx Bus Error Alarm."
        ::= { modemCardEntry 6 }
    
    -- 1.3.6.1.4.1.119.2.3.69.203.513.501.3.2.3.1.7
    modemBusErrorRx OBJECT-TYPE
        SYNTAX      SeverityValue
        ACCESS      read-only
        STATUS      mandatory
        DESCRIPTION
            "MODEM Rx Bus Error Alarm."
        ::= { modemCardEntry 7 }
    
    -- 1.3.6.1.4.1.119.2.3.69.203.513.501.3.2.3.1.8
    modemTypeMismatch OBJECT-TYPE
        SYNTAX      SeverityValue
        ACCESS      read-only
        STATUS      mandatory
        DESCRIPTION
            "MODEM Type Mismatch Alarm."
        ::= { modemCardEntry 8 }
    
    -- 1.3.6.1.4.1.119.2.3.69.203.513.501.3.2.3.1.9
    modemCardOnlineStatus OBJECT-TYPE
        SYNTAX      INTEGER { invalid(0), offline(1), online(2) }
        ACCESS      read-only
        STATUS      mandatory
        DESCRIPTION
            "MODEM Online Status"
        ::= { modemCardEntry 9 }
    
    -- 1.3.6.1.4.1.119.2.3.69.203.513.501.3.2.3.1.10
    modemCardPsAlarm OBJECT-TYPE
        SYNTAX      SeverityValue
        ACCESS      read-only
        STATUS      mandatory
        DESCRIPTION
            "MODEM Power Supply Alarm."
        ::= { modemCardEntry 10 }
    
    -- 1.3.6.1.4.1.119.2.3.69.203.513.501.3.2.4
    asModemHeaderCompressTable OBJECT-TYPE
        SYNTAX      SEQUENCE OF AsModemHeaderCompressEntry
        ACCESS      not-accessible
        STATUS      mandatory
        DESCRIPTION
            "Header Compression Function Status.
             This table is created automatically when the Modem Card is
             provisioned, if the F/W supports the new Header Compression
             function."
        ::= { asModemGroup 4 }
    
    -- 1.3.6.1.4.1.119.2.3.69.203.513.501.3.2.4.1
    asModemHeaderCompressEntry OBJECT-TYPE
        SYNTAX      AsModemHeaderCompressEntry
        ACCESS      not-accessible
        STATUS      mandatory
        DESCRIPTION
            ""
        INDEX       { asModemHeaderCompressNEAddress, asModemHeaderCompressIfIndex }
        ::= { asModemHeaderCompressTable 1 }
    
    AsModemHeaderCompressEntry ::= SEQUENCE {
        asModemHeaderCompressIfIndex        InterfaceIndex,
        asModemHeaderCompressNEAddress      IpAddress,
        asModemHeaderCompressMismatch       SeverityValue,
        asModemHeaderCompressCurrentMode    INTEGER,
        asModemHeaderCompressVersion        INTEGER
    }
    
    -- 1.3.6.1.4.1.119.2.3.69.203.513.501.3.2.4.1.1
    asModemHeaderCompressIfIndex OBJECT-TYPE
        SYNTAX      InterfaceIndex
        ACCESS      not-accessible
        STATUS      mandatory
        DESCRIPTION
            "Index of this table."
        ::= { asModemHeaderCompressEntry 1 }
    
    -- 1.3.6.1.4.1.119.2.3.69.203.513.501.3.2.4.1.2
    asModemHeaderCompressNEAddress OBJECT-TYPE
        SYNTAX      IpAddress
        ACCESS      not-accessible
        STATUS      mandatory
        DESCRIPTION
            "reserved."
        ::= { asModemHeaderCompressEntry 2 }
    
    -- 1.3.6.1.4.1.119.2.3.69.203.513.501.3.2.4.1.3
    asModemHeaderCompressMismatch OBJECT-TYPE
        SYNTAX      SeverityValue
        ACCESS      read-only
        STATUS      mandatory
        DESCRIPTION
            "Header/Payload* Compression Mismatch Alarm.
             If the configuration of local and remote header compression mode
             is different, the alarm will be reported.
             (*iPASOLINK VR series only)"
        ::= { asModemHeaderCompressEntry 3 }
    
    -- 1.3.6.1.4.1.119.2.3.69.203.513.501.3.2.4.1.4
    asModemHeaderCompressCurrentMode OBJECT-TYPE
        SYNTAX      INTEGER { invalid(0), disable(1), mac(2), macWithIpv4(3),
                        macWithIpv6(4), macWithMpls(5),
                        enhancedMacWithIpv4(6), enhancedMacWithIpv6(7),
                        enhancedMacWithMpls(8), payload(33), payloadMac(34),
                        payloadMacWithIpv4(35), payloadMacWithIpv6(36),
                        payloadMacWithMpls(37) }
        ACCESS      read-only
        STATUS      mandatory
        DESCRIPTION
            "Current Header/Payload* Compression Mode.
             This value shows same value as 'provModemHeaderCompressMode'
             usually. But the value will be different from
             'provModemHeaderCompressMode', when the new Header Compression
             Function is configured to the old Modem Card (which does not have
             new Header Compression capabilities)
             (*iPASOLINK VR series only)"
        ::= { asModemHeaderCompressEntry 4 }
    
    -- 1.3.6.1.4.1.119.2.3.69.203.513.501.3.2.4.1.5
    asModemHeaderCompressVersion OBJECT-TYPE
        SYNTAX      INTEGER
        ACCESS      read-only
        STATUS      mandatory
        DESCRIPTION
            "The version of Header/Payload* Compression Function.
             '1' means the Header Compression is not supported and the
             Payload* Compression is not supported.
             '2' means the Header Compression is supported and the Payload*
             Compression is not supported.
             '3' means the Header Compression is not supported and the
             Payload* Compression is supported.
             '4' means the Header Compression is supported and the Payload*
             Compression is supported.
             (*iPASOLINK VR series only)"
        ::= { asModemHeaderCompressEntry 5 }
    
    -- 1.3.6.1.4.1.119.2.3.69.203.513.501.3.2.5
    asModemHeaderCompressRemoteTable OBJECT-TYPE
        SYNTAX      SEQUENCE OF AsModemHeaderCompressRemoteEntry
        ACCESS      not-accessible
        STATUS      mandatory
        DESCRIPTION
            "Remote Modem Header Compression Function Status.
             This table is created automatically when the Modem Card is
             provisioned, if the F/W supports the new Header Compression
             function."
        ::= { asModemGroup 5 }
    
    -- 1.3.6.1.4.1.119.2.3.69.203.513.501.3.2.5.1
    asModemHeaderCompressRemoteEntry OBJECT-TYPE
        SYNTAX      AsModemHeaderCompressRemoteEntry
        ACCESS      not-accessible
        STATUS      mandatory
        DESCRIPTION
            ""
        INDEX       { asModemHeaderCompressRemoteNEAddress, asModemHeaderCompressRemoteIfIndex }
        ::= { asModemHeaderCompressRemoteTable 1 }
    
    AsModemHeaderCompressRemoteEntry ::= SEQUENCE {
        asModemHeaderCompressRemoteIfIndex      InterfaceIndex,
        asModemHeaderCompressRemoteNEAddress    IpAddress,
        asModemHeaderCompressRemoteMode         INTEGER,
        asModemHeaderCompressRemoteVlanMode     INTEGER,
        asModemHeaderCompressRemoteVersion      INTEGER
    }
    
    -- 1.3.6.1.4.1.119.2.3.69.203.513.501.3.2.5.1.1
    asModemHeaderCompressRemoteIfIndex OBJECT-TYPE
        SYNTAX      InterfaceIndex
        ACCESS      not-accessible
        STATUS      mandatory
        DESCRIPTION
            "Index of this table."
        ::= { asModemHeaderCompressRemoteEntry 1 }
    
    -- 1.3.6.1.4.1.119.2.3.69.203.513.501.3.2.5.1.2
    asModemHeaderCompressRemoteNEAddress OBJECT-TYPE
        SYNTAX      IpAddress
        ACCESS      not-accessible
        STATUS      mandatory
        DESCRIPTION
            "reserved."
        ::= { asModemHeaderCompressRemoteEntry 2 }
    
    -- 1.3.6.1.4.1.119.2.3.69.203.513.501.3.2.5.1.3
    asModemHeaderCompressRemoteMode OBJECT-TYPE
        SYNTAX      INTEGER { invalid(0), disable(1), mac(2), macWithIpv4(3),
                        macWithIpv6(4), macWithMpls(5),
                        enhancedMacWithIpv4(6), enhancedMacWithIpv6(7),
                        enhancedMacWithMpls(8), payload(33), payloadMac(34),
                        payloadMacWithIpv4(35), payloadMacWithIpv6(36),
                        payloadMacWithMpls(37), unknown(99) }
        ACCESS      read-only
        STATUS      mandatory
        DESCRIPTION
            "Header/Payload* Compression Mode of Remote Modem.
             When the Radio link is not established, the value will be changed
             to 'unknown'.
             (*iPASOLINK VR series only)"
        ::= { asModemHeaderCompressRemoteEntry 3 }
    
    -- 1.3.6.1.4.1.119.2.3.69.203.513.501.3.2.5.1.4
    asModemHeaderCompressRemoteVlanMode OBJECT-TYPE
        SYNTAX      INTEGER { invalid(0), dot1q(1), dot1ad(2), unknown(99) }
        ACCESS      read-only
        STATUS      mandatory
        DESCRIPTION
            "VLAN Mode of Remote equipment.
             When the Radio link is not established, the object will show the
             value 'unknown'."
        ::= { asModemHeaderCompressRemoteEntry 4 }
    
    -- 1.3.6.1.4.1.119.2.3.69.203.513.501.3.2.5.1.5
    asModemHeaderCompressRemoteVersion OBJECT-TYPE
        SYNTAX      INTEGER
        ACCESS      read-only
        STATUS      mandatory
        DESCRIPTION
            "The version of Header/Payload* Compression Function for the
             Remote Modem.
              '1' means the Header Compression is not supported and the
             Payload* Compression is not supported.
              '2' means the Header Compression is supported and the Payload*
             Compression is not supported.
              '3' means the Header Compression is not supported and the
             Payload* Compression is supported.
              '4' means the Header Compression is supported and the Payload*
             Compression is supported.
    
             When the Radio link is not established, the object will return
             '99'.
             If the object returns other value, the local node cannot
             recognize the received value from remote node.
             (*iPASOLINK VR series only)"
        ::= { asModemHeaderCompressRemoteEntry 5 }
    
    -- 1.3.6.1.4.1.119.2.3.69.203.513.501.3.2.6
    asModemTrafficAggrTable OBJECT-TYPE
        SYNTAX      SEQUENCE OF AsModemTrafficAggrEntry
        ACCESS      not-accessible
        STATUS      mandatory
        DESCRIPTION
            "This table contains alarm and status object for Radio Traffic
             Aggregation mode."
        ::= { asModemGroup 6 }
    
    -- 1.3.6.1.4.1.119.2.3.69.203.513.501.3.2.6.1
    asModemTrafficAggrEntry OBJECT-TYPE
        SYNTAX      AsModemTrafficAggrEntry
        ACCESS      not-accessible
        STATUS      mandatory
        DESCRIPTION
            ""
        INDEX       { asModemTrafficAggrNEAddress, asModemTrafficAggrIfIndex }
        ::= { asModemTrafficAggrTable 1 }
    
    AsModemTrafficAggrEntry ::= SEQUENCE {
        asModemTrafficAggrIfIndex           InterfaceIndex,
        asModemTrafficAggrNEAddress         IpAddress,
        asModemTrafficAggrModeMismatch      SeverityValue,
        asModemTrafficAggrVersion           INTEGER,
        asModemTrafficAggrEncapStatus       INTEGER,
        asModemTrafficAggrTCModeMismatch    SeverityValue
    }
    
    -- 1.3.6.1.4.1.119.2.3.69.203.513.501.3.2.6.1.1
    asModemTrafficAggrIfIndex OBJECT-TYPE
        SYNTAX      InterfaceIndex
        ACCESS      not-accessible
        STATUS      mandatory
        DESCRIPTION
            "Index of this table. This table is created automatically when
             the MODEM card is provisioned."
        ::= { asModemTrafficAggrEntry 1 }
    
    -- 1.3.6.1.4.1.119.2.3.69.203.513.501.3.2.6.1.2
    asModemTrafficAggrNEAddress OBJECT-TYPE
        SYNTAX      IpAddress
        ACCESS      not-accessible
        STATUS      mandatory
        DESCRIPTION
            "reserved."
        ::= { asModemTrafficAggrEntry 2 }
    
    -- 1.3.6.1.4.1.119.2.3.69.203.513.501.3.2.6.1.3
    asModemTrafficAggrModeMismatch OBJECT-TYPE
        SYNTAX      SeverityValue
        ACCESS      read-only
        STATUS      mandatory
        DESCRIPTION
            "Radio Traffic Aggregation Mode Mismatch Alarm.
             This alarm is asserted if the Radio Traffic Aggregation is
             configured when the H/W and/or F/W does not support the function.
             And also the alarm is asserted when the configuration is
             mismatched between local node and peer node."
        ::= { asModemTrafficAggrEntry 3 }
    
    -- 1.3.6.1.4.1.119.2.3.69.203.513.501.3.2.6.1.4
    asModemTrafficAggrVersion OBJECT-TYPE
        SYNTAX      INTEGER
        ACCESS      read-only
        STATUS      mandatory
        DESCRIPTION
            "The support version of Radio Traffic Aggreation function.
             '5' means the physical advanced mode aggregation, physical mode
                 aggregation, and legacy radio traffic aggregation are
                 supported (valid for iPASO VR 10 only)
             '2' means the physical mode aggregation and legacy radio traffic
                 aggregation are supported
             '1' means the legacy radio traffic aggregation is supported
                 but physical mode is not supported.
             '0' means the physical mode and legacy radio traffic aggregation
                 are not supported
                 (license is not installed or Modem card does not have that
             capability)."
        ::= { asModemTrafficAggrEntry 4 }
    
    -- 1.3.6.1.4.1.119.2.3.69.203.513.501.3.2.6.1.5
    asModemTrafficAggrEncapStatus OBJECT-TYPE
        SYNTAX      INTEGER { invalid(0), normal(1), fail(2) }
        ACCESS      read-only
        STATUS      mandatory
        DESCRIPTION
            "Radio Traffic Aggregation Encapsulation Status.
             When the Modem cannot build frames continuously, the object will
             assert the 'fail'.
             The value will change to 'normal' if the condition is cleared."
        ::= { asModemTrafficAggrEntry 5 }
    
    -- 1.3.6.1.4.1.119.2.3.69.203.513.501.3.2.6.1.6
    asModemTrafficAggrTCModeMismatch OBJECT-TYPE
        SYNTAX      SeverityValue
        ACCESS      read-only
        STATUS      mandatory
        DESCRIPTION
            "This object indicates the Transparent Clock Mode Mismatch Alarm
             for LAG Group."
        ::= { asModemTrafficAggrEntry 6 }
    
    -- 1.3.6.1.4.1.119.2.3.69.203.513.501.3.2.7
    asModemTransmissionModeTable OBJECT-TYPE
        SYNTAX      SEQUENCE OF AsModemTransmissionModeEntry
        ACCESS      not-accessible
        STATUS      mandatory
        DESCRIPTION
            "This table contains Alarm & Status for Modem transmission Mode."
        ::= { asModemGroup 7 }
    
    -- 1.3.6.1.4.1.119.2.3.69.203.513.501.3.2.7.1
    asModemTransmissionModeEntry OBJECT-TYPE
        SYNTAX      AsModemTransmissionModeEntry
        ACCESS      not-accessible
        STATUS      mandatory
        DESCRIPTION
            ""
        INDEX       { asModemTransmissionModeNEAddress, asModemTransmissionModeCardIndex }
        ::= { asModemTransmissionModeTable 1 }
    
    AsModemTransmissionModeEntry ::= SEQUENCE {
        asModemTransmissionModeCardIndex            INTEGER,
        asModemTransmissionModeNEAddress            IpAddress,
        asModemTransmissionModeMismatch             SeverityValue,
        asModemTransparentClockModeMismatch         SeverityValue,
        asModemTransparentClockCalibrationStatus    INTEGER,
        asModemDelayEqualizerSettingMismatch        SeverityValue,
        asModemTransparentClockFail                 SeverityValue
    }
    
    -- 1.3.6.1.4.1.119.2.3.69.203.513.501.3.2.7.1.1
    asModemTransmissionModeCardIndex OBJECT-TYPE
        SYNTAX      INTEGER
        ACCESS      not-accessible
        STATUS      mandatory
        DESCRIPTION
            "Index of this table. This table is created automatically when
             the appropriate MODEM card is provisioned."
        ::= { asModemTransmissionModeEntry 1 }
    
    -- 1.3.6.1.4.1.119.2.3.69.203.513.501.3.2.7.1.2
    asModemTransmissionModeNEAddress OBJECT-TYPE
        SYNTAX      IpAddress
        ACCESS      not-accessible
        STATUS      mandatory
        DESCRIPTION
            "reserved"
        ::= { asModemTransmissionModeEntry 2 }
    
    -- 1.3.6.1.4.1.119.2.3.69.203.513.501.3.2.7.1.3
    asModemTransmissionModeMismatch OBJECT-TYPE
        SYNTAX      SeverityValue
        ACCESS      read-only
        STATUS      mandatory
        DESCRIPTION
            "This object indicates the Transmission Mode Mismatch Alarm.
             When the local system and remote system are configured different
             transmission mode, or the H/W which does not have the capability
             for 'lowPDV' is configured as 'LowPDV', the object will report
             alarm."
        ::= { asModemTransmissionModeEntry 3 }
    
    -- 1.3.6.1.4.1.119.2.3.69.203.513.501.3.2.7.1.4
    asModemTransparentClockModeMismatch OBJECT-TYPE
        SYNTAX      SeverityValue
        ACCESS      read-only
        STATUS      mandatory
        DESCRIPTION
            "This object indicates the Transparent Clock Mode Mismatch Alarm.
             When the local system and remote system are configured different
             transparent clock mode mismatch, or the H/W which does not have
             the capability for 'transparent clock mode' is configured as
             'TransparentClockMode', the object will report alarm."
        ::= { asModemTransmissionModeEntry 4 }
    
    -- 1.3.6.1.4.1.119.2.3.69.203.513.501.3.2.7.1.5
    asModemTransparentClockCalibrationStatus OBJECT-TYPE
        SYNTAX      INTEGER { invalid(0) }
        ACCESS      read-only
        STATUS      obsolete
        DESCRIPTION
            "This object indicates the calibration status of Transparent
             Clock. This object is valid only when Transparent Clock Mode is
             enabled and the Mode is correspond version."
        ::= { asModemTransmissionModeEntry 5 }
    
    -- 1.3.6.1.4.1.119.2.3.69.203.513.501.3.2.7.1.6
    asModemDelayEqualizerSettingMismatch OBJECT-TYPE
        SYNTAX      SeverityValue
        ACCESS      read-only
        STATUS      mandatory
        DESCRIPTION
            "Delay Equalizer Setting Mismatch."
        ::= { asModemTransmissionModeEntry 6 }
    
    -- 1.3.6.1.4.1.119.2.3.69.203.513.501.3.2.7.1.7
    asModemTransparentClockFail OBJECT-TYPE
        SYNTAX      SeverityValue
        ACCESS      read-only
        STATUS      obsolete
        DESCRIPTION
            "reserved. (This object indicates the calibration status of
             Transparent Clock. This object is valid only when Transparent
             Clock Mode is enabled and the Mode is correspond version.)"
        ::= { asModemTransmissionModeEntry 7 }
    
    -- 1.3.6.1.4.1.119.2.3.69.203.513.501.3.2.8
    asModemEncryptionTable OBJECT-TYPE
        SYNTAX      SEQUENCE OF AsModemEncryptionEntry
        ACCESS      not-accessible
        STATUS      mandatory
        DESCRIPTION
            "This table contains Alarm & Status for RADIO encryption."
        ::= { asModemGroup 8 }
    
    -- 1.3.6.1.4.1.119.2.3.69.203.513.501.3.2.8.1
    asModemEncryptionEntry OBJECT-TYPE
        SYNTAX      AsModemEncryptionEntry
        ACCESS      not-accessible
        STATUS      mandatory
        DESCRIPTION
            ""
        INDEX       { asModemEncryptionNEAddress, asModemEncryptionIfIndex }
        ::= { asModemEncryptionTable 1 }
    
    AsModemEncryptionEntry ::= SEQUENCE {
        asModemEncryptionIfIndex            InterfaceIndex,
        asModemEncryptionNEAddress          IpAddress,
        asModemEncryptionModeMismatch       SeverityValue,
        asModemEncryptionDecryptFail        SeverityValue,
        asModemEncryptionKeyExchangeFail    SeverityValue,
        asModemEncryptionUnsupportedModem   SeverityValue,
        asModemEncryptionKeyStatus          INTEGER
    }
    
    -- 1.3.6.1.4.1.119.2.3.69.203.513.501.3.2.8.1.1
    asModemEncryptionIfIndex OBJECT-TYPE
        SYNTAX      InterfaceIndex
        ACCESS      not-accessible
        STATUS      mandatory
        DESCRIPTION
            "Index of this table."
        ::= { asModemEncryptionEntry 1 }
    
    -- 1.3.6.1.4.1.119.2.3.69.203.513.501.3.2.8.1.2
    asModemEncryptionNEAddress OBJECT-TYPE
        SYNTAX      IpAddress
        ACCESS      not-accessible
        STATUS      mandatory
        DESCRIPTION
            "reserved"
        ::= { asModemEncryptionEntry 2 }
    
    -- 1.3.6.1.4.1.119.2.3.69.203.513.501.3.2.8.1.3
    asModemEncryptionModeMismatch OBJECT-TYPE
        SYNTAX      SeverityValue
        ACCESS      read-only
        STATUS      mandatory
        DESCRIPTION
            "This object indicates the Mode Mismatch Alarm."
        ::= { asModemEncryptionEntry 3 }
    
    -- 1.3.6.1.4.1.119.2.3.69.203.513.501.3.2.8.1.4
    asModemEncryptionDecryptFail OBJECT-TYPE
        SYNTAX      SeverityValue
        ACCESS      read-only
        STATUS      mandatory
        DESCRIPTION
            "This object indicates the Decrypt Fail Alarm."
        ::= { asModemEncryptionEntry 4 }
    
    -- 1.3.6.1.4.1.119.2.3.69.203.513.501.3.2.8.1.6
    asModemEncryptionKeyExchangeFail OBJECT-TYPE
        SYNTAX      SeverityValue
        ACCESS      read-only
        STATUS      mandatory
        DESCRIPTION
            "This object indicates the Key Exchange Fail Alarm."
        ::= { asModemEncryptionEntry 6 }
    
    -- 1.3.6.1.4.1.119.2.3.69.203.513.501.3.2.8.1.7
    asModemEncryptionUnsupportedModem OBJECT-TYPE
        SYNTAX      SeverityValue
        ACCESS      read-only
        STATUS      mandatory
        DESCRIPTION
            "This object indicates the Unsupported Modem Alarm."
        ::= { asModemEncryptionEntry 7 }
    
    -- 1.3.6.1.4.1.119.2.3.69.203.513.501.3.2.8.1.8
    asModemEncryptionKeyStatus OBJECT-TYPE
        SYNTAX      INTEGER { invalid(0), preSharedKey(1), exchangedKey(2) }
        ACCESS      read-only
        STATUS      mandatory
        DESCRIPTION
            "if Modem Encryption is working in initial key which is generated
             from passphrase, this object shows 'preSharedKey'."
        ::= { asModemEncryptionEntry 8 }
    
    -- 1.3.6.1.4.1.119.2.3.69.203.513.501.3.2.9
    asModemSwGroupTable OBJECT-TYPE
        SYNTAX      SEQUENCE OF AsModemSwGroupEntry
        ACCESS      not-accessible
        STATUS      mandatory
        DESCRIPTION
            "This table contains Alarm & Status for SW Group."
        ::= { asModemGroup 9 }
    
    -- 1.3.6.1.4.1.119.2.3.69.203.513.501.3.2.9.1
    asModemSwGroupEntry OBJECT-TYPE
        SYNTAX      AsModemSwGroupEntry
        ACCESS      not-accessible
        STATUS      mandatory
        DESCRIPTION
            ""
        INDEX       { asModemSwGroupNEAddress, asModemSwGroupIfIndex }
        ::= { asModemSwGroupTable 1 }
    
    AsModemSwGroupEntry ::= SEQUENCE {
        asModemSwGroupIfIndex           InterfaceIndex,
        asModemSwGroupNEAddress         IpAddress,
        asModemSwGroupTCModeMismatch    SeverityValue
    }
    
    -- 1.3.6.1.4.1.119.2.3.69.203.513.501.3.2.9.1.1
    asModemSwGroupIfIndex OBJECT-TYPE
        SYNTAX      InterfaceIndex
        ACCESS      not-accessible
        STATUS      mandatory
        DESCRIPTION
            "Index of this table. This table is created automatically when
             the appropriate SW Group is provisioned."
        ::= { asModemSwGroupEntry 1 }
    
    -- 1.3.6.1.4.1.119.2.3.69.203.513.501.3.2.9.1.2
    asModemSwGroupNEAddress OBJECT-TYPE
        SYNTAX      IpAddress
        ACCESS      not-accessible
        STATUS      mandatory
        DESCRIPTION
            "reserved"
        ::= { asModemSwGroupEntry 2 }
    
    -- 1.3.6.1.4.1.119.2.3.69.203.513.501.3.2.9.1.3
    asModemSwGroupTCModeMismatch OBJECT-TYPE
        SYNTAX      SeverityValue
        ACCESS      read-only
        STATUS      mandatory
        DESCRIPTION
            "This object indicates the Transparent Clock Mode Mismatch Alarm.
             When the local system and remote system are configured different
             transparent clock mode mismatch, or the H/W which does not have
             the capability for 'transparent clock mode' is configured as
             'TransparentClockMode', the object will report alarm."
        ::= { asModemSwGroupEntry 3 }
    
    -- 1.3.6.1.4.1.119.2.3.69.203.513.501.3.3
    asCtrlGroup OBJECT IDENTIFIER
        ::= { alarmStatusGroup 3 }
    
    -- 1.3.6.1.4.1.119.2.3.69.203.513.501.3.3.3
    sncpBothGroupTable OBJECT-TYPE
        SYNTAX      SEQUENCE OF SncpBothGroupEntry
        ACCESS      not-accessible
        STATUS      mandatory
        DESCRIPTION
            ""
        ::= { asCtrlGroup 3 }
    
    -- 1.3.6.1.4.1.119.2.3.69.203.513.501.3.3.3.1
    sncpBothGroupEntry OBJECT-TYPE
        SYNTAX      SncpBothGroupEntry
        ACCESS      not-accessible
        STATUS      mandatory
        DESCRIPTION
            ""
        INDEX       { sncpBothGroupNEAddress, sncpBothGroupIndex }
        ::= { sncpBothGroupTable 1 }
    
    SncpBothGroupEntry ::= SEQUENCE {
        sncpBothGroupIndex              INTEGER,
        sncpBothGroupNEAddress          IpAddress,
        aTermPpsFail                    SeverityValue,
        sncpATermProtectionStatusCh1    INTEGER,
        sncpATermProtectionStatusCh2    INTEGER,
        sncpATermOnlineStatus           INTEGER,
        sncpATermSwStatus               INTEGER,
        bTermPpsFail                    SeverityValue,
        sncpBTermProtectionStatusCh1    INTEGER,
        sncpBTermProtectionStatusCh2    INTEGER,
        sncpBTermOnlineStatus           INTEGER,
        sncpBTermSwStatus               INTEGER
    }
    
    -- 1.3.6.1.4.1.119.2.3.69.203.513.501.3.3.3.1.1
    sncpBothGroupIndex OBJECT-TYPE
        SYNTAX      INTEGER (1..2352)
        ACCESS      not-accessible
        STATUS      mandatory
        DESCRIPTION
            "Index of this table. The table is created per each XC including
             Work/Protection E1 channel pair.   For 200/400, the range of this
             value is 1 to 168.  For 1000R3.0 or later, the range of value is
             changed to 1 to 2352."
        ::= { sncpBothGroupEntry 1 }
    
    -- 1.3.6.1.4.1.119.2.3.69.203.513.501.3.3.3.1.2
    sncpBothGroupNEAddress OBJECT-TYPE
        SYNTAX      IpAddress
        ACCESS      not-accessible
        STATUS      mandatory
        DESCRIPTION
            "reserved"
        ::= { sncpBothGroupEntry 2 }
    
    -- 1.3.6.1.4.1.119.2.3.69.203.513.501.3.3.3.1.3
    aTermPpsFail OBJECT-TYPE
        SYNTAX      SeverityValue
        ACCESS      read-only
        STATUS      mandatory
        DESCRIPTION
            "PPS FAIL Alarm."
        ::= { sncpBothGroupEntry 3 }
    
    -- 1.3.6.1.4.1.119.2.3.69.203.513.501.3.3.3.1.4
    sncpATermProtectionStatusCh1 OBJECT-TYPE
        SYNTAX      INTEGER { fs(1), sf(2), sd(3), ms(4), nr(5) }
        ACCESS      read-only
        STATUS      mandatory
        DESCRIPTION
            "SNCP Protection Status for Channel 1"
        ::= { sncpBothGroupEntry 4 }
    
    -- 1.3.6.1.4.1.119.2.3.69.203.513.501.3.3.3.1.5
    sncpATermProtectionStatusCh2 OBJECT-TYPE
        SYNTAX      INTEGER { fs(1), sf(2), sd(3), ms(4), nr(5) }
        ACCESS      read-only
        STATUS      mandatory
        DESCRIPTION
            "SNCP Protection Status for Channel 2"
        ::= { sncpBothGroupEntry 5 }
    
    -- 1.3.6.1.4.1.119.2.3.69.203.513.501.3.3.3.1.6
    sncpATermOnlineStatus OBJECT-TYPE
        SYNTAX      INTEGER { work(1), protection(2) }
        ACCESS      read-only
        STATUS      mandatory
        DESCRIPTION
            "SNCP Online Status."
        ::= { sncpBothGroupEntry 6 }
    
    -- 1.3.6.1.4.1.119.2.3.69.203.513.501.3.3.3.1.7
    sncpATermSwStatus OBJECT-TYPE
        SYNTAX      INTEGER { no1(1), no2(2) }
        ACCESS      read-only
        STATUS      mandatory
        DESCRIPTION
            "SNCP Switch Status."
        ::= { sncpBothGroupEntry 7 }
    
    -- 1.3.6.1.4.1.119.2.3.69.203.513.501.3.3.3.1.8
    bTermPpsFail OBJECT-TYPE
        SYNTAX      SeverityValue
        ACCESS      read-only
        STATUS      mandatory
        DESCRIPTION
            "PPS FAIL Alarm."
        ::= { sncpBothGroupEntry 8 }
    
    -- 1.3.6.1.4.1.119.2.3.69.203.513.501.3.3.3.1.9
    sncpBTermProtectionStatusCh1 OBJECT-TYPE
        SYNTAX      INTEGER { fs(1), sf(2), sd(3), ms(4), nr(5) }
        ACCESS      read-only
        STATUS      mandatory
        DESCRIPTION
            "SNCP Protection Status for Channel 1"
        ::= { sncpBothGroupEntry 9 }
    
    -- 1.3.6.1.4.1.119.2.3.69.203.513.501.3.3.3.1.10
    sncpBTermProtectionStatusCh2 OBJECT-TYPE
        SYNTAX      INTEGER { fs(1), sf(2), sd(3), ms(4), nr(5) }
        ACCESS      read-only
        STATUS      mandatory
        DESCRIPTION
            "SNCP Protection Status for Channel 2"
        ::= { sncpBothGroupEntry 10 }
    
    -- 1.3.6.1.4.1.119.2.3.69.203.513.501.3.3.3.1.11
    sncpBTermOnlineStatus OBJECT-TYPE
        SYNTAX      INTEGER { work(1), protection(2) }
        ACCESS      read-only
        STATUS      mandatory
        DESCRIPTION
            "SNCP Online Status."
        ::= { sncpBothGroupEntry 11 }
    
    -- 1.3.6.1.4.1.119.2.3.69.203.513.501.3.3.3.1.12
    sncpBTermSwStatus OBJECT-TYPE
        SYNTAX      INTEGER { no1(1), no2(2) }
        ACCESS      read-only
        STATUS      mandatory
        DESCRIPTION
            "SNCP Switch Status."
        ::= { sncpBothGroupEntry 12 }
    
    -- 1.3.6.1.4.1.119.2.3.69.203.513.501.3.4
    asAuxGroup OBJECT IDENTIFIER
        ::= { alarmStatusGroup 4 }
    
    -- 1.3.6.1.4.1.119.2.3.69.203.513.501.3.4.1
    auxGroupTable OBJECT-TYPE
        SYNTAX      SEQUENCE OF AuxGroupEntry
        ACCESS      not-accessible
        STATUS      mandatory
        DESCRIPTION
            "Represents AUX Card Alarm / Status."
        ::= { asAuxGroup 1 }
    
    -- 1.3.6.1.4.1.119.2.3.69.203.513.501.3.4.1.1
    auxGroupEntry OBJECT-TYPE
        SYNTAX      AuxGroupEntry
        ACCESS      not-accessible
        STATUS      mandatory
        DESCRIPTION
            ""
        INDEX       { auxGroupNEAddress, auxGroupIndex }
        ::= { auxGroupTable 1 }
    
    AuxGroupEntry ::= SEQUENCE {
        auxGroupIndex       INTEGER,
        auxGroupNEAddress   IpAddress,
        auxUnequipped       SeverityValue,
        auxTypeMismatch     SeverityValue,
        auxAlarm            SeverityValue,
        auxComFailAlarm     SeverityValue,
        auxBusErrorTx       SeverityValue,
        auxBusErrorRx       SeverityValue
    }
    
    -- 1.3.6.1.4.1.119.2.3.69.203.513.501.3.4.1.1.1
    auxGroupIndex OBJECT-TYPE
        SYNTAX      INTEGER
        ACCESS      not-accessible
        STATUS      mandatory
        DESCRIPTION
            "Index of this table."
        ::= { auxGroupEntry 1 }
    
    -- 1.3.6.1.4.1.119.2.3.69.203.513.501.3.4.1.1.2
    auxGroupNEAddress OBJECT-TYPE
        SYNTAX      IpAddress
        ACCESS      not-accessible
        STATUS      mandatory
        DESCRIPTION
            "reserved"
        ::= { auxGroupEntry 2 }
    
    -- 1.3.6.1.4.1.119.2.3.69.203.513.501.3.4.1.1.3
    auxUnequipped OBJECT-TYPE
        SYNTAX      SeverityValue
        ACCESS      read-only
        STATUS      mandatory
        DESCRIPTION
            "AUX Unequipped Alarm"
        ::= { auxGroupEntry 3 }
    
    -- 1.3.6.1.4.1.119.2.3.69.203.513.501.3.4.1.1.4
    auxTypeMismatch OBJECT-TYPE
        SYNTAX      SeverityValue
        ACCESS      read-only
        STATUS      mandatory
        DESCRIPTION
            "AUX Type Mismatch Alarm."
        ::= { auxGroupEntry 4 }
    
    -- 1.3.6.1.4.1.119.2.3.69.203.513.501.3.4.1.1.5
    auxAlarm OBJECT-TYPE
        SYNTAX      SeverityValue
        ACCESS      read-only
        STATUS      mandatory
        DESCRIPTION
            "AUX Module Alarm."
        ::= { auxGroupEntry 5 }
    
    -- 1.3.6.1.4.1.119.2.3.69.203.513.501.3.4.1.1.6
    auxComFailAlarm OBJECT-TYPE
        SYNTAX      SeverityValue
        ACCESS      read-only
        STATUS      mandatory
        DESCRIPTION
            "AUX Communication FAIL Alarm."
        ::= { auxGroupEntry 6 }
    
    -- 1.3.6.1.4.1.119.2.3.69.203.513.501.3.4.1.1.7
    auxBusErrorTx OBJECT-TYPE
        SYNTAX      SeverityValue
        ACCESS      read-only
        STATUS      mandatory
        DESCRIPTION
            "AUX Tx Bus Error Alarm"
        ::= { auxGroupEntry 7 }
    
    -- 1.3.6.1.4.1.119.2.3.69.203.513.501.3.4.1.1.8
    auxBusErrorRx OBJECT-TYPE
        SYNTAX      SeverityValue
        ACCESS      read-only
        STATUS      mandatory
        DESCRIPTION
            "AUX Rx Bus Error Alarm"
        ::= { auxGroupEntry 8 }
    
    -- 1.3.6.1.4.1.119.2.3.69.203.513.501.3.5
    asClkGroup OBJECT IDENTIFIER
        ::= { alarmStatusGroup 5 }
    
    -- 1.3.6.1.4.1.119.2.3.69.203.513.501.3.5.1
    clkCommonTable OBJECT-TYPE
        SYNTAX      SEQUENCE OF ClkCommonEntry
        ACCESS      not-accessible
        STATUS      mandatory
        DESCRIPTION
            "Represents Main Board / Ctrl Card CLK Status."
        ::= { asClkGroup 1 }
    
    -- 1.3.6.1.4.1.119.2.3.69.203.513.501.3.5.1.1
    clkCommonEntry OBJECT-TYPE
        SYNTAX      ClkCommonEntry
        ACCESS      not-accessible
        STATUS      mandatory
        DESCRIPTION
            ""
        INDEX       { clkCommonNEAddress, clkCommonIndex }
        ::= { clkCommonTable 1 }
    
    ClkCommonEntry ::= SEQUENCE {
        clkCommonIndex                  INTEGER,
        clkCommonNEAddress              IpAddress,
        ltiAlarm                        SeverityValue,
        refClkChange                    INTEGER,
        extClkLoop                      SeverityValue,
        currentTimingSource             INTEGER,
        timingSourceCondition           INTEGER,
        timingSourceControlStatus       INTEGER,
        currentTimingSourceInterface    InterfaceIndexOrZero
    }
    
    -- 1.3.6.1.4.1.119.2.3.69.203.513.501.3.5.1.1.1
    clkCommonIndex OBJECT-TYPE
        SYNTAX      INTEGER { clk(1) }
        ACCESS      not-accessible
        STATUS      mandatory
        DESCRIPTION
            "Index of this table. The value is same as Main Board or Ctrl
             Card."
        ::= { clkCommonEntry 1 }
    
    -- 1.3.6.1.4.1.119.2.3.69.203.513.501.3.5.1.1.2
    clkCommonNEAddress OBJECT-TYPE
        SYNTAX      IpAddress
        ACCESS      not-accessible
        STATUS      mandatory
        DESCRIPTION
            "reserved."
        ::= { clkCommonEntry 2 }
    
    -- 1.3.6.1.4.1.119.2.3.69.203.513.501.3.5.1.1.3
    ltiAlarm OBJECT-TYPE
        SYNTAX      SeverityValue
        ACCESS      read-only
        STATUS      mandatory
        DESCRIPTION
            "Main Board / Ctrl Card LTI Alarm."
        ::= { clkCommonEntry 3 }
    
    -- 1.3.6.1.4.1.119.2.3.69.203.513.501.3.5.1.1.4
    refClkChange OBJECT-TYPE
        SYNTAX      INTEGER { lockedRef1(1), lockedRef2(2), lockedRef3(3),
                        holdover(4), freerun(5) }
        ACCESS      read-only
        STATUS      mandatory
        DESCRIPTION
            "Main Board / Ctrl Card CLK Status."
        ::= { clkCommonEntry 4 }
    
    -- 1.3.6.1.4.1.119.2.3.69.203.513.501.3.5.1.1.5
    extClkLoop OBJECT-TYPE
        SYNTAX      SeverityValue
        ACCESS      read-only
        STATUS      mandatory
        DESCRIPTION
            "Main Board / Ctrl Card EXT CLK Timing Loop Alarm."
        ::= { clkCommonEntry 5 }
    
    -- 1.3.6.1.4.1.119.2.3.69.203.513.501.3.5.1.1.6
    currentTimingSource OBJECT-TYPE
        SYNTAX      INTEGER { selectRef1(1), selectRef2(2), selectRef3(3) }
        ACCESS      read-only
        STATUS      mandatory
        DESCRIPTION
            "Main Board / Ctrl Card Current Timing Source."
        ::= { clkCommonEntry 6 }
    
    -- 1.3.6.1.4.1.119.2.3.69.203.513.501.3.5.1.1.7
    timingSourceCondition OBJECT-TYPE
        SYNTAX      INTEGER { locked(1), holdover(2), freerun(3) }
        ACCESS      read-only
        STATUS      mandatory
        DESCRIPTION
            "Main Board / Ctrl Card Timing Source Status."
        ::= { clkCommonEntry 7 }
    
    -- 1.3.6.1.4.1.119.2.3.69.203.513.501.3.5.1.1.8
    timingSourceControlStatus OBJECT-TYPE
        SYNTAX      INTEGER { auto(1), manualSelect(2), forcedSelect(3) }
        ACCESS      read-only
        STATUS      mandatory
        DESCRIPTION
            "Main Board / Ctrl Card Timing Source Switch Status."
        ::= { clkCommonEntry 8 }
    
    -- 1.3.6.1.4.1.119.2.3.69.203.513.501.3.5.1.1.9
    currentTimingSourceInterface OBJECT-TYPE
        SYNTAX      InterfaceIndexOrZero
        ACCESS      read-only
        STATUS      mandatory
        DESCRIPTION
            "Current Timing Source for the Interface (Slot/Port/Path). The
             value 0 indicates 'invalid'."
        ::= { clkCommonEntry 9 }
    
    -- 1.3.6.1.4.1.119.2.3.69.203.513.501.3.5.2
    clkRefTable OBJECT-TYPE
        SYNTAX      SEQUENCE OF ClkRefEntry
        ACCESS      not-accessible
        STATUS      mandatory
        DESCRIPTION
            "Represents Timing Source Status."
        ::= { asClkGroup 2 }
    
    -- 1.3.6.1.4.1.119.2.3.69.203.513.501.3.5.2.1
    clkRefEntry OBJECT-TYPE
        SYNTAX      ClkRefEntry
        ACCESS      not-accessible
        STATUS      mandatory
        DESCRIPTION
            ""
        INDEX       { clkRefNEAddress, clkRefIndex }
        ::= { clkRefTable 1 }
    
    ClkRefEntry ::= SEQUENCE {
        clkRefIndex         INTEGER,
        clkRefNEAddress     IpAddress,
        clkFailedAlarm      SeverityValue,
        clkDriftAlarm       SeverityValue,
        clkRefFailedAlarm   SeverityValue,
        refLockoutStatus    INTEGER,
        refQL               INTEGER
    }
    
    -- 1.3.6.1.4.1.119.2.3.69.203.513.501.3.5.2.1.1
    clkRefIndex OBJECT-TYPE
        SYNTAX      INTEGER { refclk1(1), refclk2(2), refclk3(3) }
        ACCESS      not-accessible
        STATUS      mandatory
        DESCRIPTION
            "Index of this table. The table is created per each timing
             source."
        ::= { clkRefEntry 1 }
    
    -- 1.3.6.1.4.1.119.2.3.69.203.513.501.3.5.2.1.2
    clkRefNEAddress OBJECT-TYPE
        SYNTAX      IpAddress
        ACCESS      not-accessible
        STATUS      mandatory
        DESCRIPTION
            "reserved"
        ::= { clkRefEntry 2 }
    
    -- 1.3.6.1.4.1.119.2.3.69.203.513.501.3.5.2.1.3
    clkFailedAlarm OBJECT-TYPE
        SYNTAX      SeverityValue
        ACCESS      read-only
        STATUS      mandatory
        DESCRIPTION
            "Main Board / Ctrl Card CLK FAIL Alarm per CLK Reference."
        ::= { clkRefEntry 3 }
    
    -- 1.3.6.1.4.1.119.2.3.69.203.513.501.3.5.2.1.4
    clkDriftAlarm OBJECT-TYPE
        SYNTAX      SeverityValue
        ACCESS      read-only
        STATUS      mandatory
        DESCRIPTION
            "Main Board / Ctrl Card CLK Drift Alarm per CLK Reference."
        ::= { clkRefEntry 4 }
    
    -- 1.3.6.1.4.1.119.2.3.69.203.513.501.3.5.2.1.5
    clkRefFailedAlarm OBJECT-TYPE
        SYNTAX      SeverityValue
        ACCESS      read-only
        STATUS      mandatory
        DESCRIPTION
            "Main Board / Ctrl Card SSM FAIL Alarm per CLK Reference."
        ::= { clkRefEntry 5 }
    
    -- 1.3.6.1.4.1.119.2.3.69.203.513.501.3.5.2.1.6
    refLockoutStatus OBJECT-TYPE
        SYNTAX      INTEGER { lockout(1), normal(2) }
        ACCESS      read-only
        STATUS      mandatory
        DESCRIPTION
            "Main Board / Ctrl Card Lockout Status per CLK Reference."
        ::= { clkRefEntry 6 }
    
    -- 1.3.6.1.4.1.119.2.3.69.203.513.501.3.5.2.1.7
    refQL OBJECT-TYPE
        SYNTAX      INTEGER { qlPrc(1), qlSsuA(2), qlSsuB(3), qlOriginal(4),
                        qlSec(5), qlDnu(6), qlInvx(7), qlFailed(8),
                        notAvail(9), qlPrs(20), qlStu(21), qlSt2(22),
                        qlTnc(23), qlSt3e(24), qlSt3(25), qlSmc(26),
                        qlSt4(27), qlDus(29) }
        ACCESS      read-only
        STATUS      mandatory
        DESCRIPTION
            "Main Board / Ctrl Card Quality level per CLK Reference."
        ::= { clkRefEntry 7 }
    
    -- 1.3.6.1.4.1.119.2.3.69.203.513.501.3.6
    asExtClkGroup OBJECT IDENTIFIER
        ::= { alarmStatusGroup 6 }
    
    -- 1.3.6.1.4.1.119.2.3.69.203.513.501.3.6.1
    extClkGroupTable OBJECT-TYPE
        SYNTAX      SEQUENCE OF ExtClkGroupEntry
        ACCESS      not-accessible
        STATUS      mandatory
        DESCRIPTION
            "Represents Ext CLK Alarm / Status."
        ::= { asExtClkGroup 1 }
    
    -- 1.3.6.1.4.1.119.2.3.69.203.513.501.3.6.1.1
    extClkGroupEntry OBJECT-TYPE
        SYNTAX      ExtClkGroupEntry
        ACCESS      not-accessible
        STATUS      mandatory
        DESCRIPTION
            ""
        INDEX       { extClkGroupNEAddress, extClkGroupIndex }
        ::= { extClkGroupTable 1 }
    
    ExtClkGroupEntry ::= SEQUENCE {
        extClkGroupIndex        INTEGER,
        extClkGroupNEAddress    IpAddress,
        clk2mLosAlarm           SeverityValue,
        aisAlarm                SeverityValue,
        lofAlarm                SeverityValue,
        clk2mUnequipped         SeverityValue,
        extClkOutputStatus      INTEGER,
        extClkOutputQlValue     INTEGER,
        squelch                 INTEGER,
        clk2mTypeMismatch       SeverityValue
    }
    
    -- 1.3.6.1.4.1.119.2.3.69.203.513.501.3.6.1.1.1
    extClkGroupIndex OBJECT-TYPE
        SYNTAX      INTEGER { extclk(1) }
        ACCESS      not-accessible
        STATUS      mandatory
        DESCRIPTION
            "Index of this table."
        ::= { extClkGroupEntry 1 }
    
    -- 1.3.6.1.4.1.119.2.3.69.203.513.501.3.6.1.1.2
    extClkGroupNEAddress OBJECT-TYPE
        SYNTAX      IpAddress
        ACCESS      not-accessible
        STATUS      mandatory
        DESCRIPTION
            "reserved."
        ::= { extClkGroupEntry 2 }
    
    -- 1.3.6.1.4.1.119.2.3.69.203.513.501.3.6.1.1.3
    clk2mLosAlarm OBJECT-TYPE
        SYNTAX      SeverityValue
        ACCESS      read-only
        STATUS      mandatory
        DESCRIPTION
            "Main Board / Ctrl Card EXT CLK LOS Alarm."
        ::= { extClkGroupEntry 3 }
    
    -- 1.3.6.1.4.1.119.2.3.69.203.513.501.3.6.1.1.4
    aisAlarm OBJECT-TYPE
        SYNTAX      SeverityValue
        ACCESS      read-only
        STATUS      mandatory
        DESCRIPTION
            "Main Board / Ctrl Card EXT CLK AIS Alarm."
        ::= { extClkGroupEntry 4 }
    
    -- 1.3.6.1.4.1.119.2.3.69.203.513.501.3.6.1.1.5
    lofAlarm OBJECT-TYPE
        SYNTAX      SeverityValue
        ACCESS      read-only
        STATUS      mandatory
        DESCRIPTION
            "Main Board / Ctrl Card EXT CLK LOF Alarm."
        ::= { extClkGroupEntry 5 }
    
    -- 1.3.6.1.4.1.119.2.3.69.203.513.501.3.6.1.1.6
    clk2mUnequipped OBJECT-TYPE
        SYNTAX      SeverityValue
        ACCESS      read-only
        STATUS      obsolete
        DESCRIPTION
            "Main Board / Ctrl Card EXT CLK Unequipped Alarm."
        ::= { extClkGroupEntry 6 }
    
    -- 1.3.6.1.4.1.119.2.3.69.203.513.501.3.6.1.1.7
    extClkOutputStatus OBJECT-TYPE
        SYNTAX      INTEGER { normal(1), ais(2), shutdown(3) }
        ACCESS      read-only
        STATUS      mandatory
        DESCRIPTION
            "Main Board / Ctrl Card EXT CLK Output Status."
        ::= { extClkGroupEntry 7 }
    
    -- 1.3.6.1.4.1.119.2.3.69.203.513.501.3.6.1.1.8
    extClkOutputQlValue OBJECT-TYPE
        SYNTAX      INTEGER { qlPrc(1), qlSsuA(2), qlSsuB(3), qlOriginal(4),
                        qlSec(5), qlDnu(6), qlInvx(7), qlFailed(8),
                        notAvail(9) }
        ACCESS      read-only
        STATUS      mandatory
        DESCRIPTION
            "Main Board / Ctrl Card EXT CLK Quality Level."
        ::= { extClkGroupEntry 8 }
    
    -- 1.3.6.1.4.1.119.2.3.69.203.513.501.3.6.1.1.9
    squelch OBJECT-TYPE
        SYNTAX      INTEGER { normal(1), squelch(2) }
        ACCESS      read-only
        STATUS      mandatory
        DESCRIPTION
            "Main Board / Ctrl Card EXT CLK Squelch Status."
        ::= { extClkGroupEntry 9 }
    
    -- 1.3.6.1.4.1.119.2.3.69.203.513.501.3.6.1.1.10
    clk2mTypeMismatch OBJECT-TYPE
        SYNTAX      SeverityValue
        ACCESS      read-only
        STATUS      obsolete
        DESCRIPTION
            "Main Board / Ctrl Card EXT CLK Type Mismatch Alarm."
        ::= { extClkGroupEntry 10 }
    
    -- 1.3.6.1.4.1.119.2.3.69.203.513.501.3.7
    asFanGroup OBJECT IDENTIFIER
        ::= { alarmStatusGroup 7 }
    
    -- 1.3.6.1.4.1.119.2.3.69.203.513.501.3.7.1
    fanGroupTable OBJECT-TYPE
        SYNTAX      SEQUENCE OF FanGroupEntry
        ACCESS      not-accessible
        STATUS      mandatory
        DESCRIPTION
            "Represents FAN Card Alarm / Status."
        ::= { asFanGroup 1 }
    
    -- 1.3.6.1.4.1.119.2.3.69.203.513.501.3.7.1.1
    fanGroupEntry OBJECT-TYPE
        SYNTAX      FanGroupEntry
        ACCESS      not-accessible
        STATUS      mandatory
        DESCRIPTION
            ""
        INDEX       { fanGroupNEAddress, fanGroupIndex }
        ::= { fanGroupTable 1 }
    
    FanGroupEntry ::= SEQUENCE {
        fanGroupIndex       INTEGER,
        fanGroupNEAddress   IpAddress,
        fanAlarm            SeverityValue,
        fanUnequipped       SeverityValue,
        fanTypeMismatch     SeverityValue
    }
    
    -- 1.3.6.1.4.1.119.2.3.69.203.513.501.3.7.1.1.1
    fanGroupIndex OBJECT-TYPE
        SYNTAX      INTEGER
        ACCESS      not-accessible
        STATUS      mandatory
        DESCRIPTION
            "Index of this table."
        ::= { fanGroupEntry 1 }
    
    -- 1.3.6.1.4.1.119.2.3.69.203.513.501.3.7.1.1.2
    fanGroupNEAddress OBJECT-TYPE
        SYNTAX      IpAddress
        ACCESS      not-accessible
        STATUS      mandatory
        DESCRIPTION
            "reserved."
        ::= { fanGroupEntry 2 }
    
    -- 1.3.6.1.4.1.119.2.3.69.203.513.501.3.7.1.1.3
    fanAlarm OBJECT-TYPE
        SYNTAX      SeverityValue
        ACCESS      read-only
        STATUS      mandatory
        DESCRIPTION
            "FAN FAIL Alarm."
        ::= { fanGroupEntry 3 }
    
    -- 1.3.6.1.4.1.119.2.3.69.203.513.501.3.7.1.1.4
    fanUnequipped OBJECT-TYPE
        SYNTAX      SeverityValue
        ACCESS      read-only
        STATUS      mandatory
        DESCRIPTION
            "FAN Unequipped Alarm."
        ::= { fanGroupEntry 4 }
    
    -- 1.3.6.1.4.1.119.2.3.69.203.513.501.3.7.1.1.5
    fanTypeMismatch OBJECT-TYPE
        SYNTAX      SeverityValue
        ACCESS      read-only
        STATUS      mandatory
        DESCRIPTION
            "Equipped FAN is not proper combination with at least one of
             equipped MODEM card.  This is for MODEM-AV card only."
        ::= { fanGroupEntry 5 }
    
    -- 1.3.6.1.4.1.119.2.3.69.203.513.501.3.8
    asPsGroup OBJECT IDENTIFIER
        ::= { alarmStatusGroup 8 }
    
    -- 1.3.6.1.4.1.119.2.3.69.203.513.501.3.8.1
    psGroupTable OBJECT-TYPE
        SYNTAX      SEQUENCE OF PsGroupEntry
        ACCESS      not-accessible
        STATUS      mandatory
        DESCRIPTION
            "Represents Main Board / Ctrl Card Power Supply Alarm / Status."
        ::= { asPsGroup 1 }
    
    -- 1.3.6.1.4.1.119.2.3.69.203.513.501.3.8.1.1
    psGroupEntry OBJECT-TYPE
        SYNTAX      PsGroupEntry
        ACCESS      not-accessible
        STATUS      mandatory
        DESCRIPTION
            ""
        INDEX       { psGroupNEAddress, psGroupIndex }
        ::= { psGroupTable 1 }
    
    PsGroupEntry ::= SEQUENCE {
        psGroupIndex        INTEGER,
        psGroupNEAddress    IpAddress,
        psPowerSupply       SeverityValue,
        psUnequipped        SeverityValue
    }
    
    -- 1.3.6.1.4.1.119.2.3.69.203.513.501.3.8.1.1.1
    psGroupIndex OBJECT-TYPE
        SYNTAX      INTEGER
        ACCESS      not-accessible
        STATUS      mandatory
        DESCRIPTION
            "Index of this table."
        ::= { psGroupEntry 1 }
    
    -- 1.3.6.1.4.1.119.2.3.69.203.513.501.3.8.1.1.2
    psGroupNEAddress OBJECT-TYPE
        SYNTAX      IpAddress
        ACCESS      not-accessible
        STATUS      mandatory
        DESCRIPTION
            "reserved."
        ::= { psGroupEntry 2 }
    
    -- 1.3.6.1.4.1.119.2.3.69.203.513.501.3.8.1.1.3
    psPowerSupply OBJECT-TYPE
        SYNTAX      SeverityValue
        ACCESS      read-only
        STATUS      mandatory
        DESCRIPTION
            "Main Board / Ctrl Card Power Supply Alarm."
        ::= { psGroupEntry 3 }
    
    -- 1.3.6.1.4.1.119.2.3.69.203.513.501.3.8.1.1.4
    psUnequipped OBJECT-TYPE
        SYNTAX      SeverityValue
        ACCESS      read-only
        STATUS      mandatory
        DESCRIPTION
            "Main Board / Ctrl Card Power Supply Unequipped Alarm."
        ::= { psGroupEntry 4 }
    
    -- 1.3.6.1.4.1.119.2.3.69.203.513.501.3.9
    asTCNGroup OBJECT IDENTIFIER
        ::= { alarmStatusGroup 9 }
    
    -- 1.3.6.1.4.1.119.2.3.69.203.513.501.3.9.1
    tcn15minDataRadioGroup OBJECT IDENTIFIER
        ::= { asTCNGroup 1 }
    
    -- 1.3.6.1.4.1.119.2.3.69.203.513.501.3.9.1.1
    tcn15minDataRadioTable OBJECT-TYPE
        SYNTAX      SEQUENCE OF Tcn15minDataRadioEntry
        ACCESS      not-accessible
        STATUS      mandatory
        DESCRIPTION
            "Represents Threashold Crossing Alarm Status of 15 minutes PMON
             for Radio."
        ::= { tcn15minDataRadioGroup 1 }
    
    -- 1.3.6.1.4.1.119.2.3.69.203.513.501.3.9.1.1.1
    tcn15minDataRadioEntry OBJECT-TYPE
        SYNTAX      Tcn15minDataRadioEntry
        ACCESS      not-accessible
        STATUS      mandatory
        DESCRIPTION
            ""
        INDEX       { tcn15minDataRadioNEAddress, tcn15minDataModemIfIndex, tcn15minDataModemMonitorName }
        ::= { tcn15minDataRadioTable 1 }
    
    Tcn15minDataRadioEntry ::= SEQUENCE {
        tcn15minDataModemIfIndex        InterfaceIndex,
        tcn15minDataModemMonitorName    INTEGER,
        tcn15minDataRadioNEAddress      IpAddress,
        tcn15minDataRf                  SeverityValue
    }
    
    -- 1.3.6.1.4.1.119.2.3.69.203.513.501.3.9.1.1.1.1
    tcn15minDataModemIfIndex OBJECT-TYPE
        SYNTAX      InterfaceIndex
        ACCESS      not-accessible
        STATUS      mandatory
        DESCRIPTION
            "Index of this table. Unique number of the radio interface."
        ::= { tcn15minDataRadioEntry 1 }
    
    -- 1.3.6.1.4.1.119.2.3.69.203.513.501.3.9.1.1.1.2
    tcn15minDataModemMonitorName OBJECT-TYPE
        SYNTAX      INTEGER { bbe(1), es(2), ses(3), sep(4), uas(5), ofs(6) }
        ACCESS      not-accessible
        STATUS      mandatory
        DESCRIPTION
            "Index of this table. The index value shows counting item."
        ::= { tcn15minDataRadioEntry 2 }
    
    -- 1.3.6.1.4.1.119.2.3.69.203.513.501.3.9.1.1.1.3
    tcn15minDataRadioNEAddress OBJECT-TYPE
        SYNTAX      IpAddress
        ACCESS      not-accessible
        STATUS      mandatory
        DESCRIPTION
            "reserved."
        ::= { tcn15minDataRadioEntry 3 }
    
    -- 1.3.6.1.4.1.119.2.3.69.203.513.501.3.9.1.1.1.4
    tcn15minDataRf OBJECT-TYPE
        SYNTAX      SeverityValue
        ACCESS      read-only
        STATUS      mandatory
        DESCRIPTION
            "TCN MODEM 15 minutes RF Monitoring Alarm per counting item."
        ::= { tcn15minDataRadioEntry 4 }
    
    -- 1.3.6.1.4.1.119.2.3.69.203.513.501.3.9.1.2
    tcn15minRxLevTable OBJECT-TYPE
        SYNTAX      SEQUENCE OF Tcn15minRxLevEntry
        ACCESS      not-accessible
        STATUS      mandatory
        DESCRIPTION
            "Represents Threshold Crossing Alarm Status of 15 minutes Rx
             Level Alarm."
        ::= { tcn15minDataRadioGroup 2 }
    
    -- 1.3.6.1.4.1.119.2.3.69.203.513.501.3.9.1.2.1
    tcn15minRxLevEntry OBJECT-TYPE
        SYNTAX      Tcn15minRxLevEntry
        ACCESS      not-accessible
        STATUS      mandatory
        DESCRIPTION
            ""
        INDEX       { tcn15minRxLevNEAddress, tcn15minRxLevIfIndex }
        ::= { tcn15minRxLevTable 1 }
    
    Tcn15minRxLevEntry ::= SEQUENCE {
        tcn15minRxLevIfIndex    InterfaceIndex,
        tcn15minRxLevNEAddress  IpAddress,
        tcn15minRxLev           SeverityValue
    }
    
    -- 1.3.6.1.4.1.119.2.3.69.203.513.501.3.9.1.2.1.1
    tcn15minRxLevIfIndex OBJECT-TYPE
        SYNTAX      InterfaceIndex
        ACCESS      not-accessible
        STATUS      mandatory
        DESCRIPTION
            "Index of this table. Unique number of the radio interface."
        ::= { tcn15minRxLevEntry 1 }
    
    -- 1.3.6.1.4.1.119.2.3.69.203.513.501.3.9.1.2.1.2
    tcn15minRxLevNEAddress OBJECT-TYPE
        SYNTAX      IpAddress
        ACCESS      not-accessible
        STATUS      mandatory
        DESCRIPTION
            "reserved"
        ::= { tcn15minRxLevEntry 2 }
    
    -- 1.3.6.1.4.1.119.2.3.69.203.513.501.3.9.1.2.1.3
    tcn15minRxLev OBJECT-TYPE
        SYNTAX      SeverityValue
        ACCESS      read-only
        STATUS      mandatory
        DESCRIPTION
            "TCN MODEM 15 minutes RX Level (Min) Alarm."
        ::= { tcn15minRxLevEntry 3 }
    
    -- 1.3.6.1.4.1.119.2.3.69.203.513.501.3.9.2
    tcn15minDataCableGroup OBJECT IDENTIFIER
        ::= { asTCNGroup 2 }
    
    -- 1.3.6.1.4.1.119.2.3.69.203.513.501.3.9.2.1
    tcn15minDataThroughModeGroup OBJECT IDENTIFIER
        ::= { tcn15minDataCableGroup 1 }
    
    -- 1.3.6.1.4.1.119.2.3.69.203.513.501.3.9.2.1.1
    tcn15minDataTmRsTable OBJECT-TYPE
        SYNTAX      SEQUENCE OF Tcn15minDataTmRsEntry
        ACCESS      not-accessible
        STATUS      mandatory
        DESCRIPTION
            "Represents Threshold Crossing Alarm of 15 minutes PMON for RS
             Layer of through mode STM-1."
        ::= { tcn15minDataThroughModeGroup 1 }
    
    -- 1.3.6.1.4.1.119.2.3.69.203.513.501.3.9.2.1.1.1
    tcn15minDataTmRsEntry OBJECT-TYPE
        SYNTAX      Tcn15minDataTmRsEntry
        ACCESS      not-accessible
        STATUS      mandatory
        DESCRIPTION
            ""
        INDEX       { tcn15minDataTmRsNEAddress, tcn15minDataTmRsIfIndex, tcn15minDataTmRsMonitorName }
        ::= { tcn15minDataTmRsTable 1 }
    
    Tcn15minDataTmRsEntry ::= SEQUENCE {
        tcn15minDataTmRsIfIndex         InterfaceIndex,
        tcn15minDataTmRsMonitorName     INTEGER,
        tcn15minDataTmRsNEAddress       IpAddress,
        tcn15minDataTmRs                SeverityValue
    }
    
    -- 1.3.6.1.4.1.119.2.3.69.203.513.501.3.9.2.1.1.1.1
    tcn15minDataTmRsIfIndex OBJECT-TYPE
        SYNTAX      InterfaceIndex
        ACCESS      not-accessible
        STATUS      mandatory
        DESCRIPTION
            "Index of this table. Unique number of the STM-1 interface."
        ::= { tcn15minDataTmRsEntry 1 }
    
    -- 1.3.6.1.4.1.119.2.3.69.203.513.501.3.9.2.1.1.1.2
    tcn15minDataTmRsMonitorName OBJECT-TYPE
        SYNTAX      INTEGER { bbe(1), es(2), ses(3), sep(4), uas(5), ofs(6) }
        ACCESS      not-accessible
        STATUS      mandatory
        DESCRIPTION
            "Index of this table. The index value shows counting item."
        ::= { tcn15minDataTmRsEntry 2 }
    
    -- 1.3.6.1.4.1.119.2.3.69.203.513.501.3.9.2.1.1.1.3
    tcn15minDataTmRsNEAddress OBJECT-TYPE
        SYNTAX      IpAddress
        ACCESS      not-accessible
        STATUS      mandatory
        DESCRIPTION
            "reserved"
        ::= { tcn15minDataTmRsEntry 3 }
    
    -- 1.3.6.1.4.1.119.2.3.69.203.513.501.3.9.2.1.1.1.4
    tcn15minDataTmRs OBJECT-TYPE
        SYNTAX      SeverityValue
        ACCESS      read-only
        STATUS      mandatory
        DESCRIPTION
            "TCN STM-1 15 minutes (Through Mode) RS Monitoring Alarm."
        ::= { tcn15minDataTmRsEntry 4 }
    
    -- 1.3.6.1.4.1.119.2.3.69.203.513.501.3.9.2.1.2
    tcn15minDataTmDMRRsTable OBJECT-TYPE
        SYNTAX      SEQUENCE OF Tcn15minDataTmDMRRsEntry
        ACCESS      not-accessible
        STATUS      mandatory
        DESCRIPTION
            "Represents Threshold Crossing Alarm of 15 minutes PMON for DMR
             RS Layer of STM-1"
        ::= { tcn15minDataThroughModeGroup 2 }
    
    -- 1.3.6.1.4.1.119.2.3.69.203.513.501.3.9.2.1.2.1
    tcn15minDataTmDMRRsEntry OBJECT-TYPE
        SYNTAX      Tcn15minDataTmDMRRsEntry
        ACCESS      not-accessible
        STATUS      mandatory
        DESCRIPTION
            ""
        INDEX       { tcn15minDataTmDMRRsNEAddress, tcn15minDataTmDMRRsIfIndex,
                      tcn15minDataTmDMRRsMonitorName }
        ::= { tcn15minDataTmDMRRsTable 1 }
    
    Tcn15minDataTmDMRRsEntry ::= SEQUENCE {
        tcn15minDataTmDMRRsIfIndex      InterfaceIndex,
        tcn15minDataTmDMRRsMonitorName  INTEGER,
        tcn15minDataTmDMRRsNEAddress    IpAddress,
        tcn15minDataTmDMRRs             SeverityValue
    }
    
    -- 1.3.6.1.4.1.119.2.3.69.203.513.501.3.9.2.1.2.1.1
    tcn15minDataTmDMRRsIfIndex OBJECT-TYPE
        SYNTAX      InterfaceIndex
        ACCESS      not-accessible
        STATUS      mandatory
        DESCRIPTION
            "Index of this table. Unique number of the STM-1 interface."
        ::= { tcn15minDataTmDMRRsEntry 1 }
    
    -- 1.3.6.1.4.1.119.2.3.69.203.513.501.3.9.2.1.2.1.2
    tcn15minDataTmDMRRsMonitorName OBJECT-TYPE
        SYNTAX      INTEGER { bbe(1), es(2), ses(3), sep(4), uas(5), ofs(6) }
        ACCESS      not-accessible
        STATUS      mandatory
        DESCRIPTION
            "Index of this table. The index value shows counting item."
        ::= { tcn15minDataTmDMRRsEntry 2 }
    
    -- 1.3.6.1.4.1.119.2.3.69.203.513.501.3.9.2.1.2.1.3
    tcn15minDataTmDMRRsNEAddress OBJECT-TYPE
        SYNTAX      IpAddress
        ACCESS      not-accessible
        STATUS      mandatory
        DESCRIPTION
            "reserved."
        ::= { tcn15minDataTmDMRRsEntry 3 }
    
    -- 1.3.6.1.4.1.119.2.3.69.203.513.501.3.9.2.1.2.1.4
    tcn15minDataTmDMRRs OBJECT-TYPE
        SYNTAX      SeverityValue
        ACCESS      read-only
        STATUS      mandatory
        DESCRIPTION
            "TCN STM-1 15 minutes (Through Mode)DMR RS Monitoring Alarm."
        ::= { tcn15minDataTmDMRRsEntry 4 }
    
    -- 1.3.6.1.4.1.119.2.3.69.203.513.501.3.9.2.2
    tcn15minDataChannelizedModeGroup OBJECT IDENTIFIER
        ::= { tcn15minDataCableGroup 2 }
    
    -- 1.3.6.1.4.1.119.2.3.69.203.513.501.3.9.2.2.1
    tcn15minDataChRsTable OBJECT-TYPE
        SYNTAX      SEQUENCE OF Tcn15minDataChRsEntry
        ACCESS      not-accessible
        STATUS      mandatory
        DESCRIPTION
            "Represents Threshold Crossing Alarm of 15 minutes PMON for
             Channelized Mode RS Layer of STM-1."
        ::= { tcn15minDataChannelizedModeGroup 1 }
    
    -- 1.3.6.1.4.1.119.2.3.69.203.513.501.3.9.2.2.1.1
    tcn15minDataChRsEntry OBJECT-TYPE
        SYNTAX      Tcn15minDataChRsEntry
        ACCESS      not-accessible
        STATUS      mandatory
        DESCRIPTION
            ""
        INDEX       { tcn15minDataChRsNEAddress, tcn15minDataChRsIfIndex, tcn15minDataChRsMonitorName }
        ::= { tcn15minDataChRsTable 1 }
    
    Tcn15minDataChRsEntry ::= SEQUENCE {
        tcn15minDataChRsIfIndex         InterfaceIndex,
        tcn15minDataChRsMonitorName     INTEGER,
        tcn15minDataChRsNEAddress       IpAddress,
        tcn15minDataChRs                SeverityValue
    }
    
    -- 1.3.6.1.4.1.119.2.3.69.203.513.501.3.9.2.2.1.1.1
    tcn15minDataChRsIfIndex OBJECT-TYPE
        SYNTAX      InterfaceIndex
        ACCESS      not-accessible
        STATUS      mandatory
        DESCRIPTION
            "Index of this table. Unique number of the STM-1 interface."
        ::= { tcn15minDataChRsEntry 1 }
    
    -- 1.3.6.1.4.1.119.2.3.69.203.513.501.3.9.2.2.1.1.2
    tcn15minDataChRsMonitorName OBJECT-TYPE
        SYNTAX      INTEGER { bbe(1), es(2), ses(3), sep(4), uas(5), ofs(6) }
        ACCESS      not-accessible
        STATUS      mandatory
        DESCRIPTION
            "Index of this table. The index value shows counting item."
        ::= { tcn15minDataChRsEntry 2 }
    
    -- 1.3.6.1.4.1.119.2.3.69.203.513.501.3.9.2.2.1.1.3
    tcn15minDataChRsNEAddress OBJECT-TYPE
        SYNTAX      IpAddress
        ACCESS      not-accessible
        STATUS      mandatory
        DESCRIPTION
            "reserved."
        ::= { tcn15minDataChRsEntry 3 }
    
    -- 1.3.6.1.4.1.119.2.3.69.203.513.501.3.9.2.2.1.1.4
    tcn15minDataChRs OBJECT-TYPE
        SYNTAX      SeverityValue
        ACCESS      read-only
        STATUS      mandatory
        DESCRIPTION
            "TCN STM-1 15 minutes (Channelized Mode) RS Monitoring Alarm per
             counting item."
        ::= { tcn15minDataChRsEntry 4 }
    
    -- 1.3.6.1.4.1.119.2.3.69.203.513.501.3.9.2.2.2
    tcn15minDataChMsTable OBJECT-TYPE
        SYNTAX      SEQUENCE OF Tcn15minDataChMsEntry
        ACCESS      not-accessible
        STATUS      mandatory
        DESCRIPTION
            "Represents Threshold Crossing Alarm of 15 minutes PMON for
             Channelized Mode MS Layer of STM-1."
        ::= { tcn15minDataChannelizedModeGroup 2 }
    
    -- 1.3.6.1.4.1.119.2.3.69.203.513.501.3.9.2.2.2.1
    tcn15minDataChMsEntry OBJECT-TYPE
        SYNTAX      Tcn15minDataChMsEntry
        ACCESS      not-accessible
        STATUS      mandatory
        DESCRIPTION
            ""
        INDEX       { tcn15minDataChMsNEAddress, tcn15minDataChMsIfIndex, tcn15minDataChMsMonitorName }
        ::= { tcn15minDataChMsTable 1 }
    
    Tcn15minDataChMsEntry ::= SEQUENCE {
        tcn15minDataChMsIfIndex         InterfaceIndex,
        tcn15minDataChMsMonitorName     INTEGER,
        tcn15minDataChMsNEAddress       IpAddress,
        tcn15minDataChMs                SeverityValue
    }
    
    -- 1.3.6.1.4.1.119.2.3.69.203.513.501.3.9.2.2.2.1.1
    tcn15minDataChMsIfIndex OBJECT-TYPE
        SYNTAX      InterfaceIndex
        ACCESS      not-accessible
        STATUS      mandatory
        DESCRIPTION
            "Index of this table. Unique number of the STM-1 interface."
        ::= { tcn15minDataChMsEntry 1 }
    
    -- 1.3.6.1.4.1.119.2.3.69.203.513.501.3.9.2.2.2.1.2
    tcn15minDataChMsMonitorName OBJECT-TYPE
        SYNTAX      INTEGER { bbe(1), es(2), ses(3), sep(4), uas(5) }
        ACCESS      not-accessible
        STATUS      mandatory
        DESCRIPTION
            "Index of this table. The index value shows counting item."
        ::= { tcn15minDataChMsEntry 2 }
    
    -- 1.3.6.1.4.1.119.2.3.69.203.513.501.3.9.2.2.2.1.3
    tcn15minDataChMsNEAddress OBJECT-TYPE
        SYNTAX      IpAddress
        ACCESS      not-accessible
        STATUS      mandatory
        DESCRIPTION
            "reserved"
        ::= { tcn15minDataChMsEntry 3 }
    
    -- 1.3.6.1.4.1.119.2.3.69.203.513.501.3.9.2.2.2.1.4
    tcn15minDataChMs OBJECT-TYPE
        SYNTAX      SeverityValue
        ACCESS      read-only
        STATUS      mandatory
        DESCRIPTION
            "TCN STM-1 15 minutes (Channelized Mode) MS Monitoring Alarm."
        ::= { tcn15minDataChMsEntry 4 }
    
    -- 1.3.6.1.4.1.119.2.3.69.203.513.501.3.9.2.3
    tcn15minData16E1Group OBJECT IDENTIFIER
        ::= { tcn15minDataCableGroup 3 }
    
    -- 1.3.6.1.4.1.119.2.3.69.203.513.501.3.9.2.3.1
    tcn15minData16E1PdhTable OBJECT-TYPE
        SYNTAX      SEQUENCE OF Tcn15minData16E1PdhEntry
        ACCESS      not-accessible
        STATUS      mandatory
        DESCRIPTION
            "Represents Threshold Crossing Alarm of 15 minutes PMON for E1
             Channel."
        ::= { tcn15minData16E1Group 1 }
    
    -- 1.3.6.1.4.1.119.2.3.69.203.513.501.3.9.2.3.1.1
    tcn15minData16E1PdhEntry OBJECT-TYPE
        SYNTAX      Tcn15minData16E1PdhEntry
        ACCESS      not-accessible
        STATUS      mandatory
        DESCRIPTION
            ""
        INDEX       { tcn15minData16E1PdhNEAddress, tcn15minData16E1PdhIfIndex,
                      tcn15minData16E1PdhMonitorName }
        ::= { tcn15minData16E1PdhTable 1 }
    
    Tcn15minData16E1PdhEntry ::= SEQUENCE {
        tcn15minData16E1PdhIfIndex      InterfaceIndex,
        tcn15minData16E1PdhMonitorName  INTEGER,
        tcn15minData16E1PdhNEAddress    IpAddress,
        tcn15minData16E1Pdh             SeverityValue
    }
    
    -- 1.3.6.1.4.1.119.2.3.69.203.513.501.3.9.2.3.1.1.1
    tcn15minData16E1PdhIfIndex OBJECT-TYPE
        SYNTAX      InterfaceIndex
        ACCESS      not-accessible
        STATUS      mandatory
        DESCRIPTION
            "Index of this table. Unique number of the E1 interface."
        ::= { tcn15minData16E1PdhEntry 1 }
    
    -- 1.3.6.1.4.1.119.2.3.69.203.513.501.3.9.2.3.1.1.2
    tcn15minData16E1PdhMonitorName OBJECT-TYPE
        SYNTAX      INTEGER { cv(1) }
        ACCESS      not-accessible
        STATUS      mandatory
        DESCRIPTION
            "Index of this table. The index value shows counting item."
        ::= { tcn15minData16E1PdhEntry 2 }
    
    -- 1.3.6.1.4.1.119.2.3.69.203.513.501.3.9.2.3.1.1.3
    tcn15minData16E1PdhNEAddress OBJECT-TYPE
        SYNTAX      IpAddress
        ACCESS      not-accessible
        STATUS      mandatory
        DESCRIPTION
            "reserved"
        ::= { tcn15minData16E1PdhEntry 3 }
    
    -- 1.3.6.1.4.1.119.2.3.69.203.513.501.3.9.2.3.1.1.4
    tcn15minData16E1Pdh OBJECT-TYPE
        SYNTAX      SeverityValue
        ACCESS      read-only
        STATUS      mandatory
        DESCRIPTION
            "TCN 15 minutes E1 CV Alarm."
        ::= { tcn15minData16E1PdhEntry 4 }
    
    -- 1.3.6.1.4.1.119.2.3.69.203.513.501.3.9.3
    tcn1dayDataRadioGroup OBJECT IDENTIFIER
        ::= { asTCNGroup 3 }
    
    -- 1.3.6.1.4.1.119.2.3.69.203.513.501.3.9.3.1
    tcn1dayDataRadioTable OBJECT-TYPE
        SYNTAX      SEQUENCE OF Tcn1dayDataRadioEntry
        ACCESS      not-accessible
        STATUS      mandatory
        DESCRIPTION
            "Represents Threashold Crossing Alarm Status of 1 day PMON for
             Radio."
        ::= { tcn1dayDataRadioGroup 1 }
    
    -- 1.3.6.1.4.1.119.2.3.69.203.513.501.3.9.3.1.1
    tcn1dayDataRadioEntry OBJECT-TYPE
        SYNTAX      Tcn1dayDataRadioEntry
        ACCESS      not-accessible
        STATUS      mandatory
        DESCRIPTION
            ""
        INDEX       { tcn1dayDataRadioNEAddress, tcn1dayDataModemIfIndex, tcn1dayDataModemMonitorName }
        ::= { tcn1dayDataRadioTable 1 }
    
    Tcn1dayDataRadioEntry ::= SEQUENCE {
        tcn1dayDataModemIfIndex         InterfaceIndex,
        tcn1dayDataModemMonitorName     INTEGER,
        tcn1dayDataRadioNEAddress       IpAddress,
        tcn1dayDataRf                   SeverityValue
    }
    
    -- 1.3.6.1.4.1.119.2.3.69.203.513.501.3.9.3.1.1.1
    tcn1dayDataModemIfIndex OBJECT-TYPE
        SYNTAX      InterfaceIndex
        ACCESS      not-accessible
        STATUS      mandatory
        DESCRIPTION
            "Index of this table. Unique number of the radio interface."
        ::= { tcn1dayDataRadioEntry 1 }
    
    -- 1.3.6.1.4.1.119.2.3.69.203.513.501.3.9.3.1.1.2
    tcn1dayDataModemMonitorName OBJECT-TYPE
        SYNTAX      INTEGER { bbe(1), es(2), ses(3), sep(4), uas(5), ofs(6) }
        ACCESS      not-accessible
        STATUS      mandatory
        DESCRIPTION
            "Index of this table. The index value shows counting item."
        ::= { tcn1dayDataRadioEntry 2 }
    
    -- 1.3.6.1.4.1.119.2.3.69.203.513.501.3.9.3.1.1.3
    tcn1dayDataRadioNEAddress OBJECT-TYPE
        SYNTAX      IpAddress
        ACCESS      not-accessible
        STATUS      mandatory
        DESCRIPTION
            "reserved"
        ::= { tcn1dayDataRadioEntry 3 }
    
    -- 1.3.6.1.4.1.119.2.3.69.203.513.501.3.9.3.1.1.4
    tcn1dayDataRf OBJECT-TYPE
        SYNTAX      SeverityValue
        ACCESS      read-only
        STATUS      mandatory
        DESCRIPTION
            "TCN MODEM 1 day RF Monitoring Alarm per counting item."
        ::= { tcn1dayDataRadioEntry 4 }
    
    -- 1.3.6.1.4.1.119.2.3.69.203.513.501.3.9.3.2
    tcn1dayRxLevTable OBJECT-TYPE
        SYNTAX      SEQUENCE OF Tcn1dayRxLevEntry
        ACCESS      not-accessible
        STATUS      mandatory
        DESCRIPTION
            "Represents Threshold Crossing Alarm Status of 1 day Rx Level
             Alarm."
        ::= { tcn1dayDataRadioGroup 2 }
    
    -- 1.3.6.1.4.1.119.2.3.69.203.513.501.3.9.3.2.1
    tcn1dayRxLevEntry OBJECT-TYPE
        SYNTAX      Tcn1dayRxLevEntry
        ACCESS      not-accessible
        STATUS      mandatory
        DESCRIPTION
            ""
        INDEX       { tcn1dayRxLevNEAddress, tcn1dayRxLevIfIndex }
        ::= { tcn1dayRxLevTable 1 }
    
    Tcn1dayRxLevEntry ::= SEQUENCE {
        tcn1dayRxLevIfIndex     InterfaceIndex,
        tcn1dayRxLevNEAddress   IpAddress,
        tcn1dayRxLev            SeverityValue
    }
    
    -- 1.3.6.1.4.1.119.2.3.69.203.513.501.3.9.3.2.1.1
    tcn1dayRxLevIfIndex OBJECT-TYPE
        SYNTAX      InterfaceIndex
        ACCESS      not-accessible
        STATUS      mandatory
        DESCRIPTION
            "Index of this table. Unique number of the radio interface."
        ::= { tcn1dayRxLevEntry 1 }
    
    -- 1.3.6.1.4.1.119.2.3.69.203.513.501.3.9.3.2.1.2
    tcn1dayRxLevNEAddress OBJECT-TYPE
        SYNTAX      IpAddress
        ACCESS      not-accessible
        STATUS      mandatory
        DESCRIPTION
            "reserved"
        ::= { tcn1dayRxLevEntry 2 }
    
    -- 1.3.6.1.4.1.119.2.3.69.203.513.501.3.9.3.2.1.3
    tcn1dayRxLev OBJECT-TYPE
        SYNTAX      SeverityValue
        ACCESS      read-only
        STATUS      mandatory
        DESCRIPTION
            "TCN MODEM 1 day RX Level (Min) Alarm."
        ::= { tcn1dayRxLevEntry 3 }
    
    -- 1.3.6.1.4.1.119.2.3.69.203.513.501.3.9.4
    tcn1dayDataCableGroup OBJECT IDENTIFIER
        ::= { asTCNGroup 4 }
    
    -- 1.3.6.1.4.1.119.2.3.69.203.513.501.3.9.4.1
    tcn1dayDataThroughModeGroup OBJECT IDENTIFIER
        ::= { tcn1dayDataCableGroup 1 }
    
    -- 1.3.6.1.4.1.119.2.3.69.203.513.501.3.9.4.1.1
    tcn1dayDataTmRsTable OBJECT-TYPE
        SYNTAX      SEQUENCE OF Tcn1dayDataTmRsEntry
        ACCESS      not-accessible
        STATUS      mandatory
        DESCRIPTION
            "Represents Threshold Crossing Alarm of 1 day PMON for RS Layer
             of through mode STM-1."
        ::= { tcn1dayDataThroughModeGroup 1 }
    
    -- 1.3.6.1.4.1.119.2.3.69.203.513.501.3.9.4.1.1.1
    tcn1dayDataTmRsEntry OBJECT-TYPE
        SYNTAX      Tcn1dayDataTmRsEntry
        ACCESS      not-accessible
        STATUS      mandatory
        DESCRIPTION
            ""
        INDEX       { tcn1dayDataTmRsNEAddress, tcn1dayDataTmRsIfIndex, tcn1dayDataTmRsMonitorName }
        ::= { tcn1dayDataTmRsTable 1 }
    
    Tcn1dayDataTmRsEntry ::= SEQUENCE {
        tcn1dayDataTmRsIfIndex      InterfaceIndex,
        tcn1dayDataTmRsMonitorName  INTEGER,
        tcn1dayDataTmRsNEAddress    IpAddress,
        tcn1dayDataTmRs             SeverityValue
    }
    
    -- 1.3.6.1.4.1.119.2.3.69.203.513.501.3.9.4.1.1.1.1
    tcn1dayDataTmRsIfIndex OBJECT-TYPE
        SYNTAX      InterfaceIndex
        ACCESS      not-accessible
        STATUS      mandatory
        DESCRIPTION
            "Index of this table. Unique number of the STM-1 interface."
        ::= { tcn1dayDataTmRsEntry 1 }
    
    -- 1.3.6.1.4.1.119.2.3.69.203.513.501.3.9.4.1.1.1.2
    tcn1dayDataTmRsMonitorName OBJECT-TYPE
        SYNTAX      INTEGER { bbe(1), es(2), ses(3), sep(4), uas(5), ofs(6) }
        ACCESS      not-accessible
        STATUS      mandatory
        DESCRIPTION
            "Index of this table. The index value shows counting item."
        ::= { tcn1dayDataTmRsEntry 2 }
    
    -- 1.3.6.1.4.1.119.2.3.69.203.513.501.3.9.4.1.1.1.3
    tcn1dayDataTmRsNEAddress OBJECT-TYPE
        SYNTAX      IpAddress
        ACCESS      not-accessible
        STATUS      mandatory
        DESCRIPTION
            "reserved"
        ::= { tcn1dayDataTmRsEntry 3 }
    
    -- 1.3.6.1.4.1.119.2.3.69.203.513.501.3.9.4.1.1.1.4
    tcn1dayDataTmRs OBJECT-TYPE
        SYNTAX      SeverityValue
        ACCESS      read-only
        STATUS      mandatory
        DESCRIPTION
            "TCN STM-1 1 day (Through Mode) RS Monitoring Alarm."
        ::= { tcn1dayDataTmRsEntry 4 }
    
    -- 1.3.6.1.4.1.119.2.3.69.203.513.501.3.9.4.1.2
    tcn1dayDataTmDMRRsTable OBJECT-TYPE
        SYNTAX      SEQUENCE OF Tcn1dayDataTmDMRRsEntry
        ACCESS      not-accessible
        STATUS      mandatory
        DESCRIPTION
            "Represents Threshold Crossing Alarm of 1 day PMON for DMR RS
             Layer of STM-1"
        ::= { tcn1dayDataThroughModeGroup 2 }
    
    -- 1.3.6.1.4.1.119.2.3.69.203.513.501.3.9.4.1.2.1
    tcn1dayDataTmDMRRsEntry OBJECT-TYPE
        SYNTAX      Tcn1dayDataTmDMRRsEntry
        ACCESS      not-accessible
        STATUS      mandatory
        DESCRIPTION
            ""
        INDEX       { tcn1dayDataTmDMRRsNEAddress, tcn1dayDataTmDMRRsIfIndex,
                      tcn1dayDataTmDMRRsMonitorName }
        ::= { tcn1dayDataTmDMRRsTable 1 }
    
    Tcn1dayDataTmDMRRsEntry ::= SEQUENCE {
        tcn1dayDataTmDMRRsIfIndex       InterfaceIndex,
        tcn1dayDataTmDMRRsMonitorName   INTEGER,
        tcn1dayDataTmDMRRsNEAddress     IpAddress,
        tcn1dayDataTmDMRRs              SeverityValue
    }
    
    -- 1.3.6.1.4.1.119.2.3.69.203.513.501.3.9.4.1.2.1.1
    tcn1dayDataTmDMRRsIfIndex OBJECT-TYPE
        SYNTAX      InterfaceIndex
        ACCESS      not-accessible
        STATUS      mandatory
        DESCRIPTION
            "Index of this table. Unique number of the STM-1 interface."
        ::= { tcn1dayDataTmDMRRsEntry 1 }
    
    -- 1.3.6.1.4.1.119.2.3.69.203.513.501.3.9.4.1.2.1.2
    tcn1dayDataTmDMRRsMonitorName OBJECT-TYPE
        SYNTAX      INTEGER { bbe(1), es(2), ses(3), sep(4), uas(5), ofs(6) }
        ACCESS      not-accessible
        STATUS      mandatory
        DESCRIPTION
            "Index of this table. The index value shows counting item."
        ::= { tcn1dayDataTmDMRRsEntry 2 }
    
    -- 1.3.6.1.4.1.119.2.3.69.203.513.501.3.9.4.1.2.1.3
    tcn1dayDataTmDMRRsNEAddress OBJECT-TYPE
        SYNTAX      IpAddress
        ACCESS      not-accessible
        STATUS      mandatory
        DESCRIPTION
            "reserved"
        ::= { tcn1dayDataTmDMRRsEntry 3 }
    
    -- 1.3.6.1.4.1.119.2.3.69.203.513.501.3.9.4.1.2.1.4
    tcn1dayDataTmDMRRs OBJECT-TYPE
        SYNTAX      SeverityValue
        ACCESS      read-only
        STATUS      mandatory
        DESCRIPTION
            "TCN STM-1 1 day (Through Mode)DMR RS Monitoring Alarm."
        ::= { tcn1dayDataTmDMRRsEntry 4 }
    
    -- 1.3.6.1.4.1.119.2.3.69.203.513.501.3.9.4.2
    tcn1dayDataChannelizedModeGroup OBJECT IDENTIFIER
        ::= { tcn1dayDataCableGroup 2 }
    
    -- 1.3.6.1.4.1.119.2.3.69.203.513.501.3.9.4.2.1
    tcn1dayDataChRsTable OBJECT-TYPE
        SYNTAX      SEQUENCE OF Tcn1dayDataChRsEntry
        ACCESS      not-accessible
        STATUS      mandatory
        DESCRIPTION
            "Represents Threshold Crossing Alarm of 1 day PMON for
             Channelized Mode RS Layer of STM-1."
        ::= { tcn1dayDataChannelizedModeGroup 1 }
    
    -- 1.3.6.1.4.1.119.2.3.69.203.513.501.3.9.4.2.1.1
    tcn1dayDataChRsEntry OBJECT-TYPE
        SYNTAX      Tcn1dayDataChRsEntry
        ACCESS      not-accessible
        STATUS      mandatory
        DESCRIPTION
            ""
        INDEX       { tcn1dayDataChRsNEAddress, tcn1dayDataChRsIfIndex, tcn1dayDataChRsMonitorName }
        ::= { tcn1dayDataChRsTable 1 }
    
    Tcn1dayDataChRsEntry ::= SEQUENCE {
        tcn1dayDataChRsIfIndex      InterfaceIndex,
        tcn1dayDataChRsMonitorName  INTEGER,
        tcn1dayDataChRsNEAddress    IpAddress,
        tcn1dayDataChRs             SeverityValue
    }
    
    -- 1.3.6.1.4.1.119.2.3.69.203.513.501.3.9.4.2.1.1.1
    tcn1dayDataChRsIfIndex OBJECT-TYPE
        SYNTAX      InterfaceIndex
        ACCESS      not-accessible
        STATUS      mandatory
        DESCRIPTION
            "Index of this table. Unique number of the STM-1 interface."
        ::= { tcn1dayDataChRsEntry 1 }
    
    -- 1.3.6.1.4.1.119.2.3.69.203.513.501.3.9.4.2.1.1.2
    tcn1dayDataChRsMonitorName OBJECT-TYPE
        SYNTAX      INTEGER { bbe(1), es(2), ses(3), sep(4), uas(5), ofs(6) }
        ACCESS      not-accessible
        STATUS      mandatory
        DESCRIPTION
            "Index of this table. The index value shows counting item."
        ::= { tcn1dayDataChRsEntry 2 }
    
    -- 1.3.6.1.4.1.119.2.3.69.203.513.501.3.9.4.2.1.1.3
    tcn1dayDataChRsNEAddress OBJECT-TYPE
        SYNTAX      IpAddress
        ACCESS      not-accessible
        STATUS      mandatory
        DESCRIPTION
            "reserved"
        ::= { tcn1dayDataChRsEntry 3 }
    
    -- 1.3.6.1.4.1.119.2.3.69.203.513.501.3.9.4.2.1.1.4
    tcn1dayDataChRs OBJECT-TYPE
        SYNTAX      SeverityValue
        ACCESS      read-only
        STATUS      mandatory
        DESCRIPTION
            "TCN STM-1 1 day (Channelized Mode) RS Monitoring Alarm per
             counting item."
        ::= { tcn1dayDataChRsEntry 4 }
    
    -- 1.3.6.1.4.1.119.2.3.69.203.513.501.3.9.4.2.2
    tcn1dayDataChMsTable OBJECT-TYPE
        SYNTAX      SEQUENCE OF Tcn1dayDataChMsEntry
        ACCESS      not-accessible
        STATUS      mandatory
        DESCRIPTION
            "Represents Threshold Crossing Alarm of 1 day PMON for
             Channelized Mode MS Layer of STM-1."
        ::= { tcn1dayDataChannelizedModeGroup 2 }
    
    -- 1.3.6.1.4.1.119.2.3.69.203.513.501.3.9.4.2.2.1
    tcn1dayDataChMsEntry OBJECT-TYPE
        SYNTAX      Tcn1dayDataChMsEntry
        ACCESS      not-accessible
        STATUS      mandatory
        DESCRIPTION
            ""
        INDEX       { tcn1dayDataChMsNEAddress, tcn1dayDataChMsIfIndex, tcn1dayDataChMsMonitorName }
        ::= { tcn1dayDataChMsTable 1 }
    
    Tcn1dayDataChMsEntry ::= SEQUENCE {
        tcn1dayDataChMsIfIndex      InterfaceIndex,
        tcn1dayDataChMsMonitorName  INTEGER,
        tcn1dayDataChMsNEAddress    IpAddress,
        tcn1dayDataChMs             SeverityValue
    }
    
    -- 1.3.6.1.4.1.119.2.3.69.203.513.501.3.9.4.2.2.1.1
    tcn1dayDataChMsIfIndex OBJECT-TYPE
        SYNTAX      InterfaceIndex
        ACCESS      not-accessible
        STATUS      mandatory
        DESCRIPTION
            "Index of this table. Unique number of the STM-1 interface."
        ::= { tcn1dayDataChMsEntry 1 }
    
    -- 1.3.6.1.4.1.119.2.3.69.203.513.501.3.9.4.2.2.1.2
    tcn1dayDataChMsMonitorName OBJECT-TYPE
        SYNTAX      INTEGER { bbe(1), es(2), ses(3), sep(4), uas(5) }
        ACCESS      not-accessible
        STATUS      mandatory
        DESCRIPTION
            "Index of this table. The index value shows counting item."
        ::= { tcn1dayDataChMsEntry 2 }
    
    -- 1.3.6.1.4.1.119.2.3.69.203.513.501.3.9.4.2.2.1.3
    tcn1dayDataChMsNEAddress OBJECT-TYPE
        SYNTAX      IpAddress
        ACCESS      not-accessible
        STATUS      mandatory
        DESCRIPTION
            "reserved"
        ::= { tcn1dayDataChMsEntry 3 }
    
    -- 1.3.6.1.4.1.119.2.3.69.203.513.501.3.9.4.2.2.1.4
    tcn1dayDataChMs OBJECT-TYPE
        SYNTAX      SeverityValue
        ACCESS      read-only
        STATUS      mandatory
        DESCRIPTION
            "TCN STM-1 1 day (Channelized Mode) MS Monitoring Alarm."
        ::= { tcn1dayDataChMsEntry 4 }
    
    -- 1.3.6.1.4.1.119.2.3.69.203.513.501.3.9.4.3
    tcn1dayData16E1Group OBJECT IDENTIFIER
        ::= { tcn1dayDataCableGroup 3 }
    
    -- 1.3.6.1.4.1.119.2.3.69.203.513.501.3.9.4.3.1
    tcn1dayData16E1PdhTable OBJECT-TYPE
        SYNTAX      SEQUENCE OF Tcn1dayData16E1PdhEntry
        ACCESS      not-accessible
        STATUS      mandatory
        DESCRIPTION
            "Represents Threshold Crossing Alarm of 1 day PMON for E1
             Channel."
        ::= { tcn1dayData16E1Group 1 }
    
    -- 1.3.6.1.4.1.119.2.3.69.203.513.501.3.9.4.3.1.1
    tcn1dayData16E1PdhEntry OBJECT-TYPE
        SYNTAX      Tcn1dayData16E1PdhEntry
        ACCESS      not-accessible
        STATUS      mandatory
        DESCRIPTION
            ""
        INDEX       { tcn1dayData16E1PdhNEAddress, tcn1dayData16E1PdhIfIndex,
                      tcn1dayData16E1PdhMonitorName }
        ::= { tcn1dayData16E1PdhTable 1 }
    
    Tcn1dayData16E1PdhEntry ::= SEQUENCE {
        tcn1dayData16E1PdhIfIndex       InterfaceIndex,
        tcn1dayData16E1PdhMonitorName   INTEGER,
        tcn1dayData16E1PdhNEAddress     IpAddress,
        tcn1dayData16E1Pdh              SeverityValue
    }
    
    -- 1.3.6.1.4.1.119.2.3.69.203.513.501.3.9.4.3.1.1.1
    tcn1dayData16E1PdhIfIndex OBJECT-TYPE
        SYNTAX      InterfaceIndex
        ACCESS      not-accessible
        STATUS      mandatory
        DESCRIPTION
            "Index of this table. Unique number of the E1 interface."
        ::= { tcn1dayData16E1PdhEntry 1 }
    
    -- 1.3.6.1.4.1.119.2.3.69.203.513.501.3.9.4.3.1.1.2
    tcn1dayData16E1PdhMonitorName OBJECT-TYPE
        SYNTAX      INTEGER { cv(1) }
        ACCESS      not-accessible
        STATUS      mandatory
        DESCRIPTION
            "Index of this table. The index value shows counting item."
        ::= { tcn1dayData16E1PdhEntry 2 }
    
    -- 1.3.6.1.4.1.119.2.3.69.203.513.501.3.9.4.3.1.1.3
    tcn1dayData16E1PdhNEAddress OBJECT-TYPE
        SYNTAX      IpAddress
        ACCESS      not-accessible
        STATUS      mandatory
        DESCRIPTION
            "reserved"
        ::= { tcn1dayData16E1PdhEntry 3 }
    
    -- 1.3.6.1.4.1.119.2.3.69.203.513.501.3.9.4.3.1.1.4
    tcn1dayData16E1Pdh OBJECT-TYPE
        SYNTAX      SeverityValue
        ACCESS      read-only
        STATUS      mandatory
        DESCRIPTION
            "TCN 1 day E1 CV Alarm."
        ::= { tcn1dayData16E1PdhEntry 4 }
    
    -- 1.3.6.1.4.1.119.2.3.69.203.513.501.3.9.5
    tcn15minDataRmonGroup OBJECT IDENTIFIER
        ::= { asTCNGroup 5 }
    
    -- 1.3.6.1.4.1.119.2.3.69.203.513.501.3.9.5.1
    tcn15minDataRmonTable OBJECT-TYPE
        SYNTAX      SEQUENCE OF Tcn15minDataRmonEntry
        ACCESS      not-accessible
        STATUS      mandatory
        DESCRIPTION
            "Represents Threshold Crossing Alarm of 15 minutes RMON for
             Ethernet Port."
        ::= { tcn15minDataRmonGroup 1 }
    
    -- 1.3.6.1.4.1.119.2.3.69.203.513.501.3.9.5.1.1
    tcn15minDataRmonEntry OBJECT-TYPE
        SYNTAX      Tcn15minDataRmonEntry
        ACCESS      not-accessible
        STATUS      mandatory
        DESCRIPTION
            ""
        INDEX       { tcn15minRmonNEAddress, tcn15minRmonIfIndex }
        ::= { tcn15minDataRmonTable 1 }
    
    Tcn15minDataRmonEntry ::= SEQUENCE {
        tcn15minRmonIfIndex                 InterfaceIndex,
        tcn15minRmonNEAddress               IpAddress,
        tcn15minHCRxEthStatsDropEvents      SeverityValue,
        tcn15minHCRxEthStatsUndersizePkts   SeverityValue,
        tcn15minHCRxEthStatsFragments       SeverityValue,
        tcn15minHCRxEthStatsCRCAlignErrors  SeverityValue,
        tcn15minHCRxEthStatsOversizePkts    SeverityValue,
        tcn15minHCTxEthStatsCollisions      SeverityValue
    }
    
    -- 1.3.6.1.4.1.119.2.3.69.203.513.501.3.9.5.1.1.1
    tcn15minRmonIfIndex OBJECT-TYPE
        SYNTAX      InterfaceIndex
        ACCESS      not-accessible
        STATUS      mandatory
        DESCRIPTION
            "Index of this table. Unique number of the Ethernet Port."
        ::= { tcn15minDataRmonEntry 1 }
    
    -- 1.3.6.1.4.1.119.2.3.69.203.513.501.3.9.5.1.1.2
    tcn15minRmonNEAddress OBJECT-TYPE
        SYNTAX      IpAddress
        ACCESS      not-accessible
        STATUS      mandatory
        DESCRIPTION
            "reserved"
        ::= { tcn15minDataRmonEntry 2 }
    
    -- 1.3.6.1.4.1.119.2.3.69.203.513.501.3.9.5.1.1.3
    tcn15minHCRxEthStatsDropEvents OBJECT-TYPE
        SYNTAX      SeverityValue
        ACCESS      read-only
        STATUS      mandatory
        DESCRIPTION
            "RMON(Ethernet Port) TCN 15 minutes RX Drop Events Alarm"
        ::= { tcn15minDataRmonEntry 3 }
    
    -- 1.3.6.1.4.1.119.2.3.69.203.513.501.3.9.5.1.1.4
    tcn15minHCRxEthStatsUndersizePkts OBJECT-TYPE
        SYNTAX      SeverityValue
        ACCESS      read-only
        STATUS      mandatory
        DESCRIPTION
            "RMON(Ethernet Port) TCN 15 minutes RX Undersize Packets Alarm."
        ::= { tcn15minDataRmonEntry 4 }
    
    -- 1.3.6.1.4.1.119.2.3.69.203.513.501.3.9.5.1.1.5
    tcn15minHCRxEthStatsFragments OBJECT-TYPE
        SYNTAX      SeverityValue
        ACCESS      read-only
        STATUS      mandatory
        DESCRIPTION
            "RMON(Ethernet Port) TCN 15 minutes RX Fragments Alarm."
        ::= { tcn15minDataRmonEntry 5 }
    
    -- 1.3.6.1.4.1.119.2.3.69.203.513.501.3.9.5.1.1.6
    tcn15minHCRxEthStatsCRCAlignErrors OBJECT-TYPE
        SYNTAX      SeverityValue
        ACCESS      read-only
        STATUS      mandatory
        DESCRIPTION
            "RMON(Ethernet Port) TCN 15 minutes RX CRC Alignment Errors
             Alarm."
        ::= { tcn15minDataRmonEntry 6 }
    
    -- 1.3.6.1.4.1.119.2.3.69.203.513.501.3.9.5.1.1.7
    tcn15minHCRxEthStatsOversizePkts OBJECT-TYPE
        SYNTAX      SeverityValue
        ACCESS      read-only
        STATUS      mandatory
        DESCRIPTION
            "RMON(Ethernet Port) TCN 15 minutes RX Oversize Packets Alarm."
        ::= { tcn15minDataRmonEntry 7 }
    
    -- 1.3.6.1.4.1.119.2.3.69.203.513.501.3.9.5.1.1.8
    tcn15minHCTxEthStatsCollisions OBJECT-TYPE
        SYNTAX      SeverityValue
        ACCESS      read-only
        STATUS      mandatory
        DESCRIPTION
            "RMON(Ethernet Port) TCN 15 minutes TX Collisions Alarm."
        ::= { tcn15minDataRmonEntry 8 }
    
    -- 1.3.6.1.4.1.119.2.3.69.203.513.501.3.9.6
    tcn1dayDataRmonGroup OBJECT IDENTIFIER
        ::= { asTCNGroup 6 }
    
    -- 1.3.6.1.4.1.119.2.3.69.203.513.501.3.9.6.1
    tcn1dayDataRmonTable OBJECT-TYPE
        SYNTAX      SEQUENCE OF Tcn1dayDataRmonEntry
        ACCESS      not-accessible
        STATUS      mandatory
        DESCRIPTION
            "Represents Threshold Crossing Alarm of 1 day RMON for Ethernet
             Port"
        ::= { tcn1dayDataRmonGroup 1 }
    
    -- 1.3.6.1.4.1.119.2.3.69.203.513.501.3.9.6.1.1
    tcn1dayDataRmonEntry OBJECT-TYPE
        SYNTAX      Tcn1dayDataRmonEntry
        ACCESS      not-accessible
        STATUS      mandatory
        DESCRIPTION
            ""
        INDEX       { tcn1dayRmonNEAddress, tcn1dayRmonIfIndex }
        ::= { tcn1dayDataRmonTable 1 }
    
    Tcn1dayDataRmonEntry ::= SEQUENCE {
        tcn1dayRmonIfIndex                  InterfaceIndex,
        tcn1dayRmonNEAddress                IpAddress,
        tcn1dayHCRxEthStatsDropEvents       SeverityValue,
        tcn1dayHCRxEthStatsUndersizePkts    SeverityValue,
        tcn1dayHCRxEthStatsFragments        SeverityValue,
        tcn1dayHCRxEthStatsCRCAlignErrors   SeverityValue,
        tcn1dayHCRxEthStatsOversizePkts     SeverityValue,
        tcn1dayHCTxEthStatsCollisions       SeverityValue
    }
    
    -- 1.3.6.1.4.1.119.2.3.69.203.513.501.3.9.6.1.1.1
    tcn1dayRmonIfIndex OBJECT-TYPE
        SYNTAX      InterfaceIndex
        ACCESS      not-accessible
        STATUS      mandatory
        DESCRIPTION
            "Index of this table. Unique number of the Ethernet Port."
        ::= { tcn1dayDataRmonEntry 1 }
    
    -- 1.3.6.1.4.1.119.2.3.69.203.513.501.3.9.6.1.1.2
    tcn1dayRmonNEAddress OBJECT-TYPE
        SYNTAX      IpAddress
        ACCESS      not-accessible
        STATUS      mandatory
        DESCRIPTION
            "reserved."
        ::= { tcn1dayDataRmonEntry 2 }
    
    -- 1.3.6.1.4.1.119.2.3.69.203.513.501.3.9.6.1.1.3
    tcn1dayHCRxEthStatsDropEvents OBJECT-TYPE
        SYNTAX      SeverityValue
        ACCESS      read-only
        STATUS      mandatory
        DESCRIPTION
            "RMON(Ethernet Port) TCN 1 day RX Drop Events Alarm"
        ::= { tcn1dayDataRmonEntry 3 }
    
    -- 1.3.6.1.4.1.119.2.3.69.203.513.501.3.9.6.1.1.4
    tcn1dayHCRxEthStatsUndersizePkts OBJECT-TYPE
        SYNTAX      SeverityValue
        ACCESS      read-only
        STATUS      mandatory
        DESCRIPTION
            "RMON(Ethernet Port) TCN 1 day RX Undersize Packets Alarm."
        ::= { tcn1dayDataRmonEntry 4 }
    
    -- 1.3.6.1.4.1.119.2.3.69.203.513.501.3.9.6.1.1.5
    tcn1dayHCRxEthStatsFragments OBJECT-TYPE
        SYNTAX      SeverityValue
        ACCESS      read-only
        STATUS      mandatory
        DESCRIPTION
            "RMON(Ethernet Port) TCN 1 day RX Fragments Alarm."
        ::= { tcn1dayDataRmonEntry 5 }
    
    -- 1.3.6.1.4.1.119.2.3.69.203.513.501.3.9.6.1.1.6
    tcn1dayHCRxEthStatsCRCAlignErrors OBJECT-TYPE
        SYNTAX      SeverityValue
        ACCESS      read-only
        STATUS      mandatory
        DESCRIPTION
            "RMON(Ethernet Port) TCN 1 day RX CRC Alignment Errors Alarm."
        ::= { tcn1dayDataRmonEntry 6 }
    
    -- 1.3.6.1.4.1.119.2.3.69.203.513.501.3.9.6.1.1.7
    tcn1dayHCRxEthStatsOversizePkts OBJECT-TYPE
        SYNTAX      SeverityValue
        ACCESS      read-only
        STATUS      mandatory
        DESCRIPTION
            "RMON(Ethernet Port) TCN 1 day RX Oversize Packets Alarm."
        ::= { tcn1dayDataRmonEntry 7 }
    
    -- 1.3.6.1.4.1.119.2.3.69.203.513.501.3.9.6.1.1.8
    tcn1dayHCTxEthStatsCollisions OBJECT-TYPE
        SYNTAX      SeverityValue
        ACCESS      read-only
        STATUS      mandatory
        DESCRIPTION
            "RMON(Ethernet Port) TCN 1 day TX Collisions Alarm."
        ::= { tcn1dayDataRmonEntry 8 }
    
    -- 1.3.6.1.4.1.119.2.3.69.203.513.501.3.9.7
    tcn15minDataSfpGroup OBJECT IDENTIFIER
        ::= { asTCNGroup 7 }
    
    -- 1.3.6.1.4.1.119.2.3.69.203.513.501.3.9.7.2
    tcn15minSfpTable OBJECT-TYPE
        SYNTAX      SEQUENCE OF Tcn15minSfpEntry
        ACCESS      not-accessible
        STATUS      mandatory
        DESCRIPTION
            "Represents Threshold Crossing Alarm Status of 15 minutes ETH
             Port Sfp Tx/Rx Power."
        ::= { tcn15minDataSfpGroup 2 }
    
    -- 1.3.6.1.4.1.119.2.3.69.203.513.501.3.9.7.2.1
    tcn15minSfpEntry OBJECT-TYPE
        SYNTAX      Tcn15minSfpEntry
        ACCESS      not-accessible
        STATUS      mandatory
        DESCRIPTION
            ""
        INDEX       { tcn15minSfpNEAddress, tcn15minSfpIfIndex }
        ::= { tcn15minSfpTable 1 }
    
    Tcn15minSfpEntry ::= SEQUENCE {
        tcn15minSfpIfIndex      InterfaceIndex,
        tcn15minSfpNEAddress    IpAddress,
        tcn15minSfpTxPower      SeverityValue,
        tcn15minSfpRxPower      SeverityValue
    }
    
    -- 1.3.6.1.4.1.119.2.3.69.203.513.501.3.9.7.2.1.1
    tcn15minSfpIfIndex OBJECT-TYPE
        SYNTAX      InterfaceIndex
        ACCESS      not-accessible
        STATUS      mandatory
        DESCRIPTION
            ""
        ::= { tcn15minSfpEntry 1 }
    
    -- 1.3.6.1.4.1.119.2.3.69.203.513.501.3.9.7.2.1.2
    tcn15minSfpNEAddress OBJECT-TYPE
        SYNTAX      IpAddress
        ACCESS      not-accessible
        STATUS      mandatory
        DESCRIPTION
            "reserved"
        ::= { tcn15minSfpEntry 2 }
    
    -- 1.3.6.1.4.1.119.2.3.69.203.513.501.3.9.7.2.1.3
    tcn15minSfpTxPower OBJECT-TYPE
        SYNTAX      SeverityValue
        ACCESS      read-only
        STATUS      mandatory
        DESCRIPTION
            "TCN 15 minutes ETH Port Sfp Tx Power(Min)."
        ::= { tcn15minSfpEntry 3 }
    
    -- 1.3.6.1.4.1.119.2.3.69.203.513.501.3.9.7.2.1.4
    tcn15minSfpRxPower OBJECT-TYPE
        SYNTAX      SeverityValue
        ACCESS      read-only
        STATUS      mandatory
        DESCRIPTION
            "TCN 15 minutes ETH Port Sfp Rx Power(Min)."
        ::= { tcn15minSfpEntry 4 }
    
    -- 1.3.6.1.4.1.119.2.3.69.203.513.501.3.9.7.3
    tcn15minStm1PortSfpTable OBJECT-TYPE
        SYNTAX      SEQUENCE OF Tcn15minStm1PortSfpEntry
        ACCESS      not-accessible
        STATUS      mandatory
        DESCRIPTION
            "Represents Threshold Crossing Alarm Status of 15 minutes STM1
             Port Sfp Tx/Rx Power."
        ::= { tcn15minDataSfpGroup 3 }
    
    -- 1.3.6.1.4.1.119.2.3.69.203.513.501.3.9.7.3.1
    tcn15minStm1PortSfpEntry OBJECT-TYPE
        SYNTAX      Tcn15minStm1PortSfpEntry
        ACCESS      not-accessible
        STATUS      mandatory
        DESCRIPTION
            ""
        INDEX       { tcn15minStm1PortSfpNEAddress, tcn15minStm1PortSfpIfIndex }
        ::= { tcn15minStm1PortSfpTable 1 }
    
    Tcn15minStm1PortSfpEntry ::= SEQUENCE {
        tcn15minStm1PortSfpIfIndex      InterfaceIndex,
        tcn15minStm1PortSfpNEAddress    IpAddress,
        tcn15minStm1PortSfpTxPower      SeverityValue,
        tcn15minStm1PortSfpRxPower      SeverityValue
    }
    
    -- 1.3.6.1.4.1.119.2.3.69.203.513.501.3.9.7.3.1.1
    tcn15minStm1PortSfpIfIndex OBJECT-TYPE
        SYNTAX      InterfaceIndex
        ACCESS      not-accessible
        STATUS      mandatory
        DESCRIPTION
            ""
        ::= { tcn15minStm1PortSfpEntry 1 }
    
    -- 1.3.6.1.4.1.119.2.3.69.203.513.501.3.9.7.3.1.2
    tcn15minStm1PortSfpNEAddress OBJECT-TYPE
        SYNTAX      IpAddress
        ACCESS      not-accessible
        STATUS      mandatory
        DESCRIPTION
            "reserved"
        ::= { tcn15minStm1PortSfpEntry 2 }
    
    -- 1.3.6.1.4.1.119.2.3.69.203.513.501.3.9.7.3.1.3
    tcn15minStm1PortSfpTxPower OBJECT-TYPE
        SYNTAX      SeverityValue
        ACCESS      read-only
        STATUS      mandatory
        DESCRIPTION
            "TCN 15 minutes STM1 Port Sfp Tx Power(Min)."
        ::= { tcn15minStm1PortSfpEntry 3 }
    
    -- 1.3.6.1.4.1.119.2.3.69.203.513.501.3.9.7.3.1.4
    tcn15minStm1PortSfpRxPower OBJECT-TYPE
        SYNTAX      SeverityValue
        ACCESS      read-only
        STATUS      mandatory
        DESCRIPTION
            "TCN 15 minutes STM1 Port Sfp Rx Power(Min)."
        ::= { tcn15minStm1PortSfpEntry 4 }
    
    -- 1.3.6.1.4.1.119.2.3.69.203.513.501.3.9.8
    tcn1dayDataSfpGroup OBJECT IDENTIFIER
        ::= { asTCNGroup 8 }
    
    -- 1.3.6.1.4.1.119.2.3.69.203.513.501.3.9.8.2
    tcn1daySfpTable OBJECT-TYPE
        SYNTAX      SEQUENCE OF Tcn1daySfpEntry
        ACCESS      not-accessible
        STATUS      mandatory
        DESCRIPTION
            "Represents Threshold Crossing Alarm Status of 1 day ETH Port Sfp
             Tx/Rx Power."
        ::= { tcn1dayDataSfpGroup 2 }
    
    -- 1.3.6.1.4.1.119.2.3.69.203.513.501.3.9.8.2.1
    tcn1daySfpEntry OBJECT-TYPE
        SYNTAX      Tcn1daySfpEntry
        ACCESS      not-accessible
        STATUS      mandatory
        DESCRIPTION
            ""
        INDEX       { tcn1daySfpNEAddress, tcn1daySfpIfIndex }
        ::= { tcn1daySfpTable 1 }
    
    Tcn1daySfpEntry ::= SEQUENCE {
        tcn1daySfpIfIndex       InterfaceIndex,
        tcn1daySfpNEAddress     IpAddress,
        tcn1daySfpTxPower       SeverityValue,
        tcn1daySfpRxPower       SeverityValue
    }
    
    -- 1.3.6.1.4.1.119.2.3.69.203.513.501.3.9.8.2.1.1
    tcn1daySfpIfIndex OBJECT-TYPE
        SYNTAX      InterfaceIndex
        ACCESS      not-accessible
        STATUS      mandatory
        DESCRIPTION
            ""
        ::= { tcn1daySfpEntry 1 }
    
    -- 1.3.6.1.4.1.119.2.3.69.203.513.501.3.9.8.2.1.2
    tcn1daySfpNEAddress OBJECT-TYPE
        SYNTAX      IpAddress
        ACCESS      not-accessible
        STATUS      mandatory
        DESCRIPTION
            "reserved"
        ::= { tcn1daySfpEntry 2 }
    
    -- 1.3.6.1.4.1.119.2.3.69.203.513.501.3.9.8.2.1.3
    tcn1daySfpTxPower OBJECT-TYPE
        SYNTAX      SeverityValue
        ACCESS      read-only
        STATUS      mandatory
        DESCRIPTION
            "TCN 1 day ETH Port Sfp Tx Power(Min)."
        ::= { tcn1daySfpEntry 3 }
    
    -- 1.3.6.1.4.1.119.2.3.69.203.513.501.3.9.8.2.1.4
    tcn1daySfpRxPower OBJECT-TYPE
        SYNTAX      SeverityValue
        ACCESS      read-only
        STATUS      mandatory
        DESCRIPTION
            "TCN 1 day ETH Port Sfp Rx Power(Min)."
        ::= { tcn1daySfpEntry 4 }
    
    -- 1.3.6.1.4.1.119.2.3.69.203.513.501.3.9.8.3
    tcn1dayStm1PortSfpTable OBJECT-TYPE
        SYNTAX      SEQUENCE OF Tcn1dayStm1PortSfpEntry
        ACCESS      not-accessible
        STATUS      mandatory
        DESCRIPTION
            "Represents Threshold Crossing Alarm Status of 1 day STM1 Port
             Sfp Tx/Rx Power."
        ::= { tcn1dayDataSfpGroup 3 }
    
    -- 1.3.6.1.4.1.119.2.3.69.203.513.501.3.9.8.3.1
    tcn1dayStm1PortSfpEntry OBJECT-TYPE
        SYNTAX      Tcn1dayStm1PortSfpEntry
        ACCESS      not-accessible
        STATUS      mandatory
        DESCRIPTION
            ""
        INDEX       { tcn1dayStm1PortSfpNEAddress, tcn1dayStm1PortSfpIfIndex }
        ::= { tcn1dayStm1PortSfpTable 1 }
    
    Tcn1dayStm1PortSfpEntry ::= SEQUENCE {
        tcn1dayStm1PortSfpIfIndex       InterfaceIndex,
        tcn1dayStm1PortSfpNEAddress     IpAddress,
        tcn1dayStm1PortSfpTxPower       SeverityValue,
        tcn1dayStm1PortSfpRxPower       SeverityValue
    }
    
    -- 1.3.6.1.4.1.119.2.3.69.203.513.501.3.9.8.3.1.1
    tcn1dayStm1PortSfpIfIndex OBJECT-TYPE
        SYNTAX      InterfaceIndex
        ACCESS      not-accessible
        STATUS      mandatory
        DESCRIPTION
            ""
        ::= { tcn1dayStm1PortSfpEntry 1 }
    
    -- 1.3.6.1.4.1.119.2.3.69.203.513.501.3.9.8.3.1.2
    tcn1dayStm1PortSfpNEAddress OBJECT-TYPE
        SYNTAX      IpAddress
        ACCESS      not-accessible
        STATUS      mandatory
        DESCRIPTION
            "reserved"
        ::= { tcn1dayStm1PortSfpEntry 2 }
    
    -- 1.3.6.1.4.1.119.2.3.69.203.513.501.3.9.8.3.1.3
    tcn1dayStm1PortSfpTxPower OBJECT-TYPE
        SYNTAX      SeverityValue
        ACCESS      read-only
        STATUS      mandatory
        DESCRIPTION
            "TCN 1 day STM1 Port Sfp Tx Power(Min)."
        ::= { tcn1dayStm1PortSfpEntry 3 }
    
    -- 1.3.6.1.4.1.119.2.3.69.203.513.501.3.9.8.3.1.4
    tcn1dayStm1PortSfpRxPower OBJECT-TYPE
        SYNTAX      SeverityValue
        ACCESS      read-only
        STATUS      mandatory
        DESCRIPTION
            "TCN 1 day STM1 Port Sfp Rx Power(Min)."
        ::= { tcn1dayStm1PortSfpEntry 4 }
    
    -- 1.3.6.1.4.1.119.2.3.69.203.513.501.3.10
    asHkGroup OBJECT IDENTIFIER
        ::= { alarmStatusGroup 10 }
    
    -- 1.3.6.1.4.1.119.2.3.69.203.513.501.3.10.1
    hkInputStatusTable OBJECT-TYPE
        SYNTAX      SEQUENCE OF HkInputStatusEntry
        ACCESS      not-accessible
        STATUS      mandatory
        DESCRIPTION
            "AUX HK Input Status"
        ::= { asHkGroup 1 }
    
    -- 1.3.6.1.4.1.119.2.3.69.203.513.501.3.10.1.1
    hkInputStatusEntry OBJECT-TYPE
        SYNTAX      HkInputStatusEntry
        ACCESS      not-accessible
        STATUS      mandatory
        DESCRIPTION
            ""
        INDEX       { hkInputStatusNEAddress, hkInputStatusIndex }
        ::= { hkInputStatusTable 1 }
    
    HkInputStatusEntry ::= SEQUENCE {
        hkInputStatusIndex      INTEGER,
        hkInputStatusNEAddress  IpAddress,
        hkInputAlarm            SeverityValue,
        hkInputStatus           INTEGER
    }
    
    -- 1.3.6.1.4.1.119.2.3.69.203.513.501.3.10.1.1.1
    hkInputStatusIndex OBJECT-TYPE
        SYNTAX      INTEGER { hkInput1(1), hkInput2(2), hkInput3(3),
                        hkInput4(4), hkInput5(5), hkInput6(6) }
        ACCESS      not-accessible
        STATUS      mandatory
        DESCRIPTION
            "Index of this table."
        ::= { hkInputStatusEntry 1 }
    
    -- 1.3.6.1.4.1.119.2.3.69.203.513.501.3.10.1.1.2
    hkInputStatusNEAddress OBJECT-TYPE
        SYNTAX      IpAddress
        ACCESS      not-accessible
        STATUS      mandatory
        DESCRIPTION
            "reserved"
        ::= { hkInputStatusEntry 2 }
    
    -- 1.3.6.1.4.1.119.2.3.69.203.513.501.3.10.1.1.3
    hkInputAlarm OBJECT-TYPE
        SYNTAX      SeverityValue
        ACCESS      read-only
        STATUS      mandatory
        DESCRIPTION
            "AUX HK IN Alarm."
        ::= { hkInputStatusEntry 3 }
    
    -- 1.3.6.1.4.1.119.2.3.69.203.513.501.3.10.1.1.4
    hkInputStatus OBJECT-TYPE
        SYNTAX      INTEGER { eventOff(1), eventOn(2) }
        ACCESS      read-only
        STATUS      mandatory
        DESCRIPTION
            "AUX HK IN Status."
        ::= { hkInputStatusEntry 4 }
    
    -- 1.3.6.1.4.1.119.2.3.69.203.513.501.3.10.2
    hkOutputStatusTable OBJECT-TYPE
        SYNTAX      SEQUENCE OF HkOutputStatusEntry
        ACCESS      not-accessible
        STATUS      mandatory
        DESCRIPTION
            "AUX HK Output Status"
        ::= { asHkGroup 2 }
    
    -- 1.3.6.1.4.1.119.2.3.69.203.513.501.3.10.2.1
    hkOutputStatusEntry OBJECT-TYPE
        SYNTAX      HkOutputStatusEntry
        ACCESS      not-accessible
        STATUS      mandatory
        DESCRIPTION
            ""
        INDEX       { hkOutputStatusNEAddress, hkOutputStatusIndex }
        ::= { hkOutputStatusTable 1 }
    
    HkOutputStatusEntry ::= SEQUENCE {
        hkOutputStatusIndex         INTEGER,
        hkOutputStatusNEAddress     IpAddress,
        hkOutputStatusValue         OffOnValue
    }
    
    -- 1.3.6.1.4.1.119.2.3.69.203.513.501.3.10.2.1.1
    hkOutputStatusIndex OBJECT-TYPE
        SYNTAX      INTEGER { hkOutput1(1), hkOutput2(2), hkOutput3(3),
                        hkOutput4(4) }
        ACCESS      not-accessible
        STATUS      mandatory
        DESCRIPTION
            "Index of this table."
        ::= { hkOutputStatusEntry 1 }
    
    -- 1.3.6.1.4.1.119.2.3.69.203.513.501.3.10.2.1.2
    hkOutputStatusNEAddress OBJECT-TYPE
        SYNTAX      IpAddress
        ACCESS      not-accessible
        STATUS      mandatory
        DESCRIPTION
            "reserved."
        ::= { hkOutputStatusEntry 2 }
    
    -- 1.3.6.1.4.1.119.2.3.69.203.513.501.3.10.2.1.3
    hkOutputStatusValue OBJECT-TYPE
        SYNTAX      OffOnValue
        ACCESS      read-only
        STATUS      mandatory
        DESCRIPTION
            "AUX HK OUT Status"
        ::= { hkOutputStatusEntry 3 }
    
    -- 1.3.6.1.4.1.119.2.3.69.203.513.501.3.10.3
    clusterAlarmGroup OBJECT IDENTIFIER
        ::= { asHkGroup 3 }
    
    -- 1.3.6.1.4.1.119.2.3.69.203.513.501.3.10.3.1
    clusterAlarmInTable OBJECT-TYPE
        SYNTAX      SEQUENCE OF ClusterAlarmInEntry
        ACCESS      not-accessible
        STATUS      mandatory
        DESCRIPTION
            "Represents Cluster Alarm Input (Cluster Alarm to Peer Equipment)
             Status"
        ::= { clusterAlarmGroup 1 }
    
    -- 1.3.6.1.4.1.119.2.3.69.203.513.501.3.10.3.1.1
    clusterAlarmInEntry OBJECT-TYPE
        SYNTAX      ClusterAlarmInEntry
        ACCESS      not-accessible
        STATUS      mandatory
        DESCRIPTION
            ""
        INDEX       { clusterAlarmInNEAddress, clusterAlarmInIfIndex }
        ::= { clusterAlarmInTable 1 }
    
    ClusterAlarmInEntry ::= SEQUENCE {
        clusterAlarmInIfIndex       InterfaceIndex,
        clusterAlarmInNEAddress     IpAddress,
        clusterAlarmInStatus        INTEGER
    }
    
    -- 1.3.6.1.4.1.119.2.3.69.203.513.501.3.10.3.1.1.1
    clusterAlarmInIfIndex OBJECT-TYPE
        SYNTAX      InterfaceIndex
        ACCESS      not-accessible
        STATUS      mandatory
        DESCRIPTION
            "Index of this table."
        ::= { clusterAlarmInEntry 1 }
    
    -- 1.3.6.1.4.1.119.2.3.69.203.513.501.3.10.3.1.1.2
    clusterAlarmInNEAddress OBJECT-TYPE
        SYNTAX      IpAddress
        ACCESS      not-accessible
        STATUS      mandatory
        DESCRIPTION
            "reserved"
        ::= { clusterAlarmInEntry 2 }
    
    -- 1.3.6.1.4.1.119.2.3.69.203.513.501.3.10.3.1.1.3
    clusterAlarmInStatus OBJECT-TYPE
        SYNTAX      INTEGER { alarm(1), normal(2) }
        ACCESS      read-only
        STATUS      mandatory
        DESCRIPTION
            "Cluster Alarm Input Status."
        ::= { clusterAlarmInEntry 3 }
    
    -- 1.3.6.1.4.1.119.2.3.69.203.513.501.3.10.3.2
    clusterAlarmOutTable OBJECT-TYPE
        SYNTAX      SEQUENCE OF ClusterAlarmOutEntry
        ACCESS      not-accessible
        STATUS      mandatory
        DESCRIPTION
            "Represents Cluster Alarm Output (Cluster Alarm from Peer
             Equipment) Status"
        ::= { clusterAlarmGroup 2 }
    
    -- 1.3.6.1.4.1.119.2.3.69.203.513.501.3.10.3.2.1
    clusterAlarmOutEntry OBJECT-TYPE
        SYNTAX      ClusterAlarmOutEntry
        ACCESS      not-accessible
        STATUS      mandatory
        DESCRIPTION
            ""
        INDEX       { clusterAlarmOutNEAddress, clusterAlarmOutIndex }
        ::= { clusterAlarmOutTable 1 }
    
    ClusterAlarmOutEntry ::= SEQUENCE {
        clusterAlarmOutIndex        INTEGER,
        clusterAlarmOutNEAddress    IpAddress,
        clusterAlarmOutStatus       INTEGER
    }
    
    -- 1.3.6.1.4.1.119.2.3.69.203.513.501.3.10.3.2.1.1
    clusterAlarmOutIndex OBJECT-TYPE
        SYNTAX      INTEGER
        ACCESS      not-accessible
        STATUS      mandatory
        DESCRIPTION
            "Index of this table."
        ::= { clusterAlarmOutEntry 1 }
    
    -- 1.3.6.1.4.1.119.2.3.69.203.513.501.3.10.3.2.1.2
    clusterAlarmOutNEAddress OBJECT-TYPE
        SYNTAX      IpAddress
        ACCESS      not-accessible
        STATUS      mandatory
        DESCRIPTION
            "reserved."
        ::= { clusterAlarmOutEntry 2 }
    
    -- 1.3.6.1.4.1.119.2.3.69.203.513.501.3.10.3.2.1.3
    clusterAlarmOutStatus OBJECT-TYPE
        SYNTAX      INTEGER { alarm(1), normal(2) }
        ACCESS      read-only
        STATUS      mandatory
        DESCRIPTION
            "MODEM Cluster Alarm Out."
        ::= { clusterAlarmOutEntry 3 }
    
    -- 1.3.6.1.4.1.119.2.3.69.203.513.501.3.11
    asStm1Group OBJECT IDENTIFIER
        ::= { alarmStatusGroup 11 }
    
    -- 1.3.6.1.4.1.119.2.3.69.203.513.501.3.11.1
    asStm1ChPortTable OBJECT-TYPE
        SYNTAX      SEQUENCE OF AsStm1ChPortEntry
        ACCESS      not-accessible
        STATUS      mandatory
        DESCRIPTION
            "Alarm / Status Information of STM-1 Channelized Mode. This table
             is not used when the STM-1 Port is running on Through Mode."
        ::= { asStm1Group 1 }
    
    -- 1.3.6.1.4.1.119.2.3.69.203.513.501.3.11.1.1
    asStm1ChPortEntry OBJECT-TYPE
        SYNTAX      AsStm1ChPortEntry
        ACCESS      not-accessible
        STATUS      mandatory
        DESCRIPTION
            ""
        INDEX       { asStm1ChPortNEAddress, asStm1ChPortIfIndex }
        ::= { asStm1ChPortTable 1 }
    
    AsStm1ChPortEntry ::= SEQUENCE {
        asStm1ChPortIfIndex                 InterfaceIndex,
        asStm1ChPortNEAddress               IpAddress,
        msAisAlarm                          SeverityValue,
        msRdiAlarm                          SeverityValue,
        pjeStatus                           INTEGER,
        auAisAlarm                          SeverityValue,
        auLopAlarm                          SeverityValue,
        hpUnequipedAlarm                    SeverityValue,
        hpTimAlarm                          SeverityValue,
        hpPlmAlarm                          SeverityValue,
        hpRdiAlarm                          SeverityValue,
        lomAlarm                            SeverityValue,
        higherOrderPathTraceReceivedValue   DisplayString,
        lowerOrderPathTraceReceivedValue    DisplayString
    }
    
    -- 1.3.6.1.4.1.119.2.3.69.203.513.501.3.11.1.1.1
    asStm1ChPortIfIndex OBJECT-TYPE
        SYNTAX      InterfaceIndex
        ACCESS      not-accessible
        STATUS      mandatory
        DESCRIPTION
            "Index of this table."
        ::= { asStm1ChPortEntry 1 }
    
    -- 1.3.6.1.4.1.119.2.3.69.203.513.501.3.11.1.1.2
    asStm1ChPortNEAddress OBJECT-TYPE
        SYNTAX      IpAddress
        ACCESS      not-accessible
        STATUS      mandatory
        DESCRIPTION
            "reserved."
        ::= { asStm1ChPortEntry 2 }
    
    -- 1.3.6.1.4.1.119.2.3.69.203.513.501.3.11.1.1.3
    msAisAlarm OBJECT-TYPE
        SYNTAX      SeverityValue
        ACCESS      read-only
        STATUS      mandatory
        DESCRIPTION
            "STM-1 MS AIS Alarm."
        ::= { asStm1ChPortEntry 3 }
    
    -- 1.3.6.1.4.1.119.2.3.69.203.513.501.3.11.1.1.4
    msRdiAlarm OBJECT-TYPE
        SYNTAX      SeverityValue
        ACCESS      read-only
        STATUS      mandatory
        DESCRIPTION
            "STM-1 MS RDI Alarm."
        ::= { asStm1ChPortEntry 4 }
    
    -- 1.3.6.1.4.1.119.2.3.69.203.513.501.3.11.1.1.5
    pjeStatus OBJECT-TYPE
        SYNTAX      INTEGER { noDetected(1), detected(2) }
        ACCESS      read-only
        STATUS      mandatory
        DESCRIPTION
            "STM-1 PJE Status."
        ::= { asStm1ChPortEntry 5 }
    
    -- 1.3.6.1.4.1.119.2.3.69.203.513.501.3.11.1.1.6
    auAisAlarm OBJECT-TYPE
        SYNTAX      SeverityValue
        ACCESS      read-only
        STATUS      mandatory
        DESCRIPTION
            "STM-1 AU AIS Alarm."
        ::= { asStm1ChPortEntry 6 }
    
    -- 1.3.6.1.4.1.119.2.3.69.203.513.501.3.11.1.1.7
    auLopAlarm OBJECT-TYPE
        SYNTAX      SeverityValue
        ACCESS      read-only
        STATUS      mandatory
        DESCRIPTION
            "STM-1 AU LOP Alarm."
        ::= { asStm1ChPortEntry 7 }
    
    -- 1.3.6.1.4.1.119.2.3.69.203.513.501.3.11.1.1.8
    hpUnequipedAlarm OBJECT-TYPE
        SYNTAX      SeverityValue
        ACCESS      read-only
        STATUS      mandatory
        DESCRIPTION
            "STM-1 HP UNEQ Alarm."
        ::= { asStm1ChPortEntry 8 }
    
    -- 1.3.6.1.4.1.119.2.3.69.203.513.501.3.11.1.1.9
    hpTimAlarm OBJECT-TYPE
        SYNTAX      SeverityValue
        ACCESS      read-only
        STATUS      mandatory
        DESCRIPTION
            "STM-1 HP TIM Alarm"
        ::= { asStm1ChPortEntry 9 }
    
    -- 1.3.6.1.4.1.119.2.3.69.203.513.501.3.11.1.1.10
    hpPlmAlarm OBJECT-TYPE
        SYNTAX      SeverityValue
        ACCESS      read-only
        STATUS      mandatory
        DESCRIPTION
            "STM-1 HP PLM Alarm"
        ::= { asStm1ChPortEntry 10 }
    
    -- 1.3.6.1.4.1.119.2.3.69.203.513.501.3.11.1.1.11
    hpRdiAlarm OBJECT-TYPE
        SYNTAX      SeverityValue
        ACCESS      read-only
        STATUS      mandatory
        DESCRIPTION
            "STM-1 HP RDI Alarm"
        ::= { asStm1ChPortEntry 11 }
    
    -- 1.3.6.1.4.1.119.2.3.69.203.513.501.3.11.1.1.12
    lomAlarm OBJECT-TYPE
        SYNTAX      SeverityValue
        ACCESS      read-only
        STATUS      mandatory
        DESCRIPTION
            "STM-1 LOM Alarm."
        ::= { asStm1ChPortEntry 12 }
    
    -- 1.3.6.1.4.1.119.2.3.69.203.513.501.3.11.1.1.13
    higherOrderPathTraceReceivedValue OBJECT-TYPE
        SYNTAX      DisplayString
        ACCESS      read-only
        STATUS      mandatory
        DESCRIPTION
            "STM-1 HP Trace Received Value."
        ::= { asStm1ChPortEntry 13 }
    
    -- 1.3.6.1.4.1.119.2.3.69.203.513.501.3.11.1.1.14
    lowerOrderPathTraceReceivedValue OBJECT-TYPE
        SYNTAX      DisplayString
        ACCESS      read-only
        STATUS      mandatory
        DESCRIPTION
            "STM-1 LP Trace Received Value."
        ::= { asStm1ChPortEntry 14 }
    
    -- 1.3.6.1.4.1.119.2.3.69.203.513.501.3.11.2
    asStm1PortTable OBJECT-TYPE
        SYNTAX      SEQUENCE OF AsStm1PortEntry
        ACCESS      not-accessible
        STATUS      mandatory
        DESCRIPTION
            "Alarm / Status Information of STM-1 Interface."
        ::= { asStm1Group 2 }
    
    -- 1.3.6.1.4.1.119.2.3.69.203.513.501.3.11.2.1
    asStm1PortEntry OBJECT-TYPE
        SYNTAX      AsStm1PortEntry
        ACCESS      not-accessible
        STATUS      mandatory
        DESCRIPTION
            ""
        INDEX       { asStm1PortNEAddress, asStm1PortIfIndex }
        ::= { asStm1PortTable 1 }
    
    AsStm1PortEntry ::= SEQUENCE {
        asStm1PortIfIndex           InterfaceIndex,
        asStm1PortNEAddress         IpAddress,
        portTypeMismatchAlarm       SeverityValue,
        portRemovedAlarm            SeverityValue,
        stm1LosAlarm                SeverityValue,
        tfAlarm                     SeverityValue,
        rsLofAlarm                  SeverityValue,
        rsTimAlarm                  SeverityValue,
        rsExcAlarm                  SeverityValue,
        rsDegAlarm                  SeverityValue,
        rsUasStatus                 INTEGER,
        sectionTraceReceivedValue   DisplayString,
        alsStatus                   OffOnValue,
        sdhAisGenStatus             INTEGER,
        stm1LoopbackStatus          INTEGER,
        stm1LaserShutdownStatus     OffOnValue,
        stm1LoopbackChannel         INTEGER
    }
    
    -- 1.3.6.1.4.1.119.2.3.69.203.513.501.3.11.2.1.1
    asStm1PortIfIndex OBJECT-TYPE
        SYNTAX      InterfaceIndex
        ACCESS      not-accessible
        STATUS      mandatory
        DESCRIPTION
            "Index of this table."
        ::= { asStm1PortEntry 1 }
    
    -- 1.3.6.1.4.1.119.2.3.69.203.513.501.3.11.2.1.2
    asStm1PortNEAddress OBJECT-TYPE
        SYNTAX      IpAddress
        ACCESS      not-accessible
        STATUS      mandatory
        DESCRIPTION
            "reserved."
        ::= { asStm1PortEntry 2 }
    
    -- 1.3.6.1.4.1.119.2.3.69.203.513.501.3.11.2.1.3
    portTypeMismatchAlarm OBJECT-TYPE
        SYNTAX      SeverityValue
        ACCESS      read-only
        STATUS      mandatory
        DESCRIPTION
            "STM-1 SFP Type Mismatch Alarm."
        ::= { asStm1PortEntry 3 }
    
    -- 1.3.6.1.4.1.119.2.3.69.203.513.501.3.11.2.1.4
    portRemovedAlarm OBJECT-TYPE
        SYNTAX      SeverityValue
        ACCESS      read-only
        STATUS      mandatory
        DESCRIPTION
            "STM-1 SFP Removed Alarm."
        ::= { asStm1PortEntry 4 }
    
    -- 1.3.6.1.4.1.119.2.3.69.203.513.501.3.11.2.1.5
    stm1LosAlarm OBJECT-TYPE
        SYNTAX      SeverityValue
        ACCESS      read-only
        STATUS      mandatory
        DESCRIPTION
            "STM-1 LOS Alarm."
        ::= { asStm1PortEntry 5 }
    
    -- 1.3.6.1.4.1.119.2.3.69.203.513.501.3.11.2.1.6
    tfAlarm OBJECT-TYPE
        SYNTAX      SeverityValue
        ACCESS      read-only
        STATUS      mandatory
        DESCRIPTION
            "STM-1 Transmit FAIL Alarm."
        ::= { asStm1PortEntry 6 }
    
    -- 1.3.6.1.4.1.119.2.3.69.203.513.501.3.11.2.1.7
    rsLofAlarm OBJECT-TYPE
        SYNTAX      SeverityValue
        ACCESS      read-only
        STATUS      mandatory
        DESCRIPTION
            "STM-1 RS LOF Alarm."
        ::= { asStm1PortEntry 7 }
    
    -- 1.3.6.1.4.1.119.2.3.69.203.513.501.3.11.2.1.8
    rsTimAlarm OBJECT-TYPE
        SYNTAX      SeverityValue
        ACCESS      read-only
        STATUS      mandatory
        DESCRIPTION
            "STM-1 RS TIM Alarm."
        ::= { asStm1PortEntry 8 }
    
    -- 1.3.6.1.4.1.119.2.3.69.203.513.501.3.11.2.1.9
    rsExcAlarm OBJECT-TYPE
        SYNTAX      SeverityValue
        ACCESS      read-only
        STATUS      mandatory
        DESCRIPTION
            "STM-1 RS EXC Alarm."
        ::= { asStm1PortEntry 9 }
    
    -- 1.3.6.1.4.1.119.2.3.69.203.513.501.3.11.2.1.10
    rsDegAlarm OBJECT-TYPE
        SYNTAX      SeverityValue
        ACCESS      read-only
        STATUS      mandatory
        DESCRIPTION
            "STM-1 RS DEG Alarm."
        ::= { asStm1PortEntry 10 }
    
    -- 1.3.6.1.4.1.119.2.3.69.203.513.501.3.11.2.1.11
    rsUasStatus OBJECT-TYPE
        SYNTAX      INTEGER { normal(1), uas(2) }
        ACCESS      read-only
        STATUS      mandatory
        DESCRIPTION
            "STM-1 RS UAS Status"
        ::= { asStm1PortEntry 11 }
    
    -- 1.3.6.1.4.1.119.2.3.69.203.513.501.3.11.2.1.12
    sectionTraceReceivedValue OBJECT-TYPE
        SYNTAX      DisplayString
        ACCESS      read-only
        STATUS      mandatory
        DESCRIPTION
            "STM-1 Section Trace Received Value."
        ::= { asStm1PortEntry 12 }
    
    -- 1.3.6.1.4.1.119.2.3.69.203.513.501.3.11.2.1.13
    alsStatus OBJECT-TYPE
        SYNTAX      OffOnValue
        ACCESS      read-only
        STATUS      mandatory
        DESCRIPTION
            "STM-1 ALS Status"
        ::= { asStm1PortEntry 13 }
    
    -- 1.3.6.1.4.1.119.2.3.69.203.513.501.3.11.2.1.14
    sdhAisGenStatus OBJECT-TYPE
        SYNTAX      INTEGER { invalid(0), normal(1), generated(2),
                        shutdown(3) }
        ACCESS      read-only
        STATUS      mandatory
        DESCRIPTION
            "STM-1 AIS Generated Status."
        ::= { asStm1PortEntry 14 }
    
    -- 1.3.6.1.4.1.119.2.3.69.203.513.501.3.11.2.1.15
    stm1LoopbackStatus OBJECT-TYPE
        SYNTAX      INTEGER { ne(1), fe(2), normal(3), channelizedFe(5) }
        ACCESS      read-only
        STATUS      mandatory
        DESCRIPTION
            "STM-1 Loopback Status."
        ::= { asStm1PortEntry 15 }
    
    -- 1.3.6.1.4.1.119.2.3.69.203.513.501.3.11.2.1.16
    stm1LaserShutdownStatus OBJECT-TYPE
        SYNTAX      OffOnValue
        ACCESS      read-only
        STATUS      mandatory
        DESCRIPTION
            "STM-1 Laser Shutdown status."
        ::= { asStm1PortEntry 16 }
    
    -- 1.3.6.1.4.1.119.2.3.69.203.513.501.3.11.2.1.17
    stm1LoopbackChannel OBJECT-TYPE
        SYNTAX      INTEGER (0..63)
        ACCESS      read-only
        STATUS      mandatory
        DESCRIPTION
            "Indicate the loopback channel. The valid ranges are as follows.
    
             stm1LoopbackStatus  stm1LoopbackChannel
             --------------------------------------
             ne                          0
             fe                          0
             channelizedFe              1-63"
        ::= { asStm1PortEntry 17 }
    
    -- 1.3.6.1.4.1.119.2.3.69.203.513.501.3.11.3
    asStm1ChTable OBJECT-TYPE
        SYNTAX      SEQUENCE OF AsStm1ChEntry
        ACCESS      not-accessible
        STATUS      mandatory
        DESCRIPTION
            "Alarm / Status Information of STM-1 Channelized. This table is
             created per E1 channel allocated to the STM-1 interface."
        ::= { asStm1Group 3 }
    
    -- 1.3.6.1.4.1.119.2.3.69.203.513.501.3.11.3.1
    asStm1ChEntry OBJECT-TYPE
        SYNTAX      AsStm1ChEntry
        ACCESS      not-accessible
        STATUS      mandatory
        DESCRIPTION
            ""
        INDEX       { asStm1ChNEAddress, asStm1ChIfIndex }
        ::= { asStm1ChTable 1 }
    
    AsStm1ChEntry ::= SEQUENCE {
        asStm1ChIfIndex     InterfaceIndex,
        asStm1ChNEAddress   IpAddress,
        tuAisAlarm          SeverityValue,
        tuLopAlarm          SeverityValue,
        lpUnequipedAlarm    SeverityValue,
        lpRdiAlarm          SeverityValue,
        lpPlmAlarm          SeverityValue,
        slpAisGenStatus     INTEGER
    }
    
    -- 1.3.6.1.4.1.119.2.3.69.203.513.501.3.11.3.1.1
    asStm1ChIfIndex OBJECT-TYPE
        SYNTAX      InterfaceIndex
        ACCESS      not-accessible
        STATUS      mandatory
        DESCRIPTION
            "Index of this table"
        ::= { asStm1ChEntry 1 }
    
    -- 1.3.6.1.4.1.119.2.3.69.203.513.501.3.11.3.1.2
    asStm1ChNEAddress OBJECT-TYPE
        SYNTAX      IpAddress
        ACCESS      not-accessible
        STATUS      mandatory
        DESCRIPTION
            "reserved."
        ::= { asStm1ChEntry 2 }
    
    -- 1.3.6.1.4.1.119.2.3.69.203.513.501.3.11.3.1.3
    tuAisAlarm OBJECT-TYPE
        SYNTAX      SeverityValue
        ACCESS      read-only
        STATUS      mandatory
        DESCRIPTION
            "STM-1 TU AIS Alarm."
        ::= { asStm1ChEntry 3 }
    
    -- 1.3.6.1.4.1.119.2.3.69.203.513.501.3.11.3.1.4
    tuLopAlarm OBJECT-TYPE
        SYNTAX      SeverityValue
        ACCESS      read-only
        STATUS      mandatory
        DESCRIPTION
            "STM-1 TU LOP Alarm."
        ::= { asStm1ChEntry 4 }
    
    -- 1.3.6.1.4.1.119.2.3.69.203.513.501.3.11.3.1.5
    lpUnequipedAlarm OBJECT-TYPE
        SYNTAX      SeverityValue
        ACCESS      read-only
        STATUS      mandatory
        DESCRIPTION
            "STM-1 LP UNEQ Alarm."
        ::= { asStm1ChEntry 5 }
    
    -- 1.3.6.1.4.1.119.2.3.69.203.513.501.3.11.3.1.6
    lpRdiAlarm OBJECT-TYPE
        SYNTAX      SeverityValue
        ACCESS      read-only
        STATUS      mandatory
        DESCRIPTION
            "STM-1 LP RDI Alarm."
        ::= { asStm1ChEntry 6 }
    
    -- 1.3.6.1.4.1.119.2.3.69.203.513.501.3.11.3.1.7
    lpPlmAlarm OBJECT-TYPE
        SYNTAX      SeverityValue
        ACCESS      read-only
        STATUS      mandatory
        DESCRIPTION
            "STM-1 LP PLM Alarm."
        ::= { asStm1ChEntry 7 }
    
    -- 1.3.6.1.4.1.119.2.3.69.203.513.501.3.11.3.1.8
    slpAisGenStatus OBJECT-TYPE
        SYNTAX      INTEGER { normal(1), generated(2) }
        ACCESS      read-only
        STATUS      mandatory
        DESCRIPTION
            "STM-1 E1 AIS Generated Status."
        ::= { asStm1ChEntry 8 }
    
    -- 1.3.6.1.4.1.119.2.3.69.203.513.501.3.11.4
    asStm1CardTable OBJECT-TYPE
        SYNTAX      SEQUENCE OF AsStm1CardEntry
        ACCESS      not-accessible
        STATUS      mandatory
        DESCRIPTION
            "Alarm / Status information of STM-1 Card."
        ::= { asStm1Group 4 }
    
    -- 1.3.6.1.4.1.119.2.3.69.203.513.501.3.11.4.1
    asStm1CardEntry OBJECT-TYPE
        SYNTAX      AsStm1CardEntry
        ACCESS      not-accessible
        STATUS      mandatory
        DESCRIPTION
            ""
        INDEX       { asStm1CardNEAddress, asStm1CardIndex }
        ::= { asStm1CardTable 1 }
    
    AsStm1CardEntry ::= SEQUENCE {
        asStm1CardIndex         INTEGER,
        asStm1CardNEAddress     IpAddress,
        stm1Alarm               SeverityValue,
        stm1ComFailAlarm        SeverityValue,
        stm1Unequipped          SeverityValue,
        stm1TypeMismatch        SeverityValue,
        stm1BusErrorTx          SeverityValue,
        stm1BusErrorRx          SeverityValue
    }
    
    -- 1.3.6.1.4.1.119.2.3.69.203.513.501.3.11.4.1.1
    asStm1CardIndex OBJECT-TYPE
        SYNTAX      INTEGER
        ACCESS      not-accessible
        STATUS      mandatory
        DESCRIPTION
            "Index of this table."
        ::= { asStm1CardEntry 1 }
    
    -- 1.3.6.1.4.1.119.2.3.69.203.513.501.3.11.4.1.2
    asStm1CardNEAddress OBJECT-TYPE
        SYNTAX      IpAddress
        ACCESS      not-accessible
        STATUS      mandatory
        DESCRIPTION
            "reserved."
        ::= { asStm1CardEntry 2 }
    
    -- 1.3.6.1.4.1.119.2.3.69.203.513.501.3.11.4.1.3
    stm1Alarm OBJECT-TYPE
        SYNTAX      SeverityValue
        ACCESS      read-only
        STATUS      mandatory
        DESCRIPTION
            "STM-1 Module Alarm."
        ::= { asStm1CardEntry 3 }
    
    -- 1.3.6.1.4.1.119.2.3.69.203.513.501.3.11.4.1.4
    stm1ComFailAlarm OBJECT-TYPE
        SYNTAX      SeverityValue
        ACCESS      read-only
        STATUS      mandatory
        DESCRIPTION
            "STM-1 Communication FAIL Alarm."
        ::= { asStm1CardEntry 4 }
    
    -- 1.3.6.1.4.1.119.2.3.69.203.513.501.3.11.4.1.5
    stm1Unequipped OBJECT-TYPE
        SYNTAX      SeverityValue
        ACCESS      read-only
        STATUS      mandatory
        DESCRIPTION
            "STM-1 Unequipped Alarm."
        ::= { asStm1CardEntry 5 }
    
    -- 1.3.6.1.4.1.119.2.3.69.203.513.501.3.11.4.1.6
    stm1TypeMismatch OBJECT-TYPE
        SYNTAX      SeverityValue
        ACCESS      read-only
        STATUS      mandatory
        DESCRIPTION
            "STM-1 Type Mismatch Alarm."
        ::= { asStm1CardEntry 6 }
    
    -- 1.3.6.1.4.1.119.2.3.69.203.513.501.3.11.4.1.7
    stm1BusErrorTx OBJECT-TYPE
        SYNTAX      SeverityValue
        ACCESS      read-only
        STATUS      mandatory
        DESCRIPTION
            "STM-1 TX Bus Error Alarm."
        ::= { asStm1CardEntry 7 }
    
    -- 1.3.6.1.4.1.119.2.3.69.203.513.501.3.11.4.1.8
    stm1BusErrorRx OBJECT-TYPE
        SYNTAX      SeverityValue
        ACCESS      read-only
        STATUS      mandatory
        DESCRIPTION
            "STM-1 RX Bus Error Alarm."
        ::= { asStm1CardEntry 8 }
    
    -- 1.3.6.1.4.1.119.2.3.69.203.513.501.3.12
    asE1Group OBJECT IDENTIFIER
        ::= { alarmStatusGroup 12 }
    
    -- 1.3.6.1.4.1.119.2.3.69.203.513.501.3.12.1
    asE1CardTable OBJECT-TYPE
        SYNTAX      SEQUENCE OF AsE1CardEntry
        ACCESS      not-accessible
        STATUS      mandatory
        DESCRIPTION
            "Alarm / Status information of 16E1 Card."
        ::= { asE1Group 1 }
    
    -- 1.3.6.1.4.1.119.2.3.69.203.513.501.3.12.1.1
    asE1CardEntry OBJECT-TYPE
        SYNTAX      AsE1CardEntry
        ACCESS      not-accessible
        STATUS      mandatory
        DESCRIPTION
            ""
        INDEX       { asE1CardNEAddress, asE1CardIndex }
        ::= { asE1CardTable 1 }
    
    AsE1CardEntry ::= SEQUENCE {
        asE1CardIndex       INTEGER,
        asE1CardNEAddress   IpAddress,
        e1Alarm             SeverityValue,
        e1ComFailAlarm      SeverityValue,
        e1Unequipped        SeverityValue,
        e1TypeMismatch      SeverityValue,
        e1BusErrorTx        SeverityValue,
        e1BusErrorRx        SeverityValue
    }
    
    -- 1.3.6.1.4.1.119.2.3.69.203.513.501.3.12.1.1.1
    asE1CardIndex OBJECT-TYPE
        SYNTAX      INTEGER
        ACCESS      not-accessible
        STATUS      mandatory
        DESCRIPTION
            "Index of this table."
        ::= { asE1CardEntry 1 }
    
    -- 1.3.6.1.4.1.119.2.3.69.203.513.501.3.12.1.1.2
    asE1CardNEAddress OBJECT-TYPE
        SYNTAX      IpAddress
        ACCESS      not-accessible
        STATUS      mandatory
        DESCRIPTION
            "reserved."
        ::= { asE1CardEntry 2 }
    
    -- 1.3.6.1.4.1.119.2.3.69.203.513.501.3.12.1.1.3
    e1Alarm OBJECT-TYPE
        SYNTAX      SeverityValue
        ACCESS      read-only
        STATUS      mandatory
        DESCRIPTION
            "16E1 Module Alarm."
        ::= { asE1CardEntry 3 }
    
    -- 1.3.6.1.4.1.119.2.3.69.203.513.501.3.12.1.1.4
    e1ComFailAlarm OBJECT-TYPE
        SYNTAX      SeverityValue
        ACCESS      read-only
        STATUS      mandatory
        DESCRIPTION
            "16E1 Communication FAIL Alarm."
        ::= { asE1CardEntry 4 }
    
    -- 1.3.6.1.4.1.119.2.3.69.203.513.501.3.12.1.1.5
    e1Unequipped OBJECT-TYPE
        SYNTAX      SeverityValue
        ACCESS      read-only
        STATUS      mandatory
        DESCRIPTION
            "16E1 Unequipped Alarm."
        ::= { asE1CardEntry 5 }
    
    -- 1.3.6.1.4.1.119.2.3.69.203.513.501.3.12.1.1.6
    e1TypeMismatch OBJECT-TYPE
        SYNTAX      SeverityValue
        ACCESS      read-only
        STATUS      mandatory
        DESCRIPTION
            "16E1 Type Mismatch Alarm."
        ::= { asE1CardEntry 6 }
    
    -- 1.3.6.1.4.1.119.2.3.69.203.513.501.3.12.1.1.7
    e1BusErrorTx OBJECT-TYPE
        SYNTAX      SeverityValue
        ACCESS      read-only
        STATUS      mandatory
        DESCRIPTION
            "16E1 TX Bus Error Alarm."
        ::= { asE1CardEntry 7 }
    
    -- 1.3.6.1.4.1.119.2.3.69.203.513.501.3.12.1.1.8
    e1BusErrorRx OBJECT-TYPE
        SYNTAX      SeverityValue
        ACCESS      read-only
        STATUS      mandatory
        DESCRIPTION
            "16E1 RX Bus Error Alarm."
        ::= { asE1CardEntry 8 }
    
    -- 1.3.6.1.4.1.119.2.3.69.203.513.501.3.12.2
    asE1ChTable OBJECT-TYPE
        SYNTAX      SEQUENCE OF AsE1ChEntry
        ACCESS      not-accessible
        STATUS      mandatory
        DESCRIPTION
            "Alarm / Status information of E1 Channel."
        ::= { asE1Group 2 }
    
    -- 1.3.6.1.4.1.119.2.3.69.203.513.501.3.12.2.1
    asE1ChEntry OBJECT-TYPE
        SYNTAX      AsE1ChEntry
        ACCESS      not-accessible
        STATUS      mandatory
        DESCRIPTION
            ""
        INDEX       { asE1ChNEAddress, asE1ChIfIndex }
        ::= { asE1ChTable 1 }
    
    AsE1ChEntry ::= SEQUENCE {
        asE1ChIfIndex       InterfaceIndex,
        asE1ChNEAddress     IpAddress,
        chUsageAlarm        SeverityValue,
        e1LosAlarm          SeverityValue,
        ppiAisAlarm         SeverityValue,
        e1AisGenStatus      INTEGER,
        e1LoopbackStatus    INTEGER,
        ppiAisStatus        INTEGER
    }
    
    -- 1.3.6.1.4.1.119.2.3.69.203.513.501.3.12.2.1.1
    asE1ChIfIndex OBJECT-TYPE
        SYNTAX      InterfaceIndex
        ACCESS      not-accessible
        STATUS      mandatory
        DESCRIPTION
            "Index of this table. Unique number of E1 channel."
        ::= { asE1ChEntry 1 }
    
    -- 1.3.6.1.4.1.119.2.3.69.203.513.501.3.12.2.1.2
    asE1ChNEAddress OBJECT-TYPE
        SYNTAX      IpAddress
        ACCESS      not-accessible
        STATUS      mandatory
        DESCRIPTION
            "reserved"
        ::= { asE1ChEntry 2 }
    
    -- 1.3.6.1.4.1.119.2.3.69.203.513.501.3.12.2.1.3
    chUsageAlarm OBJECT-TYPE
        SYNTAX      SeverityValue
        ACCESS      read-only
        STATUS      mandatory
        DESCRIPTION
            "E1 Channel Usage Error Alarm."
        ::= { asE1ChEntry 3 }
    
    -- 1.3.6.1.4.1.119.2.3.69.203.513.501.3.12.2.1.4
    e1LosAlarm OBJECT-TYPE
        SYNTAX      SeverityValue
        ACCESS      read-only
        STATUS      mandatory
        DESCRIPTION
            "E1 Channel LOS Alarm."
        ::= { asE1ChEntry 4 }
    
    -- 1.3.6.1.4.1.119.2.3.69.203.513.501.3.12.2.1.5
    ppiAisAlarm OBJECT-TYPE
        SYNTAX      SeverityValue
        ACCESS      read-only
        STATUS      mandatory
        DESCRIPTION
            "E1 Channel AIS Alarm."
        ::= { asE1ChEntry 5 }
    
    -- 1.3.6.1.4.1.119.2.3.69.203.513.501.3.12.2.1.6
    e1AisGenStatus OBJECT-TYPE
        SYNTAX      INTEGER { normal(1), generated(2) }
        ACCESS      read-only
        STATUS      mandatory
        DESCRIPTION
            "E1 Channel AIS Generated Status."
        ::= { asE1ChEntry 6 }
    
    -- 1.3.6.1.4.1.119.2.3.69.203.513.501.3.12.2.1.7
    e1LoopbackStatus OBJECT-TYPE
        SYNTAX      INTEGER { ne(1), fe(2), normal(3) }
        ACCESS      read-only
        STATUS      mandatory
        DESCRIPTION
            "E1 Channel Loopback Status."
        ::= { asE1ChEntry 7 }
    
    -- 1.3.6.1.4.1.119.2.3.69.203.513.501.3.12.2.1.8
    ppiAisStatus OBJECT-TYPE
        SYNTAX      INTEGER { normal(1), ais(2) }
        ACCESS      read-only
        STATUS      mandatory
        DESCRIPTION
            "E1 Channel AIS Status."
        ::= { asE1ChEntry 8 }
    
    -- 1.3.6.1.4.1.119.2.3.69.203.513.501.3.13
    asETHGroup OBJECT IDENTIFIER
        ::= { alarmStatusGroup 13 }
    
    -- 1.3.6.1.4.1.119.2.3.69.203.513.501.3.13.2
    asRstpGroup OBJECT IDENTIFIER
        ::= { asETHGroup 2 }
    
    -- 1.3.6.1.4.1.119.2.3.69.203.513.501.3.13.2.1
    asRstpBridgeTable OBJECT-TYPE
        SYNTAX      SEQUENCE OF AsRstpBridgeEntry
        ACCESS      not-accessible
        STATUS      mandatory
        DESCRIPTION
            "Alarm / Status information of RSTP."
        ::= { asRstpGroup 1 }
    
    -- 1.3.6.1.4.1.119.2.3.69.203.513.501.3.13.2.1.1
    asRstpBridgeEntry OBJECT-TYPE
        SYNTAX      AsRstpBridgeEntry
        ACCESS      not-accessible
        STATUS      mandatory
        DESCRIPTION
            ""
        INDEX       { asRstpBridgeNEAddress, asRstpBridgeIndex }
        ::= { asRstpBridgeTable 1 }
    
    AsRstpBridgeEntry ::= SEQUENCE {
        asRstpBridgeIndex           INTEGER,
        asRstpBridgeNEAddress       IpAddress,
        asRstpBridgeDesignatedRoot  BridgeId,
        asRstpBridgeTopChanges      INTEGER
    }
    
    -- 1.3.6.1.4.1.119.2.3.69.203.513.501.3.13.2.1.1.1
    asRstpBridgeIndex OBJECT-TYPE
        SYNTAX      INTEGER (1)
        ACCESS      not-accessible
        STATUS      mandatory
        DESCRIPTION
            "Index of this table."
        ::= { asRstpBridgeEntry 1 }
    
    -- 1.3.6.1.4.1.119.2.3.69.203.513.501.3.13.2.1.1.2
    asRstpBridgeNEAddress OBJECT-TYPE
        SYNTAX      IpAddress
        ACCESS      not-accessible
        STATUS      mandatory
        DESCRIPTION
            "reserved."
        ::= { asRstpBridgeEntry 2 }
    
    -- 1.3.6.1.4.1.119.2.3.69.203.513.501.3.13.2.1.1.3
    asRstpBridgeDesignatedRoot OBJECT-TYPE
        SYNTAX      BridgeId
        ACCESS      read-only
        STATUS      mandatory
        DESCRIPTION
            "The bridge identifier of the root of the spanning tree."
        ::= { asRstpBridgeEntry 3 }
    
    -- 1.3.6.1.4.1.119.2.3.69.203.513.501.3.13.2.1.1.4
    asRstpBridgeTopChanges OBJECT-TYPE
        SYNTAX      INTEGER
        ACCESS      read-only
        STATUS      mandatory
        DESCRIPTION
            "RSTP Topology Changed Status. The total number of topology
             chagnes detected by this bridge since the equipment was last
             initialized."
        ::= { asRstpBridgeEntry 4 }
    
    -- 1.3.6.1.4.1.119.2.3.69.203.513.501.3.13.2.2
    asRstpPortTable OBJECT-TYPE
        SYNTAX      SEQUENCE OF AsRstpPortEntry
        ACCESS      not-accessible
        STATUS      mandatory
        DESCRIPTION
            "Alarm / Status information of RSTP per Ethernet Port."
        ::= { asRstpGroup 2 }
    
    -- 1.3.6.1.4.1.119.2.3.69.203.513.501.3.13.2.2.1
    asRstpPortEntry OBJECT-TYPE
        SYNTAX      AsRstpPortEntry
        ACCESS      not-accessible
        STATUS      mandatory
        DESCRIPTION
            ""
        INDEX       { asRstpPortNEAddress, asRstpIfIndex }
        ::= { asRstpPortTable 1 }
    
    AsRstpPortEntry ::= SEQUENCE {
        asRstpIfIndex                                   InterfaceIndex,
        asRstpPortNEAddress                             IpAddress,
        asRstpPortRole                                  INTEGER,
        asRstpPortState                                 INTEGER,
        asRstpPortNewRootBridgeDetectedBridgePriority   BridgeId,
        asRstpPortProtocolMigrationVersion              INTEGER,
        asRstpPortPathCost                              INTEGER,
        asRstpPortInvalidBpduCause                      INTEGER,
        asRstpPortDesignatedCost                        INTEGER,
        asRstpPortDesignatedBridge                      BridgeId,
        asRstpPortDesignatedPort                        OCTET STRING,
        asRstpPortForwardTransitions                    Counter,
        asRstpPortOperEdgePort                          INTEGER,
        asRstpPortOperPointToPoint                      EnableDisableValue
    }
    
    -- 1.3.6.1.4.1.119.2.3.69.203.513.501.3.13.2.2.1.1
    asRstpIfIndex OBJECT-TYPE
        SYNTAX      InterfaceIndex
        ACCESS      not-accessible
        STATUS      mandatory
        DESCRIPTION
            "Index of this table."
        ::= { asRstpPortEntry 1 }
    
    -- 1.3.6.1.4.1.119.2.3.69.203.513.501.3.13.2.2.1.2
    asRstpPortNEAddress OBJECT-TYPE
        SYNTAX      IpAddress
        ACCESS      not-accessible
        STATUS      mandatory
        DESCRIPTION
            "reserved"
        ::= { asRstpPortEntry 2 }
    
    -- 1.3.6.1.4.1.119.2.3.69.203.513.501.3.13.2.2.1.3
    asRstpPortRole OBJECT-TYPE
        SYNTAX      INTEGER { disabledPort(1), alternatePort(2),
                        backupPort(3), rootPort(4), designatedPort(5) }
        ACCESS      read-only
        STATUS      mandatory
        DESCRIPTION
            "RSTP Port Role. The port's current state, as defined by
             application of the Spanning Tree Protocol. This state controls
             what action a port takes on reception of a frame."
        ::= { asRstpPortEntry 3 }
    
    -- 1.3.6.1.4.1.119.2.3.69.203.513.501.3.13.2.2.1.4
    asRstpPortState OBJECT-TYPE
        SYNTAX      INTEGER { disabled(1), blocking(2), listening(3),
                        learning(4), forwarding(5), broken(6), discarding(7) }
        ACCESS      read-only
        STATUS      mandatory
        DESCRIPTION
            "RSTP Port Status. The port's current state, as defined by
             application of the Spanning Tree Protocol. This state controls
             what action a port takes on reception of a frame."
        ::= { asRstpPortEntry 4 }
    
    -- 1.3.6.1.4.1.119.2.3.69.203.513.501.3.13.2.2.1.5
    asRstpPortNewRootBridgeDetectedBridgePriority OBJECT-TYPE
        SYNTAX      BridgeId
        ACCESS      read-only
        STATUS      mandatory
        DESCRIPTION
            "RSTP New Bridge Detect Status. The unique Bridge Identifier of
             the Bridge recorded as the Root in the Configuration BPDUs."
        ::= { asRstpPortEntry 5 }
    
    -- 1.3.6.1.4.1.119.2.3.69.203.513.501.3.13.2.2.1.6
    asRstpPortProtocolMigrationVersion OBJECT-TYPE
        SYNTAX      INTEGER { stp(1), rstp(2) }
        ACCESS      read-only
        STATUS      mandatory
        DESCRIPTION
            "RSTP Protocol Migration. The port's operating protocol version."
        ::= { asRstpPortEntry 6 }
    
    -- 1.3.6.1.4.1.119.2.3.69.203.513.501.3.13.2.2.1.7
    asRstpPortPathCost OBJECT-TYPE
        SYNTAX      INTEGER (1..200000000)
        ACCESS      read-only
        STATUS      mandatory
        DESCRIPTION
            "The port's path cost, defined by application depends on its port
             speed."
        ::= { asRstpPortEntry 7 }
    
    -- 1.3.6.1.4.1.119.2.3.69.203.513.501.3.13.2.2.1.8
    asRstpPortInvalidBpduCause OBJECT-TYPE
        SYNTAX      INTEGER { restore(0), protocolID(1), bpduType(2),
                        tcnLength(3), rstpLength(4), configLength(5),
                        maxAge(6), fwdDelay(7), helloTime(8) }
        ACCESS      read-only
        STATUS      mandatory
        DESCRIPTION
            "RSTP Invalid BPDU Received. The event status of invalid BPDU
             received."
        ::= { asRstpPortEntry 8 }
    
    -- 1.3.6.1.4.1.119.2.3.69.203.513.501.3.13.2.2.1.9
    asRstpPortDesignatedCost OBJECT-TYPE
        SYNTAX      INTEGER (1..200000000)
        ACCESS      read-only
        STATUS      mandatory
        DESCRIPTION
            "The path cost of the Designated Port of the segment connected to
             this port."
        ::= { asRstpPortEntry 9 }
    
    -- 1.3.6.1.4.1.119.2.3.69.203.513.501.3.13.2.2.1.10
    asRstpPortDesignatedBridge OBJECT-TYPE
        SYNTAX      BridgeId
        ACCESS      read-only
        STATUS      mandatory
        DESCRIPTION
            "The bridge identifier of the bridge that this port considers to
             be the designated Bridge for this port's segment."
        ::= { asRstpPortEntry 10 }
    
    -- 1.3.6.1.4.1.119.2.3.69.203.513.501.3.13.2.2.1.11
    asRstpPortDesignatedPort OBJECT-TYPE
        SYNTAX      OCTET STRING
        ACCESS      read-only
        STATUS      mandatory
        DESCRIPTION
            "The port identifier of the port on the designated bridge for
             this port's segment."
        ::= { asRstpPortEntry 11 }
    
    -- 1.3.6.1.4.1.119.2.3.69.203.513.501.3.13.2.2.1.12
    asRstpPortForwardTransitions OBJECT-TYPE
        SYNTAX      Counter
        ACCESS      read-only
        STATUS      mandatory
        DESCRIPTION
            "The number of times this port has transitioned from the learning
             state to the forwarding state."
        ::= { asRstpPortEntry 12 }
    
    -- 1.3.6.1.4.1.119.2.3.69.203.513.501.3.13.2.2.1.13
    asRstpPortOperEdgePort OBJECT-TYPE
        SYNTAX      INTEGER { alarmOff(0), alarmOn(1) }
        ACCESS      read-only
        STATUS      mandatory
        DESCRIPTION
            "The operational value of the edge port parameter. This object is
             initialized to 'alarmOff'. This object will be changed to
             'alarmOn' on reception of a BPDU if the corresponding
             'provRstpExtPortAdminEdgePort' is set to 'enabled'."
        ::= { asRstpPortEntry 13 }
    
    -- 1.3.6.1.4.1.119.2.3.69.203.513.501.3.13.2.2.1.14
    asRstpPortOperPointToPoint OBJECT-TYPE
        SYNTAX      EnableDisableValue
        ACCESS      read-only
        STATUS      mandatory
        DESCRIPTION
            "The operational value of the point-to-point port parameter."
        ::= { asRstpPortEntry 14 }
    
    -- 1.3.6.1.4.1.119.2.3.69.203.513.501.3.13.3
    asEthOamGroup OBJECT IDENTIFIER
        ::= { asETHGroup 3 }
    
    -- 1.3.6.1.4.1.119.2.3.69.203.513.501.3.13.3.1
    asEthOamCcGroup OBJECT IDENTIFIER
        ::= { asEthOamGroup 1 }
    
    -- 1.3.6.1.4.1.119.2.3.69.203.513.501.3.13.3.1.1
    asEthOamMepCcmFaultTable OBJECT-TYPE
        SYNTAX      SEQUENCE OF AsEthOamMepCcmFaultEntry
        ACCESS      not-accessible
        STATUS      mandatory
        DESCRIPTION
            "ETH-CC Fault Management Table"
        ::= { asEthOamCcGroup 1 }
    
    -- 1.3.6.1.4.1.119.2.3.69.203.513.501.3.13.3.1.1.1
    asEthOamMepCcmFaultEntry OBJECT-TYPE
        SYNTAX      AsEthOamMepCcmFaultEntry
        ACCESS      not-accessible
        STATUS      mandatory
        DESCRIPTION
            ""
        INDEX       { asEthOamMepCcmFaultNEAddress, asEthOamMepCcmIndex }
        ::= { asEthOamMepCcmFaultTable 1 }
    
    AsEthOamMepCcmFaultEntry ::= SEQUENCE {
        asEthOamMepCcmIndex                     IpeMepId,
        asEthOamMepCcmFaultNEAddress            IpAddress,
        asEthOamMepCcmLOC                       SeverityValue,
        asEthOamMepCcmRdiReceived               SeverityValue,
        asEthOamMepCcmMismergeCondition         SeverityValue,
        asEthOamMepCcmUnexpectedMepCondition    SeverityValue
    }
    
    -- 1.3.6.1.4.1.119.2.3.69.203.513.501.3.13.3.1.1.1.1
    asEthOamMepCcmIndex OBJECT-TYPE
        SYNTAX      IpeMepId
        ACCESS      not-accessible
        STATUS      mandatory
        DESCRIPTION
            "Index of this table. The value is not same as MEP ID of protocol
             sense, uniquely assigned administrative value."
        ::= { asEthOamMepCcmFaultEntry 1 }
    
    -- 1.3.6.1.4.1.119.2.3.69.203.513.501.3.13.3.1.1.1.2
    asEthOamMepCcmFaultNEAddress OBJECT-TYPE
        SYNTAX      IpAddress
        ACCESS      not-accessible
        STATUS      mandatory
        DESCRIPTION
            "reserved"
        ::= { asEthOamMepCcmFaultEntry 2 }
    
    -- 1.3.6.1.4.1.119.2.3.69.203.513.501.3.13.3.1.1.1.3
    asEthOamMepCcmLOC OBJECT-TYPE
        SYNTAX      SeverityValue
        ACCESS      read-only
        STATUS      mandatory
        DESCRIPTION
            "ETH-OAM LOC Alarm. The MEP is not receiveing valid CCM from at
             least one of the remote MEP."
        ::= { asEthOamMepCcmFaultEntry 3 }
    
    -- 1.3.6.1.4.1.119.2.3.69.203.513.501.3.13.3.1.1.1.4
    asEthOamMepCcmRdiReceived OBJECT-TYPE
        SYNTAX      SeverityValue
        ACCESS      read-only
        STATUS      mandatory
        DESCRIPTION
            "ETH-OAM RDI Alarm. A remote MEP is reported the RDI in is last
             CCM."
        ::= { asEthOamMepCcmFaultEntry 4 }
    
    -- 1.3.6.1.4.1.119.2.3.69.203.513.501.3.13.3.1.1.1.5
    asEthOamMepCcmMismergeCondition OBJECT-TYPE
        SYNTAX      SeverityValue
        ACCESS      read-only
        STATUS      obsolete
        DESCRIPTION
            "obsoleted"
        ::= { asEthOamMepCcmFaultEntry 5 }
    
    -- 1.3.6.1.4.1.119.2.3.69.203.513.501.3.13.3.1.1.1.6
    asEthOamMepCcmUnexpectedMepCondition OBJECT-TYPE
        SYNTAX      SeverityValue
        ACCESS      read-only
        STATUS      obsolete
        DESCRIPTION
            "obsoleted"
        ::= { asEthOamMepCcmFaultEntry 6 }
    
    -- 1.3.6.1.4.1.119.2.3.69.203.513.501.3.13.3.1.2
    asEthOamMepCcmDbTable OBJECT-TYPE
        SYNTAX      SEQUENCE OF AsEthOamMepCcmDbEntry
        ACCESS      not-accessible
        STATUS      mandatory
        DESCRIPTION
            "ETH-CCM Database Table"
        ::= { asEthOamCcGroup 2 }
    
    -- 1.3.6.1.4.1.119.2.3.69.203.513.501.3.13.3.1.2.1
    asEthOamMepCcmDbEntry OBJECT-TYPE
        SYNTAX      AsEthOamMepCcmDbEntry
        ACCESS      not-accessible
        STATUS      mandatory
        DESCRIPTION
            ""
        INDEX       { asEthOamMepCcmDbNEAddress, asEthOamMepCcmDbPeerMepIndex }
        ::= { asEthOamMepCcmDbTable 1 }
    
    AsEthOamMepCcmDbEntry ::= SEQUENCE {
        asEthOamMepCcmDbPeerMepIndex    IpeMepId,
        asEthOamMepCcmDbNEAddress       IpAddress,
        asEthOamMepCcmDbMepIndex        IpeMepId,
        asEthOamMepCcmDbPeerMepId       INTEGER,
        asEthOamMepCcmDbMepId           INTEGER,
        asEthOamMepCcmDbCondition       TruthValue,
        asEthOamMepCcmDbRdiReceived     TruthValue
    }
    
    -- 1.3.6.1.4.1.119.2.3.69.203.513.501.3.13.3.1.2.1.1
    asEthOamMepCcmDbPeerMepIndex OBJECT-TYPE
        SYNTAX      IpeMepId
        ACCESS      not-accessible
        STATUS      mandatory
        DESCRIPTION
            "Index of this table representing peer MEP index. The value is
             not same as MEP ID of protocol sense, uniquely assigned
             administrative value."
        ::= { asEthOamMepCcmDbEntry 1 }
    
    -- 1.3.6.1.4.1.119.2.3.69.203.513.501.3.13.3.1.2.1.2
    asEthOamMepCcmDbNEAddress OBJECT-TYPE
        SYNTAX      IpAddress
        ACCESS      not-accessible
        STATUS      mandatory
        DESCRIPTION
            "reserved"
        ::= { asEthOamMepCcmDbEntry 2 }
    
    -- 1.3.6.1.4.1.119.2.3.69.203.513.501.3.13.3.1.2.1.3
    asEthOamMepCcmDbMepIndex OBJECT-TYPE
        SYNTAX      IpeMepId
        ACCESS      read-only
        STATUS      mandatory
        DESCRIPTION
            "Administrative Mep Index of own MEP."
        ::= { asEthOamMepCcmDbEntry 3 }
    
    -- 1.3.6.1.4.1.119.2.3.69.203.513.501.3.13.3.1.2.1.4
    asEthOamMepCcmDbPeerMepId OBJECT-TYPE
        SYNTAX      INTEGER (0..8191)
        ACCESS      read-only
        STATUS      mandatory
        DESCRIPTION
            "this object represents protocol sense MEP ID of peer MEP."
        ::= { asEthOamMepCcmDbEntry 4 }
    
    -- 1.3.6.1.4.1.119.2.3.69.203.513.501.3.13.3.1.2.1.5
    asEthOamMepCcmDbMepId OBJECT-TYPE
        SYNTAX      INTEGER (0..8191)
        ACCESS      read-only
        STATUS      mandatory
        DESCRIPTION
            "this object represents protocol sense MEP ID of local MEP."
        ::= { asEthOamMepCcmDbEntry 5 }
    
    -- 1.3.6.1.4.1.119.2.3.69.203.513.501.3.13.3.1.2.1.6
    asEthOamMepCcmDbCondition OBJECT-TYPE
        SYNTAX      TruthValue
        ACCESS      read-only
        STATUS      mandatory
        DESCRIPTION
            "This object represents the status of LOC detection per Peer
             MEP."
        ::= { asEthOamMepCcmDbEntry 6 }
    
    -- 1.3.6.1.4.1.119.2.3.69.203.513.501.3.13.3.1.2.1.7
    asEthOamMepCcmDbRdiReceived OBJECT-TYPE
        SYNTAX      TruthValue
        ACCESS      read-only
        STATUS      mandatory
        DESCRIPTION
            "This object represents the status of RDI receive status per peer
             MEP."
        ::= { asEthOamMepCcmDbEntry 7 }
    
    -- 1.3.6.1.4.1.119.2.3.69.203.513.501.3.13.3.1.3
    asEthOamMegCcmFaultTable OBJECT-TYPE
        SYNTAX      SEQUENCE OF AsEthOamMegCcmFaultEntry
        ACCESS      not-accessible
        STATUS      mandatory
        DESCRIPTION
            "ETH-CC Fault Management Table(MEG)"
        ::= { asEthOamCcGroup 3 }
    
    -- 1.3.6.1.4.1.119.2.3.69.203.513.501.3.13.3.1.3.1
    asEthOamMegCcmFaultEntry OBJECT-TYPE
        SYNTAX      AsEthOamMegCcmFaultEntry
        ACCESS      not-accessible
        STATUS      mandatory
        DESCRIPTION
            ""
        INDEX       { asEthOamMegCcmFaultNEAddress, asEthOamMegCcmIndex }
        ::= { asEthOamMegCcmFaultTable 1 }
    
    AsEthOamMegCcmFaultEntry ::= SEQUENCE {
        asEthOamMegCcmIndex                     INTEGER,
        asEthOamMegCcmFaultNEAddress            IpAddress,
        asEthOamMegCcmMismergeCondition         SeverityValue,
        asEthOamMegCcmUnexpectedMepCondition    SeverityValue
    }
    
    -- 1.3.6.1.4.1.119.2.3.69.203.513.501.3.13.3.1.3.1.1
    asEthOamMegCcmIndex OBJECT-TYPE
        SYNTAX      INTEGER (1..128)
        ACCESS      not-accessible
        STATUS      mandatory
        DESCRIPTION
            "Index of this table."
        ::= { asEthOamMegCcmFaultEntry 1 }
    
    -- 1.3.6.1.4.1.119.2.3.69.203.513.501.3.13.3.1.3.1.2
    asEthOamMegCcmFaultNEAddress OBJECT-TYPE
        SYNTAX      IpAddress
        ACCESS      not-accessible
        STATUS      mandatory
        DESCRIPTION
            "reserved."
        ::= { asEthOamMegCcmFaultEntry 2 }
    
    -- 1.3.6.1.4.1.119.2.3.69.203.513.501.3.13.3.1.3.1.3
    asEthOamMegCcmMismergeCondition OBJECT-TYPE
        SYNTAX      SeverityValue
        ACCESS      read-only
        STATUS      mandatory
        DESCRIPTION
            "ETH-OAM Mismerge Alarm. The MEP received a CCM frame with
             correct MEG level but an incorrect MEG ID (Maintenance Domain
             Name)."
        ::= { asEthOamMegCcmFaultEntry 3 }
    
    -- 1.3.6.1.4.1.119.2.3.69.203.513.501.3.13.3.1.3.1.4
    asEthOamMegCcmUnexpectedMepCondition OBJECT-TYPE
        SYNTAX      SeverityValue
        ACCESS      read-only
        STATUS      mandatory
        DESCRIPTION
            "ETH-OAM Unexpected MEP Alarm. The MEP Received a CCM frame with
             the correct MEG level and MEG ID, but unexpected MEP ID."
        ::= { asEthOamMegCcmFaultEntry 4 }
    
    -- 1.3.6.1.4.1.119.2.3.69.203.513.501.3.13.3.2
    asEthOamAisGroup OBJECT IDENTIFIER
        ::= { asEthOamGroup 2 }
    
    -- 1.3.6.1.4.1.119.2.3.69.203.513.501.3.13.3.2.1
    asEthOamAisTable OBJECT-TYPE
        SYNTAX      SEQUENCE OF AsEthOamAisEntry
        ACCESS      not-accessible
        STATUS      obsolete
        DESCRIPTION
            "ETH-AIS Status Table"
        ::= { asEthOamAisGroup 1 }
    
    -- 1.3.6.1.4.1.119.2.3.69.203.513.501.3.13.3.2.1.1
    asEthOamAisEntry OBJECT-TYPE
        SYNTAX      AsEthOamAisEntry
        ACCESS      not-accessible
        STATUS      obsolete
        DESCRIPTION
            ""
        INDEX       { asEthOamAisNEAddress, asEthOamAisMepIndex }
        ::= { asEthOamAisTable 1 }
    
    AsEthOamAisEntry ::= SEQUENCE {
        asEthOamAisMepIndex     IpeMepId,
        asEthOamAisNEAddress    IpAddress,
        asEthOamAisCondition    SeverityValue,
        asEthOamAisPeriod       INTEGER
    }
    
    -- 1.3.6.1.4.1.119.2.3.69.203.513.501.3.13.3.2.1.1.1
    asEthOamAisMepIndex OBJECT-TYPE
        SYNTAX      IpeMepId
        ACCESS      not-accessible
        STATUS      obsolete
        DESCRIPTION
            "Index of this table. Administrative ID of local MEP."
        ::= { asEthOamAisEntry 1 }
    
    -- 1.3.6.1.4.1.119.2.3.69.203.513.501.3.13.3.2.1.1.2
    asEthOamAisNEAddress OBJECT-TYPE
        SYNTAX      IpAddress
        ACCESS      not-accessible
        STATUS      obsolete
        DESCRIPTION
            "reserved"
        ::= { asEthOamAisEntry 2 }
    
    -- 1.3.6.1.4.1.119.2.3.69.203.513.501.3.13.3.2.1.1.3
    asEthOamAisCondition OBJECT-TYPE
        SYNTAX      SeverityValue
        ACCESS      read-only
        STATUS      obsolete
        DESCRIPTION
            "obsoleted"
        ::= { asEthOamAisEntry 3 }
    
    -- 1.3.6.1.4.1.119.2.3.69.203.513.501.3.13.3.2.1.1.4
    asEthOamAisPeriod OBJECT-TYPE
        SYNTAX      INTEGER { invalid(0), period-1s(4), period-1min(6) }
        ACCESS      read-only
        STATUS      obsolete
        DESCRIPTION
            "obsoleted"
        ::= { asEthOamAisEntry 4 }
    
    -- 1.3.6.1.4.1.119.2.3.69.203.513.501.3.13.3.3
    asEthOamBnGroup OBJECT IDENTIFIER
        ::= { asEthOamGroup 3 }
    
    -- 1.3.6.1.4.1.119.2.3.69.203.513.501.3.13.3.3.1
    asEthOamBnmTransmissionInfoTable OBJECT-TYPE
        SYNTAX      SEQUENCE OF AsEthOamBnmTransmissionInfoEntry
        ACCESS      not-accessible
        STATUS      mandatory
        DESCRIPTION
            "ETH-BN, Bandwidth Notification, Transmission Information Table."
        ::= { asEthOamBnGroup 1 }
    
    -- 1.3.6.1.4.1.119.2.3.69.203.513.501.3.13.3.3.1.1
    asEthOamBnmTransmissionInfoEntry OBJECT-TYPE
        SYNTAX      AsEthOamBnmTransmissionInfoEntry
        ACCESS      not-accessible
        STATUS      mandatory
        DESCRIPTION
            ""
        INDEX       { asEthOamBnmTransmissionNEAddress, asEthOamBnmTransmissionIndex }
        ::= { asEthOamBnmTransmissionInfoTable 1 }
    
    AsEthOamBnmTransmissionInfoEntry ::= SEQUENCE {
        asEthOamBnmTransmissionIndex            IpeMepId,
        asEthOamBnmTransmissionNEAddress        IpAddress,
        asEthOamBnmTransmissionNominalValue     INTEGER,
        asEthOamBnmTransmissionCurrentValue     INTEGER
    }
    
    -- 1.3.6.1.4.1.119.2.3.69.203.513.501.3.13.3.3.1.1.1
    asEthOamBnmTransmissionIndex OBJECT-TYPE
        SYNTAX      IpeMepId
        ACCESS      not-accessible
        STATUS      mandatory
        DESCRIPTION
            "Index of this table."
        ::= { asEthOamBnmTransmissionInfoEntry 1 }
    
    -- 1.3.6.1.4.1.119.2.3.69.203.513.501.3.13.3.3.1.1.2
    asEthOamBnmTransmissionNEAddress OBJECT-TYPE
        SYNTAX      IpAddress
        ACCESS      not-accessible
        STATUS      mandatory
        DESCRIPTION
            "reserved"
        ::= { asEthOamBnmTransmissionInfoEntry 2 }
    
    -- 1.3.6.1.4.1.119.2.3.69.203.513.501.3.13.3.3.1.1.3
    asEthOamBnmTransmissionNominalValue OBJECT-TYPE
        SYNTAX      INTEGER (0..10312)
        ACCESS      read-only
        STATUS      mandatory
        DESCRIPTION
            "This object represents nominal value of the radio bandwidth
             information of Server MEP.  The units of this value is Mbps."
        ::= { asEthOamBnmTransmissionInfoEntry 3 }
    
    -- 1.3.6.1.4.1.119.2.3.69.203.513.501.3.13.3.3.1.1.4
    asEthOamBnmTransmissionCurrentValue OBJECT-TYPE
        SYNTAX      INTEGER (0..10312)
        ACCESS      read-only
        STATUS      mandatory
        DESCRIPTION
            "This object represents current value of the radio bandwidth
             information of Server MEP.  The units of this value is Mbps."
        ::= { asEthOamBnmTransmissionInfoEntry 4 }
    
    -- 1.3.6.1.4.1.119.2.3.69.203.513.501.3.13.3.3.2
    asEthOamBnmReceptionInfoTable OBJECT-TYPE
        SYNTAX      SEQUENCE OF AsEthOamBnmReceptionInfoEntry
        ACCESS      not-accessible
        STATUS      mandatory
        DESCRIPTION
            "ETH-BN, Bandwidth Notification, Reception Information Table."
        ::= { asEthOamBnGroup 2 }
    
    -- 1.3.6.1.4.1.119.2.3.69.203.513.501.3.13.3.3.2.1
    asEthOamBnmReceptionInfoEntry OBJECT-TYPE
        SYNTAX      AsEthOamBnmReceptionInfoEntry
        ACCESS      not-accessible
        STATUS      mandatory
        DESCRIPTION
            "ETH-BN, Bandwidth Notification, Reception Information Entry."
        INDEX       { asEthOamBnmReceptionNEAddress, asEthOamBnmReceptionIndex }
        ::= { asEthOamBnmReceptionInfoTable 1 }
    
    AsEthOamBnmReceptionInfoEntry ::= SEQUENCE {
        asEthOamBnmReceptionIndex           IpeMepId,
        asEthOamBnmReceptionNEAddress       IpAddress,
        asEthOamBnmReceptionPeriod          INTEGER,
        asEthOamBnmReceptionCurrentValue    INTEGER,
        asEthOamBnmReceptionUNP             SeverityValue,
        asEthOamBnmReceptionLOC             SeverityValue,
        asEthOamBnmReceptionUNL             SeverityValue
    }
    
    -- 1.3.6.1.4.1.119.2.3.69.203.513.501.3.13.3.3.2.1.1
    asEthOamBnmReceptionIndex OBJECT-TYPE
        SYNTAX      IpeMepId
        ACCESS      not-accessible
        STATUS      mandatory
        DESCRIPTION
            "Index of this table."
        ::= { asEthOamBnmReceptionInfoEntry 1 }
    
    -- 1.3.6.1.4.1.119.2.3.69.203.513.501.3.13.3.3.2.1.2
    asEthOamBnmReceptionNEAddress OBJECT-TYPE
        SYNTAX      IpAddress
        ACCESS      not-accessible
        STATUS      mandatory
        DESCRIPTION
            "reserved"
        ::= { asEthOamBnmReceptionInfoEntry 2 }
    
    -- 1.3.6.1.4.1.119.2.3.69.203.513.501.3.13.3.3.2.1.3
    asEthOamBnmReceptionPeriod OBJECT-TYPE
        SYNTAX      INTEGER { invalid(0), period-1s(1), period-10s(2),
                        period-1min(3) }
        ACCESS      read-only
        STATUS      obsolete
        DESCRIPTION
            "BNM Frame Transmition Period"
        ::= { asEthOamBnmReceptionInfoEntry 3 }
    
    -- 1.3.6.1.4.1.119.2.3.69.203.513.501.3.13.3.3.2.1.4
    asEthOamBnmReceptionCurrentValue OBJECT-TYPE
        SYNTAX      INTEGER (0..10312)
        ACCESS      read-only
        STATUS      mandatory
        DESCRIPTION
            "This object represents current value of the radio bandwidth
             information of Client MEP.  The unit of this value is Mbps."
        ::= { asEthOamBnmReceptionInfoEntry 4 }
    
    -- 1.3.6.1.4.1.119.2.3.69.203.513.501.3.13.3.3.2.1.5
    asEthOamBnmReceptionUNP OBJECT-TYPE
        SYNTAX      SeverityValue
        ACCESS      read-only
        STATUS      mandatory
        DESCRIPTION
            "ETH-BN UNP Alarm"
        ::= { asEthOamBnmReceptionInfoEntry 5 }
    
    -- 1.3.6.1.4.1.119.2.3.69.203.513.501.3.13.3.3.2.1.6
    asEthOamBnmReceptionLOC OBJECT-TYPE
        SYNTAX      SeverityValue
        ACCESS      read-only
        STATUS      mandatory
        DESCRIPTION
            "ETH-BN LOC Alarm"
        ::= { asEthOamBnmReceptionInfoEntry 6 }
    
    -- 1.3.6.1.4.1.119.2.3.69.203.513.501.3.13.3.3.2.1.7
    asEthOamBnmReceptionUNL OBJECT-TYPE
        SYNTAX      SeverityValue
        ACCESS      read-only
        STATUS      mandatory
        DESCRIPTION
            "ETH-BN UNL Alarm"
        ::= { asEthOamBnmReceptionInfoEntry 7 }
    
    -- 1.3.6.1.4.1.119.2.3.69.203.513.501.3.13.6
    asFdbGroup OBJECT IDENTIFIER
        ::= { asETHGroup 6 }
    
    -- 1.3.6.1.4.1.119.2.3.69.203.513.501.3.13.6.1
    asFdbEquipmentTable OBJECT-TYPE
        SYNTAX      SEQUENCE OF AsFdbEquipmentEntry
        ACCESS      not-accessible
        STATUS      mandatory
        DESCRIPTION
            "Forwarding Database Status per Equipment."
        ::= { asFdbGroup 1 }
    
    -- 1.3.6.1.4.1.119.2.3.69.203.513.501.3.13.6.1.1
    asFdbEquipmentEntry OBJECT-TYPE
        SYNTAX      AsFdbEquipmentEntry
        ACCESS      not-accessible
        STATUS      mandatory
        DESCRIPTION
            ""
        INDEX       { asFdbEquipmentNEAddress, asFdbEquipmentIndex }
        ::= { asFdbEquipmentTable 1 }
    
    AsFdbEquipmentEntry ::= SEQUENCE {
        asFdbEquipmentIndex                 INTEGER,
        asFdbEquipmentNEAddress             IpAddress,
        asFdbEquipmentLearningCount         Gauge,
        asFdbEquipmentLearningLimitOver     INTEGER
    }
    
    -- 1.3.6.1.4.1.119.2.3.69.203.513.501.3.13.6.1.1.1
    asFdbEquipmentIndex OBJECT-TYPE
        SYNTAX      INTEGER (1)
        ACCESS      not-accessible
        STATUS      mandatory
        DESCRIPTION
            "Index of this table. This object is created per equipment."
        ::= { asFdbEquipmentEntry 1 }
    
    -- 1.3.6.1.4.1.119.2.3.69.203.513.501.3.13.6.1.1.2
    asFdbEquipmentNEAddress OBJECT-TYPE
        SYNTAX      IpAddress
        ACCESS      not-accessible
        STATUS      mandatory
        DESCRIPTION
            "reserved."
        ::= { asFdbEquipmentEntry 2 }
    
    -- 1.3.6.1.4.1.119.2.3.69.203.513.501.3.13.6.1.1.3
    asFdbEquipmentLearningCount OBJECT-TYPE
        SYNTAX      Gauge
        ACCESS      read-only
        STATUS      mandatory
        DESCRIPTION
            "Total FDB Dynamic Entry Count. the number of forwarding entries
             which is learned currently."
        ::= { asFdbEquipmentEntry 3 }
    
    -- 1.3.6.1.4.1.119.2.3.69.203.513.501.3.13.6.1.1.4
    asFdbEquipmentLearningLimitOver OBJECT-TYPE
        SYNTAX      INTEGER { notReached(1), reached(2) }
        ACCESS      read-only
        STATUS      mandatory
        DESCRIPTION
            "Total FDB Full. learning limit status. When
             'asFdbEquipmentLearningCount' reaches
             'provFdbEquipmentNumberOfLearningEntry', this object will be
             changed to 'reached'."
        ::= { asFdbEquipmentEntry 4 }
    
    -- 1.3.6.1.4.1.119.2.3.69.203.513.501.3.13.6.2
    asFdbPortTable OBJECT-TYPE
        SYNTAX      SEQUENCE OF AsFdbPortEntry
        ACCESS      not-accessible
        STATUS      mandatory
        DESCRIPTION
            ""
        ::= { asFdbGroup 2 }
    
    -- 1.3.6.1.4.1.119.2.3.69.203.513.501.3.13.6.2.1
    asFdbPortEntry OBJECT-TYPE
        SYNTAX      AsFdbPortEntry
        ACCESS      not-accessible
        STATUS      mandatory
        DESCRIPTION
            "Forwarding Database Status per port."
        INDEX       { asFdbPortNEAddress, asFdbPortIfIndex }
        ::= { asFdbPortTable 1 }
    
    AsFdbPortEntry ::= SEQUENCE {
        asFdbPortIfIndex            InterfaceIndex,
        asFdbPortNEAddress          IpAddress,
        asFdbPortLearningCount      Gauge,
        asFdbPortLearningLimitOver  INTEGER
    }
    
    -- 1.3.6.1.4.1.119.2.3.69.203.513.501.3.13.6.2.1.1
    asFdbPortIfIndex OBJECT-TYPE
        SYNTAX      InterfaceIndex
        ACCESS      not-accessible
        STATUS      mandatory
        DESCRIPTION
            "Index of this table."
        ::= { asFdbPortEntry 1 }
    
    -- 1.3.6.1.4.1.119.2.3.69.203.513.501.3.13.6.2.1.2
    asFdbPortNEAddress OBJECT-TYPE
        SYNTAX      IpAddress
        ACCESS      not-accessible
        STATUS      mandatory
        DESCRIPTION
            "reserved."
        ::= { asFdbPortEntry 2 }
    
    -- 1.3.6.1.4.1.119.2.3.69.203.513.501.3.13.6.2.1.3
    asFdbPortLearningCount OBJECT-TYPE
        SYNTAX      Gauge
        ACCESS      read-only
        STATUS      mandatory
        DESCRIPTION
            "FDB Dynamic Entry Count. The number of forwarding entries which
             is learned currently."
        ::= { asFdbPortEntry 3 }
    
    -- 1.3.6.1.4.1.119.2.3.69.203.513.501.3.13.6.2.1.4
    asFdbPortLearningLimitOver OBJECT-TYPE
        SYNTAX      INTEGER { notReached(1), reached(2) }
        ACCESS      read-only
        STATUS      mandatory
        DESCRIPTION
            "FDB Full. learning limit status. When 'asFdbPortLearningCount'
             reaches corresponding 'provFdbPortLearningLimit', this object
             will be changed to 'reached'."
        ::= { asFdbPortEntry 4 }
    
    -- 1.3.6.1.4.1.119.2.3.69.203.513.501.3.13.6.3
    asFdbVlanTable OBJECT-TYPE
        SYNTAX      SEQUENCE OF AsFdbVlanEntry
        ACCESS      not-accessible
        STATUS      mandatory
        DESCRIPTION
            "Forwarding Database status per VLAN."
        ::= { asFdbGroup 3 }
    
    -- 1.3.6.1.4.1.119.2.3.69.203.513.501.3.13.6.3.1
    asFdbVlanEntry OBJECT-TYPE
        SYNTAX      AsFdbVlanEntry
        ACCESS      not-accessible
        STATUS      mandatory
        DESCRIPTION
            ""
        INDEX       { asFdbVlanNEAddress, asFdbVlanIndex }
        ::= { asFdbVlanTable 1 }
    
    AsFdbVlanEntry ::= SEQUENCE {
        asFdbVlanIndex              INTEGER,
        asFdbVlanNEAddress          IpAddress,
        asFdbVlanLearningCount      Gauge,
        asFdbVlanLearningLimitOver  INTEGER
    }
    
    -- 1.3.6.1.4.1.119.2.3.69.203.513.501.3.13.6.3.1.1
    asFdbVlanIndex OBJECT-TYPE
        SYNTAX      INTEGER (1..4094)
        ACCESS      not-accessible
        STATUS      mandatory
        DESCRIPTION
            "Index of this table. The value is same as VLAN ID."
        ::= { asFdbVlanEntry 1 }
    
    -- 1.3.6.1.4.1.119.2.3.69.203.513.501.3.13.6.3.1.2
    asFdbVlanNEAddress OBJECT-TYPE
        SYNTAX      IpAddress
        ACCESS      not-accessible
        STATUS      mandatory
        DESCRIPTION
            "reserved."
        ::= { asFdbVlanEntry 2 }
    
    -- 1.3.6.1.4.1.119.2.3.69.203.513.501.3.13.6.3.1.3
    asFdbVlanLearningCount OBJECT-TYPE
        SYNTAX      Gauge
        ACCESS      read-only
        STATUS      mandatory
        DESCRIPTION
            "FDB Dynamic Entry Count per VLAN. The number of forwarding
             entries which is learned currently."
        ::= { asFdbVlanEntry 3 }
    
    -- 1.3.6.1.4.1.119.2.3.69.203.513.501.3.13.6.3.1.4
    asFdbVlanLearningLimitOver OBJECT-TYPE
        SYNTAX      INTEGER { notReached(1), reached(2) }
        ACCESS      read-only
        STATUS      mandatory
        DESCRIPTION
            "FDB Full Per VLAN. Learning limit status. When
             'asFdbVlanLearningCount' reaches corresponding
             'provFdbVlanNumberOfLearningEntry', this object will be changed
             to 'reached'."
        ::= { asFdbVlanEntry 4 }
    
    -- 1.3.6.1.4.1.119.2.3.69.203.513.501.3.13.7
    asLlfGroup OBJECT IDENTIFIER
        ::= { asETHGroup 7 }
    
    -- 1.3.6.1.4.1.119.2.3.69.203.513.501.3.13.7.1
    asLlfGroupTable OBJECT-TYPE
        SYNTAX      SEQUENCE OF AsLlfGroupEntry
        ACCESS      not-accessible
        STATUS      mandatory
        DESCRIPTION
            "Link Loss Forwarding(LLF) Status per LLF Group."
        ::= { asLlfGroup 1 }
    
    -- 1.3.6.1.4.1.119.2.3.69.203.513.501.3.13.7.1.1
    asLlfGroupEntry OBJECT-TYPE
        SYNTAX      AsLlfGroupEntry
        ACCESS      not-accessible
        STATUS      mandatory
        DESCRIPTION
            ""
        INDEX       { asLlfGroupNEAddress, asLlfGroupIndex }
        ::= { asLlfGroupTable 1 }
    
    AsLlfGroupEntry ::= SEQUENCE {
        asLlfGroupIndex         INTEGER,
        asLlfGroupNEAddress     IpAddress,
        asLlfGroupForceClose    INTEGER,
        asLlfGroupTimeout       INTEGER
    }
    
    -- 1.3.6.1.4.1.119.2.3.69.203.513.501.3.13.7.1.1.1
    asLlfGroupIndex OBJECT-TYPE
        SYNTAX      INTEGER (1..16)
        ACCESS      not-accessible
        STATUS      mandatory
        DESCRIPTION
            "Index of this table. The value means LLF Group Index."
        ::= { asLlfGroupEntry 1 }
    
    -- 1.3.6.1.4.1.119.2.3.69.203.513.501.3.13.7.1.1.2
    asLlfGroupNEAddress OBJECT-TYPE
        SYNTAX      IpAddress
        ACCESS      not-accessible
        STATUS      mandatory
        DESCRIPTION
            "reserved."
        ::= { asLlfGroupEntry 2 }
    
    -- 1.3.6.1.4.1.119.2.3.69.203.513.501.3.13.7.1.1.3
    asLlfGroupForceClose OBJECT-TYPE
        SYNTAX      INTEGER { not-forceclose(1), forceclose(2) }
        ACCESS      read-only
        STATUS      mandatory
        DESCRIPTION
            "LLF close status. 'forceclose' means that edge port which is
             assigned to the LLF group is closed because of LLF."
        ::= { asLlfGroupEntry 3 }
    
    -- 1.3.6.1.4.1.119.2.3.69.203.513.501.3.13.7.1.1.4
    asLlfGroupTimeout OBJECT-TYPE
        SYNTAX      INTEGER { received(1), timeout(2) }
        ACCESS      read-only
        STATUS      mandatory
        DESCRIPTION
            "LLF Timeout Status. The periodic LLF messages is not received."
        ::= { asLlfGroupEntry 4 }
    
    -- 1.3.6.1.4.1.119.2.3.69.203.513.501.3.13.7.2
    asLlfReceiveInfoTable OBJECT-TYPE
        SYNTAX      SEQUENCE OF AsLlfReceiveInfoEntry
        ACCESS      not-accessible
        STATUS      obsolete
        DESCRIPTION
            "Link Loss Forwarding (LLF) Status per port."
        ::= { asLlfGroup 2 }
    
    -- 1.3.6.1.4.1.119.2.3.69.203.513.501.3.13.7.2.1
    asLlfReceiveInfoEntry OBJECT-TYPE
        SYNTAX      AsLlfReceiveInfoEntry
        ACCESS      not-accessible
        STATUS      obsolete
        DESCRIPTION
            ""
        INDEX       { asLlfReceiveInfoNEAddress, asLlfReceiveInfoIfIndex, asLlfReceiveInfoGroupIndex }
        ::= { asLlfReceiveInfoTable 1 }
    
    AsLlfReceiveInfoEntry ::= SEQUENCE {
        asLlfReceiveInfoIfIndex     InterfaceIndex,
        asLlfReceiveInfoGroupIndex  INTEGER,
        asLlfReceiveInfoNEAddress   IpAddress,
        asLlfReceiveInfoLinkSts     INTEGER
    }
    
    -- 1.3.6.1.4.1.119.2.3.69.203.513.501.3.13.7.2.1.1
    asLlfReceiveInfoIfIndex OBJECT-TYPE
        SYNTAX      InterfaceIndex
        ACCESS      not-accessible
        STATUS      obsolete
        DESCRIPTION
            "reserved."
        ::= { asLlfReceiveInfoEntry 1 }
    
    -- 1.3.6.1.4.1.119.2.3.69.203.513.501.3.13.7.2.1.2
    asLlfReceiveInfoGroupIndex OBJECT-TYPE
        SYNTAX      INTEGER (1..16)
        ACCESS      not-accessible
        STATUS      obsolete
        DESCRIPTION
            "LLF Group Index. The value means LLF Group Index which is
             assigned to the port."
        ::= { asLlfReceiveInfoEntry 2 }
    
    -- 1.3.6.1.4.1.119.2.3.69.203.513.501.3.13.7.2.1.3
    asLlfReceiveInfoNEAddress OBJECT-TYPE
        SYNTAX      IpAddress
        ACCESS      not-accessible
        STATUS      obsolete
        DESCRIPTION
            "reserved"
        ::= { asLlfReceiveInfoEntry 3 }
    
    -- 1.3.6.1.4.1.119.2.3.69.203.513.501.3.13.7.2.1.4
    asLlfReceiveInfoLinkSts OBJECT-TYPE
        SYNTAX      INTEGER { down(1), up(2) }
        ACCESS      read-only
        STATUS      obsolete
        DESCRIPTION
            "LLF Link Information which is received from peer."
        ::= { asLlfReceiveInfoEntry 4 }
    
    -- 1.3.6.1.4.1.119.2.3.69.203.513.501.3.13.8
    asETHPortGroup OBJECT IDENTIFIER
        ::= { asETHGroup 8 }
    
    -- 1.3.6.1.4.1.119.2.3.69.203.513.501.3.13.8.1
    asETHPortTable OBJECT-TYPE
        SYNTAX      SEQUENCE OF AsETHPortEntry
        ACCESS      not-accessible
        STATUS      mandatory
        DESCRIPTION
            "Ethernet Port Status Table."
        ::= { asETHPortGroup 1 }
    
    -- 1.3.6.1.4.1.119.2.3.69.203.513.501.3.13.8.1.1
    asETHPortEntry OBJECT-TYPE
        SYNTAX      AsETHPortEntry
        ACCESS      not-accessible
        STATUS      mandatory
        DESCRIPTION
            ""
        INDEX       { asETHPortNEAddress, asETHPortIfIndex }
        ::= { asETHPortTable 1 }
    
    AsETHPortEntry ::= SEQUENCE {
        asETHPortIfIndex                InterfaceIndex,
        asETHPortNEAddress              IpAddress,
        asETHPortInterfaceType          INTEGER,
        asETHPortSpeedDuplex            INTEGER,
        asETHPortFlowControl            INTEGER,
        asETHPortMDIMDIX                INTEGER,
        asETHPortLinkStatus             SeverityValue,
        asETHPortAdminStatus            INTEGER,
        asETHPortSFPEquip               SeverityValue,
        asETHPortSFPLos                 SeverityValue,
        asETHPortSFPTxError             SeverityValue,
        asETHPortSFPTypeMismatch        SeverityValue,
        asETHPortOperStatus             INTEGER,
        asETHPortLlfOamReceived         INTEGER,
        asETHPortAlsStatus              OffOnValue,
        asETHPortLaserShutdownStatus    OffOnValue,
        asETHPortLocalFault             SeverityValue,
        asETHPortRemoteFault            SeverityValue
    }
    
    -- 1.3.6.1.4.1.119.2.3.69.203.513.501.3.13.8.1.1.1
    asETHPortIfIndex OBJECT-TYPE
        SYNTAX      InterfaceIndex
        ACCESS      not-accessible
        STATUS      mandatory
        DESCRIPTION
            "Index of this table. The administrative number which is assigned
             to the port uniquely."
        ::= { asETHPortEntry 1 }
    
    -- 1.3.6.1.4.1.119.2.3.69.203.513.501.3.13.8.1.1.2
    asETHPortNEAddress OBJECT-TYPE
        SYNTAX      IpAddress
        ACCESS      not-accessible
        STATUS      mandatory
        DESCRIPTION
            "reserved"
        ::= { asETHPortEntry 2 }
    
    -- 1.3.6.1.4.1.119.2.3.69.203.513.501.3.13.8.1.1.3
    asETHPortInterfaceType OBJECT-TYPE
        SYNTAX      INTEGER { invalid(0), fiber(1), copper(2) }
        ACCESS      read-only
        STATUS      mandatory
        DESCRIPTION
            "GbE SFP Port Type Status. This object represents interface type
             which is installed currently."
        ::= { asETHPortEntry 3 }
    
    -- 1.3.6.1.4.1.119.2.3.69.203.513.501.3.13.8.1.1.4
    asETHPortSpeedDuplex OBJECT-TYPE
        SYNTAX      INTEGER { invalid(0), s10M-HALF(1), s10M-FULL(2),
                        s100M-HALF(3), s100M-FULL(4), s1000M-FULL(5),
                        s10G-FULL(6) }
        ACCESS      read-only
        STATUS      mandatory
        DESCRIPTION
            "GbE Speed & Duplex Status."
        ::= { asETHPortEntry 4 }
    
    -- 1.3.6.1.4.1.119.2.3.69.203.513.501.3.13.8.1.1.5
    asETHPortFlowControl OBJECT-TYPE
        SYNTAX      INTEGER { disable(1), enable(2) }
        ACCESS      read-only
        STATUS      mandatory
        DESCRIPTION
            "GbE Flow Control Status."
        ::= { asETHPortEntry 5 }
    
    -- 1.3.6.1.4.1.119.2.3.69.203.513.501.3.13.8.1.1.6
    asETHPortMDIMDIX OBJECT-TYPE
        SYNTAX      INTEGER { invalid(0), mdi(1), mdi-x(2) }
        ACCESS      read-only
        STATUS      mandatory
        DESCRIPTION
            "GbE MDI / MDI-X Status."
        ::= { asETHPortEntry 6 }
    
    -- 1.3.6.1.4.1.119.2.3.69.203.513.501.3.13.8.1.1.7
    asETHPortLinkStatus OBJECT-TYPE
        SYNTAX      SeverityValue
        ACCESS      read-only
        STATUS      mandatory
        DESCRIPTION
            "GbE LAN Link Alarm."
        ::= { asETHPortEntry 7 }
    
    -- 1.3.6.1.4.1.119.2.3.69.203.513.501.3.13.8.1.1.8
    asETHPortAdminStatus OBJECT-TYPE
        SYNTAX      INTEGER { normal(1), force(2), oamSend(3) }
        ACCESS      read-only
        STATUS      mandatory
        DESCRIPTION
            "GbE LLF Status. When the port is closed by LLF, the object will
             be changed to 'force'.
             But if 'provLlfPortMode' is configured to 'edgeOamSend', this
             object will be changed to 'oamSend' when the port is controlled
             by LLF."
        ::= { asETHPortEntry 8 }
    
    -- 1.3.6.1.4.1.119.2.3.69.203.513.501.3.13.8.1.1.9
    asETHPortSFPEquip OBJECT-TYPE
        SYNTAX      SeverityValue
        ACCESS      read-only
        STATUS      mandatory
        DESCRIPTION
            "GbE SFP Removed Alarm."
        ::= { asETHPortEntry 9 }
    
    -- 1.3.6.1.4.1.119.2.3.69.203.513.501.3.13.8.1.1.10
    asETHPortSFPLos OBJECT-TYPE
        SYNTAX      SeverityValue
        ACCESS      read-only
        STATUS      mandatory
        DESCRIPTION
            "GbE ETH LOS Alarm."
        ::= { asETHPortEntry 10 }
    
    -- 1.3.6.1.4.1.119.2.3.69.203.513.501.3.13.8.1.1.11
    asETHPortSFPTxError OBJECT-TYPE
        SYNTAX      SeverityValue
        ACCESS      read-only
        STATUS      mandatory
        DESCRIPTION
            "GbE ETH TF (Transmit FAIL) Alarm."
        ::= { asETHPortEntry 11 }
    
    -- 1.3.6.1.4.1.119.2.3.69.203.513.501.3.13.8.1.1.12
    asETHPortSFPTypeMismatch OBJECT-TYPE
        SYNTAX      SeverityValue
        ACCESS      read-only
        STATUS      mandatory
        DESCRIPTION
            "GbE SFP Type Mismatch Alarm. This object reports that the
             provisioned interface type and the installed media type are
             inconsistent."
        ::= { asETHPortEntry 12 }
    
    -- 1.3.6.1.4.1.119.2.3.69.203.513.501.3.13.8.1.1.13
    asETHPortOperStatus OBJECT-TYPE
        SYNTAX      INTEGER { invalid(0), linkDown(1), linkUp(2) }
        ACCESS      read-only
        STATUS      mandatory
        DESCRIPTION
            "GbE ETH LAN Link Status. This object is not suppressed by the
             lower layer alarms."
        ::= { asETHPortEntry 13 }
    
    -- 1.3.6.1.4.1.119.2.3.69.203.513.501.3.13.8.1.1.14
    asETHPortLlfOamReceived OBJECT-TYPE
        SYNTAX      INTEGER { invalid(0), normal(1), receive(2) }
        ACCESS      read-only
        STATUS      mandatory
        DESCRIPTION
            "GbE LLF message receive status.
             When the port received LLF request messages, the object will
             return the value 'receive'."
        ::= { asETHPortEntry 14 }
    
    -- 1.3.6.1.4.1.119.2.3.69.203.513.501.3.13.8.1.1.15
    asETHPortAlsStatus OBJECT-TYPE
        SYNTAX      OffOnValue
        ACCESS      read-only
        STATUS      mandatory
        DESCRIPTION
            "ALS Status"
        ::= { asETHPortEntry 15 }
    
    -- 1.3.6.1.4.1.119.2.3.69.203.513.501.3.13.8.1.1.16
    asETHPortLaserShutdownStatus OBJECT-TYPE
        SYNTAX      OffOnValue
        ACCESS      read-only
        STATUS      mandatory
        DESCRIPTION
            "Laser Shutdown status."
        ::= { asETHPortEntry 16 }
    
    -- 1.3.6.1.4.1.119.2.3.69.203.513.501.3.13.8.1.1.17
    asETHPortLocalFault OBJECT-TYPE
        SYNTAX      SeverityValue
        ACCESS      read-only
        STATUS      mandatory
        DESCRIPTION
            "XGbE Local Fault"
        ::= { asETHPortEntry 17 }
    
    -- 1.3.6.1.4.1.119.2.3.69.203.513.501.3.13.8.1.1.18
    asETHPortRemoteFault OBJECT-TYPE
        SYNTAX      SeverityValue
        ACCESS      read-only
        STATUS      mandatory
        DESCRIPTION
            "XGbe Remote Fault"
        ::= { asETHPortEntry 18 }
    
    -- 1.3.6.1.4.1.119.2.3.69.203.513.501.3.13.9
    asSyncETHGroup OBJECT IDENTIFIER
        ::= { asETHGroup 9 }
    
    -- 1.3.6.1.4.1.119.2.3.69.203.513.501.3.13.9.2
    asSyncETHTable OBJECT-TYPE
        SYNTAX      SEQUENCE OF AsSyncETHEntry
        ACCESS      not-accessible
        STATUS      mandatory
        DESCRIPTION
            "Sync Ethernet Status table."
        ::= { asSyncETHGroup 2 }
    
    -- 1.3.6.1.4.1.119.2.3.69.203.513.501.3.13.9.2.1
    asSyncETHEntry OBJECT-TYPE
        SYNTAX      AsSyncETHEntry
        ACCESS      not-accessible
        STATUS      mandatory
        DESCRIPTION
            ""
        INDEX       { asSyncETHNEAddress, asSyncETHIfIndex }
        ::= { asSyncETHTable 1 }
    
    AsSyncETHEntry ::= SEQUENCE {
        asSyncETHIfIndex        InterfaceIndex,
        asSyncETHNEAddress      IpAddress,
        asSyncETHPortCLKSts     INTEGER
    }
    
    -- 1.3.6.1.4.1.119.2.3.69.203.513.501.3.13.9.2.1.1
    asSyncETHIfIndex OBJECT-TYPE
        SYNTAX      InterfaceIndex
        ACCESS      read-only
        STATUS      mandatory
        DESCRIPTION
            "Index of this table."
        ::= { asSyncETHEntry 1 }
    
    -- 1.3.6.1.4.1.119.2.3.69.203.513.501.3.13.9.2.1.2
    asSyncETHNEAddress OBJECT-TYPE
        SYNTAX      IpAddress
        ACCESS      read-only
        STATUS      mandatory
        DESCRIPTION
            "reserved."
        ::= { asSyncETHEntry 2 }
    
    -- 1.3.6.1.4.1.119.2.3.69.203.513.501.3.13.9.2.1.3
    asSyncETHPortCLKSts OBJECT-TYPE
        SYNTAX      INTEGER
        ACCESS      read-only
        STATUS      mandatory
        DESCRIPTION
            "Sync ETH Port CLK Status."
        ::= { asSyncETHEntry 3 }
    
    -- 1.3.6.1.4.1.119.2.3.69.203.513.501.3.13.10
    asQosGroup OBJECT IDENTIFIER
        ::= { asETHGroup 10 }
    
    -- 1.3.6.1.4.1.119.2.3.69.203.513.501.3.13.10.1
    asQosTable OBJECT-TYPE
        SYNTAX      SEQUENCE OF AsQosEntry
        ACCESS      not-accessible
        STATUS      obsolete
        DESCRIPTION
            "Qos Information per port."
        ::= { asQosGroup 1 }
    
    -- 1.3.6.1.4.1.119.2.3.69.203.513.501.3.13.10.1.1
    asQosEntry OBJECT-TYPE
        SYNTAX      AsQosEntry
        ACCESS      not-accessible
        STATUS      obsolete
        DESCRIPTION
            ""
        INDEX       { asQosNEAddress, asQosPortindex }
        ::= { asQosTable 1 }
    
    AsQosEntry ::= SEQUENCE {
        asQosPortindex      InterfaceIndex,
        asQosNEAddress      IpAddress,
        asQosAmrBandWidth   INTEGER
    }
    
    -- 1.3.6.1.4.1.119.2.3.69.203.513.501.3.13.10.1.1.1
    asQosPortindex OBJECT-TYPE
        SYNTAX      InterfaceIndex
        ACCESS      not-accessible
        STATUS      obsolete
        DESCRIPTION
            "Index of this table."
        ::= { asQosEntry 1 }
    
    -- 1.3.6.1.4.1.119.2.3.69.203.513.501.3.13.10.1.1.2
    asQosNEAddress OBJECT-TYPE
        SYNTAX      IpAddress
        ACCESS      not-accessible
        STATUS      obsolete
        DESCRIPTION
            "reserved."
        ::= { asQosEntry 2 }
    
    -- 1.3.6.1.4.1.119.2.3.69.203.513.501.3.13.10.1.1.3
    asQosAmrBandWidth OBJECT-TYPE
        SYNTAX      INTEGER
        ACCESS      read-only
        STATUS      obsolete
        DESCRIPTION
            "The value of Qos bandwidth which is  determined by the smaller
             value of the followings.
              AMR bandwidth - E1 bandwidth - total EIR bandwidth.
               Or
              AMR bandwidth - E1 bandwidth - total CIR bandwidth."
        ::= { asQosEntry 3 }
    
    -- 1.3.6.1.4.1.119.2.3.69.203.513.501.3.13.32
    asETHCardGroup OBJECT IDENTIFIER
        ::= { asETHGroup 32 }
    
    -- 1.3.6.1.4.1.119.2.3.69.203.513.501.3.13.32.1
    asETHCardTable OBJECT-TYPE
        SYNTAX      SEQUENCE OF AsETHCardEntry
        ACCESS      not-accessible
        STATUS      mandatory
        DESCRIPTION
            "ETH Card Status table."
        ::= { asETHCardGroup 1 }
    
    -- 1.3.6.1.4.1.119.2.3.69.203.513.501.3.13.32.1.1
    asETHCardEntry OBJECT-TYPE
        SYNTAX      AsETHCardEntry
        ACCESS      not-accessible
        STATUS      mandatory
        DESCRIPTION
            ""
        INDEX       { asETHCardNEAddress, asETHCardIndex }
        ::= { asETHCardTable 1 }
    
    AsETHCardEntry ::= SEQUENCE {
        asETHCardIndex      INTEGER,
        asETHCardNEAddress  IpAddress,
        ethAlarm            SeverityValue,
        ethComFailAlarm     SeverityValue,
        ethUnequipped       SeverityValue,
        ethTypeMismatch     SeverityValue,
        ethBusErrorTx       SeverityValue,
        ethBusErrorRx       SeverityValue
    }
    
    -- 1.3.6.1.4.1.119.2.3.69.203.513.501.3.13.32.1.1.1
    asETHCardIndex OBJECT-TYPE
        SYNTAX      INTEGER
        ACCESS      not-accessible
        STATUS      mandatory
        DESCRIPTION
            "Index of this table."
        ::= { asETHCardEntry 1 }
    
    -- 1.3.6.1.4.1.119.2.3.69.203.513.501.3.13.32.1.1.2
    asETHCardNEAddress OBJECT-TYPE
        SYNTAX      IpAddress
        ACCESS      not-accessible
        STATUS      mandatory
        DESCRIPTION
            "reserved."
        ::= { asETHCardEntry 2 }
    
    -- 1.3.6.1.4.1.119.2.3.69.203.513.501.3.13.32.1.1.3
    ethAlarm OBJECT-TYPE
        SYNTAX      SeverityValue
        ACCESS      read-only
        STATUS      mandatory
        DESCRIPTION
            "GbE Module Alarm."
        ::= { asETHCardEntry 3 }
    
    -- 1.3.6.1.4.1.119.2.3.69.203.513.501.3.13.32.1.1.4
    ethComFailAlarm OBJECT-TYPE
        SYNTAX      SeverityValue
        ACCESS      read-only
        STATUS      mandatory
        DESCRIPTION
            "GbE Communication FAIL Alarm."
        ::= { asETHCardEntry 4 }
    
    -- 1.3.6.1.4.1.119.2.3.69.203.513.501.3.13.32.1.1.5
    ethUnequipped OBJECT-TYPE
        SYNTAX      SeverityValue
        ACCESS      read-only
        STATUS      mandatory
        DESCRIPTION
            "GbE Unequipped Alarm."
        ::= { asETHCardEntry 5 }
    
    -- 1.3.6.1.4.1.119.2.3.69.203.513.501.3.13.32.1.1.6
    ethTypeMismatch OBJECT-TYPE
        SYNTAX      SeverityValue
        ACCESS      read-only
        STATUS      mandatory
        DESCRIPTION
            "GbE Type Mismatch Alarm."
        ::= { asETHCardEntry 6 }
    
    -- 1.3.6.1.4.1.119.2.3.69.203.513.501.3.13.32.1.1.7
    ethBusErrorTx OBJECT-TYPE
        SYNTAX      SeverityValue
        ACCESS      read-only
        STATUS      mandatory
        DESCRIPTION
            "GbE TX Bus Error Alarm."
        ::= { asETHCardEntry 7 }
    
    -- 1.3.6.1.4.1.119.2.3.69.203.513.501.3.13.32.1.1.8
    ethBusErrorRx OBJECT-TYPE
        SYNTAX      SeverityValue
        ACCESS      read-only
        STATUS      mandatory
        DESCRIPTION
            "GbE RX Bus Error Alarm."
        ::= { asETHCardEntry 8 }
    
    -- 1.3.6.1.4.1.119.2.3.69.203.513.501.3.14
    asCommonGroup OBJECT IDENTIFIER
        ::= { alarmStatusGroup 14 }
    
    -- 1.3.6.1.4.1.119.2.3.69.203.513.501.3.14.1
    iduCommonTable OBJECT-TYPE
        SYNTAX      SEQUENCE OF IduCommonEntry
        ACCESS      not-accessible
        STATUS      mandatory
        DESCRIPTION
            "Equipment Configuration Status Table."
        ::= { asCommonGroup 1 }
    
    -- 1.3.6.1.4.1.119.2.3.69.203.513.501.3.14.1.1
    iduCommonEntry OBJECT-TYPE
        SYNTAX      IduCommonEntry
        ACCESS      not-accessible
        STATUS      mandatory
        DESCRIPTION
            ""
        INDEX       { iduCommonNEAddress, iduCommonIndex }
        ::= { iduCommonTable 1 }
    
    IduCommonEntry ::= SEQUENCE {
        iduCommonIndex      INTEGER,
        iduCommonNEAddress  IpAddress,
        equipConfigStatus   INTEGER
    }
    
    -- 1.3.6.1.4.1.119.2.3.69.203.513.501.3.14.1.1.1
    iduCommonIndex OBJECT-TYPE
        SYNTAX      INTEGER { iduCommon(1) }
        ACCESS      not-accessible
        STATUS      mandatory
        DESCRIPTION
            "Index of this table."
        ::= { iduCommonEntry 1 }
    
    -- 1.3.6.1.4.1.119.2.3.69.203.513.501.3.14.1.1.2
    iduCommonNEAddress OBJECT-TYPE
        SYNTAX      IpAddress
        ACCESS      not-accessible
        STATUS      mandatory
        DESCRIPTION
            "reseved"
        ::= { iduCommonEntry 2 }
    
    -- 1.3.6.1.4.1.119.2.3.69.203.513.501.3.14.1.1.3
    equipConfigStatus OBJECT-TYPE
        SYNTAX      INTEGER
        ACCESS      read-only
        STATUS      mandatory
        DESCRIPTION
            "Equipment Configuration Status. The object is used for
             determining the status synchronization method for the manager
             entity."
        ::= { iduCommonEntry 3 }
    
    -- 1.3.6.1.4.1.119.2.3.69.203.513.501.3.14.2
    asCommonTable OBJECT-TYPE
        SYNTAX      SEQUENCE OF AsCommonEntry
        ACCESS      not-accessible
        STATUS      mandatory
        DESCRIPTION
            "Installed Card Status table."
        ::= { asCommonGroup 2 }
    
    -- 1.3.6.1.4.1.119.2.3.69.203.513.501.3.14.2.1
    asCommonEntry OBJECT-TYPE
        SYNTAX      AsCommonEntry
        ACCESS      not-accessible
        STATUS      mandatory
        DESCRIPTION
            ""
        INDEX       { asCommonNEAddress, asCommonIndex }
        ::= { asCommonTable 1 }
    
    AsCommonEntry ::= SEQUENCE {
        asCommonIndex                   INTEGER,
        asCommonNEAddress               IpAddress,
        asUserInterface                 INTEGER,
        asConfigStatus                  INTEGER,
        asClk2mType                     INTEGER,
        asClk2mConfigStatus             INTEGER,
        asClkOptionCardType             INTEGER,
        asClkOptionCardConfigStatus     INTEGER
    }
    
    -- 1.3.6.1.4.1.119.2.3.69.203.513.501.3.14.2.1.1
    asCommonIndex OBJECT-TYPE
        SYNTAX      INTEGER
        ACCESS      not-accessible
        STATUS      mandatory
        DESCRIPTION
            "Index of this table. The value is equivalent to the slot number
             + 1."
        ::= { asCommonEntry 1 }
    
    -- 1.3.6.1.4.1.119.2.3.69.203.513.501.3.14.2.1.2
    asCommonNEAddress OBJECT-TYPE
        SYNTAX      IpAddress
        ACCESS      not-accessible
        STATUS      mandatory
        DESCRIPTION
            "reserved."
        ::= { asCommonEntry 2 }
    
    -- 1.3.6.1.4.1.119.2.3.69.203.513.501.3.14.2.1.3
    asUserInterface OBJECT-TYPE
        SYNTAX      INTEGER { invalid(0), notUsed(1), modem(2), e1(3),
                        gbex4p(6), gbe4pEle(7), mse(9), aux(11), stm1x2p(12),
                        ps(14), fan(15), main(17), modemE(19), modemAV(30),
                        xgbex1p(32), gbe4pOpt(33), modemEV(34), termV(36),
                        swcMV(44), modemT(50), aux-swo(51), modemET(60),
                        xgbeAV1p(61), unknown(99) }
        ACCESS      read-only
        STATUS      mandatory
        DESCRIPTION
            "Installed card type.
             The value modemEX10(38) is available only for the iPASOLINK EX
             Advanced."
        ::= { asCommonEntry 3 }
    
    -- 1.3.6.1.4.1.119.2.3.69.203.513.501.3.14.2.1.4
    asConfigStatus OBJECT-TYPE
        SYNTAX      INTEGER { invalid(0), unequipped(1), configured(2),
                        unconfigured(3), mismatch(4) }
        ACCESS      read-only
        STATUS      mandatory
        DESCRIPTION
            "Configuration status of installed card. The value is determined
             from provisioned card type and installed card type."
        ::= { asCommonEntry 4 }
    
    -- 1.3.6.1.4.1.119.2.3.69.203.513.501.3.14.2.1.5
    asClk2mType OBJECT-TYPE
        SYNTAX      INTEGER { invalid(0), clk2m(2) }
        ACCESS      read-only
        STATUS      mandatory
        DESCRIPTION
            "Installed CLK type."
        ::= { asCommonEntry 5 }
    
    -- 1.3.6.1.4.1.119.2.3.69.203.513.501.3.14.2.1.6
    asClk2mConfigStatus OBJECT-TYPE
        SYNTAX      INTEGER { invalid(0), configured(2) }
        ACCESS      read-only
        STATUS      mandatory
        DESCRIPTION
            "Configuration status of CLK card. The value is determined from
             provisioned CLK type and installed CLK type."
        ::= { asCommonEntry 6 }
    
    -- 1.3.6.1.4.1.119.2.3.69.203.513.501.3.14.2.1.7
    asClkOptionCardType OBJECT-TYPE
        SYNTAX      INTEGER { invalid(0), notUsed(1), clkcv1(3), clkcv2(4),
                        unknown(99) }
        ACCESS      read-only
        STATUS      mandatory
        DESCRIPTION
            "Installed CLK option card type."
        ::= { asCommonEntry 7 }
    
    -- 1.3.6.1.4.1.119.2.3.69.203.513.501.3.14.2.1.8
    asClkOptionCardConfigStatus OBJECT-TYPE
        SYNTAX      INTEGER { invalid(0), unequipped(1), configured(2),
                        unconfigured(3), mismatch(4) }
        ACCESS      read-only
        STATUS      mandatory
        DESCRIPTION
            "Configuration status of CLK option card. The value is determined
             from provisioned CLK option card type and installed CLK option
             card type."
        ::= { asCommonEntry 8 }
    
    -- 1.3.6.1.4.1.119.2.3.69.203.513.501.3.20
    asCurrentAlarmGroup OBJECT IDENTIFIER
        ::= { alarmStatusGroup 20 }
    
    -- 1.3.6.1.4.1.119.2.3.69.203.513.501.3.20.1
    asCurrentAlarmTable OBJECT-TYPE
        SYNTAX      SEQUENCE OF AsCurrentAlarmEntry
        ACCESS      not-accessible
        STATUS      mandatory
        DESCRIPTION
            "Current Alarm Table."
        ::= { asCurrentAlarmGroup 1 }
    
    -- 1.3.6.1.4.1.119.2.3.69.203.513.501.3.20.1.1
    asCurrentAlarmEntry OBJECT-TYPE
        SYNTAX      AsCurrentAlarmEntry
        ACCESS      not-accessible
        STATUS      mandatory
        DESCRIPTION
            ""
        INDEX       { asCurrentAlarmNEAddress, asCurrentAlarmIndex }
        ::= { asCurrentAlarmTable 1 }
    
    AsCurrentAlarmEntry ::= SEQUENCE {
    -- 1.3.6.1.4.1.119.2.3.69.203.513.501.3.20.1.1.1
        asCurrentAlarmIndex         OBJECT IDENTIFIER,
        asCurrentAlarmNEAddress     IpAddress,
        asCurrentAlarmSeverity      SeverityValue,
        asCurrentAlarmTime          DateAndTime,
        asCurrentAlarmType          AlarmTypeValue,
        asCurrentAlarmName          DisplayString,
        asCurrentAlarmDescription   DisplayString
    }
    
    -- 1.3.6.1.4.1.119.2.3.69.203.513.501.3.20.1.1.1
    asCurrentAlarmIndex OBJECT-TYPE
        SYNTAX      OBJECT IDENTIFIER
        ACCESS      not-accessible
        STATUS      mandatory
        DESCRIPTION
            "The OBJECT IDENTIFIER of the object which raised the alarm."
        ::= { asCurrentAlarmEntry 1 }
    
    -- 1.3.6.1.4.1.119.2.3.69.203.513.501.3.20.1.1.2
    asCurrentAlarmNEAddress OBJECT-TYPE
        SYNTAX      IpAddress
        ACCESS      not-accessible
        STATUS      mandatory
        DESCRIPTION
            "reserved."
        ::= { asCurrentAlarmEntry 2 }
    
    -- 1.3.6.1.4.1.119.2.3.69.203.513.501.3.20.1.1.3
    asCurrentAlarmSeverity OBJECT-TYPE
        SYNTAX      SeverityValue
        ACCESS      read-only
        STATUS      mandatory
        DESCRIPTION
            "Alarm severity value."
        ::= { asCurrentAlarmEntry 3 }
    
    -- 1.3.6.1.4.1.119.2.3.69.203.513.501.3.20.1.1.4
    asCurrentAlarmTime OBJECT-TYPE
        SYNTAX      DateAndTime
        ACCESS      read-only
        STATUS      mandatory
        DESCRIPTION
            "The local date and time when the alarm occurred."
        ::= { asCurrentAlarmEntry 4 }
    
    -- 1.3.6.1.4.1.119.2.3.69.203.513.501.3.20.1.1.5
    asCurrentAlarmType OBJECT-TYPE
        SYNTAX      AlarmTypeValue
        ACCESS      read-only
        STATUS      mandatory
        DESCRIPTION
            "Alarm Type."
        ::= { asCurrentAlarmEntry 5 }
    
    -- 1.3.6.1.4.1.119.2.3.69.203.513.501.3.20.1.1.6
    asCurrentAlarmName OBJECT-TYPE
        SYNTAX      DisplayString (SIZE(0..50))
        ACCESS      read-only
        STATUS      mandatory
        DESCRIPTION
            "Alarm Name."
        ::= { asCurrentAlarmEntry 6 }
    
    -- 1.3.6.1.4.1.119.2.3.69.203.513.501.3.20.1.1.7
    asCurrentAlarmDescription OBJECT-TYPE
        SYNTAX      DisplayString (SIZE(0..192))
        ACCESS      read-only
        STATUS      mandatory
        DESCRIPTION
            "Alarm Description."
        ::= { asCurrentAlarmEntry 7 }
    
    -- 1.3.6.1.4.1.119.2.3.69.203.513.501.3.33
    asProtectionGroup OBJECT IDENTIFIER
        ::= { alarmStatusGroup 33 }
    
    -- 1.3.6.1.4.1.119.2.3.69.203.513.501.3.33.1
    asStm1ApsTable OBJECT-TYPE
        SYNTAX      SEQUENCE OF AsStm1ApsEntry
        ACCESS      not-accessible
        STATUS      mandatory
        DESCRIPTION
            "APS Status Table. This table is created automatically when the
             APS is configured."
        ::= { asProtectionGroup 1 }
    
    -- 1.3.6.1.4.1.119.2.3.69.203.513.501.3.33.1.1
    asStm1ApsEntry OBJECT-TYPE
        SYNTAX      AsStm1ApsEntry
        ACCESS      not-accessible
        STATUS      mandatory
        DESCRIPTION
            ""
        INDEX       { asStm1ApsNEAddress, asStm1ApsIfIndex }
        ::= { asStm1ApsTable 1 }
    
    AsStm1ApsEntry ::= SEQUENCE {
        asStm1ApsIfIndex        InterfaceIndex,
        asStm1ApsNEAddress      IpAddress,
        apsProtectionStatusCh1  INTEGER,
        apsProtectionStatusCh2  INTEGER,
        apsOnlineStatus         INTEGER,
        apsLockinStatus         INTEGER,
        apsSwStatus             INTEGER
    }
    
    -- 1.3.6.1.4.1.119.2.3.69.203.513.501.3.33.1.1.1
    asStm1ApsIfIndex OBJECT-TYPE
        SYNTAX      InterfaceIndex
        ACCESS      not-accessible
        STATUS      mandatory
        DESCRIPTION
            "Index of this table."
        ::= { asStm1ApsEntry 1 }
    
    -- 1.3.6.1.4.1.119.2.3.69.203.513.501.3.33.1.1.2
    asStm1ApsNEAddress OBJECT-TYPE
        SYNTAX      IpAddress
        ACCESS      not-accessible
        STATUS      mandatory
        DESCRIPTION
            "reserved."
        ::= { asStm1ApsEntry 2 }
    
    -- 1.3.6.1.4.1.119.2.3.69.203.513.501.3.33.1.1.3
    apsProtectionStatusCh1 OBJECT-TYPE
        SYNTAX      INTEGER { fs(1), sf(2), sd(3), ms(4), nr(5) }
        ACCESS      read-only
        STATUS      mandatory
        DESCRIPTION
            "APS Protection Status for Ch1"
        ::= { asStm1ApsEntry 3 }
    
    -- 1.3.6.1.4.1.119.2.3.69.203.513.501.3.33.1.1.4
    apsProtectionStatusCh2 OBJECT-TYPE
        SYNTAX      INTEGER { fs(1), sf(2), sd(3), ms(4), nr(5) }
        ACCESS      read-only
        STATUS      mandatory
        DESCRIPTION
            "APS Protection Status for Ch2"
        ::= { asStm1ApsEntry 4 }
    
    -- 1.3.6.1.4.1.119.2.3.69.203.513.501.3.33.1.1.5
    apsOnlineStatus OBJECT-TYPE
        SYNTAX      INTEGER { work(1), protection(2) }
        ACCESS      read-only
        STATUS      mandatory
        DESCRIPTION
            "APS Online Status"
        ::= { asStm1ApsEntry 5 }
    
    -- 1.3.6.1.4.1.119.2.3.69.203.513.501.3.33.1.1.6
    apsLockinStatus OBJECT-TYPE
        SYNTAX      INTEGER { normal(1), lockin(2) }
        ACCESS      read-only
        STATUS      mandatory
        DESCRIPTION
            "APS Lockin Status"
        ::= { asStm1ApsEntry 6 }
    
    -- 1.3.6.1.4.1.119.2.3.69.203.513.501.3.33.1.1.7
    apsSwStatus OBJECT-TYPE
        SYNTAX      INTEGER { work(1), protection(2) }
        ACCESS      read-only
        STATUS      mandatory
        DESCRIPTION
            "APS Switch Status"
        ::= { asStm1ApsEntry 7 }
    
    -- 1.3.6.1.4.1.119.2.3.69.203.513.501.3.45
    asLicenseGroup OBJECT IDENTIFIER
        ::= { alarmStatusGroup 45 }
    
    -- 1.3.6.1.4.1.119.2.3.69.203.513.501.3.45.1
    asLicenseAlarmTable OBJECT-TYPE
        SYNTAX      SEQUENCE OF AsLicenseAlarmEntry
        ACCESS      not-accessible
        STATUS      mandatory
        DESCRIPTION
            "License Alarm Table."
        ::= { asLicenseGroup 1 }
    
    -- 1.3.6.1.4.1.119.2.3.69.203.513.501.3.45.1.1
    asLicenseAlarmEntry OBJECT-TYPE
        SYNTAX      AsLicenseAlarmEntry
        ACCESS      not-accessible
        STATUS      mandatory
        DESCRIPTION
            ""
        INDEX       { asLicenseAlarmNEAddress, asLicenseAlarmIndex }
        ::= { asLicenseAlarmTable 1 }
    
    AsLicenseAlarmEntry ::= SEQUENCE {
        asLicenseAlarmIndex         INTEGER,
        asLicenseAlarmNEAddress     IpAddress,
        asLicenseAlarm              SeverityValue
    }
    
    -- 1.3.6.1.4.1.119.2.3.69.203.513.501.3.45.1.1.1
    asLicenseAlarmIndex OBJECT-TYPE
        SYNTAX      INTEGER (1)
        ACCESS      not-accessible
        STATUS      mandatory
        DESCRIPTION
            "Index of this table."
        ::= { asLicenseAlarmEntry 1 }
    
    -- 1.3.6.1.4.1.119.2.3.69.203.513.501.3.45.1.1.2
    asLicenseAlarmNEAddress OBJECT-TYPE
        SYNTAX      IpAddress
        ACCESS      not-accessible
        STATUS      mandatory
        DESCRIPTION
            "reserved."
        ::= { asLicenseAlarmEntry 2 }
    
    -- 1.3.6.1.4.1.119.2.3.69.203.513.501.3.45.1.1.3
    asLicenseAlarm OBJECT-TYPE
        SYNTAX      SeverityValue
        ACCESS      read-only
        STATUS      mandatory
        DESCRIPTION
            "License Alarm.
             The alarm will be asserted when the configuration and install
             license are mismatch. The following operations can be trigger the
             alarm.
               - license downgrade
               - multiple chassis configuration (2U XPIC)
             The alarm will be cleared when the conditions mentioned above are
             cleared."
        ::= { asLicenseAlarmEntry 3 }
    
    -- 1.3.6.1.4.1.119.2.3.69.203.513.501.3.52
    asServiceSwitchGroup OBJECT IDENTIFIER
        ::= { alarmStatusGroup 52 }
    
    -- 1.3.6.1.4.1.119.2.3.69.203.513.501.3.52.1
    asServiceSwitchTable OBJECT-TYPE
        SYNTAX      SEQUENCE OF AsServiceSwitchEntry
        ACCESS      not-accessible
        STATUS      mandatory
        DESCRIPTION
            "Service Switch Table"
        ::= { asServiceSwitchGroup 1 }
    
    -- 1.3.6.1.4.1.119.2.3.69.203.513.501.3.52.1.1
    asServiceSwitchEntry OBJECT-TYPE
        SYNTAX      AsServiceSwitchEntry
        ACCESS      not-accessible
        STATUS      mandatory
        DESCRIPTION
            "Service Switch Entry"
        INDEX       { asServiceSwitchNEAddress, asServiceSwitchIndex }
        ::= { asServiceSwitchTable 1 }
    
    AsServiceSwitchEntry ::= SEQUENCE {
        asServiceSwitchIndex        INTEGER,
        asServiceSwitchNEAddress    IpAddress,
        asServiceSwitchCurrentPath  INTEGER
    }
    
    -- 1.3.6.1.4.1.119.2.3.69.203.513.501.3.52.1.1.1
    asServiceSwitchIndex OBJECT-TYPE
        SYNTAX      INTEGER (1..64)
        ACCESS      not-accessible
        STATUS      mandatory
        DESCRIPTION
            "Index of this table"
        ::= { asServiceSwitchEntry 1 }
    
    -- 1.3.6.1.4.1.119.2.3.69.203.513.501.3.52.1.1.2
    asServiceSwitchNEAddress OBJECT-TYPE
        SYNTAX      IpAddress
        ACCESS      not-accessible
        STATUS      mandatory
        DESCRIPTION
            "reserved"
        ::= { asServiceSwitchEntry 2 }
    
    -- 1.3.6.1.4.1.119.2.3.69.203.513.501.3.52.1.1.3
    asServiceSwitchCurrentPath OBJECT-TYPE
        SYNTAX      INTEGER { invalid(0), primary(1), secondary(2),
                        notSwitched(3), primaryForced(4), secondaryForced(5) }
        ACCESS      read-only
        STATUS      mandatory
        DESCRIPTION
            "Current Path"
        ::= { asServiceSwitchEntry 3 }
    
    -- 1.3.6.1.4.1.119.2.3.69.203.513.501.7
    inventoryGroup OBJECT IDENTIFIER
        ::= { pasoNeoIpe-common 7 }
    
    -- 1.3.6.1.4.1.119.2.3.69.203.513.501.7.1
    invCardInfoGroup OBJECT IDENTIFIER
        ::= { inventoryGroup 1 }
    
    -- 1.3.6.1.4.1.119.2.3.69.203.513.501.7.1.1
    invMainInfoTable OBJECT-TYPE
        SYNTAX      SEQUENCE OF InvMainInfoEntry
        ACCESS      not-accessible
        STATUS      mandatory
        DESCRIPTION
            "Equipment Inventory Information (IDU) - Main Board / Ctrl Card"
        ::= { invCardInfoGroup 1 }
    
    -- 1.3.6.1.4.1.119.2.3.69.203.513.501.7.1.1.1
    invMainInfoEntry OBJECT-TYPE
        SYNTAX      InvMainInfoEntry
        ACCESS      not-accessible
        STATUS      mandatory
        DESCRIPTION
            ""
        INDEX       { invMainInfoNEAddress, invMainInfoIndex }
        ::= { invMainInfoTable 1 }
    
    InvMainInfoEntry ::= SEQUENCE {
        invMainInfoIndex                INTEGER,
        invMainInfoNEAddress            IpAddress,
        invMainName                     DisplayString,
        invMainCodeNo                   DisplayString,
        invMainSerialNo                 DisplayString,
        invMainManufacturedDate         DisplayString,
        invMainFirmVersion              DisplayString,
        invMainFirmVersionUncurrent     DisplayString,
        invMainCardHardVersion          DisplayString
    }
    
    -- 1.3.6.1.4.1.119.2.3.69.203.513.501.7.1.1.1.1
    invMainInfoIndex OBJECT-TYPE
        SYNTAX      INTEGER (1 | 17..18)
        ACCESS      not-accessible
        STATUS      mandatory
        DESCRIPTION
            "Index of this table. value range: 17 (VR 1/VR 2/VR 4), 17-18
             (1000/VR 10), 1 (others)"
        ::= { invMainInfoEntry 1 }
    
    -- 1.3.6.1.4.1.119.2.3.69.203.513.501.7.1.1.1.2
    invMainInfoNEAddress OBJECT-TYPE
        SYNTAX      IpAddress
        ACCESS      not-accessible
        STATUS      mandatory
        DESCRIPTION
            "reserved."
        ::= { invMainInfoEntry 2 }
    
    -- 1.3.6.1.4.1.119.2.3.69.203.513.501.7.1.1.1.3
    invMainName OBJECT-TYPE
        SYNTAX      DisplayString
        ACCESS      read-only
        STATUS      mandatory
        DESCRIPTION
            "Main Board / Ctrl Card Name."
        ::= { invMainInfoEntry 3 }
    
    -- 1.3.6.1.4.1.119.2.3.69.203.513.501.7.1.1.1.4
    invMainCodeNo OBJECT-TYPE
        SYNTAX      DisplayString
        ACCESS      read-only
        STATUS      mandatory
        DESCRIPTION
            "Main Board / Ctrl Card Code No."
        ::= { invMainInfoEntry 4 }
    
    -- 1.3.6.1.4.1.119.2.3.69.203.513.501.7.1.1.1.5
    invMainSerialNo OBJECT-TYPE
        SYNTAX      DisplayString (SIZE(1..8))
        ACCESS      read-only
        STATUS      mandatory
        DESCRIPTION
            "Main Board / Ctrl Card Serial No."
        ::= { invMainInfoEntry 5 }
    
    -- 1.3.6.1.4.1.119.2.3.69.203.513.501.7.1.1.1.6
    invMainManufacturedDate OBJECT-TYPE
        SYNTAX      DisplayString
        ACCESS      read-only
        STATUS      mandatory
        DESCRIPTION
            "Main Board / Ctrl Card Manufactured Date"
        ::= { invMainInfoEntry 6 }
    
    -- 1.3.6.1.4.1.119.2.3.69.203.513.501.7.1.1.1.7
    invMainFirmVersion OBJECT-TYPE
        SYNTAX      DisplayString
        ACCESS      read-only
        STATUS      mandatory
        DESCRIPTION
            "Main Board / Ctrl Card Firmware Version."
        ::= { invMainInfoEntry 7 }
    
    -- 1.3.6.1.4.1.119.2.3.69.203.513.501.7.1.1.1.8
    invMainFirmVersionUncurrent OBJECT-TYPE
        SYNTAX      DisplayString
        ACCESS      read-only
        STATUS      mandatory
        DESCRIPTION
            "Main Board / Ctrl Card Firmware Version (Uncurrent)."
        ::= { invMainInfoEntry 8 }
    
    -- 1.3.6.1.4.1.119.2.3.69.203.513.501.7.1.1.1.9
    invMainCardHardVersion OBJECT-TYPE
        SYNTAX      DisplayString
        ACCESS      read-only
        STATUS      mandatory
        DESCRIPTION
            "Main Board / Ctrl Card Hardware Version."
        ::= { invMainInfoEntry 9 }
    
    -- 1.3.6.1.4.1.119.2.3.69.203.513.501.7.1.2
    invCardInfoTable OBJECT-TYPE
        SYNTAX      SEQUENCE OF InvCardInfoEntry
        ACCESS      not-accessible
        STATUS      mandatory
        DESCRIPTION
            "Equipment Inventory Information (IDU) - Option / Universal Card"
        ::= { invCardInfoGroup 2 }
    
    -- 1.3.6.1.4.1.119.2.3.69.203.513.501.7.1.2.1
    invCardInfoEntry OBJECT-TYPE
        SYNTAX      InvCardInfoEntry
        ACCESS      not-accessible
        STATUS      mandatory
        DESCRIPTION
            ""
        INDEX       { invCardInfoNEAddress, invCardInfoIndex }
        ::= { invCardInfoTable 1 }
    
    InvCardInfoEntry ::= SEQUENCE {
        invCardInfoIndex                INTEGER,
        invCardInfoNEAddress            IpAddress,
        invCardName                     DisplayString,
        invCardCodeNo                   DisplayString,
        invCardSerialNo                 DisplayString,
        invCardManufacturedDate         DisplayString,
        invCardFirmVersion              DisplayString,
        invCardHardVersion              DisplayString,
        invCardFirmVersionUncurrent     DisplayString
    }
    
    -- 1.3.6.1.4.1.119.2.3.69.203.513.501.7.1.2.1.1
    invCardInfoIndex OBJECT-TYPE
        SYNTAX      INTEGER
        ACCESS      not-accessible
        STATUS      mandatory
        DESCRIPTION
            "Index of this table."
        ::= { invCardInfoEntry 1 }
    
    -- 1.3.6.1.4.1.119.2.3.69.203.513.501.7.1.2.1.2
    invCardInfoNEAddress OBJECT-TYPE
        SYNTAX      IpAddress
        ACCESS      not-accessible
        STATUS      mandatory
        DESCRIPTION
            "reserved"
        ::= { invCardInfoEntry 2 }
    
    -- 1.3.6.1.4.1.119.2.3.69.203.513.501.7.1.2.1.3
    invCardName OBJECT-TYPE
        SYNTAX      DisplayString
        ACCESS      read-only
        STATUS      mandatory
        DESCRIPTION
            "Card Name. when the card is removed, the value will be changed
             to '**'."
        ::= { invCardInfoEntry 3 }
    
    -- 1.3.6.1.4.1.119.2.3.69.203.513.501.7.1.2.1.4
    invCardCodeNo OBJECT-TYPE
        SYNTAX      DisplayString
        ACCESS      read-only
        STATUS      mandatory
        DESCRIPTION
            "Card Code No. when the card is removed, the value will be
             changed to '**'."
        ::= { invCardInfoEntry 4 }
    
    -- 1.3.6.1.4.1.119.2.3.69.203.513.501.7.1.2.1.5
    invCardSerialNo OBJECT-TYPE
        SYNTAX      DisplayString
        ACCESS      read-only
        STATUS      mandatory
        DESCRIPTION
            "Card Serial No. when the card is removed, the value will be
             changed to '**'."
        ::= { invCardInfoEntry 5 }
    
    -- 1.3.6.1.4.1.119.2.3.69.203.513.501.7.1.2.1.6
    invCardManufacturedDate OBJECT-TYPE
        SYNTAX      DisplayString
        ACCESS      read-only
        STATUS      mandatory
        DESCRIPTION
            "Card Manufactured Date. when the card is removed, the value will
             be changed to '**'."
        ::= { invCardInfoEntry 6 }
    
    -- 1.3.6.1.4.1.119.2.3.69.203.513.501.7.1.2.1.7
    invCardFirmVersion OBJECT-TYPE
        SYNTAX      DisplayString
        ACCESS      read-only
        STATUS      mandatory
        DESCRIPTION
            "Card Firmware Version. when the card is removed, the value will
             be changed to '**'."
        ::= { invCardInfoEntry 7 }
    
    -- 1.3.6.1.4.1.119.2.3.69.203.513.501.7.1.2.1.8
    invCardHardVersion OBJECT-TYPE
        SYNTAX      DisplayString
        ACCESS      read-only
        STATUS      mandatory
        DESCRIPTION
            "Card Hardware Version. when the card is removed, the value will
             be changed to '**'."
        ::= { invCardInfoEntry 8 }
    
    -- 1.3.6.1.4.1.119.2.3.69.203.513.501.7.1.2.1.9
    invCardFirmVersionUncurrent OBJECT-TYPE
        SYNTAX      DisplayString
        ACCESS      read-only
        STATUS      obsolete
        DESCRIPTION
            "Card Firmware Version (uncurrent side). When the card is
             removed, the value will be changed to '**'."
        ::= { invCardInfoEntry 9 }
    
    -- 1.3.6.1.4.1.119.2.3.69.203.513.501.7.2
    invFPGAInfoTable OBJECT-TYPE
        SYNTAX      SEQUENCE OF InvFPGAInfoEntry
        ACCESS      not-accessible
        STATUS      mandatory
        DESCRIPTION
            "Equipment Inventory Information (IDU) - FPGA"
        ::= { inventoryGroup 2 }
    
    -- 1.3.6.1.4.1.119.2.3.69.203.513.501.7.2.1
    invFPGAInfoEntry OBJECT-TYPE
        SYNTAX      InvFPGAInfoEntry
        ACCESS      not-accessible
        STATUS      mandatory
        DESCRIPTION
            ""
        INDEX       { invFPGAInfoNEAddress, invFPGAInfoIndex }
        ::= { invFPGAInfoTable 1 }
    
    InvFPGAInfoEntry ::= SEQUENCE {
        invFPGAInfoIndex        INTEGER,
        invFPGAInfoNEAddress    IpAddress,
        invFPGAName             DisplayString,
        invFPGACodeNo           DisplayString,
        invFPGAHardVersion      DisplayString
    }
    
    -- 1.3.6.1.4.1.119.2.3.69.203.513.501.7.2.1.1
    invFPGAInfoIndex OBJECT-TYPE
        SYNTAX      INTEGER
        ACCESS      not-accessible
        STATUS      mandatory
        DESCRIPTION
            "Index of this table."
        ::= { invFPGAInfoEntry 1 }
    
    -- 1.3.6.1.4.1.119.2.3.69.203.513.501.7.2.1.2
    invFPGAInfoNEAddress OBJECT-TYPE
        SYNTAX      IpAddress
        ACCESS      not-accessible
        STATUS      mandatory
        DESCRIPTION
            "reserved."
        ::= { invFPGAInfoEntry 2 }
    
    -- 1.3.6.1.4.1.119.2.3.69.203.513.501.7.2.1.3
    invFPGAName OBJECT-TYPE
        SYNTAX      DisplayString
        ACCESS      read-only
        STATUS      mandatory
        DESCRIPTION
            "FPGA Name. when the card is removed, the value will be changed
             to '**'."
        ::= { invFPGAInfoEntry 3 }
    
    -- 1.3.6.1.4.1.119.2.3.69.203.513.501.7.2.1.4
    invFPGACodeNo OBJECT-TYPE
        SYNTAX      DisplayString
        ACCESS      read-only
        STATUS      mandatory
        DESCRIPTION
            "FPGA Code No. when the card is removed, the value will be
             changed to '**'."
        ::= { invFPGAInfoEntry 4 }
    
    -- 1.3.6.1.4.1.119.2.3.69.203.513.501.7.2.1.5
    invFPGAHardVersion OBJECT-TYPE
        SYNTAX      DisplayString
        ACCESS      read-only
        STATUS      mandatory
        DESCRIPTION
            "FPGA Version. when the card is removed, the value will be
             changed to '**'."
        ::= { invFPGAInfoEntry 5 }
    
    -- 1.3.6.1.4.1.119.2.3.69.203.513.501.7.3
    invModuleInfoOduTable OBJECT-TYPE
        SYNTAX      SEQUENCE OF InvModuleInfoOduEntry
        ACCESS      not-accessible
        STATUS      mandatory
        DESCRIPTION
            "Equipment Inventory Information (ODU)"
        ::= { inventoryGroup 3 }
    
    -- 1.3.6.1.4.1.119.2.3.69.203.513.501.7.3.1
    invModuleInfoOduEntry OBJECT-TYPE
        SYNTAX      InvModuleInfoOduEntry
        ACCESS      not-accessible
        STATUS      mandatory
        DESCRIPTION
            ""
        INDEX       { invModuleInfoOduNEAddress, invModuleInfoOduIfIndex }
        ::= { invModuleInfoOduTable 1 }
    
    InvModuleInfoOduEntry ::= SEQUENCE {
        invModuleInfoOduIfIndex             InterfaceIndex,
        invModuleInfoOduNEAddress           IpAddress,
        invOduCardName                      DisplayString,
        invOduCardCodeNo                    DisplayString,
        invOduCardHardVersion               DisplayString,
        invOduCardSerialNo                  DisplayString,
        invOduCardManufacturedDate          DisplayString,
        invOduCardFirmCurrentVersion        DisplayString,
        invOduCardFirmUncurrentVersion      DisplayString,
        invOduProvRangeATPCMax              INTEGER,
        invOduProvRangeATPCMin              INTEGER,
        invOduProvRangeMTPCMax              INTEGER,
        invOduProvRangeMTPCMin              INTEGER,
        invOduProvRangeRxThresholdMax       INTEGER,
        invOduProvRangeRxThresholdMin       INTEGER,
        invOduProvRangeHysteresisPermit     INTEGER,
        invOduProvRangeHysteresisMax        INTEGER,
        invOduProvRangeHysteresisMin        INTEGER,
        invOduFreqInfoTxStartFrequency      DisplayString,
        invOduFreqInfoTxStopFrequency       DisplayString,
        invOduFreqInfoRxStartFrequency      DisplayString,
        invOduFreqInfoRxStopFrequency       DisplayString,
        invOduFreqInfoFrequencyStep         DisplayString,
        invOduFreqInfoShiftFrequency        DisplayString,
        invOduFreqInfoUpperLower            INTEGER,
        invOduFreqInfoTxPhase               INTEGER,
        invOduFreqInfoRxPhase               INTEGER,
        invOduFreqInfoSubBand               DisplayString,
        invOduFreqInfoTxRxIndependence      INTEGER,
        invOduFreqInfoSupportedIpe          INTEGER,
        invOduFreqInfoSubBand1              DisplayString,
        invOduFreqInfoSubBand2              DisplayString,
        invOduFreqInfoSubBand3              DisplayString,
        invOduFreqInfoSubBand4              DisplayString,
        invOduFreqInfoSubBand5              DisplayString,
        invOduFreqInfoSubBand6              DisplayString,
        invOduFreqInfoSubBand7              DisplayString,
        invOduFreqInfoSubBand8              DisplayString,
        invOduFreqInfoSubBand9              DisplayString,
        invOduFreqInfoSubBand10             DisplayString
    }
    
    -- 1.3.6.1.4.1.119.2.3.69.203.513.501.7.3.1.1
    invModuleInfoOduIfIndex OBJECT-TYPE
        SYNTAX      InterfaceIndex
        ACCESS      not-accessible
        STATUS      mandatory
        DESCRIPTION
            "Index of this table."
        ::= { invModuleInfoOduEntry 1 }
    
    -- 1.3.6.1.4.1.119.2.3.69.203.513.501.7.3.1.2
    invModuleInfoOduNEAddress OBJECT-TYPE
        SYNTAX      IpAddress
        ACCESS      not-accessible
        STATUS      mandatory
        DESCRIPTION
            "reserved."
        ::= { invModuleInfoOduEntry 2 }
    
    -- 1.3.6.1.4.1.119.2.3.69.203.513.501.7.3.1.3
    invOduCardName OBJECT-TYPE
        SYNTAX      DisplayString
        ACCESS      read-only
        STATUS      mandatory
        DESCRIPTION
            "ODU Name. when the ODU is removed or disconnected, the value
             will be changed to '**'."
        ::= { invModuleInfoOduEntry 3 }
    
    -- 1.3.6.1.4.1.119.2.3.69.203.513.501.7.3.1.4
    invOduCardCodeNo OBJECT-TYPE
        SYNTAX      DisplayString
        ACCESS      read-only
        STATUS      mandatory
        DESCRIPTION
            "ODU Code Name. when the ODU is removed or disconnected, the
             value will be changed to '**'."
        ::= { invModuleInfoOduEntry 4 }
    
    -- 1.3.6.1.4.1.119.2.3.69.203.513.501.7.3.1.5
    invOduCardHardVersion OBJECT-TYPE
        SYNTAX      DisplayString
        ACCESS      read-only
        STATUS      mandatory
        DESCRIPTION
            "ODU Hardware version. when the ODU is removed or disconnected,
             the value will be changed to '**'."
        ::= { invModuleInfoOduEntry 5 }
    
    -- 1.3.6.1.4.1.119.2.3.69.203.513.501.7.3.1.6
    invOduCardSerialNo OBJECT-TYPE
        SYNTAX      DisplayString
        ACCESS      read-only
        STATUS      mandatory
        DESCRIPTION
            "ODU Serial No. when the ODU is removed or disconnected, the
             value will be changed to '**'."
        ::= { invModuleInfoOduEntry 6 }
    
    -- 1.3.6.1.4.1.119.2.3.69.203.513.501.7.3.1.7
    invOduCardManufacturedDate OBJECT-TYPE
        SYNTAX      DisplayString
        ACCESS      read-only
        STATUS      mandatory
        DESCRIPTION
            "ODU Manufactured Date. when the ODU is removed or disconnected,
             the value will be changed to '**'."
        ::= { invModuleInfoOduEntry 7 }
    
    -- 1.3.6.1.4.1.119.2.3.69.203.513.501.7.3.1.8
    invOduCardFirmCurrentVersion OBJECT-TYPE
        SYNTAX      DisplayString
        ACCESS      read-only
        STATUS      mandatory
        DESCRIPTION
            "ODU Firmware information (current). when the ODU is removed or
             disconnected, the value will be changed to '**'."
        ::= { invModuleInfoOduEntry 8 }
    
    -- 1.3.6.1.4.1.119.2.3.69.203.513.501.7.3.1.9
    invOduCardFirmUncurrentVersion OBJECT-TYPE
        SYNTAX      DisplayString
        ACCESS      read-only
        STATUS      mandatory
        DESCRIPTION
            "ODU Firmware information (uncurrent). when the ODU is removed or
             disconnected, the value will be changed to '**'."
        ::= { invModuleInfoOduEntry 9 }
    
    -- 1.3.6.1.4.1.119.2.3.69.203.513.501.7.3.1.10
    invOduProvRangeATPCMax OBJECT-TYPE
        SYNTAX      INTEGER
        ACCESS      read-only
        STATUS      mandatory
        DESCRIPTION
            "ODU Frequency Information - Range ATPC MAX (dbm)"
        ::= { invModuleInfoOduEntry 10 }
    
    -- 1.3.6.1.4.1.119.2.3.69.203.513.501.7.3.1.11
    invOduProvRangeATPCMin OBJECT-TYPE
        SYNTAX      INTEGER
        ACCESS      read-only
        STATUS      mandatory
        DESCRIPTION
            "ODU Frequency Information - Range ATPC MIN (dbm)"
        ::= { invModuleInfoOduEntry 11 }
    
    -- 1.3.6.1.4.1.119.2.3.69.203.513.501.7.3.1.12
    invOduProvRangeMTPCMax OBJECT-TYPE
        SYNTAX      INTEGER
        ACCESS      read-only
        STATUS      mandatory
        DESCRIPTION
            "ODU Frequency Information - Range MTPC MAX (dbm)"
        ::= { invModuleInfoOduEntry 12 }
    
    -- 1.3.6.1.4.1.119.2.3.69.203.513.501.7.3.1.13
    invOduProvRangeMTPCMin OBJECT-TYPE
        SYNTAX      INTEGER
        ACCESS      read-only
        STATUS      mandatory
        DESCRIPTION
            "ODU Frequency Information - Range MTPC MIN (dbm)"
        ::= { invModuleInfoOduEntry 13 }
    
    -- 1.3.6.1.4.1.119.2.3.69.203.513.501.7.3.1.14
    invOduProvRangeRxThresholdMax OBJECT-TYPE
        SYNTAX      INTEGER
        ACCESS      read-only
        STATUS      mandatory
        DESCRIPTION
            "ODU Frequency Information - Range RX Threshold MAX (dbm)"
        ::= { invModuleInfoOduEntry 14 }
    
    -- 1.3.6.1.4.1.119.2.3.69.203.513.501.7.3.1.15
    invOduProvRangeRxThresholdMin OBJECT-TYPE
        SYNTAX      INTEGER
        ACCESS      read-only
        STATUS      mandatory
        DESCRIPTION
            "ODU Frequency Information - Range RX Threshold MIN (dbm)"
        ::= { invModuleInfoOduEntry 15 }
    
    -- 1.3.6.1.4.1.119.2.3.69.203.513.501.7.3.1.16
    invOduProvRangeHysteresisPermit OBJECT-TYPE
        SYNTAX      INTEGER { deny(0), permit(255) }
        ACCESS      read-only
        STATUS      mandatory
        DESCRIPTION
            "ODU Frequency Information - Range Hysteresis Permit"
        ::= { invModuleInfoOduEntry 16 }
    
    -- 1.3.6.1.4.1.119.2.3.69.203.513.501.7.3.1.17
    invOduProvRangeHysteresisMax OBJECT-TYPE
        SYNTAX      INTEGER
        ACCESS      read-only
        STATUS      mandatory
        DESCRIPTION
            "ODU Range Hysteresis MAX (dB)"
        ::= { invModuleInfoOduEntry 17 }
    
    -- 1.3.6.1.4.1.119.2.3.69.203.513.501.7.3.1.18
    invOduProvRangeHysteresisMin OBJECT-TYPE
        SYNTAX      INTEGER
        ACCESS      read-only
        STATUS      mandatory
        DESCRIPTION
            "ODU Range Hysteresis MIN (dB)"
        ::= { invModuleInfoOduEntry 18 }
    
    -- 1.3.6.1.4.1.119.2.3.69.203.513.501.7.3.1.19
    invOduFreqInfoTxStartFrequency OBJECT-TYPE
        SYNTAX      DisplayString
        ACCESS      read-only
        STATUS      mandatory
        DESCRIPTION
            "ODU Frequency Information - TX Start Frequency (MHz)"
        ::= { invModuleInfoOduEntry 19 }
    
    -- 1.3.6.1.4.1.119.2.3.69.203.513.501.7.3.1.20
    invOduFreqInfoTxStopFrequency OBJECT-TYPE
        SYNTAX      DisplayString
        ACCESS      read-only
        STATUS      mandatory
        DESCRIPTION
            "ODU Frequency Information - TX Stop Frequency (MHz)"
        ::= { invModuleInfoOduEntry 20 }
    
    -- 1.3.6.1.4.1.119.2.3.69.203.513.501.7.3.1.21
    invOduFreqInfoRxStartFrequency OBJECT-TYPE
        SYNTAX      DisplayString
        ACCESS      read-only
        STATUS      mandatory
        DESCRIPTION
            "ODU Frequency Information - RX Start Frequency (MHz)"
        ::= { invModuleInfoOduEntry 21 }
    
    -- 1.3.6.1.4.1.119.2.3.69.203.513.501.7.3.1.22
    invOduFreqInfoRxStopFrequency OBJECT-TYPE
        SYNTAX      DisplayString
        ACCESS      read-only
        STATUS      mandatory
        DESCRIPTION
            "ODU Frequency Information - RX Stop Frequency (MHz)"
        ::= { invModuleInfoOduEntry 22 }
    
    -- 1.3.6.1.4.1.119.2.3.69.203.513.501.7.3.1.23
    invOduFreqInfoFrequencyStep OBJECT-TYPE
        SYNTAX      DisplayString
        ACCESS      read-only
        STATUS      mandatory
        DESCRIPTION
            "ODU Frequency Information - Frequency Step (MHz)"
        ::= { invModuleInfoOduEntry 23 }
    
    -- 1.3.6.1.4.1.119.2.3.69.203.513.501.7.3.1.24
    invOduFreqInfoShiftFrequency OBJECT-TYPE
        SYNTAX      DisplayString
        ACCESS      read-only
        STATUS      mandatory
        DESCRIPTION
            "ODU Frequency Information - Shift Frequency (MHz)"
        ::= { invModuleInfoOduEntry 24 }
    
    -- 1.3.6.1.4.1.119.2.3.69.203.513.501.7.3.1.25
    invOduFreqInfoUpperLower OBJECT-TYPE
        SYNTAX      INTEGER { lower(1), upper(2) }
        ACCESS      read-only
        STATUS      mandatory
        DESCRIPTION
            "ODU Frequency Information - Upper / Lower"
        ::= { invModuleInfoOduEntry 25 }
    
    -- 1.3.6.1.4.1.119.2.3.69.203.513.501.7.3.1.26
    invOduFreqInfoTxPhase OBJECT-TYPE
        SYNTAX      INTEGER { forward(1), reverse(2) }
        ACCESS      read-only
        STATUS      mandatory
        DESCRIPTION
            "ODU Frequency Information - TX Phase"
        ::= { invModuleInfoOduEntry 26 }
    
    -- 1.3.6.1.4.1.119.2.3.69.203.513.501.7.3.1.27
    invOduFreqInfoRxPhase OBJECT-TYPE
        SYNTAX      INTEGER { forward(1), reverse(2) }
        ACCESS      read-only
        STATUS      mandatory
        DESCRIPTION
            "ODU Frequency Information - RX Phase"
        ::= { invModuleInfoOduEntry 27 }
    
    -- 1.3.6.1.4.1.119.2.3.69.203.513.501.7.3.1.28
    invOduFreqInfoSubBand OBJECT-TYPE
        SYNTAX      DisplayString
        ACCESS      read-only
        STATUS      mandatory
        DESCRIPTION
            "ODU Frequency Information - Sub Band"
        ::= { invModuleInfoOduEntry 28 }
    
    -- 1.3.6.1.4.1.119.2.3.69.203.513.501.7.3.1.29
    invOduFreqInfoTxRxIndependence OBJECT-TYPE
        SYNTAX      INTEGER { notIndependence(1), independence(2) }
        ACCESS      read-only
        STATUS      mandatory
        DESCRIPTION
            "ODU Frequency Information - TX / RX Independence"
        ::= { invModuleInfoOduEntry 29 }
    
    -- 1.3.6.1.4.1.119.2.3.69.203.513.501.7.3.1.30
    invOduFreqInfoSupportedIpe OBJECT-TYPE
        SYNTAX      INTEGER { notSupported(1), supported(2) }
        ACCESS      read-only
        STATUS      mandatory
        DESCRIPTION
            "ODU Frequency Information - Supported iPASOLINK"
        ::= { invModuleInfoOduEntry 30 }
    
    -- 1.3.6.1.4.1.119.2.3.69.203.513.501.7.3.1.31
    invOduFreqInfoSubBand1 OBJECT-TYPE
        SYNTAX      DisplayString
        ACCESS      read-only
        STATUS      mandatory
        DESCRIPTION
            "ODU Frequency Information - Sub Band 01"
        ::= { invModuleInfoOduEntry 31 }
    
    -- 1.3.6.1.4.1.119.2.3.69.203.513.501.7.3.1.32
    invOduFreqInfoSubBand2 OBJECT-TYPE
        SYNTAX      DisplayString
        ACCESS      read-only
        STATUS      mandatory
        DESCRIPTION
            "ODU Frequency Information - Sub Band 02"
        ::= { invModuleInfoOduEntry 32 }
    
    -- 1.3.6.1.4.1.119.2.3.69.203.513.501.7.3.1.33
    invOduFreqInfoSubBand3 OBJECT-TYPE
        SYNTAX      DisplayString
        ACCESS      read-only
        STATUS      mandatory
        DESCRIPTION
            "ODU Frequency Information - Sub Band 03"
        ::= { invModuleInfoOduEntry 33 }
    
    -- 1.3.6.1.4.1.119.2.3.69.203.513.501.7.3.1.34
    invOduFreqInfoSubBand4 OBJECT-TYPE
        SYNTAX      DisplayString
        ACCESS      read-only
        STATUS      mandatory
        DESCRIPTION
            "ODU Frequency Information - Sub Band 04"
        ::= { invModuleInfoOduEntry 34 }
    
    -- 1.3.6.1.4.1.119.2.3.69.203.513.501.7.3.1.35
    invOduFreqInfoSubBand5 OBJECT-TYPE
        SYNTAX      DisplayString
        ACCESS      read-only
        STATUS      mandatory
        DESCRIPTION
            "ODU Frequency Information - Sub Band 05"
        ::= { invModuleInfoOduEntry 35 }
    
    -- 1.3.6.1.4.1.119.2.3.69.203.513.501.7.3.1.36
    invOduFreqInfoSubBand6 OBJECT-TYPE
        SYNTAX      DisplayString
        ACCESS      read-only
        STATUS      mandatory
        DESCRIPTION
            "ODU Frequency Information - Sub Band 06"
        ::= { invModuleInfoOduEntry 36 }
    
    -- 1.3.6.1.4.1.119.2.3.69.203.513.501.7.3.1.37
    invOduFreqInfoSubBand7 OBJECT-TYPE
        SYNTAX      DisplayString
        ACCESS      read-only
        STATUS      mandatory
        DESCRIPTION
            "ODU Frequency Information - Sub Band 07"
        ::= { invModuleInfoOduEntry 37 }
    
    -- 1.3.6.1.4.1.119.2.3.69.203.513.501.7.3.1.38
    invOduFreqInfoSubBand8 OBJECT-TYPE
        SYNTAX      DisplayString
        ACCESS      read-only
        STATUS      mandatory
        DESCRIPTION
            "ODU Frequency Information - Sub Band 08"
        ::= { invModuleInfoOduEntry 38 }
    
    -- 1.3.6.1.4.1.119.2.3.69.203.513.501.7.3.1.39
    invOduFreqInfoSubBand9 OBJECT-TYPE
        SYNTAX      DisplayString
        ACCESS      read-only
        STATUS      mandatory
        DESCRIPTION
            "ODU Frequency Information - Sub Band 09"
        ::= { invModuleInfoOduEntry 39 }
    
    -- 1.3.6.1.4.1.119.2.3.69.203.513.501.7.3.1.40
    invOduFreqInfoSubBand10 OBJECT-TYPE
        SYNTAX      DisplayString
        ACCESS      read-only
        STATUS      mandatory
        DESCRIPTION
            "ODU Frequency Information - Sub Band 10"
        ::= { invModuleInfoOduEntry 40 }
    
    -- 1.3.6.1.4.1.119.2.3.69.203.513.501.7.4
    invUpdateInfoTable OBJECT-TYPE
        SYNTAX      SEQUENCE OF InvUpdateInfoEntry
        ACCESS      not-accessible
        STATUS      mandatory
        DESCRIPTION
            "Inventory Update Information"
        ::= { inventoryGroup 4 }
    
    -- 1.3.6.1.4.1.119.2.3.69.203.513.501.7.4.1
    invUpdateInfoEntry OBJECT-TYPE
        SYNTAX      InvUpdateInfoEntry
        ACCESS      not-accessible
        STATUS      mandatory
        DESCRIPTION
            ""
        INDEX       { invUpdateInfoNEAddress, invUpdateInfoIndex }
        ::= { invUpdateInfoTable 1 }
    
    InvUpdateInfoEntry ::= SEQUENCE {
        invUpdateInfoIndex      INTEGER,
        invUpdateInfoNEAddress  IpAddress,
        invUpdateInfoSummary    OCTET STRING
    }
    
    -- 1.3.6.1.4.1.119.2.3.69.203.513.501.7.4.1.1
    invUpdateInfoIndex OBJECT-TYPE
        SYNTAX      INTEGER (1)
        ACCESS      not-accessible
        STATUS      mandatory
        DESCRIPTION
            "Index of this table."
        ::= { invUpdateInfoEntry 1 }
    
    -- 1.3.6.1.4.1.119.2.3.69.203.513.501.7.4.1.2
    invUpdateInfoNEAddress OBJECT-TYPE
        SYNTAX      IpAddress
        ACCESS      not-accessible
        STATUS      mandatory
        DESCRIPTION
            "reserved."
        ::= { invUpdateInfoEntry 2 }
    
    -- 1.3.6.1.4.1.119.2.3.69.203.513.501.7.4.1.3
    invUpdateInfoSummary OBJECT-TYPE
        SYNTAX      OCTET STRING (SIZE(12 | 20))
        ACCESS      read-only
        STATUS      mandatory
        DESCRIPTION
            "Inventory Update Information Summary"
        ::= { invUpdateInfoEntry 3 }
    
    -- 1.3.6.1.4.1.119.2.3.69.203.513.501.7.5
    invSfpInfoTable OBJECT-TYPE
        SYNTAX      SEQUENCE OF InvSfpInfoEntry
        ACCESS      not-accessible
        STATUS      mandatory
        DESCRIPTION
            "SFP / XFP Information"
        ::= { inventoryGroup 5 }
    
    -- 1.3.6.1.4.1.119.2.3.69.203.513.501.7.5.1
    invSfpInfoEntry OBJECT-TYPE
        SYNTAX      InvSfpInfoEntry
        ACCESS      not-accessible
        STATUS      mandatory
        DESCRIPTION
            ""
        INDEX       { invSfpInfoNEAddress, invSfpInfoIfIndex }
        ::= { invSfpInfoTable 1 }
    
    InvSfpInfoEntry ::= SEQUENCE {
        invSfpInfoIfIndex           InterfaceIndex,
        invSfpInfoNEAddress         IpAddress,
        invSfpVendorName            DisplayString,
        invSfpVendorPn              DisplayString,
        invSfpVendorVer             DisplayString,
        invSfpVendorSn              DisplayString,
        invSfpType                  DisplayString,
        invSfpManufacturedDate      DisplayString,
        invSfpSupportedWavelength   DisplayString,
        invSfpSupportedLinkLength   DisplayString
    }
    
    -- 1.3.6.1.4.1.119.2.3.69.203.513.501.7.5.1.1
    invSfpInfoIfIndex OBJECT-TYPE
        SYNTAX      InterfaceIndex
        ACCESS      not-accessible
        STATUS      mandatory
        DESCRIPTION
            "Index of this table."
        ::= { invSfpInfoEntry 1 }
    
    -- 1.3.6.1.4.1.119.2.3.69.203.513.501.7.5.1.2
    invSfpInfoNEAddress OBJECT-TYPE
        SYNTAX      IpAddress
        ACCESS      not-accessible
        STATUS      mandatory
        DESCRIPTION
            "reserved."
        ::= { invSfpInfoEntry 2 }
    
    -- 1.3.6.1.4.1.119.2.3.69.203.513.501.7.5.1.3
    invSfpVendorName OBJECT-TYPE
        SYNTAX      DisplayString
        ACCESS      read-only
        STATUS      mandatory
        DESCRIPTION
            "Vendor Name"
        ::= { invSfpInfoEntry 3 }
    
    -- 1.3.6.1.4.1.119.2.3.69.203.513.501.7.5.1.4
    invSfpVendorPn OBJECT-TYPE
        SYNTAX      DisplayString
        ACCESS      read-only
        STATUS      mandatory
        DESCRIPTION
            "Part Number"
        ::= { invSfpInfoEntry 4 }
    
    -- 1.3.6.1.4.1.119.2.3.69.203.513.501.7.5.1.5
    invSfpVendorVer OBJECT-TYPE
        SYNTAX      DisplayString
        ACCESS      read-only
        STATUS      mandatory
        DESCRIPTION
            "Vendor Revision Number"
        ::= { invSfpInfoEntry 5 }
    
    -- 1.3.6.1.4.1.119.2.3.69.203.513.501.7.5.1.6
    invSfpVendorSn OBJECT-TYPE
        SYNTAX      DisplayString
        ACCESS      read-only
        STATUS      mandatory
        DESCRIPTION
            "Vendor Serial Number"
        ::= { invSfpInfoEntry 6 }
    
    -- 1.3.6.1.4.1.119.2.3.69.203.513.501.7.5.1.7
    invSfpType OBJECT-TYPE
        SYNTAX      DisplayString
        ACCESS      read-only
        STATUS      mandatory
        DESCRIPTION
            "SFP Type"
        ::= { invSfpInfoEntry 7 }
    
    -- 1.3.6.1.4.1.119.2.3.69.203.513.501.7.5.1.8
    invSfpManufacturedDate OBJECT-TYPE
        SYNTAX      DisplayString
        ACCESS      read-only
        STATUS      mandatory
        DESCRIPTION
            "SFP Manufactured Date"
        ::= { invSfpInfoEntry 8 }
    
    -- 1.3.6.1.4.1.119.2.3.69.203.513.501.7.5.1.9
    invSfpSupportedWavelength OBJECT-TYPE
        SYNTAX      DisplayString
        ACCESS      read-only
        STATUS      mandatory
        DESCRIPTION
            "Wavelength supported by SFP/XFP/SFP+.
             If the SFP media type is not optical, this object will show the
             value '0'."
        ::= { invSfpInfoEntry 9 }
    
    -- 1.3.6.1.4.1.119.2.3.69.203.513.501.7.5.1.10
    invSfpSupportedLinkLength OBJECT-TYPE
        SYNTAX      DisplayString
        ACCESS      read-only
        STATUS      mandatory
        DESCRIPTION
            "Link length supported by SFP/XFP/SFP+."
        ::= { invSfpInfoEntry 10 }
    
    -- 1.3.6.1.4.1.119.2.3.69.203.513.501.7.6
    invSoftkeyInfoTable OBJECT-TYPE
        SYNTAX      SEQUENCE OF InvSoftkeyInfoEntry
        ACCESS      not-accessible
        STATUS      mandatory
        DESCRIPTION
            "Software Key Information."
        ::= { inventoryGroup 6 }
    
    -- 1.3.6.1.4.1.119.2.3.69.203.513.501.7.6.1
    invSoftkeyInfoEntry OBJECT-TYPE
        SYNTAX      InvSoftkeyInfoEntry
        ACCESS      not-accessible
        STATUS      mandatory
        DESCRIPTION
            ""
        INDEX       { invSoftkeyInfoNEAddress, invSoftkeyInfoIndex }
        ::= { invSoftkeyInfoTable 1 }
    
    InvSoftkeyInfoEntry ::= SEQUENCE {
        invSoftkeyInfoIndex             INTEGER,
        invSoftkeyInfoNEAddress         IpAddress,
        invSoftkeySerialNo              DisplayString,
        invSupportabilityInfoFw         OCTET STRING,
        invSupportabilityInfoKey        OCTET STRING,
        invSupportabilityInfoValid      OCTET STRING,
        invCapa10MaxE1Rst               OCTET STRING,
        invCapa20MaxE1Rst               OCTET STRING,
        invCapa50MaxE1Rst               OCTET STRING,
        invCapa100MaxE1Rst              OCTET STRING,
        invCapa150MaxE1Rst              OCTET STRING,
        invCapa200MaxE1Rst              OCTET STRING,
        invCapa300MaxE1Rst              OCTET STRING,
        invCapa400MaxE1Rst              OCTET STRING,
        invSoftkeyEquipmentSerialNo     DisplayString
    }
    
    -- 1.3.6.1.4.1.119.2.3.69.203.513.501.7.6.1.1
    invSoftkeyInfoIndex OBJECT-TYPE
        SYNTAX      INTEGER (1)
        ACCESS      not-accessible
        STATUS      mandatory
        DESCRIPTION
            "Index of this table."
        ::= { invSoftkeyInfoEntry 1 }
    
    -- 1.3.6.1.4.1.119.2.3.69.203.513.501.7.6.1.2
    invSoftkeyInfoNEAddress OBJECT-TYPE
        SYNTAX      IpAddress
        ACCESS      not-accessible
        STATUS      mandatory
        DESCRIPTION
            "reserved"
        ::= { invSoftkeyInfoEntry 2 }
    
    -- 1.3.6.1.4.1.119.2.3.69.203.513.501.7.6.1.3
    invSoftkeySerialNo OBJECT-TYPE
        SYNTAX      DisplayString
        ACCESS      read-only
        STATUS      mandatory
        DESCRIPTION
            "Software Key Serial No."
        ::= { invSoftkeyInfoEntry 3 }
    
    -- 1.3.6.1.4.1.119.2.3.69.203.513.501.7.6.1.4
    invSupportabilityInfoFw OBJECT-TYPE
        SYNTAX      OCTET STRING (SIZE(32 | 40 | 52 | 60 | 68))
        ACCESS      read-only
        STATUS      mandatory
        DESCRIPTION
            "Supportability (Firmware)"
        ::= { invSoftkeyInfoEntry 4 }
    
    -- 1.3.6.1.4.1.119.2.3.69.203.513.501.7.6.1.5
    invSupportabilityInfoKey OBJECT-TYPE
        SYNTAX      OCTET STRING (SIZE(32 | 40 | 52 | 60 | 68))
        ACCESS      read-only
        STATUS      mandatory
        DESCRIPTION
            "Supportability (Software Key)"
        ::= { invSoftkeyInfoEntry 5 }
    
    -- 1.3.6.1.4.1.119.2.3.69.203.513.501.7.6.1.6
    invSupportabilityInfoValid OBJECT-TYPE
        SYNTAX      OCTET STRING (SIZE(32 | 40 | 52 | 60 | 68))
        ACCESS      read-only
        STATUS      mandatory
        DESCRIPTION
            "Supportability (Current)"
        ::= { invSoftkeyInfoEntry 6 }
    
    -- 1.3.6.1.4.1.119.2.3.69.203.513.501.7.6.1.7
    invCapa10MaxE1Rst OBJECT-TYPE
        SYNTAX      OCTET STRING (SIZE(160 | 192))
        ACCESS      read-only
        STATUS      mandatory
        DESCRIPTION
            "Maximum Available E1/RST Connections for 10M Capacity."
        ::= { invSoftkeyInfoEntry 7 }
    
    -- 1.3.6.1.4.1.119.2.3.69.203.513.501.7.6.1.8
    invCapa20MaxE1Rst OBJECT-TYPE
        SYNTAX      OCTET STRING (SIZE(160 | 192))
        ACCESS      read-only
        STATUS      mandatory
        DESCRIPTION
            "Maximum Available E1/RST Connections for 20M Capacity."
        ::= { invSoftkeyInfoEntry 8 }
    
    -- 1.3.6.1.4.1.119.2.3.69.203.513.501.7.6.1.9
    invCapa50MaxE1Rst OBJECT-TYPE
        SYNTAX      OCTET STRING (SIZE(160 | 192))
        ACCESS      read-only
        STATUS      mandatory
        DESCRIPTION
            "Maximum Available E1/RST Connections for 50M Capacity."
        ::= { invSoftkeyInfoEntry 9 }
    
    -- 1.3.6.1.4.1.119.2.3.69.203.513.501.7.6.1.10
    invCapa100MaxE1Rst OBJECT-TYPE
        SYNTAX      OCTET STRING (SIZE(160 | 192))
        ACCESS      read-only
        STATUS      mandatory
        DESCRIPTION
            "Maximum Available E1/RST Connections for 100M Capacity."
        ::= { invSoftkeyInfoEntry 10 }
    
    -- 1.3.6.1.4.1.119.2.3.69.203.513.501.7.6.1.11
    invCapa150MaxE1Rst OBJECT-TYPE
        SYNTAX      OCTET STRING (SIZE(160 | 192))
        ACCESS      read-only
        STATUS      mandatory
        DESCRIPTION
            "Maximum Available E1/RST Connections for 150M Capacity."
        ::= { invSoftkeyInfoEntry 11 }
    
    -- 1.3.6.1.4.1.119.2.3.69.203.513.501.7.6.1.12
    invCapa200MaxE1Rst OBJECT-TYPE
        SYNTAX      OCTET STRING (SIZE(160 | 192))
        ACCESS      read-only
        STATUS      mandatory
        DESCRIPTION
            "Maximum Available E1/RST Connections for 200M Capacity."
        ::= { invSoftkeyInfoEntry 12 }
    
    -- 1.3.6.1.4.1.119.2.3.69.203.513.501.7.6.1.13
    invCapa300MaxE1Rst OBJECT-TYPE
        SYNTAX      OCTET STRING (SIZE(160 | 192))
        ACCESS      read-only
        STATUS      mandatory
        DESCRIPTION
            "Maximum Available E1/RST Connections for 300M Capacity."
        ::= { invSoftkeyInfoEntry 13 }
    
    -- 1.3.6.1.4.1.119.2.3.69.203.513.501.7.6.1.14
    invCapa400MaxE1Rst OBJECT-TYPE
        SYNTAX      OCTET STRING (SIZE(160 | 192))
        ACCESS      read-only
        STATUS      mandatory
        DESCRIPTION
            "Maximum Available E1/RST Connections for 400M Capacity."
        ::= { invSoftkeyInfoEntry 14 }
    
    -- 1.3.6.1.4.1.119.2.3.69.203.513.501.7.6.1.15
    invSoftkeyEquipmentSerialNo OBJECT-TYPE
        SYNTAX      DisplayString
        ACCESS      read-only
        STATUS      obsolete
        DESCRIPTION
            "Equipment Serial Number."
        ::= { invSoftkeyInfoEntry 15 }
    
    -- 1.3.6.1.4.1.119.2.3.69.203.513.501.7.8
    invMacAddressInfoTable OBJECT-TYPE
        SYNTAX      SEQUENCE OF InvMacAddressInfoEntry
        ACCESS      not-accessible
        STATUS      mandatory
        DESCRIPTION
            "Equipment Inventory Information - Mac Address Information"
        ::= { inventoryGroup 8 }
    
    -- 1.3.6.1.4.1.119.2.3.69.203.513.501.7.8.1
    invMacAddressInfoEntry OBJECT-TYPE
        SYNTAX      InvMacAddressInfoEntry
        ACCESS      not-accessible
        STATUS      mandatory
        DESCRIPTION
            ""
        INDEX       { invMacAddressInfoNEAddress, invMacAddressInfoIfIndex }
        ::= { invMacAddressInfoTable 1 }
    
    InvMacAddressInfoEntry ::= SEQUENCE {
        invMacAddressInfoIfIndex    InterfaceIndex,
        invMacAddressInfoNEAddress  IpAddress,
        invMacAddress               MacAddress
    }
    
    -- 1.3.6.1.4.1.119.2.3.69.203.513.501.7.8.1.1
    invMacAddressInfoIfIndex OBJECT-TYPE
        SYNTAX      InterfaceIndex
        ACCESS      not-accessible
        STATUS      mandatory
        DESCRIPTION
            "Index of this table."
        ::= { invMacAddressInfoEntry 1 }
    
    -- 1.3.6.1.4.1.119.2.3.69.203.513.501.7.8.1.2
    invMacAddressInfoNEAddress OBJECT-TYPE
        SYNTAX      IpAddress
        ACCESS      not-accessible
        STATUS      mandatory
        DESCRIPTION
            "reserved"
        ::= { invMacAddressInfoEntry 2 }
    
    -- 1.3.6.1.4.1.119.2.3.69.203.513.501.7.8.1.3
    invMacAddress OBJECT-TYPE
        SYNTAX      MacAddress
        ACCESS      read-only
        STATUS      mandatory
        DESCRIPTION
            "Mac Address which assigned to that port."
        ::= { invMacAddressInfoEntry 3 }
    
    -- 1.3.6.1.4.1.119.2.3.69.203.513.501.7.9
    invModemParamInfoTable OBJECT-TYPE
        SYNTAX      SEQUENCE OF InvModemParamInfoEntry
        ACCESS      not-accessible
        STATUS      mandatory
        DESCRIPTION
            "Equipment Inventory Information (IDU) - MODEM Parameter"
        ::= { inventoryGroup 9 }
    
    -- 1.3.6.1.4.1.119.2.3.69.203.513.501.7.9.1
    invModemParamInfoEntry OBJECT-TYPE
        SYNTAX      InvModemParamInfoEntry
        ACCESS      not-accessible
        STATUS      mandatory
        DESCRIPTION
            ""
        INDEX       { invModemParamInfoNEAddress, invModemParamInfoIfIndex }
        ::= { invModemParamInfoTable 1 }
    
    InvModemParamInfoEntry ::= SEQUENCE {
        invModemParamInfoIfIndex    InterfaceIndex,
        invModemParamInfoNEAddress  IpAddress,
        invModemParamVersion        DisplayString
    }
    
    -- 1.3.6.1.4.1.119.2.3.69.203.513.501.7.9.1.1
    invModemParamInfoIfIndex OBJECT-TYPE
        SYNTAX      InterfaceIndex
        ACCESS      not-accessible
        STATUS      mandatory
        DESCRIPTION
            "Index of this table."
        ::= { invModemParamInfoEntry 1 }
    
    -- 1.3.6.1.4.1.119.2.3.69.203.513.501.7.9.1.2
    invModemParamInfoNEAddress OBJECT-TYPE
        SYNTAX      IpAddress
        ACCESS      not-accessible
        STATUS      mandatory
        DESCRIPTION
            "reserved."
        ::= { invModemParamInfoEntry 2 }
    
    -- 1.3.6.1.4.1.119.2.3.69.203.513.501.7.9.1.3
    invModemParamVersion OBJECT-TYPE
        SYNTAX      DisplayString
        ACCESS      read-only
        STATUS      mandatory
        DESCRIPTION
            "Parameter Information
             MIB format of invModemParamVersion is xx.yy."
        ::= { invModemParamInfoEntry 3 }
    
    -- 1.3.6.1.4.1.119.2.3.69.203.513.501.7.10
    invChassisInfoTable OBJECT-TYPE
        SYNTAX      SEQUENCE OF InvChassisInfoEntry
        ACCESS      not-accessible
        STATUS      mandatory
        DESCRIPTION
            "Equipment Inventory Information (IDU) - Chassis"
        ::= { inventoryGroup 10 }
    
    -- 1.3.6.1.4.1.119.2.3.69.203.513.501.7.10.1
    invChassisInfoEntry OBJECT-TYPE
        SYNTAX      InvChassisInfoEntry
        ACCESS      not-accessible
        STATUS      mandatory
        DESCRIPTION
            ""
        INDEX       { invChassisInfoNEAddress, invChassisInfoIndex }
        ::= { invChassisInfoTable 1 }
    
    InvChassisInfoEntry ::= SEQUENCE {
        invChassisInfoIndex         INTEGER,
        invChassisInfoNEAddress     IpAddress,
        invChassisName              DisplayString,
        invChassisCodeNo            DisplayString,
        invChassisSerialNo          DisplayString,
        invChassisManufacturedDate  DisplayString,
        invChassisFirmVersion       DisplayString,
        invChassisHardVersion       DisplayString
    }
    
    -- 1.3.6.1.4.1.119.2.3.69.203.513.501.7.10.1.1
    invChassisInfoIndex OBJECT-TYPE
        SYNTAX      INTEGER (1)
        ACCESS      not-accessible
        STATUS      mandatory
        DESCRIPTION
            "Index of this table."
        ::= { invChassisInfoEntry 1 }
    
    -- 1.3.6.1.4.1.119.2.3.69.203.513.501.7.10.1.2
    invChassisInfoNEAddress OBJECT-TYPE
        SYNTAX      IpAddress
        ACCESS      not-accessible
        STATUS      mandatory
        DESCRIPTION
            "reserved."
        ::= { invChassisInfoEntry 2 }
    
    -- 1.3.6.1.4.1.119.2.3.69.203.513.501.7.10.1.3
    invChassisName OBJECT-TYPE
        SYNTAX      DisplayString
        ACCESS      read-only
        STATUS      mandatory
        DESCRIPTION
            "Name"
        ::= { invChassisInfoEntry 3 }
    
    -- 1.3.6.1.4.1.119.2.3.69.203.513.501.7.10.1.4
    invChassisCodeNo OBJECT-TYPE
        SYNTAX      DisplayString
        ACCESS      read-only
        STATUS      mandatory
        DESCRIPTION
            "Code No."
        ::= { invChassisInfoEntry 4 }
    
    -- 1.3.6.1.4.1.119.2.3.69.203.513.501.7.10.1.5
    invChassisSerialNo OBJECT-TYPE
        SYNTAX      DisplayString (SIZE(1..8))
        ACCESS      read-only
        STATUS      mandatory
        DESCRIPTION
            "Serial No.
             Note: For VR 2, this object cannot be modified, acting as
             read-only object."
        ::= { invChassisInfoEntry 5 }
    
    -- 1.3.6.1.4.1.119.2.3.69.203.513.501.7.10.1.6
    invChassisManufacturedDate OBJECT-TYPE
        SYNTAX      DisplayString (SIZE(1..7))
        ACCESS      read-only
        STATUS      mandatory
        DESCRIPTION
            "Manufactured Date
             Note: For VR 2, this object cannot be modified, acting as
             read-only object."
        ::= { invChassisInfoEntry 6 }
    
    -- 1.3.6.1.4.1.119.2.3.69.203.513.501.7.10.1.7
    invChassisFirmVersion OBJECT-TYPE
        SYNTAX      DisplayString
        ACCESS      read-only
        STATUS      mandatory
        DESCRIPTION
            "Firmware Version"
        ::= { invChassisInfoEntry 7 }
    
    -- 1.3.6.1.4.1.119.2.3.69.203.513.501.7.10.1.8
    invChassisHardVersion OBJECT-TYPE
        SYNTAX      DisplayString
        ACCESS      read-only
        STATUS      mandatory
        DESCRIPTION
            "Hardware Version"
        ::= { invChassisInfoEntry 8 }
    
    -- 1.3.6.1.4.1.119.2.3.69.203.513.501.7.12
    invMainOptionInfoTable OBJECT-TYPE
        SYNTAX      SEQUENCE OF InvMainOptionInfoEntry
        ACCESS      not-accessible
        STATUS      mandatory
        DESCRIPTION
            "Supportability information for the optional functions."
        ::= { inventoryGroup 12 }
    
    -- 1.3.6.1.4.1.119.2.3.69.203.513.501.7.12.1
    invMainOptionInfoEntry OBJECT-TYPE
        SYNTAX      InvMainOptionInfoEntry
        ACCESS      not-accessible
        STATUS      mandatory
        DESCRIPTION
            ""
        INDEX       { invMainOptionInfoNEAddress, invMainOptionInfoIndex }
        ::= { invMainOptionInfoTable 1 }
    
    InvMainOptionInfoEntry ::= SEQUENCE {
        invMainOptionInfoIndex                  INTEGER,
        invMainOptionInfoNEAddress              IpAddress,
        invSupportabilityMainOptionInfoHw       OCTET STRING,
        invSupportabilityMainOptionInfoFw       OCTET STRING,
        invSupportabilityMainOptionInfoValid    OCTET STRING
    }
    
    -- 1.3.6.1.4.1.119.2.3.69.203.513.501.7.12.1.1
    invMainOptionInfoIndex OBJECT-TYPE
        SYNTAX      INTEGER (1)
        ACCESS      not-accessible
        STATUS      mandatory
        DESCRIPTION
            "Index of this table."
        ::= { invMainOptionInfoEntry 1 }
    
    -- 1.3.6.1.4.1.119.2.3.69.203.513.501.7.12.1.2
    invMainOptionInfoNEAddress OBJECT-TYPE
        SYNTAX      IpAddress
        ACCESS      not-accessible
        STATUS      mandatory
        DESCRIPTION
            "reserved"
        ::= { invMainOptionInfoEntry 2 }
    
    -- 1.3.6.1.4.1.119.2.3.69.203.513.501.7.12.1.3
    invSupportabilityMainOptionInfoHw OBJECT-TYPE
        SYNTAX      OCTET STRING (SIZE(16))
        ACCESS      read-only
        STATUS      mandatory
        DESCRIPTION
            "Supportability (Hardware)"
        ::= { invMainOptionInfoEntry 3 }
    
    -- 1.3.6.1.4.1.119.2.3.69.203.513.501.7.12.1.4
    invSupportabilityMainOptionInfoFw OBJECT-TYPE
        SYNTAX      OCTET STRING (SIZE(16))
        ACCESS      read-only
        STATUS      mandatory
        DESCRIPTION
            "Supportability (Firmware)"
        ::= { invMainOptionInfoEntry 4 }
    
    -- 1.3.6.1.4.1.119.2.3.69.203.513.501.7.12.1.5
    invSupportabilityMainOptionInfoValid OBJECT-TYPE
        SYNTAX      OCTET STRING (SIZE(16))
        ACCESS      read-only
        STATUS      mandatory
        DESCRIPTION
            "Supportability (Current)"
        ::= { invMainOptionInfoEntry 5 }
    
    -- 1.3.6.1.4.1.119.2.3.69.203.513.501.7.15
    invControllerInfoTable OBJECT-TYPE
        SYNTAX      SEQUENCE OF InvControllerInfoEntry
        ACCESS      not-accessible
        STATUS      mandatory
        DESCRIPTION
            "Equipment Inventory Information (IDU) - Controller"
        ::= { inventoryGroup 15 }
    
    -- 1.3.6.1.4.1.119.2.3.69.203.513.501.7.15.1
    invControllerInfoEntry OBJECT-TYPE
        SYNTAX      InvControllerInfoEntry
        ACCESS      not-accessible
        STATUS      mandatory
        DESCRIPTION
            ""
        INDEX       { invControllerInfoNEAddress, invControllerInfoIndex }
        ::= { invControllerInfoTable 1 }
    
    InvControllerInfoEntry ::= SEQUENCE {
        invControllerInfoIndex      INTEGER,
        invControllerInfoNEAddress  IpAddress,
        invControllerName           DisplayString,
        invControllerCodeNo         DisplayString,
        invControllerVersion        DisplayString
    }
    
    -- 1.3.6.1.4.1.119.2.3.69.203.513.501.7.15.1.1
    invControllerInfoIndex OBJECT-TYPE
        SYNTAX      INTEGER
        ACCESS      not-accessible
        STATUS      mandatory
        DESCRIPTION
            "Index of this table."
        ::= { invControllerInfoEntry 1 }
    
    -- 1.3.6.1.4.1.119.2.3.69.203.513.501.7.15.1.2
    invControllerInfoNEAddress OBJECT-TYPE
        SYNTAX      IpAddress
        ACCESS      not-accessible
        STATUS      mandatory
        DESCRIPTION
            "reserved."
        ::= { invControllerInfoEntry 2 }
    
    -- 1.3.6.1.4.1.119.2.3.69.203.513.501.7.15.1.3
    invControllerName OBJECT-TYPE
        SYNTAX      DisplayString
        ACCESS      read-only
        STATUS      mandatory
        DESCRIPTION
            "Controller Name. when the card is removed or the card doesn't
             have controller, the value will be changed to '**'."
        ::= { invControllerInfoEntry 3 }
    
    -- 1.3.6.1.4.1.119.2.3.69.203.513.501.7.15.1.4
    invControllerCodeNo OBJECT-TYPE
        SYNTAX      DisplayString
        ACCESS      read-only
        STATUS      mandatory
        DESCRIPTION
            "Controller Code No. when the card is removed or the card doesn't
             have controller, the value will be changed to '**'."
        ::= { invControllerInfoEntry 4 }
    
    -- 1.3.6.1.4.1.119.2.3.69.203.513.501.7.15.1.5
    invControllerVersion OBJECT-TYPE
        SYNTAX      DisplayString
        ACCESS      read-only
        STATUS      mandatory
        DESCRIPTION
            "Controller Version. when the card is removed or the card doesn't
             have controller, the value will be changed to '**'.
             MIB format of invControllerVersion is xx.yy."
        ::= { invControllerInfoEntry 5 }
    
    -- 1.3.6.1.4.1.119.2.3.69.203.513.501.8
    meteringGroup OBJECT IDENTIFIER
        ::= { pasoNeoIpe-common 8 }
    
    -- 1.3.6.1.4.1.119.2.3.69.203.513.501.8.1
    meteringTable OBJECT-TYPE
        SYNTAX      SEQUENCE OF MeteringEntry
        ACCESS      not-accessible
        STATUS      mandatory
        DESCRIPTION
            "MODEM TX / RX Metering Table."
        ::= { meteringGroup 1 }
    
    -- 1.3.6.1.4.1.119.2.3.69.203.513.501.8.1.1
    meteringEntry OBJECT-TYPE
        SYNTAX      MeteringEntry
        ACCESS      not-accessible
        STATUS      mandatory
        DESCRIPTION
            ""
        INDEX       { meteringNEAddress, meteringIfIndex }
        ::= { meteringTable 1 }
    
    MeteringEntry ::= SEQUENCE {
        meteringIfIndex             InterfaceIndex,
        meteringNEAddress           IpAddress,
        metSysTxPowerStatus         ValidInvalidValue,
        metSysTxPowerValue          DisplayString,
        metSysRxLevelStatus         ValidInvalidValue,
        metSysRxLevelValue          DisplayString,
        metSysPSVoltageStatus       ValidInvalidValue,
        metSysPSVoltageValue        DisplayString,
        metSysTempODUStatus         ValidInvalidValue,
        metSysTempODUValue          DisplayString,
        metSysTempIDUStatus         ValidInvalidValue,
        metSysTempIDUValue          DisplayString,
        metSysBitErrorRateStatus    INTEGER,
        metSysBitErrorRateValue     DisplayString,
        metSysXpdStatus             ValidInvalidValue,
        metSysXpdValue              DisplayString
    }
    
    -- 1.3.6.1.4.1.119.2.3.69.203.513.501.8.1.1.1
    meteringIfIndex OBJECT-TYPE
        SYNTAX      InterfaceIndex
        ACCESS      not-accessible
        STATUS      mandatory
        DESCRIPTION
            "index of this table."
        ::= { meteringEntry 1 }
    
    -- 1.3.6.1.4.1.119.2.3.69.203.513.501.8.1.1.2
    meteringNEAddress OBJECT-TYPE
        SYNTAX      IpAddress
        ACCESS      not-accessible
        STATUS      mandatory
        DESCRIPTION
            "reserved."
        ::= { meteringEntry 2 }
    
    -- 1.3.6.1.4.1.119.2.3.69.203.513.501.8.1.1.3
    metSysTxPowerStatus OBJECT-TYPE
        SYNTAX      ValidInvalidValue
        ACCESS      read-only
        STATUS      mandatory
        DESCRIPTION
            "MODEM TX Power Status."
        ::= { meteringEntry 3 }
    
    -- 1.3.6.1.4.1.119.2.3.69.203.513.501.8.1.1.4
    metSysTxPowerValue OBJECT-TYPE
        SYNTAX      DisplayString
        ACCESS      read-only
        STATUS      mandatory
        DESCRIPTION
            "MODEM TX Power"
        ::= { meteringEntry 4 }
    
    -- 1.3.6.1.4.1.119.2.3.69.203.513.501.8.1.1.5
    metSysRxLevelStatus OBJECT-TYPE
        SYNTAX      ValidInvalidValue
        ACCESS      read-only
        STATUS      mandatory
        DESCRIPTION
            "MODEM RX Power Status"
        ::= { meteringEntry 5 }
    
    -- 1.3.6.1.4.1.119.2.3.69.203.513.501.8.1.1.6
    metSysRxLevelValue OBJECT-TYPE
        SYNTAX      DisplayString
        ACCESS      read-only
        STATUS      mandatory
        DESCRIPTION
            "MODEM RX Power"
        ::= { meteringEntry 6 }
    
    -- 1.3.6.1.4.1.119.2.3.69.203.513.501.8.1.1.7
    metSysPSVoltageStatus OBJECT-TYPE
        SYNTAX      ValidInvalidValue
        ACCESS      read-only
        STATUS      mandatory
        DESCRIPTION
            "MODEM ODU Power Supply Status"
        ::= { meteringEntry 7 }
    
    -- 1.3.6.1.4.1.119.2.3.69.203.513.501.8.1.1.8
    metSysPSVoltageValue OBJECT-TYPE
        SYNTAX      DisplayString
        ACCESS      read-only
        STATUS      mandatory
        DESCRIPTION
            "MODEM ODU Power Supply"
        ::= { meteringEntry 8 }
    
    -- 1.3.6.1.4.1.119.2.3.69.203.513.501.8.1.1.9
    metSysTempODUStatus OBJECT-TYPE
        SYNTAX      ValidInvalidValue
        ACCESS      read-only
        STATUS      mandatory
        DESCRIPTION
            "MODEM ODU Temperature Status"
        ::= { meteringEntry 9 }
    
    -- 1.3.6.1.4.1.119.2.3.69.203.513.501.8.1.1.10
    metSysTempODUValue OBJECT-TYPE
        SYNTAX      DisplayString
        ACCESS      read-only
        STATUS      mandatory
        DESCRIPTION
            "MODEM ODU Temperature"
        ::= { meteringEntry 10 }
    
    -- 1.3.6.1.4.1.119.2.3.69.203.513.501.8.1.1.11
    metSysTempIDUStatus OBJECT-TYPE
        SYNTAX      ValidInvalidValue
        ACCESS      read-only
        STATUS      mandatory
        DESCRIPTION
            "IDU Temperature Status"
        ::= { meteringEntry 11 }
    
    -- 1.3.6.1.4.1.119.2.3.69.203.513.501.8.1.1.12
    metSysTempIDUValue OBJECT-TYPE
        SYNTAX      DisplayString
        ACCESS      read-only
        STATUS      mandatory
        DESCRIPTION
            "IDU Temperature"
        ::= { meteringEntry 12 }
    
    -- 1.3.6.1.4.1.119.2.3.69.203.513.501.8.1.1.13
    metSysBitErrorRateStatus OBJECT-TYPE
        SYNTAX      INTEGER
        ACCESS      read-only
        STATUS      mandatory
        DESCRIPTION
            "MODEM BER Status"
        ::= { meteringEntry 13 }
    
    -- 1.3.6.1.4.1.119.2.3.69.203.513.501.8.1.1.14
    metSysBitErrorRateValue OBJECT-TYPE
        SYNTAX      DisplayString
        ACCESS      read-only
        STATUS      mandatory
        DESCRIPTION
            "MODEM BER"
        ::= { meteringEntry 14 }
    
    -- 1.3.6.1.4.1.119.2.3.69.203.513.501.8.1.1.19
    metSysXpdStatus OBJECT-TYPE
        SYNTAX      ValidInvalidValue
        ACCESS      read-only
        STATUS      mandatory
        DESCRIPTION
            "XPD Status"
        ::= { meteringEntry 19 }
    
    -- 1.3.6.1.4.1.119.2.3.69.203.513.501.8.1.1.20
    metSysXpdValue OBJECT-TYPE
        SYNTAX      DisplayString
        ACCESS      read-only
        STATUS      mandatory
        DESCRIPTION
            "XPD. The unit of this value is dB."
        ::= { meteringEntry 20 }
    
    -- 1.3.6.1.4.1.119.2.3.69.203.513.501.8.2
    meteringSfpTable OBJECT-TYPE
        SYNTAX      SEQUENCE OF MeteringSfpEntry
        ACCESS      not-accessible
        STATUS      mandatory
        DESCRIPTION
            "SFP Metering Table"
        ::= { meteringGroup 2 }
    
    -- 1.3.6.1.4.1.119.2.3.69.203.513.501.8.2.1
    meteringSfpEntry OBJECT-TYPE
        SYNTAX      MeteringSfpEntry
        ACCESS      not-accessible
        STATUS      mandatory
        DESCRIPTION
            ""
        INDEX       { meteringSfpNEAddress, meteringSfpIfIndex }
        ::= { meteringSfpTable 1 }
    
    MeteringSfpEntry ::= SEQUENCE {
        meteringSfpIfIndex          InterfaceIndex,
        meteringSfpNEAddress        IpAddress,
        meteringSfpTxPower          DisplayString,
        meteringSfpTxPowerStatus    ValidInvalidValue,
        meteringSfpRxPower          DisplayString,
        meteringSfpRxPowerStatus    ValidInvalidValue
    }
    
    -- 1.3.6.1.4.1.119.2.3.69.203.513.501.8.2.1.1
    meteringSfpIfIndex OBJECT-TYPE
        SYNTAX      InterfaceIndex
        ACCESS      not-accessible
        STATUS      mandatory
        DESCRIPTION
            "Index of this table."
        ::= { meteringSfpEntry 1 }
    
    -- 1.3.6.1.4.1.119.2.3.69.203.513.501.8.2.1.2
    meteringSfpNEAddress OBJECT-TYPE
        SYNTAX      IpAddress
        ACCESS      not-accessible
        STATUS      mandatory
        DESCRIPTION
            "reserved."
        ::= { meteringSfpEntry 2 }
    
    -- 1.3.6.1.4.1.119.2.3.69.203.513.501.8.2.1.3
    meteringSfpTxPower OBJECT-TYPE
        SYNTAX      DisplayString
        ACCESS      read-only
        STATUS      mandatory
        DESCRIPTION
            "SFP TX Power [in dBm]"
        ::= { meteringSfpEntry 3 }
    
    -- 1.3.6.1.4.1.119.2.3.69.203.513.501.8.2.1.4
    meteringSfpTxPowerStatus OBJECT-TYPE
        SYNTAX      ValidInvalidValue
        ACCESS      read-only
        STATUS      mandatory
        DESCRIPTION
            "SFP TX Power Status"
        ::= { meteringSfpEntry 4 }
    
    -- 1.3.6.1.4.1.119.2.3.69.203.513.501.8.2.1.5
    meteringSfpRxPower OBJECT-TYPE
        SYNTAX      DisplayString
        ACCESS      read-only
        STATUS      mandatory
        DESCRIPTION
            "SFP RX Power [in dBm]"
        ::= { meteringSfpEntry 5 }
    
    -- 1.3.6.1.4.1.119.2.3.69.203.513.501.8.2.1.6
    meteringSfpRxPowerStatus OBJECT-TYPE
        SYNTAX      ValidInvalidValue
        ACCESS      read-only
        STATUS      mandatory
        DESCRIPTION
            "SFP RX Power Status"
        ::= { meteringSfpEntry 6 }
    
    -- 1.3.6.1.4.1.119.2.3.69.203.513.501.8.3
    meteringFanTable OBJECT-TYPE
        SYNTAX      SEQUENCE OF MeteringFanEntry
        ACCESS      not-accessible
        STATUS      mandatory
        DESCRIPTION
            "FAN Metering Table."
        ::= { meteringGroup 3 }
    
    -- 1.3.6.1.4.1.119.2.3.69.203.513.501.8.3.1
    meteringFanEntry OBJECT-TYPE
        SYNTAX      MeteringFanEntry
        ACCESS      not-accessible
        STATUS      mandatory
        DESCRIPTION
            ""
        INDEX       { meteringFanNEAddress, meteringFanSlotIndex }
        ::= { meteringFanTable 1 }
    
    MeteringFanEntry ::= SEQUENCE {
        meteringFanSlotIndex        INTEGER,
        meteringFanNEAddress        IpAddress,
        meteringFanSpeed1           DisplayString,
        meteringFanSpeed1Status     ValidInvalidValue,
        meteringFanSpeed2           DisplayString,
        meteringFanSpeed2Status     ValidInvalidValue,
        meteringFanSpeed3           DisplayString,
        meteringFanSpeed3Status     ValidInvalidValue
    }
    
    -- 1.3.6.1.4.1.119.2.3.69.203.513.501.8.3.1.1
    meteringFanSlotIndex OBJECT-TYPE
        SYNTAX      INTEGER (8 | 22..23)
        ACCESS      not-accessible
        STATUS      mandatory
        DESCRIPTION
            "Index of this table. value range: 8 (400/400A), 22 (VR 4), 22-23
             (1000/VR 10)"
        ::= { meteringFanEntry 1 }
    
    -- 1.3.6.1.4.1.119.2.3.69.203.513.501.8.3.1.2
    meteringFanNEAddress OBJECT-TYPE
        SYNTAX      IpAddress
        ACCESS      not-accessible
        STATUS      mandatory
        DESCRIPTION
            "reserved."
        ::= { meteringFanEntry 2 }
    
    -- 1.3.6.1.4.1.119.2.3.69.203.513.501.8.3.1.3
    meteringFanSpeed1 OBJECT-TYPE
        SYNTAX      DisplayString
        ACCESS      read-only
        STATUS      mandatory
        DESCRIPTION
            "FAN1 Rotation Speed"
        ::= { meteringFanEntry 3 }
    
    -- 1.3.6.1.4.1.119.2.3.69.203.513.501.8.3.1.4
    meteringFanSpeed1Status OBJECT-TYPE
        SYNTAX      ValidInvalidValue
        ACCESS      read-only
        STATUS      mandatory
        DESCRIPTION
            "FAN1 Rotation Speed Status"
        ::= { meteringFanEntry 4 }
    
    -- 1.3.6.1.4.1.119.2.3.69.203.513.501.8.3.1.5
    meteringFanSpeed2 OBJECT-TYPE
        SYNTAX      DisplayString
        ACCESS      read-only
        STATUS      mandatory
        DESCRIPTION
            "FAN2 Rotation Speed"
        ::= { meteringFanEntry 5 }
    
    -- 1.3.6.1.4.1.119.2.3.69.203.513.501.8.3.1.6
    meteringFanSpeed2Status OBJECT-TYPE
        SYNTAX      ValidInvalidValue
        ACCESS      read-only
        STATUS      mandatory
        DESCRIPTION
            "FAN2 Rotation Speed Status"
        ::= { meteringFanEntry 6 }
    
    -- 1.3.6.1.4.1.119.2.3.69.203.513.501.8.3.1.7
    meteringFanSpeed3 OBJECT-TYPE
        SYNTAX      DisplayString
        ACCESS      read-only
        STATUS      mandatory
        DESCRIPTION
            "FAN3 Rotation Speed"
        ::= { meteringFanEntry 7 }
    
    -- 1.3.6.1.4.1.119.2.3.69.203.513.501.8.3.1.8
    meteringFanSpeed3Status OBJECT-TYPE
        SYNTAX      ValidInvalidValue
        ACCESS      read-only
        STATUS      mandatory
        DESCRIPTION
            "FAN3 Rotation Speed Status"
        ::= { meteringFanEntry 8 }
    
    -- 1.3.6.1.4.1.119.2.3.69.203.513.501.8.4
    meteringStm1PortSfpTable OBJECT-TYPE
        SYNTAX      SEQUENCE OF MeteringStm1PortSfpEntry
        ACCESS      not-accessible
        STATUS      mandatory
        DESCRIPTION
            "STM1 Port SFP Metering Table"
        ::= { meteringGroup 4 }
    
    -- 1.3.6.1.4.1.119.2.3.69.203.513.501.8.4.1
    meteringStm1PortSfpEntry OBJECT-TYPE
        SYNTAX      MeteringStm1PortSfpEntry
        ACCESS      not-accessible
        STATUS      mandatory
        DESCRIPTION
            ""
        INDEX       { meteringStm1PortSfpNEAddress, meteringStm1PortSfpIfIndex }
        ::= { meteringStm1PortSfpTable 1 }
    
    MeteringStm1PortSfpEntry ::= SEQUENCE {
        meteringStm1PortSfpIfIndex          InterfaceIndex,
        meteringStm1PortSfpNEAddress        IpAddress,
        meteringStm1PortSfpTxPower          DisplayString,
        meteringStm1PortSfpTxPowerStatus    ValidInvalidValue,
        meteringStm1PortSfpRxPower          DisplayString,
        meteringStm1PortSfpRxPowerStatus    ValidInvalidValue
    }
    
    -- 1.3.6.1.4.1.119.2.3.69.203.513.501.8.4.1.1
    meteringStm1PortSfpIfIndex OBJECT-TYPE
        SYNTAX      InterfaceIndex
        ACCESS      not-accessible
        STATUS      mandatory
        DESCRIPTION
            "Index of this table."
        ::= { meteringStm1PortSfpEntry 1 }
    
    -- 1.3.6.1.4.1.119.2.3.69.203.513.501.8.4.1.2
    meteringStm1PortSfpNEAddress OBJECT-TYPE
        SYNTAX      IpAddress
        ACCESS      not-accessible
        STATUS      mandatory
        DESCRIPTION
            "reserved."
        ::= { meteringStm1PortSfpEntry 2 }
    
    -- 1.3.6.1.4.1.119.2.3.69.203.513.501.8.4.1.3
    meteringStm1PortSfpTxPower OBJECT-TYPE
        SYNTAX      DisplayString
        ACCESS      read-only
        STATUS      mandatory
        DESCRIPTION
            "STM1 Port SFP TX Power [in dBm]"
        ::= { meteringStm1PortSfpEntry 3 }
    
    -- 1.3.6.1.4.1.119.2.3.69.203.513.501.8.4.1.4
    meteringStm1PortSfpTxPowerStatus OBJECT-TYPE
        SYNTAX      ValidInvalidValue
        ACCESS      read-only
        STATUS      mandatory
        DESCRIPTION
            "STM1 Port SFP TX Power Status"
        ::= { meteringStm1PortSfpEntry 4 }
    
    -- 1.3.6.1.4.1.119.2.3.69.203.513.501.8.4.1.5
    meteringStm1PortSfpRxPower OBJECT-TYPE
        SYNTAX      DisplayString
        ACCESS      read-only
        STATUS      mandatory
        DESCRIPTION
            "STM1 Port SFP RX Power [in dBm]"
        ::= { meteringStm1PortSfpEntry 5 }
    
    -- 1.3.6.1.4.1.119.2.3.69.203.513.501.8.4.1.6
    meteringStm1PortSfpRxPowerStatus OBJECT-TYPE
        SYNTAX      ValidInvalidValue
        ACCESS      read-only
        STATUS      mandatory
        DESCRIPTION
            "STM1 Port SFP RX Power Status"
        ::= { meteringStm1PortSfpEntry 6 }
    
    -- 1.3.6.1.4.1.119.2.3.69.203.513.501.9
    pmonGroup OBJECT IDENTIFIER
        ::= { pasoNeoIpe-common 9 }
    
    -- 1.3.6.1.4.1.119.2.3.69.203.513.501.9.1
    pmon15minDataRadioGroup OBJECT IDENTIFIER
        ::= { pmonGroup 1 }
    
    -- 1.3.6.1.4.1.119.2.3.69.203.513.501.9.1.2
    pmon15minDataRadio2Table OBJECT-TYPE
        SYNTAX      SEQUENCE OF Pmon15minDataRadio2Entry
        ACCESS      not-accessible
        STATUS      mandatory
        DESCRIPTION
            "PMON MODEM 15min RF Monitoring Table (High Capacity)"
        ::= { pmon15minDataRadioGroup 2 }
    
    -- 1.3.6.1.4.1.119.2.3.69.203.513.501.9.1.2.1
    pmon15minDataRadio2Entry OBJECT-TYPE
        SYNTAX      Pmon15minDataRadio2Entry
        ACCESS      not-accessible
        STATUS      mandatory
        DESCRIPTION
            ""
        INDEX       { pmon15minDataRadio2NEAddress, pmon15minDataModem2IfIndex,
                      pmon15minDataModem2MonitorName }
        ::= { pmon15minDataRadio2Table 1 }
    
    Pmon15minDataRadio2Entry ::= SEQUENCE {
        pmon15minDataModem2IfIndex      InterfaceIndex,
        pmon15minDataModem2MonitorName  INTEGER,
        pmon15minDataRadio2NEAddress    IpAddress,
        pmon15minDataModem2StatusInfo   IpeStatsInfo
    }
    
    -- 1.3.6.1.4.1.119.2.3.69.203.513.501.9.1.2.1.1
    pmon15minDataModem2IfIndex OBJECT-TYPE
        SYNTAX      InterfaceIndex
        ACCESS      not-accessible
        STATUS      mandatory
        DESCRIPTION
            "Index of this table."
        ::= { pmon15minDataRadio2Entry 1 }
    
    -- 1.3.6.1.4.1.119.2.3.69.203.513.501.9.1.2.1.2
    pmon15minDataModem2MonitorName OBJECT-TYPE
        SYNTAX      INTEGER { pmonBBE(1), pmonES(2), pmonSES(3), pmonSEF(4),
                        pmonUAS(5), pmonOFS(6) }
        ACCESS      not-accessible
        STATUS      mandatory
        DESCRIPTION
            "Index of this table. The value represents the monitoring item."
        ::= { pmon15minDataRadio2Entry 2 }
    
    -- 1.3.6.1.4.1.119.2.3.69.203.513.501.9.1.2.1.3
    pmon15minDataRadio2NEAddress OBJECT-TYPE
        SYNTAX      IpAddress
        ACCESS      not-accessible
        STATUS      mandatory
        DESCRIPTION
            "reserved."
        ::= { pmon15minDataRadio2Entry 3 }
    
    -- 1.3.6.1.4.1.119.2.3.69.203.513.501.9.1.2.1.4
    pmon15minDataModem2StatusInfo OBJECT-TYPE
        SYNTAX      IpeStatsInfo
        ACCESS      read-only
        STATUS      mandatory
        DESCRIPTION
            "PMON MODEM 15min RF Monitoring Status"
        ::= { pmon15minDataRadio2Entry 4 }
    
    
    -- 1.3.6.1.4.1.119.2.3.69.203.513.501.9.2
    pmon15minDataCableGroup OBJECT IDENTIFIER
        ::= { pmonGroup 2 }
    
    -- 1.3.6.1.4.1.119.2.3.69.203.513.501.9.2.1
    pmon15minDataThroughModeGroup OBJECT IDENTIFIER
        ::= { pmon15minDataCableGroup 1 }
    
    -- 1.3.6.1.4.1.119.2.3.69.203.513.501.9.2.1.1
    pmon15minDataTmRsTable OBJECT-TYPE
        SYNTAX      SEQUENCE OF Pmon15minDataTmRsEntry
        ACCESS      not-accessible
        STATUS      mandatory
        DESCRIPTION
            "PMON STM-1 15min (Through Mode) RS Monitoring Table"
        ::= { pmon15minDataThroughModeGroup 1 }
    
    -- 1.3.6.1.4.1.119.2.3.69.203.513.501.9.2.1.1.1
    pmon15minDataTmRsEntry OBJECT-TYPE
        SYNTAX      Pmon15minDataTmRsEntry
        ACCESS      not-accessible
        STATUS      mandatory
        DESCRIPTION
            ""
        INDEX       { pmon15minDataTmRsNEAddress, pmon15minDataTmRsIfIndex, pmon15minDataTmRsMonitorName }
        ::= { pmon15minDataTmRsTable 1 }
    
    Pmon15minDataTmRsEntry ::= SEQUENCE {
        pmon15minDataTmRsIfIndex        InterfaceIndex,
        pmon15minDataTmRsMonitorName    INTEGER,
        pmon15minDataTmRsNEAddress      IpAddress,
        pmon15minDataTmRsStatusInfo     IpeStatsInfo,
        pmon15minDataTmRsValue          INTEGER
    }
    
    -- 1.3.6.1.4.1.119.2.3.69.203.513.501.9.2.1.1.1.1
    pmon15minDataTmRsIfIndex OBJECT-TYPE
        SYNTAX      InterfaceIndex
        ACCESS      not-accessible
        STATUS      mandatory
        DESCRIPTION
            "Index of this table."
        ::= { pmon15minDataTmRsEntry 1 }
    
    -- 1.3.6.1.4.1.119.2.3.69.203.513.501.9.2.1.1.1.2
    pmon15minDataTmRsMonitorName OBJECT-TYPE
        SYNTAX      INTEGER { pmonBBE(1), pmonES(2), pmonSES(3), pmonSEF(4),
                        pmonUAS(5), pmonOFS(6) }
        ACCESS      not-accessible
        STATUS      mandatory
        DESCRIPTION
            "index of this table. The value represents the monitoring item."
        ::= { pmon15minDataTmRsEntry 2 }
    
    -- 1.3.6.1.4.1.119.2.3.69.203.513.501.9.2.1.1.1.3
    pmon15minDataTmRsNEAddress OBJECT-TYPE
        SYNTAX      IpAddress
        ACCESS      not-accessible
        STATUS      mandatory
        DESCRIPTION
            "reserved"
        ::= { pmon15minDataTmRsEntry 3 }
    
    -- 1.3.6.1.4.1.119.2.3.69.203.513.501.9.2.1.1.1.4
    pmon15minDataTmRsStatusInfo OBJECT-TYPE
        SYNTAX      IpeStatsInfo
        ACCESS      read-only
        STATUS      mandatory
        DESCRIPTION
            "PMON STM-1 15min (Through Mode) RS Monitoring Status."
        ::= { pmon15minDataTmRsEntry 4 }
    
    -- 1.3.6.1.4.1.119.2.3.69.203.513.501.9.2.1.1.1.5
    pmon15minDataTmRsValue OBJECT-TYPE
        SYNTAX      INTEGER
        ACCESS      read-only
        STATUS      mandatory
        DESCRIPTION
            "PMON STM-1 15min (Through Mode) RS Monitoring Status"
        ::= { pmon15minDataTmRsEntry 5 }
    
    -- 1.3.6.1.4.1.119.2.3.69.203.513.501.9.2.1.2
    pmon15minDataTmDMRRsTable OBJECT-TYPE
        SYNTAX      SEQUENCE OF Pmon15minDataTmDMRRsEntry
        ACCESS      not-accessible
        STATUS      mandatory
        DESCRIPTION
            "PMON STM-1 15min (Through Mode) DMR RS Monitoring Table"
        ::= { pmon15minDataThroughModeGroup 2 }
    
    -- 1.3.6.1.4.1.119.2.3.69.203.513.501.9.2.1.2.1
    pmon15minDataTmDMRRsEntry OBJECT-TYPE
        SYNTAX      Pmon15minDataTmDMRRsEntry
        ACCESS      not-accessible
        STATUS      mandatory
        DESCRIPTION
            ""
        INDEX       { pmon15minDataTmDMRRsNEAddress, pmon15minDataTmDMRRsIfIndex,
                      pmon15minDataTmDMRRsMonitorName }
        ::= { pmon15minDataTmDMRRsTable 1 }
    
    Pmon15minDataTmDMRRsEntry ::= SEQUENCE {
        pmon15minDataTmDMRRsIfIndex         InterfaceIndex,
        pmon15minDataTmDMRRsMonitorName     INTEGER,
        pmon15minDataTmDMRRsNEAddress       IpAddress,
        pmon15minDataTmDMRRsStatusInfo      IpeStatsInfo,
        pmon15minDataTmDMRRsValue           INTEGER
    }
    
    -- 1.3.6.1.4.1.119.2.3.69.203.513.501.9.2.1.2.1.1
    pmon15minDataTmDMRRsIfIndex OBJECT-TYPE
        SYNTAX      InterfaceIndex
        ACCESS      not-accessible
        STATUS      mandatory
        DESCRIPTION
            "Index of this table."
        ::= { pmon15minDataTmDMRRsEntry 1 }
    
    -- 1.3.6.1.4.1.119.2.3.69.203.513.501.9.2.1.2.1.2
    pmon15minDataTmDMRRsMonitorName OBJECT-TYPE
        SYNTAX      INTEGER { pmonBBE(1), pmonES(2), pmonSES(3), pmonSEF(4),
                        pmonUAS(5), pmonOFS(6) }
        ACCESS      not-accessible
        STATUS      mandatory
        DESCRIPTION
            "Index of this table. The value represents the monitoring item."
        ::= { pmon15minDataTmDMRRsEntry 2 }
    
    -- 1.3.6.1.4.1.119.2.3.69.203.513.501.9.2.1.2.1.3
    pmon15minDataTmDMRRsNEAddress OBJECT-TYPE
        SYNTAX      IpAddress
        ACCESS      not-accessible
        STATUS      mandatory
        DESCRIPTION
            "reserverd"
        ::= { pmon15minDataTmDMRRsEntry 3 }
    
    -- 1.3.6.1.4.1.119.2.3.69.203.513.501.9.2.1.2.1.4
    pmon15minDataTmDMRRsStatusInfo OBJECT-TYPE
        SYNTAX      IpeStatsInfo
        ACCESS      read-only
        STATUS      mandatory
        DESCRIPTION
            "PMON STM-1 15min (Through Mode) DMR RS Monitoring Status"
        ::= { pmon15minDataTmDMRRsEntry 4 }
    
    -- 1.3.6.1.4.1.119.2.3.69.203.513.501.9.2.1.2.1.5
    pmon15minDataTmDMRRsValue OBJECT-TYPE
        SYNTAX      INTEGER
        ACCESS      read-only
        STATUS      mandatory
        DESCRIPTION
            "PMON STM-1 15min (Through Mode) DMR RS Monitoring Value"
        ::= { pmon15minDataTmDMRRsEntry 5 }
    
    -- 1.3.6.1.4.1.119.2.3.69.203.513.501.9.2.2
    pmon15minDataChannelizedModeGroup OBJECT IDENTIFIER
        ::= { pmon15minDataCableGroup 2 }
    
    -- 1.3.6.1.4.1.119.2.3.69.203.513.501.9.2.2.1
    pmon15minDataChRsTable OBJECT-TYPE
        SYNTAX      SEQUENCE OF Pmon15minDataChRsEntry
        ACCESS      not-accessible
        STATUS      mandatory
        DESCRIPTION
            "PMON STM-1 15min (Channelized Mode) RS Monitoring Table"
        ::= { pmon15minDataChannelizedModeGroup 1 }
    
    -- 1.3.6.1.4.1.119.2.3.69.203.513.501.9.2.2.1.1
    pmon15minDataChRsEntry OBJECT-TYPE
        SYNTAX      Pmon15minDataChRsEntry
        ACCESS      not-accessible
        STATUS      mandatory
        DESCRIPTION
            ""
        INDEX       { pmon15minDataChRsNEAddress, pmon15minDataChRsIfIndex, pmon15minDataChRsMonitorName }
        ::= { pmon15minDataChRsTable 1 }
    
    Pmon15minDataChRsEntry ::= SEQUENCE {
        pmon15minDataChRsIfIndex        InterfaceIndex,
        pmon15minDataChRsMonitorName    INTEGER,
        pmon15minDataChRsNEAddress      IpAddress,
        pmon15minDataChRsStatusInfo     IpeStatsInfo,
        pmon15minDataChRsValue          INTEGER
    }
    
    -- 1.3.6.1.4.1.119.2.3.69.203.513.501.9.2.2.1.1.1
    pmon15minDataChRsIfIndex OBJECT-TYPE
        SYNTAX      InterfaceIndex
        ACCESS      not-accessible
        STATUS      mandatory
        DESCRIPTION
            "Index of this table."
        ::= { pmon15minDataChRsEntry 1 }
    
    -- 1.3.6.1.4.1.119.2.3.69.203.513.501.9.2.2.1.1.2
    pmon15minDataChRsMonitorName OBJECT-TYPE
        SYNTAX      INTEGER { pmonBBE(1), pmonES(2), pmonSES(3), pmonSEF(4),
                        pmonUAS(5), pmonOFS(6) }
        ACCESS      not-accessible
        STATUS      mandatory
        DESCRIPTION
            "Index of this table. The value represents the monitoring item."
        ::= { pmon15minDataChRsEntry 2 }
    
    -- 1.3.6.1.4.1.119.2.3.69.203.513.501.9.2.2.1.1.3
    pmon15minDataChRsNEAddress OBJECT-TYPE
        SYNTAX      IpAddress
        ACCESS      not-accessible
        STATUS      mandatory
        DESCRIPTION
            "reserved."
        ::= { pmon15minDataChRsEntry 3 }
    
    -- 1.3.6.1.4.1.119.2.3.69.203.513.501.9.2.2.1.1.4
    pmon15minDataChRsStatusInfo OBJECT-TYPE
        SYNTAX      IpeStatsInfo
        ACCESS      read-only
        STATUS      mandatory
        DESCRIPTION
            "PMON STM-1 15min (Channelized Mode) RS Monitoring Status"
        ::= { pmon15minDataChRsEntry 4 }
    
    -- 1.3.6.1.4.1.119.2.3.69.203.513.501.9.2.2.1.1.5
    pmon15minDataChRsValue OBJECT-TYPE
        SYNTAX      INTEGER
        ACCESS      read-only
        STATUS      mandatory
        DESCRIPTION
            "PMON STM-1 15min (Channelized Mode) RS Monitoring Value"
        ::= { pmon15minDataChRsEntry 5 }
    
    -- 1.3.6.1.4.1.119.2.3.69.203.513.501.9.2.2.2
    pmon15minDataChMsTable OBJECT-TYPE
        SYNTAX      SEQUENCE OF Pmon15minDataChMsEntry
        ACCESS      not-accessible
        STATUS      mandatory
        DESCRIPTION
            "PMON STM-1 15min (Channelized Mode) MS Monitoring Table."
        ::= { pmon15minDataChannelizedModeGroup 2 }
    
    -- 1.3.6.1.4.1.119.2.3.69.203.513.501.9.2.2.2.1
    pmon15minDataChMsEntry OBJECT-TYPE
        SYNTAX      Pmon15minDataChMsEntry
        ACCESS      not-accessible
        STATUS      mandatory
        DESCRIPTION
            ""
        INDEX       { pmon15minDataChMsNEAddress, pmon15minDataChMsIfIndex, pmon15minDataChMsMonitorName }
        ::= { pmon15minDataChMsTable 1 }
    
    Pmon15minDataChMsEntry ::= SEQUENCE {
        pmon15minDataChMsIfIndex        InterfaceIndex,
        pmon15minDataChMsMonitorName    INTEGER,
        pmon15minDataChMsNEAddress      IpAddress,
        pmon15minDataChMsStatusInfo     IpeStatsInfo,
        pmon15minDataChMsValue          INTEGER
    }
    
    -- 1.3.6.1.4.1.119.2.3.69.203.513.501.9.2.2.2.1.1
    pmon15minDataChMsIfIndex OBJECT-TYPE
        SYNTAX      InterfaceIndex
        ACCESS      not-accessible
        STATUS      mandatory
        DESCRIPTION
            "Index of this table."
        ::= { pmon15minDataChMsEntry 1 }
    
    -- 1.3.6.1.4.1.119.2.3.69.203.513.501.9.2.2.2.1.2
    pmon15minDataChMsMonitorName OBJECT-TYPE
        SYNTAX      INTEGER { pmonBBE(1), pmonES(2), pmonSES(3), pmonSEP(4),
                        pmonUAS(5) }
        ACCESS      not-accessible
        STATUS      mandatory
        DESCRIPTION
            "Index of this table. The value represents the monitoring item"
        ::= { pmon15minDataChMsEntry 2 }
    
    -- 1.3.6.1.4.1.119.2.3.69.203.513.501.9.2.2.2.1.3
    pmon15minDataChMsNEAddress OBJECT-TYPE
        SYNTAX      IpAddress
        ACCESS      not-accessible
        STATUS      mandatory
        DESCRIPTION
            "reserved"
        ::= { pmon15minDataChMsEntry 3 }
    
    -- 1.3.6.1.4.1.119.2.3.69.203.513.501.9.2.2.2.1.4
    pmon15minDataChMsStatusInfo OBJECT-TYPE
        SYNTAX      IpeStatsInfo
        ACCESS      read-only
        STATUS      mandatory
        DESCRIPTION
            "PMON STM-1 15min (Channelized Mode) MS Monitoring Status."
        ::= { pmon15minDataChMsEntry 4 }
    
    -- 1.3.6.1.4.1.119.2.3.69.203.513.501.9.2.2.2.1.5
    pmon15minDataChMsValue OBJECT-TYPE
        SYNTAX      INTEGER
        ACCESS      read-only
        STATUS      mandatory
        DESCRIPTION
            "PMON STM-1 15min (Channelized Mode) MS Monitoring Value"
        ::= { pmon15minDataChMsEntry 5 }
    
    -- 1.3.6.1.4.1.119.2.3.69.203.513.501.9.2.3
    pmon15minData16E1Group OBJECT IDENTIFIER
        ::= { pmon15minDataCableGroup 3 }
    
    -- 1.3.6.1.4.1.119.2.3.69.203.513.501.9.2.3.1
    pmon15minData16E1PdhTable OBJECT-TYPE
        SYNTAX      SEQUENCE OF Pmon15minData16E1PdhEntry
        ACCESS      not-accessible
        STATUS      mandatory
        DESCRIPTION
            "PMON E1 15min Monitoring Table"
        ::= { pmon15minData16E1Group 1 }
    
    -- 1.3.6.1.4.1.119.2.3.69.203.513.501.9.2.3.1.1
    pmon15minData16E1PdhEntry OBJECT-TYPE
        SYNTAX      Pmon15minData16E1PdhEntry
        ACCESS      not-accessible
        STATUS      mandatory
        DESCRIPTION
            ""
        INDEX       { pmon15minData16E1PdhNEAddress, pmon15minData16E1PdhIfIndex,
                      pmon15minData16E1PdhMonitorName }
        ::= { pmon15minData16E1PdhTable 1 }
    
    Pmon15minData16E1PdhEntry ::= SEQUENCE {
        pmon15minData16E1PdhIfIndex         InterfaceIndex,
        pmon15minData16E1PdhMonitorName     INTEGER,
        pmon15minData16E1PdhNEAddress       IpAddress,
        pmon15minData16E1PdhStatusInfo      IpeStatsInfo,
        pmon15minData16E1PdhValue           Counter
    }
    
    -- 1.3.6.1.4.1.119.2.3.69.203.513.501.9.2.3.1.1.1
    pmon15minData16E1PdhIfIndex OBJECT-TYPE
        SYNTAX      InterfaceIndex
        ACCESS      not-accessible
        STATUS      mandatory
        DESCRIPTION
            "Index of this table."
        ::= { pmon15minData16E1PdhEntry 1 }
    
    -- 1.3.6.1.4.1.119.2.3.69.203.513.501.9.2.3.1.1.2
    pmon15minData16E1PdhMonitorName OBJECT-TYPE
        SYNTAX      INTEGER { pmonCV(1) }
        ACCESS      not-accessible
        STATUS      mandatory
        DESCRIPTION
            "Index of this table. The value represents the monitoring item"
        ::= { pmon15minData16E1PdhEntry 2 }
    
    -- 1.3.6.1.4.1.119.2.3.69.203.513.501.9.2.3.1.1.3
    pmon15minData16E1PdhNEAddress OBJECT-TYPE
        SYNTAX      IpAddress
        ACCESS      not-accessible
        STATUS      mandatory
        DESCRIPTION
            "reserved"
        ::= { pmon15minData16E1PdhEntry 3 }
    
    -- 1.3.6.1.4.1.119.2.3.69.203.513.501.9.2.3.1.1.4
    pmon15minData16E1PdhStatusInfo OBJECT-TYPE
        SYNTAX      IpeStatsInfo
        ACCESS      read-only
        STATUS      mandatory
        DESCRIPTION
            "PMON E1 15min Monitoring Status"
        ::= { pmon15minData16E1PdhEntry 4 }
    
    -- 1.3.6.1.4.1.119.2.3.69.203.513.501.9.2.3.1.1.5
    pmon15minData16E1PdhValue OBJECT-TYPE
        SYNTAX      Counter
        ACCESS      read-only
        STATUS      mandatory
        DESCRIPTION
            "PMON E1 15min Monitoring Value"
        ::= { pmon15minData16E1PdhEntry 5 }
    
    -- 1.3.6.1.4.1.119.2.3.69.203.513.501.9.3
    pmon1dayDataRadioGroup OBJECT IDENTIFIER
        ::= { pmonGroup 3 }
    
    -- 1.3.6.1.4.1.119.2.3.69.203.513.501.9.3.2
    pmon1dayDataRadio2Table OBJECT-TYPE
        SYNTAX      SEQUENCE OF Pmon1dayDataRadio2Entry
        ACCESS      not-accessible
        STATUS      mandatory
        DESCRIPTION
            "PMON MODEM 1day RF Monitoring Table (High Capacity)"
        ::= { pmon1dayDataRadioGroup 2 }
    
    -- 1.3.6.1.4.1.119.2.3.69.203.513.501.9.3.2.1
    pmon1dayDataRadio2Entry OBJECT-TYPE
        SYNTAX      Pmon1dayDataRadio2Entry
        ACCESS      not-accessible
        STATUS      mandatory
        DESCRIPTION
            ""
        INDEX       { pmon1dayDataRadio2NEAddress, pmon1dayDataModem2IfIndex,
                      pmon1dayDataModem2MonitorName }
        ::= { pmon1dayDataRadio2Table 1 }
    
    Pmon1dayDataRadio2Entry ::= SEQUENCE {
        pmon1dayDataModem2IfIndex       InterfaceIndex,
        pmon1dayDataModem2MonitorName   INTEGER,
        pmon1dayDataRadio2NEAddress     IpAddress,
        pmon1dayDataModem2StatusInfo    IpeStatsInfo
    }
    
    -- 1.3.6.1.4.1.119.2.3.69.203.513.501.9.3.2.1.1
    pmon1dayDataModem2IfIndex OBJECT-TYPE
        SYNTAX      InterfaceIndex
        ACCESS      not-accessible
        STATUS      mandatory
        DESCRIPTION
            "Index of this table."
        ::= { pmon1dayDataRadio2Entry 1 }
    
    -- 1.3.6.1.4.1.119.2.3.69.203.513.501.9.3.2.1.2
    pmon1dayDataModem2MonitorName OBJECT-TYPE
        SYNTAX      INTEGER { pmonBBE(1), pmonES(2), pmonSES(3), pmonSEF(4),
                        pmonUAS(5), pmonOFS(6) }
        ACCESS      not-accessible
        STATUS      mandatory
        DESCRIPTION
            "Index of this table. The value represents the monitoring item."
        ::= { pmon1dayDataRadio2Entry 2 }
    
    -- 1.3.6.1.4.1.119.2.3.69.203.513.501.9.3.2.1.3
    pmon1dayDataRadio2NEAddress OBJECT-TYPE
        SYNTAX      IpAddress
        ACCESS      not-accessible
        STATUS      mandatory
        DESCRIPTION
            "reserved."
        ::= { pmon1dayDataRadio2Entry 3 }
    
    -- 1.3.6.1.4.1.119.2.3.69.203.513.501.9.3.2.1.4
    pmon1dayDataModem2StatusInfo OBJECT-TYPE
        SYNTAX      IpeStatsInfo
        ACCESS      read-only
        STATUS      mandatory
        DESCRIPTION
            "PMON MODEM 1day RF Monitoring Status"
        ::= { pmon1dayDataRadio2Entry 4 }
    
    
    -- 1.3.6.1.4.1.119.2.3.69.203.513.501.9.4
    pmon1dayDataCableGroup OBJECT IDENTIFIER
        ::= { pmonGroup 4 }
    
    -- 1.3.6.1.4.1.119.2.3.69.203.513.501.9.4.1
    pmon1dayDataThroughModeGroup OBJECT IDENTIFIER
        ::= { pmon1dayDataCableGroup 1 }
    
    -- 1.3.6.1.4.1.119.2.3.69.203.513.501.9.4.1.1
    pmon1dayDataTmRsTable OBJECT-TYPE
        SYNTAX      SEQUENCE OF Pmon1dayDataTmRsEntry
        ACCESS      not-accessible
        STATUS      mandatory
        DESCRIPTION
            "PMON STM-1 1day (Through Mode) RS Monitoring Table"
        ::= { pmon1dayDataThroughModeGroup 1 }
    
    -- 1.3.6.1.4.1.119.2.3.69.203.513.501.9.4.1.1.1
    pmon1dayDataTmRsEntry OBJECT-TYPE
        SYNTAX      Pmon1dayDataTmRsEntry
        ACCESS      not-accessible
        STATUS      mandatory
        DESCRIPTION
            ""
        INDEX       { pmon1dayDataTmRsNEAddress, pmon1dayDataTmRsIfIndex, pmon1dayDataTmRsMonitorName }
        ::= { pmon1dayDataTmRsTable 1 }
    
    Pmon1dayDataTmRsEntry ::= SEQUENCE {
        pmon1dayDataTmRsIfIndex         InterfaceIndex,
        pmon1dayDataTmRsMonitorName     INTEGER,
        pmon1dayDataTmRsNEAddress       IpAddress,
        pmon1dayDataTmRsStatusInfo      IpeStatsInfo,
        pmon1dayDataTmRsValue           INTEGER
    }
    
    -- 1.3.6.1.4.1.119.2.3.69.203.513.501.9.4.1.1.1.1
    pmon1dayDataTmRsIfIndex OBJECT-TYPE
        SYNTAX      InterfaceIndex
        ACCESS      not-accessible
        STATUS      mandatory
        DESCRIPTION
            "Index of this table."
        ::= { pmon1dayDataTmRsEntry 1 }
    
    -- 1.3.6.1.4.1.119.2.3.69.203.513.501.9.4.1.1.1.2
    pmon1dayDataTmRsMonitorName OBJECT-TYPE
        SYNTAX      INTEGER { pmonBBE(1), pmonES(2), pmonSES(3), pmonSEF(4),
                        pmonUAS(5), pmonOFS(6) }
        ACCESS      not-accessible
        STATUS      mandatory
        DESCRIPTION
            "Index of this table. The value represents the monitoring item"
        ::= { pmon1dayDataTmRsEntry 2 }
    
    -- 1.3.6.1.4.1.119.2.3.69.203.513.501.9.4.1.1.1.3
    pmon1dayDataTmRsNEAddress OBJECT-TYPE
        SYNTAX      IpAddress
        ACCESS      not-accessible
        STATUS      mandatory
        DESCRIPTION
            "reserved"
        ::= { pmon1dayDataTmRsEntry 3 }
    
    -- 1.3.6.1.4.1.119.2.3.69.203.513.501.9.4.1.1.1.4
    pmon1dayDataTmRsStatusInfo OBJECT-TYPE
        SYNTAX      IpeStatsInfo
        ACCESS      read-only
        STATUS      mandatory
        DESCRIPTION
            "PMON STM-1 1day (Through Mode) RS Monitoring Status"
        ::= { pmon1dayDataTmRsEntry 4 }
    
    -- 1.3.6.1.4.1.119.2.3.69.203.513.501.9.4.1.1.1.5
    pmon1dayDataTmRsValue OBJECT-TYPE
        SYNTAX      INTEGER
        ACCESS      read-only
        STATUS      mandatory
        DESCRIPTION
            "PMON STM-1 1day (Through Mode) RS Monitoring Value"
        ::= { pmon1dayDataTmRsEntry 5 }
    
    -- 1.3.6.1.4.1.119.2.3.69.203.513.501.9.4.1.2
    pmon1dayDataTmDMRRsTable OBJECT-TYPE
        SYNTAX      SEQUENCE OF Pmon1dayDataTmDMRRsEntry
        ACCESS      not-accessible
        STATUS      mandatory
        DESCRIPTION
            "PMON STM-1 1day (Through Mode) DMR RS Monitoring Table"
        ::= { pmon1dayDataThroughModeGroup 2 }
    
    -- 1.3.6.1.4.1.119.2.3.69.203.513.501.9.4.1.2.1
    pmon1dayDataTmDMRRsEntry OBJECT-TYPE
        SYNTAX      Pmon1dayDataTmDMRRsEntry
        ACCESS      not-accessible
        STATUS      mandatory
        DESCRIPTION
            ""
        INDEX       { pmon1dayDataTmDMRRsNEAddress, pmon1dayDataTmDMRRsIfIndex,
                      pmon1dayDataTmDMRRsMonitorName }
        ::= { pmon1dayDataTmDMRRsTable 1 }
    
    Pmon1dayDataTmDMRRsEntry ::= SEQUENCE {
        pmon1dayDataTmDMRRsIfIndex      InterfaceIndex,
        pmon1dayDataTmDMRRsMonitorName  INTEGER,
        pmon1dayDataTmDMRRsNEAddress    IpAddress,
        pmon1dayDataTmDMRRsStatusInfo   IpeStatsInfo,
        pmon1dayDataTmDMRRsValue        INTEGER
    }
    
    -- 1.3.6.1.4.1.119.2.3.69.203.513.501.9.4.1.2.1.1
    pmon1dayDataTmDMRRsIfIndex OBJECT-TYPE
        SYNTAX      InterfaceIndex
        ACCESS      not-accessible
        STATUS      mandatory
        DESCRIPTION
            "Index of this table."
        ::= { pmon1dayDataTmDMRRsEntry 1 }
    
    -- 1.3.6.1.4.1.119.2.3.69.203.513.501.9.4.1.2.1.2
    pmon1dayDataTmDMRRsMonitorName OBJECT-TYPE
        SYNTAX      INTEGER { pmonBBE(1), pmonES(2), pmonSES(3), pmonSEF(4),
                        pmonUAS(5), pmonOFS(6) }
        ACCESS      not-accessible
        STATUS      mandatory
        DESCRIPTION
            "Index of this table. The value represents the monitoring item."
        ::= { pmon1dayDataTmDMRRsEntry 2 }
    
    -- 1.3.6.1.4.1.119.2.3.69.203.513.501.9.4.1.2.1.3
    pmon1dayDataTmDMRRsNEAddress OBJECT-TYPE
        SYNTAX      IpAddress
        ACCESS      not-accessible
        STATUS      mandatory
        DESCRIPTION
            "reserved"
        ::= { pmon1dayDataTmDMRRsEntry 3 }
    
    -- 1.3.6.1.4.1.119.2.3.69.203.513.501.9.4.1.2.1.4
    pmon1dayDataTmDMRRsStatusInfo OBJECT-TYPE
        SYNTAX      IpeStatsInfo
        ACCESS      read-only
        STATUS      mandatory
        DESCRIPTION
            "PMON STM-1 1day (Through Mode) DMR RS Monitoring Status"
        ::= { pmon1dayDataTmDMRRsEntry 4 }
    
    -- 1.3.6.1.4.1.119.2.3.69.203.513.501.9.4.1.2.1.5
    pmon1dayDataTmDMRRsValue OBJECT-TYPE
        SYNTAX      INTEGER
        ACCESS      read-only
        STATUS      mandatory
        DESCRIPTION
            "PMON STM-1 1day (Through Mode) DMR RS Monitoring Value"
        ::= { pmon1dayDataTmDMRRsEntry 5 }
    
    -- 1.3.6.1.4.1.119.2.3.69.203.513.501.9.4.2
    pmon1dayDataChannelizedModeGroup OBJECT IDENTIFIER
        ::= { pmon1dayDataCableGroup 2 }
    
    -- 1.3.6.1.4.1.119.2.3.69.203.513.501.9.4.2.1
    pmon1dayDataChRsTable OBJECT-TYPE
        SYNTAX      SEQUENCE OF Pmon1dayDataChRsEntry
        ACCESS      not-accessible
        STATUS      mandatory
        DESCRIPTION
            "PMON STM-1 1day (Channelized Mode) RS Monitoring Table"
        ::= { pmon1dayDataChannelizedModeGroup 1 }
    
    -- 1.3.6.1.4.1.119.2.3.69.203.513.501.9.4.2.1.1
    pmon1dayDataChRsEntry OBJECT-TYPE
        SYNTAX      Pmon1dayDataChRsEntry
        ACCESS      not-accessible
        STATUS      mandatory
        DESCRIPTION
            ""
        INDEX       { pmon1dayDataChRsNEAddress, pmon1dayDataChRsIfIndex, pmon1dayDataChRsMonitorName }
        ::= { pmon1dayDataChRsTable 1 }
    
    Pmon1dayDataChRsEntry ::= SEQUENCE {
        pmon1dayDataChRsIfIndex         InterfaceIndex,
        pmon1dayDataChRsMonitorName     INTEGER,
        pmon1dayDataChRsNEAddress       IpAddress,
        pmon1dayDataChRsStatusInfo      IpeStatsInfo,
        pmon1dayDataChRsValue           INTEGER
    }
    
    -- 1.3.6.1.4.1.119.2.3.69.203.513.501.9.4.2.1.1.1
    pmon1dayDataChRsIfIndex OBJECT-TYPE
        SYNTAX      InterfaceIndex
        ACCESS      not-accessible
        STATUS      mandatory
        DESCRIPTION
            "Index of this table."
        ::= { pmon1dayDataChRsEntry 1 }
    
    -- 1.3.6.1.4.1.119.2.3.69.203.513.501.9.4.2.1.1.2
    pmon1dayDataChRsMonitorName OBJECT-TYPE
        SYNTAX      INTEGER { pmonBBE(1), pmonES(2), pmonSES(3), pmonSEF(4),
                        pmonUAS(5), pmonOFS(6) }
        ACCESS      not-accessible
        STATUS      mandatory
        DESCRIPTION
            "Index of this table. The value represents the monitoring item"
        ::= { pmon1dayDataChRsEntry 2 }
    
    -- 1.3.6.1.4.1.119.2.3.69.203.513.501.9.4.2.1.1.3
    pmon1dayDataChRsNEAddress OBJECT-TYPE
        SYNTAX      IpAddress
        ACCESS      not-accessible
        STATUS      mandatory
        DESCRIPTION
            "reserved"
        ::= { pmon1dayDataChRsEntry 3 }
    
    -- 1.3.6.1.4.1.119.2.3.69.203.513.501.9.4.2.1.1.4
    pmon1dayDataChRsStatusInfo OBJECT-TYPE
        SYNTAX      IpeStatsInfo
        ACCESS      read-only
        STATUS      mandatory
        DESCRIPTION
            "PMON STM-1 1day (Channelized Mode) RS Monitoring Status"
        ::= { pmon1dayDataChRsEntry 4 }
    
    -- 1.3.6.1.4.1.119.2.3.69.203.513.501.9.4.2.1.1.5
    pmon1dayDataChRsValue OBJECT-TYPE
        SYNTAX      INTEGER
        ACCESS      read-only
        STATUS      mandatory
        DESCRIPTION
            "PMON STM-1 1day (Channelized Mode) RS Monitoring Value"
        ::= { pmon1dayDataChRsEntry 5 }
    
    -- 1.3.6.1.4.1.119.2.3.69.203.513.501.9.4.2.2
    pmon1dayDataChMsTable OBJECT-TYPE
        SYNTAX      SEQUENCE OF Pmon1dayDataChMsEntry
        ACCESS      not-accessible
        STATUS      mandatory
        DESCRIPTION
            "PMON STM-1 1day (Channelized Mode) MS Monitoring Table"
        ::= { pmon1dayDataChannelizedModeGroup 2 }
    
    -- 1.3.6.1.4.1.119.2.3.69.203.513.501.9.4.2.2.1
    pmon1dayDataChMsEntry OBJECT-TYPE
        SYNTAX      Pmon1dayDataChMsEntry
        ACCESS      not-accessible
        STATUS      mandatory
        DESCRIPTION
            ""
        INDEX       { pmon1dayDataChMsNEAddress, pmon1dayDataChMsIfIndex, pmon1dayDataChMsMonitorName }
        ::= { pmon1dayDataChMsTable 1 }
    
    Pmon1dayDataChMsEntry ::= SEQUENCE {
        pmon1dayDataChMsIfIndex         InterfaceIndex,
        pmon1dayDataChMsMonitorName     INTEGER,
        pmon1dayDataChMsNEAddress       IpAddress,
        pmon1dayDataChMsStatusInfo      IpeStatsInfo,
        pmon1dayDataChMsValue           INTEGER
    }
    
    -- 1.3.6.1.4.1.119.2.3.69.203.513.501.9.4.2.2.1.1
    pmon1dayDataChMsIfIndex OBJECT-TYPE
        SYNTAX      InterfaceIndex
        ACCESS      not-accessible
        STATUS      mandatory
        DESCRIPTION
            "Index of this table."
        ::= { pmon1dayDataChMsEntry 1 }
    
    -- 1.3.6.1.4.1.119.2.3.69.203.513.501.9.4.2.2.1.2
    pmon1dayDataChMsMonitorName OBJECT-TYPE
        SYNTAX      INTEGER { pmonBBE(1), pmonES(2), pmonSES(3), pmonSEP(4),
                        pmonUAS(5) }
        ACCESS      not-accessible
        STATUS      mandatory
        DESCRIPTION
            "Index of this table. The value represents the monitoring item"
        ::= { pmon1dayDataChMsEntry 2 }
    
    -- 1.3.6.1.4.1.119.2.3.69.203.513.501.9.4.2.2.1.3
    pmon1dayDataChMsNEAddress OBJECT-TYPE
        SYNTAX      IpAddress
        ACCESS      not-accessible
        STATUS      mandatory
        DESCRIPTION
            "reserved"
        ::= { pmon1dayDataChMsEntry 3 }
    
    -- 1.3.6.1.4.1.119.2.3.69.203.513.501.9.4.2.2.1.4
    pmon1dayDataChMsStatusInfo OBJECT-TYPE
        SYNTAX      IpeStatsInfo
        ACCESS      read-only
        STATUS      mandatory
        DESCRIPTION
            "PMON STM-1 1day (Channelized Mode) MS Monitoring Status"
        ::= { pmon1dayDataChMsEntry 4 }
    
    -- 1.3.6.1.4.1.119.2.3.69.203.513.501.9.4.2.2.1.5
    pmon1dayDataChMsValue OBJECT-TYPE
        SYNTAX      INTEGER
        ACCESS      read-only
        STATUS      mandatory
        DESCRIPTION
            "PMON STM-1 1day (Channelized Mode) MS Monitoring Value"
        ::= { pmon1dayDataChMsEntry 5 }
    
    -- 1.3.6.1.4.1.119.2.3.69.203.513.501.9.4.3
    pmon1dayData16E1Group OBJECT IDENTIFIER
        ::= { pmon1dayDataCableGroup 3 }
    
    -- 1.3.6.1.4.1.119.2.3.69.203.513.501.9.4.3.1
    pmon1dayData16E1PdhTable OBJECT-TYPE
        SYNTAX      SEQUENCE OF Pmon1dayData16E1PdhEntry
        ACCESS      not-accessible
        STATUS      mandatory
        DESCRIPTION
            "PMON E1 1day Monitoring Table"
        ::= { pmon1dayData16E1Group 1 }
    
    -- 1.3.6.1.4.1.119.2.3.69.203.513.501.9.4.3.1.1
    pmon1dayData16E1PdhEntry OBJECT-TYPE
        SYNTAX      Pmon1dayData16E1PdhEntry
        ACCESS      not-accessible
        STATUS      mandatory
        DESCRIPTION
            ""
        INDEX       { pmon1dayData16E1PdhNEAddress, pmon1dayData16E1PdhIfIndex,
                      pmon1dayData16E1PdhMonitorName }
        ::= { pmon1dayData16E1PdhTable 1 }
    
    Pmon1dayData16E1PdhEntry ::= SEQUENCE {
        pmon1dayData16E1PdhIfIndex      InterfaceIndex,
        pmon1dayData16E1PdhMonitorName  INTEGER,
        pmon1dayData16E1PdhNEAddress    IpAddress,
        pmon1dayData16E1PdhStatusInfo   IpeStatsInfo,
        pmon1dayData16E1PdhValue        Counter
    }
    
    -- 1.3.6.1.4.1.119.2.3.69.203.513.501.9.4.3.1.1.1
    pmon1dayData16E1PdhIfIndex OBJECT-TYPE
        SYNTAX      InterfaceIndex
        ACCESS      not-accessible
        STATUS      mandatory
        DESCRIPTION
            "Index of this table."
        ::= { pmon1dayData16E1PdhEntry 1 }
    
    -- 1.3.6.1.4.1.119.2.3.69.203.513.501.9.4.3.1.1.2
    pmon1dayData16E1PdhMonitorName OBJECT-TYPE
        SYNTAX      INTEGER { pmonCV(1) }
        ACCESS      not-accessible
        STATUS      mandatory
        DESCRIPTION
            "Index of this table. The value represents the monitoring item."
        ::= { pmon1dayData16E1PdhEntry 2 }
    
    -- 1.3.6.1.4.1.119.2.3.69.203.513.501.9.4.3.1.1.3
    pmon1dayData16E1PdhNEAddress OBJECT-TYPE
        SYNTAX      IpAddress
        ACCESS      not-accessible
        STATUS      mandatory
        DESCRIPTION
            "reserved"
        ::= { pmon1dayData16E1PdhEntry 3 }
    
    -- 1.3.6.1.4.1.119.2.3.69.203.513.501.9.4.3.1.1.4
    pmon1dayData16E1PdhStatusInfo OBJECT-TYPE
        SYNTAX      IpeStatsInfo
        ACCESS      read-only
        STATUS      mandatory
        DESCRIPTION
            "PMON E1 1day Monitoring Status"
        ::= { pmon1dayData16E1PdhEntry 4 }
    
    -- 1.3.6.1.4.1.119.2.3.69.203.513.501.9.4.3.1.1.5
    pmon1dayData16E1PdhValue OBJECT-TYPE
        SYNTAX      Counter
        ACCESS      read-only
        STATUS      mandatory
        DESCRIPTION
            "PMON E1 1day Monitoring Value"
        ::= { pmon1dayData16E1PdhEntry 5 }
    
    -- 1.3.6.1.4.1.119.2.3.69.203.513.501.9.5
    pmon15minDataModulationGroup OBJECT IDENTIFIER
        ::= { pmonGroup 5 }
    
    -- 1.3.6.1.4.1.119.2.3.69.203.513.501.9.5.1
    pmon15minModulationDataTable OBJECT-TYPE
        SYNTAX      SEQUENCE OF Pmon15minModulationDataEntry
        ACCESS      not-accessible
        STATUS      mandatory
        DESCRIPTION
            "15minutes Monitoring Table"
        ::= { pmon15minDataModulationGroup 1 }
    
    -- 1.3.6.1.4.1.119.2.3.69.203.513.501.9.5.1.1
    pmon15minModulationDataEntry OBJECT-TYPE
        SYNTAX      Pmon15minModulationDataEntry
        ACCESS      not-accessible
        STATUS      mandatory
        DESCRIPTION
            ""
        INDEX       { pmon15minModulationDataNEAddress, pmon15minModulationDataIfIndex }
        ::= { pmon15minModulationDataTable 1 }
    
    Pmon15minModulationDataEntry ::= SEQUENCE {
        pmon15minModulationDataIfIndex          InterfaceIndex,
        pmon15minModulationDataNEAddress        IpAddress,
        pmon15minTxModulationDataStatusInfo     IpeStatsInfo,
        pmon15minTxModulationData               INTEGER,
        pmon15minRxModulationDataStatusInfo     IpeStatsInfo,
        pmon15minRxModulationData               INTEGER
    }
    
    -- 1.3.6.1.4.1.119.2.3.69.203.513.501.9.5.1.1.1
    pmon15minModulationDataIfIndex OBJECT-TYPE
        SYNTAX      InterfaceIndex
        ACCESS      not-accessible
        STATUS      mandatory
        DESCRIPTION
            "Index of this table."
        ::= { pmon15minModulationDataEntry 1 }
    
    -- 1.3.6.1.4.1.119.2.3.69.203.513.501.9.5.1.1.2
    pmon15minModulationDataNEAddress OBJECT-TYPE
        SYNTAX      IpAddress
        ACCESS      not-accessible
        STATUS      mandatory
        DESCRIPTION
            "reserved"
        ::= { pmon15minModulationDataEntry 2 }
    
    -- 1.3.6.1.4.1.119.2.3.69.203.513.501.9.5.1.1.3
    pmon15minTxModulationDataStatusInfo OBJECT-TYPE
        SYNTAX      IpeStatsInfo
        ACCESS      read-only
        STATUS      mandatory
        DESCRIPTION
            "15minutes Tx Modulation."
        ::= { pmon15minModulationDataEntry 3 }
    
    -- 1.3.6.1.4.1.119.2.3.69.203.513.501.9.5.1.1.4
    pmon15minTxModulationData OBJECT-TYPE
        SYNTAX      INTEGER { invalid(0), qpsk(1), qam16(2), qam32(3),
                        qam64(4), qam128(5), qam256(6), qam512(7),
                        qam1024(8), qam2048(9), qam4096(10) }
        ACCESS      read-only
        STATUS      mandatory
        DESCRIPTION
            "15minutes Tx Modulation Status."
        ::= { pmon15minModulationDataEntry 4 }
    
    -- 1.3.6.1.4.1.119.2.3.69.203.513.501.9.5.1.1.5
    pmon15minRxModulationDataStatusInfo OBJECT-TYPE
        SYNTAX      IpeStatsInfo
        ACCESS      read-only
        STATUS      mandatory
        DESCRIPTION
            "15minutes Rx Modulation."
        ::= { pmon15minModulationDataEntry 5 }
    
    -- 1.3.6.1.4.1.119.2.3.69.203.513.501.9.5.1.1.6
    pmon15minRxModulationData OBJECT-TYPE
        SYNTAX      INTEGER { invalid(0), qpsk(1), qam16(2), qam32(3),
                        qam64(4), qam128(5), qam256(6), qam512(7),
                        qam1024(8), qam2048(9), qam4096(10) }
        ACCESS      read-only
        STATUS      mandatory
        DESCRIPTION
            "15minutes Rx Modulation Status."
        ::= { pmon15minModulationDataEntry 6 }
    
    -- 1.3.6.1.4.1.119.2.3.69.203.513.501.9.6
    pmon1dayDataModulationGroup OBJECT IDENTIFIER
        ::= { pmonGroup 6 }
    
    -- 1.3.6.1.4.1.119.2.3.69.203.513.501.9.6.2
    pmon1dayModulationDataTable OBJECT-TYPE
        SYNTAX      SEQUENCE OF Pmon1dayModulationDataEntry
        ACCESS      not-accessible
        STATUS      mandatory
        DESCRIPTION
            "1day Monitoring Table"
        ::= { pmon1dayDataModulationGroup 2 }
    
    -- 1.3.6.1.4.1.119.2.3.69.203.513.501.9.6.2.1
    pmon1dayModulationDataEntry OBJECT-TYPE
        SYNTAX      Pmon1dayModulationDataEntry
        ACCESS      not-accessible
        STATUS      mandatory
        DESCRIPTION
            ""
        INDEX       { pmon1dayModulationDataNEAddress, pmon1dayModulationDataIfIndex }
        ::= { pmon1dayModulationDataTable 1 }
    
    Pmon1dayModulationDataEntry ::= SEQUENCE {
        pmon1dayModulationDataIfIndex       InterfaceIndex,
        pmon1dayModulationDataNEAddress     IpAddress,
        pmon1dayTxModulationDataStatusInfo  IpeStatsInfo,
        pmon1dayTxModulationData            INTEGER,
        pmon1dayRxModulationDataStatusInfo  IpeStatsInfo,
        pmon1dayRxModulationData            INTEGER
    }
    
    -- 1.3.6.1.4.1.119.2.3.69.203.513.501.9.6.2.1.1
    pmon1dayModulationDataIfIndex OBJECT-TYPE
        SYNTAX      InterfaceIndex
        ACCESS      not-accessible
        STATUS      mandatory
        DESCRIPTION
            "Index of this table."
        ::= { pmon1dayModulationDataEntry 1 }
    
    -- 1.3.6.1.4.1.119.2.3.69.203.513.501.9.6.2.1.2
    pmon1dayModulationDataNEAddress OBJECT-TYPE
        SYNTAX      IpAddress
        ACCESS      not-accessible
        STATUS      mandatory
        DESCRIPTION
            "reserved"
        ::= { pmon1dayModulationDataEntry 2 }
    
    -- 1.3.6.1.4.1.119.2.3.69.203.513.501.9.6.2.1.3
    pmon1dayTxModulationDataStatusInfo OBJECT-TYPE
        SYNTAX      IpeStatsInfo
        ACCESS      read-only
        STATUS      mandatory
        DESCRIPTION
            "1day Tx Modulation."
        ::= { pmon1dayModulationDataEntry 3 }
    
    -- 1.3.6.1.4.1.119.2.3.69.203.513.501.9.6.2.1.4
    pmon1dayTxModulationData OBJECT-TYPE
        SYNTAX      INTEGER { invalid(0), qpsk(1), qam16(2), qam32(3),
                        qam64(4), qam128(5), qam256(6), qam512(7),
                        qam1024(8), qam2048(9), qam4096(10) }
        ACCESS      read-only
        STATUS      mandatory
        DESCRIPTION
            "1day Tx Modulation Status."
        ::= { pmon1dayModulationDataEntry 4 }
    
    -- 1.3.6.1.4.1.119.2.3.69.203.513.501.9.6.2.1.5
    pmon1dayRxModulationDataStatusInfo OBJECT-TYPE
        SYNTAX      IpeStatsInfo
        ACCESS      read-only
        STATUS      mandatory
        DESCRIPTION
            "1day Rx Modulation."
        ::= { pmon1dayModulationDataEntry 5 }
    
    -- 1.3.6.1.4.1.119.2.3.69.203.513.501.9.6.2.1.6
    pmon1dayRxModulationData OBJECT-TYPE
        SYNTAX      INTEGER { invalid(0), qpsk(1), qam16(2), qam32(3),
                        qam64(4), qam128(5), qam256(6), qam512(7),
                        qam1024(8), qam2048(9), qam4096(10) }
        ACCESS      read-only
        STATUS      mandatory
        DESCRIPTION
            "1day Rx Modulation Status."
        ::= { pmon1dayModulationDataEntry 6 }
    
    -- 1.3.6.1.4.1.119.2.3.69.203.513.501.9.13
    pmon15minDataSfpGroup OBJECT IDENTIFIER
        ::= { pmonGroup 13 }
    
    -- 1.3.6.1.4.1.119.2.3.69.203.513.501.9.13.1
    pmon15minSfpDataTable OBJECT-TYPE
        SYNTAX      SEQUENCE OF Pmon15minSfpDataEntry
        ACCESS      not-accessible
        STATUS      mandatory
        DESCRIPTION
            "15minutes STM1 Port Sfp Tx/Rx Power Monitoring Table"
        ::= { pmon15minDataSfpGroup 1 }
    
    -- 1.3.6.1.4.1.119.2.3.69.203.513.501.9.13.1.1
    pmon15minSfpDataEntry OBJECT-TYPE
        SYNTAX      Pmon15minSfpDataEntry
        ACCESS      not-accessible
        STATUS      mandatory
        DESCRIPTION
            ""
        INDEX       { pmon15minSfpDataNEAddress, pmon15minSfpDataIfIndex }
        ::= { pmon15minSfpDataTable 1 }
    
    Pmon15minSfpDataEntry ::= SEQUENCE {
        pmon15minSfpDataIfIndex             InterfaceIndex,
        pmon15minSfpDataNEAddress           IpAddress,
        pmon15minSfpTxPowerDataStatusInfo   IpeStatsInfo,
        pmon15minSfpTxPowerData             DisplayString,
        pmon15minSfpRxPowerDataStatusInfo   IpeStatsInfo,
        pmon15minSfpRxPowerData             DisplayString
    }
    
    -- 1.3.6.1.4.1.119.2.3.69.203.513.501.9.13.1.1.1
    pmon15minSfpDataIfIndex OBJECT-TYPE
        SYNTAX      InterfaceIndex
        ACCESS      not-accessible
        STATUS      mandatory
        DESCRIPTION
            "Index of this table."
        ::= { pmon15minSfpDataEntry 1 }
    
    -- 1.3.6.1.4.1.119.2.3.69.203.513.501.9.13.1.1.2
    pmon15minSfpDataNEAddress OBJECT-TYPE
        SYNTAX      IpAddress
        ACCESS      not-accessible
        STATUS      mandatory
        DESCRIPTION
            "reserved"
        ::= { pmon15minSfpDataEntry 2 }
    
    -- 1.3.6.1.4.1.119.2.3.69.203.513.501.9.13.1.1.3
    pmon15minSfpTxPowerDataStatusInfo OBJECT-TYPE
        SYNTAX      IpeStatsInfo
        ACCESS      read-only
        STATUS      mandatory
        DESCRIPTION
            "15minutes STM1 Port Sfp Tx Power."
        ::= { pmon15minSfpDataEntry 3 }
    
    -- 1.3.6.1.4.1.119.2.3.69.203.513.501.9.13.1.1.4
    pmon15minSfpTxPowerData OBJECT-TYPE
        SYNTAX      DisplayString
        ACCESS      read-only
        STATUS      mandatory
        DESCRIPTION
            "15minutes STM1 Port Sfp Tx Power Status."
        ::= { pmon15minSfpDataEntry 4 }
    
    -- 1.3.6.1.4.1.119.2.3.69.203.513.501.9.13.1.1.5
    pmon15minSfpRxPowerDataStatusInfo OBJECT-TYPE
        SYNTAX      IpeStatsInfo
        ACCESS      read-only
        STATUS      mandatory
        DESCRIPTION
            "15minutes STM1 Port Sfp Rx Power."
        ::= { pmon15minSfpDataEntry 5 }
    
    -- 1.3.6.1.4.1.119.2.3.69.203.513.501.9.13.1.1.6
    pmon15minSfpRxPowerData OBJECT-TYPE
        SYNTAX      DisplayString
        ACCESS      read-only
        STATUS      mandatory
        DESCRIPTION
            "15minutes STM1 Port Sfp Rx Power Status."
        ::= { pmon15minSfpDataEntry 6 }
    
    -- 1.3.6.1.4.1.119.2.3.69.203.513.501.9.14
    pmon1dayDataSfpGroup OBJECT IDENTIFIER
        ::= { pmonGroup 14 }
    
    -- 1.3.6.1.4.1.119.2.3.69.203.513.501.9.14.1
    pmon1daySfpDataTable OBJECT-TYPE
        SYNTAX      SEQUENCE OF Pmon1daySfpDataEntry
        ACCESS      not-accessible
        STATUS      mandatory
        DESCRIPTION
            "1day STM1 Port Sfp Tx/Rx Monitoring Table"
        ::= { pmon1dayDataSfpGroup 1 }
    
    -- 1.3.6.1.4.1.119.2.3.69.203.513.501.9.14.1.1
    pmon1daySfpDataEntry OBJECT-TYPE
        SYNTAX      Pmon1daySfpDataEntry
        ACCESS      not-accessible
        STATUS      mandatory
        DESCRIPTION
            ""
        INDEX       { pmon1daySfpDataNEAddress, pmon1daySfpDataIfIndex }
        ::= { pmon1daySfpDataTable 1 }
    
    Pmon1daySfpDataEntry ::= SEQUENCE {
        pmon1daySfpDataIfIndex              InterfaceIndex,
        pmon1daySfpDataNEAddress            IpAddress,
        pmon1daySfpTxPowerDataStatusInfo    IpeStatsInfo,
        pmon1daySfpTxPowerData              DisplayString,
        pmon1daySfpRxPowerDataStatusInfo    IpeStatsInfo,
        pmon1daySfpRxPowerData              DisplayString
    }
    
    -- 1.3.6.1.4.1.119.2.3.69.203.513.501.9.14.1.1.1
    pmon1daySfpDataIfIndex OBJECT-TYPE
        SYNTAX      InterfaceIndex
        ACCESS      not-accessible
        STATUS      mandatory
        DESCRIPTION
            "Index of this table."
        ::= { pmon1daySfpDataEntry 1 }
    
    -- 1.3.6.1.4.1.119.2.3.69.203.513.501.9.14.1.1.2
    pmon1daySfpDataNEAddress OBJECT-TYPE
        SYNTAX      IpAddress
        ACCESS      not-accessible
        STATUS      mandatory
        DESCRIPTION
            "reserved"
        ::= { pmon1daySfpDataEntry 2 }
    
    -- 1.3.6.1.4.1.119.2.3.69.203.513.501.9.14.1.1.3
    pmon1daySfpTxPowerDataStatusInfo OBJECT-TYPE
        SYNTAX      IpeStatsInfo
        ACCESS      read-only
        STATUS      mandatory
        DESCRIPTION
            "1day STM1 Port Sfp Tx Power."
        ::= { pmon1daySfpDataEntry 3 }
    
    -- 1.3.6.1.4.1.119.2.3.69.203.513.501.9.14.1.1.4
    pmon1daySfpTxPowerData OBJECT-TYPE
        SYNTAX      DisplayString
        ACCESS      read-only
        STATUS      mandatory
        DESCRIPTION
            "1day STM1 Port Sfp Tx Power Status."
        ::= { pmon1daySfpDataEntry 4 }
    
    -- 1.3.6.1.4.1.119.2.3.69.203.513.501.9.14.1.1.5
    pmon1daySfpRxPowerDataStatusInfo OBJECT-TYPE
        SYNTAX      IpeStatsInfo
        ACCESS      read-only
        STATUS      mandatory
        DESCRIPTION
            "1day STM1 Port Sfp Rx Power."
        ::= { pmon1daySfpDataEntry 5 }
    
    -- 1.3.6.1.4.1.119.2.3.69.203.513.501.9.14.1.1.6
    pmon1daySfpRxPowerData OBJECT-TYPE
        SYNTAX      DisplayString
        ACCESS      read-only
        STATUS      mandatory
        DESCRIPTION
            "1day STM1 Port Sfp Rx Power Status."
        ::= { pmon1daySfpDataEntry 6 }
    
    -- 1.3.6.1.4.1.119.2.3.69.203.513.501.10
    pmonTxRxLevGroup OBJECT IDENTIFIER
        ::= { pasoNeoIpe-common 10 }
    
    -- 1.3.6.1.4.1.119.2.3.69.203.513.501.10.1
    pmonTxRxLev15minCurrentDataTable OBJECT-TYPE
        SYNTAX      SEQUENCE OF PmonTxRxLev15minCurrentDataEntry
        ACCESS      not-accessible
        STATUS      mandatory
        DESCRIPTION
            "PMON ODU 15min Tx/RX Level Monitoring Table"
        ::= { pmonTxRxLevGroup 1 }
    
    -- 1.3.6.1.4.1.119.2.3.69.203.513.501.10.1.1
    pmonTxRxLev15minCurrentDataEntry OBJECT-TYPE
        SYNTAX      PmonTxRxLev15minCurrentDataEntry
        ACCESS      not-accessible
        STATUS      mandatory
        DESCRIPTION
            ""
        INDEX       { pmonTxRxLev15minCurrentDataNEAddress, pmonTxRxLev15minCurrentDataIfIndex }
        ::= { pmonTxRxLev15minCurrentDataTable 1 }
    
    PmonTxRxLev15minCurrentDataEntry ::= SEQUENCE {
        pmonTxRxLev15minCurrentDataIfIndex              InterfaceIndex,
        pmonTxRxLev15minCurrentDataNEAddress            IpAddress,
        pmonTxRxLev15minCurrentDataStatusInfo           IpeStatsInfo,
        pmonTxRxLev15minRxLevelMaxCurrentData           DisplayString,
        pmonTxRxLev15minRxLevelMinCurrentData           DisplayString,
        pmonTxRxLev15minTxLevelCurrentDataStatusInfo    IpeStatsInfo,
        pmonTxRxLev15minTxLevelMaxCurrentData           DisplayString,
        pmonTxRxLev15minTxLevelMinCurrentData           DisplayString
    }
    
    -- 1.3.6.1.4.1.119.2.3.69.203.513.501.10.1.1.1
    pmonTxRxLev15minCurrentDataIfIndex OBJECT-TYPE
        SYNTAX      InterfaceIndex
        ACCESS      not-accessible
        STATUS      mandatory
        DESCRIPTION
            "Index of this table."
        ::= { pmonTxRxLev15minCurrentDataEntry 1 }
    
    -- 1.3.6.1.4.1.119.2.3.69.203.513.501.10.1.1.2
    pmonTxRxLev15minCurrentDataNEAddress OBJECT-TYPE
        SYNTAX      IpAddress
        ACCESS      not-accessible
        STATUS      mandatory
        DESCRIPTION
            "reserved"
        ::= { pmonTxRxLev15minCurrentDataEntry 2 }
    
    -- 1.3.6.1.4.1.119.2.3.69.203.513.501.10.1.1.3
    pmonTxRxLev15minCurrentDataStatusInfo OBJECT-TYPE
        SYNTAX      IpeStatsInfo
        ACCESS      read-only
        STATUS      mandatory
        DESCRIPTION
            "PMON ODU 15min RX Level Status"
        ::= { pmonTxRxLev15minCurrentDataEntry 3 }
    
    -- 1.3.6.1.4.1.119.2.3.69.203.513.501.10.1.1.4
    pmonTxRxLev15minRxLevelMaxCurrentData OBJECT-TYPE
        SYNTAX      DisplayString
        ACCESS      read-only
        STATUS      mandatory
        DESCRIPTION
            "PMON ODU 15min RX Level (MAX)"
        ::= { pmonTxRxLev15minCurrentDataEntry 4 }
    
    -- 1.3.6.1.4.1.119.2.3.69.203.513.501.10.1.1.5
    pmonTxRxLev15minRxLevelMinCurrentData OBJECT-TYPE
        SYNTAX      DisplayString
        ACCESS      read-only
        STATUS      mandatory
        DESCRIPTION
            "PMON ODU 15min RX Level (MIN)"
        ::= { pmonTxRxLev15minCurrentDataEntry 5 }
    
    -- 1.3.6.1.4.1.119.2.3.69.203.513.501.10.1.1.6
    pmonTxRxLev15minTxLevelCurrentDataStatusInfo OBJECT-TYPE
        SYNTAX      IpeStatsInfo
        ACCESS      read-only
        STATUS      mandatory
        DESCRIPTION
            "PMON ODU 15min TX Level Status"
        ::= { pmonTxRxLev15minCurrentDataEntry 6 }
    
    -- 1.3.6.1.4.1.119.2.3.69.203.513.501.10.1.1.7
    pmonTxRxLev15minTxLevelMaxCurrentData OBJECT-TYPE
        SYNTAX      DisplayString
        ACCESS      read-only
        STATUS      mandatory
        DESCRIPTION
            "PMON ODU 15min TX Level (MAX)"
        ::= { pmonTxRxLev15minCurrentDataEntry 7 }
    
    -- 1.3.6.1.4.1.119.2.3.69.203.513.501.10.1.1.8
    pmonTxRxLev15minTxLevelMinCurrentData OBJECT-TYPE
        SYNTAX      DisplayString
        ACCESS      read-only
        STATUS      mandatory
        DESCRIPTION
            "PMON ODU 15min TX Level (MIN)"
        ::= { pmonTxRxLev15minCurrentDataEntry 8 }
    
    -- 1.3.6.1.4.1.119.2.3.69.203.513.501.10.2
    pmonTxRxLev1dayCurrentDataTable OBJECT-TYPE
        SYNTAX      SEQUENCE OF PmonTxRxLev1dayCurrentDataEntry
        ACCESS      not-accessible
        STATUS      mandatory
        DESCRIPTION
            "PMON ODU 1day Tx/RX Level Monitoring Table"
        ::= { pmonTxRxLevGroup 2 }
    
    -- 1.3.6.1.4.1.119.2.3.69.203.513.501.10.2.1
    pmonTxRxLev1dayCurrentDataEntry OBJECT-TYPE
        SYNTAX      PmonTxRxLev1dayCurrentDataEntry
        ACCESS      not-accessible
        STATUS      mandatory
        DESCRIPTION
            ""
        INDEX       { pmonTxRxLev1dayCurrentDataNEAddress, pmonTxRxLev1dayCurrentDataIfIndex }
        ::= { pmonTxRxLev1dayCurrentDataTable 1 }
    
    PmonTxRxLev1dayCurrentDataEntry ::= SEQUENCE {
        pmonTxRxLev1dayCurrentDataIfIndex               InterfaceIndex,
        pmonTxRxLev1dayCurrentDataNEAddress             IpAddress,
        pmonTxRxLev1dayCurrentDataStatusInfo            IpeStatsInfo,
        pmonTxRxLev1dayRxLevelMaxCurrentData            DisplayString,
        pmonTxRxLev1dayRxLevelMinCurrentData            DisplayString,
        pmonTxRxLev1dayTxLevelCurrentDataStatusInfo     IpeStatsInfo,
        pmonTxRxLev1dayTxLevelMaxCurrentData            DisplayString,
        pmonTxRxLev1dayTxLevelMinCurrentData            DisplayString
    }
    
    -- 1.3.6.1.4.1.119.2.3.69.203.513.501.10.2.1.1
    pmonTxRxLev1dayCurrentDataIfIndex OBJECT-TYPE
        SYNTAX      InterfaceIndex
        ACCESS      not-accessible
        STATUS      mandatory
        DESCRIPTION
            "Index of this table."
        ::= { pmonTxRxLev1dayCurrentDataEntry 1 }
    
    -- 1.3.6.1.4.1.119.2.3.69.203.513.501.10.2.1.2
    pmonTxRxLev1dayCurrentDataNEAddress OBJECT-TYPE
        SYNTAX      IpAddress
        ACCESS      not-accessible
        STATUS      mandatory
        DESCRIPTION
            "reserved"
        ::= { pmonTxRxLev1dayCurrentDataEntry 2 }
    
    -- 1.3.6.1.4.1.119.2.3.69.203.513.501.10.2.1.3
    pmonTxRxLev1dayCurrentDataStatusInfo OBJECT-TYPE
        SYNTAX      IpeStatsInfo
        ACCESS      read-only
        STATUS      mandatory
        DESCRIPTION
            "PMON ODU 1day RX Level Status"
        ::= { pmonTxRxLev1dayCurrentDataEntry 3 }
    
    -- 1.3.6.1.4.1.119.2.3.69.203.513.501.10.2.1.4
    pmonTxRxLev1dayRxLevelMaxCurrentData OBJECT-TYPE
        SYNTAX      DisplayString
        ACCESS      read-only
        STATUS      mandatory
        DESCRIPTION
            "PMON ODU 1day RX Level (MAX)"
        ::= { pmonTxRxLev1dayCurrentDataEntry 4 }
    
    -- 1.3.6.1.4.1.119.2.3.69.203.513.501.10.2.1.5
    pmonTxRxLev1dayRxLevelMinCurrentData OBJECT-TYPE
        SYNTAX      DisplayString
        ACCESS      read-only
        STATUS      mandatory
        DESCRIPTION
            "PMON ODU 1day RX Level (MIN)"
        ::= { pmonTxRxLev1dayCurrentDataEntry 5 }
    
    -- 1.3.6.1.4.1.119.2.3.69.203.513.501.10.2.1.6
    pmonTxRxLev1dayTxLevelCurrentDataStatusInfo OBJECT-TYPE
        SYNTAX      IpeStatsInfo
        ACCESS      read-only
        STATUS      mandatory
        DESCRIPTION
            "PMON ODU 1day TX Level Status"
        ::= { pmonTxRxLev1dayCurrentDataEntry 6 }
    
    -- 1.3.6.1.4.1.119.2.3.69.203.513.501.10.2.1.7
    pmonTxRxLev1dayTxLevelMaxCurrentData OBJECT-TYPE
        SYNTAX      DisplayString
        ACCESS      read-only
        STATUS      mandatory
        DESCRIPTION
            "PMON ODU 1day TX Level (MAX)"
        ::= { pmonTxRxLev1dayCurrentDataEntry 7 }
    
    -- 1.3.6.1.4.1.119.2.3.69.203.513.501.10.2.1.8
    pmonTxRxLev1dayTxLevelMinCurrentData OBJECT-TYPE
        SYNTAX      DisplayString
        ACCESS      read-only
        STATUS      mandatory
        DESCRIPTION
            "PMON ODU 1day TX Level (MIN)"
        ::= { pmonTxRxLev1dayCurrentDataEntry 8 }
    
    -- 1.3.6.1.4.1.119.2.3.69.203.513.501.11
    rmonGroup OBJECT IDENTIFIER
        ::= { pasoNeoIpe-common 11 }
    
    -- 1.3.6.1.4.1.119.2.3.69.203.513.501.11.1
    rmonEthGroup OBJECT IDENTIFIER
        ::= { rmonGroup 1 }
    
    -- 1.3.6.1.4.1.119.2.3.69.203.513.501.11.1.1
    rmon15minPortGroup OBJECT IDENTIFIER
        ::= { rmonEthGroup 1 }
    
    -- 1.3.6.1.4.1.119.2.3.69.203.513.501.11.1.1.2
    rmon15minPort2Table OBJECT-TYPE
        SYNTAX      SEQUENCE OF Rmon15minPort2Entry
        ACCESS      not-accessible
        STATUS      mandatory
        DESCRIPTION
            "RMON 15min Port Monitoring Table."
        ::= { rmon15minPortGroup 2 }
    
    -- 1.3.6.1.4.1.119.2.3.69.203.513.501.11.1.1.2.1
    rmon15minPort2Entry OBJECT-TYPE
        SYNTAX      Rmon15minPort2Entry
        ACCESS      not-accessible
        STATUS      mandatory
        DESCRIPTION
            ""
        INDEX       { rmon15minPort2NEAddress, rmon15minPort2IfIndex }
        ::= { rmon15minPort2Table 1 }
    
    Rmon15minPort2Entry ::= SEQUENCE {
        rmon15minPort2IfIndex                               InterfaceIndex,
        rmon15minPort2NEAddress                             IpAddress,
        rmon15minHCRxEthStatsOctets2Status                  IpeStatsInfo,
        rmon15minHCTxEthStatsOctets2Status                  IpeStatsInfo,
        rmon15minHCRxEthStatsPkts2Status                    IpeStatsInfo,
        rmon15minHCTxEthStatsPkts2Status                    IpeStatsInfo,
        rmon15minRxEthStatsDropEvents2                      Counter,
        rmon15minRxEthStatsDropEvents2Status                IpeStatsInfo,
        rmon15minRxEthStatsUndersizePkts2                   Counter,
        rmon15minRxEthStatsUndersizePkts2Status             IpeStatsInfo,
        rmon15minRxEthStatsFragments2                       Counter,
        rmon15minRxEthStatsFragments2Status                 IpeStatsInfo,
        rmon15minHCRxEthStatsPkts64Octets2Status            IpeStatsInfo,
        rmon15minHCTxEthStatsPkts64Octets2Status            IpeStatsInfo,
        rmon15minHCRxEthStatsPkts65to127Octets2Status       IpeStatsInfo,
        rmon15minHCTxEthStatsPkts65to127Octets2Status       IpeStatsInfo,
        rmon15minHCRxEthStatsPkts128to255Octets2Status      IpeStatsInfo,
        rmon15minHCTxEthStatsPkts128to255Octets2Status      IpeStatsInfo,
        rmon15minHCRxEthStatsPkts256to511Octets2Status      IpeStatsInfo,
        rmon15minHCTxEthStatsPkts256to511Octets2Status      IpeStatsInfo,
        rmon15minHCRxEthStatsPkts512to1023Octets2Status     IpeStatsInfo,
        rmon15minHCTxEthStatsPkts512to1023Octets2Status     IpeStatsInfo,
        rmon15minHCRxEthStatsPkts1024to1518Octets2Status    IpeStatsInfo,
        rmon15minHCTxEthStatsPkts1024to1518Octets2Status    IpeStatsInfo,
        rmon15minRxEthStatsCRCAlignErrors2                  Counter,
        rmon15minRxEthStatsCRCAlignErrors2Status            IpeStatsInfo,
        rmon15minRxEthStatsOversizePkts2                    Counter,
        rmon15minRxEthStatsOversizePkts2Status              IpeStatsInfo,
        rmon15minRxEthStatsJabbers2                         Counter,
        rmon15minRxEthStatsJabbers2Status                   IpeStatsInfo,
        rmon15minRxEthStatsMulticastPkts2                   Counter,
        rmon15minRxEthStatsMulticastPkts2Status             IpeStatsInfo,
        rmon15minTxEthStatsMulticastPkts2                   Counter,
        rmon15minTxEthStatsMulticastPkts2Status             IpeStatsInfo,
        rmon15minRxEthStatsBroadcastPkts2                   Counter,
        rmon15minRxEthStatsBroadcastPkts2Status             IpeStatsInfo,
        rmon15minTxEthStatsBroadcastPkts2                   Counter,
        rmon15minTxEthStatsBroadcastPkts2Status             IpeStatsInfo,
        rmon15minTxEthStatsCollisions2                      Counter,
        rmon15minTxEthStatsCollisions2Status                IpeStatsInfo,
        rmon15minHCRxUnknownTPID2Status                     IpeStatsInfo,
        rmon15minHCRxUnknownVID2Status                      IpeStatsInfo,
        rmon15minHCRxMAClimit2Status                        IpeStatsInfo,
        rmon15minHCRxFilterDiscard2Status                   IpeStatsInfo,
        rmon15minHCRxQoSDiscard2Status                      IpeStatsInfo,
        rmon15minHCTxQueue0Discard2Status                   IpeStatsInfo,
        rmon15minHCTxQueue1Discard2Status                   IpeStatsInfo,
        rmon15minHCTxQueue2Discard2Status                   IpeStatsInfo,
        rmon15minHCTxQueue3Discard2Status                   IpeStatsInfo,
        rmon15minHCTxQueue4Discard2Status                   IpeStatsInfo,
        rmon15minHCTxQueue5Discard2Status                   IpeStatsInfo,
        rmon15minHCTxQueue6Discard2Status                   IpeStatsInfo,
        rmon15minHCTxQueue7Discard2Status                   IpeStatsInfo,
        rmon15minTxEthStatsOversizePkts2                    Counter,
        rmon15minTxEthStatsOversizePkts2Status              IpeStatsInfo,
        rmon15minHCTxFilterDiscard2Status                   IpeStatsInfo
    }
    
    -- 1.3.6.1.4.1.119.2.3.69.203.513.501.11.1.1.2.1.1
    rmon15minPort2IfIndex OBJECT-TYPE
        SYNTAX      InterfaceIndex
        ACCESS      not-accessible
        STATUS      mandatory
        DESCRIPTION
            "Index of this table."
        ::= { rmon15minPort2Entry 1 }
    
    -- 1.3.6.1.4.1.119.2.3.69.203.513.501.11.1.1.2.1.2
    rmon15minPort2NEAddress OBJECT-TYPE
        SYNTAX      IpAddress
        ACCESS      not-accessible
        STATUS      mandatory
        DESCRIPTION
            "reserved."
        ::= { rmon15minPort2Entry 2 }
    
    
    -- 1.3.6.1.4.1.119.2.3.69.203.513.501.11.1.1.2.1.4
    rmon15minHCRxEthStatsOctets2Status OBJECT-TYPE
        SYNTAX      IpeStatsInfo
        ACCESS      read-only
        STATUS      mandatory
        DESCRIPTION
            "RMON 15min RX Octs Status. 'invalid' means the corresponding
             monitoring value is not reliable because of the alarm or other
             reasons. 'maintenance' means that some maintenance functions are
             executed on the current interval."
        ::= { rmon15minPort2Entry 4 }
    
    
    -- 1.3.6.1.4.1.119.2.3.69.203.513.501.11.1.1.2.1.6
    rmon15minHCTxEthStatsOctets2Status OBJECT-TYPE
        SYNTAX      IpeStatsInfo
        ACCESS      read-only
        STATUS      mandatory
        DESCRIPTION
            "RMON 15min TX Octs Status. 'invalid' means the corresponding
             monitoring value is not reliable because of the alarm or other
             reasons. 'maintenance' means that some maintenance functions are
             executed on the current interval."
        ::= { rmon15minPort2Entry 6 }
    
    
    -- 1.3.6.1.4.1.119.2.3.69.203.513.501.11.1.1.2.1.8
    rmon15minHCRxEthStatsPkts2Status OBJECT-TYPE
        SYNTAX      IpeStatsInfo
        ACCESS      read-only
        STATUS      mandatory
        DESCRIPTION
            "RMON 15min RX Pkts Status. 'invalid' means the corresponding
             monitoring value is not reliable because of the alarm or other
             reasons. 'maintenance' means that some maintenance functions are
             executed on the current interval."
        ::= { rmon15minPort2Entry 8 }
    
    
    -- 1.3.6.1.4.1.119.2.3.69.203.513.501.11.1.1.2.1.10
    rmon15minHCTxEthStatsPkts2Status OBJECT-TYPE
        SYNTAX      IpeStatsInfo
        ACCESS      read-only
        STATUS      mandatory
        DESCRIPTION
            "RMON 15min TX Pkts Status. 'invalid' means the corresponding
             monitoring value is not reliable because of the alarm or other
             reasons. 'maintenance' means that some maintenance functions are
             executed on the current interval."
        ::= { rmon15minPort2Entry 10 }
    
    -- 1.3.6.1.4.1.119.2.3.69.203.513.501.11.1.1.2.1.11
    rmon15minRxEthStatsDropEvents2 OBJECT-TYPE
        SYNTAX      Counter
        ACCESS      read-only
        STATUS      mandatory
        DESCRIPTION
            "RMON 15min RX Drop Events"
        ::= { rmon15minPort2Entry 11 }
    
    -- 1.3.6.1.4.1.119.2.3.69.203.513.501.11.1.1.2.1.12
    rmon15minRxEthStatsDropEvents2Status OBJECT-TYPE
        SYNTAX      IpeStatsInfo
        ACCESS      read-only
        STATUS      mandatory
        DESCRIPTION
            "RMON 15min RX Drop Events Status. 'invalid' means the
             corresponding monitoring value is not reliable because of the
             alarm or other reasons. 'maintenance' means that some maintenance
             functions are executed on the current interval."
        ::= { rmon15minPort2Entry 12 }
    
    -- 1.3.6.1.4.1.119.2.3.69.203.513.501.11.1.1.2.1.13
    rmon15minRxEthStatsUndersizePkts2 OBJECT-TYPE
        SYNTAX      Counter
        ACCESS      read-only
        STATUS      mandatory
        DESCRIPTION
            "RMON 15min RX Undersize Pkts"
        ::= { rmon15minPort2Entry 13 }
    
    -- 1.3.6.1.4.1.119.2.3.69.203.513.501.11.1.1.2.1.14
    rmon15minRxEthStatsUndersizePkts2Status OBJECT-TYPE
        SYNTAX      IpeStatsInfo
        ACCESS      read-only
        STATUS      mandatory
        DESCRIPTION
            "RMON 15min RX Undersize Pkts Status. 'invalid' means the
             corresponding monitoring value is not reliable because of the
             alarm or other reasons. 'maintenance' means that some maintenance
             functions are executed on the current interval."
        ::= { rmon15minPort2Entry 14 }
    
    -- 1.3.6.1.4.1.119.2.3.69.203.513.501.11.1.1.2.1.15
    rmon15minRxEthStatsFragments2 OBJECT-TYPE
        SYNTAX      Counter
        ACCESS      read-only
        STATUS      mandatory
        DESCRIPTION
            "RMON 15min RX Fragments"
        ::= { rmon15minPort2Entry 15 }
    
    -- 1.3.6.1.4.1.119.2.3.69.203.513.501.11.1.1.2.1.16
    rmon15minRxEthStatsFragments2Status OBJECT-TYPE
        SYNTAX      IpeStatsInfo
        ACCESS      read-only
        STATUS      mandatory
        DESCRIPTION
            "RMON 15min RX Fragments Status. 'invalid' means the
             corresponding monitoring value is not reliable because of the
             alarm or other reasons. 'maintenance' means that some maintenance
             functions are executed on the current interval."
        ::= { rmon15minPort2Entry 16 }
    
    
    -- 1.3.6.1.4.1.119.2.3.69.203.513.501.11.1.1.2.1.18
    rmon15minHCRxEthStatsPkts64Octets2Status OBJECT-TYPE
        SYNTAX      IpeStatsInfo
        ACCESS      read-only
        STATUS      mandatory
        DESCRIPTION
            "RMON 15min RX 64 Octs Status. 'invalid' means the corresponding
             monitoring value is not reliable because of the alarm or other
             reasons. 'maintenance' means that some maintenance functions are
             executed on the current interval."
        ::= { rmon15minPort2Entry 18 }
    
    
    -- 1.3.6.1.4.1.119.2.3.69.203.513.501.11.1.1.2.1.20
    rmon15minHCTxEthStatsPkts64Octets2Status OBJECT-TYPE
        SYNTAX      IpeStatsInfo
        ACCESS      read-only
        STATUS      mandatory
        DESCRIPTION
            "RMON 15min TX 64 Octs Status. 'invalid' means the corresponding
             monitoring value is not reliable because of the alarm or other
             reasons. 'maintenance' means that some maintenance functions are
             executed on the current interval."
        ::= { rmon15minPort2Entry 20 }
    
    
    -- 1.3.6.1.4.1.119.2.3.69.203.513.501.11.1.1.2.1.22
    rmon15minHCRxEthStatsPkts65to127Octets2Status OBJECT-TYPE
        SYNTAX      IpeStatsInfo
        ACCESS      read-only
        STATUS      mandatory
        DESCRIPTION
            "RMON 15min RX 65 to 127 Octs Status. 'invalid' means the
             corresponding monitoring value is not reliable because of the
             alarm or other reasons. 'maintenance' means that some maintenance
             functions are executed on the current interval."
        ::= { rmon15minPort2Entry 22 }
    
    
    -- 1.3.6.1.4.1.119.2.3.69.203.513.501.11.1.1.2.1.24
    rmon15minHCTxEthStatsPkts65to127Octets2Status OBJECT-TYPE
        SYNTAX      IpeStatsInfo
        ACCESS      read-only
        STATUS      mandatory
        DESCRIPTION
            "RMON 15min TX 65 to 127 Octs Status. 'invalid' means the
             corresponding monitoring value is not reliable because of the
             alarm or other reasons. 'maintenance' means that some maintenance
             functions are executed on the current interval."
        ::= { rmon15minPort2Entry 24 }
    
    
    -- 1.3.6.1.4.1.119.2.3.69.203.513.501.11.1.1.2.1.26
    rmon15minHCRxEthStatsPkts128to255Octets2Status OBJECT-TYPE
        SYNTAX      IpeStatsInfo
        ACCESS      read-only
        STATUS      mandatory
        DESCRIPTION
            "RMON 15min RX 128 to 255 Octs Status. 'invalid' means the
             corresponding monitoring value is not reliable because of the
             alarm or other reasons. 'maintenance' means that some maintenance
             functions are executed on the current interval."
        ::= { rmon15minPort2Entry 26 }
    
    
    -- 1.3.6.1.4.1.119.2.3.69.203.513.501.11.1.1.2.1.28
    rmon15minHCTxEthStatsPkts128to255Octets2Status OBJECT-TYPE
        SYNTAX      IpeStatsInfo
        ACCESS      read-only
        STATUS      mandatory
        DESCRIPTION
            "RMON 15min TX 128 to 255 Octs Status. 'invalid' means the
             corresponding monitoring value is not reliable because of the
             alarm or other reasons. 'maintenance' means that some maintenance
             functions are executed on the current interval."
        ::= { rmon15minPort2Entry 28 }
    
    
    -- 1.3.6.1.4.1.119.2.3.69.203.513.501.11.1.1.2.1.30
    rmon15minHCRxEthStatsPkts256to511Octets2Status OBJECT-TYPE
        SYNTAX      IpeStatsInfo
        ACCESS      read-only
        STATUS      mandatory
        DESCRIPTION
            "RMON 15min RX 256 to 511 Octs Status. 'invalid' means the
             corresponding monitoring value is not reliable because of the
             alarm or other reasons. 'maintenance' means that some maintenance
             functions are executed on the current interval."
        ::= { rmon15minPort2Entry 30 }
    
    
    -- 1.3.6.1.4.1.119.2.3.69.203.513.501.11.1.1.2.1.32
    rmon15minHCTxEthStatsPkts256to511Octets2Status OBJECT-TYPE
        SYNTAX      IpeStatsInfo
        ACCESS      read-only
        STATUS      mandatory
        DESCRIPTION
            "RMON 15min TX 256 to 511 Octs Status. 'invalid' means the
             corresponding monitoring value is not reliable because of the
             alarm or other reasons. 'maintenance' means that some maintenance
             functions are executed on the current interval."
        ::= { rmon15minPort2Entry 32 }
    
    
    -- 1.3.6.1.4.1.119.2.3.69.203.513.501.11.1.1.2.1.34
    rmon15minHCRxEthStatsPkts512to1023Octets2Status OBJECT-TYPE
        SYNTAX      IpeStatsInfo
        ACCESS      read-only
        STATUS      mandatory
        DESCRIPTION
            "RMON 15min RX 512 to 1023 Octs Status. 'invalid' means the
             corresponding monitoring value is not reliable because of the
             alarm or other reasons. 'maintenance' means that some maintenance
             functions are executed on the current interval."
        ::= { rmon15minPort2Entry 34 }
    
    
    -- 1.3.6.1.4.1.119.2.3.69.203.513.501.11.1.1.2.1.36
    rmon15minHCTxEthStatsPkts512to1023Octets2Status OBJECT-TYPE
        SYNTAX      IpeStatsInfo
        ACCESS      read-only
        STATUS      mandatory
        DESCRIPTION
            "RMON 15min TX 512 to 1023 Octs Status. 'invalid' means the
             corresponding monitoring value is not reliable because of the
             alarm or other reasons. 'maintenance' means that some maintenance
             functions are executed on the current interval."
        ::= { rmon15minPort2Entry 36 }
    
    
    -- 1.3.6.1.4.1.119.2.3.69.203.513.501.11.1.1.2.1.38
    rmon15minHCRxEthStatsPkts1024to1518Octets2Status OBJECT-TYPE
        SYNTAX      IpeStatsInfo
        ACCESS      read-only
        STATUS      mandatory
        DESCRIPTION
            "RMON 15min RX 1024 to 1518 Octs Status. 'invalid' means the
             corresponding monitoring value is not reliable because of the
             alarm or other reasons. 'maintenance' means that some maintenance
             functions are executed on the current interval."
        ::= { rmon15minPort2Entry 38 }
    
    
    -- 1.3.6.1.4.1.119.2.3.69.203.513.501.11.1.1.2.1.40
    rmon15minHCTxEthStatsPkts1024to1518Octets2Status OBJECT-TYPE
        SYNTAX      IpeStatsInfo
        ACCESS      read-only
        STATUS      mandatory
        DESCRIPTION
            "RMON 15min TX 1024 to 1518 Octs Status. 'invalid' means the
             corresponding monitoring value is not reliable because of the
             alarm or other reasons. 'maintenance' means that some maintenance
             functions are executed on the current interval."
        ::= { rmon15minPort2Entry 40 }
    
    -- 1.3.6.1.4.1.119.2.3.69.203.513.501.11.1.1.2.1.41
    rmon15minRxEthStatsCRCAlignErrors2 OBJECT-TYPE
        SYNTAX      Counter
        ACCESS      read-only
        STATUS      mandatory
        DESCRIPTION
            "RMON 15min RX CRC Alignment Errors"
        ::= { rmon15minPort2Entry 41 }
    
    -- 1.3.6.1.4.1.119.2.3.69.203.513.501.11.1.1.2.1.42
    rmon15minRxEthStatsCRCAlignErrors2Status OBJECT-TYPE
        SYNTAX      IpeStatsInfo
        ACCESS      read-only
        STATUS      mandatory
        DESCRIPTION
            "RMON 15min RX CRC Alignment Errors Status. 'invalid' means the
             corresponding monitoring value is not reliable because of the
             alarm or other reasons. 'maintenance' means that some maintenance
             functions are executed on the current interval."
        ::= { rmon15minPort2Entry 42 }
    
    -- 1.3.6.1.4.1.119.2.3.69.203.513.501.11.1.1.2.1.43
    rmon15minRxEthStatsOversizePkts2 OBJECT-TYPE
        SYNTAX      Counter
        ACCESS      read-only
        STATUS      mandatory
        DESCRIPTION
            "RMON 15min RX Oversize Pkts"
        ::= { rmon15minPort2Entry 43 }
    
    -- 1.3.6.1.4.1.119.2.3.69.203.513.501.11.1.1.2.1.44
    rmon15minRxEthStatsOversizePkts2Status OBJECT-TYPE
        SYNTAX      IpeStatsInfo
        ACCESS      read-only
        STATUS      mandatory
        DESCRIPTION
            "RMON 15min RX Oversize Pkts Status. 'invalid' means the
             corresponding monitoring value is not reliable because of the
             alarm or other reasons. 'maintenance' means that some maintenance
             functions are executed on the current interval."
        ::= { rmon15minPort2Entry 44 }
    
    -- 1.3.6.1.4.1.119.2.3.69.203.513.501.11.1.1.2.1.45
    rmon15minRxEthStatsJabbers2 OBJECT-TYPE
        SYNTAX      Counter
        ACCESS      read-only
        STATUS      mandatory
        DESCRIPTION
            "RMON 15min RX Jabbers"
        ::= { rmon15minPort2Entry 45 }
    
    -- 1.3.6.1.4.1.119.2.3.69.203.513.501.11.1.1.2.1.46
    rmon15minRxEthStatsJabbers2Status OBJECT-TYPE
        SYNTAX      IpeStatsInfo
        ACCESS      read-only
        STATUS      mandatory
        DESCRIPTION
            "RMON 15min RX Jabbers Status. 'invalid' means the corresponding
             monitoring value is not reliable because of the alarm or other
             reasons. 'maintenance' means that some maintenance functions are
             executed on the current interval."
        ::= { rmon15minPort2Entry 46 }
    
    -- 1.3.6.1.4.1.119.2.3.69.203.513.501.11.1.1.2.1.47
    rmon15minRxEthStatsMulticastPkts2 OBJECT-TYPE
        SYNTAX      Counter
        ACCESS      read-only
        STATUS      mandatory
        DESCRIPTION
            "RMON 15min RX Multicast Pkts"
        ::= { rmon15minPort2Entry 47 }
    
    -- 1.3.6.1.4.1.119.2.3.69.203.513.501.11.1.1.2.1.48
    rmon15minRxEthStatsMulticastPkts2Status OBJECT-TYPE
        SYNTAX      IpeStatsInfo
        ACCESS      read-only
        STATUS      mandatory
        DESCRIPTION
            "RMON 15min RX Multicast Pkts Status. 'invalid' means the
             corresponding monitoring value is not reliable because of the
             alarm or other reasons. 'maintenance' means that some maintenance
             functions are executed on the current interval."
        ::= { rmon15minPort2Entry 48 }
    
    -- 1.3.6.1.4.1.119.2.3.69.203.513.501.11.1.1.2.1.49
    rmon15minTxEthStatsMulticastPkts2 OBJECT-TYPE
        SYNTAX      Counter
        ACCESS      read-only
        STATUS      mandatory
        DESCRIPTION
            "RMON 15min TX Multicast Pkts"
        ::= { rmon15minPort2Entry 49 }
    
    -- 1.3.6.1.4.1.119.2.3.69.203.513.501.11.1.1.2.1.50
    rmon15minTxEthStatsMulticastPkts2Status OBJECT-TYPE
        SYNTAX      IpeStatsInfo
        ACCESS      read-only
        STATUS      mandatory
        DESCRIPTION
            "RMON 15min TX Multicast Pkts Status. 'invalid' means the
             corresponding monitoring value is not reliable because of the
             alarm or other reasons. 'maintenance' means that some maintenance
             functions are executed on the current interval."
        ::= { rmon15minPort2Entry 50 }
    
    -- 1.3.6.1.4.1.119.2.3.69.203.513.501.11.1.1.2.1.51
    rmon15minRxEthStatsBroadcastPkts2 OBJECT-TYPE
        SYNTAX      Counter
        ACCESS      read-only
        STATUS      mandatory
        DESCRIPTION
            "RMON 15min RX Broadcast Pkts"
        ::= { rmon15minPort2Entry 51 }
    
    -- 1.3.6.1.4.1.119.2.3.69.203.513.501.11.1.1.2.1.52
    rmon15minRxEthStatsBroadcastPkts2Status OBJECT-TYPE
        SYNTAX      IpeStatsInfo
        ACCESS      read-only
        STATUS      mandatory
        DESCRIPTION
            "RMON 15min RX Broadcast Pkts Status. 'invalid' means the
             corresponding monitoring value is not reliable because of the
             alarm or other reasons. 'maintenance' means that some maintenance
             functions are executed on the current interval."
        ::= { rmon15minPort2Entry 52 }
    
    -- 1.3.6.1.4.1.119.2.3.69.203.513.501.11.1.1.2.1.53
    rmon15minTxEthStatsBroadcastPkts2 OBJECT-TYPE
        SYNTAX      Counter
        ACCESS      read-only
        STATUS      mandatory
        DESCRIPTION
            "RMON 15min TX Broadcast Pkts"
        ::= { rmon15minPort2Entry 53 }
    
    -- 1.3.6.1.4.1.119.2.3.69.203.513.501.11.1.1.2.1.54
    rmon15minTxEthStatsBroadcastPkts2Status OBJECT-TYPE
        SYNTAX      IpeStatsInfo
        ACCESS      read-only
        STATUS      mandatory
        DESCRIPTION
            "RMON 15min TX Broadcast Pkts Status. 'invalid' means the
             corresponding monitoring value is not reliable because of the
             alarm or other reasons. 'maintenance' means that some maintenance
             functions are executed on the current interval."
        ::= { rmon15minPort2Entry 54 }
    
    -- 1.3.6.1.4.1.119.2.3.69.203.513.501.11.1.1.2.1.55
    rmon15minTxEthStatsCollisions2 OBJECT-TYPE
        SYNTAX      Counter
        ACCESS      read-only
        STATUS      mandatory
        DESCRIPTION
            "RMON 15min TX Collisions"
        ::= { rmon15minPort2Entry 55 }
    
    -- 1.3.6.1.4.1.119.2.3.69.203.513.501.11.1.1.2.1.56
    rmon15minTxEthStatsCollisions2Status OBJECT-TYPE
        SYNTAX      IpeStatsInfo
        ACCESS      read-only
        STATUS      mandatory
        DESCRIPTION
            "RMON 15min TX Collisions Status. 'invalid' means the
             corresponding monitoring value is not reliable because of the
             alarm or other reasons. 'maintenance' means that some maintenance
             functions are executed on the current interval."
        ::= { rmon15minPort2Entry 56 }
    
    
    -- 1.3.6.1.4.1.119.2.3.69.203.513.501.11.1.1.2.1.58
    rmon15minHCRxUnknownTPID2Status OBJECT-TYPE
        SYNTAX      IpeStatsInfo
        ACCESS      read-only
        STATUS      mandatory
        DESCRIPTION
            "RMON 15min Unknown TPID Status. 'invalid' means the
             corresponding monitoring value is not reliable because of the
             alarm or other reasons. 'maintenance' means that some maintenance
             functions are executed on the current interval."
        ::= { rmon15minPort2Entry 58 }
    
    
    -- 1.3.6.1.4.1.119.2.3.69.203.513.501.11.1.1.2.1.60
    rmon15minHCRxUnknownVID2Status OBJECT-TYPE
        SYNTAX      IpeStatsInfo
        ACCESS      read-only
        STATUS      mandatory
        DESCRIPTION
            "RMON 15min Unknown VID Status. 'invalid' means the corresponding
             monitoring value is not reliable because of the alarm or other
             reasons. 'maintenance' means that some maintenance functions are
             executed on the current interval."
        ::= { rmon15minPort2Entry 60 }
    
    
    -- 1.3.6.1.4.1.119.2.3.69.203.513.501.11.1.1.2.1.62
    rmon15minHCRxMAClimit2Status OBJECT-TYPE
        SYNTAX      IpeStatsInfo
        ACCESS      read-only
        STATUS      mandatory
        DESCRIPTION
            "RMON 15min RX MAC Limit Status. 'invalid' means the
             corresponding monitoring value is not reliable because of the
             alarm or other reasons. 'maintenance' means that some maintenance
             functions are executed on the current interval."
        ::= { rmon15minPort2Entry 62 }
    
    
    -- 1.3.6.1.4.1.119.2.3.69.203.513.501.11.1.1.2.1.64
    rmon15minHCRxFilterDiscard2Status OBJECT-TYPE
        SYNTAX      IpeStatsInfo
        ACCESS      read-only
        STATUS      mandatory
        DESCRIPTION
            "RMON 15min RX Filter Discard Status. 'invalid' means the
             corresponding monitoring value is not reliable because of the
             alarm or other reasons. 'maintenance' means that some maintenance
             functions are executed on the current interval."
        ::= { rmon15minPort2Entry 64 }
    
    
    -- 1.3.6.1.4.1.119.2.3.69.203.513.501.11.1.1.2.1.66
    rmon15minHCRxQoSDiscard2Status OBJECT-TYPE
        SYNTAX      IpeStatsInfo
        ACCESS      read-only
        STATUS      mandatory
        DESCRIPTION
            "RMON 15min RX QoS Discard Status. 'invalid' means the
             corresponding monitoring value is not reliable because of the
             alarm or other reasons. 'maintenance' means that some maintenance
             functions are executed on the current interval."
        ::= { rmon15minPort2Entry 66 }
    
    
    -- 1.3.6.1.4.1.119.2.3.69.203.513.501.11.1.1.2.1.68
    rmon15minHCTxQueue0Discard2Status OBJECT-TYPE
        SYNTAX      IpeStatsInfo
        ACCESS      read-only
        STATUS      mandatory
        DESCRIPTION
            "RMON 15min TX Queue0 Discard Status. 'invalid' means the
             corresponding monitoring value is not reliable because of the
             alarm or other reasons. 'maintenance' means that some maintenance
             functions are executed on the current interval."
        ::= { rmon15minPort2Entry 68 }
    
    
    -- 1.3.6.1.4.1.119.2.3.69.203.513.501.11.1.1.2.1.70
    rmon15minHCTxQueue1Discard2Status OBJECT-TYPE
        SYNTAX      IpeStatsInfo
        ACCESS      read-only
        STATUS      mandatory
        DESCRIPTION
            "RMON 15min TX Queue1 Discard Status. 'invalid' means the
             corresponding monitoring value is not reliable because of the
             alarm or other reasons. 'maintenance' means that some maintenance
             functions are executed on the current interval."
        ::= { rmon15minPort2Entry 70 }
    
    
    -- 1.3.6.1.4.1.119.2.3.69.203.513.501.11.1.1.2.1.72
    rmon15minHCTxQueue2Discard2Status OBJECT-TYPE
        SYNTAX      IpeStatsInfo
        ACCESS      read-only
        STATUS      mandatory
        DESCRIPTION
            "RMON 15min TX Queue2 Discard Status. 'invalid' means the
             corresponding monitoring value is not reliable because of the
             alarm or other reasons. 'maintenance' means that some maintenance
             functions are executed on the current interval."
        ::= { rmon15minPort2Entry 72 }
    
    
    -- 1.3.6.1.4.1.119.2.3.69.203.513.501.11.1.1.2.1.74
    rmon15minHCTxQueue3Discard2Status OBJECT-TYPE
        SYNTAX      IpeStatsInfo
        ACCESS      read-only
        STATUS      mandatory
        DESCRIPTION
            "RMON 15min TX Queue3 Discard Status. 'invalid' means the
             corresponding monitoring value is not reliable because of the
             alarm or other reasons. 'maintenance' means that some maintenance
             functions are executed on the current interval."
        ::= { rmon15minPort2Entry 74 }
    
    
    -- 1.3.6.1.4.1.119.2.3.69.203.513.501.11.1.1.2.1.76
    rmon15minHCTxQueue4Discard2Status OBJECT-TYPE
        SYNTAX      IpeStatsInfo
        ACCESS      read-only
        STATUS      mandatory
        DESCRIPTION
            "RMON 15min TX Queue4 Discard Status. 'invalid' means the
             corresponding monitoring value is not reliable because of the
             alarm or other reasons. 'maintenance' means that some maintenance
             functions are executed on the current interval."
        ::= { rmon15minPort2Entry 76 }
    
    
    -- 1.3.6.1.4.1.119.2.3.69.203.513.501.11.1.1.2.1.78
    rmon15minHCTxQueue5Discard2Status OBJECT-TYPE
        SYNTAX      IpeStatsInfo
        ACCESS      read-only
        STATUS      mandatory
        DESCRIPTION
            "RMON 15min TX Queue5 Discard Status. 'invalid' means the
             corresponding monitoring value is not reliable because of the
             alarm or other reasons. 'maintenance' means that some maintenance
             functions are executed on the current interval."
        ::= { rmon15minPort2Entry 78 }
    
    
    -- 1.3.6.1.4.1.119.2.3.69.203.513.501.11.1.1.2.1.80
    rmon15minHCTxQueue6Discard2Status OBJECT-TYPE
        SYNTAX      IpeStatsInfo
        ACCESS      read-only
        STATUS      mandatory
        DESCRIPTION
            "RMON 15min TX Queue6 Discard Status. 'invalid' means the
             corresponding monitoring value is not reliable because of the
             alarm or other reasons. 'maintenance' means that some maintenance
             functions are executed on the current interval."
        ::= { rmon15minPort2Entry 80 }
    
    
    -- 1.3.6.1.4.1.119.2.3.69.203.513.501.11.1.1.2.1.82
    rmon15minHCTxQueue7Discard2Status OBJECT-TYPE
        SYNTAX      IpeStatsInfo
        ACCESS      read-only
        STATUS      mandatory
        DESCRIPTION
            "RMON 15min TX Queue7 Discard Status. 'invalid' means the
             corresponding monitoring value is not reliable because of the
             alarm or other reasons. 'maintenance' means that some maintenance
             functions are executed on the current interval."
        ::= { rmon15minPort2Entry 82 }
    
    -- 1.3.6.1.4.1.119.2.3.69.203.513.501.11.1.1.2.1.83
    rmon15minTxEthStatsOversizePkts2 OBJECT-TYPE
        SYNTAX      Counter
        ACCESS      read-only
        STATUS      mandatory
        DESCRIPTION
            "RMON 15min TX Oversize Pkts."
        ::= { rmon15minPort2Entry 83 }
    
    -- 1.3.6.1.4.1.119.2.3.69.203.513.501.11.1.1.2.1.84
    rmon15minTxEthStatsOversizePkts2Status OBJECT-TYPE
        SYNTAX      IpeStatsInfo
        ACCESS      read-only
        STATUS      mandatory
        DESCRIPTION
            "RMON 15min TX Oversize Pkts Status. 'invalid' means the
             corresponding monitoring value is not reliable because of the
             alarm or other reasons. 'maintenance' means that some maintenance
             functions are executed on the current interval."
        ::= { rmon15minPort2Entry 84 }
    
    
    -- 1.3.6.1.4.1.119.2.3.69.203.513.501.11.1.1.2.1.86
    rmon15minHCTxFilterDiscard2Status OBJECT-TYPE
        SYNTAX      IpeStatsInfo
        ACCESS      read-only
        STATUS      mandatory
        DESCRIPTION
            "RMON 15min TX Filter Discard Status. 'invalid' means the
             corresponding monitoring value is not reliable because of the
             alarm or other reasons. 'maintenance' means that some maintenance
             functions are executed on the current interval."
        ::= { rmon15minPort2Entry 86 }
    
    -- 1.3.6.1.4.1.119.2.3.69.203.513.501.11.1.1.3
    rmon15minSfpDataTable OBJECT-TYPE
        SYNTAX      SEQUENCE OF Rmon15minSfpDataEntry
        ACCESS      not-accessible
        STATUS      mandatory
        DESCRIPTION
            "15minutes ETH Port Sfp Tx/Rx Power Monitoring Table"
        ::= { rmon15minPortGroup 3 }
    
    -- 1.3.6.1.4.1.119.2.3.69.203.513.501.11.1.1.3.1
    rmon15minSfpDataEntry OBJECT-TYPE
        SYNTAX      Rmon15minSfpDataEntry
        ACCESS      not-accessible
        STATUS      mandatory
        DESCRIPTION
            ""
        INDEX       { rmon15minSfpDataNEAddress, rmon15minSfpDataIfIndex }
        ::= { rmon15minSfpDataTable 1 }
    
    Rmon15minSfpDataEntry ::= SEQUENCE {
        rmon15minSfpDataIfIndex             InterfaceIndex,
        rmon15minSfpDataNEAddress           IpAddress,
        rmon15minSfpTxPowerDataStatusInfo   IpeStatsInfo,
        rmon15minSfpTxPowerData             DisplayString,
        rmon15minSfpRxPowerDataStatusInfo   IpeStatsInfo,
        rmon15minSfpRxPowerData             DisplayString
    }
    
    -- 1.3.6.1.4.1.119.2.3.69.203.513.501.11.1.1.3.1.1
    rmon15minSfpDataIfIndex OBJECT-TYPE
        SYNTAX      InterfaceIndex
        ACCESS      not-accessible
        STATUS      mandatory
        DESCRIPTION
            "Index of this table."
        ::= { rmon15minSfpDataEntry 1 }
    
    -- 1.3.6.1.4.1.119.2.3.69.203.513.501.11.1.1.3.1.2
    rmon15minSfpDataNEAddress OBJECT-TYPE
        SYNTAX      IpAddress
        ACCESS      not-accessible
        STATUS      mandatory
        DESCRIPTION
            "reserved"
        ::= { rmon15minSfpDataEntry 2 }
    
    -- 1.3.6.1.4.1.119.2.3.69.203.513.501.11.1.1.3.1.3
    rmon15minSfpTxPowerDataStatusInfo OBJECT-TYPE
        SYNTAX      IpeStatsInfo
        ACCESS      read-only
        STATUS      mandatory
        DESCRIPTION
            "15minutes ETH Port Sfp Tx Power."
        ::= { rmon15minSfpDataEntry 3 }
    
    -- 1.3.6.1.4.1.119.2.3.69.203.513.501.11.1.1.3.1.4
    rmon15minSfpTxPowerData OBJECT-TYPE
        SYNTAX      DisplayString
        ACCESS      read-only
        STATUS      mandatory
        DESCRIPTION
            "15minutes ETH Port Sfp Tx Power Status."
        ::= { rmon15minSfpDataEntry 4 }
    
    -- 1.3.6.1.4.1.119.2.3.69.203.513.501.11.1.1.3.1.5
    rmon15minSfpRxPowerDataStatusInfo OBJECT-TYPE
        SYNTAX      IpeStatsInfo
        ACCESS      read-only
        STATUS      mandatory
        DESCRIPTION
            "15minutes ETH Port Sfp Rx Power."
        ::= { rmon15minSfpDataEntry 5 }
    
    -- 1.3.6.1.4.1.119.2.3.69.203.513.501.11.1.1.3.1.6
    rmon15minSfpRxPowerData OBJECT-TYPE
        SYNTAX      DisplayString
        ACCESS      read-only
        STATUS      mandatory
        DESCRIPTION
            "15minutes ETH Port Sfp Rx Power Status."
        ::= { rmon15minSfpDataEntry 6 }
    
    -- 1.3.6.1.4.1.119.2.3.69.203.513.501.11.1.1.4
    rmon15minClassCounterGroup OBJECT IDENTIFIER
        ::= { rmon15minPortGroup 4 }
    
    -- 1.3.6.1.4.1.119.2.3.69.203.513.501.11.1.1.4.1
    rmon15minClassCounterTable OBJECT-TYPE
        SYNTAX      SEQUENCE OF Rmon15minClassCounterEntry
        ACCESS      not-accessible
        STATUS      mandatory
        DESCRIPTION
            "this table contains 64 bit counters for octets and packets per
             traffic class for 15minutes interval. The counted values are
             cleared when the interval is elapsed."
        ::= { rmon15minClassCounterGroup 1 }
    
    -- 1.3.6.1.4.1.119.2.3.69.203.513.501.11.1.1.4.1.1
    rmon15minClassCounterEntry OBJECT-TYPE
        SYNTAX      Rmon15minClassCounterEntry
        ACCESS      not-accessible
        STATUS      mandatory
        DESCRIPTION
            "this table contains 64 bit counters for octets and packets for
             15minutes interval."
        INDEX       { rmon15minClassCounterNEAddress, rmon15minClassCounterIfIndex }
        ::= { rmon15minClassCounterTable 1 }
    
    Rmon15minClassCounterEntry ::= SEQUENCE {
        rmon15minClassCounterIfIndex                InterfaceIndex,
        rmon15minClassCounterNEAddress              IpAddress,
        rmon15minClassCounterRxClass0OctetsStatus   IpeStatsInfo,
        rmon15minClassCounterTxClass0OctetsStatus   IpeStatsInfo,
        rmon15minClassCounterRxClass0PktsStatus     IpeStatsInfo,
        rmon15minClassCounterTxClass0PktsStatus     IpeStatsInfo,
        rmon15minClassCounterRxClass1OctetsStatus   IpeStatsInfo,
        rmon15minClassCounterTxClass1OctetsStatus   IpeStatsInfo,
        rmon15minClassCounterRxClass1PktsStatus     IpeStatsInfo,
        rmon15minClassCounterTxClass1PktsStatus     IpeStatsInfo,
        rmon15minClassCounterRxClass2OctetsStatus   IpeStatsInfo,
        rmon15minClassCounterTxClass2OctetsStatus   IpeStatsInfo,
        rmon15minClassCounterRxClass2PktsStatus     IpeStatsInfo,
        rmon15minClassCounterTxClass2PktsStatus     IpeStatsInfo,
        rmon15minClassCounterRxClass3OctetsStatus   IpeStatsInfo,
        rmon15minClassCounterTxClass3OctetsStatus   IpeStatsInfo,
        rmon15minClassCounterRxClass3PktsStatus     IpeStatsInfo,
        rmon15minClassCounterTxClass3PktsStatus     IpeStatsInfo,
        rmon15minClassCounterRxClass4OctetsStatus   IpeStatsInfo,
        rmon15minClassCounterTxClass4OctetsStatus   IpeStatsInfo,
        rmon15minClassCounterRxClass4PktsStatus     IpeStatsInfo,
        rmon15minClassCounterTxClass4PktsStatus     IpeStatsInfo,
        rmon15minClassCounterRxClass5OctetsStatus   IpeStatsInfo,
        rmon15minClassCounterTxClass5OctetsStatus   IpeStatsInfo,
        rmon15minClassCounterRxClass5PktsStatus     IpeStatsInfo,
        rmon15minClassCounterTxClass5PktsStatus     IpeStatsInfo,
        rmon15minClassCounterRxClass6OctetsStatus   IpeStatsInfo,
        rmon15minClassCounterTxClass6OctetsStatus   IpeStatsInfo,
        rmon15minClassCounterRxClass6PktsStatus     IpeStatsInfo,
        rmon15minClassCounterTxClass6PktsStatus     IpeStatsInfo,
        rmon15minClassCounterRxClass7OctetsStatus   IpeStatsInfo,
        rmon15minClassCounterTxClass7OctetsStatus   IpeStatsInfo,
        rmon15minClassCounterRxClass7PktsStatus     IpeStatsInfo,
        rmon15minClassCounterTxClass7PktsStatus     IpeStatsInfo
    }
    
    -- 1.3.6.1.4.1.119.2.3.69.203.513.501.11.1.1.4.1.1.1
    rmon15minClassCounterIfIndex OBJECT-TYPE
        SYNTAX      InterfaceIndex
        ACCESS      not-accessible
        STATUS      mandatory
        DESCRIPTION
            "Index of this table. The value is corresponding to refered
             physical or logical interfaces."
        ::= { rmon15minClassCounterEntry 1 }
    
    -- 1.3.6.1.4.1.119.2.3.69.203.513.501.11.1.1.4.1.1.2
    rmon15minClassCounterNEAddress OBJECT-TYPE
        SYNTAX      IpAddress
        ACCESS      not-accessible
        STATUS      mandatory
        DESCRIPTION
            "reserved."
        ::= { rmon15minClassCounterEntry 2 }
    
    
    -- 1.3.6.1.4.1.119.2.3.69.203.513.501.11.1.1.4.1.1.4
    rmon15minClassCounterRxClass0OctetsStatus OBJECT-TYPE
        SYNTAX      IpeStatsInfo
        ACCESS      read-only
        STATUS      mandatory
        DESCRIPTION
            "the monitering status for the counter."
        ::= { rmon15minClassCounterEntry 4 }
    
    
    -- 1.3.6.1.4.1.119.2.3.69.203.513.501.11.1.1.4.1.1.6
    rmon15minClassCounterTxClass0OctetsStatus OBJECT-TYPE
        SYNTAX      IpeStatsInfo
        ACCESS      read-only
        STATUS      mandatory
        DESCRIPTION
            "the monitering status for the counter."
        ::= { rmon15minClassCounterEntry 6 }
    
    
    -- 1.3.6.1.4.1.119.2.3.69.203.513.501.11.1.1.4.1.1.8
    rmon15minClassCounterRxClass0PktsStatus OBJECT-TYPE
        SYNTAX      IpeStatsInfo
        ACCESS      read-only
        STATUS      mandatory
        DESCRIPTION
            "the monitering status for the counter."
        ::= { rmon15minClassCounterEntry 8 }
    
    
    -- 1.3.6.1.4.1.119.2.3.69.203.513.501.11.1.1.4.1.1.10
    rmon15minClassCounterTxClass0PktsStatus OBJECT-TYPE
        SYNTAX      IpeStatsInfo
        ACCESS      read-only
        STATUS      mandatory
        DESCRIPTION
            "the monitering status for the counter."
        ::= { rmon15minClassCounterEntry 10 }
    
    
    -- 1.3.6.1.4.1.119.2.3.69.203.513.501.11.1.1.4.1.1.12
    rmon15minClassCounterRxClass1OctetsStatus OBJECT-TYPE
        SYNTAX      IpeStatsInfo
        ACCESS      read-only
        STATUS      mandatory
        DESCRIPTION
            "the monitering status for the counter."
        ::= { rmon15minClassCounterEntry 12 }
    
    
    -- 1.3.6.1.4.1.119.2.3.69.203.513.501.11.1.1.4.1.1.14
    rmon15minClassCounterTxClass1OctetsStatus OBJECT-TYPE
        SYNTAX      IpeStatsInfo
        ACCESS      read-only
        STATUS      mandatory
        DESCRIPTION
            "the monitering status for the counter."
        ::= { rmon15minClassCounterEntry 14 }
    
    
    -- 1.3.6.1.4.1.119.2.3.69.203.513.501.11.1.1.4.1.1.16
    rmon15minClassCounterRxClass1PktsStatus OBJECT-TYPE
        SYNTAX      IpeStatsInfo
        ACCESS      read-only
        STATUS      mandatory
        DESCRIPTION
            "the monitering status for the counter."
        ::= { rmon15minClassCounterEntry 16 }
    
    
    -- 1.3.6.1.4.1.119.2.3.69.203.513.501.11.1.1.4.1.1.18
    rmon15minClassCounterTxClass1PktsStatus OBJECT-TYPE
        SYNTAX      IpeStatsInfo
        ACCESS      read-only
        STATUS      mandatory
        DESCRIPTION
            "the monitering status for the counter."
        ::= { rmon15minClassCounterEntry 18 }
    
    
    -- 1.3.6.1.4.1.119.2.3.69.203.513.501.11.1.1.4.1.1.20
    rmon15minClassCounterRxClass2OctetsStatus OBJECT-TYPE
        SYNTAX      IpeStatsInfo
        ACCESS      read-only
        STATUS      mandatory
        DESCRIPTION
            "the monitering status for the counter."
        ::= { rmon15minClassCounterEntry 20 }
    
    
    -- 1.3.6.1.4.1.119.2.3.69.203.513.501.11.1.1.4.1.1.22
    rmon15minClassCounterTxClass2OctetsStatus OBJECT-TYPE
        SYNTAX      IpeStatsInfo
        ACCESS      read-only
        STATUS      mandatory
        DESCRIPTION
            "the monitering status for the counter."
        ::= { rmon15minClassCounterEntry 22 }
    
    
    -- 1.3.6.1.4.1.119.2.3.69.203.513.501.11.1.1.4.1.1.24
    rmon15minClassCounterRxClass2PktsStatus OBJECT-TYPE
        SYNTAX      IpeStatsInfo
        ACCESS      read-only
        STATUS      mandatory
        DESCRIPTION
            "the monitering status for the counter."
        ::= { rmon15minClassCounterEntry 24 }
    
    
    -- 1.3.6.1.4.1.119.2.3.69.203.513.501.11.1.1.4.1.1.26
    rmon15minClassCounterTxClass2PktsStatus OBJECT-TYPE
        SYNTAX      IpeStatsInfo
        ACCESS      read-only
        STATUS      mandatory
        DESCRIPTION
            "the monitering status for the counter."
        ::= { rmon15minClassCounterEntry 26 }
    
    
    -- 1.3.6.1.4.1.119.2.3.69.203.513.501.11.1.1.4.1.1.28
    rmon15minClassCounterRxClass3OctetsStatus OBJECT-TYPE
        SYNTAX      IpeStatsInfo
        ACCESS      read-only
        STATUS      mandatory
        DESCRIPTION
            "the monitering status for the counter."
        ::= { rmon15minClassCounterEntry 28 }
    
    
    -- 1.3.6.1.4.1.119.2.3.69.203.513.501.11.1.1.4.1.1.30
    rmon15minClassCounterTxClass3OctetsStatus OBJECT-TYPE
        SYNTAX      IpeStatsInfo
        ACCESS      read-only
        STATUS      mandatory
        DESCRIPTION
            "the monitering status for the counter."
        ::= { rmon15minClassCounterEntry 30 }
    
    
    -- 1.3.6.1.4.1.119.2.3.69.203.513.501.11.1.1.4.1.1.32
    rmon15minClassCounterRxClass3PktsStatus OBJECT-TYPE
        SYNTAX      IpeStatsInfo
        ACCESS      read-only
        STATUS      mandatory
        DESCRIPTION
            "the monitering status for the counter."
        ::= { rmon15minClassCounterEntry 32 }
    
    
    -- 1.3.6.1.4.1.119.2.3.69.203.513.501.11.1.1.4.1.1.34
    rmon15minClassCounterTxClass3PktsStatus OBJECT-TYPE
        SYNTAX      IpeStatsInfo
        ACCESS      read-only
        STATUS      mandatory
        DESCRIPTION
            "the monitering status for the counter."
        ::= { rmon15minClassCounterEntry 34 }
    
    
    -- 1.3.6.1.4.1.119.2.3.69.203.513.501.11.1.1.4.1.1.36
    rmon15minClassCounterRxClass4OctetsStatus OBJECT-TYPE
        SYNTAX      IpeStatsInfo
        ACCESS      read-only
        STATUS      mandatory
        DESCRIPTION
            "the monitering status for the counter."
        ::= { rmon15minClassCounterEntry 36 }
    
    
    -- 1.3.6.1.4.1.119.2.3.69.203.513.501.11.1.1.4.1.1.38
    rmon15minClassCounterTxClass4OctetsStatus OBJECT-TYPE
        SYNTAX      IpeStatsInfo
        ACCESS      read-only
        STATUS      mandatory
        DESCRIPTION
            "the monitering status for the counter."
        ::= { rmon15minClassCounterEntry 38 }
    
    
    -- 1.3.6.1.4.1.119.2.3.69.203.513.501.11.1.1.4.1.1.40
    rmon15minClassCounterRxClass4PktsStatus OBJECT-TYPE
        SYNTAX      IpeStatsInfo
        ACCESS      read-only
        STATUS      mandatory
        DESCRIPTION
            "the monitering status for the counter."
        ::= { rmon15minClassCounterEntry 40 }
    
    
    -- 1.3.6.1.4.1.119.2.3.69.203.513.501.11.1.1.4.1.1.42
    rmon15minClassCounterTxClass4PktsStatus OBJECT-TYPE
        SYNTAX      IpeStatsInfo
        ACCESS      read-only
        STATUS      mandatory
        DESCRIPTION
            "the monitering status for the counter."
        ::= { rmon15minClassCounterEntry 42 }
    
    
    -- 1.3.6.1.4.1.119.2.3.69.203.513.501.11.1.1.4.1.1.44
    rmon15minClassCounterRxClass5OctetsStatus OBJECT-TYPE
        SYNTAX      IpeStatsInfo
        ACCESS      read-only
        STATUS      mandatory
        DESCRIPTION
            "the monitering status for the counter."
        ::= { rmon15minClassCounterEntry 44 }
    
    
    -- 1.3.6.1.4.1.119.2.3.69.203.513.501.11.1.1.4.1.1.46
    rmon15minClassCounterTxClass5OctetsStatus OBJECT-TYPE
        SYNTAX      IpeStatsInfo
        ACCESS      read-only
        STATUS      mandatory
        DESCRIPTION
            "the monitering status for the counter."
        ::= { rmon15minClassCounterEntry 46 }
    
    
    -- 1.3.6.1.4.1.119.2.3.69.203.513.501.11.1.1.4.1.1.48
    rmon15minClassCounterRxClass5PktsStatus OBJECT-TYPE
        SYNTAX      IpeStatsInfo
        ACCESS      read-only
        STATUS      mandatory
        DESCRIPTION
            "the monitering status for the counter."
        ::= { rmon15minClassCounterEntry 48 }
    
    
    -- 1.3.6.1.4.1.119.2.3.69.203.513.501.11.1.1.4.1.1.50
    rmon15minClassCounterTxClass5PktsStatus OBJECT-TYPE
        SYNTAX      IpeStatsInfo
        ACCESS      read-only
        STATUS      mandatory
        DESCRIPTION
            "the monitering status for the counter."
        ::= { rmon15minClassCounterEntry 50 }
    
    
    -- 1.3.6.1.4.1.119.2.3.69.203.513.501.11.1.1.4.1.1.52
    rmon15minClassCounterRxClass6OctetsStatus OBJECT-TYPE
        SYNTAX      IpeStatsInfo
        ACCESS      read-only
        STATUS      mandatory
        DESCRIPTION
            "the monitering status for the counter."
        ::= { rmon15minClassCounterEntry 52 }
    
    
    -- 1.3.6.1.4.1.119.2.3.69.203.513.501.11.1.1.4.1.1.54
    rmon15minClassCounterTxClass6OctetsStatus OBJECT-TYPE
        SYNTAX      IpeStatsInfo
        ACCESS      read-only
        STATUS      mandatory
        DESCRIPTION
            "the monitering status for the counter."
        ::= { rmon15minClassCounterEntry 54 }
    
    
    -- 1.3.6.1.4.1.119.2.3.69.203.513.501.11.1.1.4.1.1.56
    rmon15minClassCounterRxClass6PktsStatus OBJECT-TYPE
        SYNTAX      IpeStatsInfo
        ACCESS      read-only
        STATUS      mandatory
        DESCRIPTION
            "the monitering status for the counter."
        ::= { rmon15minClassCounterEntry 56 }
    
    
    -- 1.3.6.1.4.1.119.2.3.69.203.513.501.11.1.1.4.1.1.58
    rmon15minClassCounterTxClass6PktsStatus OBJECT-TYPE
        SYNTAX      IpeStatsInfo
        ACCESS      read-only
        STATUS      mandatory
        DESCRIPTION
            "the monitering status for the counter."
        ::= { rmon15minClassCounterEntry 58 }
    
    
    -- 1.3.6.1.4.1.119.2.3.69.203.513.501.11.1.1.4.1.1.60
    rmon15minClassCounterRxClass7OctetsStatus OBJECT-TYPE
        SYNTAX      IpeStatsInfo
        ACCESS      read-only
        STATUS      mandatory
        DESCRIPTION
            "the monitering status for the counter."
        ::= { rmon15minClassCounterEntry 60 }
    
    
    -- 1.3.6.1.4.1.119.2.3.69.203.513.501.11.1.1.4.1.1.62
    rmon15minClassCounterTxClass7OctetsStatus OBJECT-TYPE
        SYNTAX      IpeStatsInfo
        ACCESS      read-only
        STATUS      mandatory
        DESCRIPTION
            "the monitering status for the counter."
        ::= { rmon15minClassCounterEntry 62 }
    
    
    -- 1.3.6.1.4.1.119.2.3.69.203.513.501.11.1.1.4.1.1.64
    rmon15minClassCounterRxClass7PktsStatus OBJECT-TYPE
        SYNTAX      IpeStatsInfo
        ACCESS      read-only
        STATUS      mandatory
        DESCRIPTION
            "the monitering status for the counter."
        ::= { rmon15minClassCounterEntry 64 }
    
    
    -- 1.3.6.1.4.1.119.2.3.69.203.513.501.11.1.1.4.1.1.66
    rmon15minClassCounterTxClass7PktsStatus OBJECT-TYPE
        SYNTAX      IpeStatsInfo
        ACCESS      read-only
        STATUS      mandatory
        DESCRIPTION
            "the monitering status for the counter."
        ::= { rmon15minClassCounterEntry 66 }
    
    -- 1.3.6.1.4.1.119.2.3.69.203.513.501.11.1.2
    rmon1dayportGroup OBJECT IDENTIFIER
        ::= { rmonEthGroup 2 }
    
    -- 1.3.6.1.4.1.119.2.3.69.203.513.501.11.1.2.2
    rmon1dayPort2Table OBJECT-TYPE
        SYNTAX      SEQUENCE OF Rmon1dayPort2Entry
        ACCESS      not-accessible
        STATUS      mandatory
        DESCRIPTION
            "RMON 1day Port Monitoring Table."
        ::= { rmon1dayportGroup 2 }
    
    -- 1.3.6.1.4.1.119.2.3.69.203.513.501.11.1.2.2.1
    rmon1dayPort2Entry OBJECT-TYPE
        SYNTAX      Rmon1dayPort2Entry
        ACCESS      not-accessible
        STATUS      mandatory
        DESCRIPTION
            ""
        INDEX       { rmon1dayPort2NEAddress, rmon1dayPort2IfIndex }
        ::= { rmon1dayPort2Table 1 }
    
    Rmon1dayPort2Entry ::= SEQUENCE {
        rmon1dayPort2IfIndex                                InterfaceIndex,
        rmon1dayPort2NEAddress                              IpAddress,
        rmon1dayHCRxEthStatsOctets2Status                   IpeStatsInfo,
        rmon1dayHCTxEthStatsOctets2Status                   IpeStatsInfo,
        rmon1dayHCRxEthStatsPkts2Status                     IpeStatsInfo,
        rmon1dayHCTxEthStatsPkts2Status                     IpeStatsInfo,
        rmon1dayRxEthStatsDropEvents2                       Counter,
        rmon1dayRxEthStatsDropEvents2Status                 IpeStatsInfo,
        rmon1dayRxEthStatsUndersizePkts2                    Counter,
        rmon1dayRxEthStatsUndersizePkts2Status              IpeStatsInfo,
        rmon1dayRxEthStatsFragments2                        Counter,
        rmon1dayRxEthStatsFragments2Status                  IpeStatsInfo,
        rmon1dayHCRxEthStatsPkts64Octets2Status             IpeStatsInfo,
        rmon1dayHCTxEthStatsPkts64Octets2Status             IpeStatsInfo,
        rmon1dayHCRxEthStatsPkts65to127Octets2Status        IpeStatsInfo,
        rmon1dayHCTxEthStatsPkts65to127Octets2Status        IpeStatsInfo,
        rmon1dayHCRxEthStatsPkts128to255Octets2Status       IpeStatsInfo,
        rmon1dayHCTxEthStatsPkts128to255Octets2Status       IpeStatsInfo,
        rmon1dayHCRxEthStatsPkts256to511Octets2Status       IpeStatsInfo,
        rmon1dayHCTxEthStatsPkts256to511Octets2Status       IpeStatsInfo,
        rmon1dayHCRxEthStatsPkts512to1023Octets2Status      IpeStatsInfo,
        rmon1dayHCTxEthStatsPkts512to1023Octets2Status      IpeStatsInfo,
        rmon1dayHCRxEthStatsPkts1024to1518Octets2Status     IpeStatsInfo,
        rmon1dayHCTxEthStatsPkts1024to1518Octets2Status     IpeStatsInfo,
        rmon1dayRxEthStatsCRCAlignErrors2                   Counter,
        rmon1dayRxEthStatsCRCAlignErrors2Status             IpeStatsInfo,
        rmon1dayRxEthStatsOversizePkts2                     Counter,
        rmon1dayRxEthStatsOversizePkts2Status               IpeStatsInfo,
        rmon1dayRxEthStatsJabbers2                          Counter,
        rmon1dayRxEthStatsJabbers2Status                    IpeStatsInfo,
        rmon1dayRxEthStatsMulticastPkts2                    Counter,
        rmon1dayRxEthStatsMulticastPkts2Status              IpeStatsInfo,
        rmon1dayTxEthStatsMulticastPkts2                    Counter,
        rmon1dayTxEthStatsMulticastPkts2Status              IpeStatsInfo,
        rmon1dayRxEthStatsBroadcastPkts2                    Counter,
        rmon1dayRxEthStatsBroadcastPkts2Status              IpeStatsInfo,
        rmon1dayTxEthStatsBroadcastPkts2                    Counter,
        rmon1dayTxEthStatsBroadcastPkts2Status              IpeStatsInfo,
        rmon1dayTxEthStatsCollisions2                       Counter,
        rmon1dayTxEthStatsCollisions2Status                 IpeStatsInfo,
        rmon1dayHCRxUnknownTPID2Status                      IpeStatsInfo,
        rmon1dayHCRxUnknownVID2Status                       IpeStatsInfo,
        rmon1dayHCRxMAClimit2Status                         IpeStatsInfo,
        rmon1dayHCRxFilterDiscard2Status                    IpeStatsInfo,
        rmon1dayHCRxQoSDiscard2Status                       IpeStatsInfo,
        rmon1dayHCTxQueue0Discard2Status                    IpeStatsInfo,
        rmon1dayHCTxQueue1Discard2Status                    IpeStatsInfo,
        rmon1dayHCTxQueue2Discard2Status                    IpeStatsInfo,
        rmon1dayHCTxQueue3Discard2Status                    IpeStatsInfo,
        rmon1dayHCTxQueue4Discard2Status                    IpeStatsInfo,
        rmon1dayHCTxQueue5Discard2Status                    IpeStatsInfo,
        rmon1dayHCTxQueue6Discard2Status                    IpeStatsInfo,
        rmon1dayHCTxQueue7Discard2Status                    IpeStatsInfo,
        rmon1dayTxEthStatsOversizePkts2                     Counter,
        rmon1dayTxEthStatsOversizePkts2Status               IpeStatsInfo,
        rmon1dayHCTxFilterDiscard2Status                    IpeStatsInfo
    }
    
    -- 1.3.6.1.4.1.119.2.3.69.203.513.501.11.1.2.2.1.1
    rmon1dayPort2IfIndex OBJECT-TYPE
        SYNTAX      InterfaceIndex
        ACCESS      not-accessible
        STATUS      mandatory
        DESCRIPTION
            "Index of this table."
        ::= { rmon1dayPort2Entry 1 }
    
    -- 1.3.6.1.4.1.119.2.3.69.203.513.501.11.1.2.2.1.2
    rmon1dayPort2NEAddress OBJECT-TYPE
        SYNTAX      IpAddress
        ACCESS      not-accessible
        STATUS      mandatory
        DESCRIPTION
            "reserved."
        ::= { rmon1dayPort2Entry 2 }
    
    
    -- 1.3.6.1.4.1.119.2.3.69.203.513.501.11.1.2.2.1.4
    rmon1dayHCRxEthStatsOctets2Status OBJECT-TYPE
        SYNTAX      IpeStatsInfo
        ACCESS      read-only
        STATUS      mandatory
        DESCRIPTION
            "RMON 1day RX Octs Status. 'invalid' means the corresponding
             monitoring value is not reliable because of the alarm or other
             reasons. 'maintenance' means that some maintenance functions are
             executed on the current interval."
        ::= { rmon1dayPort2Entry 4 }
    
    
    -- 1.3.6.1.4.1.119.2.3.69.203.513.501.11.1.2.2.1.6
    rmon1dayHCTxEthStatsOctets2Status OBJECT-TYPE
        SYNTAX      IpeStatsInfo
        ACCESS      read-only
        STATUS      mandatory
        DESCRIPTION
            "RMON 1day TX Octs Status. 'invalid' means the corresponding
             monitoring value is not reliable because of the alarm or other
             reasons. 'maintenance' means that some maintenance functions are
             executed on the current interval."
        ::= { rmon1dayPort2Entry 6 }
    
    
    -- 1.3.6.1.4.1.119.2.3.69.203.513.501.11.1.2.2.1.8
    rmon1dayHCRxEthStatsPkts2Status OBJECT-TYPE
        SYNTAX      IpeStatsInfo
        ACCESS      read-only
        STATUS      mandatory
        DESCRIPTION
            "RMON 1day RX Pkts Status. 'invalid' means the corresponding
             monitoring value is not reliable because of the alarm or other
             reasons. 'maintenance' means that some maintenance functions are
             executed on the current interval."
        ::= { rmon1dayPort2Entry 8 }
    
    
    -- 1.3.6.1.4.1.119.2.3.69.203.513.501.11.1.2.2.1.10
    rmon1dayHCTxEthStatsPkts2Status OBJECT-TYPE
        SYNTAX      IpeStatsInfo
        ACCESS      read-only
        STATUS      mandatory
        DESCRIPTION
            "RMON 1day TX Pkts Status. 'invalid' means the corresponding
             monitoring value is not reliable because of the alarm or other
             reasons. 'maintenance' means that some maintenance functions are
             executed on the current interval."
        ::= { rmon1dayPort2Entry 10 }
    
    -- 1.3.6.1.4.1.119.2.3.69.203.513.501.11.1.2.2.1.11
    rmon1dayRxEthStatsDropEvents2 OBJECT-TYPE
        SYNTAX      Counter
        ACCESS      read-only
        STATUS      mandatory
        DESCRIPTION
            "RMON 1day RX Drop Events"
        ::= { rmon1dayPort2Entry 11 }
    
    -- 1.3.6.1.4.1.119.2.3.69.203.513.501.11.1.2.2.1.12
    rmon1dayRxEthStatsDropEvents2Status OBJECT-TYPE
        SYNTAX      IpeStatsInfo
        ACCESS      read-only
        STATUS      mandatory
        DESCRIPTION
            "RMON 1day RX Drop Events Status. 'invalid' means the
             corresponding monitoring value is not reliable because of the
             alarm or other reasons. 'maintenance' means that some maintenance
             functions are executed on the current interval."
        ::= { rmon1dayPort2Entry 12 }
    
    -- 1.3.6.1.4.1.119.2.3.69.203.513.501.11.1.2.2.1.13
    rmon1dayRxEthStatsUndersizePkts2 OBJECT-TYPE
        SYNTAX      Counter
        ACCESS      read-only
        STATUS      mandatory
        DESCRIPTION
            "RMON 1day RX Undersize Pkts"
        ::= { rmon1dayPort2Entry 13 }
    
    -- 1.3.6.1.4.1.119.2.3.69.203.513.501.11.1.2.2.1.14
    rmon1dayRxEthStatsUndersizePkts2Status OBJECT-TYPE
        SYNTAX      IpeStatsInfo
        ACCESS      read-only
        STATUS      mandatory
        DESCRIPTION
            "RMON 1day RX Undersize Pkts Status. 'invalid' means the
             corresponding monitoring value is not reliable because of the
             alarm or other reasons. 'maintenance' means that some maintenance
             functions are executed on the current interval."
        ::= { rmon1dayPort2Entry 14 }
    
    -- 1.3.6.1.4.1.119.2.3.69.203.513.501.11.1.2.2.1.15
    rmon1dayRxEthStatsFragments2 OBJECT-TYPE
        SYNTAX      Counter
        ACCESS      read-only
        STATUS      mandatory
        DESCRIPTION
            "RMON 1day RX Fragments"
        ::= { rmon1dayPort2Entry 15 }
    
    -- 1.3.6.1.4.1.119.2.3.69.203.513.501.11.1.2.2.1.16
    rmon1dayRxEthStatsFragments2Status OBJECT-TYPE
        SYNTAX      IpeStatsInfo
        ACCESS      read-only
        STATUS      mandatory
        DESCRIPTION
            "RMON 1day RX Fragments Status. 'invalid' means the corresponding
             monitoring value is not reliable because of the alarm or other
             reasons. 'maintenance' means that some maintenance functions are
             executed on the current interval."
        ::= { rmon1dayPort2Entry 16 }
    
    
    -- 1.3.6.1.4.1.119.2.3.69.203.513.501.11.1.2.2.1.18
    rmon1dayHCRxEthStatsPkts64Octets2Status OBJECT-TYPE
        SYNTAX      IpeStatsInfo
        ACCESS      read-only
        STATUS      mandatory
        DESCRIPTION
            "RMON 1day RX 64 Octs Status. 'invalid' means the corresponding
             monitoring value is not reliable because of the alarm or other
             reasons. 'maintenance' means that some maintenance functions are
             executed on the current interval."
        ::= { rmon1dayPort2Entry 18 }
    
    
    -- 1.3.6.1.4.1.119.2.3.69.203.513.501.11.1.2.2.1.20
    rmon1dayHCTxEthStatsPkts64Octets2Status OBJECT-TYPE
        SYNTAX      IpeStatsInfo
        ACCESS      read-only
        STATUS      mandatory
        DESCRIPTION
            "RMON 1day TX 64 Octs Status. 'invalid' means the corresponding
             monitoring value is not reliable because of the alarm or other
             reasons. 'maintenance' means that some maintenance functions are
             executed on the current interval."
        ::= { rmon1dayPort2Entry 20 }
    
    
    -- 1.3.6.1.4.1.119.2.3.69.203.513.501.11.1.2.2.1.22
    rmon1dayHCRxEthStatsPkts65to127Octets2Status OBJECT-TYPE
        SYNTAX      IpeStatsInfo
        ACCESS      read-only
        STATUS      mandatory
        DESCRIPTION
            "RMON 1day RX 65 to 127 Octs Status. 'invalid' means the
             corresponding monitoring value is not reliable because of the
             alarm or other reasons. 'maintenance' means that some maintenance
             functions are executed on the current interval."
        ::= { rmon1dayPort2Entry 22 }
    
    
    -- 1.3.6.1.4.1.119.2.3.69.203.513.501.11.1.2.2.1.24
    rmon1dayHCTxEthStatsPkts65to127Octets2Status OBJECT-TYPE
        SYNTAX      IpeStatsInfo
        ACCESS      read-only
        STATUS      mandatory
        DESCRIPTION
            "RMON 1day TX 65 to 127 Octs Status. 'invalid' means the
             corresponding monitoring value is not reliable because of the
             alarm or other reasons. 'maintenance' means that some maintenance
             functions are executed on the current interval."
        ::= { rmon1dayPort2Entry 24 }
    
    
    -- 1.3.6.1.4.1.119.2.3.69.203.513.501.11.1.2.2.1.26
    rmon1dayHCRxEthStatsPkts128to255Octets2Status OBJECT-TYPE
        SYNTAX      IpeStatsInfo
        ACCESS      read-only
        STATUS      mandatory
        DESCRIPTION
            "RMON 1day RX 128 to 255 Octs Status. 'invalid' means the
             corresponding monitoring value is not reliable because of the
             alarm or other reasons. 'maintenance' means that some maintenance
             functions are executed on the current interval."
        ::= { rmon1dayPort2Entry 26 }
    
    
    -- 1.3.6.1.4.1.119.2.3.69.203.513.501.11.1.2.2.1.28
    rmon1dayHCTxEthStatsPkts128to255Octets2Status OBJECT-TYPE
        SYNTAX      IpeStatsInfo
        ACCESS      read-only
        STATUS      mandatory
        DESCRIPTION
            "RMON 1day TX 128 to 255 Octs Status. 'invalid' means the
             corresponding monitoring value is not reliable because of the
             alarm or other reasons. 'maintenance' means that some maintenance
             functions are executed on the current interval."
        ::= { rmon1dayPort2Entry 28 }
    
    
    -- 1.3.6.1.4.1.119.2.3.69.203.513.501.11.1.2.2.1.30
    rmon1dayHCRxEthStatsPkts256to511Octets2Status OBJECT-TYPE
        SYNTAX      IpeStatsInfo
        ACCESS      read-only
        STATUS      mandatory
        DESCRIPTION
            "RMON 1day RX 256 to 511 Octs Status. 'invalid' means the
             corresponding monitoring value is not reliable because of the
             alarm or other reasons. 'maintenance' means that some maintenance
             functions are executed on the current interval."
        ::= { rmon1dayPort2Entry 30 }
    
    
    -- 1.3.6.1.4.1.119.2.3.69.203.513.501.11.1.2.2.1.32
    rmon1dayHCTxEthStatsPkts256to511Octets2Status OBJECT-TYPE
        SYNTAX      IpeStatsInfo
        ACCESS      read-only
        STATUS      mandatory
        DESCRIPTION
            "RMON 1day TX 256 to 511 Octs Status. 'invalid' means the
             corresponding monitoring value is not reliable because of the
             alarm or other reasons. 'maintenance' means that some maintenance
             functions are executed on the current interval."
        ::= { rmon1dayPort2Entry 32 }
    
    
    -- 1.3.6.1.4.1.119.2.3.69.203.513.501.11.1.2.2.1.34
    rmon1dayHCRxEthStatsPkts512to1023Octets2Status OBJECT-TYPE
        SYNTAX      IpeStatsInfo
        ACCESS      read-only
        STATUS      mandatory
        DESCRIPTION
            "RMON 1day RX 512 to 1023 Octs Status. 'invalid' means the
             corresponding monitoring value is not reliable because of the
             alarm or other reasons. 'maintenance' means that some maintenance
             functions are executed on the current interval."
        ::= { rmon1dayPort2Entry 34 }
    
    
    -- 1.3.6.1.4.1.119.2.3.69.203.513.501.11.1.2.2.1.36
    rmon1dayHCTxEthStatsPkts512to1023Octets2Status OBJECT-TYPE
        SYNTAX      IpeStatsInfo
        ACCESS      read-only
        STATUS      mandatory
        DESCRIPTION
            "RMON 1day TX 512 to 1023 Octs Status. 'invalid' means the
             corresponding monitoring value is not reliable because of the
             alarm or other reasons. 'maintenance' means that some maintenance
             functions are executed on the current interval."
        ::= { rmon1dayPort2Entry 36 }
    
    
    -- 1.3.6.1.4.1.119.2.3.69.203.513.501.11.1.2.2.1.38
    rmon1dayHCRxEthStatsPkts1024to1518Octets2Status OBJECT-TYPE
        SYNTAX      IpeStatsInfo
        ACCESS      read-only
        STATUS      mandatory
        DESCRIPTION
            "RMON 1day RX 1024 to 1518 Octs Status. 'invalid' means the
             corresponding monitoring value is not reliable because of the
             alarm or other reasons. 'maintenance' means that some maintenance
             functions are executed on the current interval."
        ::= { rmon1dayPort2Entry 38 }
    
    
    -- 1.3.6.1.4.1.119.2.3.69.203.513.501.11.1.2.2.1.40
    rmon1dayHCTxEthStatsPkts1024to1518Octets2Status OBJECT-TYPE
        SYNTAX      IpeStatsInfo
        ACCESS      read-only
        STATUS      mandatory
        DESCRIPTION
            "RMON 1day TX 1024 to 1518 Octs Status. 'invalid' means the
             corresponding monitoring value is not reliable because of the
             alarm or other reasons. 'maintenance' means that some maintenance
             functions are executed on the current interval."
        ::= { rmon1dayPort2Entry 40 }
    
    -- 1.3.6.1.4.1.119.2.3.69.203.513.501.11.1.2.2.1.41
    rmon1dayRxEthStatsCRCAlignErrors2 OBJECT-TYPE
        SYNTAX      Counter
        ACCESS      read-only
        STATUS      mandatory
        DESCRIPTION
            "RMON 1day RX CRC Alignment Errors"
        ::= { rmon1dayPort2Entry 41 }
    
    -- 1.3.6.1.4.1.119.2.3.69.203.513.501.11.1.2.2.1.42
    rmon1dayRxEthStatsCRCAlignErrors2Status OBJECT-TYPE
        SYNTAX      IpeStatsInfo
        ACCESS      read-only
        STATUS      mandatory
        DESCRIPTION
            "RMON 1day RX CRC Alignment Errors Status. 'invalid' means the
             corresponding monitoring value is not reliable because of the
             alarm or other reasons. 'maintenance' means that some maintenance
             functions are executed on the current interval."
        ::= { rmon1dayPort2Entry 42 }
    
    -- 1.3.6.1.4.1.119.2.3.69.203.513.501.11.1.2.2.1.43
    rmon1dayRxEthStatsOversizePkts2 OBJECT-TYPE
        SYNTAX      Counter
        ACCESS      read-only
        STATUS      mandatory
        DESCRIPTION
            "RMON 1day RX Oversize Pkts"
        ::= { rmon1dayPort2Entry 43 }
    
    -- 1.3.6.1.4.1.119.2.3.69.203.513.501.11.1.2.2.1.44
    rmon1dayRxEthStatsOversizePkts2Status OBJECT-TYPE
        SYNTAX      IpeStatsInfo
        ACCESS      read-only
        STATUS      mandatory
        DESCRIPTION
            "RMON 1day RX Oversize Pkts Status. 'invalid' means the
             corresponding monitoring value is not reliable because of the
             alarm or other reasons. 'maintenance' means that some maintenance
             functions are executed on the current interval."
        ::= { rmon1dayPort2Entry 44 }
    
    -- 1.3.6.1.4.1.119.2.3.69.203.513.501.11.1.2.2.1.45
    rmon1dayRxEthStatsJabbers2 OBJECT-TYPE
        SYNTAX      Counter
        ACCESS      read-only
        STATUS      mandatory
        DESCRIPTION
            "RMON 1day RX Jabbers"
        ::= { rmon1dayPort2Entry 45 }
    
    -- 1.3.6.1.4.1.119.2.3.69.203.513.501.11.1.2.2.1.46
    rmon1dayRxEthStatsJabbers2Status OBJECT-TYPE
        SYNTAX      IpeStatsInfo
        ACCESS      read-only
        STATUS      mandatory
        DESCRIPTION
            "RMON 1day RX Jabbers Status. 'invalid' means the corresponding
             monitoring value is not reliable because of the alarm or other
             reasons. 'maintenance' means that some maintenance functions are
             executed on the current interval."
        ::= { rmon1dayPort2Entry 46 }
    
    -- 1.3.6.1.4.1.119.2.3.69.203.513.501.11.1.2.2.1.47
    rmon1dayRxEthStatsMulticastPkts2 OBJECT-TYPE
        SYNTAX      Counter
        ACCESS      read-only
        STATUS      mandatory
        DESCRIPTION
            "RMON 1day RX Multicast Pkts"
        ::= { rmon1dayPort2Entry 47 }
    
    -- 1.3.6.1.4.1.119.2.3.69.203.513.501.11.1.2.2.1.48
    rmon1dayRxEthStatsMulticastPkts2Status OBJECT-TYPE
        SYNTAX      IpeStatsInfo
        ACCESS      read-only
        STATUS      mandatory
        DESCRIPTION
            "RMON 1day RX Multicast Pkts Status. 'invalid' means the
             corresponding monitoring value is not reliable because of the
             alarm or other reasons. 'maintenance' means that some maintenance
             functions are executed on the current interval."
        ::= { rmon1dayPort2Entry 48 }
    
    -- 1.3.6.1.4.1.119.2.3.69.203.513.501.11.1.2.2.1.49
    rmon1dayTxEthStatsMulticastPkts2 OBJECT-TYPE
        SYNTAX      Counter
        ACCESS      read-only
        STATUS      mandatory
        DESCRIPTION
            "RMON 1day TX Multicast Pkts."
        ::= { rmon1dayPort2Entry 49 }
    
    -- 1.3.6.1.4.1.119.2.3.69.203.513.501.11.1.2.2.1.50
    rmon1dayTxEthStatsMulticastPkts2Status OBJECT-TYPE
        SYNTAX      IpeStatsInfo
        ACCESS      read-only
        STATUS      mandatory
        DESCRIPTION
            "RMON 1day TX Multicast Pkts Status. 'invalid' means the
             corresponding monitoring value is not reliable because of the
             alarm or other reasons. 'maintenance' means that some maintenance
             functions are executed on the current interval."
        ::= { rmon1dayPort2Entry 50 }
    
    -- 1.3.6.1.4.1.119.2.3.69.203.513.501.11.1.2.2.1.51
    rmon1dayRxEthStatsBroadcastPkts2 OBJECT-TYPE
        SYNTAX      Counter
        ACCESS      read-only
        STATUS      mandatory
        DESCRIPTION
            "RMON 1day RX Broadcast Pkts."
        ::= { rmon1dayPort2Entry 51 }
    
    -- 1.3.6.1.4.1.119.2.3.69.203.513.501.11.1.2.2.1.52
    rmon1dayRxEthStatsBroadcastPkts2Status OBJECT-TYPE
        SYNTAX      IpeStatsInfo
        ACCESS      read-only
        STATUS      mandatory
        DESCRIPTION
            "RMON 1day RX Broadcast Pkts Status. 'invalid' means the
             corresponding monitoring value is not reliable because of the
             alarm or other reasons. 'maintenance' means that some maintenance
             functions are executed on the current interval."
        ::= { rmon1dayPort2Entry 52 }
    
    -- 1.3.6.1.4.1.119.2.3.69.203.513.501.11.1.2.2.1.53
    rmon1dayTxEthStatsBroadcastPkts2 OBJECT-TYPE
        SYNTAX      Counter
        ACCESS      read-only
        STATUS      mandatory
        DESCRIPTION
            "RMON 1day TX Broadcast Pkts."
        ::= { rmon1dayPort2Entry 53 }
    
    -- 1.3.6.1.4.1.119.2.3.69.203.513.501.11.1.2.2.1.54
    rmon1dayTxEthStatsBroadcastPkts2Status OBJECT-TYPE
        SYNTAX      IpeStatsInfo
        ACCESS      read-only
        STATUS      mandatory
        DESCRIPTION
            "RMON 1day TX Broadcast Pkts Status. 'invalid' means the
             corresponding monitoring value is not reliable because of the
             alarm or other reasons. 'maintenance' means that some maintenance
             functions are executed on the current interval."
        ::= { rmon1dayPort2Entry 54 }
    
    -- 1.3.6.1.4.1.119.2.3.69.203.513.501.11.1.2.2.1.55
    rmon1dayTxEthStatsCollisions2 OBJECT-TYPE
        SYNTAX      Counter
        ACCESS      read-only
        STATUS      mandatory
        DESCRIPTION
            "RMON 1day TX Collisions."
        ::= { rmon1dayPort2Entry 55 }
    
    -- 1.3.6.1.4.1.119.2.3.69.203.513.501.11.1.2.2.1.56
    rmon1dayTxEthStatsCollisions2Status OBJECT-TYPE
        SYNTAX      IpeStatsInfo
        ACCESS      read-only
        STATUS      mandatory
        DESCRIPTION
            "RMON 1day TX Collistions Status. 'invalid' means the
             corresponding monitoring value is not reliable because of the
             alarm or other reasons. 'maintenance' means that some maintenance
             functions are executed on the current interval."
        ::= { rmon1dayPort2Entry 56 }
    
    
    -- 1.3.6.1.4.1.119.2.3.69.203.513.501.11.1.2.2.1.58
    rmon1dayHCRxUnknownTPID2Status OBJECT-TYPE
        SYNTAX      IpeStatsInfo
        ACCESS      read-only
        STATUS      mandatory
        DESCRIPTION
            "RMON 1day RX Unknown TPID Status. 'invalid' means the
             corresponding monitoring value is not reliable because of the
             alarm or other reasons. 'maintenance' means that some maintenance
             functions are executed on the current interval."
        ::= { rmon1dayPort2Entry 58 }
    
    
    -- 1.3.6.1.4.1.119.2.3.69.203.513.501.11.1.2.2.1.60
    rmon1dayHCRxUnknownVID2Status OBJECT-TYPE
        SYNTAX      IpeStatsInfo
        ACCESS      read-only
        STATUS      mandatory
        DESCRIPTION
            "RMON 1day RX Unknown VID Status. 'invalid' means the
             corresponding monitoring value is not reliable because of the
             alarm or other reasons. 'maintenance' means that some maintenance
             functions are executed on the current interval."
        ::= { rmon1dayPort2Entry 60 }
    
    
    -- 1.3.6.1.4.1.119.2.3.69.203.513.501.11.1.2.2.1.62
    rmon1dayHCRxMAClimit2Status OBJECT-TYPE
        SYNTAX      IpeStatsInfo
        ACCESS      read-only
        STATUS      mandatory
        DESCRIPTION
            "RMON 1day RX MAC Limit Status. 'invalid' means the corresponding
             monitoring value is not reliable because of the alarm or other
             reasons. 'maintenance' means that some maintenance functions are
             executed on the current interval."
        ::= { rmon1dayPort2Entry 62 }
    
    
    -- 1.3.6.1.4.1.119.2.3.69.203.513.501.11.1.2.2.1.64
    rmon1dayHCRxFilterDiscard2Status OBJECT-TYPE
        SYNTAX      IpeStatsInfo
        ACCESS      read-only
        STATUS      mandatory
        DESCRIPTION
            "RMON 1day RX Filter Discard Status. 'invalid' means the
             corresponding monitoring value is not reliable because of the
             alarm or other reasons. 'maintenance' means that some maintenance
             functions are executed on the current interval."
        ::= { rmon1dayPort2Entry 64 }
    
    
    -- 1.3.6.1.4.1.119.2.3.69.203.513.501.11.1.2.2.1.66
    rmon1dayHCRxQoSDiscard2Status OBJECT-TYPE
        SYNTAX      IpeStatsInfo
        ACCESS      read-only
        STATUS      mandatory
        DESCRIPTION
            "RMON 1day RX QoS Discard Status. 'invalid' means the
             corresponding monitoring value is not reliable because of the
             alarm or other reasons. 'maintenance' means that some maintenance
             functions are executed on the current interval."
        ::= { rmon1dayPort2Entry 66 }
    
    
    -- 1.3.6.1.4.1.119.2.3.69.203.513.501.11.1.2.2.1.68
    rmon1dayHCTxQueue0Discard2Status OBJECT-TYPE
        SYNTAX      IpeStatsInfo
        ACCESS      read-only
        STATUS      mandatory
        DESCRIPTION
            "RMON 1day TX Queue0 Discard Status. 'invalid' means the
             corresponding monitoring value is not reliable because of the
             alarm or other reasons. 'maintenance' means that some maintenance
             functions are executed on the current interval."
        ::= { rmon1dayPort2Entry 68 }
    
    
    -- 1.3.6.1.4.1.119.2.3.69.203.513.501.11.1.2.2.1.70
    rmon1dayHCTxQueue1Discard2Status OBJECT-TYPE
        SYNTAX      IpeStatsInfo
        ACCESS      read-only
        STATUS      mandatory
        DESCRIPTION
            "RMON 1day TX Queue1 Discard Status. 'invalid' means the
             corresponding monitoring value is not reliable because of the
             alarm or other reasons. 'maintenance' means that some maintenance
             functions are executed on the current interval."
        ::= { rmon1dayPort2Entry 70 }
    
    
    -- 1.3.6.1.4.1.119.2.3.69.203.513.501.11.1.2.2.1.72
    rmon1dayHCTxQueue2Discard2Status OBJECT-TYPE
        SYNTAX      IpeStatsInfo
        ACCESS      read-only
        STATUS      mandatory
        DESCRIPTION
            "RMON 1day TX Queue2 Discard Status. 'invalid' means the
             corresponding monitoring value is not reliable because of the
             alarm or other reasons. 'maintenance' means that some maintenance
             functions are executed on the current interval."
        ::= { rmon1dayPort2Entry 72 }
    
    
    -- 1.3.6.1.4.1.119.2.3.69.203.513.501.11.1.2.2.1.74
    rmon1dayHCTxQueue3Discard2Status OBJECT-TYPE
        SYNTAX      IpeStatsInfo
        ACCESS      read-only
        STATUS      mandatory
        DESCRIPTION
            "RMON 1day TX Queue3 Discard Status. 'invalid' means the
             corresponding monitoring value is not reliable because of the
             alarm or other reasons. 'maintenance' means that some maintenance
             functions are executed on the current interval."
        ::= { rmon1dayPort2Entry 74 }
    
    
    -- 1.3.6.1.4.1.119.2.3.69.203.513.501.11.1.2.2.1.76
    rmon1dayHCTxQueue4Discard2Status OBJECT-TYPE
        SYNTAX      IpeStatsInfo
        ACCESS      read-only
        STATUS      mandatory
        DESCRIPTION
            "RMON 1day TX Queue4 Discard Status. 'invalid' means the
             corresponding monitoring value is not reliable because of the
             alarm or other reasons. 'maintenance' means that some maintenance
             functions are executed on the current interval."
        ::= { rmon1dayPort2Entry 76 }
    
    
    -- 1.3.6.1.4.1.119.2.3.69.203.513.501.11.1.2.2.1.78
    rmon1dayHCTxQueue5Discard2Status OBJECT-TYPE
        SYNTAX      IpeStatsInfo
        ACCESS      read-only
        STATUS      mandatory
        DESCRIPTION
            "RMON 1day TX Queue5 Discard Status. 'invalid' means the
             corresponding monitoring value is not reliable because of the
             alarm or other reasons. 'maintenance' means that some maintenance
             functions are executed on the current interval."
        ::= { rmon1dayPort2Entry 78 }
    
    
    -- 1.3.6.1.4.1.119.2.3.69.203.513.501.11.1.2.2.1.80
    rmon1dayHCTxQueue6Discard2Status OBJECT-TYPE
        SYNTAX      IpeStatsInfo
        ACCESS      read-only
        STATUS      mandatory
        DESCRIPTION
            "RMON 1day TX Queue6 Discard Status. 'invalid' means the
             corresponding monitoring value is not reliable because of the
             alarm or other reasons. 'maintenance' means that some maintenance
             functions are executed on the current interval."
        ::= { rmon1dayPort2Entry 80 }
    
    
    -- 1.3.6.1.4.1.119.2.3.69.203.513.501.11.1.2.2.1.82
    rmon1dayHCTxQueue7Discard2Status OBJECT-TYPE
        SYNTAX      IpeStatsInfo
        ACCESS      read-only
        STATUS      mandatory
        DESCRIPTION
            "RMON 1day TX Queue7 Discard Status. 'invalid' means the
             corresponding monitoring value is not reliable because of the
             alarm or other reasons. 'maintenance' means that some maintenance
             functions are executed on the current interval."
        ::= { rmon1dayPort2Entry 82 }
    
    -- 1.3.6.1.4.1.119.2.3.69.203.513.501.11.1.2.2.1.83
    rmon1dayTxEthStatsOversizePkts2 OBJECT-TYPE
        SYNTAX      Counter
        ACCESS      read-only
        STATUS      mandatory
        DESCRIPTION
            "RMON 1day TX Oversize Pkts."
        ::= { rmon1dayPort2Entry 83 }
    
    -- 1.3.6.1.4.1.119.2.3.69.203.513.501.11.1.2.2.1.84
    rmon1dayTxEthStatsOversizePkts2Status OBJECT-TYPE
        SYNTAX      IpeStatsInfo
        ACCESS      read-only
        STATUS      mandatory
        DESCRIPTION
            "RMON 1day TX Oversize Pkts Status. 'invalid' means the
             corresponding monitoring value is not reliable because of the
             alarm or other reasons. 'maintenance' means that some maintenance
             functions are executed on the current interval."
        ::= { rmon1dayPort2Entry 84 }
    
    
    -- 1.3.6.1.4.1.119.2.3.69.203.513.501.11.1.2.2.1.86
    rmon1dayHCTxFilterDiscard2Status OBJECT-TYPE
        SYNTAX      IpeStatsInfo
        ACCESS      read-only
        STATUS      mandatory
        DESCRIPTION
            "RMON 1day TX Filter Discard Status. 'invalid' means the
             corresponding monitoring value is not reliable because of the
             alarm or other reasons. 'maintenance' means that some maintenance
             functions are executed on the current interval."
        ::= { rmon1dayPort2Entry 86 }
    
    -- 1.3.6.1.4.1.119.2.3.69.203.513.501.11.1.2.3
    rmon1daySfpDataTable OBJECT-TYPE
        SYNTAX      SEQUENCE OF Rmon1daySfpDataEntry
        ACCESS      not-accessible
        STATUS      mandatory
        DESCRIPTION
            "1day ETH Port Sfp Tx/Rx Power Monitoring Table"
        ::= { rmon1dayportGroup 3 }
    
    -- 1.3.6.1.4.1.119.2.3.69.203.513.501.11.1.2.3.1
    rmon1daySfpDataEntry OBJECT-TYPE
        SYNTAX      Rmon1daySfpDataEntry
        ACCESS      not-accessible
        STATUS      mandatory
        DESCRIPTION
            ""
        INDEX       { rmon1daySfpDataNEAddress, rmon1daySfpDataIfIndex }
        ::= { rmon1daySfpDataTable 1 }
    
    Rmon1daySfpDataEntry ::= SEQUENCE {
        rmon1daySfpDataIfIndex              InterfaceIndex,
        rmon1daySfpDataNEAddress            IpAddress,
        rmon1daySfpTxPowerDataStatusInfo    IpeStatsInfo,
        rmon1daySfpTxPowerData              DisplayString,
        rmon1daySfpRxPowerDataStatusInfo    IpeStatsInfo,
        rmon1daySfpRxPowerData              DisplayString
    }
    
    -- 1.3.6.1.4.1.119.2.3.69.203.513.501.11.1.2.3.1.1
    rmon1daySfpDataIfIndex OBJECT-TYPE
        SYNTAX      InterfaceIndex
        ACCESS      not-accessible
        STATUS      mandatory
        DESCRIPTION
            "Index of this table."
        ::= { rmon1daySfpDataEntry 1 }
    
    -- 1.3.6.1.4.1.119.2.3.69.203.513.501.11.1.2.3.1.2
    rmon1daySfpDataNEAddress OBJECT-TYPE
        SYNTAX      IpAddress
        ACCESS      not-accessible
        STATUS      mandatory
        DESCRIPTION
            "reserved"
        ::= { rmon1daySfpDataEntry 2 }
    
    -- 1.3.6.1.4.1.119.2.3.69.203.513.501.11.1.2.3.1.3
    rmon1daySfpTxPowerDataStatusInfo OBJECT-TYPE
        SYNTAX      IpeStatsInfo
        ACCESS      read-only
        STATUS      mandatory
        DESCRIPTION
            "1day ETH Port Sfp Tx Power."
        ::= { rmon1daySfpDataEntry 3 }
    
    -- 1.3.6.1.4.1.119.2.3.69.203.513.501.11.1.2.3.1.4
    rmon1daySfpTxPowerData OBJECT-TYPE
        SYNTAX      DisplayString
        ACCESS      read-only
        STATUS      mandatory
        DESCRIPTION
            "1day ETH Port Sfp Tx Power Status."
        ::= { rmon1daySfpDataEntry 4 }
    
    -- 1.3.6.1.4.1.119.2.3.69.203.513.501.11.1.2.3.1.5
    rmon1daySfpRxPowerDataStatusInfo OBJECT-TYPE
        SYNTAX      IpeStatsInfo
        ACCESS      read-only
        STATUS      mandatory
        DESCRIPTION
            "1day ETH Port Sfp Rx Power."
        ::= { rmon1daySfpDataEntry 5 }
    
    -- 1.3.6.1.4.1.119.2.3.69.203.513.501.11.1.2.3.1.6
    rmon1daySfpRxPowerData OBJECT-TYPE
        SYNTAX      DisplayString
        ACCESS      read-only
        STATUS      mandatory
        DESCRIPTION
            "1day ETH Port Sfp Rx Power Status."
        ::= { rmon1daySfpDataEntry 6 }
    
    -- 1.3.6.1.4.1.119.2.3.69.203.513.501.11.1.2.4
    rmon1dayClassCounterGroup OBJECT IDENTIFIER
        ::= { rmon1dayportGroup 4 }
    
    -- 1.3.6.1.4.1.119.2.3.69.203.513.501.11.1.2.4.1
    rmon1dayClassCounterTable OBJECT-TYPE
        SYNTAX      SEQUENCE OF Rmon1dayClassCounterEntry
        ACCESS      not-accessible
        STATUS      mandatory
        DESCRIPTION
            "this table contains 64 bit counters for octets and packets per
             traffic class for 1day interval. The counted values are cleared
             when the interval is elapsed."
        ::= { rmon1dayClassCounterGroup 1 }
    
    -- 1.3.6.1.4.1.119.2.3.69.203.513.501.11.1.2.4.1.1
    rmon1dayClassCounterEntry OBJECT-TYPE
        SYNTAX      Rmon1dayClassCounterEntry
        ACCESS      not-accessible
        STATUS      mandatory
        DESCRIPTION
            "this table contains 64 bit counters for octets and packets for
             15minutes interval."
        INDEX       { rmon1dayClassCounterNEAddress, rmon1dayClassCounterIfIndex }
        ::= { rmon1dayClassCounterTable 1 }
    
    Rmon1dayClassCounterEntry ::= SEQUENCE {
        rmon1dayClassCounterIfIndex                 InterfaceIndex,
        rmon1dayClassCounterNEAddress               IpAddress,
        rmon1dayClassCounterRxClass0OctetsStatus    IpeStatsInfo,
        rmon1dayClassCounterTxClass0OctetsStatus    IpeStatsInfo,
        rmon1dayClassCounterRxClass0PktsStatus      IpeStatsInfo,
        rmon1dayClassCounterTxClass0PktsStatus      IpeStatsInfo,
        rmon1dayClassCounterRxClass1OctetsStatus    IpeStatsInfo,
        rmon1dayClassCounterTxClass1OctetsStatus    IpeStatsInfo,
        rmon1dayClassCounterRxClass1PktsStatus      IpeStatsInfo,
        rmon1dayClassCounterTxClass1PktsStatus      IpeStatsInfo,
        rmon1dayClassCounterRxClass2OctetsStatus    IpeStatsInfo,
        rmon1dayClassCounterTxClass2OctetsStatus    IpeStatsInfo,
        rmon1dayClassCounterRxClass2PktsStatus      IpeStatsInfo,
        rmon1dayClassCounterTxClass2PktsStatus      IpeStatsInfo,
        rmon1dayClassCounterRxClass3OctetsStatus    IpeStatsInfo,
        rmon1dayClassCounterTxClass3OctetsStatus    IpeStatsInfo,
        rmon1dayClassCounterRxClass3PktsStatus      IpeStatsInfo,
        rmon1dayClassCounterTxClass3PktsStatus      IpeStatsInfo,
        rmon1dayClassCounterRxClass4OctetsStatus    IpeStatsInfo,
        rmon1dayClassCounterTxClass4OctetsStatus    IpeStatsInfo,
        rmon1dayClassCounterRxClass4PktsStatus      IpeStatsInfo,
        rmon1dayClassCounterTxClass4PktsStatus      IpeStatsInfo,
        rmon1dayClassCounterRxClass5OctetsStatus    IpeStatsInfo,
        rmon1dayClassCounterTxClass5OctetsStatus    IpeStatsInfo,
        rmon1dayClassCounterRxClass5PktsStatus      IpeStatsInfo,
        rmon1dayClassCounterTxClass5PktsStatus      IpeStatsInfo,
        rmon1dayClassCounterRxClass6OctetsStatus    IpeStatsInfo,
        rmon1dayClassCounterTxClass6OctetsStatus    IpeStatsInfo,
        rmon1dayClassCounterRxClass6PktsStatus      IpeStatsInfo,
        rmon1dayClassCounterTxClass6PktsStatus      IpeStatsInfo,
        rmon1dayClassCounterRxClass7OctetsStatus    IpeStatsInfo,
        rmon1dayClassCounterTxClass7OctetsStatus    IpeStatsInfo,
        rmon1dayClassCounterRxClass7PktsStatus      IpeStatsInfo,
        rmon1dayClassCounterTxClass7PktsStatus      IpeStatsInfo
    }
    
    -- 1.3.6.1.4.1.119.2.3.69.203.513.501.11.1.2.4.1.1.1
    rmon1dayClassCounterIfIndex OBJECT-TYPE
        SYNTAX      InterfaceIndex
        ACCESS      not-accessible
        STATUS      mandatory
        DESCRIPTION
            "Index of this table. The value is corresponding to refered
             physical or logical interfaces."
        ::= { rmon1dayClassCounterEntry 1 }
    
    -- 1.3.6.1.4.1.119.2.3.69.203.513.501.11.1.2.4.1.1.2
    rmon1dayClassCounterNEAddress OBJECT-TYPE
        SYNTAX      IpAddress
        ACCESS      not-accessible
        STATUS      mandatory
        DESCRIPTION
            "reserved."
        ::= { rmon1dayClassCounterEntry 2 }
    
    
    -- 1.3.6.1.4.1.119.2.3.69.203.513.501.11.1.2.4.1.1.4
    rmon1dayClassCounterRxClass0OctetsStatus OBJECT-TYPE
        SYNTAX      IpeStatsInfo
        ACCESS      read-only
        STATUS      mandatory
        DESCRIPTION
            "the monitering status for the counter."
        ::= { rmon1dayClassCounterEntry 4 }
    
    
    -- 1.3.6.1.4.1.119.2.3.69.203.513.501.11.1.2.4.1.1.6
    rmon1dayClassCounterTxClass0OctetsStatus OBJECT-TYPE
        SYNTAX      IpeStatsInfo
        ACCESS      read-only
        STATUS      mandatory
        DESCRIPTION
            "the monitering status for the counter."
        ::= { rmon1dayClassCounterEntry 6 }
    
    
    -- 1.3.6.1.4.1.119.2.3.69.203.513.501.11.1.2.4.1.1.8
    rmon1dayClassCounterRxClass0PktsStatus OBJECT-TYPE
        SYNTAX      IpeStatsInfo
        ACCESS      read-only
        STATUS      mandatory
        DESCRIPTION
            "the monitering status for the counter."
        ::= { rmon1dayClassCounterEntry 8 }
    
    
    -- 1.3.6.1.4.1.119.2.3.69.203.513.501.11.1.2.4.1.1.10
    rmon1dayClassCounterTxClass0PktsStatus OBJECT-TYPE
        SYNTAX      IpeStatsInfo
        ACCESS      read-only
        STATUS      mandatory
        DESCRIPTION
            "the monitering status for the counter."
        ::= { rmon1dayClassCounterEntry 10 }
    
    
    -- 1.3.6.1.4.1.119.2.3.69.203.513.501.11.1.2.4.1.1.12
    rmon1dayClassCounterRxClass1OctetsStatus OBJECT-TYPE
        SYNTAX      IpeStatsInfo
        ACCESS      read-only
        STATUS      mandatory
        DESCRIPTION
            "the monitering status for the counter."
        ::= { rmon1dayClassCounterEntry 12 }
    
    
    -- 1.3.6.1.4.1.119.2.3.69.203.513.501.11.1.2.4.1.1.14
    rmon1dayClassCounterTxClass1OctetsStatus OBJECT-TYPE
        SYNTAX      IpeStatsInfo
        ACCESS      read-only
        STATUS      mandatory
        DESCRIPTION
            "the monitering status for the counter."
        ::= { rmon1dayClassCounterEntry 14 }
    
    
    -- 1.3.6.1.4.1.119.2.3.69.203.513.501.11.1.2.4.1.1.16
    rmon1dayClassCounterRxClass1PktsStatus OBJECT-TYPE
        SYNTAX      IpeStatsInfo
        ACCESS      read-only
        STATUS      mandatory
        DESCRIPTION
            "the monitering status for the counter."
        ::= { rmon1dayClassCounterEntry 16 }
    
    
    -- 1.3.6.1.4.1.119.2.3.69.203.513.501.11.1.2.4.1.1.18
    rmon1dayClassCounterTxClass1PktsStatus OBJECT-TYPE
        SYNTAX      IpeStatsInfo
        ACCESS      read-only
        STATUS      mandatory
        DESCRIPTION
            "the monitering status for the counter."
        ::= { rmon1dayClassCounterEntry 18 }
    
    
    -- 1.3.6.1.4.1.119.2.3.69.203.513.501.11.1.2.4.1.1.20
    rmon1dayClassCounterRxClass2OctetsStatus OBJECT-TYPE
        SYNTAX      IpeStatsInfo
        ACCESS      read-only
        STATUS      mandatory
        DESCRIPTION
            "the monitering status for the counter."
        ::= { rmon1dayClassCounterEntry 20 }
    
    
    -- 1.3.6.1.4.1.119.2.3.69.203.513.501.11.1.2.4.1.1.22
    rmon1dayClassCounterTxClass2OctetsStatus OBJECT-TYPE
        SYNTAX      IpeStatsInfo
        ACCESS      read-only
        STATUS      mandatory
        DESCRIPTION
            "the monitering status for the counter."
        ::= { rmon1dayClassCounterEntry 22 }
    
    
    -- 1.3.6.1.4.1.119.2.3.69.203.513.501.11.1.2.4.1.1.24
    rmon1dayClassCounterRxClass2PktsStatus OBJECT-TYPE
        SYNTAX      IpeStatsInfo
        ACCESS      read-only
        STATUS      mandatory
        DESCRIPTION
            "the monitering status for the counter."
        ::= { rmon1dayClassCounterEntry 24 }
    
    
    -- 1.3.6.1.4.1.119.2.3.69.203.513.501.11.1.2.4.1.1.26
    rmon1dayClassCounterTxClass2PktsStatus OBJECT-TYPE
        SYNTAX      IpeStatsInfo
        ACCESS      read-only
        STATUS      mandatory
        DESCRIPTION
            "the monitering status for the counter."
        ::= { rmon1dayClassCounterEntry 26 }
    
    
    -- 1.3.6.1.4.1.119.2.3.69.203.513.501.11.1.2.4.1.1.28
    rmon1dayClassCounterRxClass3OctetsStatus OBJECT-TYPE
        SYNTAX      IpeStatsInfo
        ACCESS      read-only
        STATUS      mandatory
        DESCRIPTION
            "the monitering status for the counter."
        ::= { rmon1dayClassCounterEntry 28 }
    
    
    -- 1.3.6.1.4.1.119.2.3.69.203.513.501.11.1.2.4.1.1.30
    rmon1dayClassCounterTxClass3OctetsStatus OBJECT-TYPE
        SYNTAX      IpeStatsInfo
        ACCESS      read-only
        STATUS      mandatory
        DESCRIPTION
            "the monitering status for the counter."
        ::= { rmon1dayClassCounterEntry 30 }
    
    
    -- 1.3.6.1.4.1.119.2.3.69.203.513.501.11.1.2.4.1.1.32
    rmon1dayClassCounterRxClass3PktsStatus OBJECT-TYPE
        SYNTAX      IpeStatsInfo
        ACCESS      read-only
        STATUS      mandatory
        DESCRIPTION
            "the monitering status for the counter."
        ::= { rmon1dayClassCounterEntry 32 }
    
    
    -- 1.3.6.1.4.1.119.2.3.69.203.513.501.11.1.2.4.1.1.34
    rmon1dayClassCounterTxClass3PktsStatus OBJECT-TYPE
        SYNTAX      IpeStatsInfo
        ACCESS      read-only
        STATUS      mandatory
        DESCRIPTION
            "the monitering status for the counter."
        ::= { rmon1dayClassCounterEntry 34 }
    
    
    -- 1.3.6.1.4.1.119.2.3.69.203.513.501.11.1.2.4.1.1.36
    rmon1dayClassCounterRxClass4OctetsStatus OBJECT-TYPE
        SYNTAX      IpeStatsInfo
        ACCESS      read-only
        STATUS      mandatory
        DESCRIPTION
            "the monitering status for the counter."
        ::= { rmon1dayClassCounterEntry 36 }
    
    
    -- 1.3.6.1.4.1.119.2.3.69.203.513.501.11.1.2.4.1.1.38
    rmon1dayClassCounterTxClass4OctetsStatus OBJECT-TYPE
        SYNTAX      IpeStatsInfo
        ACCESS      read-only
        STATUS      mandatory
        DESCRIPTION
            "the monitering status for the counter."
        ::= { rmon1dayClassCounterEntry 38 }
    
    
    -- 1.3.6.1.4.1.119.2.3.69.203.513.501.11.1.2.4.1.1.40
    rmon1dayClassCounterRxClass4PktsStatus OBJECT-TYPE
        SYNTAX      IpeStatsInfo
        ACCESS      read-only
        STATUS      mandatory
        DESCRIPTION
            "the monitering status for the counter."
        ::= { rmon1dayClassCounterEntry 40 }
    
    
    -- 1.3.6.1.4.1.119.2.3.69.203.513.501.11.1.2.4.1.1.42
    rmon1dayClassCounterTxClass4PktsStatus OBJECT-TYPE
        SYNTAX      IpeStatsInfo
        ACCESS      read-only
        STATUS      mandatory
        DESCRIPTION
            "the monitering status for the counter."
        ::= { rmon1dayClassCounterEntry 42 }
    
    
    -- 1.3.6.1.4.1.119.2.3.69.203.513.501.11.1.2.4.1.1.44
    rmon1dayClassCounterRxClass5OctetsStatus OBJECT-TYPE
        SYNTAX      IpeStatsInfo
        ACCESS      read-only
        STATUS      mandatory
        DESCRIPTION
            "the monitering status for the counter."
        ::= { rmon1dayClassCounterEntry 44 }
    
    
    -- 1.3.6.1.4.1.119.2.3.69.203.513.501.11.1.2.4.1.1.46
    rmon1dayClassCounterTxClass5OctetsStatus OBJECT-TYPE
        SYNTAX      IpeStatsInfo
        ACCESS      read-only
        STATUS      mandatory
        DESCRIPTION
            "the monitering status for the counter."
        ::= { rmon1dayClassCounterEntry 46 }
    
    
    -- 1.3.6.1.4.1.119.2.3.69.203.513.501.11.1.2.4.1.1.48
    rmon1dayClassCounterRxClass5PktsStatus OBJECT-TYPE
        SYNTAX      IpeStatsInfo
        ACCESS      read-only
        STATUS      mandatory
        DESCRIPTION
            "the monitering status for the counter."
        ::= { rmon1dayClassCounterEntry 48 }
    
    
    -- 1.3.6.1.4.1.119.2.3.69.203.513.501.11.1.2.4.1.1.50
    rmon1dayClassCounterTxClass5PktsStatus OBJECT-TYPE
        SYNTAX      IpeStatsInfo
        ACCESS      read-only
        STATUS      mandatory
        DESCRIPTION
            "the monitering status for the counter."
        ::= { rmon1dayClassCounterEntry 50 }
    
    
    -- 1.3.6.1.4.1.119.2.3.69.203.513.501.11.1.2.4.1.1.52
    rmon1dayClassCounterRxClass6OctetsStatus OBJECT-TYPE
        SYNTAX      IpeStatsInfo
        ACCESS      read-only
        STATUS      mandatory
        DESCRIPTION
            "the monitering status for the counter."
        ::= { rmon1dayClassCounterEntry 52 }
    
    
    -- 1.3.6.1.4.1.119.2.3.69.203.513.501.11.1.2.4.1.1.54
    rmon1dayClassCounterTxClass6OctetsStatus OBJECT-TYPE
        SYNTAX      IpeStatsInfo
        ACCESS      read-only
        STATUS      mandatory
        DESCRIPTION
            "the monitering status for the counter."
        ::= { rmon1dayClassCounterEntry 54 }
    
    
    -- 1.3.6.1.4.1.119.2.3.69.203.513.501.11.1.2.4.1.1.56
    rmon1dayClassCounterRxClass6PktsStatus OBJECT-TYPE
        SYNTAX      IpeStatsInfo
        ACCESS      read-only
        STATUS      mandatory
        DESCRIPTION
            "the monitering status for the counter."
        ::= { rmon1dayClassCounterEntry 56 }
    
    
    -- 1.3.6.1.4.1.119.2.3.69.203.513.501.11.1.2.4.1.1.58
    rmon1dayClassCounterTxClass6PktsStatus OBJECT-TYPE
        SYNTAX      IpeStatsInfo
        ACCESS      read-only
        STATUS      mandatory
        DESCRIPTION
            "the monitering status for the counter."
        ::= { rmon1dayClassCounterEntry 58 }
    
    
    -- 1.3.6.1.4.1.119.2.3.69.203.513.501.11.1.2.4.1.1.60
    rmon1dayClassCounterRxClass7OctetsStatus OBJECT-TYPE
        SYNTAX      IpeStatsInfo
        ACCESS      read-only
        STATUS      mandatory
        DESCRIPTION
            "the monitering status for the counter."
        ::= { rmon1dayClassCounterEntry 60 }
    
    
    -- 1.3.6.1.4.1.119.2.3.69.203.513.501.11.1.2.4.1.1.62
    rmon1dayClassCounterTxClass7OctetsStatus OBJECT-TYPE
        SYNTAX      IpeStatsInfo
        ACCESS      read-only
        STATUS      mandatory
        DESCRIPTION
            "the monitering status for the counter."
        ::= { rmon1dayClassCounterEntry 62 }
    
    
    -- 1.3.6.1.4.1.119.2.3.69.203.513.501.11.1.2.4.1.1.64
    rmon1dayClassCounterRxClass7PktsStatus OBJECT-TYPE
        SYNTAX      IpeStatsInfo
        ACCESS      read-only
        STATUS      mandatory
        DESCRIPTION
            "the monitering status for the counter."
        ::= { rmon1dayClassCounterEntry 64 }
    
    
    -- 1.3.6.1.4.1.119.2.3.69.203.513.501.11.1.2.4.1.1.66
    rmon1dayClassCounterTxClass7PktsStatus OBJECT-TYPE
        SYNTAX      IpeStatsInfo
        ACCESS      read-only
        STATUS      mandatory
        DESCRIPTION
            "the monitering status for the counter."
        ::= { rmon1dayClassCounterEntry 66 }
    
    -- 1.3.6.1.4.1.119.2.3.69.203.513.501.11.1.3
    rmon15minVlanGroup OBJECT IDENTIFIER
        ::= { rmonEthGroup 3 }
    
    -- 1.3.6.1.4.1.119.2.3.69.203.513.501.11.1.3.1
    rmon15minVlanTable OBJECT-TYPE
        SYNTAX      SEQUENCE OF Rmon15minVlanEntry
        ACCESS      not-accessible
        STATUS      mandatory
        DESCRIPTION
            "RMON 15min VLAN Counter Table."
        ::= { rmon15minVlanGroup 1 }
    
    -- 1.3.6.1.4.1.119.2.3.69.203.513.501.11.1.3.1.1
    rmon15minVlanEntry OBJECT-TYPE
        SYNTAX      Rmon15minVlanEntry
        ACCESS      not-accessible
        STATUS      mandatory
        DESCRIPTION
            ""
        INDEX       { rmon15minVlanCounterNEAddress, rmon15minVlanCounterIndex }
        ::= { rmon15minVlanTable 1 }
    
    Rmon15minVlanEntry ::= SEQUENCE {
        rmon15minVlanCounterIndex               INTEGER,
        rmon15minVlanCounterNEAddress           IpAddress,
        rmon15minHCRxFrameStatusInfo            INTEGER,
        rmon15minHCTxFrameStatusInfo            INTEGER,
        rmon15minHCRxQoSDiscardFrameStatusInfo  INTEGER,
        rmon15minHCRxOctetsStatus               IpeStatsInfo,
        rmon15minHCTxOctetsStatus               IpeStatsInfo
    }
    
    -- 1.3.6.1.4.1.119.2.3.69.203.513.501.11.1.3.1.1.1
    rmon15minVlanCounterIndex OBJECT-TYPE
        SYNTAX      INTEGER (1..256)
        ACCESS      not-accessible
        STATUS      mandatory
        DESCRIPTION
            "Index of this table.
             value range : 1 -   8 (iPASOLINK200/400/1000series/EX/iX)
                         : 1 - 256 (iPASOLINK VR 1/VR 2/VR 4/VR 10)"
        ::= { rmon15minVlanEntry 1 }
    
    -- 1.3.6.1.4.1.119.2.3.69.203.513.501.11.1.3.1.1.2
    rmon15minVlanCounterNEAddress OBJECT-TYPE
        SYNTAX      IpAddress
        ACCESS      not-accessible
        STATUS      mandatory
        DESCRIPTION
            "reserved."
        ::= { rmon15minVlanEntry 2 }
    
    
    -- 1.3.6.1.4.1.119.2.3.69.203.513.501.11.1.3.1.1.4
    rmon15minHCRxFrameStatusInfo OBJECT-TYPE
        SYNTAX      INTEGER { invalid(0), valid-no-maintenance(1),
                        valid-maintenance(2), invalid-no-maintenance(3),
                        invalid-maintenance(4) }
        ACCESS      read-only
        STATUS      mandatory
        DESCRIPTION
            "RMON 15min VLAN RX Frames Status. 'invalid' means the
             corresponding monitoring value is not reliable because of the
             alarm or other reasons. 'maintenance' means that some maintenance
             functions are executed on the current interval."
        ::= { rmon15minVlanEntry 4 }
    
    
    -- 1.3.6.1.4.1.119.2.3.69.203.513.501.11.1.3.1.1.6
    rmon15minHCTxFrameStatusInfo OBJECT-TYPE
        SYNTAX      INTEGER { invalid(0), valid-no-maintenance(1),
                        valid-maintenance(2), invalid-no-maintenance(3),
                        invalid-maintenance(4) }
        ACCESS      read-only
        STATUS      mandatory
        DESCRIPTION
            "RMON 15min VLAN TX Frames Status. 'invalid' means the
             corresponding monitoring value is not reliable because of the
             alarm or other reasons. 'maintenance' means that some maintenance
             functions are executed on the current interval."
        ::= { rmon15minVlanEntry 6 }
    
    
    -- 1.3.6.1.4.1.119.2.3.69.203.513.501.11.1.3.1.1.8
    rmon15minHCRxQoSDiscardFrameStatusInfo OBJECT-TYPE
        SYNTAX      INTEGER { invalid(0), valid-no-maintenance(1),
                        valid-maintenance(2), invalid-no-maintenance(3),
                        invalid-maintenance(4) }
        ACCESS      read-only
        STATUS      mandatory
        DESCRIPTION
            "RMON 15min RX QoS Discard Frames Status. 'invalid' means the
             corresponding monitoring value is not reliable because of the
             alarm or other reasons. 'maintenance' means that some maintenance
             functions are executed on the current interval."
        ::= { rmon15minVlanEntry 8 }
    
    
    -- 1.3.6.1.4.1.119.2.3.69.203.513.501.11.1.3.1.1.10
    rmon15minHCRxOctetsStatus OBJECT-TYPE
        SYNTAX      IpeStatsInfo
        ACCESS      read-only
        STATUS      mandatory
        DESCRIPTION
            "RMON 15min RX Octs Status. 'invalid' means the corresponding
             monitoring value is not reliable because of the alarm or other
             reasons. 'maintenance' means that some maintenance functions are
             executed on the current interval."
        ::= { rmon15minVlanEntry 10 }
    
    
    -- 1.3.6.1.4.1.119.2.3.69.203.513.501.11.1.3.1.1.12
    rmon15minHCTxOctetsStatus OBJECT-TYPE
        SYNTAX      IpeStatsInfo
        ACCESS      read-only
        STATUS      mandatory
        DESCRIPTION
            "RMON 15min TX Octs Status. 'invalid' means the corresponding
             monitoring value is not reliable because of the alarm or other
             reasons. 'maintenance' means that some maintenance functions are
             executed on the current interval."
        ::= { rmon15minVlanEntry 12 }
    
    -- 1.3.6.1.4.1.119.2.3.69.203.513.501.11.1.3.2
    rmon15minVlanPortMappingTable OBJECT-TYPE
        SYNTAX      SEQUENCE OF Rmon15minVlanPortMappingEntry
        ACCESS      not-accessible
        STATUS      mandatory
        DESCRIPTION
            "If the VLAN Counter is enabled to the port, this object will
             show the corresponding VLAN Counter Index."
        ::= { rmon15minVlanGroup 2 }
    
    -- 1.3.6.1.4.1.119.2.3.69.203.513.501.11.1.3.2.1
    rmon15minVlanPortMappingEntry OBJECT-TYPE
        SYNTAX      Rmon15minVlanPortMappingEntry
        ACCESS      not-accessible
        STATUS      mandatory
        DESCRIPTION
            ""
        INDEX       { rmon15minVlanMappingNEAddress, rmon15minVlanPortMappingIfIndex,
                      rmon15minVlanMappingVlanIndex }
        ::= { rmon15minVlanPortMappingTable 1 }
    
    Rmon15minVlanPortMappingEntry ::= SEQUENCE {
        rmon15minVlanPortMappingIfIndex     InterfaceIndex,
        rmon15minVlanMappingVlanIndex       INTEGER,
        rmon15minVlanMappingNEAddress       IpAddress,
        rmon15minVlanCounterId              INTEGER
    }
    
    -- 1.3.6.1.4.1.119.2.3.69.203.513.501.11.1.3.2.1.1
    rmon15minVlanPortMappingIfIndex OBJECT-TYPE
        SYNTAX      InterfaceIndex
        ACCESS      not-accessible
        STATUS      mandatory
        DESCRIPTION
            "Index of this table."
        ::= { rmon15minVlanPortMappingEntry 1 }
    
    -- 1.3.6.1.4.1.119.2.3.69.203.513.501.11.1.3.2.1.2
    rmon15minVlanMappingVlanIndex OBJECT-TYPE
        SYNTAX      INTEGER (1..4094)
        ACCESS      not-accessible
        STATUS      mandatory
        DESCRIPTION
            "VLAN ID enabling VLAN Counter"
        ::= { rmon15minVlanPortMappingEntry 2 }
    
    -- 1.3.6.1.4.1.119.2.3.69.203.513.501.11.1.3.2.1.3
    rmon15minVlanMappingNEAddress OBJECT-TYPE
        SYNTAX      IpAddress
        ACCESS      not-accessible
        STATUS      mandatory
        DESCRIPTION
            "reserved."
        ::= { rmon15minVlanPortMappingEntry 3 }
    
    -- 1.3.6.1.4.1.119.2.3.69.203.513.501.11.1.3.2.1.4
    rmon15minVlanCounterId OBJECT-TYPE
        SYNTAX      INTEGER (1..256)
        ACCESS      read-only
        STATUS      mandatory
        DESCRIPTION
            "VLAN Counter ID which is assigned to the port.
             value range : 1 -   8 (iPASOLINK200/400/1000series/EX/iX)
                         : 1 - 256 (iPASOLINK VR 2/VR 4/VR 10)"
        ::= { rmon15minVlanPortMappingEntry 4 }
    
    -- 1.3.6.1.4.1.119.2.3.69.203.513.501.11.1.3.3
    rmon15minVlanGroupTable OBJECT-TYPE
        SYNTAX      SEQUENCE OF Rmon15minVlanGroupEntry
        ACCESS      not-accessible
        STATUS      mandatory
        DESCRIPTION
            "RMON 15min VLAN Group Counter Table."
        ::= { rmon15minVlanGroup 3 }
    
    -- 1.3.6.1.4.1.119.2.3.69.203.513.501.11.1.3.3.1
    rmon15minVlanGroupEntry OBJECT-TYPE
        SYNTAX      Rmon15minVlanGroupEntry
        ACCESS      not-accessible
        STATUS      mandatory
        DESCRIPTION
            ""
        INDEX       { rmon15minVlanGroupCounterNEAddress, rmon15minVlanGroupCounterIndex }
        ::= { rmon15minVlanGroupTable 1 }
    
    Rmon15minVlanGroupEntry ::= SEQUENCE {
        rmon15minVlanGroupCounterIndex          INTEGER,
        rmon15minVlanGroupCounterNEAddress      IpAddress,
        rmon15minVGRxFrameStatusInfo            IpeStatsInfo,
        rmon15minVGTxFrameStatusInfo            IpeStatsInfo,
        rmon15minVGRxOctetsStatus               IpeStatsInfo,
        rmon15minVGTxOctetsStatus               IpeStatsInfo,
        rmon15minVGTxQueue0DiscardStatusInfo    IpeStatsInfo,
        rmon15minVGTxQueue1DiscardStatusInfo    IpeStatsInfo,
        rmon15minVGTxQueue2DiscardStatusInfo    IpeStatsInfo,
        rmon15minVGTxQueue3DiscardStatusInfo    IpeStatsInfo,
        rmon15minVGTxQueue4DiscardStatusInfo    IpeStatsInfo,
        rmon15minVGTxQueue5DiscardStatusInfo    IpeStatsInfo,
        rmon15minVGTxQueue6DiscardStatusInfo    IpeStatsInfo,
        rmon15minVGTxQueue7DiscardStatusInfo    IpeStatsInfo
    }
    
    -- 1.3.6.1.4.1.119.2.3.69.203.513.501.11.1.3.3.1.1
    rmon15minVlanGroupCounterIndex OBJECT-TYPE
        SYNTAX      INTEGER (1..64)
        ACCESS      not-accessible
        STATUS      mandatory
        DESCRIPTION
            "Index of this table."
        ::= { rmon15minVlanGroupEntry 1 }
    
    -- 1.3.6.1.4.1.119.2.3.69.203.513.501.11.1.3.3.1.2
    rmon15minVlanGroupCounterNEAddress OBJECT-TYPE
        SYNTAX      IpAddress
        ACCESS      not-accessible
        STATUS      mandatory
        DESCRIPTION
            "reserved."
        ::= { rmon15minVlanGroupEntry 2 }
    
    
    -- 1.3.6.1.4.1.119.2.3.69.203.513.501.11.1.3.3.1.4
    rmon15minVGRxFrameStatusInfo OBJECT-TYPE
        SYNTAX      IpeStatsInfo
        ACCESS      read-only
        STATUS      obsolete
        DESCRIPTION
            "RMON 15min RX Frames Status. 'invalid' means the corresponding
             monitoring value is not reliable because of the alarm or other
             reasons. 'maintenance' means that some maintenance functions are
             executed on the current interval."
        ::= { rmon15minVlanGroupEntry 4 }
    
    
    -- 1.3.6.1.4.1.119.2.3.69.203.513.501.11.1.3.3.1.6
    rmon15minVGTxFrameStatusInfo OBJECT-TYPE
        SYNTAX      IpeStatsInfo
        ACCESS      read-only
        STATUS      mandatory
        DESCRIPTION
            "RMON 15min TX Frames Status. 'invalid' means the corresponding
             monitoring value is not reliable because of the alarm or other
             reasons. 'maintenance' means that some maintenance functions are
             executed on the current interval."
        ::= { rmon15minVlanGroupEntry 6 }
    
    
    -- 1.3.6.1.4.1.119.2.3.69.203.513.501.11.1.3.3.1.8
    rmon15minVGRxOctetsStatus OBJECT-TYPE
        SYNTAX      IpeStatsInfo
        ACCESS      read-only
        STATUS      obsolete
        DESCRIPTION
            "RMON 15min RX Octs Status. 'invalid' means the corresponding
             monitoring value is not reliable because of the alarm or other
             reasons. 'maintenance' means that some maintenance functions are
             executed on the current interval."
        ::= { rmon15minVlanGroupEntry 8 }
    
    
    -- 1.3.6.1.4.1.119.2.3.69.203.513.501.11.1.3.3.1.10
    rmon15minVGTxOctetsStatus OBJECT-TYPE
        SYNTAX      IpeStatsInfo
        ACCESS      read-only
        STATUS      mandatory
        DESCRIPTION
            "RMON 15min TX Octs Status. 'invalid' means the corresponding
             monitoring value is not reliable because of the alarm or other
             reasons. 'maintenance' means that some maintenance functions are
             executed on the current interval."
        ::= { rmon15minVlanGroupEntry 10 }
    
    
    -- 1.3.6.1.4.1.119.2.3.69.203.513.501.11.1.3.3.1.12
    rmon15minVGTxQueue0DiscardStatusInfo OBJECT-TYPE
        SYNTAX      IpeStatsInfo
        ACCESS      read-only
        STATUS      mandatory
        DESCRIPTION
            "RMON 15min TX Queue0 Discard Status. 'invalid' means the
             corresponding monitoring value is not reliable because of the
             alarm or other reasons. 'maintenance' means that some maintenance
             functions are executed on the current interval."
        ::= { rmon15minVlanGroupEntry 12 }
    
    
    -- 1.3.6.1.4.1.119.2.3.69.203.513.501.11.1.3.3.1.14
    rmon15minVGTxQueue1DiscardStatusInfo OBJECT-TYPE
        SYNTAX      IpeStatsInfo
        ACCESS      read-only
        STATUS      mandatory
        DESCRIPTION
            "RMON 15min TX Queue1 Discard Status. 'invalid' means the
             corresponding monitoring value is not reliable because of the
             alarm or other reasons. 'maintenance' means that some maintenance
             functions are executed on the current interval."
        ::= { rmon15minVlanGroupEntry 14 }
    
    
    -- 1.3.6.1.4.1.119.2.3.69.203.513.501.11.1.3.3.1.16
    rmon15minVGTxQueue2DiscardStatusInfo OBJECT-TYPE
        SYNTAX      IpeStatsInfo
        ACCESS      read-only
        STATUS      mandatory
        DESCRIPTION
            "RMON 15min TX Queue2 Discard Status. 'invalid' means the
             corresponding monitoring value is not reliable because of the
             alarm or other reasons. 'maintenance' means that some maintenance
             functions are executed on the current interval."
        ::= { rmon15minVlanGroupEntry 16 }
    
    
    -- 1.3.6.1.4.1.119.2.3.69.203.513.501.11.1.3.3.1.18
    rmon15minVGTxQueue3DiscardStatusInfo OBJECT-TYPE
        SYNTAX      IpeStatsInfo
        ACCESS      read-only
        STATUS      mandatory
        DESCRIPTION
            "RMON 15min TX Queue3 Discard Status. 'invalid' means the
             corresponding monitoring value is not reliable because of the
             alarm or other reasons. 'maintenance' means that some maintenance
             functions are executed on the current interval."
        ::= { rmon15minVlanGroupEntry 18 }
    
    
    -- 1.3.6.1.4.1.119.2.3.69.203.513.501.11.1.3.3.1.20
    rmon15minVGTxQueue4DiscardStatusInfo OBJECT-TYPE
        SYNTAX      IpeStatsInfo
        ACCESS      read-only
        STATUS      mandatory
        DESCRIPTION
            "RMON 15min TX Queue4 Discard Status. 'invalid' means the
             corresponding monitoring value is not reliable because of the
             alarm or other reasons. 'maintenance' means that some maintenance
             functions are executed on the current interval."
        ::= { rmon15minVlanGroupEntry 20 }
    
    
    -- 1.3.6.1.4.1.119.2.3.69.203.513.501.11.1.3.3.1.22
    rmon15minVGTxQueue5DiscardStatusInfo OBJECT-TYPE
        SYNTAX      IpeStatsInfo
        ACCESS      read-only
        STATUS      mandatory
        DESCRIPTION
            "RMON 15min TX Queue5 Discard Status. 'invalid' means the
             corresponding monitoring value is not reliable because of the
             alarm or other reasons. 'maintenance' means that some maintenance
             functions are executed on the current interval."
        ::= { rmon15minVlanGroupEntry 22 }
    
    
    -- 1.3.6.1.4.1.119.2.3.69.203.513.501.11.1.3.3.1.24
    rmon15minVGTxQueue6DiscardStatusInfo OBJECT-TYPE
        SYNTAX      IpeStatsInfo
        ACCESS      read-only
        STATUS      mandatory
        DESCRIPTION
            "RMON 15min TX Queue6 Discard Status. 'invalid' means the
             corresponding monitoring value is not reliable because of the
             alarm or other reasons. 'maintenance' means that some maintenance
             functions are executed on the current interval."
        ::= { rmon15minVlanGroupEntry 24 }
    
    
    -- 1.3.6.1.4.1.119.2.3.69.203.513.501.11.1.3.3.1.26
    rmon15minVGTxQueue7DiscardStatusInfo OBJECT-TYPE
        SYNTAX      IpeStatsInfo
        ACCESS      read-only
        STATUS      mandatory
        DESCRIPTION
            "RMON 15min TX Queue7 Discard Status. 'invalid' means the
             corresponding monitoring value is not reliable because of the
             alarm or other reasons. 'maintenance' means that some maintenance
             functions are executed on the current interval."
        ::= { rmon15minVlanGroupEntry 26 }
    
    -- 1.3.6.1.4.1.119.2.3.69.203.513.501.11.1.4
    rmon1dayVlanGroup OBJECT IDENTIFIER
        ::= { rmonEthGroup 4 }
    
    -- 1.3.6.1.4.1.119.2.3.69.203.513.501.11.1.4.1
    rmon1dayVlanTable OBJECT-TYPE
        SYNTAX      SEQUENCE OF Rmon1dayVlanEntry
        ACCESS      not-accessible
        STATUS      mandatory
        DESCRIPTION
            "RMON 1day VLAN Counter Table."
        ::= { rmon1dayVlanGroup 1 }
    
    -- 1.3.6.1.4.1.119.2.3.69.203.513.501.11.1.4.1.1
    rmon1dayVlanEntry OBJECT-TYPE
        SYNTAX      Rmon1dayVlanEntry
        ACCESS      not-accessible
        STATUS      mandatory
        DESCRIPTION
            ""
        INDEX       { rmon1dayVlanCounterNEAddress, rmon1dayVlanCounterIndex }
        ::= { rmon1dayVlanTable 1 }
    
    Rmon1dayVlanEntry ::= SEQUENCE {
        rmon1dayVlanCounterIndex                INTEGER,
        rmon1dayVlanCounterNEAddress            IpAddress,
        rmon1dayHCRxFrameStatusInfo             INTEGER,
        rmon1dayHCTxFrameStatusInfo             INTEGER,
        rmon1dayHCRxQoSDiscardFrameStatusInfo   INTEGER,
        rmon1dayHCRxOctetsStatus                IpeStatsInfo,
        rmon1dayHCTxOctetsStatus                IpeStatsInfo
    }
    
    -- 1.3.6.1.4.1.119.2.3.69.203.513.501.11.1.4.1.1.1
    rmon1dayVlanCounterIndex OBJECT-TYPE
        SYNTAX      INTEGER (1..256)
        ACCESS      not-accessible
        STATUS      mandatory
        DESCRIPTION
            "Index of this table.
             value range : 1 -   8 (iPASOLINK200/400/1000series/EX/iX)
                         : 1 - 256 (iPASOLINK VR 1/VR 2/VR 4/VR 10)"
        ::= { rmon1dayVlanEntry 1 }
    
    -- 1.3.6.1.4.1.119.2.3.69.203.513.501.11.1.4.1.1.2
    rmon1dayVlanCounterNEAddress OBJECT-TYPE
        SYNTAX      IpAddress
        ACCESS      not-accessible
        STATUS      mandatory
        DESCRIPTION
            "reserved."
        ::= { rmon1dayVlanEntry 2 }
    
    
    -- 1.3.6.1.4.1.119.2.3.69.203.513.501.11.1.4.1.1.4
    rmon1dayHCRxFrameStatusInfo OBJECT-TYPE
        SYNTAX      INTEGER { invalid(0), valid-no-maintenance(1),
                        valid-maintenance(2), invalid-no-maintenance(3),
                        invalid-maintenance(4) }
        ACCESS      read-only
        STATUS      mandatory
        DESCRIPTION
            "RMON 1day VLAN RX Frames Status. 'invalid' means the
             corresponding monitoring value is not reliable because of the
             alarm or other reasons. 'maintenance' means that some maintenance
             functions are executed on the current interval."
        ::= { rmon1dayVlanEntry 4 }
    
    
    -- 1.3.6.1.4.1.119.2.3.69.203.513.501.11.1.4.1.1.6
    rmon1dayHCTxFrameStatusInfo OBJECT-TYPE
        SYNTAX      INTEGER { invalid(0), valid-no-maintenance(1),
                        valid-maintenance(2), invalid-no-maintenance(3),
                        invalid-maintenance(4) }
        ACCESS      read-only
        STATUS      mandatory
        DESCRIPTION
            "RMON 1day VLAN TX Frames Status. 'invalid' means the
             corresponding monitoring value is not reliable because of the
             alarm or other reasons. 'maintenance' means that some maintenance
             functions are executed on the current interval."
        ::= { rmon1dayVlanEntry 6 }
    
    
    -- 1.3.6.1.4.1.119.2.3.69.203.513.501.11.1.4.1.1.8
    rmon1dayHCRxQoSDiscardFrameStatusInfo OBJECT-TYPE
        SYNTAX      INTEGER { invalid(0), valid-no-maintenance(1),
                        valid-maintenance(2), invalid-no-maintenance(3),
                        invalid-maintenance(4) }
        ACCESS      read-only
        STATUS      mandatory
        DESCRIPTION
            "RMON 1day RX QoS Discard Frames Status. 'invalid' means the
             corresponding monitoring value is not reliable because of the
             alarm or other reasons. 'maintenance' means that some maintenance
             functions are executed on the current interval."
        ::= { rmon1dayVlanEntry 8 }
    
    
    -- 1.3.6.1.4.1.119.2.3.69.203.513.501.11.1.4.1.1.10
    rmon1dayHCRxOctetsStatus OBJECT-TYPE
        SYNTAX      IpeStatsInfo
        ACCESS      read-only
        STATUS      mandatory
        DESCRIPTION
            "RMON 1day RX Octs Status. 'invalid' means the corresponding
             monitoring value is not reliable because of the alarm or other
             reasons. 'maintenance' means that some maintenance functions are
             executed on the current interval."
        ::= { rmon1dayVlanEntry 10 }
    
    
    -- 1.3.6.1.4.1.119.2.3.69.203.513.501.11.1.4.1.1.12
    rmon1dayHCTxOctetsStatus OBJECT-TYPE
        SYNTAX      IpeStatsInfo
        ACCESS      read-only
        STATUS      mandatory
        DESCRIPTION
            "RMON 1day TX Octs Status. 'invalid' means the corresponding
             monitoring value is not reliable because of the alarm or other
             reasons. 'maintenance' means that some maintenance functions are
             executed on the current interval."
        ::= { rmon1dayVlanEntry 12 }
    
    -- 1.3.6.1.4.1.119.2.3.69.203.513.501.11.1.4.2
    rmon1dayVlanPortMappingTable OBJECT-TYPE
        SYNTAX      SEQUENCE OF Rmon1dayVlanPortMappingEntry
        ACCESS      not-accessible
        STATUS      mandatory
        DESCRIPTION
            "If the VLAN Counter is enabled to the port, this object will
             show the corresponding VLAN Counter Index."
        ::= { rmon1dayVlanGroup 2 }
    
    -- 1.3.6.1.4.1.119.2.3.69.203.513.501.11.1.4.2.1
    rmon1dayVlanPortMappingEntry OBJECT-TYPE
        SYNTAX      Rmon1dayVlanPortMappingEntry
        ACCESS      not-accessible
        STATUS      mandatory
        DESCRIPTION
            ""
        INDEX       { rmon1dayVlanMappingNEAddress, rmon1dayVlanPortMappingIfIndex,
                      rmon1dayVlanMappingVlanIndex }
        ::= { rmon1dayVlanPortMappingTable 1 }
    
    Rmon1dayVlanPortMappingEntry ::= SEQUENCE {
        rmon1dayVlanPortMappingIfIndex  InterfaceIndex,
        rmon1dayVlanMappingVlanIndex    INTEGER,
        rmon1dayVlanMappingNEAddress    IpAddress,
        rmon1dayVlanCounterId           INTEGER
    }
    
    -- 1.3.6.1.4.1.119.2.3.69.203.513.501.11.1.4.2.1.1
    rmon1dayVlanPortMappingIfIndex OBJECT-TYPE
        SYNTAX      InterfaceIndex
        ACCESS      not-accessible
        STATUS      mandatory
        DESCRIPTION
            "Index of this table."
        ::= { rmon1dayVlanPortMappingEntry 1 }
    
    -- 1.3.6.1.4.1.119.2.3.69.203.513.501.11.1.4.2.1.2
    rmon1dayVlanMappingVlanIndex OBJECT-TYPE
        SYNTAX      INTEGER (1..4094)
        ACCESS      not-accessible
        STATUS      mandatory
        DESCRIPTION
            "VLAN ID enabling VLAN Counter"
        ::= { rmon1dayVlanPortMappingEntry 2 }
    
    -- 1.3.6.1.4.1.119.2.3.69.203.513.501.11.1.4.2.1.3
    rmon1dayVlanMappingNEAddress OBJECT-TYPE
        SYNTAX      IpAddress
        ACCESS      not-accessible
        STATUS      mandatory
        DESCRIPTION
            "reserved."
        ::= { rmon1dayVlanPortMappingEntry 3 }
    
    -- 1.3.6.1.4.1.119.2.3.69.203.513.501.11.1.4.2.1.4
    rmon1dayVlanCounterId OBJECT-TYPE
        SYNTAX      INTEGER (1..256)
        ACCESS      read-only
        STATUS      mandatory
        DESCRIPTION
            "VLAN Counter ID which is assigned to the port.
             value range : 1 -   8 (iPASOLINK200/400/1000series/EX/iX)
                         : 1 - 256 (iPASOLINK VR 2/VR 4/VR 10)"
        ::= { rmon1dayVlanPortMappingEntry 4 }
    
    -- 1.3.6.1.4.1.119.2.3.69.203.513.501.11.1.4.3
    rmon1dayVlanGroupTable OBJECT-TYPE
        SYNTAX      SEQUENCE OF Rmon1dayVlanGroupEntry
        ACCESS      not-accessible
        STATUS      mandatory
        DESCRIPTION
            "RMON 1day VLAN Group Counter Table."
        ::= { rmon1dayVlanGroup 3 }
    
    -- 1.3.6.1.4.1.119.2.3.69.203.513.501.11.1.4.3.1
    rmon1dayVlanGroupEntry OBJECT-TYPE
        SYNTAX      Rmon1dayVlanGroupEntry
        ACCESS      not-accessible
        STATUS      mandatory
        DESCRIPTION
            ""
        INDEX       { rmon1dayVlanGroupCounterNEAddress, rmon1dayVlanGroupCounterIndex }
        ::= { rmon1dayVlanGroupTable 1 }
    
    Rmon1dayVlanGroupEntry ::= SEQUENCE {
        rmon1dayVlanGroupCounterIndex           INTEGER,
        rmon1dayVlanGroupCounterNEAddress       IpAddress,
        rmon1dayVGRxFrameStatusInfo             IpeStatsInfo,
        rmon1dayVGTxFrameStatusInfo             IpeStatsInfo,
        rmon1dayVGRxOctetsStatus                IpeStatsInfo,
        rmon1dayVGTxOctetsStatus                IpeStatsInfo,
        rmon1dayVGTxQueue0DiscardStatusInfo     IpeStatsInfo,
        rmon1dayVGTxQueue1DiscardStatusInfo     IpeStatsInfo,
        rmon1dayVGTxQueue2DiscardStatusInfo     IpeStatsInfo,
        rmon1dayVGTxQueue3DiscardStatusInfo     IpeStatsInfo,
        rmon1dayVGTxQueue4DiscardStatusInfo     IpeStatsInfo,
        rmon1dayVGTxQueue5DiscardStatusInfo     IpeStatsInfo,
        rmon1dayVGTxQueue6DiscardStatusInfo     IpeStatsInfo,
        rmon1dayVGTxQueue7DiscardStatusInfo     IpeStatsInfo
    }
    
    -- 1.3.6.1.4.1.119.2.3.69.203.513.501.11.1.4.3.1.1
    rmon1dayVlanGroupCounterIndex OBJECT-TYPE
        SYNTAX      INTEGER (1..64)
        ACCESS      not-accessible
        STATUS      mandatory
        DESCRIPTION
            "Index of this table."
        ::= { rmon1dayVlanGroupEntry 1 }
    
    -- 1.3.6.1.4.1.119.2.3.69.203.513.501.11.1.4.3.1.2
    rmon1dayVlanGroupCounterNEAddress OBJECT-TYPE
        SYNTAX      IpAddress
        ACCESS      not-accessible
        STATUS      mandatory
        DESCRIPTION
            "reserved."
        ::= { rmon1dayVlanGroupEntry 2 }
    
    
    -- 1.3.6.1.4.1.119.2.3.69.203.513.501.11.1.4.3.1.4
    rmon1dayVGRxFrameStatusInfo OBJECT-TYPE
        SYNTAX      IpeStatsInfo
        ACCESS      read-only
        STATUS      obsolete
        DESCRIPTION
            "RMON 1day RX Frames Status. 'invalid' means the corresponding
             monitoring value is not reliable because of the alarm or other
             reasons. 'maintenance' means that some maintenance functions are
             executed on the current interval."
        ::= { rmon1dayVlanGroupEntry 4 }
    
    
    -- 1.3.6.1.4.1.119.2.3.69.203.513.501.11.1.4.3.1.6
    rmon1dayVGTxFrameStatusInfo OBJECT-TYPE
        SYNTAX      IpeStatsInfo
        ACCESS      read-only
        STATUS      mandatory
        DESCRIPTION
            "RMON 1day TX Frames Status. 'invalid' means the corresponding
             monitoring value is not reliable because of the alarm or other
             reasons. 'maintenance' means that some maintenance functions are
             executed on the current interval."
        ::= { rmon1dayVlanGroupEntry 6 }
    
    
    -- 1.3.6.1.4.1.119.2.3.69.203.513.501.11.1.4.3.1.8
    rmon1dayVGRxOctetsStatus OBJECT-TYPE
        SYNTAX      IpeStatsInfo
        ACCESS      read-only
        STATUS      obsolete
        DESCRIPTION
            "RMON 1day RX Octs Status. 'invalid' means the corresponding
             monitoring value is not reliable because of the alarm or other
             reasons. 'maintenance' means that some maintenance functions are
             executed on the current interval."
        ::= { rmon1dayVlanGroupEntry 8 }
    
    
    -- 1.3.6.1.4.1.119.2.3.69.203.513.501.11.1.4.3.1.10
    rmon1dayVGTxOctetsStatus OBJECT-TYPE
        SYNTAX      IpeStatsInfo
        ACCESS      read-only
        STATUS      mandatory
        DESCRIPTION
            "RMON 1day TX Octs Status. 'invalid' means the corresponding
             monitoring value is not reliable because of the alarm or other
             reasons. 'maintenance' means that some maintenance functions are
             executed on the current interval."
        ::= { rmon1dayVlanGroupEntry 10 }
    
    
    -- 1.3.6.1.4.1.119.2.3.69.203.513.501.11.1.4.3.1.12
    rmon1dayVGTxQueue0DiscardStatusInfo OBJECT-TYPE
        SYNTAX      IpeStatsInfo
        ACCESS      read-only
        STATUS      mandatory
        DESCRIPTION
            "RMON 1day TX Queue0 Discard Status. 'invalid' means the
             corresponding monitoring value is not reliable because of the
             alarm or other reasons. 'maintenance' means that some maintenance
             functions are executed on the current interval."
        ::= { rmon1dayVlanGroupEntry 12 }
    
    
    -- 1.3.6.1.4.1.119.2.3.69.203.513.501.11.1.4.3.1.14
    rmon1dayVGTxQueue1DiscardStatusInfo OBJECT-TYPE
        SYNTAX      IpeStatsInfo
        ACCESS      read-only
        STATUS      mandatory
        DESCRIPTION
            "RMON 1day TX Queue1 Discard Status. 'invalid' means the
             corresponding monitoring value is not reliable because of the
             alarm or other reasons. 'maintenance' means that some maintenance
             functions are executed on the current interval."
        ::= { rmon1dayVlanGroupEntry 14 }
    
    
    -- 1.3.6.1.4.1.119.2.3.69.203.513.501.11.1.4.3.1.16
    rmon1dayVGTxQueue2DiscardStatusInfo OBJECT-TYPE
        SYNTAX      IpeStatsInfo
        ACCESS      read-only
        STATUS      mandatory
        DESCRIPTION
            "RMON 1day TX Queue2 Discard Status. 'invalid' means the
             corresponding monitoring value is not reliable because of the
             alarm or other reasons. 'maintenance' means that some maintenance
             functions are executed on the current interval."
        ::= { rmon1dayVlanGroupEntry 16 }
    
    
    -- 1.3.6.1.4.1.119.2.3.69.203.513.501.11.1.4.3.1.18
    rmon1dayVGTxQueue3DiscardStatusInfo OBJECT-TYPE
        SYNTAX      IpeStatsInfo
        ACCESS      read-only
        STATUS      mandatory
        DESCRIPTION
            "RMON 1day TX Queue3 Discard Status. 'invalid' means the
             corresponding monitoring value is not reliable because of the
             alarm or other reasons. 'maintenance' means that some maintenance
             functions are executed on the current interval."
        ::= { rmon1dayVlanGroupEntry 18 }
    
    
    -- 1.3.6.1.4.1.119.2.3.69.203.513.501.11.1.4.3.1.20
    rmon1dayVGTxQueue4DiscardStatusInfo OBJECT-TYPE
        SYNTAX      IpeStatsInfo
        ACCESS      read-only
        STATUS      mandatory
        DESCRIPTION
            "RMON 1day TX Queue4 Discard Status. 'invalid' means the
             corresponding monitoring value is not reliable because of the
             alarm or other reasons. 'maintenance' means that some maintenance
             functions are executed on the current interval."
        ::= { rmon1dayVlanGroupEntry 20 }
    
    
    -- 1.3.6.1.4.1.119.2.3.69.203.513.501.11.1.4.3.1.22
    rmon1dayVGTxQueue5DiscardStatusInfo OBJECT-TYPE
        SYNTAX      IpeStatsInfo
        ACCESS      read-only
        STATUS      mandatory
        DESCRIPTION
            "RMON 1day TX Queue5 Discard Status. 'invalid' means the
             corresponding monitoring value is not reliable because of the
             alarm or other reasons. 'maintenance' means that some maintenance
             functions are executed on the current interval."
        ::= { rmon1dayVlanGroupEntry 22 }
    
    
    -- 1.3.6.1.4.1.119.2.3.69.203.513.501.11.1.4.3.1.24
    rmon1dayVGTxQueue6DiscardStatusInfo OBJECT-TYPE
        SYNTAX      IpeStatsInfo
        ACCESS      read-only
        STATUS      mandatory
        DESCRIPTION
            "RMON 1day TX Queue6 Discard Status. 'invalid' means the
             corresponding monitoring value is not reliable because of the
             alarm or other reasons. 'maintenance' means that some maintenance
             functions are executed on the current interval."
        ::= { rmon1dayVlanGroupEntry 24 }
    
    
    -- 1.3.6.1.4.1.119.2.3.69.203.513.501.11.1.4.3.1.26
    rmon1dayVGTxQueue7DiscardStatusInfo OBJECT-TYPE
        SYNTAX      IpeStatsInfo
        ACCESS      read-only
        STATUS      mandatory
        DESCRIPTION
            "RMON 1day TX Queue7 Discard Status. 'invalid' means the
             corresponding monitoring value is not reliable because of the
             alarm or other reasons. 'maintenance' means that some maintenance
             functions are executed on the current interval."
        ::= { rmon1dayVlanGroupEntry 26 }
    
    -- 1.3.6.1.4.1.119.2.3.69.203.513.501.2.3.1.0.1
    alarmStateChange TRAP-TYPE
        ENTERPRISE  ipeAlarmTrapItemVar
        VARIABLES   { eventTotalCount, eventCount, eventTime, eventType,
                      eventResourceID, eventSeverity, eventAlarmType,
                      eventProbableCause, eventAdditionalText1,
                      eventAdditionalText2, eventAdditionalText3,
                      eventAdditionalText4, eventAdditionalText5 }
        DESCRIPTION
            "Trap for Alarm
             This notification reports that a processed alarm status may have
             changed.
             The object information is recorded in 'eventResourceID' and also
             changed alarm status is recorded in 'eventSeverity'.
             The 'eventTotalCount' and 'eventCount' is sequential number.
             'eventTotalCount' is notification event count since agent was
             booted.
             'eventAdditionalText' provides some event description."
        ::= 1
    
    -- 1.3.6.1.4.1.119.2.3.69.203.513.501.2.3.2.0.1
    statusChange TRAP-TYPE
        ENTERPRISE  ipeStatusTrapItemVar
        VARIABLES   { eventTotalCount, eventCount, eventTime, eventType,
                      eventResourceID, eventStatusValue,
                      eventAdditionalText1, eventAdditionalText2,
                      eventAdditionalText3, eventAdditionalText4,
                      eventAdditionalText5 }
        DESCRIPTION
            "Trap for Status (Integer)
             This notification reports that the object's status whose SYNTAX
             is INTEGER type may have changed.
             The object information is recorded in 'eventResourceID'.
             The 'eventTotalCount' and 'eventCount' is sequential number.
             'eventTotalCount' is notification event count since agent was
             booted.
             'eventAdditionalText' provides some event description."
        ::= 1
    
    -- 1.3.6.1.4.1.119.2.3.69.203.513.501.2.3.2.0.2
    statusChangeDspStr TRAP-TYPE
        ENTERPRISE  ipeStatusTrapItemVar
        VARIABLES   { eventTotalCount, eventCount, eventTime, eventType,
                      eventResourceID, eventStatusValueDspStr,
                      eventAdditionalText1, eventAdditionalText2,
                      eventAdditionalText3, eventAdditionalText4,
                      eventAdditionalText5 }
        DESCRIPTION
            "Trap for Status (Display String)
             This notification reports that the object's status whose SYNTAX
             is DISPLAY STRING type may have changed.
             The object information is recorded in 'eventResourceID'.
             The 'eventTotalCount' and 'eventCount' is sequential number.
             'eventTotalCount' is notification event count since agent was
             booted.
             'eventAdditionalText' provides some event description."
        ::= 2
    
    -- 1.3.6.1.4.1.119.2.3.69.203.513.501.2.3.2.0.3
    statusChangeOctStr TRAP-TYPE
        ENTERPRISE  ipeStatusTrapItemVar
        VARIABLES   { eventTotalCount, eventCount, eventTime, eventType,
                      eventResourceID, eventStatusValueOctStr,
                      eventAdditionalText1, eventAdditionalText2,
                      eventAdditionalText3, eventAdditionalText4,
                      eventAdditionalText5 }
        DESCRIPTION
            "Trap for Status (Octet String)
             This notification reports that the object's status whose SYNTAX
             is OCTET STRING type may have changed.
             The object information is recorded in 'eventResourceID'.
             The 'eventTotalCount' and 'eventCount' is sequential number.
             'eventTotalCount' is notification event count since agent was
             booted.
             'eventAdditionalText' provides some event description."
        ::= 3
    
    -- 1.3.6.1.4.1.119.2.3.69.203.513.501.2.3.2.0.4
    statusChangeUnsigned32 TRAP-TYPE
        ENTERPRISE  ipeStatusTrapItemVar
        VARIABLES   { eventTotalCount, eventCount, eventTime, eventType,
                      eventResourceID, eventStatusValueUnsigned32,
                      eventAdditionalText1, eventAdditionalText2,
                      eventAdditionalText3, eventAdditionalText4,
                      eventAdditionalText5 }
        DESCRIPTION
            "Trap for Status (Unsigned32)
             This notification reports that the object's status whose SYNTAX
             is Unsigned type may have changed.
             The object information is recorded in 'eventResourceID' and also
             changed alarm status is recorded in 'eventSeverity'.
             The 'eventTotalCount' and 'eventCount' is sequential number.
             'eventTotalCount' is notification event count since agent was
             booted.
             'eventAdditionalText' provides some event description."
        ::= 4
    
    -- 1.3.6.1.4.1.119.2.3.69.203.513.501.2.3.3.0.1
    controlEvent TRAP-TYPE
        ENTERPRISE  ipeControlTrapItemVar
        VARIABLES   { eventTotalCount, eventCount, eventTime, eventType,
                      eventResourceID, eventControlValue,
                      eventRecordUserName, eventRecordAccessType,
                      eventRecordAccessFrom, eventAdditionalText1,
                      eventAdditionalText2, eventAdditionalText3,
                      eventAdditionalText4, eventAdditionalText5,
                      eventRecordAccessFromV6 }
        DESCRIPTION
            "Trap for Control (Integer)
             This notification reports that the object's value is changed by
             snmp-set request.
             The object information is recorded in 'eventResourceID' and also
             changed value is recorded in 'eventControlValue'.
             The 'eventTotalCount' and 'eventCount' is sequential number.
             'eventTotalCount' is notification event count since agent was
             booted.
             'eventAdditionalText' provides some event description."
        ::= 1
    
    -- 1.3.6.1.4.1.119.2.3.69.203.513.501.2.3.3.0.2
    controlEventDspStr TRAP-TYPE
        ENTERPRISE  ipeControlTrapItemVar
        VARIABLES   { eventTotalCount, eventCount, eventTime, eventType,
                      eventResourceID, eventControlValueDspStr,
                      eventRecordUserName, eventRecordAccessType,
                      eventRecordAccessFrom, eventAdditionalText1,
                      eventAdditionalText2, eventAdditionalText3,
                      eventAdditionalText4, eventAdditionalText5,
                      eventRecordAccessFromV6 }
        DESCRIPTION
            "Trap for Control (Display String)
             This notification reports that the object's value is changed by
             snmp-set request.
             The object information is recorded in 'eventResourceID' and also
             changed value is recorded in 'eventControlValueDspStr'.
             The 'eventTotalCount' and 'eventCount' is sequential number.
             'eventTotalCount' is notification event count since agent was
             booted.
             'eventAdditionalText' provides some event description."
        ::= 2
    
    -- 1.3.6.1.4.1.119.2.3.69.203.513.501.2.3.3.0.3
    controlEventOctStr TRAP-TYPE
        ENTERPRISE  ipeControlTrapItemVar
        VARIABLES   { eventTotalCount, eventCount, eventTime, eventType,
                      eventResourceID, eventControlValueOctStr,
                      eventRecordUserName, eventRecordAccessType,
                      eventRecordAccessFrom, eventAdditionalText1,
                      eventAdditionalText2, eventAdditionalText3,
                      eventAdditionalText4, eventAdditionalText5,
                      eventRecordAccessFromV6 }
        DESCRIPTION
            "Trap for Control (Octet String)
             This notification reports that the object's value is changed by
             snmp-set request.
             The object information is recorded in 'eventResourceID' and also
             changed value is recorded in 'eventControlValueOctStr'.
             The 'eventTotalCount' and 'eventCount' is sequential number.
             'eventTotalCount' is notification event count since agent was
             booted.
             'eventAdditionalText' provides some event description."
        ::= 3
    
    -- 1.3.6.1.4.1.119.2.3.69.203.513.501.2.3.3.0.4
    controlEventUnsigned32 TRAP-TYPE
        ENTERPRISE  ipeControlTrapItemVar
        VARIABLES   { eventTotalCount, eventCount, eventTime, eventType,
                      eventResourceID, eventControlValueUnsigned32,
                      eventRecordUserName, eventRecordAccessType,
                      eventRecordAccessFrom, eventAdditionalText1,
                      eventAdditionalText2, eventAdditionalText3,
                      eventAdditionalText4, eventAdditionalText5,
                      eventRecordAccessFromV6 }
        DESCRIPTION
            "Trap for Control (Unsigned32)
             This notification reports that the object's value is changed by
             snmp-set request.
             The object information is recorded in 'eventResourceID' and also
             changed value is recorded in 'eventControlValueUnsigned32'.
             The 'eventTotalCount' and 'eventCount' is sequential number.
             'eventTotalCount' is notification event count since agent was
             booted.
             'eventAdditionalText' provides some event description."
        ::= 4
    
    -- 1.3.6.1.4.1.119.2.3.69.203.513.501.2.3.4.0.1
    fileDownloadEvent TRAP-TYPE
        ENTERPRISE  ipeFileDownloadTrapItemVar
        VARIABLES   { eventTotalCount, eventCount, eventTime, eventType,
                      eventResourceID, eventDownloadModule,
                      eventDownloadStatus, eventAdditionalText1,
                      eventAdditionalText2, eventAdditionalText3,
                      eventAdditionalText4, eventAdditionalText5 }
        DESCRIPTION
            "Trap for File Download
             This notification reports that the executed download status is
             changed. Changed value is recorded in 'eventDownloadStatus'. The
             'eventTotalCount' and 'eventCount' is sequential number.
             'eventTotalCount' is notification event count since agent was
             booted.
             'eventAdditionalText' provides some event description."
        ::= 1
    
    -- 1.3.6.1.4.1.119.2.3.69.203.513.501.2.3.4.0.2
    fileUpdateEvent TRAP-TYPE
        ENTERPRISE  ipeFileDownloadTrapItemVar
        VARIABLES   { eventTotalCount, eventCount, eventTime, eventType,
                      eventResourceID, eventUpdateDetail, eventUpdateStatus,
                      eventAdditionalText1, eventAdditionalText2,
                      eventAdditionalText3, eventAdditionalText4,
                      eventAdditionalText5 }
        DESCRIPTION
            "Trap for File Update
             This notification reports that the executed file update status is
             changed. Changed value is recorded in 'eventUpdateStatus'. The
             'eventTotalCount' and 'eventCount' is sequential number.
             'eventTotalCount' is notification event count since agent was
             booted.
             'eventAdditionalText' provides some event description."
        ::= 2
    
END -- end of module MIB-EMS-IPASOLINK-VR4-COMMON-MIB.
