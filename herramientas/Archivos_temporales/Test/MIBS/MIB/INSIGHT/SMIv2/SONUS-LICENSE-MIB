--
-- This SMIv2 module has been generated by smidump 0.2-cvs. Do not edit.
--

SONUS-LICENSE-MIB DEFINITIONS ::= BEGIN

IMPORTS
    sysName, sysObjectID
        FROM SNMPv2-MIB
    Integer32, MODULE-IDENTITY, NOTIFICATION-TYPE, OBJECT-TYPE
        FROM SNMPv2-SMI
    DateAndTime, DisplayString
        FROM SNMPv2-TC
    sonusEventClass, sonusEventDescription, sonusEventLevel, 
    sonusEventTime
        FROM SONUS-COMMON-MIB
    sonusEmsMIB
        FROM SONUS-EMS-MIB;

sonusLicMIB MODULE-IDENTITY
    LAST-UPDATED    "201505060000Z"
    ORGANIZATION    
            "Sonus Networks, Inc."
    CONTACT-INFO    
            "   Customer Support    
             Sonus Networks, Inc.
             250 Apollo Drive
             Chelmsford, MA 01824
             USA
             
             Tel: 978-614-8100
             Fax: 978-614-8609"
    DESCRIPTION     
            "The MIB Module for Sonus License Manager related objects."
    ::= { sonusEmsMIB 3 }


sonusLicMIBObjects OBJECT IDENTIFIER
    ::= { sonusLicMIB 1 }

sonusLicNotifications OBJECT IDENTIFIER
    ::= { sonusLicMIB 2 }

sonusLicNotificationsPrefix OBJECT IDENTIFIER
    ::= { sonusLicNotifications 0 }

sonusLicNotificationsObjects OBJECT IDENTIFIER
    ::= { sonusLicNotifications 1 }

sonusLicTargetType OBJECT-TYPE
    SYNTAX          DisplayString
    MAX-ACCESS      read-only
    STATUS          current
    DESCRIPTION     
            "The license target type."
    ::= { sonusLicNotificationsObjects 1 }

sonusLicTargetId OBJECT-TYPE
    SYNTAX          DisplayString
    MAX-ACCESS      read-only
    STATUS          current
    DESCRIPTION     
            "The license target identifier"
    ::= { sonusLicNotificationsObjects 2 }

sonusLicFeatureId OBJECT-TYPE
    SYNTAX          DisplayString
    MAX-ACCESS      read-only
    STATUS          current
    DESCRIPTION     
            "The license feature identifier."
    ::= { sonusLicNotificationsObjects 3 }

sonusLicExpireTime OBJECT-TYPE
    SYNTAX          DateAndTime
    MAX-ACCESS      read-only
    STATUS          current
    DESCRIPTION     
            "The date/time when the license expires."
    ::= { sonusLicNotificationsObjects 4 }

sonusLicPresentValue OBJECT-TYPE
    SYNTAX          Integer32
    MAX-ACCESS      read-only
    STATUS          current
    DESCRIPTION     
            "The current license usage."
    ::= { sonusLicNotificationsObjects 5 }

sonusLicConfiguredValue OBJECT-TYPE
    SYNTAX          Integer32
    MAX-ACCESS      read-only
    STATUS          current
    DESCRIPTION     
            "The current configured maximum usage."
    ::= { sonusLicNotificationsObjects 6 }

sonusLicPPDFileName OBJECT-TYPE
    SYNTAX          DisplayString
    MAX-ACCESS      read-only
    STATUS          current
    DESCRIPTION     
            "Auto-generated post-paid license usage file name."
    ::= { sonusLicNotificationsObjects 9 }

sonusLicExpiredNotification NOTIFICATION-TYPE
    OBJECTS         { sonusEventTime, sonusEventDescription, 
                      sonusEventClass, sonusEventLevel, 
                      sonusLicTargetType, sonusLicTargetId, 
                      sonusLicFeatureId, sonusLicExpireTime }
    STATUS          current
    DESCRIPTION     
            "A license identified by the tuple sonusTargetType, sonusTargetId, and sonusFeatureId has expired as of sonusLicExpireTime."
    ::= { sonusLicNotificationsPrefix 1 }

sonusLicStatusNotification NOTIFICATION-TYPE
    OBJECTS         { sonusEventTime, sonusEventDescription, 
                      sonusEventClass, sonusEventLevel, 
                      sonusLicTargetType, sonusLicTargetId, 
                      sonusLicFeatureId, sonusLicExpireTime }
    STATUS          current
    DESCRIPTION     
            "A license identified by the tuple sonusTargetType, sonusTargetId, and sonusFeatureId will expire as of sonusLicExpireTime."
    ::= { sonusLicNotificationsPrefix 2 }

sonusLicUsageExceededNotification NOTIFICATION-TYPE
    OBJECTS         { sonusEventTime, sonusEventDescription, 
                      sonusEventClass, sonusEventLevel, 
                      sonusLicTargetType, sonusLicTargetId, 
                      sonusLicFeatureId, sonusLicPresentValue, 
                      sonusLicConfiguredValue }
    STATUS          current
    DESCRIPTION     
            "Current usage, sonusLicPresentValue, for the license identified by the tuple sonusTargetType, sonusTargetId, and sonusFeatureId has exceeded the configured maximum value, sonusLicConfiguredValue."
    ::= { sonusLicNotificationsPrefix 3 }

sonusLicUsageStatusNotification NOTIFICATION-TYPE
    OBJECTS         { sonusEventTime, sonusEventDescription, 
                      sonusEventClass, sonusEventLevel, 
                      sonusLicTargetType, sonusLicTargetId, 
                      sonusLicFeatureId, sonusLicPresentValue, 
                      sonusLicConfiguredValue }
    STATUS          current
    DESCRIPTION     
            "Current usage, sonusLicPresentValue, for the license identified by the tuple sonusTargetType, sonusTargetId, and sonusFeatureId is approching the configured maximum value, sonusLicConfiguredValue."
    ::= { sonusLicNotificationsPrefix 4 }

sonusLicStatusClearNotification NOTIFICATION-TYPE
    OBJECTS         { sonusEventTime, sonusEventDescription, 
                      sonusEventClass, sonusEventLevel, 
                      sonusLicTargetType, sonusLicTargetId, 
                      sonusLicFeatureId, sonusLicExpireTime }
    STATUS          current
    DESCRIPTION     
            "Configuration pertaining to pre-expiry has changed resulting in clearing of this pre-expiry notification."
    ::= { sonusLicNotificationsPrefix 5 }

sonusLicUsageStatusClearNotification NOTIFICATION-TYPE
    OBJECTS         { sonusEventTime, sonusEventDescription, 
                      sonusEventClass, sonusEventLevel, 
                      sonusLicTargetType, sonusLicTargetId, 
                      sonusLicFeatureId, sonusLicPresentValue, 
                      sonusLicConfiguredValue }
    STATUS          current
    DESCRIPTION     
            "Current usage, sonusLicPresentValue, for the license identified by the tuple sonusTargetType, sonusTargetId, and sonusFeatureId is now below the configured maximum value, sonusLicConfiguredValue."
    ::= { sonusLicNotificationsPrefix 6 }

sonusLicSBCLicMismatchNotification NOTIFICATION-TYPE
    OBJECTS         { sonusEventTime, sonusEventDescription, 
                      sonusEventClass, sonusEventLevel, 
                      sonusLicTargetType }
    STATUS          current
    DESCRIPTION     
            "Installed license count of SBC-POL-RTU has exceeded that of SBC-RTU."
    ::= { sonusLicNotificationsPrefix 7 }

sonusLicSBCLicMismatchClearNotification NOTIFICATION-TYPE
    OBJECTS         { sonusEventTime, sonusEventDescription, 
                      sonusEventClass, sonusEventLevel, 
                      sonusLicTargetType }
    STATUS          current
    DESCRIPTION     
            "License count mismatch of SBC-RTU and SBC-POL-RTU is rectified. Clear trap for sonusLicSBCLicMismatchNotification."
    ::= { sonusLicNotificationsPrefix 8 }

sonusLicFailedToSendUsageFileNotification NOTIFICATION-TYPE
    OBJECTS         { sonusEventTime, sonusEventDescription, 
                      sonusEventClass, sonusEventLevel, 
                      sonusLicPPDFileName }
    STATUS          current
    DESCRIPTION     
            "Failed to send the autogenerated post-paid license usage file."
    ::= { sonusLicNotificationsPrefix 9 }

sonusLicFailedToRegisterWithITNotification NOTIFICATION-TYPE
    OBJECTS         { sonusEventTime, sonusEventDescription, 
                      sonusEventClass, sonusEventLevel }
    STATUS          current
    DESCRIPTION     
            "Failed to register with IT."
    ::= { sonusLicNotificationsPrefix 10 }

END -- end of module SONUS-LICENSE-MIB.
