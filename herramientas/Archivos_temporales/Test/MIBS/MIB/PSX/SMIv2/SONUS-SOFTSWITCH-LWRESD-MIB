--
-- This SMIv2 module has been generated by smidump 0.2-cvs. Do not edit.
--

SONUS-SOFTSWITCH-LWRESD-MIB DEFINITIONS ::= BEGIN

IMPORTS
    InetAddress, InetAddressType
        FROM INET-ADDRESS-MIB
    Counter32, Gauge32, Integer32, MODULE-IDENTITY, NOTIFICATION-TYPE, 
    OBJECT-TYPE
        FROM SNMPv2-SMI
    sonusEventClass, sonusEventDescription, sonusEventLevel, 
    sonusEventTime
        FROM SONUS-COMMON-MIB
    sonusServicesMIBs
        FROM SONUS-SMI
    SonusSoftSwitchDomainName, SonusSoftSwitchDomainNameLength
        FROM SONUS-SOFTSWITCH-TC;

sonusSoftSwitchLwresdMIB MODULE-IDENTITY
    LAST-UPDATED    "201107010000Z"
    ORGANIZATION    
            "Sonus Networks, Inc."
    CONTACT-INFO    
            "   Customer Support    
             Sonus Networks, Inc.
             7 Tech Park Dr
             Westford, MA 01886
             USA
             
             Tel: 978-614-8100
             Fax: 978-614-8609"
    DESCRIPTION     
            "The MIB Module for SoftSwitch Lwresd Management."
    ::= { sonusServicesMIBs 33 }


sonusSoftSwitchLwresdMIBObjects OBJECT IDENTIFIER
    ::= { sonusSoftSwitchLwresdMIB 1 }

sonusSoftSwitchLwresdMIBNotifications OBJECT IDENTIFIER
    ::= { sonusSoftSwitchLwresdMIB 2 }

sonusSoftSwitchLwresdMIBNotificationsPrefix OBJECT IDENTIFIER
    ::= { sonusSoftSwitchLwresdMIBNotifications 0 }

sonusSoftSwitchLwresdStatistics OBJECT IDENTIFIER
    ::= { sonusSoftSwitchLwresdMIB 3 }

sonusSoftSwitchLwresdServerCounters OBJECT IDENTIFIER
    ::= { sonusSoftSwitchLwresdStatistics 1 }

sonusSoftSwitchLwresdCountersServerTable OBJECT-TYPE
    SYNTAX          SEQUENCE OF SonusSoftSwitchLwresdCountersServerEntry
    MAX-ACCESS      not-accessible
    STATUS          current
    DESCRIPTION     
            "Server Table to hold ENUM/DNS server counters."
    ::= { sonusSoftSwitchLwresdServerCounters 1 }

sonusSoftSwitchLwresdCountersServerEntry OBJECT-TYPE
    SYNTAX          SonusSoftSwitchLwresdCountersServerEntry
    MAX-ACCESS      not-accessible
    STATUS          current
    DESCRIPTION     
            "An entry in the ENUM/DNS Server Table."
    INDEX           { sonusSoftSwitchLwresdCountersServerIpAddressType, 
                      sonusSoftSwitchLwresdCountersServerIpAddress, 
                      sonusSoftSwitchLwresdCountersServerPort, 
                      sonusSoftSwitchLwresdCountersServerTransportType }
    ::= { sonusSoftSwitchLwresdCountersServerTable 1 }

SonusSoftSwitchLwresdCountersServerEntry ::=
    SEQUENCE {
        sonusSoftSwitchLwresdCountersServerIpAddressType                InetAddressType,
        sonusSoftSwitchLwresdCountersServerIpAddress            InetAddress,
        sonusSoftSwitchLwresdCountersServerPort       Integer32,
        sonusSoftSwitchLwresdCountersServerTransportType                Integer32,
        sonusSoftSwitchLwresdCountersServerNAPTRReq           Counter32,
        sonusSoftSwitchLwresdCountersServerNAPTRRsp           Counter32,
        sonusSoftSwitchLwresdCountersServerNAPTRNoAnsRsp                Counter32,
        sonusSoftSwitchLwresdCountersServerNAPTRTimeout               Counter32,
        sonusSoftSwitchLwresdCountersServerNAPTRDestUnreachable                       Counter32,
        sonusSoftSwitchLwresdCountersServerSRVReq         Counter32,
        sonusSoftSwitchLwresdCountersServerSRVRsp         Counter32,
        sonusSoftSwitchLwresdCountersServerSRVNoAnsRsp              Counter32,
        sonusSoftSwitchLwresdCountersServerSRVTimeout             Counter32,
        sonusSoftSwitchLwresdCountersServerSRVDestUnreachable                     Counter32,
        sonusSoftSwitchLwresdCountersServerAReq       Counter32,
        sonusSoftSwitchLwresdCountersServerARsp       Counter32,
        sonusSoftSwitchLwresdCountersServerANoAnsRsp            Counter32,
        sonusSoftSwitchLwresdCountersServerATimeout           Counter32,
        sonusSoftSwitchLwresdCountersServerADestUnreachable                   Counter32,
        sonusSoftSwitchLwresdCountersServerAAAAReq          Counter32,
        sonusSoftSwitchLwresdCountersServerAAAARsp          Counter32,
        sonusSoftSwitchLwresdCountersServerAAAANoAnsRsp               Counter32,
        sonusSoftSwitchLwresdCountersServerAAAATimeout              Counter32,
        sonusSoftSwitchLwresdCountersServerAAAADestUnreachable                      Counter32,
        sonusSoftSwitchLwresdCountersServerTCPConnectionAttempt                       Counter32,
        sonusSoftSwitchLwresdCountersServerTCPConnectionEstablished                           Counter32,
        sonusSoftSwitchLwresdCountersServerTCPConnectionFailed                      Counter32
    }

sonusSoftSwitchLwresdCountersServerIpAddressType OBJECT-TYPE
    SYNTAX          InetAddressType
    MAX-ACCESS      read-only
    STATUS          current
    DESCRIPTION     
            "The ENUM/DNS Server IP address Type."
    ::= { sonusSoftSwitchLwresdCountersServerEntry 1 }

sonusSoftSwitchLwresdCountersServerIpAddress OBJECT-TYPE
    SYNTAX          InetAddress
    MAX-ACCESS      read-only
    STATUS          current
    DESCRIPTION     
            "The ENUM/DNS Server IP address."
    ::= { sonusSoftSwitchLwresdCountersServerEntry 2 }

sonusSoftSwitchLwresdCountersServerPort OBJECT-TYPE
    SYNTAX          Integer32
    MAX-ACCESS      read-only
    STATUS          current
    DESCRIPTION     
            "The Port on which the ENUM/DNS server is listening."
    ::= { sonusSoftSwitchLwresdCountersServerEntry 3 }

sonusSoftSwitchLwresdCountersServerTransportType OBJECT-TYPE
    SYNTAX          Integer32
    MAX-ACCESS      read-only
    STATUS          current
    DESCRIPTION     
            "The transport type used towards the ENUM/DNS Server.1-tcp, 2-udp, 3-tcp fallback"
    ::= { sonusSoftSwitchLwresdCountersServerEntry 4 }

sonusSoftSwitchLwresdCountersServerNAPTRReq OBJECT-TYPE
    SYNTAX          Counter32
    MAX-ACCESS      read-only
    STATUS          current
    DESCRIPTION     
            "Number of NAPTR requests sent to the server."
    ::= { sonusSoftSwitchLwresdCountersServerEntry 5 }

sonusSoftSwitchLwresdCountersServerNAPTRRsp OBJECT-TYPE
    SYNTAX          Counter32
    MAX-ACCESS      read-only
    STATUS          current
    DESCRIPTION     
            "Number of NAPTR responses received from the Server."
    ::= { sonusSoftSwitchLwresdCountersServerEntry 6 }

sonusSoftSwitchLwresdCountersServerNAPTRNoAnsRsp OBJECT-TYPE
    SYNTAX          Counter32
    MAX-ACCESS      read-only
    STATUS          current
    DESCRIPTION     
            "Number of NAPTR no answer responses received from the  Server."
    ::= { sonusSoftSwitchLwresdCountersServerEntry 7 }

sonusSoftSwitchLwresdCountersServerNAPTRTimeout OBJECT-TYPE
    SYNTAX          Counter32
    MAX-ACCESS      read-only
    STATUS          current
    DESCRIPTION     
            "Number of NAPTR requests timed out for the Server."
    ::= { sonusSoftSwitchLwresdCountersServerEntry 8 }

sonusSoftSwitchLwresdCountersServerNAPTRDestUnreachable OBJECT-TYPE
    SYNTAX          Counter32
    MAX-ACCESS      read-only
    STATUS          current
    DESCRIPTION     
            "Number of NAPTR requests failed due to destination unreachable for the Server."
    ::= { sonusSoftSwitchLwresdCountersServerEntry 9 }

sonusSoftSwitchLwresdCountersServerSRVReq OBJECT-TYPE
    SYNTAX          Counter32
    MAX-ACCESS      read-only
    STATUS          current
    DESCRIPTION     
            "Number of SRV requests sent to the Server."
    ::= { sonusSoftSwitchLwresdCountersServerEntry 10 }

sonusSoftSwitchLwresdCountersServerSRVRsp OBJECT-TYPE
    SYNTAX          Counter32
    MAX-ACCESS      read-only
    STATUS          current
    DESCRIPTION     
            "Number of SRV responses received from the  Server."
    ::= { sonusSoftSwitchLwresdCountersServerEntry 11 }

sonusSoftSwitchLwresdCountersServerSRVNoAnsRsp OBJECT-TYPE
    SYNTAX          Counter32
    MAX-ACCESS      read-only
    STATUS          current
    DESCRIPTION     
            "Number of SRV no answer responses received from the Server."
    ::= { sonusSoftSwitchLwresdCountersServerEntry 12 }

sonusSoftSwitchLwresdCountersServerSRVTimeout OBJECT-TYPE
    SYNTAX          Counter32
    MAX-ACCESS      read-only
    STATUS          current
    DESCRIPTION     
            "Number of SRV requests timed out for the Server."
    ::= { sonusSoftSwitchLwresdCountersServerEntry 13 }

sonusSoftSwitchLwresdCountersServerSRVDestUnreachable OBJECT-TYPE
    SYNTAX          Counter32
    MAX-ACCESS      read-only
    STATUS          current
    DESCRIPTION     
            "Number of SRV requests failed due to destination unreachable for the Server."
    ::= { sonusSoftSwitchLwresdCountersServerEntry 14 }

sonusSoftSwitchLwresdCountersServerAReq OBJECT-TYPE
    SYNTAX          Counter32
    MAX-ACCESS      read-only
    STATUS          current
    DESCRIPTION     
            "Number of A requests sent to the Server."
    ::= { sonusSoftSwitchLwresdCountersServerEntry 15 }

sonusSoftSwitchLwresdCountersServerARsp OBJECT-TYPE
    SYNTAX          Counter32
    MAX-ACCESS      read-only
    STATUS          current
    DESCRIPTION     
            "Number of A responses received from the  Server."
    ::= { sonusSoftSwitchLwresdCountersServerEntry 16 }

sonusSoftSwitchLwresdCountersServerANoAnsRsp OBJECT-TYPE
    SYNTAX          Counter32
    MAX-ACCESS      read-only
    STATUS          current
    DESCRIPTION     
            "Number of A no answer responses received from the Server."
    ::= { sonusSoftSwitchLwresdCountersServerEntry 17 }

sonusSoftSwitchLwresdCountersServerATimeout OBJECT-TYPE
    SYNTAX          Counter32
    MAX-ACCESS      read-only
    STATUS          current
    DESCRIPTION     
            "Number of A requests timed out for the Server."
    ::= { sonusSoftSwitchLwresdCountersServerEntry 18 }

sonusSoftSwitchLwresdCountersServerADestUnreachable OBJECT-TYPE
    SYNTAX          Counter32
    MAX-ACCESS      read-only
    STATUS          current
    DESCRIPTION     
            "Number of A requests failed due to destination unreachable for the Server."
    ::= { sonusSoftSwitchLwresdCountersServerEntry 19 }

sonusSoftSwitchLwresdCountersServerAAAAReq OBJECT-TYPE
    SYNTAX          Counter32
    MAX-ACCESS      read-only
    STATUS          current
    DESCRIPTION     
            "Number of AAAA requests sent to the Server."
    ::= { sonusSoftSwitchLwresdCountersServerEntry 20 }

sonusSoftSwitchLwresdCountersServerAAAARsp OBJECT-TYPE
    SYNTAX          Counter32
    MAX-ACCESS      read-only
    STATUS          current
    DESCRIPTION     
            "Number of AAAA responses received from the  Server."
    ::= { sonusSoftSwitchLwresdCountersServerEntry 21 }

sonusSoftSwitchLwresdCountersServerAAAANoAnsRsp OBJECT-TYPE
    SYNTAX          Counter32
    MAX-ACCESS      read-only
    STATUS          current
    DESCRIPTION     
            "Number of AAAA no answer responses received from the Server."
    ::= { sonusSoftSwitchLwresdCountersServerEntry 22 }

sonusSoftSwitchLwresdCountersServerAAAATimeout OBJECT-TYPE
    SYNTAX          Counter32
    MAX-ACCESS      read-only
    STATUS          current
    DESCRIPTION     
            "Number of AAAA requests timed out for the Server."
    ::= { sonusSoftSwitchLwresdCountersServerEntry 23 }

sonusSoftSwitchLwresdCountersServerAAAADestUnreachable OBJECT-TYPE
    SYNTAX          Counter32
    MAX-ACCESS      read-only
    STATUS          current
    DESCRIPTION     
            "Number of AAAA requests failed due to destination unreachable for the Server."
    ::= { sonusSoftSwitchLwresdCountersServerEntry 24 }

sonusSoftSwitchLwresdCountersServerTCPConnectionAttempt OBJECT-TYPE
    SYNTAX          Counter32
    MAX-ACCESS      read-only
    STATUS          current
    DESCRIPTION     
            "Number of TCP Connection esteblishment attempts."
    ::= { sonusSoftSwitchLwresdCountersServerEntry 25 }

sonusSoftSwitchLwresdCountersServerTCPConnectionEstablished OBJECT-TYPE
    SYNTAX          Counter32
    MAX-ACCESS      read-only
    STATUS          current
    DESCRIPTION     
            "Number of established TCP Connections."
    ::= { sonusSoftSwitchLwresdCountersServerEntry 26 }

sonusSoftSwitchLwresdCountersServerTCPConnectionFailed OBJECT-TYPE
    SYNTAX          Counter32
    MAX-ACCESS      read-only
    STATUS          current
    DESCRIPTION     
            "Number of failed TCP Connections."
    ::= { sonusSoftSwitchLwresdCountersServerEntry 27 }

sonusSoftSwitchLwresdZoneCounters OBJECT IDENTIFIER
    ::= { sonusSoftSwitchLwresdStatistics 2 }

sonusSoftSwitchLwresdCountersZoneTable OBJECT-TYPE
    SYNTAX          SEQUENCE OF SonusSoftSwitchLwresdCountersZoneEntry
    MAX-ACCESS      not-accessible
    STATUS          current
    DESCRIPTION     
            "Zone table to hold ENUM/DNS Zone counters."
    ::= { sonusSoftSwitchLwresdZoneCounters 1 }

sonusSoftSwitchLwresdCountersZoneEntry OBJECT-TYPE
    SYNTAX          SonusSoftSwitchLwresdCountersZoneEntry
    MAX-ACCESS      not-accessible
    STATUS          current
    DESCRIPTION     
            "An entry in the ENUM/DNS Zone table."
    INDEX           { sonusSoftSwitchLwresdCountersZoneNameLength, 
                      sonusSoftSwitchLwresdCountersZoneName, 
                      sonusSoftSwitchLwresdCountersZoneTransportType }
    ::= { sonusSoftSwitchLwresdCountersZoneTable 1 }

SonusSoftSwitchLwresdCountersZoneEntry ::=
    SEQUENCE {
        sonusSoftSwitchLwresdCountersZoneNameLength           SonusSoftSwitchDomainNameLength,
        sonusSoftSwitchLwresdCountersZoneName     SonusSoftSwitchDomainName,
        sonusSoftSwitchLwresdCountersZoneTransportType              Integer32,
        sonusSoftSwitchLwresdCountersZoneNAPTRReq         Counter32,
        sonusSoftSwitchLwresdCountersZoneNAPTRRsp         Counter32,
        sonusSoftSwitchLwresdCountersZoneNAPTRNoAnsRsp              Counter32,
        sonusSoftSwitchLwresdCountersZoneNAPTRTimeout             Counter32,
        sonusSoftSwitchLwresdCountersZoneNAPTRDestUnreachable                     Counter32,
        sonusSoftSwitchLwresdCountersZoneSRVReq       Counter32,
        sonusSoftSwitchLwresdCountersZoneSRVRsp       Counter32,
        sonusSoftSwitchLwresdCountersZoneSRVNoAnsRsp            Counter32,
        sonusSoftSwitchLwresdCountersZoneSRVTimeout           Counter32,
        sonusSoftSwitchLwresdCountersZoneSRVDestUnreachable                   Counter32,
        sonusSoftSwitchLwresdCountersZoneAReq     Counter32,
        sonusSoftSwitchLwresdCountersZoneARsp     Counter32,
        sonusSoftSwitchLwresdCountersZoneANoAnsRsp          Counter32,
        sonusSoftSwitchLwresdCountersZoneATimeout         Counter32,
        sonusSoftSwitchLwresdCountersZoneADestUnreachable                 Counter32,
        sonusSoftSwitchLwresdCountersZoneAAAAReq        Counter32,
        sonusSoftSwitchLwresdCountersZoneAAAARsp        Counter32,
        sonusSoftSwitchLwresdCountersZoneAAAANoAnsRsp             Counter32,
        sonusSoftSwitchLwresdCountersZoneAAAATimeout            Counter32,
        sonusSoftSwitchLwresdCountersZoneAAAADestUnreachable                    Counter32,
        sonusSoftSwitchLwresdCountersZoneTCPConnectionAttempt                     Counter32,
        sonusSoftSwitchLwresdCountersZoneTCPConnectionEstablished                         Counter32,
        sonusSoftSwitchLwresdCountersZoneTCPConnectionFailed                    Counter32
    }

sonusSoftSwitchLwresdCountersZoneNameLength OBJECT-TYPE
    SYNTAX          SonusSoftSwitchDomainNameLength
    MAX-ACCESS      read-only
    STATUS          current
    DESCRIPTION     
            "Length of the Zone Name."
    ::= { sonusSoftSwitchLwresdCountersZoneEntry 1 }

sonusSoftSwitchLwresdCountersZoneName OBJECT-TYPE
    SYNTAX          SonusSoftSwitchDomainName
    MAX-ACCESS      read-only
    STATUS          current
    DESCRIPTION     
            "Zone Name for which counters are applicable."
    ::= { sonusSoftSwitchLwresdCountersZoneEntry 2 }

sonusSoftSwitchLwresdCountersZoneTransportType OBJECT-TYPE
    SYNTAX          Integer32
    MAX-ACCESS      read-only
    STATUS          current
    DESCRIPTION     
            "The transport type used towards the Zone.1-tcp, 2-udp, 3-tcp fallback"
    ::= { sonusSoftSwitchLwresdCountersZoneEntry 3 }

sonusSoftSwitchLwresdCountersZoneNAPTRReq OBJECT-TYPE
    SYNTAX          Counter32
    MAX-ACCESS      read-only
    STATUS          current
    DESCRIPTION     
            "Number of NAPTR requests sent for the Zone."
    ::= { sonusSoftSwitchLwresdCountersZoneEntry 4 }

sonusSoftSwitchLwresdCountersZoneNAPTRRsp OBJECT-TYPE
    SYNTAX          Counter32
    MAX-ACCESS      read-only
    STATUS          current
    DESCRIPTION     
            "Number of NAPTR responses received for the Zone."
    ::= { sonusSoftSwitchLwresdCountersZoneEntry 5 }

sonusSoftSwitchLwresdCountersZoneNAPTRNoAnsRsp OBJECT-TYPE
    SYNTAX          Counter32
    MAX-ACCESS      read-only
    STATUS          current
    DESCRIPTION     
            "Number of NAPTR no answer responses received for the Zone."
    ::= { sonusSoftSwitchLwresdCountersZoneEntry 6 }

sonusSoftSwitchLwresdCountersZoneNAPTRTimeout OBJECT-TYPE
    SYNTAX          Counter32
    MAX-ACCESS      read-only
    STATUS          current
    DESCRIPTION     
            "Number of NAPTR requests timed out for the Zone."
    ::= { sonusSoftSwitchLwresdCountersZoneEntry 7 }

sonusSoftSwitchLwresdCountersZoneNAPTRDestUnreachable OBJECT-TYPE
    SYNTAX          Counter32
    MAX-ACCESS      read-only
    STATUS          current
    DESCRIPTION     
            "Number of NAPTR requests failed due to destination unreachable for the Zone."
    ::= { sonusSoftSwitchLwresdCountersZoneEntry 8 }

sonusSoftSwitchLwresdCountersZoneSRVReq OBJECT-TYPE
    SYNTAX          Counter32
    MAX-ACCESS      read-only
    STATUS          current
    DESCRIPTION     
            "Number of SRV requests sent for the Zone."
    ::= { sonusSoftSwitchLwresdCountersZoneEntry 9 }

sonusSoftSwitchLwresdCountersZoneSRVRsp OBJECT-TYPE
    SYNTAX          Counter32
    MAX-ACCESS      read-only
    STATUS          current
    DESCRIPTION     
            "Number of SRV responses received for the Zone."
    ::= { sonusSoftSwitchLwresdCountersZoneEntry 10 }

sonusSoftSwitchLwresdCountersZoneSRVNoAnsRsp OBJECT-TYPE
    SYNTAX          Counter32
    MAX-ACCESS      read-only
    STATUS          current
    DESCRIPTION     
            "Number of SRV no answer responses received for the Zone."
    ::= { sonusSoftSwitchLwresdCountersZoneEntry 11 }

sonusSoftSwitchLwresdCountersZoneSRVTimeout OBJECT-TYPE
    SYNTAX          Counter32
    MAX-ACCESS      read-only
    STATUS          current
    DESCRIPTION     
            "Number of SRV requests timed out for the Zone."
    ::= { sonusSoftSwitchLwresdCountersZoneEntry 12 }

sonusSoftSwitchLwresdCountersZoneSRVDestUnreachable OBJECT-TYPE
    SYNTAX          Counter32
    MAX-ACCESS      read-only
    STATUS          current
    DESCRIPTION     
            "Number of SRV requests failed due to destination unreachable for the Zone."
    ::= { sonusSoftSwitchLwresdCountersZoneEntry 13 }

sonusSoftSwitchLwresdCountersZoneAReq OBJECT-TYPE
    SYNTAX          Counter32
    MAX-ACCESS      read-only
    STATUS          current
    DESCRIPTION     
            "Number of A requests sent for the Zone."
    ::= { sonusSoftSwitchLwresdCountersZoneEntry 14 }

sonusSoftSwitchLwresdCountersZoneARsp OBJECT-TYPE
    SYNTAX          Counter32
    MAX-ACCESS      read-only
    STATUS          current
    DESCRIPTION     
            "Number of A responses received for the Zone."
    ::= { sonusSoftSwitchLwresdCountersZoneEntry 15 }

sonusSoftSwitchLwresdCountersZoneANoAnsRsp OBJECT-TYPE
    SYNTAX          Counter32
    MAX-ACCESS      read-only
    STATUS          current
    DESCRIPTION     
            "Number of A no answer responses received for the Zone."
    ::= { sonusSoftSwitchLwresdCountersZoneEntry 16 }

sonusSoftSwitchLwresdCountersZoneATimeout OBJECT-TYPE
    SYNTAX          Counter32
    MAX-ACCESS      read-only
    STATUS          current
    DESCRIPTION     
            "Number of A requests timed out for the Zone."
    ::= { sonusSoftSwitchLwresdCountersZoneEntry 17 }

sonusSoftSwitchLwresdCountersZoneADestUnreachable OBJECT-TYPE
    SYNTAX          Counter32
    MAX-ACCESS      read-only
    STATUS          current
    DESCRIPTION     
            "Number of A requests failed due to destination unreachable for the Zone."
    ::= { sonusSoftSwitchLwresdCountersZoneEntry 18 }

sonusSoftSwitchLwresdCountersZoneAAAAReq OBJECT-TYPE
    SYNTAX          Counter32
    MAX-ACCESS      read-only
    STATUS          current
    DESCRIPTION     
            "Number of AAAA requests sent for the Zone."
    ::= { sonusSoftSwitchLwresdCountersZoneEntry 19 }

sonusSoftSwitchLwresdCountersZoneAAAARsp OBJECT-TYPE
    SYNTAX          Counter32
    MAX-ACCESS      read-only
    STATUS          current
    DESCRIPTION     
            "Number of AAAA responses received for the Zone."
    ::= { sonusSoftSwitchLwresdCountersZoneEntry 20 }

sonusSoftSwitchLwresdCountersZoneAAAANoAnsRsp OBJECT-TYPE
    SYNTAX          Counter32
    MAX-ACCESS      read-only
    STATUS          current
    DESCRIPTION     
            "Number of AAAA no answer responses received for the Zone."
    ::= { sonusSoftSwitchLwresdCountersZoneEntry 21 }

sonusSoftSwitchLwresdCountersZoneAAAATimeout OBJECT-TYPE
    SYNTAX          Counter32
    MAX-ACCESS      read-only
    STATUS          current
    DESCRIPTION     
            "Number of AAAA requests timed out for the Zone."
    ::= { sonusSoftSwitchLwresdCountersZoneEntry 22 }

sonusSoftSwitchLwresdCountersZoneAAAADestUnreachable OBJECT-TYPE
    SYNTAX          Counter32
    MAX-ACCESS      read-only
    STATUS          current
    DESCRIPTION     
            "Number of AAAA requests failed due to destination unreachable for the Zone."
    ::= { sonusSoftSwitchLwresdCountersZoneEntry 23 }

sonusSoftSwitchLwresdCountersZoneTCPConnectionAttempt OBJECT-TYPE
    SYNTAX          Counter32
    MAX-ACCESS      read-only
    STATUS          current
    DESCRIPTION     
            "Number of TCP connection establishment attempts for the Zone."
    ::= { sonusSoftSwitchLwresdCountersZoneEntry 24 }

sonusSoftSwitchLwresdCountersZoneTCPConnectionEstablished OBJECT-TYPE
    SYNTAX          Counter32
    MAX-ACCESS      read-only
    STATUS          current
    DESCRIPTION     
            "Number of successfully established TCP connections for the Zone."
    ::= { sonusSoftSwitchLwresdCountersZoneEntry 25 }

sonusSoftSwitchLwresdCountersZoneTCPConnectionFailed OBJECT-TYPE
    SYNTAX          Counter32
    MAX-ACCESS      read-only
    STATUS          current
    DESCRIPTION     
            "Number of failed TCP connections for the Zone."
    ::= { sonusSoftSwitchLwresdCountersZoneEntry 26 }

sonusSoftSwitchLwresdServerHpcCounters OBJECT IDENTIFIER
    ::= { sonusSoftSwitchLwresdStatistics 3 }

sonusSoftSwitchLwresdHpcCountersServerTable OBJECT-TYPE
    SYNTAX          SEQUENCE OF SonusSoftSwitchLwresdHpcCountersServerEntry
    MAX-ACCESS      not-accessible
    STATUS          current
    DESCRIPTION     
            "Server Table to hold ENUM/DNS server counters for High Priority and Normal calls."
    ::= { sonusSoftSwitchLwresdServerHpcCounters 1 }

sonusSoftSwitchLwresdHpcCountersServerEntry OBJECT-TYPE
    SYNTAX          SonusSoftSwitchLwresdHpcCountersServerEntry
    MAX-ACCESS      not-accessible
    STATUS          current
    DESCRIPTION     
            "An entry in the ENUM/DNS Server Table."
    INDEX           { 
                      sonusSoftSwitchLwresdHpcCountersServerIpAddressType, 
                      sonusSoftSwitchLwresdHpcCountersServerIpAddress, 
                      sonusSoftSwitchLwresdHpcCountersServerPort, 
                      sonusSoftSwitchLwresdHpcCountersServerTransportType }
    ::= { sonusSoftSwitchLwresdHpcCountersServerTable 1 }

SonusSoftSwitchLwresdHpcCountersServerEntry ::=
    SEQUENCE {
        sonusSoftSwitchLwresdHpcCountersServerIpAddressType                   InetAddressType,
        sonusSoftSwitchLwresdHpcCountersServerIpAddress               InetAddress,
        sonusSoftSwitchLwresdHpcCountersServerPort          Integer32,
        sonusSoftSwitchLwresdHpcCountersServerTransportType                   Integer32,
        sonusSoftSwitchLwresdHpcCountersServerHpcReq            Counter32,
        sonusSoftSwitchLwresdHpcCountersServerHpcRsp            Counter32,
        sonusSoftSwitchLwresdHpcCountersServerHpcNoAnsRsp                 Counter32,
        sonusSoftSwitchLwresdHpcCountersServerHpcTimeout                Counter32,
        sonusSoftSwitchLwresdHpcCountersServerHpcDestUnreachable                        Counter32,
        sonusSoftSwitchLwresdHpcCountersServerNonHpcReq               Counter32,
        sonusSoftSwitchLwresdHpcCountersServerNonHpcRsp               Counter32,
        sonusSoftSwitchLwresdHpcCountersServerNonHpcNoAnsRsp                    Counter32,
        sonusSoftSwitchLwresdHpcCountersServerNonHpcTimeout                   Counter32,
        sonusSoftSwitchLwresdHpcCountersServerNonHpcDestUnreachable                           Counter32
    }

sonusSoftSwitchLwresdHpcCountersServerIpAddressType OBJECT-TYPE
    SYNTAX          InetAddressType
    MAX-ACCESS      read-only
    STATUS          current
    DESCRIPTION     
            "The ENUM/DNS Server IP address Type."
    ::= { sonusSoftSwitchLwresdHpcCountersServerEntry 1 }

sonusSoftSwitchLwresdHpcCountersServerIpAddress OBJECT-TYPE
    SYNTAX          InetAddress
    MAX-ACCESS      read-only
    STATUS          current
    DESCRIPTION     
            "The ENUM/DNS Server IP address."
    ::= { sonusSoftSwitchLwresdHpcCountersServerEntry 2 }

sonusSoftSwitchLwresdHpcCountersServerPort OBJECT-TYPE
    SYNTAX          Integer32
    MAX-ACCESS      read-only
    STATUS          current
    DESCRIPTION     
            "The Port on which the ENUM/DNS server is listening."
    ::= { sonusSoftSwitchLwresdHpcCountersServerEntry 3 }

sonusSoftSwitchLwresdHpcCountersServerTransportType OBJECT-TYPE
    SYNTAX          Integer32
    MAX-ACCESS      read-only
    STATUS          current
    DESCRIPTION     
            "The transport type used towards the ENUM/DNS Server.1-tcp, 2-udp, 3-tcp fallback"
    ::= { sonusSoftSwitchLwresdHpcCountersServerEntry 4 }

sonusSoftSwitchLwresdHpcCountersServerHpcReq OBJECT-TYPE
    SYNTAX          Counter32
    MAX-ACCESS      read-only
    STATUS          current
    DESCRIPTION     
            "Number of DNS requests sent to the server for High Priority Calls ."
    ::= { sonusSoftSwitchLwresdHpcCountersServerEntry 5 }

sonusSoftSwitchLwresdHpcCountersServerHpcRsp OBJECT-TYPE
    SYNTAX          Counter32
    MAX-ACCESS      read-only
    STATUS          current
    DESCRIPTION     
            "Number of DNS responses received from the Server for High Priority Calls ."
    ::= { sonusSoftSwitchLwresdHpcCountersServerEntry 6 }

sonusSoftSwitchLwresdHpcCountersServerHpcNoAnsRsp OBJECT-TYPE
    SYNTAX          Counter32
    MAX-ACCESS      read-only
    STATUS          current
    DESCRIPTION     
            "Number of DNS no answer responses received from the  Server for High Priority Calls ."
    ::= { sonusSoftSwitchLwresdHpcCountersServerEntry 7 }

sonusSoftSwitchLwresdHpcCountersServerHpcTimeout OBJECT-TYPE
    SYNTAX          Counter32
    MAX-ACCESS      read-only
    STATUS          current
    DESCRIPTION     
            "Number of HPC DNS requests timed out for the Server."
    ::= { sonusSoftSwitchLwresdHpcCountersServerEntry 8 }

sonusSoftSwitchLwresdHpcCountersServerHpcDestUnreachable OBJECT-TYPE
    SYNTAX          Counter32
    MAX-ACCESS      read-only
    STATUS          current
    DESCRIPTION     
            "Number of HPC DNS requests failed due to destination unreachable for the Server."
    ::= { sonusSoftSwitchLwresdHpcCountersServerEntry 9 }

sonusSoftSwitchLwresdHpcCountersServerNonHpcReq OBJECT-TYPE
    SYNTAX          Counter32
    MAX-ACCESS      read-only
    STATUS          current
    DESCRIPTION     
            "Number of DNS requests sent to the Server for Non High Priority Calls."
    ::= { sonusSoftSwitchLwresdHpcCountersServerEntry 10 }

sonusSoftSwitchLwresdHpcCountersServerNonHpcRsp OBJECT-TYPE
    SYNTAX          Counter32
    MAX-ACCESS      read-only
    STATUS          current
    DESCRIPTION     
            "Number of DNS responses received from the Server for Non High Priority Calls.."
    ::= { sonusSoftSwitchLwresdHpcCountersServerEntry 11 }

sonusSoftSwitchLwresdHpcCountersServerNonHpcNoAnsRsp OBJECT-TYPE
    SYNTAX          Counter32
    MAX-ACCESS      read-only
    STATUS          current
    DESCRIPTION     
            "Number of DNS no answer responses received from the Server for Non High Priority Calls.."
    ::= { sonusSoftSwitchLwresdHpcCountersServerEntry 12 }

sonusSoftSwitchLwresdHpcCountersServerNonHpcTimeout OBJECT-TYPE
    SYNTAX          Counter32
    MAX-ACCESS      read-only
    STATUS          current
    DESCRIPTION     
            "Number of Non HPC DNS requests timed out for the Server."
    ::= { sonusSoftSwitchLwresdHpcCountersServerEntry 13 }

sonusSoftSwitchLwresdHpcCountersServerNonHpcDestUnreachable OBJECT-TYPE
    SYNTAX          Counter32
    MAX-ACCESS      read-only
    STATUS          current
    DESCRIPTION     
            "Number of Non HPC DNS requests failed due to destination unreachable for the Server."
    ::= { sonusSoftSwitchLwresdHpcCountersServerEntry 14 }

sonusSoftSwitchLwresdZoneHpcCounters OBJECT IDENTIFIER
    ::= { sonusSoftSwitchLwresdStatistics 4 }

sonusSoftSwitchLwresdHpcCountersZoneTable OBJECT-TYPE
    SYNTAX          SEQUENCE OF SonusSoftSwitchLwresdHpcCountersZoneEntry
    MAX-ACCESS      not-accessible
    STATUS          current
    DESCRIPTION     
            "Zone table to hold ENUM/DNS Zone Hpc counters."
    ::= { sonusSoftSwitchLwresdZoneHpcCounters 1 }

sonusSoftSwitchLwresdHpcCountersZoneEntry OBJECT-TYPE
    SYNTAX          SonusSoftSwitchLwresdHpcCountersZoneEntry
    MAX-ACCESS      not-accessible
    STATUS          current
    DESCRIPTION     
            "An entry in the ENUM/DNS Zone table."
    INDEX           { sonusSoftSwitchLwresdHpcCountersZoneNameLength, 
                      sonusSoftSwitchLwresdHpcCountersZoneName, 
                      sonusSoftSwitchLwresdHpcCountersZoneTransportType }
    ::= { sonusSoftSwitchLwresdHpcCountersZoneTable 1 }

SonusSoftSwitchLwresdHpcCountersZoneEntry ::=
    SEQUENCE {
        sonusSoftSwitchLwresdHpcCountersZoneNameLength              SonusSoftSwitchDomainNameLength,
        sonusSoftSwitchLwresdHpcCountersZoneName        SonusSoftSwitchDomainName,
        sonusSoftSwitchLwresdHpcCountersZoneTransportType                 Integer32,
        sonusSoftSwitchLwresdHpcCountersZoneHpcReq          Counter32,
        sonusSoftSwitchLwresdHpcCountersZoneHpcRsp          Counter32,
        sonusSoftSwitchLwresdHpcCountersZoneHpcNoAnsRsp               Counter32,
        sonusSoftSwitchLwresdHpcCountersZoneHpcTimeout              Counter32,
        sonusSoftSwitchLwresdHpcCountersZoneHpcDestUnreachable                      Counter32,
        sonusSoftSwitchLwresdHpcCountersZoneNonHpcReq             Counter32,
        sonusSoftSwitchLwresdHpcCountersZoneNonHpcRsp             Counter32,
        sonusSoftSwitchLwresdHpcCountersZoneNonHpcNoAnsRsp                  Counter32,
        sonusSoftSwitchLwresdHpcCountersZoneNonHpcTimeout                 Counter32,
        sonusSoftSwitchLwresdHpcCountersZoneNonHpcDestUnreachable                         Counter32
    }

sonusSoftSwitchLwresdHpcCountersZoneNameLength OBJECT-TYPE
    SYNTAX          SonusSoftSwitchDomainNameLength
    MAX-ACCESS      read-only
    STATUS          current
    DESCRIPTION     
            "Length of the Zone Name."
    ::= { sonusSoftSwitchLwresdHpcCountersZoneEntry 1 }

sonusSoftSwitchLwresdHpcCountersZoneName OBJECT-TYPE
    SYNTAX          SonusSoftSwitchDomainName
    MAX-ACCESS      read-only
    STATUS          current
    DESCRIPTION     
            "Zone Name for which counters are applicable."
    ::= { sonusSoftSwitchLwresdHpcCountersZoneEntry 2 }

sonusSoftSwitchLwresdHpcCountersZoneTransportType OBJECT-TYPE
    SYNTAX          Integer32
    MAX-ACCESS      read-only
    STATUS          current
    DESCRIPTION     
            "The transport type used towards the Zone.1-tcp, 2-udp, 3-tcp fallback"
    ::= { sonusSoftSwitchLwresdHpcCountersZoneEntry 3 }

sonusSoftSwitchLwresdHpcCountersZoneHpcReq OBJECT-TYPE
    SYNTAX          Counter32
    MAX-ACCESS      read-only
    STATUS          current
    DESCRIPTION     
            "Number of HPC DNS requests sent for the Zone."
    ::= { sonusSoftSwitchLwresdHpcCountersZoneEntry 4 }

sonusSoftSwitchLwresdHpcCountersZoneHpcRsp OBJECT-TYPE
    SYNTAX          Counter32
    MAX-ACCESS      read-only
    STATUS          current
    DESCRIPTION     
            "Number of HPC DNS responses received for the Zone."
    ::= { sonusSoftSwitchLwresdHpcCountersZoneEntry 5 }

sonusSoftSwitchLwresdHpcCountersZoneHpcNoAnsRsp OBJECT-TYPE
    SYNTAX          Counter32
    MAX-ACCESS      read-only
    STATUS          current
    DESCRIPTION     
            "Number of HPC DNS no answer responses received for the Zone."
    ::= { sonusSoftSwitchLwresdHpcCountersZoneEntry 6 }

sonusSoftSwitchLwresdHpcCountersZoneHpcTimeout OBJECT-TYPE
    SYNTAX          Counter32
    MAX-ACCESS      read-only
    STATUS          current
    DESCRIPTION     
            "Number of HPC DNS requests timed out for the Zone."
    ::= { sonusSoftSwitchLwresdHpcCountersZoneEntry 7 }

sonusSoftSwitchLwresdHpcCountersZoneHpcDestUnreachable OBJECT-TYPE
    SYNTAX          Counter32
    MAX-ACCESS      read-only
    STATUS          current
    DESCRIPTION     
            "Number of HPC DNS requests failed due to destination unreachable for the Zone."
    ::= { sonusSoftSwitchLwresdHpcCountersZoneEntry 8 }

sonusSoftSwitchLwresdHpcCountersZoneNonHpcReq OBJECT-TYPE
    SYNTAX          Counter32
    MAX-ACCESS      read-only
    STATUS          current
    DESCRIPTION     
            "Number of Non HPC DNS requests sent for the Zone."
    ::= { sonusSoftSwitchLwresdHpcCountersZoneEntry 9 }

sonusSoftSwitchLwresdHpcCountersZoneNonHpcRsp OBJECT-TYPE
    SYNTAX          Counter32
    MAX-ACCESS      read-only
    STATUS          current
    DESCRIPTION     
            "Number of Non HPC DNS responses received for the Zone."
    ::= { sonusSoftSwitchLwresdHpcCountersZoneEntry 10 }

sonusSoftSwitchLwresdHpcCountersZoneNonHpcNoAnsRsp OBJECT-TYPE
    SYNTAX          Counter32
    MAX-ACCESS      read-only
    STATUS          current
    DESCRIPTION     
            "Number of Non HPC DNS no answer responses received for the Zone."
    ::= { sonusSoftSwitchLwresdHpcCountersZoneEntry 11 }

sonusSoftSwitchLwresdHpcCountersZoneNonHpcTimeout OBJECT-TYPE
    SYNTAX          Counter32
    MAX-ACCESS      read-only
    STATUS          current
    DESCRIPTION     
            "Number of Non HPC DNS requests timed out for the Zone."
    ::= { sonusSoftSwitchLwresdHpcCountersZoneEntry 12 }

sonusSoftSwitchLwresdHpcCountersZoneNonHpcDestUnreachable OBJECT-TYPE
    SYNTAX          Counter32
    MAX-ACCESS      read-only
    STATUS          current
    DESCRIPTION     
            "Number of Non HPC DNS requests failed due to destination unreachable for the Zone."
    ::= { sonusSoftSwitchLwresdHpcCountersZoneEntry 13 }

sonusSoftswitchLWRESDDNSServerBlacklistedNotification NOTIFICATION-TYPE
    OBJECTS         { sonusEventDescription, sonusEventClass, 
                      sonusEventLevel, sonusEventTime }
    STATUS          current
    DESCRIPTION     
            "DNS Server is Black listed"
    ::= { sonusSoftSwitchLwresdMIBNotificationsPrefix 1 }

sonusSoftswitchLWRESDDNSServerRecoveredNotification NOTIFICATION-TYPE
    OBJECTS         { sonusEventDescription, sonusEventClass, 
                      sonusEventLevel, sonusEventTime }
    STATUS          current
    DESCRIPTION     
            "DNS Serevr is Recovered"
    ::= { sonusSoftSwitchLwresdMIBNotificationsPrefix 2 }

sonusSoftswitchLWRESDEDNSResponseFailure NOTIFICATION-TYPE
    OBJECTS         { sonusEventDescription, sonusEventClass, 
                      sonusEventLevel, sonusEventTime }
    STATUS          current
    DESCRIPTION     
            "Failure Response for EDNS query with NOT-IMPLE, FORMERR or SERVFAIL"
    ::= { sonusSoftSwitchLwresdMIBNotificationsPrefix 3 }

sonusSoftswitchLWRESDEDNSResponseSuccess NOTIFICATION-TYPE
    OBJECTS         { sonusEventDescription, sonusEventClass, 
                      sonusEventLevel, sonusEventTime }
    STATUS          current
    DESCRIPTION     
            "Successful Response for EDNS query which failed earlier for that domain"
    ::= { sonusSoftSwitchLwresdMIBNotificationsPrefix 4 }

sonusSoftswitchLWRESDTTLExpiredRRFallback NOTIFICATION-TYPE
    OBJECTS         { sonusEventDescription, sonusEventClass, 
                      sonusEventLevel, sonusEventTime }
    STATUS          current
    DESCRIPTION     
            "Fallback to TTL expired RR due to DNS response failure"
    ::= { sonusSoftSwitchLwresdMIBNotificationsPrefix 5 }

sonusSoftswitchLWRESDNormalDNSResponse NOTIFICATION-TYPE
    OBJECTS         { sonusEventDescription, sonusEventClass, 
                      sonusEventLevel, sonusEventTime }
    STATUS          current
    DESCRIPTION     
            "Normal DNS response for a query that previously used expired TTL RR"
    ::= { sonusSoftSwitchLwresdMIBNotificationsPrefix 6 }

END -- end of module SONUS-SOFTSWITCH-LWRESD-MIB.
