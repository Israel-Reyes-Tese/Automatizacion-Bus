--
-- This SMIv1 module has been generated by smidump 0.2-cvs. Do not edit.
--

SONUS-SOFTSWITCH-SCPA-MIB DEFINITIONS ::= BEGIN

IMPORTS
    InetAddress, InetAddressType
        FROM INET-ADDRESS-MIB
    OBJECT-TYPE
        FROM RFC-1212
    TRAP-TYPE
        FROM RFC-1215
    Counter, Gauge, IpAddress, TimeTicks
        FROM RFC1155-SMI
    DisplayString
        FROM SNMPv2-TC
    sonusEventClass, sonusEventDescription, sonusEventLevel, 
    sonusEventTime
        FROM SONUS-COMMON-MIB
    sonusServicesMIBs
        FROM SONUS-SMI
    sonusSoftSwitchTMAppliedControlType, 
    sonusSoftSwitchTMProvControlType
        FROM SONUS-SOFTSWITCH-MIB
    SonusCriteriaFormat, SonusTMIdentifier
        FROM SONUS-SOFTSWITCH-TC
    SonusSystemName
        FROM SONUS-TC;

sonusSoftSwitchSCPAMIB OBJECT IDENTIFIER
    ::= { sonusServicesMIBs 20 }

-- sonusSoftSwitchSCPAMIB MODULE-IDENTITY
--     LAST-UPDATED    "200211040000Z"
--     ORGANIZATION    
--             "Sonus Networks, Inc."
--     CONTACT-INFO    
--             "   Customer Support    
--              Sonus Networks, Inc.
--              250 Apollo Drive
--              Chelmsford, MA 01824
--              USA
--              
--              Tel: 978-614-8100
--              Fax: 978-614-8609"
--     DESCRIPTION     
--             "The MIB Module for SoftSwitch SCPA Management."
--     ::= { sonusServicesMIBs 20 }


sonusSoftSwitchSCPAMIBObjects OBJECT IDENTIFIER
    ::= { sonusSoftSwitchSCPAMIB 1 }

sonusSoftSwitchSCPAStatistics OBJECT IDENTIFIER
    ::= { sonusSoftSwitchSCPAMIBObjects 1 }

sonusSoftSwitchScpaTcap OBJECT IDENTIFIER
    ::= { sonusSoftSwitchSCPAStatistics 1 }

sonusSoftSwitchScpaAnsiTcap OBJECT IDENTIFIER
    ::= { sonusSoftSwitchScpaTcap 1 }

sonusSoftSwitchScpaAnsiTcapQuerySent OBJECT-TYPE
    SYNTAX          Counter
    ACCESS          read-only
    STATUS          mandatory
    DESCRIPTION     
            "This counter keeps track of the number of ANSI TCAP queries 
             which have been sent by PSX."
    ::= { sonusSoftSwitchScpaAnsiTcap 1 }

sonusSoftSwitchScpaAnsiTcapQueryRcvd OBJECT-TYPE
    SYNTAX          Counter
    ACCESS          read-only
    STATUS          mandatory
    DESCRIPTION     
            "This counter keeps track of the number of ANSI TCAP queries 
             which have been received by PSX."
    ::= { sonusSoftSwitchScpaAnsiTcap 2 }

sonusSoftSwitchScpaAnsiTcapTimeout OBJECT-TYPE
    SYNTAX          Counter
    ACCESS          read-only
    STATUS          mandatory
    DESCRIPTION     
            "This counter keeps track of the number of ANSI TCAP queries 
             which have timed out."
    ::= { sonusSoftSwitchScpaAnsiTcap 3 }

sonusSoftSwitchScpaAnsiTcapError OBJECT-TYPE
    SYNTAX          Counter
    ACCESS          read-only
    STATUS          mandatory
    DESCRIPTION     
            "This counter keeps track of the number of ANSI TCAP error messages 
             which have been received by PSX."
    ::= { sonusSoftSwitchScpaAnsiTcap 4 }

sonusSoftSwitchScpaAnsiTcapPurged OBJECT-TYPE
    SYNTAX          Counter
    ACCESS          read-only
    STATUS          mandatory
    DESCRIPTION     
            "This counter keeps track of the number of ANSI TCAP queries 
             which have been purged by PSX."
    ::= { sonusSoftSwitchScpaAnsiTcap 5 }

sonusSoftSwitchScpaAnsiTcapRspSent OBJECT-TYPE
    SYNTAX          Counter
    ACCESS          read-only
    STATUS          mandatory
    DESCRIPTION     
            "This counter keeps track of the number of ANSI TCAP responses 
             which have been sent by PSX."
    ::= { sonusSoftSwitchScpaAnsiTcap 6 }

sonusSoftSwitchScpaAnsiTcapRspRcvd OBJECT-TYPE
    SYNTAX          Counter
    ACCESS          read-only
    STATUS          mandatory
    DESCRIPTION     
            "This counter keeps track of the number of ANSI TCAP responses 
             which have been received by PSX."
    ::= { sonusSoftSwitchScpaAnsiTcap 7 }

sonusSoftSwitchScpaAnsiTcapOpenTrans OBJECT-TYPE
    SYNTAX          Gauge
    ACCESS          read-only
    STATUS          mandatory
    DESCRIPTION     
            "This counter keeps track of the number of ANSI TCAP transactions 
             which are still open pending for response."
    ::= { sonusSoftSwitchScpaAnsiTcap 8 }

sonusSoftSwitchScpaAnsiTcapDialogIdPoolSize OBJECT-TYPE
    SYNTAX          Counter
    ACCESS          read-only
    STATUS          mandatory
    DESCRIPTION     
            "This counter keeps track of the number of ANSI TCAP dialog ids 
             which have been allocated by PSX/SGX."
    ::= { sonusSoftSwitchScpaAnsiTcap 9 }

sonusSoftSwitchScpaAnsiTcapIntervalTime OBJECT-TYPE
    SYNTAX          TimeTicks
    ACCESS          read-only
    STATUS          mandatory
    DESCRIPTION     
            "This variable contains the end of interval time stamp for 
             the specified interval."
    ::= { sonusSoftSwitchScpaAnsiTcap 10 }

sonusSoftSwitchScpaGsmTcap OBJECT IDENTIFIER
    ::= { sonusSoftSwitchScpaTcap 2 }

sonusSoftSwitchScpaGsmTcapQuerySent OBJECT-TYPE
    SYNTAX          Counter
    ACCESS          read-only
    STATUS          mandatory
    DESCRIPTION     
            "This counter keeps track of the number of GSM TCAP queries 
             which have been sent by PSX."
    ::= { sonusSoftSwitchScpaGsmTcap 1 }

sonusSoftSwitchScpaGsmTcapQueryRcvd OBJECT-TYPE
    SYNTAX          Counter
    ACCESS          read-only
    STATUS          mandatory
    DESCRIPTION     
            "This counter keeps track of the number of GSM TCAP queries 
             which have been received by PSX."
    ::= { sonusSoftSwitchScpaGsmTcap 2 }

sonusSoftSwitchScpaGsmTcapTimeout OBJECT-TYPE
    SYNTAX          Counter
    ACCESS          read-only
    STATUS          mandatory
    DESCRIPTION     
            "This counter keeps track of the number of GSM TCAP queries 
             which have timed out."
    ::= { sonusSoftSwitchScpaGsmTcap 3 }

sonusSoftSwitchScpaGsmTcapError OBJECT-TYPE
    SYNTAX          Counter
    ACCESS          read-only
    STATUS          mandatory
    DESCRIPTION     
            "This counter keeps track of the number of GSM TCAP error messages 
             which have been received by PSX."
    ::= { sonusSoftSwitchScpaGsmTcap 4 }

sonusSoftSwitchScpaGsmTcapPurged OBJECT-TYPE
    SYNTAX          Counter
    ACCESS          read-only
    STATUS          mandatory
    DESCRIPTION     
            "This counter keeps track of the number of GSM TCAP queries 
             which have been purged by PSX."
    ::= { sonusSoftSwitchScpaGsmTcap 5 }

sonusSoftSwitchScpaGsmTcapRspSent OBJECT-TYPE
    SYNTAX          Counter
    ACCESS          read-only
    STATUS          mandatory
    DESCRIPTION     
            "This counter keeps track of the number of GSM TCAP responses 
             which have been sent by PSX."
    ::= { sonusSoftSwitchScpaGsmTcap 6 }

sonusSoftSwitchScpaGsmTcapRspRcvd OBJECT-TYPE
    SYNTAX          Counter
    ACCESS          read-only
    STATUS          mandatory
    DESCRIPTION     
            "This counter keeps track of the number of GSM TCAP responses 
             which have been received by PSX."
    ::= { sonusSoftSwitchScpaGsmTcap 7 }

sonusSoftSwitchScpaGsmTcapOpenTrans OBJECT-TYPE
    SYNTAX          Gauge
    ACCESS          read-only
    STATUS          mandatory
    DESCRIPTION     
            "This counter keeps track of the number of GSM TCAP transactions 
             which are still open pending for response."
    ::= { sonusSoftSwitchScpaGsmTcap 8 }

sonusSoftSwitchScpaGsmTcapDialogIdPoolSize OBJECT-TYPE
    SYNTAX          Counter
    ACCESS          read-only
    STATUS          mandatory
    DESCRIPTION     
            "This counter keeps track of the number of GSM TCAP dialog ids 
             which have been allocated by PSX/SGX."
    ::= { sonusSoftSwitchScpaGsmTcap 9 }

sonusSoftSwitchScpaGsmTcapIntervalTime OBJECT-TYPE
    SYNTAX          TimeTicks
    ACCESS          read-only
    STATUS          mandatory
    DESCRIPTION     
            "This variable contains the end of interval time stamp for 
             the specified interval."
    ::= { sonusSoftSwitchScpaGsmTcap 10 }

sonusSoftSwitchScpaGsmTcapAbortRcvd OBJECT-TYPE
    SYNTAX          Counter
    ACCESS          read-only
    STATUS          mandatory
    DESCRIPTION     
            "This counter keeps track of the number of GSM TCAP abort messages
             which have been received by PSX."
    ::= { sonusSoftSwitchScpaGsmTcap 11 }

sonusSoftSwitchScpaGsmTcapAbortSent OBJECT-TYPE
    SYNTAX          Counter
    ACCESS          read-only
    STATUS          mandatory
    DESCRIPTION     
            "This counter keeps track of the number of GSM TCAP abort messages
             which have been sent by PSX."
    ::= { sonusSoftSwitchScpaGsmTcap 12 }

sonusSoftSwitchScpaGsmTcapContinueRcvd OBJECT-TYPE
    SYNTAX          Counter
    ACCESS          read-only
    STATUS          mandatory
    DESCRIPTION     
            "This counter keeps track of the number of GSM TCAP continue messages
             which have been received by PSX."
    ::= { sonusSoftSwitchScpaGsmTcap 13 }

sonusSoftSwitchScpaGsmTcapContinueSent OBJECT-TYPE
    SYNTAX          Counter
    ACCESS          read-only
    STATUS          mandatory
    DESCRIPTION     
            "This counter keeps track of the number of GSM TCAP continue messages
             which have been sent by PSX."
    ::= { sonusSoftSwitchScpaGsmTcap 14 }

sonusSoftSwitchScpaGsmTcapInvokeRcvd OBJECT-TYPE
    SYNTAX          Counter
    ACCESS          read-only
    STATUS          mandatory
    DESCRIPTION     
            "This counter keeps track of the number of GSM TCAP Invoke components
             which have been received by PSX."
    ::= { sonusSoftSwitchScpaGsmTcap 15 }

sonusSoftSwitchScpaGsmTcapInvokeSent OBJECT-TYPE
    SYNTAX          Counter
    ACCESS          read-only
    STATUS          mandatory
    DESCRIPTION     
            "This counter keeps track of the number of GSM TCAP Invoke components
             which have been sent by PSX."
    ::= { sonusSoftSwitchScpaGsmTcap 16 }

sonusSoftSwitchScpaTtcTcap OBJECT IDENTIFIER
    ::= { sonusSoftSwitchScpaTcap 3 }

sonusSoftSwitchScpaTtcTcapQuerySent OBJECT-TYPE
    SYNTAX          Counter
    ACCESS          read-only
    STATUS          mandatory
    DESCRIPTION     
            "This counter keeps track of the number of TTC TCAP queries 
             which have been sent by PSX."
    ::= { sonusSoftSwitchScpaTtcTcap 1 }

sonusSoftSwitchScpaTtcTcapReturnSuccess OBJECT-TYPE
    SYNTAX          Counter
    ACCESS          read-only
    STATUS          mandatory
    DESCRIPTION     
            "This counter keeps track of the number of TTC TCAP responses 
             which have been received successfully by PSX."
    ::= { sonusSoftSwitchScpaTtcTcap 2 }

sonusSoftSwitchScpaTtcTcapReturnError OBJECT-TYPE
    SYNTAX          Counter
    ACCESS          read-only
    STATUS          mandatory
    DESCRIPTION     
            "This counter keeps track of the number of TTC TCAP error messages 
             which have been received by PSX."
    ::= { sonusSoftSwitchScpaTtcTcap 3 }

sonusSoftSwitchScpaTtcTcapReturnAbort OBJECT-TYPE
    SYNTAX          Counter
    ACCESS          read-only
    STATUS          mandatory
    DESCRIPTION     
            "This counter keeps track of the number of TTC TCAP abort messages 
             which have been received by PSX."
    ::= { sonusSoftSwitchScpaTtcTcap 4 }

sonusSoftSwitchScpaTtcTcapUdtsReplied OBJECT-TYPE
    SYNTAX          Counter
    ACCESS          read-only
    STATUS          mandatory
    DESCRIPTION     
            "This counter keeps track of the number of TTC TCAP UDTS replies 
             which have been received by PSX."
    ::= { sonusSoftSwitchScpaTtcTcap 5 }

sonusSoftSwitchScpaTtcTcapRspTimeout OBJECT-TYPE
    SYNTAX          Counter
    ACCESS          read-only
    STATUS          mandatory
    DESCRIPTION     
            "This counter keeps track of the number of TTC TCAP queries
             which have been timed out by PSX."
    ::= { sonusSoftSwitchScpaTtcTcap 6 }

sonusSoftSwitchScpaTtcTcapIntervalTime OBJECT-TYPE
    SYNTAX          TimeTicks
    ACCESS          read-only
    STATUS          mandatory
    DESCRIPTION     
            "This variable contains the end of interval time stamp for 
             the specified interval."
    ::= { sonusSoftSwitchScpaTtcTcap 7 }

sonusSoftSwitchScpaItuTcap OBJECT IDENTIFIER
    ::= { sonusSoftSwitchScpaTcap 4 }

sonusSoftSwitchScpaItuTcapQuerySent OBJECT-TYPE
    SYNTAX          Counter
    ACCESS          read-only
    STATUS          mandatory
    DESCRIPTION     
            "This counter keeps track of the number of ITU TCAP queries 
             which have been sent by PSX."
    ::= { sonusSoftSwitchScpaItuTcap 1 }

sonusSoftSwitchScpaItuTcapQueryRcvd OBJECT-TYPE
    SYNTAX          Counter
    ACCESS          read-only
    STATUS          mandatory
    DESCRIPTION     
            "This counter keeps track of the number of ITU TCAP queries 
             which have been received by PSX."
    ::= { sonusSoftSwitchScpaItuTcap 2 }

sonusSoftSwitchScpaItuTcapTimeout OBJECT-TYPE
    SYNTAX          Counter
    ACCESS          read-only
    STATUS          mandatory
    DESCRIPTION     
            "This counter keeps track of the number of ITU TCAP queries 
             which have timed out."
    ::= { sonusSoftSwitchScpaItuTcap 3 }

sonusSoftSwitchScpaItuTcapError OBJECT-TYPE
    SYNTAX          Counter
    ACCESS          read-only
    STATUS          mandatory
    DESCRIPTION     
            "This counter keeps track of the number of ITU TCAP error messages 
             which have been received by PSX."
    ::= { sonusSoftSwitchScpaItuTcap 4 }

sonusSoftSwitchScpaItuTcapPurged OBJECT-TYPE
    SYNTAX          Counter
    ACCESS          read-only
    STATUS          mandatory
    DESCRIPTION     
            "This counter keeps track of the number of ITU TCAP queries 
             which have been purged by PSX."
    ::= { sonusSoftSwitchScpaItuTcap 5 }

sonusSoftSwitchScpaItuTcapRspSent OBJECT-TYPE
    SYNTAX          Counter
    ACCESS          read-only
    STATUS          mandatory
    DESCRIPTION     
            "This counter keeps track of the number of ITU TCAP responses 
             which have been sent by PSX."
    ::= { sonusSoftSwitchScpaItuTcap 6 }

sonusSoftSwitchScpaItuTcapRspRcvd OBJECT-TYPE
    SYNTAX          Counter
    ACCESS          read-only
    STATUS          mandatory
    DESCRIPTION     
            "This counter keeps track of the number of ITU TCAP responses 
             which have been received by PSX."
    ::= { sonusSoftSwitchScpaItuTcap 7 }

sonusSoftSwitchScpaItuTcapOpenTrans OBJECT-TYPE
    SYNTAX          Gauge
    ACCESS          read-only
    STATUS          mandatory
    DESCRIPTION     
            "This counter keeps track of the number of ITU TCAP transactions 
             which are still open pending for response."
    ::= { sonusSoftSwitchScpaItuTcap 8 }

sonusSoftSwitchScpaItuTcapDialogIdPoolSize OBJECT-TYPE
    SYNTAX          Counter
    ACCESS          read-only
    STATUS          mandatory
    DESCRIPTION     
            "This counter keeps track of the number of ITU TCAP dialog ids 
             which have been allocated by PSX/SGX."
    ::= { sonusSoftSwitchScpaItuTcap 9 }

sonusSoftSwitchScpaItuTcapAbortRcvd OBJECT-TYPE
    SYNTAX          Counter
    ACCESS          read-only
    STATUS          mandatory
    DESCRIPTION     
            "This counter keeps track of the number of ITU TCAP abort messages 
             which have been received by PSX."
    ::= { sonusSoftSwitchScpaItuTcap 10 }

sonusSoftSwitchScpaItuTcapAbortSent OBJECT-TYPE
    SYNTAX          Counter
    ACCESS          read-only
    STATUS          mandatory
    DESCRIPTION     
            "This counter keeps track of the number of ITU TCAP abort messages 
             which have been sent by PSX."
    ::= { sonusSoftSwitchScpaItuTcap 11 }

sonusSoftSwitchScpaItuTcapContinueRcvd OBJECT-TYPE
    SYNTAX          Counter
    ACCESS          read-only
    STATUS          mandatory
    DESCRIPTION     
            "This counter keeps track of the number of ITU TCAP continue messages 
             which have been received by PSX."
    ::= { sonusSoftSwitchScpaItuTcap 12 }

sonusSoftSwitchScpaItuTcapContinueSent OBJECT-TYPE
    SYNTAX          Counter
    ACCESS          read-only
    STATUS          mandatory
    DESCRIPTION     
            "This counter keeps track of the number of ITU TCAP continue messages 
             which have been sent by PSX."
    ::= { sonusSoftSwitchScpaItuTcap 13 }

sonusSoftSwitchScpaItuTcapInvokeRcvd OBJECT-TYPE
    SYNTAX          Counter
    ACCESS          read-only
    STATUS          mandatory
    DESCRIPTION     
            "This counter keeps track of the number of ITU TCAP Invoke components 
             which have been received by PSX."
    ::= { sonusSoftSwitchScpaItuTcap 14 }

sonusSoftSwitchScpaItuTcapInvokeSent OBJECT-TYPE
    SYNTAX          Counter
    ACCESS          read-only
    STATUS          mandatory
    DESCRIPTION     
            "This counter keeps track of the number of ITU TCAP Invoke components 
             which have been sent by PSX."
    ::= { sonusSoftSwitchScpaItuTcap 15 }

sonusSoftSwitchScpaSpasTable OBJECT-TYPE
    SYNTAX          SEQUENCE OF SonusSoftSwitchScpaSpasEntry
    ACCESS          not-accessible
    STATUS          mandatory
    DESCRIPTION     
            "The SPAS device related counters per SPAS device table."
    ::= { sonusSoftSwitchSCPAStatistics 2 }

sonusSoftSwitchScpaSpasEntry OBJECT-TYPE
    SYNTAX          SonusSoftSwitchScpaSpasEntry
    ACCESS          not-accessible
    STATUS          mandatory
    DESCRIPTION     
            "An entry in the Sonus PSX SPAS device table."
    INDEX           { sonusSoftSwitchScpaSpasDeviceId }
    ::= { sonusSoftSwitchScpaSpasTable 1 }

SonusSoftSwitchScpaSpasEntry ::=
    SEQUENCE {
        sonusSoftSwitchScpaSpasDeviceId DisplayString,
        sonusSoftSwitchScpaSpasStartDialog  Counter,
        sonusSoftSwitchScpaSpasEndDialog Counter,
        sonusSoftSwitchScpaSpasAbortDialog  Counter,
        sonusSoftSwitchScpaSpasSendConfirm  Counter,
        sonusSoftSwitchScpaSpasContinue Counter,
        sonusSoftSwitchScpaSpasContRslt Counter,
        sonusSoftSwitchScpaSpasXfer     Counter,
        sonusSoftSwitchScpaSpasXferRes  Counter,
        sonusSoftSwitchScpaSpasXferTerm Counter,
        sonusSoftSwitchScpaSpasContTerm Counter,
        sonusSoftSwitchScpaSpasRsetCfna Counter,
        sonusSoftSwitchScpaSpasIgnore   Counter,
        sonusSoftSwitchScpaSpasRls      Counter,
        sonusSoftSwitchScpaSpasReg      Counter,
        sonusSoftSwitchScpaSpasRegAck   Counter,
        sonusSoftSwitchScpaSpasKaSent   Counter,
        sonusSoftSwitchScpaSpasKaRcvd   Counter,
        sonusSoftSwitchScpaSpasKaAckRcvd Counter,
        sonusSoftSwitchScpaSpasKaAckSent Counter,
        sonusSoftSwitchScpaSpasTotalMsg Counter,
--         sonusSoftSwitchScpaSpasTotalRtt Counter64,
        sonusSoftSwitchScpaSpasAvgRtt   Gauge,
        sonusSoftSwitchScpaSpasSesInProg Gauge,
        sonusSoftSwitchScpaSpasIntervalTime   TimeTicks
    }

sonusSoftSwitchScpaSpasDeviceId OBJECT-TYPE
    SYNTAX          DisplayString
    ACCESS          read-only
    STATUS          mandatory
    DESCRIPTION     
            "This is the SPAS device name."
    ::= { sonusSoftSwitchScpaSpasEntry 1 }

sonusSoftSwitchScpaSpasStartDialog OBJECT-TYPE
    SYNTAX          Counter
    ACCESS          read-only
    STATUS          mandatory
    DESCRIPTION     
            "This counter keeps track of the number of START_DLG messages sent by PSX."
    ::= { sonusSoftSwitchScpaSpasEntry 2 }

sonusSoftSwitchScpaSpasEndDialog OBJECT-TYPE
    SYNTAX          Counter
    ACCESS          read-only
    STATUS          mandatory
    DESCRIPTION     
            "This counter keeps track of the number of END_DLG messages sent by PSX."
    ::= { sonusSoftSwitchScpaSpasEntry 3 }

sonusSoftSwitchScpaSpasAbortDialog OBJECT-TYPE
    SYNTAX          Counter
    ACCESS          read-only
    STATUS          mandatory
    DESCRIPTION     
            "This counter keeps track of the number of ABRT_DLG messages 
             sent/received by PSX."
    ::= { sonusSoftSwitchScpaSpasEntry 4 }

sonusSoftSwitchScpaSpasSendConfirm OBJECT-TYPE
    SYNTAX          Counter
    ACCESS          read-only
    STATUS          mandatory
    DESCRIPTION     
            "This counter keeps track of the number of SD_CNFRM messages 
             received by PSX."
    ::= { sonusSoftSwitchScpaSpasEntry 5 }

sonusSoftSwitchScpaSpasContinue OBJECT-TYPE
    SYNTAX          Counter
    ACCESS          read-only
    STATUS          mandatory
    DESCRIPTION     
            "This counter keeps track of the number of CONT messages received by PSX."
    ::= { sonusSoftSwitchScpaSpasEntry 6 }

sonusSoftSwitchScpaSpasContRslt OBJECT-TYPE
    SYNTAX          Counter
    ACCESS          read-only
    STATUS          mandatory
    DESCRIPTION     
            "This counter keeps track of the number of CONT_RSLT messages sent by PSX."
    ::= { sonusSoftSwitchScpaSpasEntry 7 }

sonusSoftSwitchScpaSpasXfer OBJECT-TYPE
    SYNTAX          Counter
    ACCESS          read-only
    STATUS          mandatory
    DESCRIPTION     
            "This counter keeps track of the number of XFER messages received by PSX."
    ::= { sonusSoftSwitchScpaSpasEntry 8 }

sonusSoftSwitchScpaSpasXferRes OBJECT-TYPE
    SYNTAX          Counter
    ACCESS          read-only
    STATUS          mandatory
    DESCRIPTION     
            "This counter keeps track of the number of XFER_RSLT messages sent by PSX."
    ::= { sonusSoftSwitchScpaSpasEntry 9 }

sonusSoftSwitchScpaSpasXferTerm OBJECT-TYPE
    SYNTAX          Counter
    ACCESS          read-only
    STATUS          mandatory
    DESCRIPTION     
            "This counter keeps track of the number of XFER_TERM messages sent by PSX."
    ::= { sonusSoftSwitchScpaSpasEntry 10 }

sonusSoftSwitchScpaSpasContTerm OBJECT-TYPE
    SYNTAX          Counter
    ACCESS          read-only
    STATUS          mandatory
    DESCRIPTION     
            "This counter keeps track of the number of CONT_TERM messages sent by PSX."
    ::= { sonusSoftSwitchScpaSpasEntry 11 }

sonusSoftSwitchScpaSpasRsetCfna OBJECT-TYPE
    SYNTAX          Counter
    ACCESS          read-only
    STATUS          mandatory
    DESCRIPTION     
            "This counter keeps track of the number of RSET_CFNA messages 
             received by PSX."
    ::= { sonusSoftSwitchScpaSpasEntry 12 }

sonusSoftSwitchScpaSpasIgnore OBJECT-TYPE
    SYNTAX          Counter
    ACCESS          read-only
    STATUS          mandatory
    DESCRIPTION     
            "This counter keeps track of the number of IGNORE messages received by PSX."
    ::= { sonusSoftSwitchScpaSpasEntry 13 }

sonusSoftSwitchScpaSpasRls OBJECT-TYPE
    SYNTAX          Counter
    ACCESS          read-only
    STATUS          mandatory
    DESCRIPTION     
            "This counter keeps track of the number of RLS messages received by PSX."
    ::= { sonusSoftSwitchScpaSpasEntry 14 }

sonusSoftSwitchScpaSpasReg OBJECT-TYPE
    SYNTAX          Counter
    ACCESS          read-only
    STATUS          mandatory
    DESCRIPTION     
            "This counter keeps track of the number of REG messages received by PSX."
    ::= { sonusSoftSwitchScpaSpasEntry 15 }

sonusSoftSwitchScpaSpasRegAck OBJECT-TYPE
    SYNTAX          Counter
    ACCESS          read-only
    STATUS          mandatory
    DESCRIPTION     
            "This counter keeps track of the number of REG_ACK messages sent by PSX."
    ::= { sonusSoftSwitchScpaSpasEntry 16 }

sonusSoftSwitchScpaSpasKaSent OBJECT-TYPE
    SYNTAX          Counter
    ACCESS          read-only
    STATUS          mandatory
    DESCRIPTION     
            "This counter keeps track of the number of KA messages sent by PSX."
    ::= { sonusSoftSwitchScpaSpasEntry 17 }

sonusSoftSwitchScpaSpasKaRcvd OBJECT-TYPE
    SYNTAX          Counter
    ACCESS          read-only
    STATUS          mandatory
    DESCRIPTION     
            "This counter keeps track of the number of KA messages received by PSX."
    ::= { sonusSoftSwitchScpaSpasEntry 18 }

sonusSoftSwitchScpaSpasKaAckRcvd OBJECT-TYPE
    SYNTAX          Counter
    ACCESS          read-only
    STATUS          mandatory
    DESCRIPTION     
            "number of KA_ACK messages received by PSX."
    ::= { sonusSoftSwitchScpaSpasEntry 19 }

sonusSoftSwitchScpaSpasKaAckSent OBJECT-TYPE
    SYNTAX          Counter
    ACCESS          read-only
    STATUS          mandatory
    DESCRIPTION     
            "This counter keeps track of the number of KA_ACK messages sent by PSX."
    ::= { sonusSoftSwitchScpaSpasEntry 20 }

sonusSoftSwitchScpaSpasTotalMsg OBJECT-TYPE
    SYNTAX          Counter
    ACCESS          read-only
    STATUS          mandatory
    DESCRIPTION     
            "This counter keeps track of the number of total messages 
             counted in Round Trip Time (RTT) calculation."
    ::= { sonusSoftSwitchScpaSpasEntry 21 }

-- sonusSoftSwitchScpaSpasTotalRtt OBJECT-TYPE
--     SYNTAX          Counter64
--     ACCESS          read-only
--     STATUS          mandatory
--     DESCRIPTION     
--             "total RTT in msecs."
--     ::= { sonusSoftSwitchScpaSpasEntry 22 }

sonusSoftSwitchScpaSpasAvgRtt OBJECT-TYPE
    SYNTAX          Gauge
    ACCESS          read-only
    STATUS          mandatory
    DESCRIPTION     
            "This is the average RTT value i.e. TOTAL_RTT / TOTAL_MSG ."
    ::= { sonusSoftSwitchScpaSpasEntry 23 }

sonusSoftSwitchScpaSpasSesInProg OBJECT-TYPE
    SYNTAX          Gauge
    ACCESS          read-only
    STATUS          mandatory
    DESCRIPTION     
            "This counter keeps track of the number of SPAS sessions in progress."
    ::= { sonusSoftSwitchScpaSpasEntry 24 }

sonusSoftSwitchScpaSpasIntervalTime OBJECT-TYPE
    SYNTAX          TimeTicks
    ACCESS          read-only
    STATUS          mandatory
    DESCRIPTION     
            "This variable contains the end of interval time stamp for 
             the specified interval."
    ::= { sonusSoftSwitchScpaSpasEntry 25 }

sonusSoftSwitchScpaSipE911 OBJECT IDENTIFIER
    ::= { sonusSoftSwitchSCPAStatistics 3 }

sonusSoftSwitchScpaSipE911ESRReqSent OBJECT-TYPE
    SYNTAX          Counter
    ACCESS          read-only
    STATUS          mandatory
    DESCRIPTION     
            "This counter keeps track of the number of Emergency Services
             Routing Requests (ESRReq) which have been sent by the PSX."
    ::= { sonusSoftSwitchScpaSipE911 1 }

sonusSoftSwitchScpaSipE911TotalESRRspRcvd OBJECT-TYPE
    SYNTAX          Counter
    ACCESS          read-only
    STATUS          mandatory
    DESCRIPTION     
            "This counter keeps track of the total number of Emergency Services
             Routing Responses (ESRRsp) which have been received by the PSX."
    ::= { sonusSoftSwitchScpaSipE911 2 }

sonusSoftSwitchScpaSipE911SuccessESRRspRcvd OBJECT-TYPE
    SYNTAX          Counter
    ACCESS          read-only
    STATUS          mandatory
    DESCRIPTION     
            "This counter keeps track of the number of successful Emergency Services
             Routing Responses (ESRRsp) which have been received by the PSX."
    ::= { sonusSoftSwitchScpaSipE911 3 }

sonusSoftSwitchScpaSipE911FailedESRRspRcvd OBJECT-TYPE
    SYNTAX          Counter
    ACCESS          read-only
    STATUS          mandatory
    DESCRIPTION     
            "This counter keeps track of the number of failed Emergency Services
             Routing Responses (ESRRsp) which have been received by the PSX."
    ::= { sonusSoftSwitchScpaSipE911 4 }

sonusSoftSwitchScpaSipE911ESRReqRetry OBJECT-TYPE
    SYNTAX          Counter
    ACCESS          read-only
    STATUS          mandatory
    DESCRIPTION     
            "This counter keeps track of the number of Emergency Services
             Routing Requests (ESRReq) which have been retransmitted by the PSX.
             Every retry is to a new VPC."
    ::= { sonusSoftSwitchScpaSipE911 5 }

sonusSoftSwitchScpaSip OBJECT IDENTIFIER
    ::= { sonusSoftSwitchSCPAStatistics 4 }

sonusSoftSwitchScpaSipInviteSent OBJECT-TYPE
    SYNTAX          Counter
    ACCESS          read-only
    STATUS          mandatory
    DESCRIPTION     
            "This counter keeps track of the number of INVITE requests 
             which have been sent by SCPA process.  
             Retransmissions of messages are not counted."
    ::= { sonusSoftSwitchScpaSip 1 }

sonusSoftSwitchScpaSip2xxRcvd OBJECT-TYPE
    SYNTAX          Counter
    ACCESS          read-only
    STATUS          mandatory
    DESCRIPTION     
            "This counter keeps track of the number of 2XX responses
             which have been received by SCPA proces. Retransmissions 
             of messages are not counted."
    ::= { sonusSoftSwitchScpaSip 2 }

sonusSoftSwitchScpaSip3xxRcvd OBJECT-TYPE
    SYNTAX          Counter
    ACCESS          read-only
    STATUS          mandatory
    DESCRIPTION     
            "This counter keeps track of the number of 3XX responses
             which have been received by SCPA process for INVITE
             transactions. Retransmissions of messages are not counted."
    ::= { sonusSoftSwitchScpaSip 3 }

sonusSoftSwitchScpaSip4xxRcvd OBJECT-TYPE
    SYNTAX          Counter
    ACCESS          read-only
    STATUS          mandatory
    DESCRIPTION     
            "This counter keeps track of the number of 4XX responses
             which have been received by SCPA process for INVITE
             transactions. Retransmissions of messages are not counted."
    ::= { sonusSoftSwitchScpaSip 4 }

sonusSoftSwitchScpaSip5xxRcvd OBJECT-TYPE
    SYNTAX          Counter
    ACCESS          read-only
    STATUS          mandatory
    DESCRIPTION     
            "This counter keeps track of the number of 5XX responses
             which have been received by SCPA process for INVITE
             transactions. Retransmissions of messages are not counted."
    ::= { sonusSoftSwitchScpaSip 5 }

sonusSoftSwitchScpaSip6xxRcvd OBJECT-TYPE
    SYNTAX          Counter
    ACCESS          read-only
    STATUS          mandatory
    DESCRIPTION     
            "This counter keeps track of the number of 6XX responses
             which have been received by SCPA process for INVITE
             transactions. Retransmissions of messages are not counted."
    ::= { sonusSoftSwitchScpaSip 6 }

sonusSoftSwitchScpaSipTimeOutRcvd OBJECT-TYPE
    SYNTAX          Counter
    ACCESS          read-only
    STATUS          mandatory
    DESCRIPTION     
            "This counter keeps track of the number of Transaction 
             timeouts that happened for SIP-SCP calls"
    ::= { sonusSoftSwitchScpaSip 7 }

sonusSoftSwitchScpaHPCInvites OBJECT-TYPE
    SYNTAX          Counter
    ACCESS          read-only
    STATUS          mandatory
    DESCRIPTION     
            "This counter keeps track of the number of HCP Invites
             sent out while encoding HPC Dscp Value"
    ::= { sonusSoftSwitchScpaSip 8 }

sonusSoftSwitchScpaHPCSip2xxRcvd OBJECT-TYPE
    SYNTAX          Counter
    ACCESS          read-only
    STATUS          mandatory
    DESCRIPTION     
            "This counter keeps track of the number of 2XX responses
             which have been received by SCPA proces for HPC Calls. Retransmissions
             of messages are not counted."
    ::= { sonusSoftSwitchScpaSip 9 }

sonusSoftSwitchScpaHPCSip3xxRcvd OBJECT-TYPE
    SYNTAX          Counter
    ACCESS          read-only
    STATUS          mandatory
    DESCRIPTION     
            "This counter keeps track of the number of 3XX responses
             which have been received by SCPA process for INVITE
             transactions for HPC Calls. Retransmissions of messages are not counted."
    ::= { sonusSoftSwitchScpaSip 10 }

sonusSoftSwitchScpaHPCSip4xxRcvd OBJECT-TYPE
    SYNTAX          Counter
    ACCESS          read-only
    STATUS          mandatory
    DESCRIPTION     
            "This counter keeps track of the number of 4XX responses
             which have been received by SCPA process for INVITE
             transactions for HPC Calls. Retransmissions of messages are not counted."
    ::= { sonusSoftSwitchScpaSip 11 }

sonusSoftSwitchScpaHPCSip5xxRcvd OBJECT-TYPE
    SYNTAX          Counter
    ACCESS          read-only
    STATUS          mandatory
    DESCRIPTION     
            "This counter keeps track of the number of 5XX responses
             which have been received by SCPA process for INVITE
             transactions for HPC Calls. Retransmissions of messages are not counted."
    ::= { sonusSoftSwitchScpaSip 12 }

sonusSoftSwitchScpaHPCSip6xxRcvd OBJECT-TYPE
    SYNTAX          Counter
    ACCESS          read-only
    STATUS          mandatory
    DESCRIPTION     
            "This counter keeps track of the number of 6XX responses
             which have been received by SCPA process for INVITE
             transactions for HPC Calls. Retransmissions of messages are not counted."
    ::= { sonusSoftSwitchScpaSip 13 }

sonusSoftSwitchScpaHPCSipTimeOutRcvd OBJECT-TYPE
    SYNTAX          Counter
    ACCESS          read-only
    STATUS          mandatory
    DESCRIPTION     
            "This counter keeps track of the number of Transaction
             timeouts that happened for SIP-SCP HPC calls"
    ::= { sonusSoftSwitchScpaSip 14 }

sonusSoftSwitchScpaSua OBJECT IDENTIFIER
    ::= { sonusSoftSwitchSCPAStatistics 5 }

sonusSoftSwitchScpaSuaProtocol OBJECT IDENTIFIER
    ::= { sonusSoftSwitchScpaSua 1 }

sonusSoftSwitchScpaSuaProtocolSCCPMgmtMsgTx OBJECT-TYPE
    SYNTAX          Counter
    ACCESS          read-only
    STATUS          mandatory
    DESCRIPTION     
            "Total Number of SCCP Management Msgs Sent."
    ::= { sonusSoftSwitchScpaSuaProtocol 1 }

sonusSoftSwitchScpaSuaProtocolSCCPMgmtMsgRx OBJECT-TYPE
    SYNTAX          Counter
    ACCESS          read-only
    STATUS          mandatory
    DESCRIPTION     
            "Total Number of SCCP Management Msgs Rcvd."
    ::= { sonusSoftSwitchScpaSuaProtocol 2 }

sonusSoftSwitchScpaSuaProtocolCLMsgTx OBJECT-TYPE
    SYNTAX          Counter
    ACCESS          read-only
    STATUS          mandatory
    DESCRIPTION     
            "Total Number of ConnectionLess Msgs Sent."
    ::= { sonusSoftSwitchScpaSuaProtocol 3 }

sonusSoftSwitchScpaSuaProtocolCLMsgRx OBJECT-TYPE
    SYNTAX          Counter
    ACCESS          read-only
    STATUS          mandatory
    DESCRIPTION     
            "Total Number of  ConnectionLess Msgs Rcvd."
    ::= { sonusSoftSwitchScpaSuaProtocol 4 }

sonusSoftSwitchScpaSuaProtocolCOMsgTx OBJECT-TYPE
    SYNTAX          Counter
    ACCESS          read-only
    STATUS          mandatory
    DESCRIPTION     
            "Total Number of ConnectionOriented Msgs Sent."
    ::= { sonusSoftSwitchScpaSuaProtocol 5 }

sonusSoftSwitchScpaSuaProtocolCOMsgRx OBJECT-TYPE
    SYNTAX          Counter
    ACCESS          read-only
    STATUS          mandatory
    DESCRIPTION     
            "Total Number of  ConnectionOriented Msgs Rcvd."
    ::= { sonusSoftSwitchScpaSuaProtocol 6 }

-- sonusSoftSwitchScpaSuaProtocolCLCOSizeTx OBJECT-TYPE
--     SYNTAX          Counter64
--     ACCESS          read-only
--     STATUS          mandatory
--     DESCRIPTION     
--             "Total Bytes of Connection Less & Oriented Msgs Sent."
--     ::= { sonusSoftSwitchScpaSuaProtocol 7 }

-- sonusSoftSwitchScpaSuaProtocolCLCOSizeRx OBJECT-TYPE
--     SYNTAX          Counter64
--     ACCESS          read-only
--     STATUS          mandatory
--     DESCRIPTION     
--             "Total Bytes of Connection Less & Oriented Msgs Rcvd."
--     ::= { sonusSoftSwitchScpaSuaProtocol 8 }

sonusSoftSwitchScpaSuaProtocolLocalSSNMsgRx OBJECT-TYPE
    SYNTAX          Counter
    ACCESS          read-only
    STATUS          mandatory
    DESCRIPTION     
            "Total Number of Msgs Rcvd for Local SSN."
    ::= { sonusSoftSwitchScpaSuaProtocol 9 }

sonusSoftSwitchScpaSuaProtocolGTTMsg OBJECT-TYPE
    SYNTAX          Counter
    ACCESS          read-only
    STATUS          mandatory
    DESCRIPTION     
            "Total Number of Msgs requiring GTT."
    ::= { sonusSoftSwitchScpaSuaProtocol 10 }

sonusSoftSwitchScpaSuaRouting OBJECT IDENTIFIER
    ::= { sonusSoftSwitchScpaSua 2 }

sonusSoftSwitchScpaSuaRoutingGTTFail OBJECT-TYPE
    SYNTAX          Counter
    ACCESS          read-only
    STATUS          mandatory
    DESCRIPTION     
            "Total Number of GTT Routing Failures."
    ::= { sonusSoftSwitchScpaSuaRouting 1 }

sonusSoftSwitchScpaSuaRoutingSSFail OBJECT-TYPE
    SYNTAX          Counter
    ACCESS          read-only
    STATUS          mandatory
    DESCRIPTION     
            "Total Number of SubSystem Routing Failures."
    ::= { sonusSoftSwitchScpaSuaRouting 2 }

sonusSoftSwitchScpaSuaRoutingNetworkFail OBJECT-TYPE
    SYNTAX          Counter
    ACCESS          read-only
    STATUS          mandatory
    DESCRIPTION     
            "Total Number of Network Routing Failures."
    ::= { sonusSoftSwitchScpaSuaRouting 3 }

sonusSoftSwitchScpaSuaRoutingNetworkCong OBJECT-TYPE
    SYNTAX          Counter
    ACCESS          read-only
    STATUS          mandatory
    DESCRIPTION     
            "Total Number of Network Routing Congestions."
    ::= { sonusSoftSwitchScpaSuaRouting 4 }

sonusSoftSwitchScpaSuaRoutingUnequipped OBJECT-TYPE
    SYNTAX          Counter
    ACCESS          read-only
    STATUS          mandatory
    DESCRIPTION     
            "Total Number of Unequipped Users Routing Errors."
    ::= { sonusSoftSwitchScpaSuaRouting 5 }

sonusSoftSwitchScpaSuaRoutingPCNotConfig OBJECT-TYPE
    SYNTAX          Counter
    ACCESS          read-only
    STATUS          mandatory
    DESCRIPTION     
            "Total Number of PC Not Configured Routing Errors."
    ::= { sonusSoftSwitchScpaSuaRouting 6 }

sonusSoftSwitchScpaSuaAssocTable OBJECT-TYPE
    SYNTAX          SEQUENCE OF SonusSoftSwitchScpaSuaAssocEntry
    ACCESS          not-accessible
    STATUS          mandatory
    DESCRIPTION     
            "SUA Association related counters per Association table."
    ::= { sonusSoftSwitchScpaSua 3 }

sonusSoftSwitchScpaSuaAssocEntry OBJECT-TYPE
    SYNTAX          SonusSoftSwitchScpaSuaAssocEntry
    ACCESS          not-accessible
    STATUS          mandatory
    DESCRIPTION     
            "An entry in the Sonus PSX SUA Association table."
    INDEX           { sonusSoftSwitchScpaSuaAssocLocalIp, 
                      sonusSoftSwitchScpaSuaAssocLocalPort, 
                      sonusSoftSwitchScpaSuaAssocPeerIp, 
                      sonusSoftSwitchScpaSuaAssocPeerPort }
    ::= { sonusSoftSwitchScpaSuaAssocTable 1 }

SonusSoftSwitchScpaSuaAssocEntry ::=
    SEQUENCE {
        sonusSoftSwitchScpaSuaAssocLocalIp  IpAddress,
        sonusSoftSwitchScpaSuaAssocLocalPort    INTEGER,
        sonusSoftSwitchScpaSuaAssocPeerIp IpAddress,
        sonusSoftSwitchScpaSuaAssocPeerPort   INTEGER,
        sonusSoftSwitchScpaSuaAssocCLMsgTx  Counter,
        sonusSoftSwitchScpaSuaAssocCLMsgRx  Counter,
        sonusSoftSwitchScpaSuaAssocCOMsgTx  Counter,
        sonusSoftSwitchScpaSuaAssocCOMsgRx  Counter,
--         sonusSoftSwitchScpaSuaAssocCLCOSizeTx     Counter64,
--         sonusSoftSwitchScpaSuaAssocCLCOSizeRx     Counter64,
        sonusSoftSwitchScpaSuaAssocErrTx Counter,
        sonusSoftSwitchScpaSuaAssocErrRx Counter,
        sonusSoftSwitchScpaSuaAssocNotifyTx   Counter,
        sonusSoftSwitchScpaSuaAssocNotifyRx   Counter,
        sonusSoftSwitchScpaSuaAssocDUNATx Counter,
        sonusSoftSwitchScpaSuaAssocDUNARx Counter,
        sonusSoftSwitchScpaSuaAssocDAVATx Counter,
        sonusSoftSwitchScpaSuaAssocDAVARx Counter,
        sonusSoftSwitchScpaSuaAssocDAUDTx Counter,
        sonusSoftSwitchScpaSuaAssocDAUDRx Counter,
        sonusSoftSwitchScpaSuaAssocSCONTx Counter,
        sonusSoftSwitchScpaSuaAssocSCONRx Counter,
        sonusSoftSwitchScpaSuaAssocDUPUTx Counter,
        sonusSoftSwitchScpaSuaAssocDUPURx Counter,
        sonusSoftSwitchScpaSuaAssocDRSTTx Counter,
        sonusSoftSwitchScpaSuaAssocDRSTRx Counter,
        sonusSoftSwitchScpaSuaAssocASPUPTx  Counter,
        sonusSoftSwitchScpaSuaAssocASPUPRx  Counter,
        sonusSoftSwitchScpaSuaAssocASPUPAckTx     Counter,
        sonusSoftSwitchScpaSuaAssocASPUPAckRx     Counter,
        sonusSoftSwitchScpaSuaAssocASPDNTx  Counter,
        sonusSoftSwitchScpaSuaAssocASPDNRx  Counter,
        sonusSoftSwitchScpaSuaAssocASPDNAckTx     Counter,
        sonusSoftSwitchScpaSuaAssocASPDNAckRx     Counter,
        sonusSoftSwitchScpaSuaAssocBEATTx Counter,
        sonusSoftSwitchScpaSuaAssocBEATRx Counter,
        sonusSoftSwitchScpaSuaAssocBEATAckTx    Counter,
        sonusSoftSwitchScpaSuaAssocBEATAckRx    Counter,
        sonusSoftSwitchScpaSuaAssocASPACTx  Counter,
        sonusSoftSwitchScpaSuaAssocASPACRx  Counter,
        sonusSoftSwitchScpaSuaAssocASPACAckTx     Counter,
        sonusSoftSwitchScpaSuaAssocASPACAckRx     Counter,
        sonusSoftSwitchScpaSuaAssocASPIATx  Counter,
        sonusSoftSwitchScpaSuaAssocASPIARx  Counter,
        sonusSoftSwitchScpaSuaAssocASPIAAckTx     Counter,
        sonusSoftSwitchScpaSuaAssocASPIAAckRx     Counter,
        sonusSoftSwitchScpaSuaAssocRegReqTx   Counter,
        sonusSoftSwitchScpaSuaAssocRegReqRx   Counter,
        sonusSoftSwitchScpaSuaAssocRegRspTx   Counter,
        sonusSoftSwitchScpaSuaAssocRegRspRx   Counter,
        sonusSoftSwitchScpaSuaAssocDeRegReqTx     Counter,
        sonusSoftSwitchScpaSuaAssocDeRegReqRx     Counter,
        sonusSoftSwitchScpaSuaAssocDeRegRspTx     Counter,
        sonusSoftSwitchScpaSuaAssocDeRegRspRx     Counter,
        sonusSoftSwitchScpaSuaAssocSCTPTransTimeout           Counter,
        sonusSoftSwitchScpaSuaAssocASPMFail   Counter
    }

sonusSoftSwitchScpaSuaAssocLocalIp OBJECT-TYPE
    SYNTAX          IpAddress
    ACCESS          read-only
    STATUS          deprecated
    DESCRIPTION     
            "Local Host's IP Address."
    ::= { sonusSoftSwitchScpaSuaAssocEntry 1 }

sonusSoftSwitchScpaSuaAssocLocalPort OBJECT-TYPE
    SYNTAX          INTEGER
    ACCESS          read-only
    STATUS          deprecated
    DESCRIPTION     
            "Local Host's Port Number."
    ::= { sonusSoftSwitchScpaSuaAssocEntry 2 }

sonusSoftSwitchScpaSuaAssocPeerIp OBJECT-TYPE
    SYNTAX          IpAddress
    ACCESS          read-only
    STATUS          deprecated
    DESCRIPTION     
            "Remote Peer's IP Address."
    ::= { sonusSoftSwitchScpaSuaAssocEntry 3 }

sonusSoftSwitchScpaSuaAssocPeerPort OBJECT-TYPE
    SYNTAX          INTEGER
    ACCESS          read-only
    STATUS          deprecated
    DESCRIPTION     
            "Remote Peer's Port Number."
    ::= { sonusSoftSwitchScpaSuaAssocEntry 4 }

sonusSoftSwitchScpaSuaAssocCLMsgTx OBJECT-TYPE
    SYNTAX          Counter
    ACCESS          read-only
    STATUS          deprecated
    DESCRIPTION     
            "Number of ConnectionLess Association Msgs Sent."
    ::= { sonusSoftSwitchScpaSuaAssocEntry 5 }

sonusSoftSwitchScpaSuaAssocCLMsgRx OBJECT-TYPE
    SYNTAX          Counter
    ACCESS          read-only
    STATUS          deprecated
    DESCRIPTION     
            "Number of ConnectionLess Association Msgs Rcvd."
    ::= { sonusSoftSwitchScpaSuaAssocEntry 6 }

sonusSoftSwitchScpaSuaAssocCOMsgTx OBJECT-TYPE
    SYNTAX          Counter
    ACCESS          read-only
    STATUS          deprecated
    DESCRIPTION     
            "Number of ConnectionOriented Association Msgs Sent."
    ::= { sonusSoftSwitchScpaSuaAssocEntry 7 }

sonusSoftSwitchScpaSuaAssocCOMsgRx OBJECT-TYPE
    SYNTAX          Counter
    ACCESS          read-only
    STATUS          deprecated
    DESCRIPTION     
            "Number of ConnectionOriented Association Msgs Rcvd."
    ::= { sonusSoftSwitchScpaSuaAssocEntry 8 }

-- sonusSoftSwitchScpaSuaAssocCLCOSizeTx OBJECT-TYPE
--     SYNTAX          Counter64
--     ACCESS          read-only
--     STATUS          deprecated
--     DESCRIPTION     
--             "Total Bytes of CL & CO Association Msgs Sent."
--     ::= { sonusSoftSwitchScpaSuaAssocEntry 9 }

-- sonusSoftSwitchScpaSuaAssocCLCOSizeRx OBJECT-TYPE
--     SYNTAX          Counter64
--     ACCESS          read-only
--     STATUS          deprecated
--     DESCRIPTION     
--             "Total Bytes of CL & CO Association Msgs Rcvd."
--     ::= { sonusSoftSwitchScpaSuaAssocEntry 10 }

sonusSoftSwitchScpaSuaAssocErrTx OBJECT-TYPE
    SYNTAX          Counter
    ACCESS          read-only
    STATUS          deprecated
    DESCRIPTION     
            "Number of Error Association Msgs Sent."
    ::= { sonusSoftSwitchScpaSuaAssocEntry 11 }

sonusSoftSwitchScpaSuaAssocErrRx OBJECT-TYPE
    SYNTAX          Counter
    ACCESS          read-only
    STATUS          deprecated
    DESCRIPTION     
            "Number of Error Association Msgs Rcvd."
    ::= { sonusSoftSwitchScpaSuaAssocEntry 12 }

sonusSoftSwitchScpaSuaAssocNotifyTx OBJECT-TYPE
    SYNTAX          Counter
    ACCESS          read-only
    STATUS          deprecated
    DESCRIPTION     
            "Number of Association Notifications Sent."
    ::= { sonusSoftSwitchScpaSuaAssocEntry 13 }

sonusSoftSwitchScpaSuaAssocNotifyRx OBJECT-TYPE
    SYNTAX          Counter
    ACCESS          read-only
    STATUS          deprecated
    DESCRIPTION     
            "Number of Association Notifications Rcvd."
    ::= { sonusSoftSwitchScpaSuaAssocEntry 14 }

sonusSoftSwitchScpaSuaAssocDUNATx OBJECT-TYPE
    SYNTAX          Counter
    ACCESS          read-only
    STATUS          deprecated
    DESCRIPTION     
            "Number of DUNA Association Msgs Sent."
    ::= { sonusSoftSwitchScpaSuaAssocEntry 15 }

sonusSoftSwitchScpaSuaAssocDUNARx OBJECT-TYPE
    SYNTAX          Counter
    ACCESS          read-only
    STATUS          deprecated
    DESCRIPTION     
            "Number of DUNA Association Msgs Rcvd."
    ::= { sonusSoftSwitchScpaSuaAssocEntry 16 }

sonusSoftSwitchScpaSuaAssocDAVATx OBJECT-TYPE
    SYNTAX          Counter
    ACCESS          read-only
    STATUS          deprecated
    DESCRIPTION     
            "Number of DAVA Association Msgs Sent."
    ::= { sonusSoftSwitchScpaSuaAssocEntry 17 }

sonusSoftSwitchScpaSuaAssocDAVARx OBJECT-TYPE
    SYNTAX          Counter
    ACCESS          read-only
    STATUS          deprecated
    DESCRIPTION     
            "Number of DAVA Association Msgs Rcvd."
    ::= { sonusSoftSwitchScpaSuaAssocEntry 18 }

sonusSoftSwitchScpaSuaAssocDAUDTx OBJECT-TYPE
    SYNTAX          Counter
    ACCESS          read-only
    STATUS          deprecated
    DESCRIPTION     
            "Number of DAUD Association Msgs Sent."
    ::= { sonusSoftSwitchScpaSuaAssocEntry 19 }

sonusSoftSwitchScpaSuaAssocDAUDRx OBJECT-TYPE
    SYNTAX          Counter
    ACCESS          read-only
    STATUS          deprecated
    DESCRIPTION     
            "Number of DAUD Association Msgs Rcvd."
    ::= { sonusSoftSwitchScpaSuaAssocEntry 20 }

sonusSoftSwitchScpaSuaAssocSCONTx OBJECT-TYPE
    SYNTAX          Counter
    ACCESS          read-only
    STATUS          deprecated
    DESCRIPTION     
            "Number of SCON Association Msgs Sent."
    ::= { sonusSoftSwitchScpaSuaAssocEntry 21 }

sonusSoftSwitchScpaSuaAssocSCONRx OBJECT-TYPE
    SYNTAX          Counter
    ACCESS          read-only
    STATUS          deprecated
    DESCRIPTION     
            "Number of SCON Association Msgs Rcvd."
    ::= { sonusSoftSwitchScpaSuaAssocEntry 22 }

sonusSoftSwitchScpaSuaAssocDUPUTx OBJECT-TYPE
    SYNTAX          Counter
    ACCESS          read-only
    STATUS          deprecated
    DESCRIPTION     
            "Number of DUPU Association Msgs Sent."
    ::= { sonusSoftSwitchScpaSuaAssocEntry 23 }

sonusSoftSwitchScpaSuaAssocDUPURx OBJECT-TYPE
    SYNTAX          Counter
    ACCESS          read-only
    STATUS          deprecated
    DESCRIPTION     
            "Number of DUPU Association Msgs Rcvd."
    ::= { sonusSoftSwitchScpaSuaAssocEntry 24 }

sonusSoftSwitchScpaSuaAssocDRSTTx OBJECT-TYPE
    SYNTAX          Counter
    ACCESS          read-only
    STATUS          deprecated
    DESCRIPTION     
            "Number of DUPU Association Msgs Sent."
    ::= { sonusSoftSwitchScpaSuaAssocEntry 25 }

sonusSoftSwitchScpaSuaAssocDRSTRx OBJECT-TYPE
    SYNTAX          Counter
    ACCESS          read-only
    STATUS          deprecated
    DESCRIPTION     
            "Number of DUPU Association Msgs Rcvd."
    ::= { sonusSoftSwitchScpaSuaAssocEntry 26 }

sonusSoftSwitchScpaSuaAssocASPUPTx OBJECT-TYPE
    SYNTAX          Counter
    ACCESS          read-only
    STATUS          deprecated
    DESCRIPTION     
            "Number of ASPUP Association Msgs Sent."
    ::= { sonusSoftSwitchScpaSuaAssocEntry 27 }

sonusSoftSwitchScpaSuaAssocASPUPRx OBJECT-TYPE
    SYNTAX          Counter
    ACCESS          read-only
    STATUS          deprecated
    DESCRIPTION     
            "Number of ASPUP Association Msgs Rcvd."
    ::= { sonusSoftSwitchScpaSuaAssocEntry 28 }

sonusSoftSwitchScpaSuaAssocASPUPAckTx OBJECT-TYPE
    SYNTAX          Counter
    ACCESS          read-only
    STATUS          deprecated
    DESCRIPTION     
            "Number of ASPUP Ack Association Msgs Sent."
    ::= { sonusSoftSwitchScpaSuaAssocEntry 29 }

sonusSoftSwitchScpaSuaAssocASPUPAckRx OBJECT-TYPE
    SYNTAX          Counter
    ACCESS          read-only
    STATUS          deprecated
    DESCRIPTION     
            "Number of ASPUP Ack Association Msgs Rcvd."
    ::= { sonusSoftSwitchScpaSuaAssocEntry 30 }

sonusSoftSwitchScpaSuaAssocASPDNTx OBJECT-TYPE
    SYNTAX          Counter
    ACCESS          read-only
    STATUS          deprecated
    DESCRIPTION     
            "Number of ASP Down Association Msgs Sent."
    ::= { sonusSoftSwitchScpaSuaAssocEntry 31 }

sonusSoftSwitchScpaSuaAssocASPDNRx OBJECT-TYPE
    SYNTAX          Counter
    ACCESS          read-only
    STATUS          deprecated
    DESCRIPTION     
            "Number of ASP Down Association Msgs Rcvd."
    ::= { sonusSoftSwitchScpaSuaAssocEntry 32 }

sonusSoftSwitchScpaSuaAssocASPDNAckTx OBJECT-TYPE
    SYNTAX          Counter
    ACCESS          read-only
    STATUS          deprecated
    DESCRIPTION     
            "Number of ASP Down Ack Association Msgs Sent."
    ::= { sonusSoftSwitchScpaSuaAssocEntry 33 }

sonusSoftSwitchScpaSuaAssocASPDNAckRx OBJECT-TYPE
    SYNTAX          Counter
    ACCESS          read-only
    STATUS          deprecated
    DESCRIPTION     
            "Number of ASP Down Ack Association Msgs Rcvd."
    ::= { sonusSoftSwitchScpaSuaAssocEntry 34 }

sonusSoftSwitchScpaSuaAssocBEATTx OBJECT-TYPE
    SYNTAX          Counter
    ACCESS          read-only
    STATUS          deprecated
    DESCRIPTION     
            "Number of BEAT Association Msgs Sent."
    ::= { sonusSoftSwitchScpaSuaAssocEntry 35 }

sonusSoftSwitchScpaSuaAssocBEATRx OBJECT-TYPE
    SYNTAX          Counter
    ACCESS          read-only
    STATUS          deprecated
    DESCRIPTION     
            "Number of BEAT Association Msgs Rcvd."
    ::= { sonusSoftSwitchScpaSuaAssocEntry 36 }

sonusSoftSwitchScpaSuaAssocBEATAckTx OBJECT-TYPE
    SYNTAX          Counter
    ACCESS          read-only
    STATUS          deprecated
    DESCRIPTION     
            "Number of BEAT Ack Association Msgs Sent."
    ::= { sonusSoftSwitchScpaSuaAssocEntry 37 }

sonusSoftSwitchScpaSuaAssocBEATAckRx OBJECT-TYPE
    SYNTAX          Counter
    ACCESS          read-only
    STATUS          deprecated
    DESCRIPTION     
            "Number of BEAT Ack Association Msgs Rcvd."
    ::= { sonusSoftSwitchScpaSuaAssocEntry 38 }

sonusSoftSwitchScpaSuaAssocASPACTx OBJECT-TYPE
    SYNTAX          Counter
    ACCESS          read-only
    STATUS          deprecated
    DESCRIPTION     
            "Number of ASP Active Association Msgs Sent."
    ::= { sonusSoftSwitchScpaSuaAssocEntry 39 }

sonusSoftSwitchScpaSuaAssocASPACRx OBJECT-TYPE
    SYNTAX          Counter
    ACCESS          read-only
    STATUS          deprecated
    DESCRIPTION     
            "Number of ASP Active Association Msgs Rcvd."
    ::= { sonusSoftSwitchScpaSuaAssocEntry 40 }

sonusSoftSwitchScpaSuaAssocASPACAckTx OBJECT-TYPE
    SYNTAX          Counter
    ACCESS          read-only
    STATUS          deprecated
    DESCRIPTION     
            "Number of ASP Active Ack Association Msgs Sent."
    ::= { sonusSoftSwitchScpaSuaAssocEntry 41 }

sonusSoftSwitchScpaSuaAssocASPACAckRx OBJECT-TYPE
    SYNTAX          Counter
    ACCESS          read-only
    STATUS          deprecated
    DESCRIPTION     
            "Number of ASP Active Ack Association Msgs Rcvd."
    ::= { sonusSoftSwitchScpaSuaAssocEntry 42 }

sonusSoftSwitchScpaSuaAssocASPIATx OBJECT-TYPE
    SYNTAX          Counter
    ACCESS          read-only
    STATUS          deprecated
    DESCRIPTION     
            "Number of ASPIA Association Msgs Sent."
    ::= { sonusSoftSwitchScpaSuaAssocEntry 43 }

sonusSoftSwitchScpaSuaAssocASPIARx OBJECT-TYPE
    SYNTAX          Counter
    ACCESS          read-only
    STATUS          deprecated
    DESCRIPTION     
            "Number of ASPIA Association Msgs Rcvd."
    ::= { sonusSoftSwitchScpaSuaAssocEntry 44 }

sonusSoftSwitchScpaSuaAssocASPIAAckTx OBJECT-TYPE
    SYNTAX          Counter
    ACCESS          read-only
    STATUS          deprecated
    DESCRIPTION     
            "Number of ASPIA Ack Association Msgs Sent."
    ::= { sonusSoftSwitchScpaSuaAssocEntry 45 }

sonusSoftSwitchScpaSuaAssocASPIAAckRx OBJECT-TYPE
    SYNTAX          Counter
    ACCESS          read-only
    STATUS          deprecated
    DESCRIPTION     
            "Number of ASPIA Ack Association Msgs Rcvd."
    ::= { sonusSoftSwitchScpaSuaAssocEntry 46 }

sonusSoftSwitchScpaSuaAssocRegReqTx OBJECT-TYPE
    SYNTAX          Counter
    ACCESS          read-only
    STATUS          deprecated
    DESCRIPTION     
            "Number of REG Req Association Msgs Sent."
    ::= { sonusSoftSwitchScpaSuaAssocEntry 47 }

sonusSoftSwitchScpaSuaAssocRegReqRx OBJECT-TYPE
    SYNTAX          Counter
    ACCESS          read-only
    STATUS          deprecated
    DESCRIPTION     
            "Number of REG Req Association Msgs Rcvd."
    ::= { sonusSoftSwitchScpaSuaAssocEntry 48 }

sonusSoftSwitchScpaSuaAssocRegRspTx OBJECT-TYPE
    SYNTAX          Counter
    ACCESS          read-only
    STATUS          deprecated
    DESCRIPTION     
            "Number of REG Rsp Association Msgs Sent."
    ::= { sonusSoftSwitchScpaSuaAssocEntry 49 }

sonusSoftSwitchScpaSuaAssocRegRspRx OBJECT-TYPE
    SYNTAX          Counter
    ACCESS          read-only
    STATUS          deprecated
    DESCRIPTION     
            "Number of REG Rsp Association Msgs Rcvd."
    ::= { sonusSoftSwitchScpaSuaAssocEntry 50 }

sonusSoftSwitchScpaSuaAssocDeRegReqTx OBJECT-TYPE
    SYNTAX          Counter
    ACCESS          read-only
    STATUS          deprecated
    DESCRIPTION     
            "Number of DEREG Req Association Msgs Sent."
    ::= { sonusSoftSwitchScpaSuaAssocEntry 51 }

sonusSoftSwitchScpaSuaAssocDeRegReqRx OBJECT-TYPE
    SYNTAX          Counter
    ACCESS          read-only
    STATUS          deprecated
    DESCRIPTION     
            "Number of DEREG Req Association Msgs Rcvd."
    ::= { sonusSoftSwitchScpaSuaAssocEntry 52 }

sonusSoftSwitchScpaSuaAssocDeRegRspTx OBJECT-TYPE
    SYNTAX          Counter
    ACCESS          read-only
    STATUS          deprecated
    DESCRIPTION     
            "Number of DEREG Rsp Association Msgs Sent."
    ::= { sonusSoftSwitchScpaSuaAssocEntry 53 }

sonusSoftSwitchScpaSuaAssocDeRegRspRx OBJECT-TYPE
    SYNTAX          Counter
    ACCESS          read-only
    STATUS          deprecated
    DESCRIPTION     
            "Number of DEREG Rsp Association Msgs Rcvd."
    ::= { sonusSoftSwitchScpaSuaAssocEntry 54 }

sonusSoftSwitchScpaSuaAssocSCTPTransTimeout OBJECT-TYPE
    SYNTAX          Counter
    ACCESS          read-only
    STATUS          deprecated
    DESCRIPTION     
            "Number of SCTP Association Transmission Timeouts."
    ::= { sonusSoftSwitchScpaSuaAssocEntry 55 }

sonusSoftSwitchScpaSuaAssocASPMFail OBJECT-TYPE
    SYNTAX          Counter
    ACCESS          read-only
    STATUS          deprecated
    DESCRIPTION     
            "Number of ASPM Association Failures."
    ::= { sonusSoftSwitchScpaSuaAssocEntry 56 }

sonusSoftSwitchScpaSuaSSNTable OBJECT-TYPE
    SYNTAX          SEQUENCE OF SonusSoftSwitchScpaSuaSSNEntry
    ACCESS          not-accessible
    STATUS          mandatory
    DESCRIPTION     
            "The SUA SSN related counters per SSN table."
    ::= { sonusSoftSwitchScpaSua 4 }

sonusSoftSwitchScpaSuaSSNEntry OBJECT-TYPE
    SYNTAX          SonusSoftSwitchScpaSuaSSNEntry
    ACCESS          not-accessible
    STATUS          mandatory
    DESCRIPTION     
            "An entry in the Sonus PSX SUA SSN table."
    INDEX           { sonusSoftSwitchScpaSuaSSNId }
    ::= { sonusSoftSwitchScpaSuaSSNTable 1 }

SonusSoftSwitchScpaSuaSSNEntry ::=
    SEQUENCE {
        sonusSoftSwitchScpaSuaSSNId     INTEGER,
        sonusSoftSwitchScpaSuaSSNCLDTMsgTx  Counter,
        sonusSoftSwitchScpaSuaSSNCLDTMsgRx  Counter,
        sonusSoftSwitchScpaSuaSSNCODTMsgTx  Counter,
        sonusSoftSwitchScpaSuaSSNCODTMsgRx  Counter
    }

sonusSoftSwitchScpaSuaSSNId OBJECT-TYPE
    SYNTAX          INTEGER
    ACCESS          read-only
    STATUS          mandatory
    DESCRIPTION     
            "Subsystem Number."
    ::= { sonusSoftSwitchScpaSuaSSNEntry 1 }

sonusSoftSwitchScpaSuaSSNCLDTMsgTx OBJECT-TYPE
    SYNTAX          Counter
    ACCESS          read-only
    STATUS          mandatory
    DESCRIPTION     
            "Total Number of ConnectionLess Msgs Sent."
    ::= { sonusSoftSwitchScpaSuaSSNEntry 2 }

sonusSoftSwitchScpaSuaSSNCLDTMsgRx OBJECT-TYPE
    SYNTAX          Counter
    ACCESS          read-only
    STATUS          mandatory
    DESCRIPTION     
            "Total Number of ConnectionLess Msgs Rcvd."
    ::= { sonusSoftSwitchScpaSuaSSNEntry 3 }

sonusSoftSwitchScpaSuaSSNCODTMsgTx OBJECT-TYPE
    SYNTAX          Counter
    ACCESS          read-only
    STATUS          mandatory
    DESCRIPTION     
            "Total Number of ConnectionOriented Msgs Sent."
    ::= { sonusSoftSwitchScpaSuaSSNEntry 4 }

sonusSoftSwitchScpaSuaSSNCODTMsgRx OBJECT-TYPE
    SYNTAX          Counter
    ACCESS          read-only
    STATUS          mandatory
    DESCRIPTION     
            "Total Number of ConnectionOriented Msgs Rcvd."
    ::= { sonusSoftSwitchScpaSuaSSNEntry 5 }

sonusSoftSwitchScpaSuaExtendedAssoc OBJECT IDENTIFIER
    ::= { sonusSoftSwitchScpaSua 5 }

sonusSoftSwitchScpaSuaExtendedAssocTable OBJECT-TYPE
    SYNTAX          SEQUENCE OF SonusSoftSwitchScpaSuaExtendedAssocEntry
    ACCESS          not-accessible
    STATUS          mandatory
    DESCRIPTION     
            "SUA Association related extended counters per Association table."
    ::= { sonusSoftSwitchScpaSuaExtendedAssoc 1 }

sonusSoftSwitchScpaSuaExtendedAssocEntry OBJECT-TYPE
    SYNTAX          SonusSoftSwitchScpaSuaExtendedAssocEntry
    ACCESS          not-accessible
    STATUS          mandatory
    DESCRIPTION     
            "An entry in the Sonus PSX SUA Association Extended table."
    INDEX           { sonusSoftSwitchScpaSuaExtendedAssocLocalIpType, 
                      sonusSoftSwitchScpaSuaExtendedAssocLocalIp, 
                      sonusSoftSwitchScpaSuaExtendedAssocLocalPort, 
                      sonusSoftSwitchScpaSuaExtendedAssocPeerIpType, 
                      sonusSoftSwitchScpaSuaExtendedAssocPeerIp, 
                      sonusSoftSwitchScpaSuaExtendedAssocPeerPort }
    ::= { sonusSoftSwitchScpaSuaExtendedAssocTable 1 }

SonusSoftSwitchScpaSuaExtendedAssocEntry ::=
    SEQUENCE {
        sonusSoftSwitchScpaSuaExtendedAssocLocalIpType              InetAddressType,
        sonusSoftSwitchScpaSuaExtendedAssocLocalIp          InetAddress,
        sonusSoftSwitchScpaSuaExtendedAssocLocalPort            INTEGER,
        sonusSoftSwitchScpaSuaExtendedAssocPeerIpType             InetAddressType,
        sonusSoftSwitchScpaSuaExtendedAssocPeerIp         InetAddress,
        sonusSoftSwitchScpaSuaExtendedAssocPeerPort           INTEGER,
        sonusSoftSwitchScpaSuaExtendedAssocCLMsgTx          Counter,
        sonusSoftSwitchScpaSuaExtendedAssocCLMsgRx          Counter,
        sonusSoftSwitchScpaSuaExtendedAssocCOMsgTx          Counter,
        sonusSoftSwitchScpaSuaExtendedAssocCOMsgRx          Counter,
--         sonusSoftSwitchScpaSuaExtendedAssocCLCOSizeTx             Counter64,
--         sonusSoftSwitchScpaSuaExtendedAssocCLCOSizeRx             Counter64,
        sonusSoftSwitchScpaSuaExtendedAssocErrTx        Counter,
        sonusSoftSwitchScpaSuaExtendedAssocErrRx        Counter,
        sonusSoftSwitchScpaSuaExtendedAssocNotifyTx           Counter,
        sonusSoftSwitchScpaSuaExtendedAssocNotifyRx           Counter,
        sonusSoftSwitchScpaSuaExtendedAssocDUNATx         Counter,
        sonusSoftSwitchScpaSuaExtendedAssocDUNARx         Counter,
        sonusSoftSwitchScpaSuaExtendedAssocDAVATx         Counter,
        sonusSoftSwitchScpaSuaExtendedAssocDAVARx         Counter,
        sonusSoftSwitchScpaSuaExtendedAssocDAUDTx         Counter,
        sonusSoftSwitchScpaSuaExtendedAssocDAUDRx         Counter,
        sonusSoftSwitchScpaSuaExtendedAssocSCONTx         Counter,
        sonusSoftSwitchScpaSuaExtendedAssocSCONRx         Counter,
        sonusSoftSwitchScpaSuaExtendedAssocDUPUTx         Counter,
        sonusSoftSwitchScpaSuaExtendedAssocDUPURx         Counter,
        sonusSoftSwitchScpaSuaExtendedAssocDRSTTx         Counter,
        sonusSoftSwitchScpaSuaExtendedAssocDRSTRx         Counter,
        sonusSoftSwitchScpaSuaExtendedAssocASPUPTx          Counter,
        sonusSoftSwitchScpaSuaExtendedAssocASPUPRx          Counter,
        sonusSoftSwitchScpaSuaExtendedAssocASPUPAckTx             Counter,
        sonusSoftSwitchScpaSuaExtendedAssocASPUPAckRx             Counter,
        sonusSoftSwitchScpaSuaExtendedAssocASPDNTx          Counter,
        sonusSoftSwitchScpaSuaExtendedAssocASPDNRx          Counter,
        sonusSoftSwitchScpaSuaExtendedAssocASPDNAckTx             Counter,
        sonusSoftSwitchScpaSuaExtendedAssocASPDNAckRx             Counter,
        sonusSoftSwitchScpaSuaExtendedAssocBEATTx         Counter,
        sonusSoftSwitchScpaSuaExtendedAssocBEATRx         Counter,
        sonusSoftSwitchScpaSuaExtendedAssocBEATAckTx            Counter,
        sonusSoftSwitchScpaSuaExtendedAssocBEATAckRx            Counter,
        sonusSoftSwitchScpaSuaExtendedAssocASPACTx          Counter,
        sonusSoftSwitchScpaSuaExtendedAssocASPACRx          Counter,
        sonusSoftSwitchScpaSuaExtendedAssocASPACAckTx             Counter,
        sonusSoftSwitchScpaSuaExtendedAssocASPACAckRx             Counter,
        sonusSoftSwitchScpaSuaExtendedAssocASPIATx          Counter,
        sonusSoftSwitchScpaSuaExtendedAssocASPIARx          Counter,
        sonusSoftSwitchScpaSuaExtendedAssocASPIAAckTx             Counter,
        sonusSoftSwitchScpaSuaExtendedAssocASPIAAckRx             Counter,
        sonusSoftSwitchScpaSuaExtendedAssocRegReqTx           Counter,
        sonusSoftSwitchScpaSuaExtendedAssocRegReqRx           Counter,
        sonusSoftSwitchScpaSuaExtendedAssocRegRspTx           Counter,
        sonusSoftSwitchScpaSuaExtendedAssocRegRspRx           Counter,
        sonusSoftSwitchScpaSuaExtendedAssocDeRegReqTx             Counter,
        sonusSoftSwitchScpaSuaExtendedAssocDeRegReqRx             Counter,
        sonusSoftSwitchScpaSuaExtendedAssocDeRegRspTx             Counter,
        sonusSoftSwitchScpaSuaExtendedAssocDeRegRspRx             Counter,
        sonusSoftSwitchScpaSuaExtendedAssocSCTPTransTimeout                   Counter,
        sonusSoftSwitchScpaSuaExtendedAssocASPMFail           Counter
    }

sonusSoftSwitchScpaSuaExtendedAssocLocalIpType OBJECT-TYPE
    SYNTAX          InetAddressType
    ACCESS          read-only
    STATUS          mandatory
    DESCRIPTION     
            "Local Host's IP Address type."
    ::= { sonusSoftSwitchScpaSuaExtendedAssocEntry 1 }

sonusSoftSwitchScpaSuaExtendedAssocLocalIp OBJECT-TYPE
    SYNTAX          InetAddress
    ACCESS          read-only
    STATUS          mandatory
    DESCRIPTION     
            "Local Host's IP Address."
    ::= { sonusSoftSwitchScpaSuaExtendedAssocEntry 2 }

sonusSoftSwitchScpaSuaExtendedAssocLocalPort OBJECT-TYPE
    SYNTAX          INTEGER
    ACCESS          read-only
    STATUS          mandatory
    DESCRIPTION     
            "Local Host's Port Number."
    ::= { sonusSoftSwitchScpaSuaExtendedAssocEntry 3 }

sonusSoftSwitchScpaSuaExtendedAssocPeerIpType OBJECT-TYPE
    SYNTAX          InetAddressType
    ACCESS          read-only
    STATUS          mandatory
    DESCRIPTION     
            "Remote Peer's IP Address type."
    ::= { sonusSoftSwitchScpaSuaExtendedAssocEntry 4 }

sonusSoftSwitchScpaSuaExtendedAssocPeerIp OBJECT-TYPE
    SYNTAX          InetAddress
    ACCESS          read-only
    STATUS          mandatory
    DESCRIPTION     
            "Remote Peer's IP Address."
    ::= { sonusSoftSwitchScpaSuaExtendedAssocEntry 5 }

sonusSoftSwitchScpaSuaExtendedAssocPeerPort OBJECT-TYPE
    SYNTAX          INTEGER
    ACCESS          read-only
    STATUS          mandatory
    DESCRIPTION     
            "Remote Peer's Port Number."
    ::= { sonusSoftSwitchScpaSuaExtendedAssocEntry 6 }

sonusSoftSwitchScpaSuaExtendedAssocCLMsgTx OBJECT-TYPE
    SYNTAX          Counter
    ACCESS          read-only
    STATUS          mandatory
    DESCRIPTION     
            "Number of ConnectionLess Association Msgs Sent."
    ::= { sonusSoftSwitchScpaSuaExtendedAssocEntry 7 }

sonusSoftSwitchScpaSuaExtendedAssocCLMsgRx OBJECT-TYPE
    SYNTAX          Counter
    ACCESS          read-only
    STATUS          mandatory
    DESCRIPTION     
            "Number of ConnectionLess Association Msgs Rcvd."
    ::= { sonusSoftSwitchScpaSuaExtendedAssocEntry 8 }

sonusSoftSwitchScpaSuaExtendedAssocCOMsgTx OBJECT-TYPE
    SYNTAX          Counter
    ACCESS          read-only
    STATUS          mandatory
    DESCRIPTION     
            "Number of ConnectionOriented Association Msgs Sent."
    ::= { sonusSoftSwitchScpaSuaExtendedAssocEntry 9 }

sonusSoftSwitchScpaSuaExtendedAssocCOMsgRx OBJECT-TYPE
    SYNTAX          Counter
    ACCESS          read-only
    STATUS          mandatory
    DESCRIPTION     
            "Number of ConnectionOriented Association Msgs Rcvd."
    ::= { sonusSoftSwitchScpaSuaExtendedAssocEntry 10 }

-- sonusSoftSwitchScpaSuaExtendedAssocCLCOSizeTx OBJECT-TYPE
--     SYNTAX          Counter64
--     ACCESS          read-only
--     STATUS          mandatory
--     DESCRIPTION     
--             "Total Bytes of CL & CO Association Msgs Sent."
--     ::= { sonusSoftSwitchScpaSuaExtendedAssocEntry 11 }

-- sonusSoftSwitchScpaSuaExtendedAssocCLCOSizeRx OBJECT-TYPE
--     SYNTAX          Counter64
--     ACCESS          read-only
--     STATUS          mandatory
--     DESCRIPTION     
--             "Total Bytes of CL & CO Association Msgs Rcvd."
--     ::= { sonusSoftSwitchScpaSuaExtendedAssocEntry 12 }

sonusSoftSwitchScpaSuaExtendedAssocErrTx OBJECT-TYPE
    SYNTAX          Counter
    ACCESS          read-only
    STATUS          mandatory
    DESCRIPTION     
            "Number of Error Association Msgs Sent."
    ::= { sonusSoftSwitchScpaSuaExtendedAssocEntry 13 }

sonusSoftSwitchScpaSuaExtendedAssocErrRx OBJECT-TYPE
    SYNTAX          Counter
    ACCESS          read-only
    STATUS          mandatory
    DESCRIPTION     
            "Number of Error Association Msgs Rcvd."
    ::= { sonusSoftSwitchScpaSuaExtendedAssocEntry 14 }

sonusSoftSwitchScpaSuaExtendedAssocNotifyTx OBJECT-TYPE
    SYNTAX          Counter
    ACCESS          read-only
    STATUS          mandatory
    DESCRIPTION     
            "Number of Association Notifications Sent."
    ::= { sonusSoftSwitchScpaSuaExtendedAssocEntry 15 }

sonusSoftSwitchScpaSuaExtendedAssocNotifyRx OBJECT-TYPE
    SYNTAX          Counter
    ACCESS          read-only
    STATUS          mandatory
    DESCRIPTION     
            "Number of Association Notifications Rcvd."
    ::= { sonusSoftSwitchScpaSuaExtendedAssocEntry 16 }

sonusSoftSwitchScpaSuaExtendedAssocDUNATx OBJECT-TYPE
    SYNTAX          Counter
    ACCESS          read-only
    STATUS          mandatory
    DESCRIPTION     
            "Number of DUNA Association Msgs Sent."
    ::= { sonusSoftSwitchScpaSuaExtendedAssocEntry 17 }

sonusSoftSwitchScpaSuaExtendedAssocDUNARx OBJECT-TYPE
    SYNTAX          Counter
    ACCESS          read-only
    STATUS          mandatory
    DESCRIPTION     
            "Number of DUNA Association Msgs Rcvd."
    ::= { sonusSoftSwitchScpaSuaExtendedAssocEntry 18 }

sonusSoftSwitchScpaSuaExtendedAssocDAVATx OBJECT-TYPE
    SYNTAX          Counter
    ACCESS          read-only
    STATUS          mandatory
    DESCRIPTION     
            "Number of DAVA Association Msgs Sent."
    ::= { sonusSoftSwitchScpaSuaExtendedAssocEntry 19 }

sonusSoftSwitchScpaSuaExtendedAssocDAVARx OBJECT-TYPE
    SYNTAX          Counter
    ACCESS          read-only
    STATUS          mandatory
    DESCRIPTION     
            "Number of DAVA Association Msgs Rcvd."
    ::= { sonusSoftSwitchScpaSuaExtendedAssocEntry 20 }

sonusSoftSwitchScpaSuaExtendedAssocDAUDTx OBJECT-TYPE
    SYNTAX          Counter
    ACCESS          read-only
    STATUS          mandatory
    DESCRIPTION     
            "Number of DAUD Association Msgs Sent."
    ::= { sonusSoftSwitchScpaSuaExtendedAssocEntry 21 }

sonusSoftSwitchScpaSuaExtendedAssocDAUDRx OBJECT-TYPE
    SYNTAX          Counter
    ACCESS          read-only
    STATUS          mandatory
    DESCRIPTION     
            "Number of DAUD Association Msgs Rcvd."
    ::= { sonusSoftSwitchScpaSuaExtendedAssocEntry 22 }

sonusSoftSwitchScpaSuaExtendedAssocSCONTx OBJECT-TYPE
    SYNTAX          Counter
    ACCESS          read-only
    STATUS          mandatory
    DESCRIPTION     
            "Number of SCON Association Msgs Sent."
    ::= { sonusSoftSwitchScpaSuaExtendedAssocEntry 23 }

sonusSoftSwitchScpaSuaExtendedAssocSCONRx OBJECT-TYPE
    SYNTAX          Counter
    ACCESS          read-only
    STATUS          mandatory
    DESCRIPTION     
            "Number of SCON Association Msgs Rcvd."
    ::= { sonusSoftSwitchScpaSuaExtendedAssocEntry 24 }

sonusSoftSwitchScpaSuaExtendedAssocDUPUTx OBJECT-TYPE
    SYNTAX          Counter
    ACCESS          read-only
    STATUS          mandatory
    DESCRIPTION     
            "Number of DUPU Association Msgs Sent."
    ::= { sonusSoftSwitchScpaSuaExtendedAssocEntry 25 }

sonusSoftSwitchScpaSuaExtendedAssocDUPURx OBJECT-TYPE
    SYNTAX          Counter
    ACCESS          read-only
    STATUS          mandatory
    DESCRIPTION     
            "Number of DUPU Association Msgs Rcvd."
    ::= { sonusSoftSwitchScpaSuaExtendedAssocEntry 26 }

sonusSoftSwitchScpaSuaExtendedAssocDRSTTx OBJECT-TYPE
    SYNTAX          Counter
    ACCESS          read-only
    STATUS          mandatory
    DESCRIPTION     
            "Number of DUPU Association Msgs Sent."
    ::= { sonusSoftSwitchScpaSuaExtendedAssocEntry 27 }

sonusSoftSwitchScpaSuaExtendedAssocDRSTRx OBJECT-TYPE
    SYNTAX          Counter
    ACCESS          read-only
    STATUS          mandatory
    DESCRIPTION     
            "Number of DUPU Association Msgs Rcvd."
    ::= { sonusSoftSwitchScpaSuaExtendedAssocEntry 28 }

sonusSoftSwitchScpaSuaExtendedAssocASPUPTx OBJECT-TYPE
    SYNTAX          Counter
    ACCESS          read-only
    STATUS          mandatory
    DESCRIPTION     
            "Number of ASPUP Association Msgs Sent."
    ::= { sonusSoftSwitchScpaSuaExtendedAssocEntry 29 }

sonusSoftSwitchScpaSuaExtendedAssocASPUPRx OBJECT-TYPE
    SYNTAX          Counter
    ACCESS          read-only
    STATUS          mandatory
    DESCRIPTION     
            "Number of ASPUP Association Msgs Rcvd."
    ::= { sonusSoftSwitchScpaSuaExtendedAssocEntry 30 }

sonusSoftSwitchScpaSuaExtendedAssocASPUPAckTx OBJECT-TYPE
    SYNTAX          Counter
    ACCESS          read-only
    STATUS          mandatory
    DESCRIPTION     
            "Number of ASPUP Ack Association Msgs Sent."
    ::= { sonusSoftSwitchScpaSuaExtendedAssocEntry 31 }

sonusSoftSwitchScpaSuaExtendedAssocASPUPAckRx OBJECT-TYPE
    SYNTAX          Counter
    ACCESS          read-only
    STATUS          mandatory
    DESCRIPTION     
            "Number of ASPUP Ack Association Msgs Rcvd."
    ::= { sonusSoftSwitchScpaSuaExtendedAssocEntry 32 }

sonusSoftSwitchScpaSuaExtendedAssocASPDNTx OBJECT-TYPE
    SYNTAX          Counter
    ACCESS          read-only
    STATUS          mandatory
    DESCRIPTION     
            "Number of ASP Down Association Msgs Sent."
    ::= { sonusSoftSwitchScpaSuaExtendedAssocEntry 33 }

sonusSoftSwitchScpaSuaExtendedAssocASPDNRx OBJECT-TYPE
    SYNTAX          Counter
    ACCESS          read-only
    STATUS          mandatory
    DESCRIPTION     
            "Number of ASP Down Association Msgs Rcvd."
    ::= { sonusSoftSwitchScpaSuaExtendedAssocEntry 34 }

sonusSoftSwitchScpaSuaExtendedAssocASPDNAckTx OBJECT-TYPE
    SYNTAX          Counter
    ACCESS          read-only
    STATUS          mandatory
    DESCRIPTION     
            "Number of ASP Down Ack Association Msgs Sent."
    ::= { sonusSoftSwitchScpaSuaExtendedAssocEntry 35 }

sonusSoftSwitchScpaSuaExtendedAssocASPDNAckRx OBJECT-TYPE
    SYNTAX          Counter
    ACCESS          read-only
    STATUS          mandatory
    DESCRIPTION     
            "Number of ASP Down Ack Association Msgs Rcvd."
    ::= { sonusSoftSwitchScpaSuaExtendedAssocEntry 36 }

sonusSoftSwitchScpaSuaExtendedAssocBEATTx OBJECT-TYPE
    SYNTAX          Counter
    ACCESS          read-only
    STATUS          mandatory
    DESCRIPTION     
            "Number of BEAT Association Msgs Sent."
    ::= { sonusSoftSwitchScpaSuaExtendedAssocEntry 37 }

sonusSoftSwitchScpaSuaExtendedAssocBEATRx OBJECT-TYPE
    SYNTAX          Counter
    ACCESS          read-only
    STATUS          mandatory
    DESCRIPTION     
            "Number of BEAT Association Msgs Rcvd."
    ::= { sonusSoftSwitchScpaSuaExtendedAssocEntry 38 }

sonusSoftSwitchScpaSuaExtendedAssocBEATAckTx OBJECT-TYPE
    SYNTAX          Counter
    ACCESS          read-only
    STATUS          mandatory
    DESCRIPTION     
            "Number of BEAT Ack Association Msgs Sent."
    ::= { sonusSoftSwitchScpaSuaExtendedAssocEntry 39 }

sonusSoftSwitchScpaSuaExtendedAssocBEATAckRx OBJECT-TYPE
    SYNTAX          Counter
    ACCESS          read-only
    STATUS          mandatory
    DESCRIPTION     
            "Number of BEAT Ack Association Msgs Rcvd."
    ::= { sonusSoftSwitchScpaSuaExtendedAssocEntry 40 }

sonusSoftSwitchScpaSuaExtendedAssocASPACTx OBJECT-TYPE
    SYNTAX          Counter
    ACCESS          read-only
    STATUS          mandatory
    DESCRIPTION     
            "Number of ASP Active Association Msgs Sent."
    ::= { sonusSoftSwitchScpaSuaExtendedAssocEntry 41 }

sonusSoftSwitchScpaSuaExtendedAssocASPACRx OBJECT-TYPE
    SYNTAX          Counter
    ACCESS          read-only
    STATUS          mandatory
    DESCRIPTION     
            "Number of ASP Active Association Msgs Rcvd."
    ::= { sonusSoftSwitchScpaSuaExtendedAssocEntry 42 }

sonusSoftSwitchScpaSuaExtendedAssocASPACAckTx OBJECT-TYPE
    SYNTAX          Counter
    ACCESS          read-only
    STATUS          mandatory
    DESCRIPTION     
            "Number of ASP Active Ack Association Msgs Sent."
    ::= { sonusSoftSwitchScpaSuaExtendedAssocEntry 43 }

sonusSoftSwitchScpaSuaExtendedAssocASPACAckRx OBJECT-TYPE
    SYNTAX          Counter
    ACCESS          read-only
    STATUS          mandatory
    DESCRIPTION     
            "Number of ASP Active Ack Association Msgs Rcvd."
    ::= { sonusSoftSwitchScpaSuaExtendedAssocEntry 44 }

sonusSoftSwitchScpaSuaExtendedAssocASPIATx OBJECT-TYPE
    SYNTAX          Counter
    ACCESS          read-only
    STATUS          mandatory
    DESCRIPTION     
            "Number of ASPIA Association Msgs Sent."
    ::= { sonusSoftSwitchScpaSuaExtendedAssocEntry 45 }

sonusSoftSwitchScpaSuaExtendedAssocASPIARx OBJECT-TYPE
    SYNTAX          Counter
    ACCESS          read-only
    STATUS          mandatory
    DESCRIPTION     
            "Number of ASPIA Association Msgs Rcvd."
    ::= { sonusSoftSwitchScpaSuaExtendedAssocEntry 46 }

sonusSoftSwitchScpaSuaExtendedAssocASPIAAckTx OBJECT-TYPE
    SYNTAX          Counter
    ACCESS          read-only
    STATUS          mandatory
    DESCRIPTION     
            "Number of ASPIA Ack Association Msgs Sent."
    ::= { sonusSoftSwitchScpaSuaExtendedAssocEntry 47 }

sonusSoftSwitchScpaSuaExtendedAssocASPIAAckRx OBJECT-TYPE
    SYNTAX          Counter
    ACCESS          read-only
    STATUS          mandatory
    DESCRIPTION     
            "Number of ASPIA Ack Association Msgs Rcvd."
    ::= { sonusSoftSwitchScpaSuaExtendedAssocEntry 48 }

sonusSoftSwitchScpaSuaExtendedAssocRegReqTx OBJECT-TYPE
    SYNTAX          Counter
    ACCESS          read-only
    STATUS          mandatory
    DESCRIPTION     
            "Number of REG Req Association Msgs Sent."
    ::= { sonusSoftSwitchScpaSuaExtendedAssocEntry 49 }

sonusSoftSwitchScpaSuaExtendedAssocRegReqRx OBJECT-TYPE
    SYNTAX          Counter
    ACCESS          read-only
    STATUS          mandatory
    DESCRIPTION     
            "Number of REG Req Association Msgs Rcvd."
    ::= { sonusSoftSwitchScpaSuaExtendedAssocEntry 50 }

sonusSoftSwitchScpaSuaExtendedAssocRegRspTx OBJECT-TYPE
    SYNTAX          Counter
    ACCESS          read-only
    STATUS          mandatory
    DESCRIPTION     
            "Number of REG Rsp Association Msgs Sent."
    ::= { sonusSoftSwitchScpaSuaExtendedAssocEntry 51 }

sonusSoftSwitchScpaSuaExtendedAssocRegRspRx OBJECT-TYPE
    SYNTAX          Counter
    ACCESS          read-only
    STATUS          mandatory
    DESCRIPTION     
            "Number of REG Rsp Association Msgs Rcvd."
    ::= { sonusSoftSwitchScpaSuaExtendedAssocEntry 52 }

sonusSoftSwitchScpaSuaExtendedAssocDeRegReqTx OBJECT-TYPE
    SYNTAX          Counter
    ACCESS          read-only
    STATUS          mandatory
    DESCRIPTION     
            "Number of DEREG Req Association Msgs Sent."
    ::= { sonusSoftSwitchScpaSuaExtendedAssocEntry 53 }

sonusSoftSwitchScpaSuaExtendedAssocDeRegReqRx OBJECT-TYPE
    SYNTAX          Counter
    ACCESS          read-only
    STATUS          mandatory
    DESCRIPTION     
            "Number of DEREG Req Association Msgs Rcvd."
    ::= { sonusSoftSwitchScpaSuaExtendedAssocEntry 54 }

sonusSoftSwitchScpaSuaExtendedAssocDeRegRspTx OBJECT-TYPE
    SYNTAX          Counter
    ACCESS          read-only
    STATUS          mandatory
    DESCRIPTION     
            "Number of DEREG Rsp Association Msgs Sent."
    ::= { sonusSoftSwitchScpaSuaExtendedAssocEntry 55 }

sonusSoftSwitchScpaSuaExtendedAssocDeRegRspRx OBJECT-TYPE
    SYNTAX          Counter
    ACCESS          read-only
    STATUS          mandatory
    DESCRIPTION     
            "Number of DEREG Rsp Association Msgs Rcvd."
    ::= { sonusSoftSwitchScpaSuaExtendedAssocEntry 56 }

sonusSoftSwitchScpaSuaExtendedAssocSCTPTransTimeout OBJECT-TYPE
    SYNTAX          Counter
    ACCESS          read-only
    STATUS          mandatory
    DESCRIPTION     
            "Number of SCTP Association Transmission Timeouts."
    ::= { sonusSoftSwitchScpaSuaExtendedAssocEntry 57 }

sonusSoftSwitchScpaSuaExtendedAssocASPMFail OBJECT-TYPE
    SYNTAX          Counter
    ACCESS          read-only
    STATUS          mandatory
    DESCRIPTION     
            "Number of ASPM Association Failures."
    ::= { sonusSoftSwitchScpaSuaExtendedAssocEntry 58 }

sonusSoftSwitchSipScpCounters OBJECT IDENTIFIER
    ::= { sonusSoftSwitchSCPAStatistics 6 }

sonusSoftSwitchSipScpCountersTable OBJECT-TYPE
    SYNTAX          SEQUENCE OF SonusSoftSwitchSipScpCountersEntry
    ACCESS          not-accessible
    STATUS          mandatory
    DESCRIPTION     
            "SCPA SIP Counters for a SIP SCP Server"
    ::= { sonusSoftSwitchSipScpCounters 1 }

sonusSoftSwitchSipScpCountersEntry OBJECT-TYPE
    SYNTAX          SonusSoftSwitchSipScpCountersEntry
    ACCESS          not-accessible
    STATUS          mandatory
    DESCRIPTION     
            "An entry of Traffic counters related to SIP SCP Servers"
    INDEX           { sonusSoftSwitchSipScpCountersIpAddressType, 
                      sonusSoftSwitchSipScpCountersIpAddress, 
                      sonusSoftSwitchSipScpCountersPort }
    ::= { sonusSoftSwitchSipScpCountersTable 1 }

SonusSoftSwitchSipScpCountersEntry ::=
    SEQUENCE {
        sonusSoftSwitchSipScpCountersIpAddressType          InetAddressType,
        sonusSoftSwitchSipScpCountersIpAddress      InetAddress,
        sonusSoftSwitchSipScpCountersPort INTEGER,
        sonusSoftSwitchSipScpInviteSent Counter,
        sonusSoftSwitchSipScp2xxRcvd    Counter,
        sonusSoftSwitchSipScp3xxRcvd    Counter,
        sonusSoftSwitchSipScp4xxRcvd    Counter,
        sonusSoftSwitchSipScp5xxRcvd    Counter,
        sonusSoftSwitchSipScp6xxRcvd    Counter,
        sonusSoftSwitchSipScpHPCInviteSent  Counter,
        sonusSoftSwitchSipScpHPC2xxRcvd Counter,
        sonusSoftSwitchSipScpHPC3xxRcvd Counter,
        sonusSoftSwitchSipScpHPC4xxRcvd Counter,
        sonusSoftSwitchSipScpHPC5xxRcvd Counter,
        sonusSoftSwitchSipScpHPC6xxRcvd Counter
    }

sonusSoftSwitchSipScpCountersIpAddressType OBJECT-TYPE
    SYNTAX          InetAddressType
    ACCESS          read-only
    STATUS          mandatory
    DESCRIPTION     
            "SIP Scp Host's IP address Type."
    ::= { sonusSoftSwitchSipScpCountersEntry 1 }

sonusSoftSwitchSipScpCountersIpAddress OBJECT-TYPE
    SYNTAX          InetAddress
    ACCESS          read-only
    STATUS          mandatory
    DESCRIPTION     
            "The IP address of the SCP Server for which counters are collected "
    ::= { sonusSoftSwitchSipScpCountersEntry 2 }

sonusSoftSwitchSipScpCountersPort OBJECT-TYPE
    SYNTAX          INTEGER
    ACCESS          read-only
    STATUS          mandatory
    DESCRIPTION     
            "The Port of SCP Server for which counters are collected"
    ::= { sonusSoftSwitchSipScpCountersEntry 3 }

sonusSoftSwitchSipScpInviteSent OBJECT-TYPE
    SYNTAX          Counter
    ACCESS          read-only
    STATUS          mandatory
    DESCRIPTION     
            "This counter keeps track of the number of INVITE requests 
             which have been sent by SCPA process.  
             Retransmissions of messages are not counted."
    ::= { sonusSoftSwitchSipScpCountersEntry 4 }

sonusSoftSwitchSipScp2xxRcvd OBJECT-TYPE
    SYNTAX          Counter
    ACCESS          read-only
    STATUS          mandatory
    DESCRIPTION     
            "This counter keeps track of the number of 2XX responses
             which have been received by SCPA proces. Retransmissions 
             of messages are not counted."
    ::= { sonusSoftSwitchSipScpCountersEntry 5 }

sonusSoftSwitchSipScp3xxRcvd OBJECT-TYPE
    SYNTAX          Counter
    ACCESS          read-only
    STATUS          mandatory
    DESCRIPTION     
            "This counter keeps track of the number of 3XX responses
             which have been received by SCPA process for INVITE
             transactions. Retransmissions of messages are not counted."
    ::= { sonusSoftSwitchSipScpCountersEntry 6 }

sonusSoftSwitchSipScp4xxRcvd OBJECT-TYPE
    SYNTAX          Counter
    ACCESS          read-only
    STATUS          mandatory
    DESCRIPTION     
            "This counter keeps track of the number of 4XX responses
             which have been received by SCPA process for INVITE
             transactions. Retransmissions of messages are not counted."
    ::= { sonusSoftSwitchSipScpCountersEntry 7 }

sonusSoftSwitchSipScp5xxRcvd OBJECT-TYPE
    SYNTAX          Counter
    ACCESS          read-only
    STATUS          mandatory
    DESCRIPTION     
            "This counter keeps track of the number of 5XX responses
             which have been received by SCPA process for INVITE
             transactions. Retransmissions of messages are not counted."
    ::= { sonusSoftSwitchSipScpCountersEntry 8 }

sonusSoftSwitchSipScp6xxRcvd OBJECT-TYPE
    SYNTAX          Counter
    ACCESS          read-only
    STATUS          mandatory
    DESCRIPTION     
            "This counter keeps track of the number of 6XX responses
             which have been received by SCPA process for INVITE
             transactions. Retransmissions of messages are not counted."
    ::= { sonusSoftSwitchSipScpCountersEntry 9 }

sonusSoftSwitchSipScpHPCInviteSent OBJECT-TYPE
    SYNTAX          Counter
    ACCESS          read-only
    STATUS          mandatory
    DESCRIPTION     
            "This counter keeps track of the number of INVITE requests
             which have been sent by SCPA process for HPC Calls.
             Retransmissions of messages are not counted."
    ::= { sonusSoftSwitchSipScpCountersEntry 10 }

sonusSoftSwitchSipScpHPC2xxRcvd OBJECT-TYPE
    SYNTAX          Counter
    ACCESS          read-only
    STATUS          mandatory
    DESCRIPTION     
            "This counter keeps track of the number of 2XX responses
             which have been received by SCPA proces for HPC Calls. Retransmissions
             of messages are not counted."
    ::= { sonusSoftSwitchSipScpCountersEntry 11 }

sonusSoftSwitchSipScpHPC3xxRcvd OBJECT-TYPE
    SYNTAX          Counter
    ACCESS          read-only
    STATUS          mandatory
    DESCRIPTION     
            "This counter keeps track of the number of 3XX responses
             which have been received by SCPA process for INVITE
             transactions for HPC Calls. Retransmissions of messages are not counted."
    ::= { sonusSoftSwitchSipScpCountersEntry 12 }

sonusSoftSwitchSipScpHPC4xxRcvd OBJECT-TYPE
    SYNTAX          Counter
    ACCESS          read-only
    STATUS          mandatory
    DESCRIPTION     
            "This counter keeps track of the number of 4XX responses
             which have been received by SCPA process for INVITE
             transactions for HPC Calls. Retransmissions of messages are not counted."
    ::= { sonusSoftSwitchSipScpCountersEntry 13 }

sonusSoftSwitchSipScpHPC5xxRcvd OBJECT-TYPE
    SYNTAX          Counter
    ACCESS          read-only
    STATUS          mandatory
    DESCRIPTION     
            "This counter keeps track of the number of 5XX responses
             which have been received by SCPA process for INVITE
             transactions for HPC Calls. Retransmissions of messages are not counted."
    ::= { sonusSoftSwitchSipScpCountersEntry 14 }

sonusSoftSwitchSipScpHPC6xxRcvd OBJECT-TYPE
    SYNTAX          Counter
    ACCESS          read-only
    STATUS          mandatory
    DESCRIPTION     
            "This counter keeps track of the number of 6XX responses
             which have been received by SCPA process for INVITE
             transactions for HPC Calls. Retransmissions of messages are not counted."
    ::= { sonusSoftSwitchSipScpCountersEntry 15 }

sonusSoftSwitchSCPAMIBNotifications OBJECT IDENTIFIER
    ::= { sonusSoftSwitchSCPAMIB 2 }

sonusSoftSwitchSCPAMIBNotificationsPrefix OBJECT IDENTIFIER
    ::= { sonusSoftSwitchSCPAMIBNotifications 0 }

sonusSoftSwitchSCPAMIBNotificationsObjects OBJECT IDENTIFIER
    ::= { sonusSoftSwitchSCPAMIBNotifications 1 }

sonusSoftSwitchScpaTranslationType OBJECT-TYPE
    SYNTAX          SonusTMIdentifier
    ACCESS          read-only
    STATUS          mandatory
    DESCRIPTION     
            "."
    ::= { sonusSoftSwitchSCPAMIBNotificationsObjects 1 }

sonusSoftSwitchScpaControlDigits OBJECT-TYPE
    SYNTAX          SonusTMIdentifier
    ACCESS          read-only
    STATUS          mandatory
    DESCRIPTION     
            "Identifies the control."
    ::= { sonusSoftSwitchSCPAMIBNotificationsObjects 2 }

sonusSoftSwitchScpaSpasDevice OBJECT-TYPE
    SYNTAX          SonusSystemName
    ACCESS          read-only
    STATUS          mandatory
    DESCRIPTION     
            "Name of SPAS device, Application Server ID."
    ::= { sonusSoftSwitchSCPAMIBNotificationsObjects 3 }

sonusSoftSwitchScpaSpasDeviceIpAddress OBJECT-TYPE
    SYNTAX          IpAddress
    ACCESS          read-only
    STATUS          mandatory
    DESCRIPTION     
            "IP address of SPAS device."
    ::= { sonusSoftSwitchSCPAMIBNotificationsObjects 4 }

sonusSoftSwitchScpaSpasDeviceUnregisterReason OBJECT-TYPE
    SYNTAX          INTEGER { unknown(1), unknownDevice(2), unknownIp(3), 
                        deviceIpMismatch(4), remoteDisconnected(5), 
                        psxDisconnectedLostKA(6), 
                        psxDisconnectedDeviceConfigChanged(7), 
                        maxConnectionsExceeded(8) }
    ACCESS          read-only
    STATUS          mandatory
    DESCRIPTION     
            "Unregister operation reason."
    ::= { sonusSoftSwitchSCPAMIBNotificationsObjects 5 }

sonusSoftSwitchScpaCriteriaIdentifier OBJECT-TYPE
    SYNTAX          SonusTMIdentifier
    ACCESS          read-only
    STATUS          mandatory
    DESCRIPTION     
            "Identifies the Call Gap Criteria"
    ::= { sonusSoftSwitchSCPAMIBNotificationsObjects 6 }

sonusSoftSwitchScpaCriteriaFormat OBJECT-TYPE
    SYNTAX          SonusCriteriaFormat
    ACCESS          read-only
    STATUS          mandatory
    DESCRIPTION     
            "Format of the Call Gap Criteria Identifier"
    ::= { sonusSoftSwitchSCPAMIBNotificationsObjects 7 }

sonusSoftSwitchScpaSuaHostIp OBJECT-TYPE
    SYNTAX          IpAddress
    ACCESS          read-only
    STATUS          deprecated
    DESCRIPTION     
            "Local Host's IP address."
    ::= { sonusSoftSwitchSCPAMIBNotificationsObjects 8 }

sonusSoftSwitchScpaSuaPeerIp OBJECT-TYPE
    SYNTAX          IpAddress
    ACCESS          read-only
    STATUS          deprecated
    DESCRIPTION     
            "Remote Peer's IP address."
    ::= { sonusSoftSwitchSCPAMIBNotificationsObjects 9 }

sonusSoftSwitchScpaSuaHostPort OBJECT-TYPE
    SYNTAX          INTEGER
    ACCESS          read-only
    STATUS          mandatory
    DESCRIPTION     
            "Local Host's Port Number."
    ::= { sonusSoftSwitchSCPAMIBNotificationsObjects 10 }

sonusSoftSwitchScpaSuaPeerPort OBJECT-TYPE
    SYNTAX          INTEGER
    ACCESS          read-only
    STATUS          mandatory
    DESCRIPTION     
            "Remote Peer's Port Number."
    ::= { sonusSoftSwitchSCPAMIBNotificationsObjects 11 }

sonusSoftSwitchScpaSuaPC OBJECT-TYPE
    SYNTAX          OCTET STRING (SIZE(0..15))
    ACCESS          read-only
    STATUS          mandatory
    DESCRIPTION     
            "Point Code (PC)."
    ::= { sonusSoftSwitchSCPAMIBNotificationsObjects 12 }

sonusSoftSwitchScpaSuaSSN OBJECT-TYPE
    SYNTAX          INTEGER
    ACCESS          read-only
    STATUS          mandatory
    DESCRIPTION     
            "SubSystem Number (SSN)."
    ::= { sonusSoftSwitchSCPAMIBNotificationsObjects 13 }

sonusSoftSwitchScpaSuaHostExtendedIpType OBJECT-TYPE
    SYNTAX          InetAddressType
    ACCESS          read-only
    STATUS          mandatory
    DESCRIPTION     
            "Local Host's IP address Type."
    ::= { sonusSoftSwitchSCPAMIBNotificationsObjects 14 }

sonusSoftSwitchScpaSuaHostExtendedIp OBJECT-TYPE
    SYNTAX          InetAddress
    ACCESS          read-only
    STATUS          mandatory
    DESCRIPTION     
            "Local Host's IP address."
    ::= { sonusSoftSwitchSCPAMIBNotificationsObjects 15 }

sonusSoftSwitchScpaSuaPeerExtendedIpType OBJECT-TYPE
    SYNTAX          InetAddressType
    ACCESS          read-only
    STATUS          mandatory
    DESCRIPTION     
            "Remote Peer's IP address Type."
    ::= { sonusSoftSwitchSCPAMIBNotificationsObjects 16 }

sonusSoftSwitchScpaSuaPeerExtendedIp OBJECT-TYPE
    SYNTAX          InetAddress
    ACCESS          read-only
    STATUS          mandatory
    DESCRIPTION     
            "Remote Peer's IP address."
    ::= { sonusSoftSwitchSCPAMIBNotificationsObjects 17 }

sonusSoftSwitchSCPAMIBCounters OBJECT IDENTIFIER
    ::= { sonusSoftSwitchSCPAMIB 3 }

sonusSoftSwitchScpaOpenConversations OBJECT-TYPE
    SYNTAX          Counter
    ACCESS          read-only
    STATUS          mandatory
    DESCRIPTION     
            "This counter records the number of open conversation transactions at a given time."
    ::= { sonusSoftSwitchSCPAMIBCounters 1 }

sonusSoftSwitchScpaOpenConvIntervalTime OBJECT-TYPE
    SYNTAX          TimeTicks
    ACCESS          read-only
    STATUS          mandatory
    DESCRIPTION     
            "This variable contains the end of interval time stamp for
             the specified interval."
    ::= { sonusSoftSwitchSCPAMIBCounters 2 }

sonusSoftSwitchScpaDownNotification TRAP-TYPE
    ENTERPRISE      sonusSoftSwitchSCPAMIBNotifications
    VARIABLES       { sonusEventDescription, sonusEventClass, 
                      sonusEventLevel, sonusEventTime }
--     STATUS          mandatory
    DESCRIPTION     
            "SCP Access is down"
    ::= 1

sonusSoftSwitchScpaUpNotification TRAP-TYPE
    ENTERPRISE      sonusSoftSwitchSCPAMIBNotifications
    VARIABLES       { sonusEventDescription, sonusEventClass, 
                      sonusEventLevel, sonusEventTime }
--     STATUS          mandatory
    DESCRIPTION     
            "SCP Access is up"
    ::= 2

sonusSoftSwitchScpaTMControlProvisionedNotification TRAP-TYPE
    ENTERPRISE      sonusSoftSwitchSCPAMIBNotifications
    VARIABLES       { sonusSoftSwitchScpaTranslationType, 
                      sonusSoftSwitchScpaControlDigits, 
                      sonusSoftSwitchTMProvControlType, 
                      sonusEventDescription, sonusEventClass, 
                      sonusEventLevel, sonusEventTime }
--     STATUS          mandatory
    DESCRIPTION     
            "A traffic control has been provisioned."
    ::= 3

sonusSoftSwitchScpaTMControlRemovedNotification TRAP-TYPE
    ENTERPRISE      sonusSoftSwitchSCPAMIBNotifications
    VARIABLES       { sonusSoftSwitchScpaTranslationType, 
                      sonusSoftSwitchScpaControlDigits, 
                      sonusSoftSwitchTMProvControlType, 
                      sonusEventDescription, sonusEventClass, 
                      sonusEventLevel, sonusEventTime }
--     STATUS          mandatory
    DESCRIPTION     
            "A traffic control has been removed."
    ::= 4

sonusSoftSwitchScpaTMControlModifiedNotification TRAP-TYPE
    ENTERPRISE      sonusSoftSwitchSCPAMIBNotifications
    VARIABLES       { sonusSoftSwitchScpaTranslationType, 
                      sonusSoftSwitchScpaControlDigits, 
                      sonusSoftSwitchTMProvControlType, 
                      sonusEventDescription, sonusEventClass, 
                      sonusEventLevel, sonusEventTime }
--     STATUS          mandatory
    DESCRIPTION     
            "A traffic control has been modified."
    ::= 5

sonusSoftSwitchScpaTMControlAppliedNotification TRAP-TYPE
    ENTERPRISE      sonusSoftSwitchSCPAMIBNotifications
    VARIABLES       { sonusSoftSwitchScpaTranslationType, 
                      sonusSoftSwitchScpaControlDigits, 
                      sonusSoftSwitchTMAppliedControlType, 
                      sonusEventDescription, sonusEventClass, 
                      sonusEventLevel, sonusEventTime }
--     STATUS          mandatory
    DESCRIPTION     
            "A traffic control has been applied."
    ::= 6

sonusSoftSwitchScpaSpasDeviceRegisterNotification TRAP-TYPE
    ENTERPRISE      sonusSoftSwitchSCPAMIBNotifications
    VARIABLES       { sonusSoftSwitchScpaSpasDevice, 
                      sonusSoftSwitchScpaSpasDeviceIpAddress, 
                      sonusEventDescription, sonusEventClass, 
                      sonusEventLevel, sonusEventTime }
--     STATUS          mandatory
    DESCRIPTION     
            "SPAS Device Register operation."
    ::= 7

sonusSoftSwitchScpaSpasDeviceUnregisterNotification TRAP-TYPE
    ENTERPRISE      sonusSoftSwitchSCPAMIBNotifications
    VARIABLES       { sonusSoftSwitchScpaSpasDevice, 
                      sonusSoftSwitchScpaSpasDeviceIpAddress, 
                      sonusSoftSwitchScpaSpasDeviceUnregisterReason, 
                      sonusEventDescription, sonusEventClass, 
                      sonusEventLevel, sonusEventTime }
--     STATUS          mandatory
    DESCRIPTION     
            "Unregister operation. Look at unregister reason."
    ::= 8

sonusSoftSwitchScpaCallGapTMControlProvisionedNotification TRAP-TYPE
    ENTERPRISE      sonusSoftSwitchSCPAMIBNotifications
    VARIABLES       { sonusSoftSwitchScpaCriteriaIdentifier, 
                      sonusSoftSwitchScpaCriteriaFormat, 
                      sonusEventDescription, sonusEventClass, 
                      sonusEventLevel, sonusEventTime }
--     STATUS          mandatory
    DESCRIPTION     
            "A Call Gap control has been provisioned."
    ::= 9

sonusSoftSwitchScpaCallGapTMControlRemovedNotification TRAP-TYPE
    ENTERPRISE      sonusSoftSwitchSCPAMIBNotifications
    VARIABLES       { sonusSoftSwitchScpaCriteriaIdentifier, 
                      sonusSoftSwitchScpaCriteriaFormat, 
                      sonusEventDescription, sonusEventClass, 
                      sonusEventLevel, sonusEventTime }
--     STATUS          mandatory
    DESCRIPTION     
            "A Call Gap control has been removed."
    ::= 10

sonusSoftSwitchScpaCallGapTMControlModifiedNotification TRAP-TYPE
    ENTERPRISE      sonusSoftSwitchSCPAMIBNotifications
    VARIABLES       { sonusSoftSwitchScpaCriteriaIdentifier, 
                      sonusSoftSwitchScpaCriteriaFormat, 
                      sonusEventDescription, sonusEventClass, 
                      sonusEventLevel, sonusEventTime }
--     STATUS          mandatory
    DESCRIPTION     
            "A Call Gap control has been modified."
    ::= 11

sonusSoftSwitchScpaCallGapTMControlAppliedNotification TRAP-TYPE
    ENTERPRISE      sonusSoftSwitchSCPAMIBNotifications
    VARIABLES       { sonusSoftSwitchScpaCriteriaIdentifier, 
                      sonusSoftSwitchScpaCriteriaFormat, 
                      sonusEventDescription, sonusEventClass, 
                      sonusEventLevel, sonusEventTime }
--     STATUS          mandatory
    DESCRIPTION     
            "A Call Gap control has been applied."
    ::= 12

sonusSoftSwitchScpaSuaAssocDownNotification TRAP-TYPE
    ENTERPRISE      sonusSoftSwitchSCPAMIBNotifications
    VARIABLES       { sonusSoftSwitchScpaSuaHostIp, 
                      sonusSoftSwitchScpaSuaHostPort, 
                      sonusSoftSwitchScpaSuaPeerIp, 
                      sonusSoftSwitchScpaSuaPeerPort, 
                      sonusEventDescription, sonusEventClass, 
                      sonusEventLevel, sonusEventTime }
--     STATUS          deprecated
    DESCRIPTION     
            "SUA Association is DOWN"
    ::= 13

sonusSoftSwitchScpaSuaAssocUpNotification TRAP-TYPE
    ENTERPRISE      sonusSoftSwitchSCPAMIBNotifications
    VARIABLES       { sonusSoftSwitchScpaSuaHostIp, 
                      sonusSoftSwitchScpaSuaHostPort, 
                      sonusSoftSwitchScpaSuaPeerIp, 
                      sonusSoftSwitchScpaSuaPeerPort, 
                      sonusEventDescription, sonusEventClass, 
                      sonusEventLevel, sonusEventTime }
--     STATUS          deprecated
    DESCRIPTION     
            "SUA Association is UP"
    ::= 14

sonusSoftSwitchScpaSuaAssocAllDownNotification TRAP-TYPE
    ENTERPRISE      sonusSoftSwitchSCPAMIBNotifications
    VARIABLES       { sonusSoftSwitchScpaSuaHostIp, 
                      sonusSoftSwitchScpaSuaHostPort, 
                      sonusSoftSwitchScpaSuaPeerIp, 
                      sonusSoftSwitchScpaSuaPeerPort, 
                      sonusEventDescription, sonusEventClass, 
                      sonusEventLevel, sonusEventTime }
--     STATUS          deprecated
    DESCRIPTION     
            "All SUA Associations are DOWN. PSX is isolated from SUA SGX interface."
    ::= 15

sonusSoftSwitchScpaSuaPCDownNotification TRAP-TYPE
    ENTERPRISE      sonusSoftSwitchSCPAMIBNotifications
    VARIABLES       { sonusSoftSwitchScpaSuaPC, sonusEventDescription, 
                      sonusEventClass, sonusEventLevel, sonusEventTime }
--     STATUS          mandatory
    DESCRIPTION     
            "Remote PC is DOWN"
    ::= 16

sonusSoftSwitchScpaSuaPCUpNotification TRAP-TYPE
    ENTERPRISE      sonusSoftSwitchSCPAMIBNotifications
    VARIABLES       { sonusSoftSwitchScpaSuaPC, sonusEventDescription, 
                      sonusEventClass, sonusEventLevel, sonusEventTime }
--     STATUS          mandatory
    DESCRIPTION     
            "Remote PC is UP"
    ::= 17

sonusSoftSwitchScpaSuaSSNDownNotification TRAP-TYPE
    ENTERPRISE      sonusSoftSwitchSCPAMIBNotifications
    VARIABLES       { sonusSoftSwitchScpaSuaSSN, sonusEventDescription, 
                      sonusEventClass, sonusEventLevel, sonusEventTime }
--     STATUS          mandatory
    DESCRIPTION     
            "Remote SSN is DOWN"
    ::= 18

sonusSoftSwitchScpaSuaSSNUpNotification TRAP-TYPE
    ENTERPRISE      sonusSoftSwitchSCPAMIBNotifications
    VARIABLES       { sonusSoftSwitchScpaSuaSSN, sonusEventDescription, 
                      sonusEventClass, sonusEventLevel, sonusEventTime }
--     STATUS          mandatory
    DESCRIPTION     
            "Remote SSN is UP"
    ::= 19

sonusExtendedSoftSwitchScpaSuaAssocDownNotification TRAP-TYPE
    ENTERPRISE      sonusSoftSwitchSCPAMIBNotifications
    VARIABLES       { sonusSoftSwitchScpaSuaHostExtendedIpType, 
                      sonusSoftSwitchScpaSuaHostExtendedIp, 
                      sonusSoftSwitchScpaSuaHostPort, 
                      sonusSoftSwitchScpaSuaPeerExtendedIpType, 
                      sonusSoftSwitchScpaSuaPeerExtendedIp, 
                      sonusSoftSwitchScpaSuaPeerPort, 
                      sonusEventDescription, sonusEventClass, 
                      sonusEventLevel, sonusEventTime }
--     STATUS          mandatory
    DESCRIPTION     
            "SUA Association is DOWN"
    ::= 20

sonusExtendedSoftSwitchScpaSuaAssocUpNotification TRAP-TYPE
    ENTERPRISE      sonusSoftSwitchSCPAMIBNotifications
    VARIABLES       { sonusSoftSwitchScpaSuaHostExtendedIpType, 
                      sonusSoftSwitchScpaSuaHostExtendedIp, 
                      sonusSoftSwitchScpaSuaHostPort, 
                      sonusSoftSwitchScpaSuaPeerExtendedIpType, 
                      sonusSoftSwitchScpaSuaPeerExtendedIp, 
                      sonusSoftSwitchScpaSuaPeerPort, 
                      sonusEventDescription, sonusEventClass, 
                      sonusEventLevel, sonusEventTime }
--     STATUS          mandatory
    DESCRIPTION     
            "SUA Association is UP"
    ::= 21

sonusExtendedSoftSwitchScpaSuaAssocAllDownNotification TRAP-TYPE
    ENTERPRISE      sonusSoftSwitchSCPAMIBNotifications
    VARIABLES       { sonusSoftSwitchScpaSuaHostExtendedIpType, 
                      sonusSoftSwitchScpaSuaHostExtendedIp, 
                      sonusSoftSwitchScpaSuaHostPort, 
                      sonusSoftSwitchScpaSuaPeerExtendedIpType, 
                      sonusSoftSwitchScpaSuaPeerExtendedIp, 
                      sonusSoftSwitchScpaSuaPeerPort, 
                      sonusEventDescription, sonusEventClass, 
                      sonusEventLevel, sonusEventTime }
--     STATUS          mandatory
    DESCRIPTION     
            "All SUA Associations are DOWN. PSX is isolated from SUA SGX interface."
    ::= 22

END -- end of module SONUS-SOFTSWITCH-SCPA-MIB.
