--
-- This SMIv1 module has been generated by smidump 0.2-cvs. Do not edit.
--

SONUS-QSBC-CDR-MIB DEFINITIONS ::= BEGIN

IMPORTS
    Counter, Gauge, IpAddress
        FROM RFC1155-SMI
    sonusCommonSoftwarePlatformServicesMIBs
        FROM SONUS-SMI;

sonusQSbcCdrMIB OBJECT IDENTIFIER
    ::= { sonusCommonSoftwarePlatformServicesMIBs 24 }

-- sonusQSbcCdrMIB MODULE-IDENTITY
--     LAST-UPDATED    "201902070000Z"
--     ORGANIZATION    
--             "Ribbon Communications, Inc."
--     CONTACT-INFO    
--             "Customer Support        
--              Ribbon Communications, Inc. 
--              4 Technology Park Drive 
--              Westford, MA 01886      
--              USA                     
--                                      
--              Tel: 978-614-8100       
--              Fax: 978-614-8609"
--     DESCRIPTION     
--             "Configuration for Q Series SBC Format Accounting Records."
--     REVISION        "201902070000Z"
--     DESCRIPTION     
--             "Auto generated MIB."
--     ::= { sonusCommonSoftwarePlatformServicesMIBs 24 }


String ::=
    OCTET STRING

-- String ::= TEXTUAL-CONVENTION
--     DISPLAY-HINT    "1t"
--     STATUS          mandatory
--     DESCRIPTION     
--             "xs:string"
--     SYNTAX          OCTET STRING

SonusQSbcCdrChecksumKey ::=
    OCTET STRING (SIZE(16..64))

-- SonusQSbcCdrChecksumKey ::= TEXTUAL-CONVENTION
--     DISPLAY-HINT    "1t"
--     STATUS          mandatory
--     DESCRIPTION     
--             "
--              Enter checksum key between 16 and 64 characters in length and
--              consisting of digits and upper or lower-case letters.
--              "
--     SYNTAX          OCTET STRING (SIZE(16..64))

sonusQSbcCdr OBJECT IDENTIFIER
    ::= { sonusQSbcCdrMIB 1 }

sonusQSbcCdrAdmin OBJECT IDENTIFIER
    ::= { sonusQSbcCdr 1 }

END -- end of module SONUS-QSBC-CDR-MIB.
