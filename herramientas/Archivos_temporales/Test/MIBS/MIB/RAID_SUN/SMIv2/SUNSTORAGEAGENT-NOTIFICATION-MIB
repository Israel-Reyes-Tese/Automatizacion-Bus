--
-- This SMIv2 module has been generated by smidump 0.2-cvs. Do not edit.
--

SUNSTORAGEAGENT-NOTIFICATION-MIB DEFINITIONS ::= BEGIN

IMPORTS
    MODULE-IDENTITY, NOTIFICATION-TYPE, OBJECT-TYPE, enterprises
        FROM SNMPv2-SMI;

alertTrap MODULE-IDENTITY
    LAST-UPDATED    "200210160000Z"
    ORGANIZATION    
            "Sun Microsystems Inc."
    CONTACT-INFO    
            "        Sun Microsystems Inc.
             Customer Support
             Postal: 901 San Antonio Road
             Palo Alto, CA-94303-4900, USA
             Tel: 650-960-1300
             E-mail: service@sun.com"
    DESCRIPTION     
            "This mib defines the trap sent by the Sun Storage Agent
             with the variable bindings.  Any outside entity can
             subscribe for this trap."
    REVISION        "200210160000Z"
    DESCRIPTION     
            "Rev 1.0  19 January 2000 12:00, Initial version Of MIB."
    ::= { storagent 0 }


sun OBJECT IDENTIFIER
    ::= { enterprises 42 }

prod OBJECT IDENTIFIER
    ::= { sun 2 }

storagent OBJECT IDENTIFIER
    ::= { prod 95 }

alert OBJECT IDENTIFIER
    ::= { storagent 1 }

alertInfoGroup OBJECT IDENTIFIER
    ::= { alert 3 }

deviceName OBJECT-TYPE
    SYNTAX          OCTET STRING
    MAX-ACCESS      accessible-for-notify
    STATUS          current
    DESCRIPTION     
            "The name of the storage device that the alert message
             pertains to."
    ::= { alertInfoGroup 1 }

alertLevel OBJECT-TYPE
    SYNTAX          INTEGER { clear(0), minor(1), major(2), critical(3), 
                        down(4) }
    MAX-ACCESS      accessible-for-notify
    STATUS          current
    DESCRIPTION     
            "The level of importance of the alert related to failure."
    ::= { alertInfoGroup 2 }

message OBJECT-TYPE
    SYNTAX          OCTET STRING
    MAX-ACCESS      accessible-for-notify
    STATUS          current
    DESCRIPTION     
            "The alert message for the storage device."
    ::= { alertInfoGroup 3 }

gridId OBJECT-TYPE
    SYNTAX          OCTET STRING
    MAX-ACCESS      accessible-for-notify
    STATUS          current
    DESCRIPTION     
            "Event Grid ID"
    ::= { alertInfoGroup 4 }

deviceId OBJECT-TYPE
    SYNTAX          OCTET STRING
    MAX-ACCESS      accessible-for-notify
    STATUS          current
    DESCRIPTION     
            "Device ID ie: t3:serialno"
    ::= { alertInfoGroup 5 }

componentName OBJECT-TYPE
    SYNTAX          OCTET STRING
    MAX-ACCESS      accessible-for-notify
    STATUS          current
    DESCRIPTION     
            "The name of the component with in the device.
             Tray.85.Battery.A"
    ::= { alertInfoGroup 6 }

componentId OBJECT-TYPE
    SYNTAX          OCTET STRING
    MAX-ACCESS      accessible-for-notify
    STATUS          current
    DESCRIPTION     
            "The identifier of the failed component.
             t85bat1"
    ::= { alertInfoGroup 7 }

eventId OBJECT-TYPE
    SYNTAX          OCTET STRING
    MAX-ACCESS      accessible-for-notify
    STATUS          current
    DESCRIPTION     
            "Id of the event that caused the notification.
             1227284238057.008c0dc0.2"
    ::= { alertInfoGroup 8 }

eventName OBJECT-TYPE
    SYNTAX          OCTET STRING
    MAX-ACCESS      accessible-for-notify
    STATUS          current
    DESCRIPTION     
            "The event name corresponding to the gridId
             6140.ProblemEvent.REC_REMOVED_BATTERY"
    ::= { alertInfoGroup 9 }

alertMessage NOTIFICATION-TYPE
    OBJECTS         { deviceName, alertLevel, message, gridId, deviceId, 
                      componentName, componentId, eventId, eventName }
    STATUS          current
    DESCRIPTION     
            "An alertMessage trap signifies that an alert was
             was generated for a storage device monitored
             by the Storage Agent."
    ::= { alertTrap 6 }

END -- end of module SUNSTORAGEAGENT-NOTIFICATION-MIB.
