--
-- This SMIv2 module has been generated by smidump 0.2-cvs. Do not edit.
--

SONUS-HA-INSIGHT-MIB DEFINITIONS ::= BEGIN

IMPORTS
    Integer32, IpAddress, MODULE-IDENTITY, NOTIFICATION-TYPE, 
    OBJECT-TYPE, Unsigned32
        FROM SNMPv2-SMI
    sonusEventClass, sonusEventDescription, sonusEventLevel, 
    sonusEventTime, sonusSequenceId
        FROM SONUS-COMMON-MIB
    sonusSystemMIBs
        FROM SONUS-SMI;

sonusHAInsightMIB MODULE-IDENTITY
    LAST-UPDATED    "200811220000Z"
    ORGANIZATION    
            "Sonus Networks, Inc."
    CONTACT-INFO    
            "   Customer Support    
             Sonus Networks, Inc.
             250 Apollo Drive
             Chelmsford, MA 01824
             USA
             
             Tel: 978-614-8100
             Fax: 978-614-8609"
    DESCRIPTION     
            "The MIB Module for  HA Insight related objects."
    ::= { sonusSystemMIBs 14 }


sonusHAInsightMIBObjects OBJECT IDENTIFIER
    ::= { sonusHAInsightMIB 1 }

sonusHAInsightNotifications OBJECT IDENTIFIER
    ::= { sonusHAInsightMIB 2 }

sonusHAInsightNotificationsPrefix OBJECT IDENTIFIER
    ::= { sonusHAInsightNotifications 0 }

sonusHAInsightStartFailureNotification NOTIFICATION-TYPE
    OBJECTS         { sonusEventTime, sonusEventDescription, 
                      sonusEventClass, sonusEventLevel }
    STATUS          current
    DESCRIPTION     
            "Insight failed to start after failover"
    ::= { sonusHAInsightNotificationsPrefix 1 }

sonusHAInsightStopFailureNotification NOTIFICATION-TYPE
    OBJECTS         { sonusEventTime, sonusEventDescription, 
                      sonusEventClass, sonusEventLevel }
    STATUS          current
    DESCRIPTION     
            "Insight failed to stop before failing over"
    ::= { sonusHAInsightNotificationsPrefix 2 }

END -- end of module SONUS-HA-INSIGHT-MIB.
