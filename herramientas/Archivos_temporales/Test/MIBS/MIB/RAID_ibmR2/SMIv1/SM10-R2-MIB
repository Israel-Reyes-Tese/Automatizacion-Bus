--
-- This SMIv1 module has been generated by smidump 0.2-cvs. Do not edit.
--

SM10-R2-MIB DEFINITIONS ::= BEGIN

IMPORTS
    InetAddress, InetAddressType
        FROM INET-ADDRESS-MIB
    OBJECT-TYPE
        FROM RFC-1212
    TRAP-TYPE
        FROM RFC-1215
    enterprises
        FROM SNMPv2-SMI;

engenioinformationtechnologies OBJECT IDENTIFIER
    ::= { enterprises 1123 }

wichita OBJECT IDENTIFIER
    ::= { engenioinformationtechnologies 1 }

ftcollins OBJECT IDENTIFIER
    ::= { engenioinformationtechnologies 2 }

cosprings OBJECT IDENTIFIER
    ::= { engenioinformationtechnologies 3 }

austin OBJECT IDENTIFIER
    ::= { engenioinformationtechnologies 4 }

sm10R2 OBJECT IDENTIFIER
    ::= { austin 500 }

infoTable OBJECT-TYPE
    SYNTAX          SEQUENCE OF InfoEntry
    ACCESS          not-accessible
    STATUS          mandatory
    DESCRIPTION     
            "Information for array traps."
    ::= { sm10R2 1 }

infoEntry OBJECT-TYPE
    SYNTAX          InfoEntry
    ACCESS          not-accessible
    STATUS          mandatory
    DESCRIPTION     
            "The data for array traps."
    INDEX           { deviceHostIPType }
    ::= { infoTable 1 }

InfoEntry ::=
    SEQUENCE {
        deviceHostIPType                InetAddressType,
        deviceHostIPAddr                InetAddress,
        deviceHostName                  DisplayString,
        deviceUserLabel                 DisplayString,
        deviceErrorCode                 DisplayString,
        eventTime                       DisplayString,
        trapDescription                 DisplayString,
        componentType                   DisplayString,
        componentLocation               DisplayString
    }

deviceHostIPType OBJECT-TYPE
    SYNTAX          InetAddressType
    ACCESS          read-only
    STATUS          mandatory
    DESCRIPTION     
            "Type of IP Address of the network-attached device or device host. 0 unknown, 1 ipv4, 2 ipv6"
    ::= { infoEntry 1 }

deviceHostIPAddr OBJECT-TYPE
    SYNTAX          InetAddress
    ACCESS          read-only
    STATUS          mandatory
    DESCRIPTION     
            "IP Address of the network-attached device or device host."
    ::= { infoEntry 2 }

deviceHostName OBJECT-TYPE
    SYNTAX          DisplayString (SIZE(0..17))
    ACCESS          read-only
    STATUS          mandatory
    DESCRIPTION     
            "The user label for the host of the device being reported on."
    ::= { infoEntry 3 }

deviceUserLabel OBJECT-TYPE
    SYNTAX          DisplayString (SIZE(0..29))
    ACCESS          read-only
    STATUS          mandatory
    DESCRIPTION     
            "The user label for the device being reported on."
    ::= { infoEntry 4 }

deviceErrorCode OBJECT-TYPE
    SYNTAX          DisplayString (SIZE(0..19))
    ACCESS          read-only
    STATUS          mandatory
    DESCRIPTION     
            "The error code as reported by the device or host."
    ::= { infoEntry 5 }

eventTime OBJECT-TYPE
    SYNTAX          DisplayString (SIZE(0..39))
    ACCESS          read-only
    STATUS          mandatory
    DESCRIPTION     
            "The time at which the event happen on the device."
    ::= { infoEntry 6 }

trapDescription OBJECT-TYPE
    SYNTAX          DisplayString (SIZE(0..69))
    ACCESS          read-only
    STATUS          mandatory
    DESCRIPTION     
            "A string to indicate the nature of the trap"
    ::= { infoEntry 7 }

componentType OBJECT-TYPE
    SYNTAX          DisplayString (SIZE(0..59))
    ACCESS          read-only
    STATUS          mandatory
    DESCRIPTION     
            "A string to identify the failing component type"
    ::= { infoEntry 8 }

componentLocation OBJECT-TYPE
    SYNTAX          DisplayString (SIZE(0..39))
    ACCESS          read-only
    STATUS          mandatory
    DESCRIPTION     
            "A string to identify the location of the failing component"
    ::= { infoEntry 9 }

tucson OBJECT IDENTIFIER
    ::= { engenioinformationtechnologies 5 }

reston OBJECT IDENTIFIER
    ::= { engenioinformationtechnologies 6 }

boulder OBJECT IDENTIFIER
    ::= { engenioinformationtechnologies 7 }

storageArrayCritical TRAP-TYPE
    ENTERPRISE      sm10R2
    VARIABLES       { deviceHostIPType, deviceHostIPAddr, deviceHostName, 
                      deviceUserLabel, deviceErrorCode, eventTime, 
                      trapDescription, componentType, componentLocation }
--     STATUS          mandatory
    DESCRIPTION     
            "This trap indicates an event where user-interaction is required immediately.
             Some example events are component failures or critical errors."
    ::= 2

END -- end of module SM10-R2-MIB.
