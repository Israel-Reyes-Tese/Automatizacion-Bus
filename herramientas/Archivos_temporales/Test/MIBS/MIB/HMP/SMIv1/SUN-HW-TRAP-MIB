--
-- This SMIv1 module has been generated by smidump 0.2-cvs. Do not edit.
--

SUN-HW-TRAP-MIB DEFINITIONS ::= BEGIN

IMPORTS
    OBJECT-TYPE
        FROM RFC-1212
    TRAP-TYPE
        FROM RFC-1215
    enterprises
        FROM SNMPv2-SMI
    DisplayString, RowPointer
        FROM SNMPv2-TC;

sunHwTrapMIB OBJECT IDENTIFIER
    ::= { ilom 103 }

-- sunHwTrapMIB MODULE-IDENTITY
--     LAST-UPDATED    "200803170000Z"
--     ORGANIZATION    
--             "Sun Microsystems, Inc."
--     CONTACT-INFO    
--             "Sun Microsystems, Inc.
--              4150 Network Circle
--              Santa Clara, CA 95054
--              
--              1-800-555-9SUN or
--              1-650-960-1300
--              
--              http://www.sun.com
--              or contact your local support representative"
--     DESCRIPTION     
--             "Copyright 2008 Sun Microsystems, Inc.  All rights reserved.
--              Use is subject to license terms.
--              
--              The SUN-HW-TRAP-MIB describes the hardware related
--              notifications/traps that may be generated by Sun systems"
--     REVISION        "200803170000Z"
--     DESCRIPTION     
--             "Version: 2.0
--              Released with ILOM version 3.0"
--     REVISION        "200702060000Z"
--     DESCRIPTION     
--             "Version: 1.0"
--     ::= { ilom 103 }


SunHwTrapThresholdTypeTC ::=
    INTEGER { upper(1), lower(2), unknown(3) }

-- SunHwTrapThresholdTypeTC ::= TEXTUAL-CONVENTION
--     STATUS          mandatory
--     DESCRIPTION     
--             "Describes whether a threshold is an upper threshold or
--              a lower threshold"
--     SYNTAX          INTEGER
--                       { upper(1), lower(2), unknown(3) }

SunHwTrapSeverityTC ::=
    INTEGER { other(1), fatal(2), critical(3), nonCritical(4), ok(5) }

-- SunHwTrapSeverityTC ::= TEXTUAL-CONVENTION
--     STATUS          mandatory
--     DESCRIPTION     
--             "Describes the severity levels that a trap can take."
--     SYNTAX          INTEGER
--                       { other(1), fatal(2), critical(3), 
--                         nonCritical(4), ok(5) }

SunHwTrapHAStateTC ::=
    INTEGER { other(1), initializing(2), standalone(3), standby(4), 
                        master(5) }

-- SunHwTrapHAStateTC ::= TEXTUAL-CONVENTION
--     STATUS          mandatory
--     DESCRIPTION     
--             "Describes the states that a high availability system can take."
--     SYNTAX          INTEGER
--                       { other(1), initializing(2), standalone(3), 
--                         standby(4), master(5) }

SunHwTrapHardDriveStatesTC ::=
    INTEGER { other(1), present(2), fault(3), predictiveFailure(4), 
                        hotSpare(5), consistencyCheckInProgress(6), 
                        inCriticalArray(7), inFailedArray(8), 
                        rebuildInProgress(9), rebuildAborted(10) }

-- SunHwTrapHardDriveStatesTC ::= TEXTUAL-CONVENTION
--     STATUS          mandatory
--     DESCRIPTION     
--             "Describes the states a hard drive can be in when hard drive status
--              is reported."
--     SYNTAX          INTEGER
--                       { other(1), present(2), fault(3), 
--                         predictiveFailure(4), hotSpare(5), 
--                         consistencyCheckInProgress(6), 
--                         inCriticalArray(7), inFailedArray(8), 
--                         rebuildInProgress(9), rebuildAborted(10) }

SunHwTrapDisableReasonsTC ::=
    INTEGER { unknown(1), faultOrError(2), configuration(3) }

-- SunHwTrapDisableReasonsTC ::= TEXTUAL-CONVENTION
--     STATUS          mandatory
--     DESCRIPTION     
--             "Describes the reasons that a component is disabled."
--     SYNTAX          INTEGER
--                       { unknown(1), faultOrError(2), configuration(3) }

SunHwTrapFloatingPointValueTC ::=
    OCTET STRING (SIZE(0..255))

-- SunHwTrapFloatingPointValueTC ::= TEXTUAL-CONVENTION
--     DISPLAY-HINT    "255a"
--     STATUS          mandatory
--     DESCRIPTION     
--             "A floating point number converted to a string
--              in decimal notation of the form [-]mmm.dd"
--     SYNTAX          OCTET STRING (SIZE(0..255))

sun OBJECT IDENTIFIER
    ::= { enterprises 42 }

products OBJECT IDENTIFIER
    ::= { sun 2 }

ilom OBJECT IDENTIFIER
    ::= { products 175 }

sunHwTrapObjects OBJECT IDENTIFIER
    ::= { sunHwTrapMIB 1 }

sunHwTraps OBJECT IDENTIFIER
    ::= { sunHwTrapMIB 2 }

sunHwTrapPrefix OBJECT IDENTIFIER
    ::= { sunHwTraps 0 }

sunHwTrapData OBJECT IDENTIFIER
    ::= { sunHwTraps 1 }

sunHwTrapSystemIdentifier OBJECT-TYPE
    SYNTAX          DisplayString
    ACCESS          read-only
    STATUS          mandatory
    DESCRIPTION     
            "A text string used to identify the source of the trap. Typically
             this is the host name."
    ::= { sunHwTrapData 1 }

sunHwTrapComponentName OBJECT-TYPE
    SYNTAX          DisplayString
    ACCESS          read-only
    STATUS          mandatory
    DESCRIPTION     
            "The name of the component which is the source of the trap."
    ::= { sunHwTrapData 2 }

sunHwTrapThresholdType OBJECT-TYPE
    SYNTAX          SunHwTrapThresholdTypeTC
    ACCESS          read-only
    STATUS          mandatory
    DESCRIPTION     
            "Identifies the threshold type that the sensor is reporting on."
    ::= { sunHwTrapData 3 }

sunHwTrapThresholdValue OBJECT-TYPE
    SYNTAX          SunHwTrapFloatingPointValueTC
    ACCESS          read-only
    STATUS          mandatory
    DESCRIPTION     
            "The threshold setting that has been crossed."
    ::= { sunHwTrapData 4 }

sunHwTrapSensorValue OBJECT-TYPE
    SYNTAX          SunHwTrapFloatingPointValueTC
    ACCESS          read-only
    STATUS          mandatory
    DESCRIPTION     
            "The threshold sensor's reading at the time the trap was generated."
    ::= { sunHwTrapData 5 }

sunHwTrapSuspectComponentName OBJECT-TYPE
    SYNTAX          DisplayString
    ACCESS          read-only
    STATUS          mandatory
    DESCRIPTION     
            "Contains the name of a component that is suspected of causing
             a fault."
    ::= { sunHwTrapData 6 }

sunHwTrapFaultClass OBJECT-TYPE
    SYNTAX          DisplayString
    ACCESS          read-only
    STATUS          mandatory
    DESCRIPTION     
            "The class represents a hierarchical classification string indicating
             the type of problem detected, as reported by the fault management
             subsystem, such as, for instance the Solaris fault manager.
             Information on the Solaris fault manager can be found at
             http://www.opensolaris.org/os/community/fm.
             
             This object will have a value of NULL if the system doesn't
             support this information."
--     REFERENCE       
--             "SUN-FM-MIB.sunFmFaultEventClass
--              http://www.opensolaris.org/os/community/fm/mib/sun-fm-mib.mib"
    ::= { sunHwTrapData 7 }

sunHwTrapFaultCertainty OBJECT-TYPE
    SYNTAX          INTEGER (0..100)
    ACCESS          read-only
    STATUS          mandatory
    DESCRIPTION     
            "The percentage likelihood that the component is the source
             of the problem. This object will have a value of 0 if the
             system doesn't support this information."
    ::= { sunHwTrapData 8 }

sunHwTrapAdditionalInfo OBJECT-TYPE
    SYNTAX          DisplayString
    ACCESS          read-only
    STATUS          mandatory
    DESCRIPTION     
            "An optional textual description which provides additional
             information relevant to this notification."
    ::= { sunHwTrapData 9 }

sunHwTrapAssocObjectId OBJECT-TYPE
    SYNTAX          RowPointer
    ACCESS          read-only
    STATUS          mandatory
    DESCRIPTION     
            "The object in the entPhysicalTable to which this notification applies.
             The value is the name of the instance of the first accessible columnar
             object in the entPhysicalTable conceptual row. If no association exists
             or the association cannot be determined, this object will have a value
             of 0.0."
    ::= { sunHwTrapData 10 }

sunHwTrapNewHAState OBJECT-TYPE
    SYNTAX          SunHwTrapHAStateTC
    ACCESS          read-only
    STATUS          mandatory
    DESCRIPTION     
            "This object provides the new value of the high availability state
             after a high availability state change has occurred."
    ::= { sunHwTrapData 11 }

sunHwTrapOldHAState OBJECT-TYPE
    SYNTAX          SunHwTrapHAStateTC
    ACCESS          read-only
    STATUS          mandatory
    DESCRIPTION     
            "This object provides the old value of the high availability state
             after a high availability state change has occurred."
    ::= { sunHwTrapData 12 }

sunHwTrapSeverity OBJECT-TYPE
    SYNTAX          SunHwTrapSeverityTC
    ACCESS          read-only
    STATUS          mandatory
    DESCRIPTION     
            "An indication of the severity of the notfication."
    ::= { sunHwTrapData 13 }

sunHwTrapChassisId OBJECT-TYPE
    SYNTAX          DisplayString
    ACCESS          read-only
    STATUS          mandatory
    DESCRIPTION     
            "A text string containing the chassis serial number. When combined
             with the sunHwTrapProductName, it unambiguously identifies the
             system. If the source of the trap is a blade, the text string will
             contain the chassis serial number and the blade serial number, in
             the following format <chassis-serial-number::blade-serial-number>"
    ::= { sunHwTrapData 14 }

sunHwTrapProductName OBJECT-TYPE
    SYNTAX          DisplayString
    ACCESS          read-only
    STATUS          mandatory
    DESCRIPTION     
            "A text string containing the product name. When combined with the
             sunHwTrapChassisId, it unambiguously identifies the system. If the
             source of the trap is a blade, the text string will contain the
             chassis product name and the blade product name, in the following
             format <chassis-name>::<blade-name>"
    ::= { sunHwTrapData 15 }

sunHwTrapHardDriveState OBJECT-TYPE
    SYNTAX          SunHwTrapHardDriveStatesTC
    ACCESS          read-only
    STATUS          mandatory
    DESCRIPTION     
            "The states a hard drive can be in when hard drive status
             is reported."
    ::= { sunHwTrapData 16 }

sunHwTrapFaultMessageID OBJECT-TYPE
    SYNTAX          DisplayString
    ACCESS          read-only
    STATUS          mandatory
    DESCRIPTION     
            "The message ID that can be used to get additional information about
             the problem from Sun's knowledge article database. This object will
             have a value of NULL if the system doesn't support this
             information."
    ::= { sunHwTrapData 17 }

sunHwTrapFaultUUID OBJECT-TYPE
    SYNTAX          DisplayString
    ACCESS          read-only
    STATUS          mandatory
    DESCRIPTION     
            "The universal unique identifier that was assigned to this fault. This
             object will have a value of NULL if the system doesn't support this
             information."
    ::= { sunHwTrapData 18 }

sunHwTrapDisableReason OBJECT-TYPE
    SYNTAX          SunHwTrapDisableReasonsTC
    ACCESS          read-only
    STATUS          mandatory
    DESCRIPTION     
            "An indication as to why the component was disabled."
    ::= { sunHwTrapData 19 }

sunHwTrapTestMessage OBJECT-TYPE
    SYNTAX          DisplayString
    ACCESS          read-only
    STATUS          mandatory
    DESCRIPTION     
            "This is a test trap"
    ::= { sunHwTrapData 20 }

sunHwTrapConformances OBJECT IDENTIFIER
    ::= { sunHwTrapMIB 3 }

sunHwTrapCompliances OBJECT IDENTIFIER
    ::= { sunHwTrapConformances 1 }

sunHwTrapGroups OBJECT IDENTIFIER
    ::= { sunHwTrapConformances 2 }

sunHwTrapObjectGroups OBJECT IDENTIFIER
    ::= { sunHwTrapGroups 1 }

sunHwTrapNotifGroups OBJECT IDENTIFIER
    ::= { sunHwTrapGroups 2 }

sunHwTrapVoltageFatalThresholdExceeded TRAP-TYPE
    ENTERPRISE      sunHwTraps
    VARIABLES       { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
--     STATUS          mandatory
    DESCRIPTION     
            "A voltage sensor has reported that its value has gone above an upper
             fatal threshold setting or below a lower fatal threshold setting.
             The sunHwTrapThresholdType object indicates whether the threshold was
             an upper or lower."
    ::= 1

sunHwTrapVoltageFatalThresholdDeasserted TRAP-TYPE
    ENTERPRISE      sunHwTraps
    VARIABLES       { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
--     STATUS          mandatory
    DESCRIPTION     
            "A voltage sensor has reported that its value has gone below an upper
             fatal threshold setting or above a lower fatal threshold setting.
             The sunHwTrapThresholdType object indicates whether the threshold was
             an upper or lower."
    ::= 2

sunHwTrapVoltageCritThresholdExceeded TRAP-TYPE
    ENTERPRISE      sunHwTraps
    VARIABLES       { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
--     STATUS          mandatory
    DESCRIPTION     
            "A voltage sensor has reported that its value has gone above an upper
             critical threshold setting or below a lower critical threshold setting.
             The sunHwTrapThresholdType object indicates whether the threshold was
             an upper or lower."
    ::= 3

sunHwTrapVoltageCritThresholdDeasserted TRAP-TYPE
    ENTERPRISE      sunHwTraps
    VARIABLES       { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
--     STATUS          mandatory
    DESCRIPTION     
            "A voltage sensor has reported that its value has gone below an upper
             critical threshold setting or above a lower critical threshold setting.
             The sunHwTrapThresholdType object indicates whether the threshold was
             an upper or lower."
    ::= 4

sunHwTrapVoltageNonCritThresholdExceeded TRAP-TYPE
    ENTERPRISE      sunHwTraps
    VARIABLES       { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
--     STATUS          mandatory
    DESCRIPTION     
            "A voltage sensor has reported that its value has gone above an upper
             non-critical threshold setting or below a lower non-critical threshold
             setting. The sunHwTrapThresholdType object indicates whether the threshold
             was an upper or lower."
    ::= 5

sunHwTrapVoltageOk TRAP-TYPE
    ENTERPRISE      sunHwTraps
    VARIABLES       { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
--     STATUS          mandatory
    DESCRIPTION     
            "A voltage sensor has reported that its value is in the normal
             operating range."
    ::= 6

sunHwTrapTempFatalThresholdExceeded TRAP-TYPE
    ENTERPRISE      sunHwTraps
    VARIABLES       { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
--     STATUS          mandatory
    DESCRIPTION     
            "A temperature sensor has reported that its value has gone above an upper
             fatal threshold setting or below a lower fatal threshold setting.
             The sunHwTrapThresholdType object indicates whether the threshold was
             an upper or lower."
    ::= 7

sunHwTrapTempFatalThresholdDeasserted TRAP-TYPE
    ENTERPRISE      sunHwTraps
    VARIABLES       { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
--     STATUS          mandatory
    DESCRIPTION     
            "A temperature sensor has reported that its value has gone below an
             upper fatal threshold setting or above a lower fatal threshold setting.
             The sunHwTrapThresholdType object indicates whether the threshold was
             an upper or lower."
    ::= 8

sunHwTrapTempCritThresholdExceeded TRAP-TYPE
    ENTERPRISE      sunHwTraps
    VARIABLES       { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
--     STATUS          mandatory
    DESCRIPTION     
            "A temperature sensor has reported that its value has gone above an
             upper critical threshold setting or below a lower critical threshold
             setting. The sunHwTrapThresholdType object indicates whether the
             threshold was an upper or lower."
    ::= 9

sunHwTrapTempCritThresholdDeasserted TRAP-TYPE
    ENTERPRISE      sunHwTraps
    VARIABLES       { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
--     STATUS          mandatory
    DESCRIPTION     
            "A temperature sensor has reported that its value has gone below an
             upper critical threshold setting or above a lower critical threshold
             setting. The sunHwTrapThresholdType object indicates whether the
             threshold was an upper or lower."
    ::= 10

sunHwTrapTempNonCritThresholdExceeded TRAP-TYPE
    ENTERPRISE      sunHwTraps
    VARIABLES       { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
--     STATUS          mandatory
    DESCRIPTION     
            "A temperature sensor has reported that its value has gone above an
             upper non-critical threshold setting or below a lower non-critical
             threshold setting. The sunHwTrapThresholdType object indicates whether
             the threshold was an upper or lower."
    ::= 11

sunHwTrapTempOk TRAP-TYPE
    ENTERPRISE      sunHwTraps
    VARIABLES       { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
--     STATUS          mandatory
    DESCRIPTION     
            "A temperature sensor has reported that its value is in the normal
             operating range."
    ::= 12

sunHwTrapElectricalCurrentFatalThresholdExceeded TRAP-TYPE
    ENTERPRISE      sunHwTraps
    VARIABLES       { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
--     STATUS          mandatory
    DESCRIPTION     
            "An electrical current sensor has reported that its value has gone above
             an upper fatal threshold setting or below a lower fatal threshold
             setting. The sunHwTrapThresholdType object indicates whether the
             threshold was an upper or lower."
    ::= 13

sunHwTrapElectricalCurrentFatalThresholdDeasserted TRAP-TYPE
    ENTERPRISE      sunHwTraps
    VARIABLES       { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
--     STATUS          mandatory
    DESCRIPTION     
            "An electrical current sensor has reported that its value has gone below
             an upper fatal threshold setting or above a lower fatal threshold
             setting. The sunHwTrapThresholdType object indicates whether the
             threshold was an upper or lower."
    ::= 14

sunHwTrapElectricalCurrentCritThresholdExceeded TRAP-TYPE
    ENTERPRISE      sunHwTraps
    VARIABLES       { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
--     STATUS          mandatory
    DESCRIPTION     
            "An electrical current sensor has reported that its value has gone above
             an upper critical threshold setting or below a lower critical threshold
             setting. The sunHwTrapThresholdType object indicates whether the
             threshold was an upper or lower."
    ::= 15

sunHwTrapElectricalCurrentCritThresholdDeasserted TRAP-TYPE
    ENTERPRISE      sunHwTraps
    VARIABLES       { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
--     STATUS          mandatory
    DESCRIPTION     
            "An electrical current sensor has reported that its value has gone below
             an upper critical threshold setting or above a lower critical threshold
             setting. The sunHwTrapThresholdType object indicates whether the
             threshold was an upper or lower."
    ::= 16

sunHwTrapElectricalCurrentNonCritThresholdExceeded TRAP-TYPE
    ENTERPRISE      sunHwTraps
    VARIABLES       { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
--     STATUS          mandatory
    DESCRIPTION     
            "An electrical current sensor has reported that its value has gone above
             an upper non-critical threshold setting or below a lower non-critical
             threshold setting. The sunHwTrapThresholdType object indicates whether
             the threshold was an upper or lower."
    ::= 17

sunHwTrapElectricalCurrentOk TRAP-TYPE
    ENTERPRISE      sunHwTraps
    VARIABLES       { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
--     STATUS          mandatory
    DESCRIPTION     
            "An electrical current sensor has reported that its value is in
             the normal operating range."
    ::= 18

sunHwTrapFanSpeedFatalThresholdExceeded TRAP-TYPE
    ENTERPRISE      sunHwTraps
    VARIABLES       { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
--     STATUS          mandatory
    DESCRIPTION     
            "A fan speed sensor has reported that its value has gone above an upper
             fatal threshold setting or below a lower fatal threshold setting.
             The sunHwTrapThresholdType object indicates whether the threshold was
             an upper or lower."
    ::= 19

sunHwTrapFanSpeedFatalThresholdDeasserted TRAP-TYPE
    ENTERPRISE      sunHwTraps
    VARIABLES       { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
--     STATUS          mandatory
    DESCRIPTION     
            "A fan speed sensor has reported that its value has gone below an upper
             fatal threshold setting or above a lower fatal threshold setting.
             The sunHwTrapThresholdType object indicates whether the threshold was
             an upper or lower."
    ::= 20

sunHwTrapFanSpeedCritThresholdExceeded TRAP-TYPE
    ENTERPRISE      sunHwTraps
    VARIABLES       { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
--     STATUS          mandatory
    DESCRIPTION     
            "A fan speed sensor has reported that its value has gone above an upper
             critical threshold setting or below a lower critical threshold setting.
             The sunHwTrapThresholdType object indicates whether the threshold was
             an upper or lower."
    ::= 21

sunHwTrapFanSpeedCritThresholdDeasserted TRAP-TYPE
    ENTERPRISE      sunHwTraps
    VARIABLES       { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
--     STATUS          mandatory
    DESCRIPTION     
            "A fan speed sensor has reported that its value has gone below an upper
             critical threshold setting or above a lower critical threshold setting.
             The sunHwTrapThresholdType object indicates whether the threshold was
             an upper or lower."
    ::= 22

sunHwTrapFanSpeedNonCritThresholdExceeded TRAP-TYPE
    ENTERPRISE      sunHwTraps
    VARIABLES       { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
--     STATUS          mandatory
    DESCRIPTION     
            "A fan speed sensor has reported that its value has gone above an upper
             non-critical threshold setting or below a lower non-critical threshold
             setting. The sunHwTrapThresholdType object indicates whether the
             threshold was an upper or lower."
    ::= 23

sunHwTrapFanSpeedOk TRAP-TYPE
    ENTERPRISE      sunHwTraps
    VARIABLES       { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
--     STATUS          mandatory
    DESCRIPTION     
            "A fan speed sensor has reported that its value is in
             the normal operating range."
    ::= 24

sunHwTrapSensorFatalThresholdExceeded TRAP-TYPE
    ENTERPRISE      sunHwTraps
    VARIABLES       { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
--     STATUS          mandatory
    DESCRIPTION     
            "A sensor has reported that its value has gone above an upper fatal
             threshold setting or below a lower fatal threshold setting. The 
             generic 'sensor' trap is generated when the SNMP agent does not
             recognize the component type. The sunHwTrapThresholdType object
             indicates whether the threshold was an upper or lower."
    ::= 25

sunHwTrapSensorFatalThresholdDeasserted TRAP-TYPE
    ENTERPRISE      sunHwTraps
    VARIABLES       { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
--     STATUS          mandatory
    DESCRIPTION     
            "A sensor has reported that its value has gone below an upper fatal
             threshold setting or above a lower fatal threshold setting. The
             generic 'sensor' trap is generated when the SNMP agent does not
             recognize the component type. The sunHwTrapThresholdType object
             indicates whether the threshold was an upper or lower."
    ::= 26

sunHwTrapSensorCritThresholdExceeded TRAP-TYPE
    ENTERPRISE      sunHwTraps
    VARIABLES       { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
--     STATUS          mandatory
    DESCRIPTION     
            "A sensor has reported that its value has gone above an upper critical
             threshold setting or below a lower critical threshold setting. The 
             generic 'sensor' trap is generated when the SNMP agent does not
             recognize the component type. The sunHwTrapThresholdType object
             indicates whether the threshold was an upper or lower."
    ::= 27

sunHwTrapSensorCritThresholdDeasserted TRAP-TYPE
    ENTERPRISE      sunHwTraps
    VARIABLES       { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
--     STATUS          mandatory
    DESCRIPTION     
            "A sensor has reported that its value has gone below an upper critical
             threshold setting or above a lower critical threshold setting. The
             generic 'sensor' trap is generated when the SNMP agent does not
             recognize the component type. The sunHwTrapThresholdType object
             indicates whether the threshold was an upper or lower."
    ::= 28

sunHwTrapSensorNonCritThresholdExceeded TRAP-TYPE
    ENTERPRISE      sunHwTraps
    VARIABLES       { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
--     STATUS          mandatory
    DESCRIPTION     
            "A sensor has reported that its value has gone above an upper
             non-critical threshold setting or below a lower non-critical threshold
             setting. The generic 'sensor' trap is generated when the SNMP agent
             does not recognize the component type. The sunHwTrapThresholdType
             object indicates whether the threshold was an upper or lower."
    ::= 29

sunHwTrapSensorThresholdOk TRAP-TYPE
    ENTERPRISE      sunHwTraps
    VARIABLES       { sunHwTrapSystemIdentifier, sunHwTrapChassisId, 
                      sunHwTrapProductName, sunHwTrapComponentName, 
                      sunHwTrapThresholdType, sunHwTrapThresholdValue, 
                      sunHwTrapSensorValue, sunHwTrapAdditionalInfo, 
                      sunHwTrapAssocObjectId, sunHwTrapSeverity }
--     STATUS          mandatory
    DESCRIPTION     
            "A sensor has reported that its value is in the normal operating range.
             The generic 'sensor' trap is generated when the SNMP agent does not
             recognize the component type."
    ::= 30

sunHwTrapPowerSupplyFault TRAP-TYPE
    ENTERPRISE      sunHwTraps
    VARIABLES       { sunHwTrapSystemIdentifier, sunHwTrapChassisId, 
                      sunHwTrapProductName, 
                      sunHwTrapSuspectComponentName, sunHwTrapFaultClass, 
                      sunHwTrapFaultCertainty, sunHwTrapFaultMessageID, 
                      sunHwTrapFaultUUID, sunHwTrapAssocObjectId, 
                      sunHwTrapAdditionalInfo }
--     STATUS          mandatory
    DESCRIPTION     
            "A power supply component is suspected of causing a fault."
    ::= 31

sunHwTrapPowerSupplyError TRAP-TYPE
    ENTERPRISE      sunHwTraps
    VARIABLES       { sunHwTrapSystemIdentifier, sunHwTrapChassisId, 
                      sunHwTrapProductName, sunHwTrapComponentName, 
                      sunHwTrapAdditionalInfo, sunHwTrapAssocObjectId }
--     STATUS          mandatory
    DESCRIPTION     
            "A power supply sensor has detected an error."
    ::= 32

sunHwTrapPowerSupplyOk TRAP-TYPE
    ENTERPRISE      sunHwTraps
    VARIABLES       { sunHwTrapSystemIdentifier, sunHwTrapChassisId, 
                      sunHwTrapProductName, sunHwTrapComponentName, 
                      sunHwTrapAdditionalInfo, sunHwTrapAssocObjectId }
--     STATUS          mandatory
    DESCRIPTION     
            "A power supply sensor has returned to its normal state."
    ::= 33

sunHwTrapFanFault TRAP-TYPE
    ENTERPRISE      sunHwTraps
    VARIABLES       { sunHwTrapSystemIdentifier, sunHwTrapChassisId, 
                      sunHwTrapProductName, 
                      sunHwTrapSuspectComponentName, sunHwTrapFaultClass, 
                      sunHwTrapFaultCertainty, sunHwTrapFaultMessageID, 
                      sunHwTrapFaultUUID, sunHwTrapAssocObjectId, 
                      sunHwTrapAdditionalInfo }
--     STATUS          mandatory
    DESCRIPTION     
            "A fan component is suspected of causing a fault."
    ::= 34

sunHwTrapFanError TRAP-TYPE
    ENTERPRISE      sunHwTraps
    VARIABLES       { sunHwTrapSystemIdentifier, sunHwTrapChassisId, 
                      sunHwTrapProductName, sunHwTrapComponentName, 
                      sunHwTrapAdditionalInfo, sunHwTrapAssocObjectId }
--     STATUS          mandatory
    DESCRIPTION     
            "A fan sensor has detected an error."
    ::= 35

sunHwTrapFanOk TRAP-TYPE
    ENTERPRISE      sunHwTraps
    VARIABLES       { sunHwTrapSystemIdentifier, sunHwTrapChassisId, 
                      sunHwTrapProductName, sunHwTrapComponentName, 
                      sunHwTrapAdditionalInfo, sunHwTrapAssocObjectId }
--     STATUS          mandatory
    DESCRIPTION     
            "A fan sensor has returned to its normal state."
    ::= 36

sunHwTrapProcessorFault TRAP-TYPE
    ENTERPRISE      sunHwTraps
    VARIABLES       { sunHwTrapSystemIdentifier, sunHwTrapChassisId, 
                      sunHwTrapProductName, 
                      sunHwTrapSuspectComponentName, sunHwTrapFaultClass, 
                      sunHwTrapFaultCertainty, sunHwTrapFaultMessageID, 
                      sunHwTrapFaultUUID, sunHwTrapAssocObjectId, 
                      sunHwTrapAdditionalInfo }
--     STATUS          mandatory
    DESCRIPTION     
            "A processor component is suspected of causing a fault."
    ::= 37

sunHwTrapProcessorError TRAP-TYPE
    ENTERPRISE      sunHwTraps
    VARIABLES       { sunHwTrapSystemIdentifier, sunHwTrapChassisId, 
                      sunHwTrapProductName, sunHwTrapComponentName, 
                      sunHwTrapAdditionalInfo, sunHwTrapAssocObjectId }
--     STATUS          mandatory
    DESCRIPTION     
            "A processor sensor has detected an error."
    ::= 38

sunHwTrapProcessorOk TRAP-TYPE
    ENTERPRISE      sunHwTraps
    VARIABLES       { sunHwTrapSystemIdentifier, sunHwTrapChassisId, 
                      sunHwTrapProductName, sunHwTrapComponentName, 
                      sunHwTrapAdditionalInfo, sunHwTrapAssocObjectId }
--     STATUS          mandatory
    DESCRIPTION     
            "A processor sensor has returned to its normal state."
    ::= 39

sunHwTrapMemoryFault TRAP-TYPE
    ENTERPRISE      sunHwTraps
    VARIABLES       { sunHwTrapSystemIdentifier, sunHwTrapChassisId, 
                      sunHwTrapProductName, 
                      sunHwTrapSuspectComponentName, sunHwTrapFaultClass, 
                      sunHwTrapFaultCertainty, sunHwTrapFaultMessageID, 
                      sunHwTrapFaultUUID, sunHwTrapAssocObjectId, 
                      sunHwTrapAdditionalInfo }
--     STATUS          mandatory
    DESCRIPTION     
            "A memory component is suspected of causing a fault."
    ::= 40

sunHwTrapMemoryError TRAP-TYPE
    ENTERPRISE      sunHwTraps
    VARIABLES       { sunHwTrapSystemIdentifier, sunHwTrapChassisId, 
                      sunHwTrapProductName, sunHwTrapComponentName, 
                      sunHwTrapAdditionalInfo, sunHwTrapAssocObjectId }
--     STATUS          mandatory
    DESCRIPTION     
            "A memory sensor has detected an error."
    ::= 41

sunHwTrapMemoryOk TRAP-TYPE
    ENTERPRISE      sunHwTraps
    VARIABLES       { sunHwTrapSystemIdentifier, sunHwTrapChassisId, 
                      sunHwTrapProductName, sunHwTrapComponentName, 
                      sunHwTrapAdditionalInfo, sunHwTrapAssocObjectId }
--     STATUS          mandatory
    DESCRIPTION     
            "A memory sensor has returned to its normal state."
    ::= 42

sunHwTrapHardDriveFault TRAP-TYPE
    ENTERPRISE      sunHwTraps
    VARIABLES       { sunHwTrapSystemIdentifier, sunHwTrapChassisId, 
                      sunHwTrapProductName, 
                      sunHwTrapSuspectComponentName, sunHwTrapFaultClass, 
                      sunHwTrapFaultCertainty, sunHwTrapFaultMessageID, 
                      sunHwTrapFaultUUID, sunHwTrapAssocObjectId, 
                      sunHwTrapAdditionalInfo }
--     STATUS          mandatory
    DESCRIPTION     
            "A hard drive component is suspected of causing a fault."
    ::= 43

sunHwTrapHardDriveError TRAP-TYPE
    ENTERPRISE      sunHwTraps
    VARIABLES       { sunHwTrapSystemIdentifier, sunHwTrapChassisId, 
                      sunHwTrapProductName, sunHwTrapComponentName, 
                      sunHwTrapAdditionalInfo, sunHwTrapAssocObjectId }
--     STATUS          mandatory
    DESCRIPTION     
            "A hard drive sensor has detected an error."
    ::= 44

sunHwTrapHardDriveOk TRAP-TYPE
    ENTERPRISE      sunHwTraps
    VARIABLES       { sunHwTrapSystemIdentifier, sunHwTrapChassisId, 
                      sunHwTrapProductName, sunHwTrapComponentName, 
                      sunHwTrapAdditionalInfo, sunHwTrapAssocObjectId }
--     STATUS          mandatory
    DESCRIPTION     
            "A hard drive sensor has returned to its normal state."
    ::= 45

sunHwTrapIOFault TRAP-TYPE
    ENTERPRISE      sunHwTraps
    VARIABLES       { sunHwTrapSystemIdentifier, sunHwTrapChassisId, 
                      sunHwTrapProductName, 
                      sunHwTrapSuspectComponentName, sunHwTrapFaultClass, 
                      sunHwTrapFaultCertainty, sunHwTrapFaultMessageID, 
                      sunHwTrapFaultUUID, sunHwTrapAssocObjectId, 
                      sunHwTrapAdditionalInfo }
--     STATUS          mandatory
    DESCRIPTION     
            "A component in the IO subsystem is suspected of causing a fault."
    ::= 46

sunHwTrapIOError TRAP-TYPE
    ENTERPRISE      sunHwTraps
    VARIABLES       { sunHwTrapSystemIdentifier, sunHwTrapChassisId, 
                      sunHwTrapProductName, sunHwTrapComponentName, 
                      sunHwTrapAdditionalInfo, sunHwTrapAssocObjectId }
--     STATUS          mandatory
    DESCRIPTION     
            "An IO sensor has detected an error."
    ::= 47

sunHwTrapIOOk TRAP-TYPE
    ENTERPRISE      sunHwTraps
    VARIABLES       { sunHwTrapSystemIdentifier, sunHwTrapChassisId, 
                      sunHwTrapProductName, sunHwTrapComponentName, 
                      sunHwTrapAdditionalInfo, sunHwTrapAssocObjectId }
--     STATUS          mandatory
    DESCRIPTION     
            "An IO sensor has returned to its normal state."
    ::= 48

sunHwTrapSlotOrConnectorFault TRAP-TYPE
    ENTERPRISE      sunHwTraps
    VARIABLES       { sunHwTrapSystemIdentifier, sunHwTrapChassisId, 
                      sunHwTrapProductName, 
                      sunHwTrapSuspectComponentName, sunHwTrapFaultClass, 
                      sunHwTrapFaultCertainty, sunHwTrapFaultMessageID, 
                      sunHwTrapFaultUUID, sunHwTrapAssocObjectId, 
                      sunHwTrapAdditionalInfo }
--     STATUS          mandatory
    DESCRIPTION     
            "A slot or connector component is suspected of causing a fault."
    ::= 49

sunHwTrapSlotOrConnectorError TRAP-TYPE
    ENTERPRISE      sunHwTraps
    VARIABLES       { sunHwTrapSystemIdentifier, sunHwTrapChassisId, 
                      sunHwTrapProductName, sunHwTrapComponentName, 
                      sunHwTrapAdditionalInfo, sunHwTrapAssocObjectId }
--     STATUS          mandatory
    DESCRIPTION     
            "A sensor associated with a slot or connector has detected an error."
    ::= 50

sunHwTrapSlotOrConnectorOk TRAP-TYPE
    ENTERPRISE      sunHwTraps
    VARIABLES       { sunHwTrapSystemIdentifier, sunHwTrapChassisId, 
                      sunHwTrapProductName, sunHwTrapComponentName, 
                      sunHwTrapAdditionalInfo, sunHwTrapAssocObjectId }
--     STATUS          mandatory
    DESCRIPTION     
            "A sensor associated with a slot or connector has returned
             to its normal state."
    ::= 51

sunHwTrapComponentFault TRAP-TYPE
    ENTERPRISE      sunHwTraps
    VARIABLES       { sunHwTrapSystemIdentifier, sunHwTrapChassisId, 
                      sunHwTrapProductName, 
                      sunHwTrapSuspectComponentName, sunHwTrapFaultClass, 
                      sunHwTrapFaultCertainty, sunHwTrapFaultMessageID, 
                      sunHwTrapFaultUUID, sunHwTrapAssocObjectId, 
                      sunHwTrapAdditionalInfo }
--     STATUS          mandatory
    DESCRIPTION     
            "A component is suspected of causing a fault. This generic 'component'
             trap is generated when the SNMP agent does not recognize the component
             type."
    ::= 52

sunHwTrapComponentError TRAP-TYPE
    ENTERPRISE      sunHwTraps
    VARIABLES       { sunHwTrapSystemIdentifier, sunHwTrapChassisId, 
                      sunHwTrapProductName, sunHwTrapComponentName, 
                      sunHwTrapAdditionalInfo, sunHwTrapAssocObjectId }
--     STATUS          mandatory
    DESCRIPTION     
            "A sensor has detected an error. This generic 'component' trap is
             generated when the SNMP agent does not recognize the component type."
    ::= 53

sunHwTrapComponentOk TRAP-TYPE
    ENTERPRISE      sunHwTraps
    VARIABLES       { sunHwTrapSystemIdentifier, sunHwTrapChassisId, 
                      sunHwTrapProductName, sunHwTrapComponentName, 
                      sunHwTrapAdditionalInfo, sunHwTrapAssocObjectId }
--     STATUS          mandatory
    DESCRIPTION     
            "A sensor has returned to its normal state. This generic 'component'
             trap is generated when the SNMP agent does not recognize the component
             type."
    ::= 54

sunHwTrapFruInserted TRAP-TYPE
    ENTERPRISE      sunHwTraps
    VARIABLES       { sunHwTrapSystemIdentifier, sunHwTrapChassisId, 
                      sunHwTrapProductName, sunHwTrapComponentName, 
                      sunHwTrapAssocObjectId }
--     STATUS          mandatory
    DESCRIPTION     
            "A field replaceable unit has been inserted into the system."
    ::= 55

sunHwTrapFruRemoved TRAP-TYPE
    ENTERPRISE      sunHwTraps
    VARIABLES       { sunHwTrapSystemIdentifier, sunHwTrapChassisId, 
                      sunHwTrapProductName, sunHwTrapComponentName, 
                      sunHwTrapAssocObjectId }
--     STATUS          mandatory
    DESCRIPTION     
            "A field replaceable unit has been removed from the system."
    ::= 56

sunHwTrapComponentDisabled TRAP-TYPE
    ENTERPRISE      sunHwTraps
    VARIABLES       { sunHwTrapSystemIdentifier, sunHwTrapChassisId, 
                      sunHwTrapProductName, sunHwTrapComponentName, 
                      sunHwTrapDisableReason, sunHwTrapAdditionalInfo, 
                      sunHwTrapAssocObjectId }
--     STATUS          mandatory
    DESCRIPTION     
            "The component operational state has changed or is changing
             to disabled."
    ::= 57

sunHwTrapComponentEnabled TRAP-TYPE
    ENTERPRISE      sunHwTraps
    VARIABLES       { sunHwTrapSystemIdentifier, sunHwTrapChassisId, 
                      sunHwTrapProductName, sunHwTrapComponentName, 
                      sunHwTrapAdditionalInfo, sunHwTrapAssocObjectId }
--     STATUS          mandatory
    DESCRIPTION     
            "The component operational state has changed or is changing
             to enabled."
    ::= 58

sunHwTrapPreOSError TRAP-TYPE
    ENTERPRISE      sunHwTraps
    VARIABLES       { sunHwTrapSystemIdentifier, sunHwTrapChassisId, 
                      sunHwTrapProductName, sunHwTrapAdditionalInfo }
--     STATUS          mandatory
    DESCRIPTION     
            "An error has been detected in the period before the operating
             system has taken control of the system."
    ::= 59

sunHwTrapHAStateChange TRAP-TYPE
    ENTERPRISE      sunHwTraps
    VARIABLES       { sunHwTrapSystemIdentifier, sunHwTrapChassisId, 
                      sunHwTrapProductName, sunHwTrapNewHAState, 
                      sunHwTrapOldHAState, sunHwTrapAdditionalInfo }
--     STATUS          mandatory
    DESCRIPTION     
            "The high availability component identified by sunHwTrapSystemIdentifier
             has changed state."
    ::= 60

sunHwTrapSecurityIntrusion TRAP-TYPE
    ENTERPRISE      sunHwTraps
    VARIABLES       { sunHwTrapSystemIdentifier, sunHwTrapChassisId, 
                      sunHwTrapProductName, sunHwTrapAdditionalInfo }
--     STATUS          mandatory
    DESCRIPTION     
            "An intrusion sensor has detected that someone may have physically
             tampered with the system."
    ::= 61

sunHwTrapHardDriveStatus TRAP-TYPE
    ENTERPRISE      sunHwTraps
    VARIABLES       { sunHwTrapSystemIdentifier, sunHwTrapChassisId, 
                      sunHwTrapProductName, sunHwTrapComponentName, 
                      sunHwTrapHardDriveState }
--     STATUS          mandatory
    DESCRIPTION     
            "The hard drive identified by sunHwTrapComponentName has changed state."
    ::= 62

sunHwTrapTestTrap TRAP-TYPE
    ENTERPRISE      sunHwTraps
    VARIABLES       { sunHwTrapSystemIdentifier, sunHwTrapChassisId, 
                      sunHwTrapProductName, sunHwTrapTestMessage }
--     STATUS          mandatory
    DESCRIPTION     
            "This is a test trap"
    ::= 63

sunHwTrapPowerSupplyFaultCleared TRAP-TYPE
    ENTERPRISE      sunHwTraps
    VARIABLES       { sunHwTrapSystemIdentifier, sunHwTrapChassisId, 
                      sunHwTrapProductName, sunHwTrapComponentName, 
                      sunHwTrapAssocObjectId, sunHwTrapAdditionalInfo }
--     STATUS          mandatory
    DESCRIPTION     
            "A power supply component fault has been cleared."
    ::= 64

sunHwTrapFanFaultCleared TRAP-TYPE
    ENTERPRISE      sunHwTraps
    VARIABLES       { sunHwTrapSystemIdentifier, sunHwTrapChassisId, 
                      sunHwTrapProductName, sunHwTrapComponentName, 
                      sunHwTrapAssocObjectId, sunHwTrapAdditionalInfo }
--     STATUS          mandatory
    DESCRIPTION     
            "A fan component fault has been cleared."
    ::= 65

sunHwTrapProcessorFaultCleared TRAP-TYPE
    ENTERPRISE      sunHwTraps
    VARIABLES       { sunHwTrapSystemIdentifier, sunHwTrapChassisId, 
                      sunHwTrapProductName, sunHwTrapComponentName, 
                      sunHwTrapAssocObjectId, sunHwTrapAdditionalInfo }
--     STATUS          mandatory
    DESCRIPTION     
            "A processor component fault has been cleared."
    ::= 66

sunHwTrapMemoryFaultCleared TRAP-TYPE
    ENTERPRISE      sunHwTraps
    VARIABLES       { sunHwTrapSystemIdentifier, sunHwTrapChassisId, 
                      sunHwTrapProductName, sunHwTrapComponentName, 
                      sunHwTrapAssocObjectId, sunHwTrapAdditionalInfo }
--     STATUS          mandatory
    DESCRIPTION     
            "A memory component fault has been cleared."
    ::= 67

sunHwTrapHardDriveFaultCleared TRAP-TYPE
    ENTERPRISE      sunHwTraps
    VARIABLES       { sunHwTrapSystemIdentifier, sunHwTrapChassisId, 
                      sunHwTrapProductName, sunHwTrapComponentName, 
                      sunHwTrapAssocObjectId, sunHwTrapAdditionalInfo }
--     STATUS          mandatory
    DESCRIPTION     
            "A hard drive component fault has been cleared."
    ::= 68

sunHwTrapIOFaultCleared TRAP-TYPE
    ENTERPRISE      sunHwTraps
    VARIABLES       { sunHwTrapSystemIdentifier, sunHwTrapChassisId, 
                      sunHwTrapProductName, sunHwTrapComponentName, 
                      sunHwTrapAssocObjectId, sunHwTrapAdditionalInfo }
--     STATUS          mandatory
    DESCRIPTION     
            "An IO subsystem component fault has been cleared."
    ::= 69

sunHwTrapSlotOrConnectorFaultCleared TRAP-TYPE
    ENTERPRISE      sunHwTraps
    VARIABLES       { sunHwTrapSystemIdentifier, sunHwTrapChassisId, 
                      sunHwTrapProductName, sunHwTrapComponentName, 
                      sunHwTrapAssocObjectId, sunHwTrapAdditionalInfo }
--     STATUS          mandatory
    DESCRIPTION     
            "A slot or connector component fault has been cleared."
    ::= 70

sunHwTrapComponentFaultCleared TRAP-TYPE
    ENTERPRISE      sunHwTraps
    VARIABLES       { sunHwTrapSystemIdentifier, sunHwTrapChassisId, 
                      sunHwTrapProductName, sunHwTrapComponentName, 
                      sunHwTrapAssocObjectId, sunHwTrapAdditionalInfo }
--     STATUS          mandatory
    DESCRIPTION     
            "A component fault has been cleared. This generic 'component'
             trap is generated when the SNMP agent does not recognize the component
             type."
    ::= 71

sunHwTrapNotificationObjectGroup OBJECT IDENTIFIER
    ::= { sunHwTrapObjectGroups 2 }

-- sunHwTrapNotificationObjectGroup OBJECT-GROUP
--     OBJECTS         { sunHwTrapSystemIdentifier, 
--                       sunHwTrapComponentName, sunHwTrapThresholdType, 
--                       sunHwTrapThresholdValue, sunHwTrapSensorValue, 
--                       sunHwTrapSuspectComponentName, 
--                       sunHwTrapFaultClass, sunHwTrapFaultCertainty, 
--                       sunHwTrapAdditionalInfo, sunHwTrapAssocObjectId, 
--                       sunHwTrapNewHAState, sunHwTrapOldHAState, 
--                       sunHwTrapSeverity, sunHwTrapChassisId, 
--                       sunHwTrapProductName, sunHwTrapHardDriveState, 
--                       sunHwTrapFaultMessageID, sunHwTrapFaultUUID, 
--                       sunHwTrapDisableReason, sunHwTrapTestMessage }
--     STATUS          mandatory
--     DESCRIPTION     
--             "The collection of objects used in notifications."
--     ::= { sunHwTrapObjectGroups 2 }

sunHwTrapNotificationsGroup OBJECT IDENTIFIER
    ::= { sunHwTrapNotifGroups 1 }

-- sunHwTrapNotificationsGroup NOTIFICATION-GROUP
--     NOTIFICATIONS   { sunHwTrapVoltageFatalThresholdExceeded, 
--                       sunHwTrapVoltageFatalThresholdDeasserted, 
--                       sunHwTrapVoltageCritThresholdExceeded, 
--                       sunHwTrapVoltageCritThresholdDeasserted, 
--                       sunHwTrapVoltageNonCritThresholdExceeded, 
--                       sunHwTrapVoltageOk, 
--                       sunHwTrapTempFatalThresholdExceeded, 
--                       sunHwTrapTempFatalThresholdDeasserted, 
--                       sunHwTrapTempCritThresholdExceeded, 
--                       sunHwTrapTempCritThresholdDeasserted, 
--                       sunHwTrapTempNonCritThresholdExceeded, 
--                       sunHwTrapTempOk, 
--                       sunHwTrapElectricalCurrentFatalThresholdExceeded, 
--                       sunHwTrapElectricalCurrentFatalThresholdDeasserted, 
--                       sunHwTrapElectricalCurrentCritThresholdExceeded, 
--                       sunHwTrapElectricalCurrentCritThresholdDeasserted, 
--                       sunHwTrapElectricalCurrentNonCritThresholdExceeded, 
--                       sunHwTrapElectricalCurrentOk, 
--                       sunHwTrapFanSpeedFatalThresholdExceeded, 
--                       sunHwTrapFanSpeedFatalThresholdDeasserted, 
--                       sunHwTrapFanSpeedCritThresholdExceeded, 
--                       sunHwTrapFanSpeedCritThresholdDeasserted, 
--                       sunHwTrapFanSpeedNonCritThresholdExceeded, 
--                       sunHwTrapFanSpeedOk, 
--                       sunHwTrapSensorFatalThresholdExceeded, 
--                       sunHwTrapSensorFatalThresholdDeasserted, 
--                       sunHwTrapSensorCritThresholdExceeded, 
--                       sunHwTrapSensorCritThresholdDeasserted, 
--                       sunHwTrapSensorNonCritThresholdExceeded, 
--                       sunHwTrapSensorThresholdOk, 
--                       sunHwTrapPowerSupplyFault, 
--                       sunHwTrapPowerSupplyFaultCleared, 
--                       sunHwTrapPowerSupplyError, 
--                       sunHwTrapPowerSupplyOk, sunHwTrapFanFault, 
--                       sunHwTrapFanFaultCleared, sunHwTrapFanError, 
--                       sunHwTrapFanOk, sunHwTrapProcessorFault, 
--                       sunHwTrapProcessorFaultCleared, 
--                       sunHwTrapProcessorError, sunHwTrapProcessorOk, 
--                       sunHwTrapMemoryFault, 
--                       sunHwTrapMemoryFaultCleared, 
--                       sunHwTrapMemoryError, sunHwTrapMemoryOk, 
--                       sunHwTrapHardDriveFault, 
--                       sunHwTrapHardDriveFaultCleared, 
--                       sunHwTrapHardDriveError, sunHwTrapHardDriveOk, 
--                       sunHwTrapIOFault, sunHwTrapIOFaultCleared, 
--                       sunHwTrapIOError, sunHwTrapIOOk, 
--                       sunHwTrapSlotOrConnectorFault, 
--                       sunHwTrapSlotOrConnectorFaultCleared, 
--                       sunHwTrapSlotOrConnectorError, 
--                       sunHwTrapSlotOrConnectorOk, 
--                       sunHwTrapComponentFault, 
--                       sunHwTrapComponentFaultCleared, 
--                       sunHwTrapComponentError, sunHwTrapComponentOk, 
--                       sunHwTrapFruInserted, sunHwTrapFruRemoved, 
--                       sunHwTrapComponentDisabled, 
--                       sunHwTrapComponentEnabled, sunHwTrapPreOSError, 
--                       sunHwTrapHAStateChange, 
--                       sunHwTrapSecurityIntrusion, 
--                       sunHwTrapHardDriveStatus, sunHwTrapTestTrap }
--     STATUS          mandatory
--     DESCRIPTION     
--             "The collection of notifications used to indicate faults, errors,
--              and other conditions related to HW components in the system."
--     ::= { sunHwTrapNotifGroups 1 }

END -- end of module SUN-HW-TRAP-MIB.
