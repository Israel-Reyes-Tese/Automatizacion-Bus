--
-- This SMIv1 module has been generated by smidump 0.2-cvs. Do not edit.
--

SONUS-SOFTSWITCH-SSREQ-MIB DEFINITIONS ::= BEGIN

IMPORTS
    TRAP-TYPE
        FROM RFC-1215
    sonusEventClass, sonusEventDescription, sonusEventLevel, 
    sonusEventTime
        FROM SONUS-COMMON-MIB
    sonusServicesMIBs
        FROM SONUS-SMI;

sonusSoftSwitchSsreqMIB OBJECT IDENTIFIER
    ::= { sonusServicesMIBs 19 }

-- sonusSoftSwitchSsreqMIB MODULE-IDENTITY
--     LAST-UPDATED    "200211040000Z"
--     ORGANIZATION    
--             "Sonus Networks, Inc."
--     CONTACT-INFO    
--             "   Customer Support    
--              Sonus Networks, Inc.
--              250 Apollo Drive
--              Chelmsford, MA 01824
--              USA
--              
--              Tel: 978-614-8100
--              Fax: 978-614-8609"
--     DESCRIPTION     
--             "The MIB Module for SoftSwitch Ss Request Management."
--     ::= { sonusServicesMIBs 19 }


sonusSoftSwitchSsreqMIBObjects OBJECT IDENTIFIER
    ::= { sonusSoftSwitchSsreqMIB 1 }

sonusSoftSwitchSsreqMIBNotifications OBJECT IDENTIFIER
    ::= { sonusSoftSwitchSsreqMIB 2 }

sonusSoftSwitchSsreqMIBNotificationsPrefix OBJECT IDENTIFIER
    ::= { sonusSoftSwitchSsreqMIBNotifications 0 }

sonusSoftSwitchSsreqMIBNotificationsObjects OBJECT IDENTIFIER
    ::= { sonusSoftSwitchSsreqMIBNotifications 1 }

sonusSoftSwitchSsreqDownNotification TRAP-TYPE
    ENTERPRISE      sonusSoftSwitchSsreqMIBNotifications
    VARIABLES       { sonusEventDescription, sonusEventClass, 
                      sonusEventLevel, sonusEventTime }
--     STATUS          mandatory
    DESCRIPTION     
            "Ss Request is down"
    ::= 1

sonusSoftSwitchSsreqUpNotification TRAP-TYPE
    ENTERPRISE      sonusSoftSwitchSsreqMIBNotifications
    VARIABLES       { sonusEventDescription, sonusEventClass, 
                      sonusEventLevel, sonusEventTime }
--     STATUS          mandatory
    DESCRIPTION     
            "Ss Request is up"
    ::= 2

END -- end of module SONUS-SOFTSWITCH-SSREQ-MIB.
