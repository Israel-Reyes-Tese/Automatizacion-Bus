-- COPYRIGHT 2013 CA, Inc. ALL RIGHTS RESERVED.
-- THIS DOCUMENT CONTAINS CONFIDENTIAL AND TRADE SECRET INFORMATION OF
-- THE CA, Inc.  COPYRIGHT NOTICE IS PRECAUTIONARY
-- ONLY AND DOES NOT IMPLY PUBLICATION.

-- No part of this document may be reproduced, transmitted, transcribed,
-- stored in a retrieval system, or translated into any language or
-- computer language, in any form or by any means, without
-- prior written consent of CA, Inc.

-- SystemEDGE/MIB Version 5.8

EMPIRE-EXTENSIONS DEFINITIONS ::= BEGIN
    IMPORTS
        MODULE-IDENTITY, OBJECT-TYPE, enterprises,
        Integer32, Counter32, Gauge32, TimeTicks, IpAddress
            FROM SNMPv2-SMI
        DisplayString
            FROM SNMPv2-TC
        SnmpAdminString
            FROM SNMP-FRAMEWORK-MIB;

extensionGroup MODULE-IDENTITY
    LAST-UPDATED "201012140000Z"
    ORGANIZATION "CA Technologies"
    CONTACT-INFO    
        "One CA Plaza, Islandia, NY 11749, USA, www.ca.com/support"
    DESCRIPTION
       "This MIB allows users of the SystemEDGE agent to extend the EMPIRE MIB
       by adding new scalar variables. Each leaf in the extensionGroup and the
       ntRegPerf group specifies a different MIB scalar value. The values for
       these variables are determined by executing a command or (Windows only)
       by querying the (performance) registry. The name of the command resp.
       the registry path (and other parameters) are configured in the sysedge.cf
       configuration file (see 'extension' and 'ntregperf' section)."

    REVISION "201012140000Z"
    DESCRIPTION
        "Initial version of this MIB module."
    ::= { empire 14 }

    empire    OBJECT IDENTIFIER ::= { enterprises 546 }
    nt        OBJECT IDENTIFIER ::= { empire 5 }
    ntRegPerf OBJECT IDENTIFIER ::= { nt 7 }


------------------------------------------------------------
--  For this extensionGroup example, configure an entry in sysedge.cf file:
--      extension 1 octetstring readonly '%CASYSEDGE%\bin\getver.exe -f %CASYSEDGE%\bin\sysedge.dll'
------------------------------------------------------------
--  Now the manager application can read the attribute value. For example:
--      snmpget -h <host> -c <community> -o extensionGroup.1.0
------------------------------------------------------------
    mySysedgeDllVersion OBJECT-TYPE
        SYNTAX DisplayString
        MAX-ACCESS read-only
        STATUS current
        DESCRIPTION
            "My first extensionGroup attribute retrieving the version of the SystemEDGE DLL."
    ::= { extensionGroup 1 }


------------------------------------------------------------
--  For this ntRegPerf group example, configure an entry in sysedge.cf file:
--      ntregperf 1 gauge performance 'LogicalDisk' 'Free Megabytes' 'C:'
------------------------------------------------------------
--  Now the manager application can read the attribute value. For example:
--      snmpget -h <host> -c <community> -o ntRegPerf.1.0
------------------------------------------------------------
    myFileSystemCUsage OBJECT-TYPE
        SYNTAX Gauge32
        MAX-ACCESS read-only
        STATUS current
        DESCRIPTION
            "My first ntRegPerf attribute retrieving the free megabytes of filesystem C."
    ::= { ntRegPerf 1 }


END
