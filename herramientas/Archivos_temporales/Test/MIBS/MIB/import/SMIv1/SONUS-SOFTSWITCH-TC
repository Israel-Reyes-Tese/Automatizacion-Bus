--
-- This SMIv1 module has been generated by smidump 0.2-cvs. Do not edit.
--

SONUS-SOFTSWITCH-TC DEFINITIONS ::= BEGIN

IMPORTS
    sonusModules
        FROM SONUS-SMI;

sonusSoftSwitchTextualConventions OBJECT IDENTIFIER
    ::= { sonusModules 2 }

-- sonusSoftSwitchTextualConventions MODULE-IDENTITY
--     LAST-UPDATED    "200004230000Z"
--     ORGANIZATION    
--             "Sonus Networks, Inc."
--     CONTACT-INFO    
--             "   Customer Support    
--              Sonus Networks, Inc.
--              250 Apollo Drive
--              Chelmsford, MA 01824
--              USA
--              
--              Tel: 978-614-8100
--              Fax: 978-614-8609"
--     DESCRIPTION     
--             "This module defines textual conventions used througout Sonus
--              SoftSwitch MIBs."
--     ::= { sonusModules 2 }


SonusSoftSwitchDbOperationFailureReason ::=
    INTEGER { connection(1), update(2) }

-- SonusSoftSwitchDbOperationFailureReason ::= TEXTUAL-CONVENTION
--     STATUS          mandatory
--     DESCRIPTION     
--             "DB operation failure reason."
--     SYNTAX          INTEGER
--                       { connection(1), update(2) }

SonusSoftSwitchEntityId ::=
    INTEGER { pes(1), scpa(2) }

-- SonusSoftSwitchEntityId ::= TEXTUAL-CONVENTION
--     STATUS          mandatory
--     DESCRIPTION     
--             "An INTEGER representing the entity identifiers for
--              software entities in a SoftSwitch."
--     SYNTAX          INTEGER
--                       { pes(1), scpa(2) }

SonusTMIdentifier ::=
    OCTET STRING (SIZE(0..31))

-- SonusTMIdentifier ::= TEXTUAL-CONVENTION
--     DISPLAY-HINT    "31a"
--     STATUS          mandatory
--     DESCRIPTION     
--             "Identifies the control."
--     SYNTAX          OCTET STRING (SIZE(0..31))

SonusCriteriaFormat ::=
    INTEGER { calledAddressAndService(1), calledAddress(2), 
                        callingAddressAndService(3), service(4) }

-- SonusCriteriaFormat ::= TEXTUAL-CONVENTION
--     STATUS          mandatory
--     DESCRIPTION     
--             "The format of the criteria identifier"
--     SYNTAX          INTEGER
--                       { calledAddressAndService(1), calledAddress(2), 
--                         callingAddressAndService(3), service(4) }

SonusSoftSwitchTransportType ::=
    INTEGER { tcp(1), udp(2), sctp(3) }

-- SonusSoftSwitchTransportType ::= TEXTUAL-CONVENTION
--     STATUS          mandatory
--     DESCRIPTION     
--             "Specifies the transport type used for traffic"
--     SYNTAX          INTEGER
--                       { tcp(1), udp(2), sctp(3) }

SonusSoftSwitchDomainNameLength ::=
    INTEGER (0..2147483647)

-- SonusSoftSwitchDomainNameLength ::= TEXTUAL-CONVENTION
--     STATUS          mandatory
--     DESCRIPTION     
--             "Indicates the Domain Name length."
--     SYNTAX          INTEGER (0..2147483647)

SonusSoftSwitchDomainName ::=
    OCTET STRING (SIZE(0..255))

-- SonusSoftSwitchDomainName ::= TEXTUAL-CONVENTION
--     STATUS          mandatory
--     DESCRIPTION     
--             "Indicates the Domain Name value."
--     SYNTAX          OCTET STRING (SIZE(0..255))

END -- end of module SONUS-SOFTSWITCH-TC.
