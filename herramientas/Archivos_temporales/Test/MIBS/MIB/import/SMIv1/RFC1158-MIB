--
-- This SMIv1 module has been generated by smidump 0.2-cvs. Do not edit.
--

RFC1158-MIB DEFINITIONS ::= BEGIN

IMPORTS
    OBJECT-TYPE
        FROM RFC-1212
    Counter, Gauge, IpAddress, NetworkAddress, TimeTicks, mgmt
        FROM RFC1155-SMI;

DisplayString ::=
    OCTET STRING

nullSpecific OBJECT IDENTIFIER
    ::= { 0 0 }

mib-2 OBJECT IDENTIFIER
    ::= { mgmt 1 }

system OBJECT IDENTIFIER
    ::= { mib-2 1 }

sysDescr OBJECT-TYPE
    SYNTAX          DisplayString (SIZE(0..255))
    ACCESS          read-only
    STATUS          mandatory
    DESCRIPTION     
            "..."
    ::= { system 1 }

sysObjectID OBJECT-TYPE
    SYNTAX          OBJECT IDENTIFIER
    ACCESS          read-only
    STATUS          mandatory
    DESCRIPTION     
            "..."
    ::= { system 2 }

sysUpTime OBJECT-TYPE
    SYNTAX          TimeTicks
    ACCESS          read-only
    STATUS          mandatory
    DESCRIPTION     
            "..."
    ::= { system 3 }

sysContact OBJECT-TYPE
    SYNTAX          DisplayString (SIZE(0..255))
    ACCESS          read-write
    STATUS          mandatory
    DESCRIPTION     
            "..."
    ::= { system 4 }

sysName OBJECT-TYPE
    SYNTAX          DisplayString (SIZE(0..255))
    ACCESS          read-write
    STATUS          mandatory
    DESCRIPTION     
            "..."
    ::= { system 5 }

sysLocation OBJECT-TYPE
    SYNTAX          DisplayString (SIZE(0..255))
    ACCESS          read-only
    STATUS          mandatory
    DESCRIPTION     
            "..."
    ::= { system 6 }

sysServices OBJECT-TYPE
    SYNTAX          INTEGER (0..127)
    ACCESS          read-only
    STATUS          mandatory
    DESCRIPTION     
            "..."
    ::= { system 7 }

interfaces OBJECT IDENTIFIER
    ::= { mib-2 2 }

ifNumber OBJECT-TYPE
    SYNTAX          INTEGER
    ACCESS          read-only
    STATUS          mandatory
    DESCRIPTION     
            "..."
    ::= { interfaces 1 }

ifTable OBJECT-TYPE
    SYNTAX          SEQUENCE OF IfEntry
    ACCESS          read-only
    STATUS          mandatory
    DESCRIPTION     
            "..."
    ::= { interfaces 2 }

ifEntry OBJECT-TYPE
    SYNTAX          IfEntry
    ACCESS          read-only
    STATUS          mandatory
    DESCRIPTION     
            "..."
    ::= { ifTable 1 }

IfEntry ::=
    SEQUENCE {
        ifIndex                         INTEGER,
        ifDescr                         DisplayString,
        ifType                          INTEGER,
        ifMtu                           INTEGER,
        ifSpeed                         Gauge,
        ifPhysAddress                   OCTET STRING,
        ifAdminStatus                   INTEGER,
        ifOperStatus                    INTEGER,
        ifLastChange                    TimeTicks,
        ifInOctets                      Counter,
        ifInUcastPkts                   Counter,
        ifInNUcastPkts                  Counter,
        ifInDiscards                    Counter,
        ifInErrors                      Counter,
        ifInUnknownProtos               Counter,
        ifOutOctets                     Counter,
        ifOutUcastPkts                  Counter,
        ifOutNUcastPkts                 Counter,
        ifOutDiscards                   Counter,
        ifOutErrors                     Counter,
        ifOutQLen                       Gauge,
        ifSpecific                      OBJECT IDENTIFIER
    }

ifIndex OBJECT-TYPE
    SYNTAX          INTEGER
    ACCESS          read-only
    STATUS          mandatory
    DESCRIPTION     
            "..."
    ::= { ifEntry 1 }

ifDescr OBJECT-TYPE
    SYNTAX          DisplayString (SIZE(0..255))
    ACCESS          read-only
    STATUS          mandatory
    DESCRIPTION     
            "..."
    ::= { ifEntry 2 }

ifType OBJECT-TYPE
    SYNTAX          INTEGER { other(1), regular1822(2), hdh1822(3), 
                        ddn-x25(4), rfc877-x25(5), ethernet-csmacd(6), 
                        iso88023-csmacd(7), iso88024-tokenBus(8), 
                        iso88025-tokenRing(9), iso88026-man(10), 
                        starLan(11), proteon-10Mbit(12), 
                        proteon-80Mbit(13), hyperchannel(14), fddi(15), 
                        lapb(16), sdlc(17), t1-carrier(18), cept(19), 
                        basicISDN(20), primaryISDN(21), 
                        propPointToPointSerial(22), 
                        terminalServer-asyncPort(23), 
                        softwareLoopback(24), eon(25), 
                        ethernet-3Mbit(26), nsip(27), slip(28) }
    ACCESS          read-only
    STATUS          mandatory
    DESCRIPTION     
            "..."
    ::= { ifEntry 3 }

ifMtu OBJECT-TYPE
    SYNTAX          INTEGER
    ACCESS          read-only
    STATUS          mandatory
    DESCRIPTION     
            "..."
    ::= { ifEntry 4 }

ifSpeed OBJECT-TYPE
    SYNTAX          Gauge
    ACCESS          read-only
    STATUS          mandatory
    DESCRIPTION     
            "..."
    ::= { ifEntry 5 }

ifPhysAddress OBJECT-TYPE
    SYNTAX          OCTET STRING
    ACCESS          read-only
    STATUS          mandatory
    DESCRIPTION     
            "..."
    ::= { ifEntry 6 }

ifAdminStatus OBJECT-TYPE
    SYNTAX          INTEGER { up(1), down(2), testing(3) }
    ACCESS          read-write
    STATUS          mandatory
    DESCRIPTION     
            "..."
    ::= { ifEntry 7 }

ifOperStatus OBJECT-TYPE
    SYNTAX          INTEGER { up(1), down(2), testing(3) }
    ACCESS          read-only
    STATUS          mandatory
    DESCRIPTION     
            "..."
    ::= { ifEntry 8 }

ifLastChange OBJECT-TYPE
    SYNTAX          TimeTicks
    ACCESS          read-only
    STATUS          mandatory
    DESCRIPTION     
            "..."
    ::= { ifEntry 9 }

ifInOctets OBJECT-TYPE
    SYNTAX          Counter
    ACCESS          read-only
    STATUS          mandatory
    DESCRIPTION     
            "..."
    ::= { ifEntry 10 }

ifInUcastPkts OBJECT-TYPE
    SYNTAX          Counter
    ACCESS          read-only
    STATUS          mandatory
    DESCRIPTION     
            "..."
    ::= { ifEntry 11 }

ifInNUcastPkts OBJECT-TYPE
    SYNTAX          Counter
    ACCESS          read-only
    STATUS          mandatory
    DESCRIPTION     
            "..."
    ::= { ifEntry 12 }

ifInDiscards OBJECT-TYPE
    SYNTAX          Counter
    ACCESS          read-only
    STATUS          mandatory
    DESCRIPTION     
            "..."
    ::= { ifEntry 13 }

ifInErrors OBJECT-TYPE
    SYNTAX          Counter
    ACCESS          read-only
    STATUS          mandatory
    DESCRIPTION     
            "..."
    ::= { ifEntry 14 }

ifInUnknownProtos OBJECT-TYPE
    SYNTAX          Counter
    ACCESS          read-only
    STATUS          mandatory
    DESCRIPTION     
            "..."
    ::= { ifEntry 15 }

ifOutOctets OBJECT-TYPE
    SYNTAX          Counter
    ACCESS          read-only
    STATUS          mandatory
    DESCRIPTION     
            "..."
    ::= { ifEntry 16 }

ifOutUcastPkts OBJECT-TYPE
    SYNTAX          Counter
    ACCESS          read-only
    STATUS          mandatory
    DESCRIPTION     
            "..."
    ::= { ifEntry 17 }

ifOutNUcastPkts OBJECT-TYPE
    SYNTAX          Counter
    ACCESS          read-only
    STATUS          mandatory
    DESCRIPTION     
            "..."
    ::= { ifEntry 18 }

ifOutDiscards OBJECT-TYPE
    SYNTAX          Counter
    ACCESS          read-only
    STATUS          mandatory
    DESCRIPTION     
            "..."
    ::= { ifEntry 19 }

ifOutErrors OBJECT-TYPE
    SYNTAX          Counter
    ACCESS          read-only
    STATUS          mandatory
    DESCRIPTION     
            "..."
    ::= { ifEntry 20 }

ifOutQLen OBJECT-TYPE
    SYNTAX          Gauge
    ACCESS          read-only
    STATUS          mandatory
    DESCRIPTION     
            "..."
    ::= { ifEntry 21 }

ifSpecific OBJECT-TYPE
    SYNTAX          OBJECT IDENTIFIER
    ACCESS          read-only
    STATUS          mandatory
    DESCRIPTION     
            "..."
    ::= { ifEntry 22 }

at OBJECT IDENTIFIER
    ::= { mib-2 3 }

atTable OBJECT-TYPE
    SYNTAX          SEQUENCE OF AtEntry
    ACCESS          read-write
    STATUS          obsolete
    DESCRIPTION     
            "..."
    ::= { at 1 }

atEntry OBJECT-TYPE
    SYNTAX          AtEntry
    ACCESS          read-write
    STATUS          obsolete
    DESCRIPTION     
            "..."
    ::= { atTable 1 }

AtEntry ::=
    SEQUENCE {
        atIfIndex                       INTEGER,
        atPhysAddress                   OCTET STRING,
        atNetAddress                    NetworkAddress
    }

atIfIndex OBJECT-TYPE
    SYNTAX          INTEGER
    ACCESS          read-write
    STATUS          obsolete
    DESCRIPTION     
            "..."
    ::= { atEntry 1 }

atPhysAddress OBJECT-TYPE
    SYNTAX          OCTET STRING
    ACCESS          read-write
    STATUS          obsolete
    DESCRIPTION     
            "..."
    ::= { atEntry 2 }

atNetAddress OBJECT-TYPE
    SYNTAX          NetworkAddress
    ACCESS          read-write
    STATUS          obsolete
    DESCRIPTION     
            "..."
    ::= { atEntry 3 }

ip OBJECT IDENTIFIER
    ::= { mib-2 4 }

ipForwarding OBJECT-TYPE
    SYNTAX          INTEGER { gateway(1), host(2) }
    ACCESS          read-write
    STATUS          mandatory
    DESCRIPTION     
            "..."
    ::= { ip 1 }

ipDefaultTTL OBJECT-TYPE
    SYNTAX          INTEGER
    ACCESS          read-write
    STATUS          mandatory
    DESCRIPTION     
            "..."
    ::= { ip 2 }

ipInReceives OBJECT-TYPE
    SYNTAX          Counter
    ACCESS          read-only
    STATUS          mandatory
    DESCRIPTION     
            "..."
    ::= { ip 3 }

ipInHdrErrors OBJECT-TYPE
    SYNTAX          Counter
    ACCESS          read-only
    STATUS          mandatory
    DESCRIPTION     
            "..."
    ::= { ip 4 }

ipInAddrErrors OBJECT-TYPE
    SYNTAX          Counter
    ACCESS          read-only
    STATUS          mandatory
    DESCRIPTION     
            "..."
    ::= { ip 5 }

ipForwDatagrams OBJECT-TYPE
    SYNTAX          Counter
    ACCESS          read-only
    STATUS          mandatory
    DESCRIPTION     
            "..."
    ::= { ip 6 }

ipInUnknownProtos OBJECT-TYPE
    SYNTAX          Counter
    ACCESS          read-only
    STATUS          mandatory
    DESCRIPTION     
            "..."
    ::= { ip 7 }

ipInDiscards OBJECT-TYPE
    SYNTAX          Counter
    ACCESS          read-only
    STATUS          mandatory
    DESCRIPTION     
            "..."
    ::= { ip 8 }

ipInDelivers OBJECT-TYPE
    SYNTAX          Counter
    ACCESS          read-only
    STATUS          mandatory
    DESCRIPTION     
            "..."
    ::= { ip 9 }

ipOutRequests OBJECT-TYPE
    SYNTAX          Counter
    ACCESS          read-only
    STATUS          mandatory
    DESCRIPTION     
            "..."
    ::= { ip 10 }

ipOutDiscards OBJECT-TYPE
    SYNTAX          Counter
    ACCESS          read-only
    STATUS          mandatory
    DESCRIPTION     
            "..."
    ::= { ip 11 }

ipOutNoRoutes OBJECT-TYPE
    SYNTAX          Counter
    ACCESS          read-only
    STATUS          mandatory
    DESCRIPTION     
            "..."
    ::= { ip 12 }

ipReasmTimeout OBJECT-TYPE
    SYNTAX          INTEGER
    ACCESS          read-only
    STATUS          mandatory
    DESCRIPTION     
            "..."
    ::= { ip 13 }

ipReasmReqds OBJECT-TYPE
    SYNTAX          Counter
    ACCESS          read-only
    STATUS          mandatory
    DESCRIPTION     
            "..."
    ::= { ip 14 }

ipReasmOKs OBJECT-TYPE
    SYNTAX          Counter
    ACCESS          read-only
    STATUS          mandatory
    DESCRIPTION     
            "..."
    ::= { ip 15 }

ipReasmFails OBJECT-TYPE
    SYNTAX          Counter
    ACCESS          read-only
    STATUS          mandatory
    DESCRIPTION     
            "..."
    ::= { ip 16 }

ipFragOKs OBJECT-TYPE
    SYNTAX          Counter
    ACCESS          read-only
    STATUS          mandatory
    DESCRIPTION     
            "..."
    ::= { ip 17 }

ipFragFails OBJECT-TYPE
    SYNTAX          Counter
    ACCESS          read-only
    STATUS          mandatory
    DESCRIPTION     
            "..."
    ::= { ip 18 }

ipFragCreates OBJECT-TYPE
    SYNTAX          Counter
    ACCESS          read-only
    STATUS          mandatory
    DESCRIPTION     
            "..."
    ::= { ip 19 }

ipAddrTable OBJECT-TYPE
    SYNTAX          SEQUENCE OF IpAddrEntry
    ACCESS          read-only
    STATUS          mandatory
    DESCRIPTION     
            "..."
    ::= { ip 20 }

ipAddrEntry OBJECT-TYPE
    SYNTAX          IpAddrEntry
    ACCESS          read-only
    STATUS          mandatory
    DESCRIPTION     
            "..."
    ::= { ipAddrTable 1 }

IpAddrEntry ::=
    SEQUENCE {
        ipAdEntAddr                     IpAddress,
        ipAdEntIfIndex                  INTEGER,
        ipAdEntNetMask                  IpAddress,
        ipAdEntBcastAddr                INTEGER,
        ipAdEntReasmMaxSize             INTEGER
    }

ipAdEntAddr OBJECT-TYPE
    SYNTAX          IpAddress
    ACCESS          read-only
    STATUS          mandatory
    DESCRIPTION     
            "..."
    ::= { ipAddrEntry 1 }

ipAdEntIfIndex OBJECT-TYPE
    SYNTAX          INTEGER
    ACCESS          read-only
    STATUS          mandatory
    DESCRIPTION     
            "..."
    ::= { ipAddrEntry 2 }

ipAdEntNetMask OBJECT-TYPE
    SYNTAX          IpAddress
    ACCESS          read-only
    STATUS          mandatory
    DESCRIPTION     
            "..."
    ::= { ipAddrEntry 3 }

ipAdEntBcastAddr OBJECT-TYPE
    SYNTAX          INTEGER
    ACCESS          read-only
    STATUS          mandatory
    DESCRIPTION     
            "..."
    ::= { ipAddrEntry 4 }

ipAdEntReasmMaxSize OBJECT-TYPE
    SYNTAX          INTEGER (0..65535)
    ACCESS          read-only
    STATUS          mandatory
    DESCRIPTION     
            "..."
    ::= { ipAddrEntry 5 }

ipRoutingTable OBJECT-TYPE
    SYNTAX          SEQUENCE OF IpRouteEntry
    ACCESS          read-write
    STATUS          mandatory
    DESCRIPTION     
            "..."
    ::= { ip 21 }

ipRouteEntry OBJECT-TYPE
    SYNTAX          IpRouteEntry
    ACCESS          read-write
    STATUS          mandatory
    DESCRIPTION     
            "..."
    ::= { ipRoutingTable 1 }

IpRouteEntry ::=
    SEQUENCE {
        ipRouteDest                     IpAddress,
        ipRouteIfIndex                  INTEGER,
        ipRouteMetric1                  INTEGER,
        ipRouteMetric2                  INTEGER,
        ipRouteMetric3                  INTEGER,
        ipRouteMetric4                  INTEGER,
        ipRouteNextHop                  IpAddress,
        ipRouteType                     INTEGER,
        ipRouteProto                    INTEGER,
        ipRouteAge                      INTEGER,
        ipRouteMask                     IpAddress
    }

ipRouteDest OBJECT-TYPE
    SYNTAX          IpAddress
    ACCESS          read-write
    STATUS          mandatory
    DESCRIPTION     
            "..."
    ::= { ipRouteEntry 1 }

ipRouteIfIndex OBJECT-TYPE
    SYNTAX          INTEGER
    ACCESS          read-write
    STATUS          mandatory
    DESCRIPTION     
            "..."
    ::= { ipRouteEntry 2 }

ipRouteMetric1 OBJECT-TYPE
    SYNTAX          INTEGER
    ACCESS          read-write
    STATUS          mandatory
    DESCRIPTION     
            "..."
    ::= { ipRouteEntry 3 }

ipRouteMetric2 OBJECT-TYPE
    SYNTAX          INTEGER
    ACCESS          read-write
    STATUS          mandatory
    DESCRIPTION     
            "..."
    ::= { ipRouteEntry 4 }

ipRouteMetric3 OBJECT-TYPE
    SYNTAX          INTEGER
    ACCESS          read-write
    STATUS          mandatory
    DESCRIPTION     
            "..."
    ::= { ipRouteEntry 5 }

ipRouteMetric4 OBJECT-TYPE
    SYNTAX          INTEGER
    ACCESS          read-write
    STATUS          mandatory
    DESCRIPTION     
            "..."
    ::= { ipRouteEntry 6 }

ipRouteNextHop OBJECT-TYPE
    SYNTAX          IpAddress
    ACCESS          read-write
    STATUS          mandatory
    DESCRIPTION     
            "..."
    ::= { ipRouteEntry 7 }

ipRouteType OBJECT-TYPE
    SYNTAX          INTEGER { other(1), invalid(2), direct(3), remote(4) }
    ACCESS          read-write
    STATUS          mandatory
    DESCRIPTION     
            "..."
    ::= { ipRouteEntry 8 }

ipRouteProto OBJECT-TYPE
    SYNTAX          INTEGER { other(1), local(2), netmgmt(3), icmp(4), 
                        egp(5), ggp(6), hello(7), rip(8), is-is(9), 
                        es-is(10), ciscoIgrp(11), bbnSpfIgp(12), 
                        ospf(13), bgp(14) }
    ACCESS          read-only
    STATUS          mandatory
    DESCRIPTION     
            "..."
    ::= { ipRouteEntry 9 }

ipRouteAge OBJECT-TYPE
    SYNTAX          INTEGER
    ACCESS          read-write
    STATUS          mandatory
    DESCRIPTION     
            "..."
    ::= { ipRouteEntry 10 }

ipRouteMask OBJECT-TYPE
    SYNTAX          IpAddress
    ACCESS          read-write
    STATUS          mandatory
    DESCRIPTION     
            "..."
    ::= { ipRouteEntry 11 }

ipNetToMediaTable OBJECT-TYPE
    SYNTAX          SEQUENCE OF IpNetToMediaEntry
    ACCESS          read-write
    STATUS          mandatory
    DESCRIPTION     
            "..."
    ::= { ip 22 }

ipNetToMediaEntry OBJECT-TYPE
    SYNTAX          IpNetToMediaEntry
    ACCESS          read-write
    STATUS          mandatory
    DESCRIPTION     
            "..."
    ::= { ipNetToMediaTable 1 }

IpNetToMediaEntry ::=
    SEQUENCE {
        ipNetToMediaIfIndex             INTEGER,
        ipNetToMediaPhysAddress         OCTET STRING,
        ipNetToMediaNetAddress          IpAddress,
        ipNetToMediaType                INTEGER
    }

ipNetToMediaIfIndex OBJECT-TYPE
    SYNTAX          INTEGER
    ACCESS          read-write
    STATUS          mandatory
    DESCRIPTION     
            "..."
    ::= { ipNetToMediaEntry 1 }

ipNetToMediaPhysAddress OBJECT-TYPE
    SYNTAX          OCTET STRING
    ACCESS          read-write
    STATUS          mandatory
    DESCRIPTION     
            "..."
    ::= { ipNetToMediaEntry 2 }

ipNetToMediaNetAddress OBJECT-TYPE
    SYNTAX          IpAddress
    ACCESS          read-write
    STATUS          mandatory
    DESCRIPTION     
            "..."
    ::= { ipNetToMediaEntry 3 }

ipNetToMediaType OBJECT-TYPE
    SYNTAX          INTEGER { other(1), invalid(2), dynamic(3), 
                        static(4) }
    ACCESS          read-write
    STATUS          mandatory
    DESCRIPTION     
            "..."
    ::= { ipNetToMediaEntry 4 }

icmp OBJECT IDENTIFIER
    ::= { mib-2 5 }

icmpInMsgs OBJECT-TYPE
    SYNTAX          Counter
    ACCESS          read-only
    STATUS          mandatory
    DESCRIPTION     
            "..."
    ::= { icmp 1 }

icmpInErrors OBJECT-TYPE
    SYNTAX          Counter
    ACCESS          read-only
    STATUS          mandatory
    DESCRIPTION     
            "..."
    ::= { icmp 2 }

icmpInDestUnreachs OBJECT-TYPE
    SYNTAX          Counter
    ACCESS          read-only
    STATUS          mandatory
    DESCRIPTION     
            "..."
    ::= { icmp 3 }

icmpInTimeExcds OBJECT-TYPE
    SYNTAX          Counter
    ACCESS          read-only
    STATUS          mandatory
    DESCRIPTION     
            "..."
    ::= { icmp 4 }

icmpInParmProbs OBJECT-TYPE
    SYNTAX          Counter
    ACCESS          read-only
    STATUS          mandatory
    DESCRIPTION     
            "..."
    ::= { icmp 5 }

icmpInSrcQuenchs OBJECT-TYPE
    SYNTAX          Counter
    ACCESS          read-only
    STATUS          mandatory
    DESCRIPTION     
            "..."
    ::= { icmp 6 }

icmpInRedirects OBJECT-TYPE
    SYNTAX          Counter
    ACCESS          read-only
    STATUS          mandatory
    DESCRIPTION     
            "..."
    ::= { icmp 7 }

icmpInEchos OBJECT-TYPE
    SYNTAX          Counter
    ACCESS          read-only
    STATUS          mandatory
    DESCRIPTION     
            "..."
    ::= { icmp 8 }

icmpInEchoReps OBJECT-TYPE
    SYNTAX          Counter
    ACCESS          read-only
    STATUS          mandatory
    DESCRIPTION     
            "..."
    ::= { icmp 9 }

icmpInTimestamps OBJECT-TYPE
    SYNTAX          Counter
    ACCESS          read-only
    STATUS          mandatory
    DESCRIPTION     
            "..."
    ::= { icmp 10 }

icmpInTimestampReps OBJECT-TYPE
    SYNTAX          Counter
    ACCESS          read-only
    STATUS          mandatory
    DESCRIPTION     
            "..."
    ::= { icmp 11 }

icmpInAddrMasks OBJECT-TYPE
    SYNTAX          Counter
    ACCESS          read-only
    STATUS          mandatory
    DESCRIPTION     
            "..."
    ::= { icmp 12 }

icmpInAddrMaskReps OBJECT-TYPE
    SYNTAX          Counter
    ACCESS          read-only
    STATUS          mandatory
    DESCRIPTION     
            "..."
    ::= { icmp 13 }

icmpOutMsgs OBJECT-TYPE
    SYNTAX          Counter
    ACCESS          read-only
    STATUS          mandatory
    DESCRIPTION     
            "..."
    ::= { icmp 14 }

icmpOutErrors OBJECT-TYPE
    SYNTAX          Counter
    ACCESS          read-only
    STATUS          mandatory
    DESCRIPTION     
            "..."
    ::= { icmp 15 }

icmpOutDestUnreachs OBJECT-TYPE
    SYNTAX          Counter
    ACCESS          read-only
    STATUS          mandatory
    DESCRIPTION     
            "..."
    ::= { icmp 16 }

icmpOutTimeExcds OBJECT-TYPE
    SYNTAX          Counter
    ACCESS          read-only
    STATUS          mandatory
    DESCRIPTION     
            "..."
    ::= { icmp 17 }

icmpOutParmProbs OBJECT-TYPE
    SYNTAX          Counter
    ACCESS          read-only
    STATUS          mandatory
    DESCRIPTION     
            "..."
    ::= { icmp 18 }

icmpOutSrcQuenchs OBJECT-TYPE
    SYNTAX          Counter
    ACCESS          read-only
    STATUS          mandatory
    DESCRIPTION     
            "..."
    ::= { icmp 19 }

icmpOutRedirects OBJECT-TYPE
    SYNTAX          Counter
    ACCESS          read-only
    STATUS          mandatory
    DESCRIPTION     
            "..."
    ::= { icmp 20 }

icmpOutEchos OBJECT-TYPE
    SYNTAX          Counter
    ACCESS          read-only
    STATUS          mandatory
    DESCRIPTION     
            "..."
    ::= { icmp 21 }

icmpOutEchoReps OBJECT-TYPE
    SYNTAX          Counter
    ACCESS          read-only
    STATUS          mandatory
    DESCRIPTION     
            "..."
    ::= { icmp 22 }

icmpOutTimestamps OBJECT-TYPE
    SYNTAX          Counter
    ACCESS          read-only
    STATUS          mandatory
    DESCRIPTION     
            "..."
    ::= { icmp 23 }

icmpOutTimestampReps OBJECT-TYPE
    SYNTAX          Counter
    ACCESS          read-only
    STATUS          mandatory
    DESCRIPTION     
            "..."
    ::= { icmp 24 }

icmpOutAddrMasks OBJECT-TYPE
    SYNTAX          Counter
    ACCESS          read-only
    STATUS          mandatory
    DESCRIPTION     
            "..."
    ::= { icmp 25 }

icmpOutAddrMaskReps OBJECT-TYPE
    SYNTAX          Counter
    ACCESS          read-only
    STATUS          mandatory
    DESCRIPTION     
            "..."
    ::= { icmp 26 }

tcp OBJECT IDENTIFIER
    ::= { mib-2 6 }

tcpRtoAlgorithm OBJECT-TYPE
    SYNTAX          INTEGER { other(1), constant(2), rsre(3), vanj(4) }
    ACCESS          read-only
    STATUS          mandatory
    DESCRIPTION     
            "..."
    ::= { tcp 1 }

tcpRtoMin OBJECT-TYPE
    SYNTAX          INTEGER
    ACCESS          read-only
    STATUS          mandatory
    DESCRIPTION     
            "..."
    ::= { tcp 2 }

tcpRtoMax OBJECT-TYPE
    SYNTAX          INTEGER
    ACCESS          read-only
    STATUS          mandatory
    DESCRIPTION     
            "..."
    ::= { tcp 3 }

tcpMaxConn OBJECT-TYPE
    SYNTAX          INTEGER
    ACCESS          read-only
    STATUS          mandatory
    DESCRIPTION     
            "..."
    ::= { tcp 4 }

tcpActiveOpens OBJECT-TYPE
    SYNTAX          Counter
    ACCESS          read-only
    STATUS          mandatory
    DESCRIPTION     
            "..."
    ::= { tcp 5 }

tcpPassiveOpens OBJECT-TYPE
    SYNTAX          Counter
    ACCESS          read-only
    STATUS          mandatory
    DESCRIPTION     
            "..."
    ::= { tcp 6 }

tcpAttemptFails OBJECT-TYPE
    SYNTAX          Counter
    ACCESS          read-only
    STATUS          mandatory
    DESCRIPTION     
            "..."
    ::= { tcp 7 }

tcpEstabResets OBJECT-TYPE
    SYNTAX          Counter
    ACCESS          read-only
    STATUS          mandatory
    DESCRIPTION     
            "..."
    ::= { tcp 8 }

tcpCurrEstab OBJECT-TYPE
    SYNTAX          Gauge
    ACCESS          read-only
    STATUS          mandatory
    DESCRIPTION     
            "..."
    ::= { tcp 9 }

tcpInSegs OBJECT-TYPE
    SYNTAX          Counter
    ACCESS          read-only
    STATUS          mandatory
    DESCRIPTION     
            "..."
    ::= { tcp 10 }

tcpOutSegs OBJECT-TYPE
    SYNTAX          Counter
    ACCESS          read-only
    STATUS          mandatory
    DESCRIPTION     
            "..."
    ::= { tcp 11 }

tcpRetransSegs OBJECT-TYPE
    SYNTAX          Counter
    ACCESS          read-only
    STATUS          mandatory
    DESCRIPTION     
            "..."
    ::= { tcp 12 }

tcpConnTable OBJECT-TYPE
    SYNTAX          SEQUENCE OF TcpConnEntry
    ACCESS          read-only
    STATUS          mandatory
    DESCRIPTION     
            "..."
    ::= { tcp 13 }

tcpConnEntry OBJECT-TYPE
    SYNTAX          TcpConnEntry
    ACCESS          read-only
    STATUS          mandatory
    DESCRIPTION     
            "..."
    ::= { tcpConnTable 1 }

TcpConnEntry ::=
    SEQUENCE {
        tcpConnState                    INTEGER,
        tcpConnLocalAddress             IpAddress,
        tcpConnLocalPort                INTEGER,
        tcpConnRemAddress               IpAddress,
        tcpConnRemPort                  INTEGER
    }

tcpConnState OBJECT-TYPE
    SYNTAX          INTEGER { closed(1), listen(2), synSent(3), 
                        synReceived(4), established(5), finWait1(6), 
                        finWait2(7), closeWait(8), lastAck(9), 
                        closing(10), timeWait(11) }
    ACCESS          read-only
    STATUS          mandatory
    DESCRIPTION     
            "..."
    ::= { tcpConnEntry 1 }

tcpConnLocalAddress OBJECT-TYPE
    SYNTAX          IpAddress
    ACCESS          read-only
    STATUS          mandatory
    DESCRIPTION     
            "..."
    ::= { tcpConnEntry 2 }

tcpConnLocalPort OBJECT-TYPE
    SYNTAX          INTEGER (0..65535)
    ACCESS          read-only
    STATUS          mandatory
    DESCRIPTION     
            "..."
    ::= { tcpConnEntry 3 }

tcpConnRemAddress OBJECT-TYPE
    SYNTAX          IpAddress
    ACCESS          read-only
    STATUS          mandatory
    DESCRIPTION     
            "..."
    ::= { tcpConnEntry 4 }

tcpConnRemPort OBJECT-TYPE
    SYNTAX          INTEGER (0..65535)
    ACCESS          read-only
    STATUS          mandatory
    DESCRIPTION     
            "..."
    ::= { tcpConnEntry 5 }

tcpInErrs OBJECT-TYPE
    SYNTAX          Counter
    ACCESS          read-only
    STATUS          mandatory
    DESCRIPTION     
            "..."
    ::= { tcp 14 }

tcpOutRsts OBJECT-TYPE
    SYNTAX          Counter
    ACCESS          read-only
    STATUS          mandatory
    DESCRIPTION     
            "..."
    ::= { tcp 15 }

udp OBJECT IDENTIFIER
    ::= { mib-2 7 }

udpInDatagrams OBJECT-TYPE
    SYNTAX          Counter
    ACCESS          read-only
    STATUS          mandatory
    DESCRIPTION     
            "..."
    ::= { udp 1 }

udpNoPorts OBJECT-TYPE
    SYNTAX          Counter
    ACCESS          read-only
    STATUS          mandatory
    DESCRIPTION     
            "..."
    ::= { udp 2 }

udpInErrors OBJECT-TYPE
    SYNTAX          Counter
    ACCESS          read-only
    STATUS          mandatory
    DESCRIPTION     
            "..."
    ::= { udp 3 }

udpOutDatagrams OBJECT-TYPE
    SYNTAX          Counter
    ACCESS          read-only
    STATUS          mandatory
    DESCRIPTION     
            "..."
    ::= { udp 4 }

udpTable OBJECT-TYPE
    SYNTAX          SEQUENCE OF UdpEntry
    ACCESS          read-only
    STATUS          mandatory
    DESCRIPTION     
            "..."
    ::= { udp 5 }

udpEntry OBJECT-TYPE
    SYNTAX          UdpEntry
    ACCESS          read-only
    STATUS          mandatory
    DESCRIPTION     
            "..."
    ::= { udpTable 1 }

UdpEntry ::=
    SEQUENCE {
        udpLocalAddress                 IpAddress,
        udpLocalPort                    INTEGER
    }

udpLocalAddress OBJECT-TYPE
    SYNTAX          IpAddress
    ACCESS          read-only
    STATUS          mandatory
    DESCRIPTION     
            "..."
    ::= { udpEntry 1 }

udpLocalPort OBJECT-TYPE
    SYNTAX          INTEGER (0..65535)
    ACCESS          read-only
    STATUS          mandatory
    DESCRIPTION     
            "..."
    ::= { udpEntry 2 }

egp OBJECT IDENTIFIER
    ::= { mib-2 8 }

egpInMsgs OBJECT-TYPE
    SYNTAX          Counter
    ACCESS          read-only
    STATUS          mandatory
    DESCRIPTION     
            "..."
    ::= { egp 1 }

egpInErrors OBJECT-TYPE
    SYNTAX          Counter
    ACCESS          read-only
    STATUS          mandatory
    DESCRIPTION     
            "..."
    ::= { egp 2 }

egpOutMsgs OBJECT-TYPE
    SYNTAX          Counter
    ACCESS          read-only
    STATUS          mandatory
    DESCRIPTION     
            "..."
    ::= { egp 3 }

egpOutErrors OBJECT-TYPE
    SYNTAX          Counter
    ACCESS          read-only
    STATUS          mandatory
    DESCRIPTION     
            "..."
    ::= { egp 4 }

egpNeighTable OBJECT-TYPE
    SYNTAX          SEQUENCE OF EgpNeighEntry
    ACCESS          read-only
    STATUS          mandatory
    DESCRIPTION     
            "..."
    ::= { egp 5 }

egpNeighEntry OBJECT-TYPE
    SYNTAX          EgpNeighEntry
    ACCESS          read-only
    STATUS          mandatory
    DESCRIPTION     
            "..."
    ::= { egpNeighTable 1 }

EgpNeighEntry ::=
    SEQUENCE {
        egpNeighState                   INTEGER,
        egpNeighAddr                    IpAddress,
        egpNeighAs                      INTEGER,
        egpNeighInMsgs                  Counter,
        egpNeighInErrs                  Counter,
        egpNeighOutMsgs                 Counter,
        egpNeighOutErrs                 Counter,
        egpNeighInErrMsgs               Counter,
        egpNeighOutErrMsgs              Counter,
        egpNeighStateUps                Counter,
        egpNeighStateDowns              Counter,
        egpNeighIntervalHello           INTEGER,
        egpNeighIntervalPoll            INTEGER,
        egpNeighMode                    INTEGER,
        egpNeighEventTrigger            INTEGER
    }

egpNeighState OBJECT-TYPE
    SYNTAX          INTEGER { idle(1), acquisition(2), down(3), up(4), 
                        cease(5) }
    ACCESS          read-only
    STATUS          mandatory
    DESCRIPTION     
            "..."
    ::= { egpNeighEntry 1 }

egpNeighAddr OBJECT-TYPE
    SYNTAX          IpAddress
    ACCESS          read-only
    STATUS          mandatory
    DESCRIPTION     
            "..."
    ::= { egpNeighEntry 2 }

egpNeighAs OBJECT-TYPE
    SYNTAX          INTEGER
    ACCESS          read-only
    STATUS          mandatory
    DESCRIPTION     
            "..."
    ::= { egpNeighEntry 3 }

egpNeighInMsgs OBJECT-TYPE
    SYNTAX          Counter
    ACCESS          read-only
    STATUS          mandatory
    DESCRIPTION     
            "..."
    ::= { egpNeighEntry 4 }

egpNeighInErrs OBJECT-TYPE
    SYNTAX          Counter
    ACCESS          read-only
    STATUS          mandatory
    DESCRIPTION     
            "..."
    ::= { egpNeighEntry 5 }

egpNeighOutMsgs OBJECT-TYPE
    SYNTAX          Counter
    ACCESS          read-only
    STATUS          mandatory
    DESCRIPTION     
            "..."
    ::= { egpNeighEntry 6 }

egpNeighOutErrs OBJECT-TYPE
    SYNTAX          Counter
    ACCESS          read-only
    STATUS          mandatory
    DESCRIPTION     
            "..."
    ::= { egpNeighEntry 7 }

egpNeighInErrMsgs OBJECT-TYPE
    SYNTAX          Counter
    ACCESS          read-only
    STATUS          mandatory
    DESCRIPTION     
            "..."
    ::= { egpNeighEntry 8 }

egpNeighOutErrMsgs OBJECT-TYPE
    SYNTAX          Counter
    ACCESS          read-only
    STATUS          mandatory
    DESCRIPTION     
            "..."
    ::= { egpNeighEntry 9 }

egpNeighStateUps OBJECT-TYPE
    SYNTAX          Counter
    ACCESS          read-only
    STATUS          mandatory
    DESCRIPTION     
            "..."
    ::= { egpNeighEntry 10 }

egpNeighStateDowns OBJECT-TYPE
    SYNTAX          Counter
    ACCESS          read-only
    STATUS          mandatory
    DESCRIPTION     
            "..."
    ::= { egpNeighEntry 11 }

egpNeighIntervalHello OBJECT-TYPE
    SYNTAX          INTEGER
    ACCESS          read-only
    STATUS          mandatory
    DESCRIPTION     
            "..."
    ::= { egpNeighEntry 12 }

egpNeighIntervalPoll OBJECT-TYPE
    SYNTAX          INTEGER
    ACCESS          read-only
    STATUS          mandatory
    DESCRIPTION     
            "..."
    ::= { egpNeighEntry 13 }

egpNeighMode OBJECT-TYPE
    SYNTAX          INTEGER { active(1), passive(2) }
    ACCESS          read-only
    STATUS          mandatory
    DESCRIPTION     
            "..."
    ::= { egpNeighEntry 14 }

egpNeighEventTrigger OBJECT-TYPE
    SYNTAX          INTEGER { start(1), stop(2) }
    ACCESS          read-write
    STATUS          mandatory
    DESCRIPTION     
            "..."
    ::= { egpNeighEntry 15 }

egpAs OBJECT-TYPE
    SYNTAX          INTEGER
    ACCESS          read-only
    STATUS          mandatory
    DESCRIPTION     
            "..."
    ::= { egp 6 }

transmission OBJECT IDENTIFIER
    ::= { mib-2 10 }

snmp OBJECT IDENTIFIER
    ::= { mib-2 11 }

snmpInPkts OBJECT-TYPE
    SYNTAX          Counter
    ACCESS          read-only
    STATUS          mandatory
    DESCRIPTION     
            "..."
    ::= { snmp 1 }

snmpOutPkts OBJECT-TYPE
    SYNTAX          Counter
    ACCESS          read-only
    STATUS          mandatory
    DESCRIPTION     
            "..."
    ::= { snmp 2 }

snmpInBadVersions OBJECT-TYPE
    SYNTAX          Counter
    ACCESS          read-only
    STATUS          mandatory
    DESCRIPTION     
            "..."
    ::= { snmp 3 }

snmpInBadCommunityNames OBJECT-TYPE
    SYNTAX          Counter
    ACCESS          read-only
    STATUS          mandatory
    DESCRIPTION     
            "..."
    ::= { snmp 4 }

snmpInBadCommunityUses OBJECT-TYPE
    SYNTAX          Counter
    ACCESS          read-only
    STATUS          mandatory
    DESCRIPTION     
            "..."
    ::= { snmp 5 }

snmpInASNParseErrs OBJECT-TYPE
    SYNTAX          Counter
    ACCESS          read-only
    STATUS          mandatory
    DESCRIPTION     
            "..."
    ::= { snmp 6 }

snmpInBadTypes OBJECT-TYPE
    SYNTAX          Counter
    ACCESS          read-only
    STATUS          mandatory
    DESCRIPTION     
            "..."
    ::= { snmp 7 }

snmpInTooBigs OBJECT-TYPE
    SYNTAX          Counter
    ACCESS          read-only
    STATUS          mandatory
    DESCRIPTION     
            "..."
    ::= { snmp 8 }

snmpInNoSuchNames OBJECT-TYPE
    SYNTAX          Counter
    ACCESS          read-only
    STATUS          mandatory
    DESCRIPTION     
            "..."
    ::= { snmp 9 }

snmpInBadValues OBJECT-TYPE
    SYNTAX          Counter
    ACCESS          read-only
    STATUS          mandatory
    DESCRIPTION     
            "..."
    ::= { snmp 10 }

snmpInReadOnlys OBJECT-TYPE
    SYNTAX          Counter
    ACCESS          read-only
    STATUS          mandatory
    DESCRIPTION     
            "..."
    ::= { snmp 11 }

snmpInGenErrs OBJECT-TYPE
    SYNTAX          Counter
    ACCESS          read-only
    STATUS          mandatory
    DESCRIPTION     
            "..."
    ::= { snmp 12 }

snmpInTotalReqVars OBJECT-TYPE
    SYNTAX          Counter
    ACCESS          read-only
    STATUS          mandatory
    DESCRIPTION     
            "..."
    ::= { snmp 13 }

snmpInTotalSetVars OBJECT-TYPE
    SYNTAX          Counter
    ACCESS          read-only
    STATUS          mandatory
    DESCRIPTION     
            "..."
    ::= { snmp 14 }

snmpInGetRequests OBJECT-TYPE
    SYNTAX          Counter
    ACCESS          read-only
    STATUS          mandatory
    DESCRIPTION     
            "..."
    ::= { snmp 15 }

snmpInGetNexts OBJECT-TYPE
    SYNTAX          Counter
    ACCESS          read-only
    STATUS          mandatory
    DESCRIPTION     
            "..."
    ::= { snmp 16 }

snmpInSetRequests OBJECT-TYPE
    SYNTAX          Counter
    ACCESS          read-only
    STATUS          mandatory
    DESCRIPTION     
            "..."
    ::= { snmp 17 }

snmpInGetResponses OBJECT-TYPE
    SYNTAX          Counter
    ACCESS          read-only
    STATUS          mandatory
    DESCRIPTION     
            "..."
    ::= { snmp 18 }

snmpInTraps OBJECT-TYPE
    SYNTAX          Counter
    ACCESS          read-only
    STATUS          mandatory
    DESCRIPTION     
            "..."
    ::= { snmp 19 }

snmpOutTooBigs OBJECT-TYPE
    SYNTAX          Counter
    ACCESS          read-only
    STATUS          mandatory
    DESCRIPTION     
            "..."
    ::= { snmp 20 }

snmpOutNoSuchNames OBJECT-TYPE
    SYNTAX          Counter
    ACCESS          read-only
    STATUS          mandatory
    DESCRIPTION     
            "..."
    ::= { snmp 21 }

snmpOutBadValues OBJECT-TYPE
    SYNTAX          Counter
    ACCESS          read-only
    STATUS          mandatory
    DESCRIPTION     
            "..."
    ::= { snmp 22 }

snmpOutReadOnlys OBJECT-TYPE
    SYNTAX          Counter
    ACCESS          read-only
    STATUS          mandatory
    DESCRIPTION     
            "..."
    ::= { snmp 23 }

snmpOutGenErrs OBJECT-TYPE
    SYNTAX          Counter
    ACCESS          read-only
    STATUS          mandatory
    DESCRIPTION     
            "..."
    ::= { snmp 24 }

snmpOutGetRequests OBJECT-TYPE
    SYNTAX          Counter
    ACCESS          read-only
    STATUS          mandatory
    DESCRIPTION     
            "..."
    ::= { snmp 25 }

snmpOutGetNexts OBJECT-TYPE
    SYNTAX          Counter
    ACCESS          read-only
    STATUS          mandatory
    DESCRIPTION     
            "..."
    ::= { snmp 26 }

snmpOutSetRequests OBJECT-TYPE
    SYNTAX          Counter
    ACCESS          read-only
    STATUS          mandatory
    DESCRIPTION     
            "..."
    ::= { snmp 27 }

snmpOutGetResponses OBJECT-TYPE
    SYNTAX          Counter
    ACCESS          read-only
    STATUS          mandatory
    DESCRIPTION     
            "..."
    ::= { snmp 28 }

snmpOutTraps OBJECT-TYPE
    SYNTAX          Counter
    ACCESS          read-only
    STATUS          mandatory
    DESCRIPTION     
            "..."
    ::= { snmp 29 }

snmpEnableAuthTraps OBJECT-TYPE
    SYNTAX          INTEGER { enabled(1), disabled(2) }
    ACCESS          read-write
    STATUS          mandatory
    DESCRIPTION     
            "..."
    ::= { snmp 30 }

END -- end of module RFC1158-MIB.
