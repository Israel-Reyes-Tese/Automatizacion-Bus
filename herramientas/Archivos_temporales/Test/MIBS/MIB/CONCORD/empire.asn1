--  COPYRIGHT 2013 CA, Inc. ALL RIGHTS RESERVED.
--  THIS DOCUMENT CONTAINS CONFIDENTIAL AND TRADE SECRET INFORMATION OF 
--  THE CA, Inc.  COPYRIGHT NOTICE IS PRECAUTIONARY 
--  ONLY AND DOES NOT IMPLY PUBLICATION.

--  No part of this document may be reproduced, transmitted, transcribed,
--  stored in a retrieval system, or translated into any language or
--  computer language, in any form or by any means, without
--  prior written consent of CA, Inc.

--  This MIB is implemented by the SystemEDGE agent.
--  It has been implemented on several platforms:
--    OS                        Version               Architecture
--    Windows                   >= XP,2003            x86,x64,ia64
--    Solaris                   >= 9                  SPARC,x86,x64
--    HP-UX                     >= 11.23              PARISC,ia64
--    AIX                       >= 5.3                POWER 
--    RedHat Linux              >= 5                  x86,ia64,s390-x,PowerPC
--    SLES Linux                >= 10                 x86,ia64,s390-x,PowerPC
--    Debian Linux              >= 5                  x86,ia64,PowerPC

-- SystemEDGE/MIB Version 5.8

EMPIRE DEFINITIONS ::= BEGIN

    IMPORTS
        OBJECT-TYPE
            FROM RFC-1212
        DisplayString
            FROM RFC1213-MIB
        enterprises, TimeTicks, Counter, Gauge
            FROM RFC1155-SMI
--      Counter64                  Note: The MIB implementation uses Counter64 although MIB definition is (still) SMIv1.
--          FROM SNMPv2-SMI
        TRAP-TYPE
            FROM RFC-1215
	SnmpAdminString
            FROM SNMP-FRAMEWORK-MIB;

    empire OBJECT IDENTIFIER ::= { enterprises 546 }

------------------------------------------------------------
--  Top Level Groups
------------------------------------------------------------
    unix           OBJECT IDENTIFIER ::= { empire 1 }
--  dos            OBJECT IDENTIFIER ::= { empire 2 }  deprecated
--  os2            OBJECT IDENTIFIER ::= { empire 3 }  deprecated
--  windows        OBJECT IDENTIFIER ::= { empire 4 }  deprecated
    nt             OBJECT IDENTIFIER ::= { empire 5 }
    monitor        OBJECT IDENTIFIER ::= { empire 6 }
--  empireexp      OBJECT IDENTIFIER ::= { empire 7 }  deprecated
    distribsys     OBJECT IDENTIFIER ::= { empire 8 }
    traps          OBJECT IDENTIFIER ::= { empire 9 }
    empireHistory  OBJECT IDENTIFIER ::= { empire 10 }
    logMonitor     OBJECT IDENTIFIER ::= { empire 11 }
    diskGroup      OBJECT IDENTIFIER ::= { empire 12 }
    cpuGroup       OBJECT IDENTIFIER ::= { empire 13 }
    extensionGroup OBJECT IDENTIFIER ::= { empire 14 }
    processMonitor OBJECT IDENTIFIER ::= { empire 15 }
    applications   OBJECT IDENTIFIER ::= { empire 16 }
    objectState    OBJECT IDENTIFIER ::= { empire 17 }
    autoWatch      OBJECT IDENTIFIER ::= { empire 18 }


------------------------------------------------------------
--  Trap Definitions
------------------------------------------------------------
    monitorEvent                  OBJECT IDENTIFIER ::= { traps 1 }
--  kernelErrorEvent              OBJECT IDENTIFIER ::= { traps 2 }  deprecated
    monitorEntryNotReadyEvent     OBJECT IDENTIFIER ::= { traps 3 }
    logMonMatchEvent              OBJECT IDENTIFIER ::= { traps 4 }
    logMonNotReadyEvent           OBJECT IDENTIFIER ::= { traps 5 }
--  sendTrapEvent                 OBJECT IDENTIFIER ::= { traps 6 }  deprecated
    ntEventMonMatchEvent          OBJECT IDENTIFIER ::= { traps 7 }
    ntEventMonNotReadyEvent       OBJECT IDENTIFIER ::= { traps 8 }
    monitorClearEvent             OBJECT IDENTIFIER ::= { traps 9 }
    processStopEvent              OBJECT IDENTIFIER ::= { traps 10 }
    processStartEvent             OBJECT IDENTIFIER ::= { traps 11 }
    processThresholdEvent         OBJECT IDENTIFIER ::= { traps 12 }
    processClearEvent             OBJECT IDENTIFIER ::= { traps 13 }
    processNotReadyEvent          OBJECT IDENTIFIER ::= { traps 14 }
--  logMonReinitEvent             OBJECT IDENTIFIER ::= { traps 15 }  deprecated
--  licenseEvent                  OBJECT IDENTIFIER ::= { traps 16 }  deprecated
    fwLogmonEvent                 OBJECT IDENTIFIER ::= { traps 17 }
    addrChangeEvent               OBJECT IDENTIFIER ::= { traps 18 }
    procGroupChangeEvent          OBJECT IDENTIFIER ::= { traps 19 }
    aggregateStateEvent           OBJECT IDENTIFIER ::= { traps 20 }
    aggregateAddEvent             OBJECT IDENTIFIER ::= { traps 21 }
    aggregateDeleteEvent          OBJECT IDENTIFIER ::= { traps 22 }
    autowatchInstanceAddedEvent   OBJECT IDENTIFIER ::= { traps 23 }
    autowatchInstanceRemovedEvent OBJECT IDENTIFIER ::= { traps 24 }
    autowatchInstanceLostEvent    OBJECT IDENTIFIER ::= { traps 25 }
    autowatchNotReadyEvent        OBJECT IDENTIFIER ::= { traps 26 }

------------------------------------------------------------
--  AIM Plugin Groups (defined in their resp. MIBs)
------------------------------------------------------------
--  msExchange   OBJECT IDENTIFIER ::= { applications 1 }
--  msIIS        OBJECT IDENTIFIER ::= { applications 2 }
--  apacheSrv    OBJECT IDENTIFIER ::= { applications 3 }
--  oracledb     OBJECT IDENTIFIER ::= { applications 4 }
--  sybase       OBJECT IDENTIFIER ::= { applications 5 }
--  svcRsp       OBJECT IDENTIFIER ::= { applications 6 }
--  topProcs     OBJECT IDENTIFIER ::= { applications 7 }
--  sqlServer    OBJECT IDENTIFIER ::= { applications 8 }
--  netService   OBJECT IDENTIFIER ::= { applications 9 }
--  domino       OBJECT IDENTIFIER ::= { applications 10 }
--  surveyor     OBJECT IDENTIFIER ::= { applications 11 }
--  mosMod       OBJECT IDENTIFIER ::= { applications 12 } 
--  ccmmod       OBJECT IDENTIFIER ::= { applications 13 }
--  siebelmod    OBJECT IDENTIFIER ::= { applications 14 }
--  testplugin   OBJECT IDENTIFIER ::= { applications 16 }
--  firewall     OBJECT IDENTIFIER ::= { applications 17 }
--  dirmwp       OBJECT IDENTIFIER ::= { applications 18 }
--  unitymod     OBJECT IDENTIFIER ::= { applications 19 }
--  monwin       OBJECT IDENTIFIER ::= { applications 20 }
--  perfcube     OBJECT IDENTIFIER ::= { applications 21 }
--  rmonWbem     OBJECT IDENTIFIER ::= { applications 22 }
--  reserved     OBJECT IDENTIFIER ::= { applications 23 }
--  reserved     OBJECT IDENTIFIER ::= { applications 24 }
--  iddmod       OBJECT IDENTIFIER ::= { applications 25 }

--  camscsa      OBJECT IDENTIFIER ::= { applications 51 }
--  cavmvcaim    OBJECT IDENTIFIER ::= { applications 52 }
--  calpara      OBJECT IDENTIFIER ::= { applications 53 }
--  casunza      OBJECT IDENTIFIER ::= { applications 54 }
--  cahacmpa     OBJECT IDENTIFIER ::= { applications 55 }

--  custom       OBJECT IDENTIFIER ::= { applications 100 }

------------------------------------------------------------
--  perfcube AIM MIB (just one attribute) is defined here
------------------------------------------------------------
    perfcube OBJECT IDENTIFIER ::= { applications 21 }

    perfCubeVersion OBJECT-TYPE
        SYNTAX DisplayString
        ACCESS read-only
        STATUS mandatory
        DESCRIPTION
            "Description and version number of this module adhering to the format: 
             VERSION:a.b PATCHLEVEL:c BUILD:yyddd REQUIRES:d.e.f"
    ::= { perfcube 1 }


------------------------------------------------------------
--  The System Management Group
------------------------------------------------------------

    sysmgmt OBJECT IDENTIFIER ::= { unix 1 }


------------------------------------------------------------
--  The Sysedge System Group
------------------------------------------------------------

    sysedgeSystem OBJECT IDENTIFIER ::= { sysmgmt 1 }

    nodename OBJECT-TYPE
        SYNTAX DisplayString
        ACCESS read-only
        STATUS mandatory
        DESCRIPTION
            "The name of the system that the agent is running on as given by the login prompt."
    ::= { sysedgeSystem 1 }

    cpu OBJECT-TYPE
        SYNTAX DisplayString
        ACCESS read-only
        STATUS mandatory
        DESCRIPTION
            "The CPU type of the system that the agent is running on (e.g. sun4c, sun4m)."
    ::= { sysedgeSystem 2 }

    memory OBJECT-TYPE
        SYNTAX INTEGER
        ACCESS read-only
        STATUS mandatory
        DESCRIPTION
            "The amount of memory in 1024 byte units contained in the system."
    ::= { sysedgeSystem 3 }

    hostid OBJECT-TYPE
        SYNTAX DisplayString
        ACCESS read-only
        STATUS mandatory
        DESCRIPTION
            "The hostid number that resides on the mother board of the system that the agent is running on.
            The hostid is unique across all machines manufactured by the same vendor."
    ::= { sysedgeSystem 4 }

    osver OBJECT-TYPE
        SYNTAX DisplayString
        ACCESS read-only
        STATUS mandatory
        DESCRIPTION
            "The operating system version of the system that the agent resides.
            Each time a new kernel is re-linked for a given kernel configuration file, this number is incremented."
    ::= { sysedgeSystem 5 }

    osrel OBJECT-TYPE
        SYNTAX DisplayString
        ACCESS read-only
        STATUS mandatory
        DESCRIPTION
            "The operating system release of the system that the agent resides."
    ::= { sysedgeSystem 6 }

--  devTable OBJECT-TYPE
--      defined below
--  ::= { sysedgeSystem 7 }

    agentVersion OBJECT-TYPE
        SYNTAX DisplayString
        ACCESS read-only
        STATUS mandatory
        DESCRIPTION
            "The agent's description and software version number." 
    ::= { sysedgeSystem 8 }

    kernelConfig OBJECT IDENTIFIER ::= { sysedgeSystem 9 }
    bootconf     OBJECT IDENTIFIER ::= { sysedgeSystem 10 }
    streams      OBJECT IDENTIFIER ::= { sysedgeSystem 11 }

    systemType OBJECT-TYPE
        SYNTAX INTEGER {
            unknown(1),
            solarisSparc(2),   -- SunOS 5.x
            solarisIntel(3),
            solarisPPC(4),
            sunosSparc(5),     -- SunOS 4.x
            hpux9Parisc(6),
            hpux10Parisc(7),
            nt351Intel(8),
            nt351Alpha(9),
            nt40Intel(10),
            nt40Alpha(11),
            irix62Mips(12),
            irix63Mips(13),
            irix64Mips(14),
            aix41RS6000(15),
            aix42RS6000(16),
            aix43RS6000(17),
            irix65Mips(18),
            digitalUNIX(19),   -- Tru64
            linuxIntel(20),
            hpux11Parisc(21),
            nt50Intel(22),     -- Windows 2000
            nt50Alpha(23),
            nt51Intel(24),     -- Windows XP
            aix5RS6000(25),
            nt52Intel(26),     -- Windows 2003
            linuxIA64(27),     -- Linux Itanium
            hpux11IA64(28),
            nt52IA64(29),      -- Windows 2003 Itanium
            nt52X64(30),       -- Windows 2003 x64 (AMD64 or EMT64)
            linuxX64(31),
            aix6RS6000(32),
            nt60Intel(33),     -- Windows 2008/Vista, Windows 2008 R2/Windows 7, Windows 2012/Windows 8 32bit
            nt60IA64(34),      -- Windows 2008 (R2) Itanium
            nt60X64(35),       -- Windows 2008/Vista, Windows 2008 R2/Windows 7, Windows 2012/Windows 8 64bit
            linuxS390X(36),    -- Linux on IBM zSeries 64bit
            linuxPPC(37),      -- Linux on IBM PowerPC
            aix7RS6000(38)     -- AIX7
        }
        ACCESS read-only
        STATUS mandatory
        DESCRIPTION
            "The underlying system (hardware/OS) type"
    ::= { sysedgeSystem 12 }

    sysedgeUptime OBJECT-TYPE
        SYNTAX TimeTicks
        ACCESS read-only
        STATUS mandatory
        DESCRIPTION
            "The SystemEDGE agent's uptime. This is the same value as returned by the sysUpTime value in MIB2.
            sysUpTime is the elapsed time (in hundredths of a second) since the agent was started."
    ::= { sysedgeSystem 13 }

    sysedgeLicenseString OBJECT-TYPE
        SYNTAX DisplayString
        ACCESS read-only
        STATUS mandatory
        DESCRIPTION
            "This object is deprecated."
    ::= { sysedgeSystem 14 }

    sysedgeLicenseKey OBJECT-TYPE
        SYNTAX DisplayString
        ACCESS read-write
        STATUS mandatory
        DESCRIPTION
            "This object is deprecated."
    ::= { sysedgeSystem 16 }

    sysedgeMode OBJECT-TYPE
        SYNTAX INTEGER {
            fullMode(1),
            restrictedMode(2)
        }
        ACCESS read-only
        STATUS mandatory
        DESCRIPTION
            "This object is deprecated."
    ::= { sysedgeSystem 17 }

    systemTimeZone OBJECT-TYPE
        SYNTAX DisplayString
        ACCESS read-only
        STATUS mandatory
        DESCRIPTION
            "The timezone this system is in obtained via TZ environment variable (UNIX) or NT win32 call.
            This value is operating-system depdendent. Each OS often has slightly different names for same timezone."
    ::= { sysedgeSystem 18 }

    sysedgeAddressList OBJECT-TYPE
        SYNTAX DisplayString
        ACCESS read-only
        STATUS mandatory
        DESCRIPTION
            "The space-separated list of up to 5 past IP addresses that this system was configured for.
            This MIB object, when used with the addrChangeTrap, is useful to managers trying to poll
            agent machines whose addresses change due to DHCP (or other configuration changes) over time.
            Addresses are ordered from most-recently used to least-recently used (left to right)."
    ::= { sysedgeSystem 19 }

    sysedgeFQDN OBJECT-TYPE
        SYNTAX DisplayString
        ACCESS read-only
        STATUS mandatory
        DESCRIPTION
            "The system's fully qualified domain name (FQDN).
            This is the same value as returned by the sysName value in MIB2."
    ::= {sysedgeSystem 20 }

    sysedgeConfProfile OBJECT-TYPE
        SYNTAX DisplayString (SIZE (0..1024))
        ACCESS read-write
        STATUS mandatory
        DESCRIPTION
            "A space-separated list of configuration profile names currently configured in SystemEDGE.
            Configuration profiles are managed by AdvantEDGE View, which uses this MIB object to store,
            which profiles are currently deployed to the agent. Writing to this attribute outside of AView
            is strongly discouraged. This attribute should not contain single nor double quotations."
    ::= {sysedgeSystem 21 }

    sysedgeInstallDir OBJECT-TYPE
        SYNTAX DisplayString 
        ACCESS read-only
        STATUS mandatory
        DESCRIPTION
            "The directory where the SystemEDGE distribution is installed (e.g. C:\sysedge or /opt/EMPsysedge)."
    ::= {sysedgeSystem 22 }

    sysedgePluginListLoaded OBJECT-TYPE
        SYNTAX DisplayString 
        ACCESS read-only
        STATUS mandatory
        DESCRIPTION
            "A comma-separated list of plugins that are currently loaded into SystemEDGE." 
    ::= {sysedgeSystem 23 }
        
    sysedgePluginListInstalled OBJECT-TYPE
        SYNTAX DisplayString
        ACCESS read-only
        STATUS mandatory
        DESCRIPTION
            "A comma-separated list of plugins that are installed and available to be loaded into SystemEDGE." 
    ::= { sysedgeSystem 24 }

    sysedgeMaintenanceMode OBJECT-TYPE
        SYNTAX INTEGER {
            off(1),
            on(2)
        }
        ACCESS read-write
        STATUS mandatory
        DESCRIPTION
            "Setting this attribute to on(2) instructs the agent to go into a 'maintenance' mode,
            where it stops the processing of all monitors and stops sending traps to managers."
    ::= { sysedgeSystem 25 }

    sysNameCIM OBJECT-TYPE
        SYNTAX DisplayString (SIZE (0..128))
        ACCESS read-write
        STATUS mandatory
        DESCRIPTION
            "The name of system as referred to by CIM based manager. This value is empty unless set via SNMP.
            The value is preserved over agent re-starts. It can be used to build URLs for manager integrations."
    ::= { sysedgeSystem 26 }


------------------------------------------------------------
--  The Device Table
------------------------------------------------------------

    devTable OBJECT-TYPE
        SYNTAX SEQUENCE OF DevTableEntry
        ACCESS not-accessible
        STATUS mandatory
        DESCRIPTION
            "This table describes all mounted file systems on the system that the agent resides."
    ::= { sysedgeSystem 7 }

    devTableEntry OBJECT-TYPE
        SYNTAX DevTableEntry
        ACCESS not-accessible
        STATUS mandatory
        DESCRIPTION
            "An entry in the device table."
        INDEX { devIndex }
    ::= { devTable 1 }

    DevTableEntry ::= SEQUENCE {
        devIndex         INTEGER,
        devDevice        SnmpAdminString,
        devMntPt         SnmpAdminString,
        devBsize         INTEGER,
        devTblks         INTEGER,
        devFblks         Gauge,
        devTfiles        INTEGER,
        devFfiles        Gauge,
        devMaxNameLen    INTEGER,
        devType          DisplayString,
        devFsid          INTEGER,
        devFstr          SnmpAdminString,
        devUnmount       INTEGER,
        devCapacity      INTEGER,
        devInodeCapacity INTEGER,
		devInodesUsed    Gauge,		
		devAllocatedSpace Gauge,
		devFreeSpace	 Gauge,
		devUsedSpace     Gauge
    }

    devIndex OBJECT-TYPE
        SYNTAX INTEGER (1..2147483647)
        ACCESS read-only
        STATUS mandatory
        DESCRIPTION
            "This object does not describe the mounted device.  Its sole purpose is to indicate the row instance.
            The instance is derived from the index number from the mounted file systems file. "
    ::= { devTableEntry 1 }

    devDevice OBJECT-TYPE
        SYNTAX SnmpAdminString
        ACCESS read-only
        STATUS mandatory
        DESCRIPTION
            "The device name (e.g. /dev/sd0a) corresponding to the mounted file system. For example, the '/' file
            system is commonly mounted from the device '/dev/sd0a'.  For network file systems, the value corresponds
            to the remote host and remote file system name (e.g. emptech:/usr/local)."
    ::= { devTableEntry 2 }

    devMntPt OBJECT-TYPE
        SYNTAX SnmpAdminString
        ACCESS read-only
        STATUS mandatory
        DESCRIPTION
            "The mount point or path name in the local file system where the device is mounted (e.g. /home)."
    ::= { devTableEntry 3 }

    devBsize OBJECT-TYPE
        SYNTAX INTEGER
        ACCESS read-only
        STATUS mandatory
        DESCRIPTION
            "The block size of the mounted device in bytes.  File systems and disk devices generally allocate data in
            fixed size 'blocks' generally referred to as the device's block size.  Common block sizes are 1024 (1K)
            and 2048 (2K) bytes."
    ::= { devTableEntry 4 }

    devTblks OBJECT-TYPE
        SYNTAX INTEGER
        ACCESS read-only
        STATUS mandatory
        DESCRIPTION
            "The total number of blocks contained in the mounted device."
    ::= { devTableEntry 5 }

    devFblks OBJECT-TYPE
        SYNTAX Gauge
        ACCESS read-only
        STATUS mandatory
        DESCRIPTION
            "The total number of free or unallocated blocks in the mounted device."
    ::= { devTableEntry 6 }

    devTfiles OBJECT-TYPE
        SYNTAX INTEGER
        ACCESS read-only
        STATUS mandatory
        DESCRIPTION
            "Each disk device and file system allocates a fixed, maximum number of files that can be written to the
            device. The value of this object indicates the maximum number of files that can be written to this
            device."
    ::= { devTableEntry 7 }

    devFfiles OBJECT-TYPE
        SYNTAX Gauge
        ACCESS read-only
        STATUS mandatory
        DESCRIPTION
            "The number of free or unallocated files that can be created on this device."
    ::= { devTableEntry 8 }

    devMaxNameLen OBJECT-TYPE
        SYNTAX INTEGER
        ACCESS read-only
        STATUS mandatory
        DESCRIPTION
            "The maximum file name length that this mounted device supports. 
            If no fixed limit exists, 0 is returned."
    ::= { devTableEntry 9 }

    devType OBJECT-TYPE
        SYNTAX DisplayString
        ACCESS read-only
        STATUS mandatory
        DESCRIPTION
            "The type of the mounted device. If this underlying device does not support feature, 0 is returned."
    ::= { devTableEntry 10 }

    devFsid OBJECT-TYPE
        SYNTAX INTEGER
        ACCESS read-only
        STATUS mandatory
        DESCRIPTION
            "The (possibly unique) file system ID of the mounted device.  V.4 systems support its uniqueness while
            SunOS does not.  For devices or operating systems not supporting this object, the object instance
            identifier is returned instead."
    ::= { devTableEntry 11 }

    devFstr OBJECT-TYPE
        SYNTAX SnmpAdminString
        ACCESS read-only
        STATUS mandatory
        DESCRIPTION
            "Some devices support a description string. If supported by the underlying device and operating system,
            that device specific description string is returned.  If not supported, the  string 'Not supported' is
            returned.  An example description string may be 'User home directories'."
    ::= { devTableEntry 12 }

    devUnmount OBJECT-TYPE
        SYNTAX INTEGER {
            delete(1),
            valid(2)
        }
        ACCESS read-write
        STATUS mandatory
        DESCRIPTION
            "Writing a delete(1) to this object causes the agent to unmount this device and remove its entry from the
            mounted file system table.  Writing any other value to this object will cause no action to be taken by
            the agent."
    ::= { devTableEntry 13 }

    devCapacity OBJECT-TYPE
        SYNTAX INTEGER (0..100)
        ACCESS read-only
        STATUS mandatory
        DESCRIPTION
            "The percentage of the device's total capacity in use."
    ::= { devTableEntry 14 }

    devInodeCapacity OBJECT-TYPE
        SYNTAX INTEGER (0..100)
        ACCESS read-only
        STATUS mandatory
        DESCRIPTION
            "The percentage of the device's total file capacity (inodes) in use.  File systems often place an upper
            bound on the number of files that can be created on a filesystem.  This value indicates the percentage of
            total possible files that are in use.  Many times, NFS clients cannot determine this value for remotely
            mounted filesystems; in that case, 0 is returned."
    ::= { devTableEntry 15 }

    devInodesUsed OBJECT-TYPE
        SYNTAX Gauge
        ACCESS read-only
        STATUS mandatory
        DESCRIPTION
            "Inodes Used - Number of inodes or files in use for the file system."
    ::= { devTableEntry 16 } 	
	
    devAllocatedSpace OBJECT-TYPE
        SYNTAX Gauge
        ACCESS read-only
        STATUS mandatory
        DESCRIPTION
            "Allocated Space - Total number of MB available in the file system."
    ::= { devTableEntry 17 } 	

    devFreeSpace OBJECT-TYPE
        SYNTAX Gauge
        ACCESS read-only
        STATUS mandatory
        DESCRIPTION
            "Free Space - Number of available MB on the file system. Note that this may not include space reserved for the super user."
    ::= { devTableEntry 18 } 	

    devUsedSpace OBJECT-TYPE
        SYNTAX Gauge
        ACCESS read-only
        STATUS mandatory
        DESCRIPTION
            "Used Space - Number of MB in use on the file system."
    ::= { devTableEntry 19 } 	
	
	
------------------------------------------------------------
--  The Kernel Config Group
------------------------------------------------------------
--  This group gives Kernel configuration and identification information

    maxProcs OBJECT-TYPE
        SYNTAX INTEGER
        ACCESS read-only
        STATUS mandatory
        DESCRIPTION
            "Maximum number of slots in the system process table or simply, the maximum number of processes that may
            run at any one time on the system."
    ::= { kernelConfig 1 }

    serialNumber OBJECT-TYPE
        SYNTAX INTEGER
        ACCESS read-only
        STATUS mandatory
        DESCRIPTION
            "The system's serial number.  This number is different from the system's hostid value; it should be
            unique across all platforms manufactured by the same vendor."
    ::= { kernelConfig 2 }

    romVersion OBJECT-TYPE
        SYNTAX DisplayString
        ACCESS read-only
        STATUS mandatory
        DESCRIPTION
            "The system's ROM version number (e.g 2.6). Different versions of ROM often support different commands
            and options.  Knowing the system's ROM version number is often helpful in debugging operating system
            problems."
    ::= { kernelConfig 3 }

    numCPU OBJECT-TYPE
        SYNTAX Gauge
        ACCESS read-only
        STATUS mandatory
        DESCRIPTION
            "The number of CPUs contained within this host."
    ::= { kernelConfig 4 }

    clockHZ OBJECT-TYPE
        SYNTAX INTEGER
        ACCESS read-only
        STATUS mandatory
        DESCRIPTION
            "The system's clock or 'tick' rate in HZ. This is the rate at operating system is given regularly,
            periodic interrupts in order to handle I/O, schedule processes, etc.  This value should not be confused
            with the CPU clock speed which is generally on the order mega-hertz."
    ::= { kernelConfig 5 }

    kernelVers OBJECT-TYPE
        SYNTAX DisplayString
        ACCESS read-only
        STATUS mandatory
        DESCRIPTION
            "The kernel version; This description string is compiled into the kernel at kernel build time and is
            generally used to convey information about its functionality, patch level, or administrative domain."
    ::= { kernelConfig 6 }

    virtualMem OBJECT-TYPE
        SYNTAX Gauge
        ACCESS read-only
        STATUS mandatory
        DESCRIPTION
            "The amount of virtual memory in 1024 byte units (KBytes)."
    ::= { kernelConfig 7 }

    maxInode OBJECT-TYPE
        SYNTAX Gauge
        ACCESS read-only
        STATUS mandatory
        DESCRIPTION
            "Maximum number of in core file inodes allocated by this host.  An inode is a data structure used by a
            file system to describe a file.  Part of it is cached in memory (in core) while the other is stored on
            disk; the kernel allocates a fixed amount of these structures at kernel boot time for use with file I/O."
    ::= { kernelConfig 8 }

    maxFiles OBJECT-TYPE
        SYNTAX Gauge
        ACCESS read-only
        STATUS mandatory
        DESCRIPTION
            "Maximum number of open files the system can support at any one time.  The kernel pre-allocates, at
            kernel boot time, a table of structures for file I/O.  If the kernel does not place any upper bound (e.g.
            Solaris 2.x), than 0 is returned."
    ::= { kernelConfig 9 }

    maxClist OBJECT-TYPE
        SYNTAX Gauge
        ACCESS read-only
        STATUS mandatory
        DESCRIPTION
            "The maximum number of 'clist' structures allocated by the kernel.  Line disciplines, like terminals,
            manipulate data on 'clists' which are essentially linked-lists of data heading to and from terminal or
            serial devices.  If the underlying operating system does not utilize 'clists', then 0 is returned."
    ::= { kernelConfig 10 }

    maxMemPerProc OBJECT-TYPE
        SYNTAX Gauge
        ACCESS read-only
        STATUS mandatory
        DESCRIPTION
            "Maximum memory per process in KBytes. Operating systems often set an upper limit on the amount of memory
            a process may use.  If the underlying operating system does not set such a limit, than 0 is returned."
    ::= { kernelConfig 11 }

    totalSwap OBJECT-TYPE
        SYNTAX INTEGER
        ACCESS read-only
        STATUS mandatory
        DESCRIPTION
            "Total system swap space in KBytes.  Swap is a region on secondary storage (primarily disks) that is used
            for swapping and paging. Swapping is a memory management policy in which entire processes are written to
            secondary storage when memory is in short supply.  When a process begins, all its pages are in virtual
            memory; only those pages actively being used are brought in from disk or swap."
    ::= { kernelConfig 12 }

    openMaxPerProc OBJECT-TYPE
        SYNTAX INTEGER
        ACCESS read-only
        STATUS mandatory
        DESCRIPTION
            "Maximum number of open files per process. Each process is generally given a limit on the maximum number
            of files it may have open at any one time.  If the operating system does not impose such limits, the
            value 0 is returned."
    ::= { kernelConfig 13 }

    posixJobCtrl OBJECT-TYPE
        SYNTAX INTEGER {
            true(1),
            false(2)
        }
        ACCESS read-only
        STATUS mandatory
        DESCRIPTION
            "Boolean variable indicating if Posix Job Control supported.  POSIX, an IEEE standard, defines a
            portable, open interface to operating systems.  Part of the specification includes the definition of
            support for advanced job control.  This value indicates whether the system supports POSIX-style job
            control."
    ::= { kernelConfig 14 }

    posixVersion OBJECT-TYPE
        SYNTAX INTEGER
        ACCESS read-only
        STATUS mandatory
        DESCRIPTION
            "The POSIX version number supported by host operating system.  As new versions of POSIX are released, it
            may be important to monitor which host supports which version of the POSIX standard."
    ::= { kernelConfig 15 }

    pageSize OBJECT-TYPE
        SYNTAX INTEGER
        ACCESS read-only
        STATUS mandatory
        DESCRIPTION
            "This object returns the number of bytes in a page; a 'page' is the fixed size unit of measurement when
            dealing with both virtual and physical memory.  Page granularity is the granularity of many of the memory
            statistics and objects throughout the Concord MIB.  This page size is an operating system page size and
            may not correspond to the underlying hardware page size."
    ::= { kernelConfig 16 }

    wordSize OBJECT-TYPE
        SYNTAX INTEGER
        ACCESS read-only
        STATUS mandatory
        DESCRIPTION
            "This object returns the kernel word size. For example, if Solaris is booted with a 64 bit kernel, this
            object would return 64.  If Solaris is booted with a 32 bit kernel, this object would return 32. This
            object is available in SystemEDGE 4.1 and higher."
    ::= { kernelConfig 17 }

    zoneType OBJECT-TYPE
        SYNTAX INTEGER {
            globalZone(1),
            sparseZone(2)
        }
        ACCESS read-only
        STATUS mandatory
        DESCRIPTION
            "This object returns enumerated values indicating the type of Solaris zone in which sysedge is
            executing."
    ::= { kernelConfig 18 }

    zoneName OBJECT-TYPE
        SYNTAX DisplayString
        ACCESS read-only
        STATUS mandatory
        DESCRIPTION
            "This object returns the name of the Solaris zone in which sysedge is executing."
    ::= { kernelConfig 19 }

    zoneID OBJECT-TYPE
        SYNTAX INTEGER
        ACCESS read-only
        STATUS mandatory
        DESCRIPTION
            "This object returns the zone ID for the Solaris zone in which sysedge is executing."
    ::= { kernelConfig 20 }


------------------------------------------------------------
--  The Boot Config Group
------------------------------------------------------------
--  This group identifies device and partition information that
--  the root, dump, and swap file systems reside on.

    rootName OBJECT-TYPE
        SYNTAX DisplayString
        ACCESS read-only
        STATUS mandatory
        DESCRIPTION
            "The Device and partition (e.g. sd0a) that the root filesystem is mounted from."
    ::= { bootconf 1 }

    rootFSType OBJECT-TYPE
        SYNTAX DisplayString
        ACCESS read-only
        STATUS mandatory
        DESCRIPTION
            "The root filesystem type (e.g. 4.2)."
    ::= { bootconf 2 }

    rootBlocks OBJECT-TYPE
        SYNTAX INTEGER
        ACCESS read-only
        STATUS mandatory
        DESCRIPTION
            "The total number of blocks contained in the root filesystem.  The value 0 is returned if unknown."
    ::= { bootconf 3 }

    dumpName OBJECT-TYPE
        SYNTAX DisplayString
        ACCESS read-only
        STATUS mandatory
        DESCRIPTION
            "The device and partition (e.g. sd0b) that the dump filesystem is mounted from.  'Dump' is a area of
            secondary storage reserved by the operating system so that it may write diagnostic information in the
            event of a kernel crash."
    ::= { bootconf 4 }

    dumpFSType OBJECT-TYPE
        SYNTAX DisplayString
        ACCESS read-only
        STATUS mandatory
        DESCRIPTION
            "The dump filesystem type (e.g. spec).  Dump is generally not a 'normal' file system like UFS, 4.2, etc."
    ::= { bootconf 5 }

    dumpBlocks OBJECT-TYPE
        SYNTAX INTEGER
        ACCESS read-only
        STATUS mandatory
        DESCRIPTION
            "The total number of blocks contained in the dump filesystem."
    ::= { bootconf 6 } 

    swapName OBJECT-TYPE
        SYNTAX DisplayString
        ACCESS read-only
        STATUS mandatory
        DESCRIPTION
            "The device and partition (e.g. sd0b) that serves as swap space for the running kernel."
    ::= { bootconf 7 }

    swapFSType OBJECT-TYPE
        SYNTAX DisplayString
        ACCESS read-only
        STATUS mandatory
        DESCRIPTION
            "The swap filesystem type (e.g. spec).  Swap space is not generally a typical file system like UFS, 4.2,
            etc."
    ::= { bootconf 8 }

    swapSize OBJECT-TYPE
        SYNTAX INTEGER
        ACCESS read-only
        STATUS mandatory
        DESCRIPTION
            "The total number of blocks contained in the kernel's swap area."
    ::= { bootconf 9 }


------------------------------------------------------------
--  The Streams Group
------------------------------------------------------------
--  This group reports statistics and configuration information for the
--  Streams network/terminal I/O subsystem

    maxmsgSize OBJECT-TYPE
        SYNTAX INTEGER
        ACCESS read-only
        STATUS mandatory
        DESCRIPTION
            "The maximum Streams message size in bytes. Streams often places a limit on the size of an individual
            message.  If the underlying system does not place such a limit, 0 is returned."
    ::= { streams 1 }

    maxNumPush OBJECT-TYPE
        SYNTAX INTEGER
        ACCESS read-only
        STATUS mandatory
        DESCRIPTION
            "Maximum number of Streams modules that may be 'pushed' onto an individual stream at any one time.  If
            the underlying system does not define such a limit, 0 is returned."
    ::= { streams 2 }

    numMuxLinks OBJECT-TYPE
        SYNTAX Gauge
        ACCESS read-only
        STATUS mandatory
        DESCRIPTION
            "Number of Streams multiplexor links."
    ::= { streams 3 }

    streamUse OBJECT-TYPE
        SYNTAX Gauge
        ACCESS read-only
        STATUS mandatory
        DESCRIPTION
            "Current number of open 'streams' in the system.  Operating systems often place a limit on the number of
             streams that may be in use at any one time.  Monitoring this variable and streamMax can indicate if
             additional streams should be configured."
    ::= { streams 4 }

    streamMaxs OBJECT-TYPE
        SYNTAX INTEGER
        ACCESS read-only
        STATUS mandatory
        DESCRIPTION
            "The largest number of open 'streams' recorded by the system.  This value represents a 'high-water'
             mark."
    ::= { streams 5 }

    streamFails OBJECT-TYPE
        SYNTAX Counter
        ACCESS read-only
        STATUS mandatory
        DESCRIPTION
            "The number of 'stream' allocation failures that have occurred.  Monitoring the streamUse, streamMax, and
             streamFail variables can help determine if the Streams subsystem is properly configured."
    ::= { streams 6 }

    queueUse OBJECT-TYPE
        SYNTAX Gauge
        ACCESS read-only
        STATUS mandatory
        DESCRIPTION
            "Number of Streams queues currently in use by the system.  Streams are composed of queues, one for each
             direction of data flow.  The value of this variable indicates the number of queue data structures
             currently in use."
    ::= { streams 7 }

    queueMaxs OBJECT-TYPE
        SYNTAX INTEGER
        ACCESS read-only
        STATUS mandatory
        DESCRIPTION
            "The largest number of open 'streams' recorded by the system.  This value represents the 'high-water'
             mark."
    ::= { streams 8 }

    queueFails OBJECT-TYPE
        SYNTAX Counter
        ACCESS read-only
        STATUS mandatory
        DESCRIPTION
            "The number of Streams queue allocation failures.  Monitoring the queueUse, queueMax, and queueFail
             variables can help determine if the Streams subsystem is properly configured."
    ::= { streams 9 }

    mblockUse OBJECT-TYPE
        SYNTAX Gauge
        ACCESS read-only
        STATUS mandatory
        DESCRIPTION
            "The number of Streams message blocks currently in use.  Streams messages are composed of message-blocks
             in a linked-list.  The value of this variable indicates how many of the systems message blocks are in
             use."
    ::= { streams 10 }

    mblockMaxs OBJECT-TYPE
        SYNTAX INTEGER
        ACCESS read-only
        STATUS mandatory
        DESCRIPTION
            "The largest number of Streams message blocks in use at any one time.  This value represents a
             'high-water' mark."
    ::= { streams 11 }

    mblockFails OBJECT-TYPE
        SYNTAX Counter
        ACCESS read-only
        STATUS mandatory
        DESCRIPTION
            "The number of Streams message block allocation failures.  Monitoring the mblockUse, mblockMax, and
             mblockFail variables can help determine if the Streams subsystem is properly configured."
    ::= { streams 12 }

    dblockUse OBJECT-TYPE
        SYNTAX Gauge
        ACCESS read-only
        STATUS mandatory
        DESCRIPTION
            "The number of Streams data blocks currently in use.  Message data is stored in data-blocks; the value of
             this variable indicates how many of the data-blocks are currently in use."
    ::= { streams 13 }

    dblockMaxs OBJECT-TYPE
        SYNTAX INTEGER
        ACCESS read-only
        STATUS mandatory
        DESCRIPTION
            "The largest number of Streams data blocks in use at any one time.  This value represents a 'high-water'
             mark."
    ::= { streams 14 }

    dblockFails OBJECT-TYPE
        SYNTAX Counter
        ACCESS read-only
        STATUS mandatory
        DESCRIPTION
            "The number of Streams data block allocation failures.  Monitoring the dblockUse, dblockMax, and
             dblockFail variables can help determine if the Streams subsystem is properly configured."
    ::= { streams 15 }


------------------------------------------------------------
--  The User Table
------------------------------------------------------------

    userTable OBJECT-TYPE
        SYNTAX SEQUENCE OF UserEntry
        ACCESS not-accessible
        STATUS mandatory
        DESCRIPTION
            "Table describing defined users of the node which the agent resides on.  Normally, the list of valid
             users is stored in the /etc/passwd file; on systems which run NIS or NIS+, this table represents both
             users in the /etc/passwd file and in the NIS passwd file."
    ::= { sysmgmt 2 }

    userEntry OBJECT-TYPE
        SYNTAX UserEntry
        ACCESS not-accessible
        STATUS mandatory
        DESCRIPTION
            "An entry in the table describing defined users."
        INDEX { userIndex }
    ::= { userTable 1 }

    UserEntry ::= SEQUENCE {
        userIndex   INTEGER,
        userLoginID SnmpAdminString,
        userPasswd  DisplayString,
        userUID     INTEGER,
        userGID     INTEGER,
        userName    SnmpAdminString,
        userHomeDir SnmpAdminString,
        userShell   SnmpAdminString
    }

    userIndex OBJECT-TYPE
        SYNTAX INTEGER (1..2147483647)
        ACCESS read-only
        STATUS mandatory
        DESCRIPTION
            "The instance of the userEntry object, derived from its index number in the password file."
    ::= { userEntry 1 }

    userLoginID OBJECT-TYPE
        SYNTAX SnmpAdminString
        ACCESS read-only
        STATUS mandatory
        DESCRIPTION
            "The user's login ID which is normally given to the system's login prompt (e.g. root)."
    ::= { userEntry 2 }

    userPasswd OBJECT-TYPE
        SYNTAX DisplayString
        ACCESS read-only
        STATUS mandatory
        DESCRIPTION
            "The user's encrypted password.  Users without passwords have an '*' in this field."
    ::= { userEntry 3 }

    userUID OBJECT-TYPE
        SYNTAX INTEGER
        ACCESS read-only
        STATUS mandatory
        DESCRIPTION
            "The user's User-ID or UID (e.g. 0)."
    ::= { userEntry 4 }

    userGID OBJECT-TYPE
        SYNTAX INTEGER
        ACCESS read-only
        STATUS mandatory
        DESCRIPTION
            "The user's Group-ID or GID (e.g. 1)."
    ::= { userEntry 5 }

    userName OBJECT-TYPE
        SYNTAX SnmpAdminString
        ACCESS read-only
        STATUS mandatory
        DESCRIPTION
            "The user's real life name (e.g. John Doe)."
    ::= { userEntry 6 }

    userHomeDir OBJECT-TYPE
        SYNTAX SnmpAdminString
        ACCESS read-only
        STATUS mandatory
        DESCRIPTION
            "The user's home directory when that user logs in (e.g. /home/john)."
    ::= { userEntry 7 }

    userShell OBJECT-TYPE
        SYNTAX SnmpAdminString
        ACCESS read-only
        STATUS mandatory
        DESCRIPTION
            "The user's preferred shell (e.g. /bin/csh)."
    ::= { userEntry 8 }


------------------------------------------------------------
--  The Group Table
------------------------------------------------------------

    groupTable OBJECT-TYPE
        SYNTAX SEQUENCE OF GroupEntry
        ACCESS not-accessible
        STATUS mandatory
        DESCRIPTION
            "Table describing defined groups on node that agent resides.  Normally the list of valid user groups is
            stored in the file /etc/group. On systems running NIS or NIS+, this table represents valid groups in
            /etc/group and in the NIS group file."
    ::= { sysmgmt 3 }

    groupEntry OBJECT-TYPE
        SYNTAX GroupEntry
        ACCESS not-accessible
        STATUS mandatory
        DESCRIPTION
            "Entry in table describing valid groups."
        INDEX { groupIndex }
    ::= { groupTable 1 }

    GroupEntry ::= SEQUENCE {
        groupIndex  INTEGER,
        groupName   SnmpAdminString,
        groupPasswd DisplayString,
        groupGID    INTEGER
    }

    groupIndex OBJECT-TYPE
        SYNTAX INTEGER (1..2147483647)
        ACCESS read-only
        STATUS mandatory
        DESCRIPTION
            "The instance of the groupEntry object, derived from its index in the groups file."
    ::= { groupEntry 1 }

    groupName OBJECT-TYPE
        SYNTAX SnmpAdminString
        ACCESS read-only
        STATUS mandatory
        DESCRIPTION
            "The name of the group (e.g. wheel)."
    ::= { groupEntry 2 }

    groupPasswd OBJECT-TYPE
        SYNTAX DisplayString
        ACCESS read-only
        STATUS mandatory
        DESCRIPTION
            "The encrypted password for the group.  Groups without passwords have an '*' in this field."
    ::= { groupEntry 3 }

    groupGID OBJECT-TYPE
        SYNTAX INTEGER
        ACCESS read-only
        STATUS mandatory
        DESCRIPTION
            "The group-ID or GID (e.g. 1)."
    ::= { groupEntry 4 }


------------------------------------------------------------
--  The Process Table
------------------------------------------------------------
--  This group provides access to the kernel's process table which can
--  be queried to find out information on processes currently running
--  on this host.

    processTable OBJECT-TYPE
        SYNTAX SEQUENCE OF ProcessEntry
        ACCESS not-accessible
        STATUS mandatory
        DESCRIPTION
            "Table describing currently running processes on the node which the SNMP agent resides."
    ::= { sysmgmt 4 }

    processEntry OBJECT-TYPE
        SYNTAX ProcessEntry
        ACCESS not-accessible
        STATUS mandatory
        DESCRIPTION
            "Each entry in the process table represents a single running process.  Because the SNMP standard does not
            allow tables to be indexed with the value 0, and because PID 0 is valid on many UNIX and NT systems,
            SystemEDGE really indexes the processTable with processID+1.  That is, process with PID 0 is contained at
            table index 1."
        INDEX { processID }
    ::= { processTable 1 }

    ProcessEntry ::= SEQUENCE {
        processID          INTEGER,
        processName        SnmpAdminString,
        processState       INTEGER,
        processNice        INTEGER,
        processFlags       INTEGER,
        processUID         INTEGER,
        processGID         INTEGER,
        processKill        INTEGER,
        processMEM         Gauge,
        processSize        Gauge,
        processRSS         Gauge,
        processTime        INTEGER,
        processParentPID   INTEGER,
        processNumThreads  INTEGER,
        processInBlks      Counter,
        processOutBlks     Counter,
        processMsgsSent    Counter,
        processMsgsRecv    Counter,
        processSysCalls    Counter,
        processMinorPgFlts Counter,
        processMajorPgFlts Counter,
        processNumSwaps    Counter,
        processVolCtx      Counter,
        processInvolCtx    Counter,
        processArgs        SnmpAdminString,
        processStartTime   DisplayString,
        processStateStr    DisplayString,
        processStateInt    INTEGER,
        processZoneID      INTEGER,
        processZoneName    DisplayString,
        processTimePermil  INTEGER,
        processTimePercent INTEGER
    }

    processID OBJECT-TYPE
        SYNTAX INTEGER (0..2147483647)
        ACCESS read-only
        STATUS mandatory
        DESCRIPTION
            "The unique process ID (e.g. 0).  The value of this object also serves as the instance of the
            processEntry object."
    ::= { processEntry 1 }

    processName OBJECT-TYPE
        SYNTAX SnmpAdminString
        ACCESS read-only
        STATUS mandatory
        DESCRIPTION
            "The name of the running process (e.g. swapper). Shares the same limitations as processArgs OID."
    ::= { processEntry 2 }

    processState OBJECT-TYPE
        SYNTAX INTEGER
        ACCESS read-only
        STATUS deprecated
        DESCRIPTION
            "The process state is operating system dependent.  Possible states (for SunOS 4.1.3) include sleeping(1),
            waiting(2), running (3), idle (4), zombie (5), stopped(6), unknown(7). This MIB object should be
            deprecated in favor of processStateStr which is portable and standard across all platforms.  processState
            values are platform specific and thus harder to handle in platform-independent manner."
    ::= { processEntry 3 }

    processNice OBJECT-TYPE
        SYNTAX INTEGER
        ACCESS read-write
        STATUS mandatory
        DESCRIPTION
            "The 'nice' value of the process which can be modified to give a process greater or lesser priority over
            other processes.  The 'nice' value reflects the level of priority that the running process has; the
            higher the value, the lower the priority the process has. Setting this value is a deprecated functionality 
            and should not be used; it is only available on some platforms, including Linux, Solaris and HPUX."
    ::= { processEntry 4 }

    processFlags OBJECT-TYPE
        SYNTAX INTEGER
        ACCESS read-only
        STATUS mandatory
        DESCRIPTION
            "The process flags; flags are operating system dependent and are generally documented in system header
            files."
    ::= { processEntry 5 }

    processUID OBJECT-TYPE
        SYNTAX INTEGER
        ACCESS read-only
        STATUS mandatory
        DESCRIPTION
            "The process owner's user ID (e.g. 0 for root)."
    ::= { processEntry 6 }

    processGID OBJECT-TYPE
        SYNTAX INTEGER
        ACCESS read-only
        STATUS mandatory
        DESCRIPTION
            "The process owner's group ID (e.g. 0 for wheel)."
    ::= { processEntry 7 }

    processKill OBJECT-TYPE
        SYNTAX INTEGER
        ACCESS read-write
        STATUS mandatory
        DESCRIPTION
            "This object represents a signal that can be sent to the running process.  When accessed with GET or
            GetNext, a 0 is returned.  When a valid signal value is written, the agent sends that signal to the
            corresponding process. To kill or delete a process from the process table, the value corresponding to
            SIGKILL(9) should be written to this object.  Signals are defined in a system dependent manner and are
            usually defined in system header files and manual pages."
    ::= { processEntry 8 }

    processMEM OBJECT-TYPE
        SYNTAX Gauge
        ACCESS read-only
        STATUS mandatory
        DESCRIPTION
            "The percentage (0-100) of real memory used by this process."
    ::= { processEntry 9 }

    processSize OBJECT-TYPE
        SYNTAX Gauge
        ACCESS read-only
        STATUS mandatory
        DESCRIPTION
            "The combined size of the text, data and stack segments in KBytes.  Processes are normally broken into
            segments including those for text (or program), data, and stack.  This variable indicates how large the
            variable size portion of a process is.  Monitoring this value can help determine the health of a
            process."
    ::= { processEntry 10 }

    processRSS OBJECT-TYPE
        SYNTAX Gauge
        ACCESS read-only
        STATUS mandatory
        DESCRIPTION
            "Real memory (resident set) size of the process in kilobytes.  This value indicates how many bytes are
            held by a process."
    ::= { processEntry 11 }

    processTime OBJECT-TYPE
        SYNTAX INTEGER
        ACCESS read-only
        STATUS mandatory
        DESCRIPTION
            "This process' accumulated CPU time in seconds."
    ::= { processEntry 12 }

    processParentPID OBJECT-TYPE
        SYNTAX INTEGER
        ACCESS read-only
        STATUS mandatory
        DESCRIPTION
            "This process' parent process ID (PID)."
    ::= { processEntry 13 }

    processNumThreads OBJECT-TYPE
        SYNTAX INTEGER
        ACCESS read-only
        STATUS mandatory
        DESCRIPTION
            "The number of threads executing within this process.  Note, on some systems, the operating system may be
            un-aware of user-level threads executing within the process.  This object reflects the number of threads
            executing within the process that the operating system is aware of."
    ::= { processEntry 14 }

    processInBlks OBJECT-TYPE
        SYNTAX Counter
        ACCESS read-only
        STATUS mandatory
        DESCRIPTION
            "The number of blocks of data input by the process."
    ::= { processEntry 15 }

    processOutBlks OBJECT-TYPE
        SYNTAX Counter
        ACCESS read-only
        STATUS mandatory
        DESCRIPTION
            "The number of blocks of data output by the process."
    ::= { processEntry 16 }

    processMsgsSent OBJECT-TYPE
        SYNTAX Counter
        ACCESS read-only
        STATUS mandatory
        DESCRIPTION
            "The number of messages sent by the process."
    ::= { processEntry 17 }

    processMsgsRecv OBJECT-TYPE
        SYNTAX Counter
        ACCESS read-only
        STATUS mandatory
        DESCRIPTION
            "The number of messages received by the process."
    ::= { processEntry 18 }

    processSysCalls OBJECT-TYPE
        SYNTAX Counter
        ACCESS read-only
        STATUS mandatory
        DESCRIPTION
            "The number of system calls invoked by this process."
    ::= { processEntry 19 }

    processMinorPgFlts OBJECT-TYPE
        SYNTAX Counter
        ACCESS read-only
        STATUS mandatory
        DESCRIPTION
            "The number of minor page faults incurred by this process.  Minor faults do not require I/O to retrieve
            the page."
    ::= { processEntry 20 }

    processMajorPgFlts OBJECT-TYPE
        SYNTAX Counter
        ACCESS read-only
        STATUS mandatory
        DESCRIPTION
            "The number of major page faults incurred by this process.  Major faults require I/O to retrieve the
            page."
    ::= { processEntry 21 }

    processNumSwaps OBJECT-TYPE
        SYNTAX Counter
        ACCESS read-only
        STATUS mandatory
        DESCRIPTION
            "The number of times this process has been swapped."
    ::= { processEntry 22 }

    processVolCtx OBJECT-TYPE
        SYNTAX Counter
        ACCESS read-only
        STATUS mandatory
        DESCRIPTION
            "The number of voluntary context switches incurred by this process.  Voluntary context switches occur
            when the processor 'voluntary' gives up the CPU (e.g. waiting on I/O.)"
    ::= { processEntry 23 }

    processInvolCtx OBJECT-TYPE
        SYNTAX Counter
        ACCESS read-only
        STATUS mandatory
        DESCRIPTION
            "The number of involuntary context switches incurred by this process.   An involuntary context switch
            occurs when the process has executed for the duration of its time quantum and is switched out by the
            process scheduler."
    ::= { processEntry 24 }

    processArgs OBJECT-TYPE
        SYNTAX SnmpAdminString
        ACCESS read-only
        STATUS mandatory
        DESCRIPTION
            "The parameters supplied to this process when it was initially started. The supported length varies
            depending on the operating system. On Windows, Solaris and AIX is limited by OS only, Linux up to 4k,
            HP-UX up to 1020 characters including the process name."
    ::= { processEntry 25 }

    processStartTime OBJECT-TYPE
        SYNTAX DisplayString
        ACCESS read-only
        STATUS mandatory
        DESCRIPTION
            "The date/time when this process started. The format is as follows: to local time in the form of  a
            26-character string as shown below. Time zone and daylight savings corrections are  made before  string
            generation.  The fields are constant width: Fri Sep 13 00:00:00 1986\n"
    ::= { processEntry 26 }

    processStateStr OBJECT-TYPE
        SYNTAX DisplayString
        ACCESS read-only
        STATUS mandatory
        DESCRIPTION
            "The process state in an operating-system independent format.  A process-state matrix is included below.
            Note that not all operating systems may support a specific process-state.
            --------  --------------------------------
            State     Description
            --------  --------------------------------
            starting  Process under creation
            runnable  Process is on run queue
            sleeping  Process is waiting for event to complete
            sleep     Uninterruptible sleep (usually IO)
            zombie    Process terminated; parent not waiting
            stop      Process stopped either by job control
                      signal or because it is being traced
            active    The process is running on a processor
            swapped   Process is swapped out to secondary storage
            wait      Process is waiting for memory;
                      subclass of sleeping state
            other     Misc state 
                      (forking, exiting, transition, etc.)"       
    ::= { processEntry 27 }

    processStateInt OBJECT-TYPE
        SYNTAX INTEGER {
            procStateStarting(1),
            procStateRunnable(2),
            procStateActive(3),
            procStateWait(4),
            procStateSleeping(5),
            procStateSwapped(6),
            procStateSleep(7),
            procStateStop(8),
            procStateOther(9),
            procStateZombie(10)
        }
        ACCESS read-only
        STATUS mandatory
        DESCRIPTION
            "The process state, as above, represented by integer for easier polling and trending."
    ::= { processEntry 28 }

    processZoneID OBJECT-TYPE
        SYNTAX INTEGER
        ACCESS read-only
        STATUS mandatory
        DESCRIPTION
            "This attribute returns the zone ID for the Solaris zone in which the process is executing."
    ::= { processEntry 29 }

    processZoneName OBJECT-TYPE
        SYNTAX DisplayString (SIZE (0..62))
        ACCESS read-only
        STATUS mandatory
        DESCRIPTION
            "The name of the zone that the process belongs to. Only valid on Solaris 10 or newer."
    ::= { processEntry 30 }

    processTimePermil OBJECT-TYPE
        SYNTAX INTEGER
        ACCESS read-only
        STATUS mandatory
        DESCRIPTION
            "The permil CPU utilization, of this process, over the last sample interval.
            Although this value is highly system-dependent, it is usually determined by calculating
            the difference in the number of CPU ticks and dividing by the total possible CPU ticks.
            Since fractions are not supported by SNMP, the value reported is permil multiplied by 1000.
            For example, a CPU permil of 1.37 would be returned as 1370." 
    ::= { processEntry 31 }

    processTimePercent OBJECT-TYPE
        SYNTAX INTEGER
        ACCESS read-only
        STATUS mandatory
        DESCRIPTION
            "The CPU utilization in percents, of this process, over the last sample interval.
            Although this value is highly system-dependent, it is usually determined by calculating
            the difference in the number of CPU ticks and dividing by the total possible CPU ticks." 
    ::= { processEntry 32 }

------------------------------------------------------------
--  The Who Table
------------------------------------------------------------
--  Who is logged onto this system

    whoTable OBJECT-TYPE
        SYNTAX SEQUENCE OF WhoEntry
        ACCESS not-accessible
        STATUS mandatory
        DESCRIPTION
            "This table represents users who are currently logged into the node which the agent resides."
    ::= { sysmgmt 5 }

    whoEntry OBJECT-TYPE
        SYNTAX WhoEntry
        ACCESS not-accessible
        STATUS mandatory
        DESCRIPTION
            "An entry in the who table."
        INDEX { whoIndex }
    ::= { whoTable 1 }

    WhoEntry ::= SEQUENCE {
        whoIndex  INTEGER,
        whoName   SnmpAdminString,
        whoDevice DisplayString,
        whoPID    INTEGER,
        whoTime   TimeTicks,
        whoWhere  DisplayString
    }

    whoIndex OBJECT-TYPE
        SYNTAX INTEGER (1..2147483647)
        ACCESS read-only
        STATUS mandatory
        DESCRIPTION
            "The instance of the whoEntry object."
    ::= { whoEntry 1 }

    whoName OBJECT-TYPE
        SYNTAX SnmpAdminString
        ACCESS read-only
        STATUS mandatory
        DESCRIPTION
            "The user name of a user logged into the node which the agent resides (e.g. root)."
    ::= { whoEntry 2 }

    whoDevice OBJECT-TYPE
        SYNTAX DisplayString
        ACCESS read-only
        STATUS mandatory
        DESCRIPTION
            "The device the user is using to log into the node which the agent resides (e.g. console or ttyp1)."
    ::= { whoEntry 3 }

    whoPID OBJECT-TYPE
        SYNTAX INTEGER
        ACCESS read-only
        STATUS mandatory
        DESCRIPTION
            "This object represents the process ID for the user's login shell.  This object is not supported on SunOS
            4.X systems; 0 is returned instead."
    ::= { whoEntry 4 }

    whoTime OBJECT-TYPE
        SYNTAX TimeTicks
        ACCESS read-only
        STATUS mandatory
        DESCRIPTION
            "The time when the user first logged in.
            This relative time (R) is given in hundredths of a second since the agent was started. It can be
            converted into an absolute time (A) using sysUpTime (from MIB-II) and hrSystemDate (from HR-MIB).
            sysUpTime (S) is the elapsed time (in hundredths of a second) since the agent was started.
            hrSysDate (H) is the current absolute date and time (in DateAndTime format) and must be converted
            to Unix Time format (seconds elapsed since 01.01.1970). Finally calculate: A = H - S/100 + R/100"
    ::= { whoEntry 5 }

    whoWhere OBJECT-TYPE
        SYNTAX DisplayString
        ACCESS read-only
        STATUS mandatory
        DESCRIPTION
            "The location the user logged in from if applicable. (e.g. :0.0 if local or host name if logged in from a
            remote system)."
    ::= { whoEntry 6 }


------------------------------------------------------------
--  The Remote Shell Group
------------------------------------------------------------
--  A remote shell is invoked in the following manner via:
--    1) Write (via SNMP SET) a filename that all output
--       from the resulting remote shell invocation will
--       be placed in.  This file shall reside in '/tmp'
--       for safety and security considerations
--
--    2) Write (via SNMP SET) the command and arguments to be executed
--       by the agent.  When the object is SET (given that
--       shellOutput has been properly set) the agent invokes (via
--       fork/exec) the command and redirects the output into the file
--       given by the value in shellOutput.
--
--    3) When complete, the remote shell invocation's exit status
--       is placed in the object shellExitStat

    remoteShell OBJECT IDENTIFIER ::= { sysmgmt 6 }

    shellOutput OBJECT-TYPE
        SYNTAX SnmpAdminString
        ACCESS read-write
        STATUS mandatory
        DESCRIPTION
            "The name of a file that will receive all output from the execution of a UNIX command initiated by the
            agent.  This file is restricted to the '/tmp' ('\temp' or '\tmp' for NT) directory for security and
            safety considerations.  If the value object is set to anything other that that residing in '/tmp' or a
            relative pathname, an error will be returned."
    ::= { remoteShell 1 }

    shellCmd OBJECT-TYPE
        SYNTAX SnmpAdminString
        ACCESS read-write
        STATUS mandatory
        DESCRIPTION
            "The command and arguments to be executed by the agent.  When this object is SET, (and a valid
            shellOutput object exists), the agent fork/execs the command with STDOUT and STDERR going to the value of
            shellOutput.  On NT systems, the command is run synchronously so care should be taken not to block the
            subagent indefinitely."
    ::= { remoteShell 2 }

    shellExitStat
        OBJECT-TYPE
        SYNTAX INTEGER
        ACCESS read-only
        STATUS mandatory
        DESCRIPTION
            "The exit code from the execution of a shell command.  The value remains unchanged until another command
            is executed.  Each execution of a shell command overwrites the previous value of this object.  On some
            systems (HPUX-9), the exit status is not available if the shell command was invoked in the background in
            order to avoid defunct or zombie processes waiting on that shell command's exit value."
    ::= { remoteShell 3 }

    shellOutputContents OBJECT-TYPE
        SYNTAX DisplayString (SIZE (0..512))
        ACCESS read-only
        STATUS mandatory
        DESCRIPTION
            "This object returns up to the first 512 characters of the last shell-command output stored in the file
            specified by shellOutput (remoteShell.1).  No attempt at translating the character output is made by the
            agent."
    ::= { remoteShell 4}


------------------------------------------------------------
--  The Performance Group
------------------------------------------------------------
--  Kernel performance related parameters and statistics

    performance OBJECT IDENTIFIER ::= { sysmgmt 7 }
    kernelperf  OBJECT IDENTIFIER ::= { performance 8 }

--  kernelperf attributes 1, 2 and 3 are deprecated and removed

    runQLen OBJECT-TYPE
        SYNTAX Gauge
        ACCESS read-only
        STATUS mandatory
        DESCRIPTION
            "The length of the scheduler's run queue sampled over a fixed period of time.  The sampling interval is
            system dependent.  In SunOS, the kernel updates this parameter once every 5 seconds.  The system's load
            average is computed from the value of runQLen; the load average is defined as the average runQLen value
            over some interval."
    ::= { kernelperf 4 }

    diskWaitNum OBJECT-TYPE
        SYNTAX Gauge
        ACCESS read-only
        STATUS mandatory
        DESCRIPTION
            "The number of jobs that are waiting on disk I/O sampled over a fixed period of time.  The sampling
            interval is system dependent.  In SunOS, the kernel updates this parameter once every 5 seconds.  A large
            value may indicate an overloaded system although larger values may be observed on file server systems."
    ::= { kernelperf 5 }

    pageWaitNum OBJECT-TYPE
        SYNTAX Gauge
        ACCESS read-only
        STATUS mandatory
        DESCRIPTION
            "The number of jobs that are waiting on page I/O sampled over a fixed period of time.  The sampling
            interval is system dependent.  In SunOS, the kernel updates this parameter once every 5 seconds.  A large
            value may indicate the system does not have enough memory for the current load."
    ::= { kernelperf 6 }

    swapActive OBJECT-TYPE
        SYNTAX Gauge
        ACCESS read-only
        STATUS mandatory
        DESCRIPTION
            "The number of jobs that are active yet swapped out of memory, sampled over a fixed period of time.  The
             sampling interval is system dependent.  In SunOS, the kernel updates this parameter once every 5
             seconds. A high value for this object may indicate that system memory is not sufficient for the current
             load."
    ::= { kernelperf 7 }

    sleepActive OBJECT-TYPE
        SYNTAX Gauge
        ACCESS read-only
        STATUS mandatory
        DESCRIPTION
            "The number of jobs that are active yet sleeping in core, sampled over a fixed period of time.  The
             sampling interval is system dependent.  In SunOS, the kernel updates this parameter once every 5
             seconds. A process is active yet sleeping in core when it is not running and not swapped out to
             secondary storage (swap)."
    ::= { kernelperf 8 }

    memInUse OBJECT-TYPE
        SYNTAX Gauge
        ACCESS read-only
        STATUS mandatory
        DESCRIPTION
            "The total real KBytes of memory in use sampled over a fixed period of time.  The sampling interval is
             system dependent.  In SunOS, the kernel updates this parameter once every 5 seconds.  Comparing memInUse
             to memory (in the Concord 'sysedgeSystem' group) can help indicate if a system has sufficent memory for
             its current load."
    ::= { kernelperf 9 }

    activeMem OBJECT-TYPE
        SYNTAX Gauge
        ACCESS read-only
        STATUS mandatory
        DESCRIPTION
            "The total active real memory (KBytes) sampled over a fixed period of time.  The sampling interval is
             system dependent.  In SunOS, the kernel updates this parameter once every 5 seconds.  Memory is active
             when it is actually being used by a process running in memory.  This value should be less than or equal
             to memInUse.  A high value may indicate a system with insufficient memory."
    ::= { kernelperf 10 }

    numProcs OBJECT-TYPE
        SYNTAX Gauge
        ACCESS read-only
        STATUS mandatory
        DESCRIPTION
             "The number of processes table slots currently allocated and in use.  On older BSD-based systems, this
              metric is important since it places an uppder bound on the total number of processes that may run on
              the system at any one time."
    ::= { kernelperf 11 }

    numOpenFiles OBJECT-TYPE
        SYNTAX Gauge
        ACCESS read-only
        STATUS mandatory
        DESCRIPTION
             "The system-wide total number of open files."
    ::= { kernelperf 12 }

    swapInUse OBJECT-TYPE
        SYNTAX Gauge
        ACCESS read-only
        STATUS mandatory
        DESCRIPTION
             "The amount of swap space (KBytes) currently in use by the system.  Swap space is used when memory is in
              short supply.  Typically, entire processes are swapped out to secondary storage.  Comparing this value
              to totalSwap (in Concord's kernelConfig group) can help indicate if additional swap space is needed."
    ::= { kernelperf 13 }

    numSwitches OBJECT-TYPE
        SYNTAX Counter
        ACCESS read-only
        STATUS mandatory
        DESCRIPTION
            "The total number of context switches that have occurred since the kernel was last initialized.  A
            context switch occurs each time a process gives up the CPU and another takes its place.  This counter
            reflects the level of system activity; a high rate of context switching is indicative of the system
            load."
    ::= { kernelperf 14 }

    numTraps OBJECT-TYPE
        SYNTAX Counter
        ACCESS read-only
        STATUS mandatory
        DESCRIPTION
            "The total number of traps switching a process from user to kernel mode that have occurred since the
            kernel was last initialized.  Traps are hardware exceptions that occur and are usually caused by the
            currently running process.  Example traps include those for incorrect arithmetic operations, segmentation
            violations or page faults.  An excessive trap rate can indicate a faulty program, excessive system
            loading, or some other abnormality."
    ::= { kernelperf 15 }

    numSyscalls OBJECT-TYPE
        SYNTAX Counter
        ACCESS read-only
        STATUS mandatory
        DESCRIPTION
            "The total number of system calls that have occurred since the kernel was last initialized.  System calls
            occur when a process calls a function which must execute in kernel or privileged mode; it is a indicator
            of the system load and may be higher on servers or machines shared by many users."
    ::= { kernelperf 16 }

    numInterrupts OBJECT-TYPE
        SYNTAX Counter
        ACCESS read-only
        STATUS mandatory
        DESCRIPTION
            "The total number of device interrupts that have occurred since the kernel was last initialized.  The
            operating system is interrupted by devices and peripherals when they require the attention of the system.
            An excessive rate of interrupts can indicate a heavily loaded machine; servers and machines shared by
            many users will typically have a higher rate though."
    ::= { kernelperf 17 }

    numPageSwapIns OBJECT-TYPE
        SYNTAX Counter
        ACCESS read-only
        STATUS mandatory
        DESCRIPTION
            "The total number of pages that have been swapped in since the kernel was last initialized.  Page
            swapping occurs when a process is swapped to and from secondary storage.  A high rate of page swap
            activity can indicate an overloaded system."
    ::= { kernelperf 18 }

    numPageSwapOuts OBJECT-TYPE
        SYNTAX Counter
        ACCESS read-only
        STATUS mandatory
        DESCRIPTION
            "The total number of pages that have been swapped out since the kernel was last initialized.  Page
            swapping occurs when a process is swapped to and from secondary storage.  A high rate of page swap
            activity can indicate an overloaded system."
    ::= { kernelperf 19 }

    numSwapIns OBJECT-TYPE
        SYNTAX Counter
        ACCESS read-only
        STATUS mandatory
        DESCRIPTION
            "The total number of processes that have been swapped in since the kernel was last initialized. Processes
            are swapped to and from secondary storage when memory is in short supply.  A high rate may indicate an
            overloaded system."
    ::= { kernelperf 20 }

    numSwapOuts OBJECT-TYPE
        SYNTAX Counter
        ACCESS read-only
        STATUS mandatory
        DESCRIPTION
            "The total number of processes that have been swapped out since the kernel was last initialized.
            Processes are swapped to and from secondary storage when memory is in short supply.  A high rate may
            indicate an overloaded system."
    ::= { kernelperf 21 }

    numPageIns OBJECT-TYPE
        SYNTAX Counter
        ACCESS read-only
        STATUS mandatory
        DESCRIPTION
            "The total number of pages that have been paged in since the kernel was last initialized. Page-in is an
            operation performed by the virtual memory system in which the contents of a page are read from secondary
            storage.  A high rate of change may indicate an overloaded system."
    ::= { kernelperf 22 }

    numPageOuts OBJECT-TYPE
        SYNTAX Counter
        ACCESS read-only
        STATUS mandatory
        DESCRIPTION
            "The total number of pages that have been paged out since the kernel was last initialized. Page-out is an
            operation performed by the virtual memory system in which the contents of a page are written to secondary
            storage. A high rate of change may indicate an overloaded system."
    ::= { kernelperf 23 }

    numPageReclaims OBJECT-TYPE
        SYNTAX Counter
        ACCESS read-only
        STATUS mandatory
        DESCRIPTION
            "The total pages that have been reclaimed from the freelist since the kernel was last initialized.
            Memory pages are stored on a free-list when not in use.  If a page has been acquired from the free-list,
            it has been reclaimed.  A high rate of changed indicates an active system which is not generally
            considered to be overloaded."
    ::= { kernelperf 24 }

    numPageFaults OBJECT-TYPE
        SYNTAX Counter
        ACCESS read-only
        STATUS mandatory
        DESCRIPTION
            "The total number of page faults that have occurred since the kernel was last initialized.  A page fault
            occurs when a running process attempts to access a virtual memory page that is not currently in physical
            memory resulting in a hardware page fault.  A high rage of page faults may indicate an overloaded system
            or one with insufficient memory."
    ::= { kernelperf 25 }

    loadAverage1Min OBJECT-TYPE
        SYNTAX INTEGER
        ACCESS read-only
        STATUS mandatory
        DESCRIPTION
            "The load average over the last 1 minute.  The load average represents the average number of jobs in the
            run queue over the specified time range.  The value reported is the load average multiplied by 100.  For
            example, if the value 50 represents a load average of 0.50"
    ::= { kernelperf 26 }

    loadAverage5Min OBJECT-TYPE
        SYNTAX INTEGER
        ACCESS read-only
        STATUS mandatory
        DESCRIPTION
            "The load average over the last 5 minutes.  The load average represents the average number of jobs in the
            run queue over the specified time range.  The value reported is the load average multiplied by 100.  For
            example, if the value 50 represents a load average of 0.50"
    ::= { kernelperf 27 }

    loadAverage15Min OBJECT-TYPE
        SYNTAX INTEGER
        ACCESS read-only
        STATUS mandatory
        DESCRIPTION
            "The load average over the last 15 minutes.  The load average represents the average number of jobs in
            the run queue over the specified time range.  The value reported is the load average multiplied by 100.
            For example, if the value 50 represents a load average of 0.50"
    ::= { kernelperf 28 }

    totalSwapSpace OBJECT-TYPE
        SYNTAX INTEGER
        ACCESS read-only
        STATUS mandatory
        DESCRIPTION
            "Total system swap space in KBytes.  This object is identical to the kernelConfig.totalSwap(12) object
            and is repeated here for the convenience of management stations which cannot simultaneously poll groups
            of objects in different branches of the MIB."
    ::= { kernelperf 29 }

    swapCapacity OBJECT-TYPE
        SYNTAX INTEGER (0..100)
        ACCESS read-only
        STATUS mandatory
        DESCRIPTION
            "The percentage of the system's total swap in use. The value of this object can be computed by dividing
            swapInUse(13) by totalSwapSpace(29) and multiplying by 100.  It is included here for convenient polling,
            monitoring, and history sampling.  This object is an aggregate value over all the swap partitions and
            areas."
    ::= { kernelperf 30 }

    memCapacity OBJECT-TYPE
        SYNTAX INTEGER (0..100)
        ACCESS read-only
        STATUS mandatory
        DESCRIPTION
            "The percentage of the system's active memory in use. The value of this object can be approximated by
            dividing activeMem(10) by memory(sysedgeSystem.3) and converting to a percentage.  Because virutal memory
            allows systems to operate with a higher memCapacity value, this value alone should not be used to judge
            how loaded a system is.  Managers should also monitor swapCapacity."
    ::= { kernelperf 31 }

    memInUseCapacity OBJECT-TYPE
        SYNTAX INTEGER (0..100)
        ACCESS read-only
        STATUS mandatory
        DESCRIPTION
            "The percentage of the system's memory in use. The value of this object can be approximated by dividing
            memInUse(9) by memory(sysedgeSystem.3) and converting to a percentage.  Because virutal memory allows
            systems to operate with a higher memCapacity value, this value alone should not be used to judge how
            loaded a system is.  Managers should also monitor swapCapacity."
    ::= { kernelperf 32 }

    pageScans OBJECT-TYPE
        SYNTAX Counter
        ACCESS read-only
        STATUS mandatory
        DESCRIPTION
            "Total number of pages examined by pageout daemon. Excessive rates of scans (change in this counter) can
            indicate a machine with insufficient memory."
    ::= { kernelperf 33 }

    numZombieProcs OBJECT-TYPE
        SYNTAX Gauge
        ACCESS read-only
        STATUS mandatory
        DESCRIPTION
            "Current number of zombie processes found on the system.  This MIB object is found by adding up all
            processes with a processStateStr of zombie. The lower the number the better.  Supported in SystemEDGE 4.1
            and higher."
    ::= { kernelperf 34 }

    numPagingSpaceIns OBJECT-TYPE
        SYNTAX Counter
        ACCESS read-only
        STATUS mandatory
        DESCRIPTION
            "The total number of paging space page-ins. Supported in SystemEDGE 4.3 and higher for AIX."
    ::= { kernelperf 35 }

    numPagingSpaceOuts OBJECT-TYPE
        SYNTAX Counter
        ACCESS read-only
        STATUS mandatory
        DESCRIPTION
            "The total number of paging space page outs. Supported in SystemEDGE 4.3 and higher for AIX."
    ::= { kernelperf 36 }

    totalPagingSpace OBJECT-TYPE
        SYNTAX INTEGER 
        ACCESS read-only
        STATUS mandatory
        DESCRIPTION
            "The total paging space (in 4 KB pages) Supported in SystemEDGE 4.3 and higher for AIX."
    ::= { kernelperf 37 }

    freePagingSpace OBJECT-TYPE
        SYNTAX INTEGER 
        ACCESS read-only
        STATUS mandatory
        DESCRIPTION
            "The total free paging space (in 4 KB pages) Supported in SystemEDGE 4.3 and higher for AIX."
    ::= { kernelperf 38 }

    reservedPagingSpace OBJECT-TYPE
        SYNTAX INTEGER 
        ACCESS read-only
        STATUS mandatory
        DESCRIPTION
            "The total reserved paging space (in MB) Supported in SystemEDGE 4.3 and higher for AIX."
    ::= { kernelperf 39 }

    workUsedMem OBJECT-TYPE
	SYNTAX INTEGER
	ACCESS read-only
	STATUS mandatory
	DESCRIPTION
	    "Amount of used real memory in KB containing working segment pages.
	     Supported in SystemEDGE 4.3.4 and higher for AIX."
    ::= { kernelperf 40 }	

    persUsedMem OBJECT-TYPE
        SYNTAX INTEGER
        ACCESS read-only
        STATUS mandatory
        DESCRIPTION
             "Amount of used real memory in KB containing persistent segment pages.
              Supported in SystemEDGE 4.3.4 and higher for AIX."
    ::= { kernelperf 41 }

    clntUsedMem OBJECT-TYPE
        SYNTAX INTEGER
        ACCESS read-only
        STATUS mandatory
        DESCRIPTION
            "Amount of used real memory in KB containing client segment pages.
             Supported in SystemEDGE 4.3.4 and higher for AIX."
    ::= { kernelperf 42 }

    compPercent OBJECT-TYPE
        SYNTAX INTEGER
        ACCESS read-only
        STATUS mandatory
        DESCRIPTION
            "The percentage of real memory currently allocated to computational page frames. Computational page
             frames are generally those that are backed by paging space.
             Supported in SystemEDGE 4.3.4 and higher for AIX."
    ::= { kernelperf 43 }

    noncompPercent OBJECT-TYPE
        SYNTAX INTEGER
        ACCESS read-only
        STATUS mandatory
        DESCRIPTION
            "The percentage of real memory currently allocated to non-computational frames. Non-computational
             page frames are generally those that are backed by file space, either data files, executable files,
             or shared library files.
             Supported in SystemEDGE 4.3.4 and higher for AIX."
    ::= { kernelperf 44 }

    activeVirtualMemory OBJECT-TYPE
        SYNTAX INTEGER
        ACCESS read-only
        STATUS mandatory
        DESCRIPTION
            "Amount of active virtual memory (avm) in KB. Virtual pages are considered active if they
             have been accessed recently. 
             Supported in SystemEDGE 4.3.4 and higher for AIX."
    ::= { kernelperf 45 }

    forkRequestssec OBJECT-TYPE
        SYNTAX Gauge
        ACCESS read-only
        STATUS mandatory
        DESCRIPTION
            "Fork Requests/sec - Number of forks per second."
    ::= { kernelperf 46 }

	memoryStats  OBJECT IDENTIFIER ::= { performance 9 }	

    freePhysicalMemory OBJECT-TYPE
        SYNTAX INTEGER (0..100)
        ACCESS read-only
        STATUS mandatory
        DESCRIPTION
            "% Free Physical Memory - The percentage of physical (real) memory not in use."
    ::= { memoryStats 1 } 

    systemUsageFreeMemory OBJECT-TYPE
        SYNTAX Gauge
        ACCESS read-only
        STATUS mandatory
        DESCRIPTION
            "System Usage Free Memory - The total amount of unallocated virtual memory. (in kBytes)"
    ::= { memoryStats 2 }

    systemUsageTotalMemory OBJECT-TYPE
        SYNTAX Gauge
        ACCESS read-only
        STATUS mandatory
        DESCRIPTION
            "System Usage Total Memory - The total amount of  virtual memory available on the system. (in kBytes)"
    ::= { memoryStats 3 }

    systemUsageUsedMemory OBJECT-TYPE
        SYNTAX Gauge
        ACCESS read-only
        STATUS mandatory
        DESCRIPTION
            "System Usage Used Memory - The total number of kBytes of virtual memory in use."
    ::= { memoryStats 4 }

    scanRatePageScanssec OBJECT-TYPE
        SYNTAX Gauge
        ACCESS read-only
        STATUS mandatory
        DESCRIPTION
            "Scan Rate Page Scans/sec - The frequency with which the kernel checks for free memory pages."
    ::= { memoryStats 5 }

    requestsPageInssec OBJECT-TYPE
        SYNTAX Gauge
        ACCESS read-only
        STATUS mandatory
        DESCRIPTION
            "Requests Page Ins/sec - The number of pages paged in per second."
    ::= { memoryStats 6 }

    requestsPageOutssec OBJECT-TYPE
        SYNTAX Gauge
        ACCESS read-only
        STATUS mandatory
        DESCRIPTION
            "Requests Page Outs/sec - The number of pages paged out per second."
    ::= { memoryStats 7 }
	
    pagesIntransit OBJECT-TYPE
        SYNTAX Counter
        ACCESS read-only
        STATUS mandatory
        DESCRIPTION
            "Pages Intransit - The total number of in-transit blocking page faults. Supported on HP-UX only."
    ::= { memoryStats 8 }
	
    pagesIntransitsec OBJECT-TYPE
        SYNTAX Gauge
        ACCESS read-only
        STATUS mandatory
        DESCRIPTION
            "Pages Intransit/sec - The number of in-transit blocking page faults per second. Supported on HP-UX only."
    ::= { memoryStats 9 }

    requestsPageFreeBytessec OBJECT-TYPE
        SYNTAX Gauge
        ACCESS read-only
        STATUS mandatory
        DESCRIPTION
            "Requests Page Free kBytes/sec - The amount of space released to the kernel by terminating processes."
    ::= { memoryStats 10 }

    requestsPageFrees OBJECT-TYPE
        SYNTAX Counter
        ACCESS read-only
        STATUS mandatory
        DESCRIPTION
            "Requests Page Frees - The total number of pages released to the kernel since the system was started."
    ::= { memoryStats 11 }
	
    requestsPageFreessec OBJECT-TYPE
        SYNTAX Gauge
        ACCESS read-only
        STATUS mandatory
        DESCRIPTION
            "Requests Page Frees/sec - The number of pages released to the kernel by terminating processes."
    ::= { memoryStats 12 }

    requestsPageInBytessec OBJECT-TYPE
        SYNTAX Gauge
        ACCESS read-only
        STATUS mandatory
        DESCRIPTION
            "Requests Page In kBytes/sec - The amount of data paged in per second."
    ::= { memoryStats 13 }
	
    requestsPageOutBytessec OBJECT-TYPE
        SYNTAX Gauge
        ACCESS read-only
        STATUS mandatory
        DESCRIPTION
            "Requests Page Out kBytes/sec - The amount of data paged out per second."
    ::= { memoryStats 14 }

    requestsPageReclaimBytessec OBJECT-TYPE
        SYNTAX Gauge
        ACCESS read-only
        STATUS mandatory
        DESCRIPTION
            "Requests Page Reclaim kBytes/sec - The amount of space in pages reclaimed from the free list."
    ::= { memoryStats 15 }

    requestsPageReclaimssec OBJECT-TYPE
        SYNTAX Gauge
        ACCESS read-only
        STATUS mandatory
        DESCRIPTION
            "Requests Page Reclaims/sec - The number of pages reclaimed per second."
    ::= { memoryStats 16 }

    systemUsageLockedMemory OBJECT-TYPE
        SYNTAX Gauge
        ACCESS read-only
        STATUS mandatory
        DESCRIPTION
            "System Usage Locked Memory - The total number of kBytes of locked memory."
    ::= { memoryStats 17 }
	
	
	network  OBJECT IDENTIFIER ::= { performance 10 }	
	
	networkStatsTable OBJECT-TYPE
        SYNTAX SEQUENCE OF NetworkStatsEntry
        ACCESS not-accessible
        STATUS mandatory
        DESCRIPTION
            "Table containing network I/O stat entries; each entry provides the latest network interface statistics for one NIC. The
            agent periodically stats the system data structures for each NIC and records the values in the table."
    ::= { network 1 }

    networkStatsEntry OBJECT-TYPE
        SYNTAX NetworkStatsEntry
        ACCESS not-accessible
        STATUS mandatory
        DESCRIPTION
            "An entry in the networkStatsTable."
        INDEX { networkStatsIndex }
    ::= { networkStatsTable 1 }

    NetworkStatsEntry ::= SEQUENCE {
        networkStatsIndex             INTEGER,
        interfaceTrafficIncomingSec   Gauge,
		interfaceTrafficOutgoingSec   Gauge,
		inputErrors					  Counter,
		inputPackets				  Counter,
		outputPackets				  Counter
    }
	
	networkStatsIndex OBJECT-TYPE
        SYNTAX INTEGER (1..2147483647)
        ACCESS read-only
        STATUS mandatory
        DESCRIPTION
            "An index that uniquely identifies an entry in the networkStatsTable."
    ::= { networkStatsEntry 1 } 	
	
    interfaceTrafficIncomingSec OBJECT-TYPE
        SYNTAX Gauge
        ACCESS read-only
        STATUS mandatory
        DESCRIPTION
            "Interface Traffic Incoming/sec - Number of input packets per second for the interface card."
    ::= { networkStatsEntry 2 }
	
    interfaceTrafficOutgoingSec OBJECT-TYPE
        SYNTAX Gauge
        ACCESS read-only
        STATUS mandatory
        DESCRIPTION
            "Interface Traffic Outgoing/sec - Number of output packets per second for the interface card."
    ::= { networkStatsEntry 3 }

    inputErrors OBJECT-TYPE
        SYNTAX Counter
        ACCESS read-only
        STATUS mandatory
        DESCRIPTION
            "input errors - The number of input errors. These errors usually indicate faulty hardware, which can range from another computer that is generating bad packets to a bad connector or terminator."
    ::= { networkStatsEntry 4 }

    inputPackets OBJECT-TYPE
        SYNTAX Counter
        ACCESS read-only
        STATUS mandatory
        DESCRIPTION
            "input packets - The number of input packets transferred on the interface."
    ::= { networkStatsEntry 5 }

    outputPackets OBJECT-TYPE
        SYNTAX Counter
        ACCESS read-only
        STATUS mandatory
        DESCRIPTION
            "output packets - The number of output packets transferred on the interface."
    ::= { networkStatsEntry 6 }
	
	
------------------------------------------------------------
--  The Error Table
------------------------------------------------------------
--  Due to lack of support across the various supported platforms,
--  this table has been deprecated and removed.

--  errorTable OBJECT-TYPE
--      was defined
--  ::= { sysmgmt 8 }


------------------------------------------------------------
--  The IPC Group
------------------------------------------------------------
--  Report System V IPC configuration and usage statistics
--  System V IPC includes message queues, shared memory, and semaphores

    ipc OBJECT IDENTIFIER ::= { sysmgmt 9 }


------------------------------------------------------------
--  The Message Queue Table
------------------------------------------------------------

    msgqueTable OBJECT-TYPE
        SYNTAX SEQUENCE OF MsgqueEntry
        ACCESS not-accessible
        STATUS mandatory
        DESCRIPTION
            "This table contains an entry for each system SysV message queue currently in use."
    ::= { ipc 1 }

    msgqueEntry OBJECT-TYPE
        SYNTAX MsgqueEntry
        ACCESS not-accessible
        STATUS mandatory
        DESCRIPTION
            "An entry in the message queue table."
        INDEX { queID }
    ::= { msgqueTable 1 }

    MsgqueEntry ::= SEQUENCE {
        queID     INTEGER,
        queKey    DisplayString,
        queMode   DisplayString,
        queOwner  DisplayString,
        queGroup  DisplayString,
        queNBytes Gauge,
        queNMesg  Gauge,
        queDel    INTEGER
    }

    queID OBJECT-TYPE
        SYNTAX INTEGER (0..2147483647)
        ACCESS read-only
        STATUS mandatory
        DESCRIPTION
            "The unique queue ID.  The value of this object also represents the instance for the queEntry object."
    ::= { msgqueEntry 1 }

    queKey OBJECT-TYPE
        SYNTAX DisplayString
        ACCESS read-only
        STATUS mandatory
        DESCRIPTION
            "The message queue key.  Each message queue has a key value chosen by the creating user. Its value is
            only significant to the creating process."
    ::= { msgqueEntry 2 }

    queMode OBJECT-TYPE
        SYNTAX DisplayString
        ACCESS read-only
        STATUS mandatory
        DESCRIPTION
            "The message queue permissions mode.  The mode defines access permissions for the message queue as well
            as status information.  See the man page ipcs(1) for more information."
    ::= { msgqueEntry 3 }

    queOwner OBJECT-TYPE
        SYNTAX DisplayString
        ACCESS read-only
        STATUS mandatory
        DESCRIPTION
            "The login name (e.g. root) of the owner of the message queue."
    ::= { msgqueEntry 4 }

    queGroup OBJECT-TYPE
        SYNTAX DisplayString
        ACCESS read-only
        STATUS mandatory
        DESCRIPTION
            "The group name (e.g. wheel) of the owner of the message queue."
    ::= { msgqueEntry 5 }

    queNBytes OBJECT-TYPE
        SYNTAX Gauge
        ACCESS read-only
        STATUS mandatory
        DESCRIPTION
            "The number of bytes currently in the message queue."
    ::= { msgqueEntry 6 }

    queNMesg OBJECT-TYPE
        SYNTAX Gauge
        ACCESS read-only
        STATUS mandatory
        DESCRIPTION
            "The number of messages currently in the message queue."
    ::= { msgqueEntry 7 }

    queDel OBJECT-TYPE
        SYNTAX INTEGER {
            delete(1),
            valid(2)
        }
        ACCESS read-write
        STATUS mandatory
        DESCRIPTION
            "Setting this object to the value 1 causes this agent to remove the message queue from its table.  The
            message queue identifier is removed from the system-wide table and the kernel message queue and
            associated data structure are destroyed."
    ::= { msgqueEntry 8 }


------------------------------------------------------------
--  The Shared Memory Table
------------------------------------------------------------

    shmemTable OBJECT-TYPE
        SYNTAX SEQUENCE OF ShmemEntry
        ACCESS not-accessible
        STATUS mandatory
        DESCRIPTION
            "This table contains an entry for each system SysV shared memory segment currently in use."
    ::= { ipc 2 }

    shmemEntry
        OBJECT-TYPE
        SYNTAX ShmemEntry
        ACCESS not-accessible
        STATUS mandatory
        DESCRIPTION
            "An entry in the shared memory table."
        INDEX { shmemID }
    ::= { shmemTable 1 }

    ShmemEntry ::= SEQUENCE {
        shmemID    INTEGER,
        shmemKey   DisplayString,
        shmemMode  DisplayString,
        shmemOwner DisplayString,
        shmemGroup DisplayString,
        shmemSegSz INTEGER,
        shmemNLcks INTEGER,
        shmemDel   INTEGER
    }

    shmemID OBJECT-TYPE
        SYNTAX INTEGER (0..2147483647)
        ACCESS read-only
        STATUS mandatory
        DESCRIPTION
            "The unique shared memory segment ID.  The value of this object also represents the instance of the
            shmemEntry object."
    ::= { shmemEntry 1 }

    shmemKey OBJECT-TYPE
        SYNTAX DisplayString
        ACCESS read-only
        STATUS mandatory
        DESCRIPTION
            "The shared memory segment key.  Each shared memory segment is assigned a key value by the creating user.
            Its value is only significant to the creating process."
    ::= { shmemEntry 2 }

    shmemMode OBJECT-TYPE
        SYNTAX DisplayString
        ACCESS read-only
        STATUS mandatory
        DESCRIPTION
            "The shared memory segment permissions mode. The mode defines access permissions for the message queue as
            well as status information.  See the man page ipcs(1) for more information."
    ::= { shmemEntry 3 }

    shmemOwner OBJECT-TYPE
        SYNTAX DisplayString
        ACCESS read-only
        STATUS mandatory
        DESCRIPTION
            "The user login name (e.g. root) of the owner of the shared memory segment."
    ::= { shmemEntry 4 }

    shmemGroup OBJECT-TYPE
        SYNTAX DisplayString
        ACCESS read-only
        STATUS mandatory
        DESCRIPTION
            "The group name (e.g. wheel) of the owner of the shared memory segment."
    ::= { shmemEntry 5 }

    shmemSegSz OBJECT-TYPE
        SYNTAX INTEGER
        ACCESS read-only
        STATUS mandatory
        DESCRIPTION
            "The size in bytes of the shared memory segment"
    ::= { shmemEntry 6 }

    shmemNLcks
        OBJECT-TYPE
        SYNTAX INTEGER
        ACCESS read-only
        STATUS mandatory
        DESCRIPTION
            "The number of times the shared memory segment
            has been locked."
    ::= { shmemEntry 7 }

    shmemDel OBJECT-TYPE
        SYNTAX INTEGER {
            delete(1),
            valid(2)
        }
        ACCESS read-write
        STATUS mandatory
        DESCRIPTION
            "Setting this object to the value of 1 causes the agent to remove this entry from the table.  The shared
            memory identifier is removed from the system-wide table and the kernel shared memory segment and
            associated data structure are destroyed."
    ::= { shmemEntry 8 }


------------------------------------------------------------
--  The Semaphore Table
------------------------------------------------------------

    semTable OBJECT-TYPE
        SYNTAX SEQUENCE OF SemEntry
        ACCESS not-accessible
        STATUS mandatory
        DESCRIPTION
            "This table contains an entry for each system SysV semaphore currently in use."
    ::= { ipc 3 }

    semEntry OBJECT-TYPE
        SYNTAX SemEntry
        ACCESS not-accessible
        STATUS mandatory
        DESCRIPTION
            "An entry in the semaphore table."
        INDEX { semID }
    ::= { semTable 1 }

    SemEntry ::= SEQUENCE {
        semID    INTEGER,
        semKey   DisplayString,
        semMode  DisplayString,
        semOwner DisplayString,
        semGroup DisplayString,
        semNsems INTEGER,
        semDel   INTEGER
    }

    semID OBJECT-TYPE
        SYNTAX INTEGER (0..2147483647)
        ACCESS read-only
        STATUS mandatory
        DESCRIPTION
            "The unique semaphore ID.  The value of this object represents the instance for the semEntry object."
    ::= { semEntry 1 }

    semKey OBJECT-TYPE
        SYNTAX DisplayString
        ACCESS read-only
        STATUS mandatory
        DESCRIPTION
            "The semaphore's key. Each semaphore is assigned a key value by the creating user. Its value is only
            significant to the creating process."
    ::= { semEntry 2 }

    semMode OBJECT-TYPE
        SYNTAX DisplayString
        ACCESS read-only
        STATUS mandatory
        DESCRIPTION
            "The semaphore permissions mode.  The mode defines access permissions for the message queue as well as
            status information.  See the man page ipcs(1) for more information."
    ::= { semEntry 3 }

    semOwner OBJECT-TYPE
        SYNTAX DisplayString
        ACCESS read-only
        STATUS mandatory
        DESCRIPTION
            "The user login name (e.g. root) of the owner of the semaphore."
    ::= { semEntry 4 }

    semGroup OBJECT-TYPE
        SYNTAX DisplayString
        ACCESS read-only
        STATUS mandatory
        DESCRIPTION
            "The group name (e.g. wheel) of the owner of the semaphore."
    ::= { semEntry 5 }

    semNsems OBJECT-TYPE
        SYNTAX INTEGER
        ACCESS read-only
        STATUS mandatory
        DESCRIPTION
            "The number of individual semaphores within this semaphore group."
    ::= { semEntry 6 }

    semDel OBJECT-TYPE
        SYNTAX INTEGER {
            delete(1),
            valid(2)
        }
        ACCESS read-write
        STATUS mandatory
        DESCRIPTION
            "Setting the value of 1, causes the agent to remove this entry from its semaphore table. The semaphore
            identifier is removed from the system-wide table and the kernel semaphore group and associated data
            structures are destroyed."
    ::= { semEntry 7 }


------------------------------------------------------------
--  The Buffers Group
------------------------------------------------------------
--  Buffer allocation and usage is very
--  important to any running operating system.  Therefore, the buffer
--  group is divided into network buffers (mbufs group), Streams 
--  buffers (strbuf), and I/O buffer cache (ioBufferCache group)

    buffers OBJECT IDENTIFIER ::= { sysmgmt 10 }


------------------------------------------------------------
--  The Message Buffers Group
------------------------------------------------------------

    mbufs OBJECT IDENTIFIER ::= { buffers 1 }

    numMbufs OBJECT-TYPE
        SYNTAX Gauge
        ACCESS read-only
        STATUS mandatory
        DESCRIPTION
            "The total number of mbufs contained in the mbuf pool.  The BSD networking subsystem utilizes a buffer
            abstraction called 'mbufs'.  This object indicates the number of mbuf buffers pre-allocated by the
            operating system.  If the BSD networking subsystem is not supported, than 0 is returned."
    ::= { mbufs 1 }

    numClusters OBJECT-TYPE
        SYNTAX Gauge
        ACCESS read-only
        STATUS mandatory
        DESCRIPTION
            "The total number of logical pages or clusters obtained from the page pool.  Memory pages (or clusters)
            can also be attached to mbufs if needed.  The size of this pool is returned in this object.  If the BSD
            subsystem is not supported, than 0 is returned."
    ::= { mbufs 2 }

    freeClusters OBJECT-TYPE
        SYNTAX Gauge
        ACCESS read-only
        STATUS mandatory
        DESCRIPTION
            "The number of free clusters or memory pages in the mbuf cluster pool.  Monitoring the number of free
            clusters can help determine if the BSD protocol subsystem is properly configured.  On SunOS 4.X systems,
            TCP/IP is coded in the BSD subsystem.  Monitoring this variable can help determine if TCP/IP performance
            problems are due to insufficient buffer resources."
    ::= { mbufs 3 }

    numDrops OBJECT-TYPE
        SYNTAX Counter
        ACCESS read-only
        STATUS mandatory
        DESCRIPTION
            "The number of times requests for mbufs were denied.  An excessive rate of mbuf allocation failures may
            indicate an overloaded system or one with insufficient memory resources."
    ::= { mbufs 4 }

    numWaits OBJECT-TYPE
        SYNTAX Counter
        ACCESS read-only
        STATUS mandatory
        DESCRIPTION
            "The number of times requests for mbufs were delayed.  An excessive rate of mbuf allocation 'waits' may
            indicate an overloaded system or one with insufficient memory resources."
    ::= { mbufs 5 }

    numDrains OBJECT-TYPE
        SYNTAX Counter
        ACCESS read-only
        STATUS mandatory
        DESCRIPTION
            "The total number of calls to protocol drain routines.  When the protocol subsystem is running low on
            buffers, it can call each protocol's 'drain' function forcing that protocol to free buffers.  This object
            reveals how many times this even has occurred. An excessive rate of calls to 'drain' may indicate an
            overloaded or misconfigured system."
    ::= { mbufs 6 }


------------------------------------------------------------
--  The Message Buffers Allocation Table
------------------------------------------------------------
--  A table indicating mbuf allocation data by type

    mbufAllocTable OBJECT-TYPE
        SYNTAX SEQUENCE OF MbufAllocEntry
        ACCESS not-accessible
        STATUS mandatory
        DESCRIPTION
            "This table contains an entry for each mbuf type that has been allocated.  In the BSD networking
            subsystem, when an mbuf is allocated, the mbuf's intended use is categorized.  This table represents the
            categories and the number of mbuf's allocated to each type."
    ::= { mbufs 7 }

    mbufAllocEntry OBJECT-TYPE
        SYNTAX MbufAllocEntry
        ACCESS not-accessible
        STATUS mandatory
        DESCRIPTION
            "An entry in the mbuf Allocation table."
        INDEX { mbufType }
    ::= { mbufAllocTable 1 }

    MbufAllocEntry ::= SEQUENCE {
        mbufType  INTEGER,
        mbufDesc  DisplayString,
        mbufAlloc Gauge
    }

    mbufType OBJECT-TYPE
        SYNTAX INTEGER (0..255)
        ACCESS read-only
        STATUS mandatory
        DESCRIPTION
            "The type of mbuf.  Mbuf types generally range from from 0 to 255; many mbuf types (numbers > 30) are
            undefined and generally not used.  Their use and description are a local matter and may vary from system
            to system."
    ::= { mbufAllocEntry 1 }

    mbufDesc OBJECT-TYPE
        SYNTAX DisplayString
        ACCESS read-only
        STATUS mandatory
        DESCRIPTION
            "A textual description of the mbuf type. Example mbuf descriptions include 'Packet header', 'Socket
            structure', etc.  Undefined or unknown mbuf type descriptions return 'Unknown mbuf type' as their
            description."
    ::= { mbufAllocEntry 2 }

    mbufAlloc OBJECT-TYPE
        SYNTAX Gauge
        ACCESS read-only
        STATUS mandatory
        DESCRIPTION
            "The number of mbufs allocated and declared of to be of this type."
    ::= { mbufAllocEntry 3 }


------------------------------------------------------------
--  The Stream Buffers Group
------------------------------------------------------------
--  Streams buffers are partitioned into buckets of several sizes;
--  this table gives the message sizes and allocation statistics per
--  bucket.

    strbufs OBJECT IDENTIFIER ::= { buffers 2 }


------------------------------------------------------------
--  The Streams Buffers Allocation Table
------------------------------------------------------------

    strbufAllocTable OBJECT-TYPE
        SYNTAX SEQUENCE OF StrbufAllocEntry
        ACCESS not-accessible
        STATUS mandatory
        DESCRIPTION
            "This table contains an entry for each Streams buffer bucket sizes."
    ::= { strbufs 1 }

    strbufAllocEntry OBJECT-TYPE
        SYNTAX StrbufAllocEntry
        ACCESS not-accessible
        STATUS mandatory
        DESCRIPTION
            "An entry in the Streams buffer allocation table."
        INDEX { strbufAllocIndex }
    ::= { strbufAllocTable 1 }

    StrbufAllocEntry ::= SEQUENCE {
        strbufAllocIndex   INTEGER,
        strbufAllocSize    INTEGER,
        strbufAllocCurrent Gauge,
        strbufAllocMaxs    INTEGER,
        strbufAllocTotals  Counter,
        strbufAllocFails   Counter
    }

    strbufAllocIndex OBJECT-TYPE
        SYNTAX INTEGER (1..2147483647)
        ACCESS read-only
        STATUS mandatory
        DESCRIPTION
            "The table index of this entry."
    ::= { strbufAllocEntry 1 }

    strbufAllocSize OBJECT-TYPE
        SYNTAX INTEGER
        ACCESS read-only
        STATUS mandatory
        DESCRIPTION
            "The size of this bucket in bytes.  The size is less than or equal to this value yet greater than the
            previous entry's bucket size.  For example, if the bucket size os 1024 bytes, all Streams buffer requests
            of less than or equal to 1024 bytes will return a buffer of size 1024."
    ::= { strbufAllocEntry 2 }

    strbufAllocCurrent OBJECT-TYPE
        SYNTAX Gauge
        ACCESS read-only
        STATUS mandatory
        DESCRIPTION
            "The number of Streams buffers of this currently allocated.  Comparing the value of this object to
            strbufAllocMax can help one determine if the system is properly configured."
    ::= { strbufAllocEntry 3 }

    strbufAllocMaxs OBJECT-TYPE
        SYNTAX INTEGER
        ACCESS read-only
        STATUS mandatory
        DESCRIPTION
            "The maximum number of Streams buffers of this size ever allocated at any one time.  This value serves as
            a high-water mark for buffer allocations of this size."
    ::= { strbufAllocEntry 4 }

    strbufAllocTotals OBJECT-TYPE
        SYNTAX Counter
        ACCESS read-only
        STATUS mandatory
        DESCRIPTION
            "The total number of allocations of Streams buffers of this bucket size.  A high allocation rate can help
            one diagnose an overloaded system."
    ::= { strbufAllocEntry 5 }

    strbufAllocFails OBJECT-TYPE
        SYNTAX Counter
        ACCESS read-only
        STATUS mandatory
        DESCRIPTION
            "The total number of allocation failures for Streams buffers of this bucket size.  A high rate of failure
            can indicate an overloaded system or one that is not properly configured."
    ::= { strbufAllocEntry 6 }


------------------------------------------------------------
--  The I/O Buffer Cache Group
------------------------------------------------------------
--  Statistics and allocation information for the I/O Buffer Cache

    ioBufferCache OBJECT IDENTIFIER ::= { buffers 3 }

    numBreadRequests OBJECT-TYPE
        SYNTAX Counter
        ACCESS read-only
        STATUS mandatory
        DESCRIPTION
            "The total number of calls to the kernel's bread() function.  This function is the primary read interface
            to the kernel's buffer pool used for file system I/O.  On NT systems, this value is an aggregate of
            several read variables in the ntCachePerf group."
    ::= { ioBufferCache 1 }

    numBreadHits OBJECT-TYPE
        SYNTAX Counter
        ACCESS read-only
        STATUS mandatory
        DESCRIPTION
            "The number of kernel buffer cache 'hits'. The kernel caches previously used I/O buffers in an attempt to
            avoid excessive reading and writing to disk.  A cache 'hit' indicates that this strategy has paid off
            because a process has requested a buffer that was in the buffer cache thereby avoiding a more expensive
            disk read.  A high rate of cache hits indicates a relatively smooth running system.  On NT systems, this
            value is an aggregate of several hit variables in the ntCachePerf group."
    ::= { ioBufferCache 2 }

    numBufSleeps OBJECT-TYPE
        SYNTAX Counter
        ACCESS read-only
        STATUS mandatory
        DESCRIPTION
            "The total number of times the kernel had to 'sleep' for a buffer.  The kernel 'sleeps' for a buffer when
            it fails to find it in the cache and must access the disk for it.  Excessive buffer 'sleeps' indicates
            that the caching algorithm is not able to effectively predict and cache disk I/O patterns.  Adding more
            memory for buffering may improve the cache hit ratio."
    ::= { ioBufferCache 3 }

    numAgeAllocs OBJECT-TYPE
        SYNTAX Counter
        ACCESS read-only
        STATUS mandatory
        DESCRIPTION
            "The total number of times an aged buffer was allocated.  The buffer pool is stored in one of several
            lists.  One such list, the AGE list, holds buffers buffers that have a lower probability of being used.
            New buffer requests are filled from this list first. This variable contains the number of times a buffer
            request was satisfied by a buffer on the AGE list."
    ::= { ioBufferCache 4 }

    numLRUAllocs OBJECT-TYPE
        SYNTAX Counter
        ACCESS read-only
        STATUS mandatory
        DESCRIPTION
            "The total number times an LRU buffer was allocated.  The Least-recently-used list is another list on
            which buffers are stored. They are allocated in a 'least-recently-used' manner.  This variable indicates
            the number of times a buffer was allocated from the LRU list."
    ::= { ioBufferCache 5 }

    minNumBufHdrs OBJECT-TYPE
        SYNTAX Gauge
        ACCESS read-only
        STATUS mandatory
        DESCRIPTION
            "The minimum number of buffer headers to allocated.  These headers are used at the head of each buffer
            hash list.  This value represents an upper bound on the number of separate hash lists the buffer cache
            may use."
    ::= { ioBufferCache 6 }

    numAllocBuf OBJECT-TYPE
        SYNTAX Gauge
        ACCESS read-only
        STATUS mandatory
        DESCRIPTION
            "Number of buffers that are currently allocated.  Monitoring this variable, and others in the
            ioBufferCache group, can help indicate if the system is properly configured or has sufficient memory for
            buffering."
    ::= { ioBufferCache 7 }

    ioBufferHitRate OBJECT-TYPE
        SYNTAX INTEGER (0..100)
        ACCESS read-only
        STATUS mandatory
        DESCRIPTION
            "Percentage of buffer cache lookups that result in a 'hit'.  This value is derived from numBreadHits /
            numBreadRequests."
    ::= { ioBufferCache 8 }


------------------------------------------------------------
--  The Directory Name Lookup Cache (dnlc) Group
------------------------------------------------------------
--  UNIX kernels typically cache directory and file name to vnode mappings.
--  The efficiency and effectiveness of this caching can greatly effect I/O
--  performance. This group contains performance statistics for that cache.

    dnlc OBJECT IDENTIFIER ::= { sysmgmt 11 }

    dnlcHits OBJECT-TYPE
        SYNTAX Counter
        ACCESS read-only
        STATUS mandatory
        DESCRIPTION
            "Total number of DNLC cache hits."
    ::= { dnlc 1 }

    dnlcMisses OBJECT-TYPE
        SYNTAX Counter
        ACCESS read-only
        STATUS mandatory
        DESCRIPTION
            "Total number of DNLC cache misses."
    ::= { dnlc 2 }

    dnlcEnters OBJECT-TYPE
        SYNTAX Counter
        ACCESS read-only
        STATUS mandatory
        DESCRIPTION
            "Total number of DNLC enters done."
    ::= { dnlc 3 }

    dnlcDblEnters OBJECT-TYPE
        SYNTAX Counter
        ACCESS read-only
        STATUS mandatory
        DESCRIPTION
            "Total number enters tried when already cached."
    ::= { dnlc 4 }

    dnlcLongEnters OBJECT-TYPE
        SYNTAX Counter
        ACCESS read-only
        STATUS mandatory
        DESCRIPTION
            "Total number of long names tried to enter."
    ::= { dnlc 5 }

    dnlcLongLooks OBJECT-TYPE
        SYNTAX Counter
        ACCESS read-only
        STATUS mandatory
        DESCRIPTION
            "Total number of long name lookup attempts."
    ::= { dnlc 6 }

    dnlcLruEmpty OBJECT-TYPE
        SYNTAX Counter
        ACCESS read-only
        STATUS mandatory
        DESCRIPTION
            "Total number of least-recently used list empty."
    ::= { dnlc 7 }

    dnlcPurges OBJECT-TYPE
        SYNTAX Counter
        ACCESS read-only
        STATUS mandatory
        DESCRIPTION
            "Total number of purges to the DNLC cache."
    ::= { dnlc 8 }

    dnlcHitRate OBJECT-TYPE
        SYNTAX INTEGER (0..100)
        ACCESS read-only
        STATUS mandatory
        DESCRIPTION
            "Percentage of DNLC cache lookups that result in a 'hit'.  Hit rates less than 90% are considered poor
            and may require kernel tuning.  This value is derived from dnlcHits / dnlcHits + dnlcMisses."
    ::= { dnlc 9 }

    dnlcCacheSize OBJECT-TYPE
        SYNTAX INTEGER 
        ACCESS read-only
        STATUS mandatory
        DESCRIPTION
            "The maximum number of possible entries in the DNLC cache.  If there is no set upper bound, 0 is
            returned."
    ::= { dnlc 10 }


------------------------------------------------------------
--  The AIX Logic Partition (LPAR) Group
------------------------------------------------------------
--  This group contains Physical/Logical CPU statistics for 
--  the logical partition.

    logicalPartition      OBJECT IDENTIFIER ::= { sysmgmt 12 } 
    totalPhysicalCpuStats OBJECT IDENTIFIER ::= { logicalPartition 1 }

    totalPhysicalCpuStatsIdlePercent OBJECT-TYPE
        SYNTAX INTEGER
        ACCESS read-only
        STATUS mandatory
        DESCRIPTION
            "The percentage of time (over the sample period) that the physical processor slice was attribited to
            idle."
    ::= { totalPhysicalCpuStats 1 }

    totalPhysicalCpuStatsUserPercent OBJECT-TYPE
        SYNTAX INTEGER
        ACCESS read-only
        STATUS mandatory
        DESCRIPTION
            "The percentage of time (over the sample period) that the physical processor slice was attribited to
            user."
    ::= { totalPhysicalCpuStats 2 }

    totalPhysicalCpuStatsSysPercent OBJECT-TYPE
        SYNTAX INTEGER
        ACCESS read-only
        STATUS mandatory
        DESCRIPTION
            "The percentage of time (over the sample period) that the physical processor slice was attribited to
            system."
    ::= { totalPhysicalCpuStats 3 }

    totalPhysicalCpuStatsWaitPercent OBJECT-TYPE
        SYNTAX INTEGER
        ACCESS read-only
        STATUS mandatory
        DESCRIPTION
            "The percentage of time (over the sample period) that the physical processor slice was attribited to
            wait."
    ::= { totalPhysicalCpuStats 4 }

    totalPhysicalCpuStatsLastUpdate OBJECT-TYPE
        SYNTAX TimeTicks 
        ACCESS read-only
        STATUS mandatory
        DESCRIPTION
            "The time (in hundredths of a second since the agent was started) that the counters for this CPU were
            last updated. Because these values are cached periodically by the agent, the time of last update is
            important for determining the interval over which CPU mode percentages are calculated."
    ::= { totalPhysicalCpuStats 5 }

    totalLparPC OBJECT-TYPE
        SYNTAX INTEGER
        ACCESS read-only
        STATUS mandatory
        DESCRIPTION
            "Number of physical processors consumed (pc) by the whole LPAR. The value reported is pc multiplied by 100.
             For example, the value 80 represents pc of 0.8"							
    ::= { totalPhysicalCpuStats 6 }

    totalLparEC OBJECT-TYPE
        SYNTAX INTEGER
        ACCESS read-only
        STATUS mandatory
        DESCRIPTION
            "The percentage of entitled capacity  consumed (ec) by the whole LPAR."
    ::= { totalPhysicalCpuStats 7 }

--
--  LPAR group (continued)
--

    numCpuOnline OBJECT-TYPE
        SYNTAX INTEGER 
        ACCESS read-only
        STATUS mandatory
        DESCRIPTION
            "Total number of current online logical CPUs"
    ::= { logicalPartition 2 }

    maxCpuAllocated OBJECT-TYPE
        SYNTAX INTEGER 
        ACCESS read-only
        STATUS mandatory
        DESCRIPTION
            "The total maximum number of virtual CPUs this partition can ever have."
    ::= { logicalPartition 3 }
    
    minCpuAllocated OBJECT-TYPE
        SYNTAX INTEGER 
        ACCESS read-only
        STATUS mandatory
        DESCRIPTION
            "The total minimum number of virtual CPUs this partition must have."
    ::= { logicalPartition 4 }

    currentMemoryOnline OBJECT-TYPE
        SYNTAX Counter
        ACCESS read-only
        STATUS mandatory
        DESCRIPTION
            "The total amount of memory currently online. (MB)" 
    ::= { logicalPartition 5 }

    maxMemoryAllocated OBJECT-TYPE
        SYNTAX Counter
        ACCESS read-only
        STATUS mandatory
        DESCRIPTION
            "The maximum amount of memory this lpar partition can ever have. (MB)"
    ::= { logicalPartition 6 }

    minMemoryAllocated OBJECT-TYPE
        SYNTAX Counter
        ACCESS read-only
        STATUS mandatory
        DESCRIPTION
            "The minimum amount of memory this lpar partition must have. (MB)"
    ::= { logicalPartition 7 }

    currentCpuCapacityEntitled OBJECT-TYPE
        SYNTAX Counter
        ACCESS read-only
        STATUS mandatory
        DESCRIPTION
            "The total number of processor units this lpar partition is entitled."
    ::= { logicalPartition 8 }

    maxCpuCapacityEntitled OBJECT-TYPE
        SYNTAX Counter
        ACCESS read-only
        STATUS mandatory
        DESCRIPTION
            "The maximum number of processor units this partition can ever have." 
    ::= { logicalPartition 9 }

    minCpuCapacityEntitled OBJECT-TYPE
        SYNTAX Counter
        ACCESS read-only
        STATUS mandatory
        DESCRIPTION
            "The minimum number of processor units this partition can must have." 
    ::= { logicalPartition 10 }

    availCpuPoolCapacity OBJECT-TYPE
        SYNTAX INTEGER 
        ACCESS read-only
        STATUS mandatory
        DESCRIPTION
            "The total number of processor units currently unallocated in the shared processor pool this partition
            belongs to."
    ::= { logicalPartition 11 }

    cpuCapacityPriorityWeight OBJECT-TYPE
        SYNTAX INTEGER 
        ACCESS read-only
        STATUS mandatory
        DESCRIPTION
            "Partition priority weight to receive extra capacity."
    ::= { logicalPartition 12 }

    availCpuCapacityPriorityWeight OBJECT-TYPE
        SYNTAX INTEGER 
        ACCESS read-only
        STATUS mandatory
        DESCRIPTION
            "The variable processor capacity weight units currently unallocated in the shared processor pool this
            partition belongs to."
    ::= { logicalPartition 13 }

    physicalCpuUsedPercent OBJECT-TYPE
        SYNTAX INTEGER 
        ACCESS read-only
        STATUS mandatory
        DESCRIPTION
             "The percentage of processor units this partition is entitled.
              Fractional representation relative to whole physical CPUs that these LPARs virtual CPUs equate
              to. This is a function of Entitled Capacity / Online CPUs. Dedicated LPARs would have 100%
              Physical CPU Percentage. A 4-way virtual with Entitled Capacity of 2 processor units would have
              a 50% physical CPU Percentage."
    ::= { logicalPartition 14 }

    numTotalPhysicalCpu OBJECT-TYPE
        SYNTAX INTEGER 
        ACCESS read-only
        STATUS mandatory
        DESCRIPTION
            "The total number of physical CPUs in the system containing this partition."
    ::= { logicalPartition 15 }

    numActivePhysicalCpu OBJECT-TYPE
        SYNTAX INTEGER 
        ACCESS read-only
        STATUS mandatory
        DESCRIPTION
            "The total number of physical CPUs currently active in the system containing this partition."
    ::= { logicalPartition 16 }

    numPhysicalCpuInPool OBJECT-TYPE
        SYNTAX INTEGER 
        ACCESS read-only
        STATUS mandatory
        DESCRIPTION
            "The number of physical CPUs in the available pool in the system containing this partition."
    ::= { logicalPartition 17 }

    voluntaryVirtualContextSwitches OBJECT-TYPE
        SYNTAX INTEGER 
        ACCESS read-only
        STATUS mandatory
        DESCRIPTION
            "The total number voluntary virtual CPU context switches."
    ::= { logicalPartition 18 }

    involuntaryVirtualContextSwitches OBJECT-TYPE
        SYNTAX INTEGER 
        ACCESS read-only
        STATUS mandatory
        DESCRIPTION
            "Ihe total number of involuntary virtual CPU context switches."
    ::= { logicalPartition 19 }

    phantomInterrupts OBJECT-TYPE
        SYNTAX INTEGER 
        ACCESS read-only
        STATUS mandatory
        DESCRIPTION
            "The total number of phantom interrupts ."
    ::= { logicalPartition 20 }

    lparType OBJECT-TYPE
        SYNTAX INTEGER 
        ACCESS read-only
        STATUS mandatory
        DESCRIPTION
            "The partition runs in Dedicated(1) or Shared(2) mode."
    ::= { logicalPartition 21 }

    lparMode OBJECT-TYPE
        SYNTAX INTEGER 
        ACCESS read-only
        STATUS mandatory
        DESCRIPTION
            "The partition is Uncapped(1) or Capped(2)."
    ::= { logicalPartition 22 }

    lparSmtEnabled  OBJECT-TYPE
         SYNTAX INTEGER 
         ACCESS read-only
         STATUS mandatory
         DESCRIPTION
              "Indicates whether simultaneous multi-threading
               is enabled or disabled in the partition.
               SMT disabled(1), SMT enabled(2)."
    ::= { logicalPartition 23 }

    lparDonating  OBJECT-TYPE
         SYNTAX INTEGER 
         ACCESS read-only
         STATUS mandatory
         DESCRIPTION
              "Partition is enabled(1) for donating cycles or disabled(2)"
    ::= { logicalPartition 24 }

    numVirtCPUOnline OBJECT-TYPE
         SYNTAX INTEGER 
         ACCESS read-only
         STATUS mandatory
         DESCRIPTION
              "Number of virtual CPUs currently online."
        ::= { logicalPartition 25 }		
		
     totalLparLogicalCpuUtilPercent OBJECT-TYPE
         SYNTAX INTEGER 
         ACCESS read-only
         STATUS mandatory
         DESCRIPTION
              "Indicates the percentage of logical processor(s) utilization that occurred
               while executing at the user and system level. (lbusy)"
        ::= { logicalPartition 26 }		

------------------------------------------------------------
--  AIX Workload Manager (WLM) Statistics
--  Note that everything under this group is only available
--  when the SystemEDGE agent is running directly on AIX
--  based system and the WLM is enabled
------------------------------------------------------------

    workLoadManager      OBJECT IDENTIFIER ::= { sysmgmt 13 } 

------------------------------------------------------------
--  Table of Work Load Manager (WLM) Classes
------------------------------------------------------------

    wlmClassTable OBJECT-TYPE
        SYNTAX SEQUENCE OF WlmClassEntry
        ACCESS not-accessible
        STATUS mandatory
        DESCRIPTION
            "Table describing defined WLM Classes of the node which the agent resides on.
             Note that the data in this table are only available when the SystemEDGE agent
             is running on an AIX based OS and the Work Load Manager in the OS is enabled."
    ::= { workLoadManager 2 }

    wlmClassEntry OBJECT-TYPE
        SYNTAX WlmClassEntry
        ACCESS not-accessible
        STATUS mandatory
        DESCRIPTION
            "An entry in the table describing WLM Classes."
        INDEX { wlmClassIndex }
    ::= { wlmClassTable 1 }

    WlmClassEntry ::= SEQUENCE {
        wlmClassIndex              INTEGER,
        wlmClassName               SnmpAdminString,
        wlmClassCpuConsumedBp      INTEGER,
        wlmClassCpuConsumedUnitsBp INTEGER,
        wlmClassMemConsumedBp      INTEGER,
        wlmClassMemConsumedKb      INTEGER,
        wlmClassDiskIoConsumedBp   INTEGER
    }

    wlmClassIndex OBJECT-TYPE
        SYNTAX INTEGER (1..2147483647)
        ACCESS read-only
        STATUS mandatory
        DESCRIPTION
            "The instance of the wlmClassEntry object."
    ::= { wlmClassEntry 1 }

    wlmClassName OBJECT-TYPE
        SYNTAX SnmpAdminString
        ACCESS read-only
        STATUS mandatory
        DESCRIPTION
            "The name of the WLM Class."
    ::= { wlmClassEntry 2 }

    wlmClassCpuConsumedBp OBJECT-TYPE
        SYNTAX INTEGER
        ACCESS read-only
        STATUS mandatory
        DESCRIPTION
            "Number of basic points (1/10000) of total available CPU consumed by this WLM Class."
    ::= { wlmClassEntry 3 }

     wlmClassCpuConsumedUnitsBp OBJECT-TYPE
        SYNTAX INTEGER
        ACCESS read-only
        STATUS mandatory
        DESCRIPTION
            "Number of basic points (1/10000) of CPU unit consumed by this WLM Class."
    ::= { wlmClassEntry 4 }

    wlmClassMemConsumedBp OBJECT-TYPE
        SYNTAX INTEGER
        ACCESS read-only
        STATUS mandatory
        DESCRIPTION
            "Number of basic points (1/10000) of total available memory consumed by this WLM Class."
    ::= { wlmClassEntry 5 }

     wlmClassMemConsumedKb OBJECT-TYPE
        SYNTAX INTEGER
        ACCESS read-only
        STATUS mandatory
        DESCRIPTION
            "Number of kB of physical memory consumed by this WLM Class. Only non-pinned memory pages are included."
    ::= { wlmClassEntry 6 }

    wlmClassDiskIoConsumedBp OBJECT-TYPE
        SYNTAX INTEGER
        ACCESS read-only
        STATUS mandatory
        DESCRIPTION
            "Number of basic points (1/10000) of total disk I/O consumed by this WLM Class."
    ::= { wlmClassEntry 7 }

------------------------------------------------------------
--  The Agent Configurations Group
------------------------------------------------------------
--  This group is intended to carry new additional attributes related to agent configuration.

    agtconfig OBJECT IDENTIFIER ::= { unix 2 }


------------------------------------------------------------
--  Trap Community Table
------------------------------------------------------------

    trapCommunityTable OBJECT-TYPE
        SYNTAX SEQUENCE OF TrapCommunityEntry
        ACCESS not-accessible
        STATUS mandatory
        DESCRIPTION
            "The trap community table lists trap destinations for SNMPv1, v2 and v3."
    ::= { agtconfig 1 }

    trapCommunityEntry OBJECT-TYPE
        SYNTAX TrapCommunityEntry
        ACCESS not-accessible
        STATUS mandatory
        DESCRIPTION
            ""
        INDEX { tcIndex }
    ::= { trapCommunityTable 1 }

    TrapCommunityEntry ::= SEQUENCE {
        tcIndex             INTEGER,
        tcSnmpVersion       INTEGER,
        tcMessageType       INTEGER,
        tcDestinationAddr   DisplayString,
        tcDestinationPort   INTEGER,
        tcCommunityName     SnmpAdminString,
        tcContextInfo       DisplayString,
        tcNotifyTimeout     INTEGER,
        tcNotifyRetries     INTEGER,
        tcSourceAddr        DisplayString,
        tcEncoding          DisplayString
    }

    tcIndex OBJECT-TYPE
        SYNTAX INTEGER (1..2147483647)
        ACCESS read-only
        STATUS mandatory
        DESCRIPTION
            "A unique value for the table entry, not necessarily remaining constant between agent restarts."
    ::= { trapCommunityEntry 1 }

    tcSnmpVersion OBJECT-TYPE
        SYNTAX INTEGER {
            v1(1),
            v2(2),
            v3(3)
        }
        ACCESS read-only
        STATUS mandatory
        DESCRIPTION
            "The SNMP version of this trap community entry."
    ::= { trapCommunityEntry 2 }

    tcMessageType OBJECT-TYPE
        SYNTAX INTEGER {
            trap(1),
            notification(2)
        }
        ACCESS read-only
        STATUS mandatory
        DESCRIPTION
            "The message type, i.e. trap (SNMPv1/v2/v3) or notification (SNMPv2/v3)."
    ::= { trapCommunityEntry 3 }

    tcDestinationAddr OBJECT-TYPE
        SYNTAX DisplayString
        ACCESS read-only
        STATUS mandatory
        DESCRIPTION
            "The destination address (IPv4/IPv6 or hostname) to send traps or notifications to."
    ::= { trapCommunityEntry 4 }

    tcDestinationPort OBJECT-TYPE
        SYNTAX INTEGER
        ACCESS read-only
        STATUS mandatory
        DESCRIPTION
            "The destination port to send traps or notifications to."
    ::= { trapCommunityEntry 5 }

    tcCommunityName OBJECT-TYPE
        SYNTAX SnmpAdminString
        ACCESS read-only
        STATUS mandatory
        DESCRIPTION
            "The community name (SNMPv1/v2) or the user name (SNMPv3) to send with traps or notifications."
    ::= { trapCommunityEntry 6 }

    tcContextInfo OBJECT-TYPE
        SYNTAX DisplayString
        ACCESS read-only
        STATUS mandatory
        DESCRIPTION
            "The context information (SNMPv2/v3) to apply. Currently only context '*' is supported."
    ::= { trapCommunityEntry 7 }

    tcNotifyTimeout OBJECT-TYPE
        SYNTAX INTEGER
        ACCESS read-only
        STATUS mandatory
        DESCRIPTION
            "The timeout for a notification (SNMPv2/v3)."
    ::= { trapCommunityEntry 8 }

    tcNotifyRetries OBJECT-TYPE
        SYNTAX INTEGER
        ACCESS read-only
        STATUS mandatory
        DESCRIPTION
            "The number of retries for a notification (SNMPv2/v3)."
    ::= { trapCommunityEntry 9 }

    tcSourceAddr OBJECT-TYPE
        SYNTAX DisplayString
        ACCESS read-only
        STATUS mandatory
        DESCRIPTION
            "The trap source address (IPv4/IPv6 or hostname) to send with traps or notifications."
    ::= { trapCommunityEntry 10 }

    tcEncoding OBJECT-TYPE
        SYNTAX DisplayString
        ACCESS read-only
        STATUS mandatory
        DESCRIPTION
            "The encoding to use when sending trap source addresses (see sysedge.cf configuration file for details)."
    ::= { trapCommunityEntry 11 }


------------------------------------------------------------
--  The NT System Group
------------------------------------------------------------
--  The NT Systems Management branch is intended for the 
--  management and monitoring of systems running MS Windows.

    ntSystem OBJECT IDENTIFIER ::= { nt 1 }

    ntSystemVersion OBJECT-TYPE
        SYNTAX DisplayString
        ACCESS read-only
        STATUS mandatory
        DESCRIPTION
            "The kernel/system version including the release, build, and service-pack numbers."
    ::= { ntSystem 1 }

    ntBuildNumber OBJECT-TYPE
        SYNTAX INTEGER
        ACCESS read-only
        STATUS mandatory
        DESCRIPTION
            "The kernel build number (e.g. 1057)"
    ::= { ntSystem 2 }

    ntServicePackNumber OBJECT-TYPE
        SYNTAX INTEGER
        ACCESS read-only
        STATUS mandatory
        DESCRIPTION
            "The system service-pack number.  If no service-packs have been applied, then 0 is returned."
    ::= { ntSystem 3 }

    ntWorkstationOrServer OBJECT-TYPE
        SYNTAX INTEGER {
            server(1),
            workstation(2),
            unknown(3)
        }
        ACCESS read-only
        STATUS mandatory
        DESCRIPTION
            "The type of NT system -- NT Server or NT Workstation"
    ::= { ntSystem 4 }

    ntfsDisable8dot3NameCreation OBJECT-TYPE
        SYNTAX INTEGER {
            true(1),
            false(2)
        }
        ACCESS read-only
        STATUS mandatory
        DESCRIPTION
            "This object reflects whether the underlying NT system has enabled or disabled the creation of short
            names to correspond with long filenames. For example, if enabled, then NT will create a short filename to
            correspond to a file created with a long filename.  This feature is often enabled if backward
            compatibility with DOS based applications is desired."
    ::= { ntSystem 5 }

    ntWin31FileSystem OBJECT-TYPE
        SYNTAX INTEGER {
            true(1),
            false(2)
        }
        ACCESS read-only
        STATUS mandatory
        DESCRIPTION
            "This object reflects whether the FAT will allow creation, enumeration, opening, or querying of long file
            names, and whether extended time stamp information is stored and reported. Setting to true(1) reverts the
            system back to Win3x semantics."
    ::= { ntSystem 6 }

    ntCriticalSectTimeout OBJECT-TYPE
        SYNTAX INTEGER
        ACCESS read-only
        STATUS mandatory
        DESCRIPTION
            "The deadlock time-out for critical sections."
    ::= { ntSystem 7 }

    ntGlobalFlag OBJECT-TYPE
        SYNTAX INTEGER
        ACCESS read-only
        STATUS mandatory
        DESCRIPTION
            "NT system global hexadecimal flag that controls various internal operations."
    ::= { ntSystem 8 }

    ntIoPageLockLimit OBJECT-TYPE
        SYNTAX INTEGER
        ACCESS read-only
        STATUS mandatory
        DESCRIPTION
            "Specifies the limit of the number of bytes that can be locked for I/O operations.  When 0, the default
            (512k) is used."
    ::= { ntSystem 9 }

    ntLargeSystemCache OBJECT-TYPE
        SYNTAX INTEGER
        ACCESS read-only
        STATUS mandatory
        DESCRIPTION
            "A nonzero value indicates that the system favors the system-cache working set rather than the processes
            working set."
    ::= { ntSystem 10 }

    ntPagedPoolSize OBJECT-TYPE
        SYNTAX INTEGER
        ACCESS read-only
        STATUS mandatory
        DESCRIPTION
            "Size of paged pool in bytes.  When 0, system uses default size (32 MB)."
    ::= { ntSystem 11 }

    ntNonPagedPoolSize OBJECT-TYPE
        SYNTAX INTEGER
        ACCESS read-only
        STATUS mandatory
        DESCRIPTION
            "Size of nonpaged pool in bytes.  When 0, system uses default size (based on physical memory)."
    ::= { ntSystem 12 }

    ntPagingFiles OBJECT-TYPE
        SYNTAX DisplayString
        ACCESS read-only
        STATUS mandatory
        DESCRIPTION
            "List of paging files and their sizes used by the system for paging. For each paging file the description
            includes the file pathname, current size in MB and maximum size in MB."
    ::= { ntSystem 13 }

    ntSystemPages OBJECT-TYPE
        SYNTAX INTEGER
        ACCESS read-only
        STATUS mandatory
        DESCRIPTION
            "This object defines the number of system page table entries reserved for I/O buffers and other
            information."
    ::= { ntSystem 14 }

    ntOptionalSubsystem OBJECT-TYPE
        SYNTAX DisplayString
        ACCESS read-only
        STATUS mandatory
        DESCRIPTION
            "This object lists those subsystems that are only loaded when the user starts a depending application."
    ::= { ntSystem 15 }

    ntCmdlineOptions OBJECT-TYPE
        SYNTAX DisplayString
        ACCESS read-only
        STATUS mandatory
        DESCRIPTION
            "This object lists the command-line that runs when an MS-DOS application is launched under NT."
    ::= { ntSystem 16 }

    ntLPTTimeout OBJECT-TYPE
        SYNTAX INTEGER
        ACCESS read-only
        STATUS mandatory
        DESCRIPTION
            "This object defines how many seconds after the LPT port has been used that Windows NT waits before
            grabbing the port, closing it, and flushing the output.  This value is only needed for MS-DOS based
            applications that use BIOS and do not close the port."
    ::= { ntSystem 17 }

    ntDosMemSize OBJECT-TYPE
        SYNTAX INTEGER
        ACCESS read-only
        STATUS mandatory
        DESCRIPTION
            "Size in MBytes of memory to be given to each individual MS-DOS virtual DOS machine (VDM)."
    ::= { ntSystem 18 }

    ntWowCmdline OBJECT-TYPE
        SYNTAX DisplayString
        ACCESS read-only
        STATUS mandatory
        DESCRIPTION
            "This object defines the command line that runs when a 16-bit Windows-based application is started.  The
            switches instruct NT to start either an MS-DOS VDM or a WOW VDM."
    ::= { ntSystem 19 }

    ntWowSize OBJECT-TYPE
        SYNTAX INTEGER
        ACCESS read-only
        STATUS mandatory
        DESCRIPTION
            "For RISC based computers, this object defines the amount of memory provided in a VDM when a WOW session
            is started.  Value is in MBytes."
    ::= { ntSystem 20 }

    ntUserFullScreen OBJECT-TYPE
        SYNTAX INTEGER {
            windowed(0),
            fullscreen(1)
        }
        ACCESS read-only
        STATUS mandatory
        DESCRIPTION
            "This object indicates whether full-screen or windowed mode is used for the console by default. Valid on
            x86 machines only."
    ::= { ntSystem 21 }

    ntHistoryBufferSize OBJECT-TYPE
        SYNTAX INTEGER
        ACCESS read-only
        STATUS mandatory
        DESCRIPTION
            "This object indicates the number of commands stored in the history buffer by default."
    ::= { ntSystem 22 }

    ntNumberHistoryBuffers OBJECT-TYPE
        SYNTAX INTEGER
        ACCESS read-only
        STATUS mandatory
        DESCRIPTION
            "This object indicates the number of history buffers associated with the console by default."
    ::= { ntSystem 23 }

    ntQuickEdit OBJECT-TYPE
        SYNTAX INTEGER {
            disabled(0),
            enabled(1)
        }
        ACCESS read-only
        STATUS mandatory
        DESCRIPTION
            "This object indicates if Quick-Edit mode is enabled by default."
    ::= { ntSystem 24 }

    ntScreenBufferSize OBJECT-TYPE
        SYNTAX DisplayString
        ACCESS read-only
        STATUS mandatory
        DESCRIPTION
            "Width and height of the default console screen buffer."
    ::= { ntSystem 25 }

    ntWindowSize OBJECT-TYPE
        SYNTAX DisplayString
        ACCESS read-only
        STATUS mandatory
        DESCRIPTION
            "Default width and height of the console window."
    ::= { ntSystem 26 }

    ntWindowsAppInitDLLs OBJECT-TYPE
        SYNTAX DisplayString
        ACCESS read-only
        STATUS mandatory
        DESCRIPTION
            "Lists the DLLs that will be attached to all Windows-based applications."
    ::= { ntSystem 27 }

    ntWindowsDeviceNotSelectedTimeout OBJECT-TYPE
        SYNTAX INTEGER
        ACCESS read-only
        STATUS mandatory
        DESCRIPTION
            "Indicates how much time the system waits for a devices to be switched on."
    ::= { ntSystem 28 }

    ntWindowsSpooler OBJECT-TYPE
        SYNTAX INTEGER {
            true(1),
            false(2)
        }
        ACCESS read-only
        STATUS mandatory
        DESCRIPTION
            "Indicates whether printer output is be sent through Print Manager."
    ::= { ntSystem 29 }

    ntWindowsSwapDisk OBJECT-TYPE
        SYNTAX DisplayString
        ACCESS read-only
        STATUS mandatory
        DESCRIPTION
            "Indicates the name of disk drive and directory to which Windows for MS-DOS in standard-mode swaps
            non-Windows-based applications."
    ::= { ntSystem 30 }

    ntWindowsXmitRetryTimeout OBJECT-TYPE
        SYNTAX INTEGER
        ACCESS read-only
        STATUS mandatory
        DESCRIPTION
            "Transmission retry timeout in seconds used by Print Manager."
    ::= { ntSystem 31 }

    ntSystemRoot OBJECT-TYPE
        SYNTAX DisplayString
        ACCESS read-only
        STATUS mandatory
        DESCRIPTION
            "Drive and directory where the NT system resides."
    ::= { ntSystem 32 }

    ntBuildType OBJECT-TYPE
        SYNTAX INTEGER {
            uniprocessor(1),
            multiprocessor(2),
            unknown(3)
        }
        ACCESS read-only
        STATUS mandatory
        DESCRIPTION
            "System build type (uniprocessor or multiprocessor)."
    ::= { ntSystem 33 }

    ntSysStartOptions OBJECT-TYPE
        SYNTAX DisplayString
        ACCESS read-only
        STATUS mandatory
        DESCRIPTION
            "System start options."
    ::= { ntSystem 34 }

    ntSysBiosDate OBJECT-TYPE
        SYNTAX DisplayString
        ACCESS read-only
        STATUS mandatory
        DESCRIPTION
            "System BIOS date."
    ::= { ntSystem 35 }

    ntSysBiosVersion OBJECT-TYPE
        SYNTAX DisplayString
        ACCESS read-only
        STATUS mandatory
        DESCRIPTION
            "System BIOS version."
    ::= { ntSystem 36 }

    ntVideoResolution OBJECT-TYPE
        SYNTAX DisplayString
        ACCESS read-only
        STATUS mandatory
        DESCRIPTION
            "System video resolution."
    ::= { ntSystem 37 }

    ntCrashDumpEnabled OBJECT-TYPE
        SYNTAX INTEGER {
            disabled(0),
            enabled(1),
            unknown(2)
        }
        ACCESS read-only
        STATUS mandatory
        DESCRIPTION
            "This object indicates whether debugging information is to be written to a log file in the event of a
            system crash."
    ::= { ntSystem 38 }

    ntLogEvent OBJECT-TYPE
        SYNTAX INTEGER {
            disabled(0),
            enabled(1),
            unknown(2)
        }
        ACCESS read-only
        STATUS mandatory
        DESCRIPTION
            "This object indicates whether NTAS logging is enabled or disabled.  If disabled, NT workstation logging
            is used."
    ::= { ntSystem 39 }

    ntOverwrite OBJECT-TYPE
        SYNTAX INTEGER {
            disabled(0),
            enabled(1),
            unknown(2)
        }
        ACCESS read-only
        STATUS mandatory
        DESCRIPTION
            "Indicates whether an existing log file is to be overwritten by the new one.  Enabled for NTAS, disabled
            for NT workstation."
    ::= { ntSystem 40 }

    ntSendAlert OBJECT-TYPE
        SYNTAX INTEGER {
            disabled(0),
            enabled(1),
            unknown(2)
        }
        ACCESS read-only
        STATUS mandatory
        DESCRIPTION
            "Indicates whether an administrative alert is sent; enabled for NTAS, disabled for NT workstation."
    ::= { ntSystem 41}

    ntIsClustered OBJECT-TYPE
        SYNTAX INTEGER {
            true(1),
            false(2)
        }
        ACCESS read-only
        STATUS mandatory
        DESCRIPTION
            "Indicates whether this system is installed and/or running in a windows cluster"
    ::= { ntSystem 42 }

    ntClusterName OBJECT-TYPE
        SYNTAX DisplayString
        ACCESS read-only
        STATUS mandatory
        DESCRIPTION
            "The cluster name that this system is a member of. If the system is not a member of any cluster, then a
            zero-length string is returned.  The cluster name can then be used with DNS or NetBIOS to determine the
            virtual address of the logical cluster."
    ::= { ntSystem 43 }

    ntClusterMembers OBJECT-TYPE
        SYNTAX DisplayString
        ACCESS read-only
        STATUS mandatory
        DESCRIPTION
            "A comma-separated list of nodes that are members of the cluster in which this system is a member. Using
            this information, management software can determine the members of a logical cluster and act accordingly
            to deal with the logical cluster and the individual nodes."
    ::= { ntSystem 44 }

    ntClusterIsActive OBJECT-TYPE
        SYNTAX INTEGER {
            true(1),
            false(2)
        }
        ACCESS read-only
        STATUS mandatory
        DESCRIPTION
            "Indicates whether this system is the primary or active node in the NT cluster.  It does not necessarily
            say if the cluster service(s) are active and up and running per se."
    ::= { ntSystem 45 }

    ntClusterActiveNode OBJECT-TYPE
        SYNTAX DisplayString
        ACCESS read-only
        STATUS mandatory
        DESCRIPTION
            "Indicates which of cluster members is active or primary node.  Active node owns the Cluster Name
            resource object."
    ::= { ntSystem 46 }


------------------------------------------------------------
--  The NT Thread Table
------------------------------------------------------------

    ntThreads OBJECT IDENTIFIER ::= { nt 2 }

    ntThreadTable OBJECT-TYPE
        SYNTAX SEQUENCE OF NtThreadEntry
        ACCESS not-accessible
        STATUS mandatory
        DESCRIPTION
            "Table of NT system threads."
    ::= { ntThreads 1 }

    ntThreadEntry OBJECT-TYPE
        SYNTAX NtThreadEntry
        ACCESS not-accessible
        STATUS mandatory
        DESCRIPTION
            "An entry in the NT system thread table."
        INDEX { ntThreadPID, ntThreadNumber }
    ::= { ntThreadTable 1 }

    NtThreadEntry ::= SEQUENCE {
        ntThreadPID             INTEGER,
        ntThreadNumber          INTEGER,
        ntThreadPrivTime        Counter,
        ntThreadProcTime        Counter,
        ntThreadUserTime        Counter,
        ntThreadContextSwitches Counter,
        ntThreadElapsedTime     INTEGER,
        ntThreadPriorityBase    Gauge,
        ntThreadPriority        Gauge,
        ntThreadWaitReason      INTEGER,
        ntThreadStartAddr       INTEGER,
        ntThreadState           INTEGER,
        ntThreadID              INTEGER
    }

    ntThreadPID OBJECT-TYPE
        SYNTAX INTEGER (0..2147483647)
        ACCESS read-only
        STATUS mandatory
        DESCRIPTION
            "The unique process ID with which this thread is contained and executing within."
    ::= { ntThreadEntry 1 }

    ntThreadNumber OBJECT-TYPE
        SYNTAX INTEGER (0..2147483647)
        ACCESS read-only
        STATUS mandatory
        DESCRIPTION
            "The thread number within a given process. Thread numbers are not unique across all threads in the
            system."
    ::= { ntThreadEntry 2 }

    ntThreadPrivTime OBJECT-TYPE
        SYNTAX Counter 
        ACCESS read-only
        STATUS mandatory
        DESCRIPTION
            "The total elapsed time (in centiseconds) that this thread has executed in Privileged Mode."
    ::= { ntThreadEntry 3 }

    ntThreadProcTime OBJECT-TYPE
        SYNTAX Counter 
        ACCESS read-only
        STATUS mandatory
        DESCRIPTION
            "The total elapsed time (in centiseconds) that this thread has used the processor to execute instructions."
    ::= { ntThreadEntry 4 }

    ntThreadUserTime OBJECT-TYPE
        SYNTAX Counter 
        ACCESS read-only
        STATUS mandatory
        DESCRIPTION
            "Total elapsed time (in centiseconds) that this thread has executed in User Mode."
    ::= { ntThreadEntry 5 }

    ntThreadContextSwitches OBJECT-TYPE
        SYNTAX Counter
        ACCESS read-only
        STATUS mandatory
        DESCRIPTION
            "Number of thread context switches."
    ::= { ntThreadEntry 6 }

    ntThreadElapsedTime OBJECT-TYPE
        SYNTAX INTEGER
        ACCESS read-only
        STATUS mandatory
        DESCRIPTION
            "The total elapsed time (in seconds) this thread has been running."
    ::= { ntThreadEntry 7 }

    ntThreadPriorityBase OBJECT-TYPE
        SYNTAX Gauge
        ACCESS read-only
        STATUS mandatory
        DESCRIPTION
            "The current base priority of this thread.  The system may alter the thread's dynamic priority above,
            below the base priority."
    ::= { ntThreadEntry 8 }

    ntThreadPriority OBJECT-TYPE
        SYNTAX Gauge
        ACCESS read-only
        STATUS mandatory
        DESCRIPTION
            "The current dynamic priority of this thread."
    ::= { ntThreadEntry 9 }

    ntThreadWaitReason OBJECT-TYPE
        SYNTAX INTEGER {
            waitForExecutive(0),
            waitForFreePage(1),
            waitForPageIn(2),
            waitForPoolAlloc(3),
            executionDelay(4),
            suspended(5),
            waitForUserRequest(6),
            waitForExecutive1(7),
            waitForFreePage1(8),
            waitForPageIn1(9),
            waitForPoolAlloc1(10),
            executionDelay1(11),
            suspended1(12),
            waitForUserRequest1(13),
            waitForEventPairHigh(14),
            waitForEventPairLow(15),
            waitForLPCRecv(16),
            waitForLPCReply(17),
            waitForVmem(18),
            waitForPageOut(19)
        }
        ACCESS read-only
        STATUS mandatory
        DESCRIPTION
            "Reason thread is waiting; valid only if ntThreadState is currently wait(5), otherwise undefined."
    ::= { ntThreadEntry 10 }

    ntThreadStartAddr OBJECT-TYPE
        SYNTAX INTEGER
        ACCESS read-only
        STATUS mandatory
        DESCRIPTION
            "The starting virtual address of this thread."
    ::= { ntThreadEntry 11 }

    ntThreadState OBJECT-TYPE
        SYNTAX INTEGER {
            initialized(0),
            ready(1),
            running(2),
            standby(3),
            terminated(4),
            wait(5),
            transition(6),
            unknown(7)
        }
        ACCESS read-only
        STATUS mandatory
        DESCRIPTION
            "The current state of this thread."
    ::= { ntThreadEntry 12 }

    ntThreadID OBJECT-TYPE
        SYNTAX INTEGER
        ACCESS read-only
        STATUS mandatory
        DESCRIPTION
            "The system-wide unique identifier associated with this thread."
    ::= { ntThreadEntry 13 }


------------------------------------------------------------
--  The NT Registry Group
------------------------------------------------------------

    ntRegistry OBJECT IDENTIFIER ::= { nt 3 }

    ntRegistryCurrentSize OBJECT-TYPE
        SYNTAX INTEGER
        ACCESS read-only
        STATUS mandatory
        DESCRIPTION
            "The current size of the registry in MBytes."
    ::= { ntRegistry 1 }

    ntRegistrySizeLimit OBJECT-TYPE
        SYNTAX INTEGER
        ACCESS read-only
        STATUS mandatory
        DESCRIPTION
            "The size limit of the registry in MBytes."
    ::= { ntRegistry 2 }


------------------------------------------------------------
--  The NT Services Group
------------------------------------------------------------

    ntServices OBJECT IDENTIFIER ::= { nt 4 }

    ntServiceTable OBJECT-TYPE
        SYNTAX SEQUENCE OF NtServiceEntry
        ACCESS not-accessible
        STATUS mandatory
        DESCRIPTION
            "Table of NT system services"
    ::= { ntServices 1 }

    ntServiceEntry OBJECT-TYPE
        SYNTAX NtServiceEntry
        ACCESS not-accessible
        STATUS mandatory
        DESCRIPTION
            "An entry in the NT system service table."
        INDEX { ntServiceIndex }
    ::= { ntServiceTable 1 }

    NtServiceEntry ::= SEQUENCE {
        ntServiceIndex      INTEGER,
        ntServiceName       SnmpAdminString,
        ntServicePathName   SnmpAdminString,
        ntServiceStartType  INTEGER,
        ntServiceParameters SnmpAdminString,
        ntServiceState      INTEGER,
        ntServiceObjectName SnmpAdminString
    }

    ntServiceIndex OBJECT-TYPE
        SYNTAX INTEGER (1..2147483647)
        ACCESS read-only
        STATUS mandatory
        DESCRIPTION
            "The index of this system service."
    ::= { ntServiceEntry 1 }

    ntServiceName OBJECT-TYPE
        SYNTAX SnmpAdminString
        ACCESS read-only
        STATUS mandatory
        DESCRIPTION
            "The system service name."
    ::= { ntServiceEntry 2 }

    ntServicePathName OBJECT-TYPE
        SYNTAX SnmpAdminString
        ACCESS read-only
        STATUS mandatory
        DESCRIPTION
            "The system service path."
    ::= { ntServiceEntry 3 }

    ntServiceStartType OBJECT-TYPE
        SYNTAX INTEGER {
            automatic(1),
            manual(2),
            disabled(3),
            other(4)
        }
        ACCESS read-write
        STATUS mandatory
        DESCRIPTION
            "The manner in which the service is started; automatic(1) implies that the system starts the service at
            boot time while manual(2) implies that the service must be started by hand by an administrator.
            Disabled(3) indicates that the service cannot be started."
    ::= { ntServiceEntry 4 }

    ntServiceParameters OBJECT-TYPE
        SYNTAX SnmpAdminString
        ACCESS read-only
        STATUS mandatory
        DESCRIPTION
            "The parameters passed to this service when it is invoked."
    ::= { ntServiceEntry 5 }

    ntServiceState OBJECT-TYPE
        SYNTAX INTEGER {
            running(1),
            notRunning(2),
            paused(3),
            other(4)
        }
        ACCESS read-write
        STATUS mandatory
        DESCRIPTION
            "The current state of the system service."
    ::= { ntServiceEntry 6 }

    ntServiceObjectName OBJECT-TYPE
        SYNTAX SnmpAdminString
        ACCESS read-only
        STATUS mandatory
        DESCRIPTION
            "The object name for this service. This indicates the user name the service is currently running as."
    ::= { ntServiceEntry 7 }


------------------------------------------------------------
--  The NT Performance Groups
------------------------------------------------------------
-- Various NT-specific performance groups are located under the
-- ntPerformance branch

    ntPerformance OBJECT IDENTIFIER ::= { nt 5 }


------------------------------------------------------------
--  The NT System Performance Group
------------------------------------------------------------

    ntSystemPerf OBJECT IDENTIFIER ::= { ntPerformance 1 }

    ntTotalPrivTime OBJECT-TYPE
        SYNTAX Counter
        ACCESS read-only
        STATUS mandatory
        DESCRIPTION
            "Running counter of centiseconds spent by the system processor(s) in Privileged mode."
    ::= { ntSystemPerf 1 }

    ntTotalProcessorTime OBJECT-TYPE
        SYNTAX Counter
        ACCESS read-only
        STATUS mandatory
        DESCRIPTION
            "Running counter of centiseconds spent by the system processor(s) running Idle threads. Note that this is
            actually the inverse of the total processor time."
    ::= { ntSystemPerf 2 }

    ntTotalUserTime OBJECT-TYPE
        SYNTAX Counter
        ACCESS read-only
        STATUS mandatory
        DESCRIPTION
            "Running counter of centiseconds spent by the system processor(s) running User mode."
    ::= { ntSystemPerf 3 }

    ntAlignFixups OBJECT-TYPE
        SYNTAX Counter
        ACCESS read-only
        STATUS mandatory
        DESCRIPTION
            "The number of alignment faults fixed by the system."
    ::= { ntSystemPerf 4 }

    ntContextSwitches OBJECT-TYPE
        SYNTAX Counter
        ACCESS read-only
        STATUS mandatory
        DESCRIPTION
            "The total number of context switches that have occurred since the kernel was last initialized.  A
            context switch occurs each time a thread gives up the CPU and another takes its place.  This counter
            reflects the level of system activity; a high rate of context switching is indicative of the system load.
            This counter is equivalent (for NT systems) to the UNIX counter numSwitches(kernelperf.14)"
    ::= { ntSystemPerf 5 }

    ntExceptionDispatches OBJECT-TYPE
        SYNTAX Counter
        ACCESS read-only
        STATUS mandatory
        DESCRIPTION
            "The total number of exceptions dispacted by the system since it was initialized."
    ::= { ntSystemPerf 6 }

    ntFileCtrlKBytes OBJECT-TYPE
        SYNTAX Counter
        ACCESS read-only
        STATUS mandatory
        DESCRIPTION
            "An aggregate of KBytes transferred for all file system operations that are neither reads or writes (e.g.
            file system control requests or device control requests)."
    ::= { ntSystemPerf 7 }

    ntFileCtrlOps OBJECT-TYPE
        SYNTAX Counter
        ACCESS read-only
        STATUS mandatory
        DESCRIPTION
            "Aggregate counter of all file system operations that are neither reads nor writes."
    ::= { ntSystemPerf 8 }

    ntFileDataOps OBJECT-TYPE
        SYNTAX Counter
        ACCESS read-only
        STATUS mandatory
        DESCRIPTION
            "Total number of read and write operations to file system devices issued by the system since system
            initialization."
    ::= { ntSystemPerf 9 }

    ntReadKBytes OBJECT-TYPE
        SYNTAX Counter
        ACCESS read-only
        STATUS mandatory
        DESCRIPTION
            "Aggregate number of KBytes transferred for all the file system read operations on this system since
            system initialization."
    ::= { ntSystemPerf 10 }

    ntReadOps OBJECT-TYPE
        SYNTAX Counter
        ACCESS read-only
        STATUS mandatory
        DESCRIPTION
            "Aggregate of all the file system read operations on this system since system initialization."
    ::= { ntSystemPerf 11 }

    ntWriteKBytes OBJECT-TYPE
        SYNTAX Counter
        ACCESS read-only
        STATUS mandatory
        DESCRIPTION
            "Aggregate number of KBytes transferred for all the file system write operations on this system since
            system initialization."
    ::= { ntSystemPerf 12 }

    ntWriteOps OBJECT-TYPE
        SYNTAX Counter
        ACCESS read-only
        STATUS mandatory
        DESCRIPTION
            "Aggregate number of all the file system write operations on this system since system initialization."
    ::= { ntSystemPerf 13 }

    ntFloatEmuls OBJECT-TYPE
        SYNTAX Counter
        ACCESS read-only
        STATUS mandatory
        DESCRIPTION
            "Number of floating emulations performed by the system."
    ::= { ntSystemPerf 14 }

    ntRunQLen OBJECT-TYPE
        SYNTAX Gauge
        ACCESS read-only
        STATUS mandatory
        DESCRIPTION
            "Instantaneous processor queue length in threads and is equivalent to runQLen(kernelperf.4)"
    ::= { ntSystemPerf 15 }

    ntSystemCalls OBJECT-TYPE
        SYNTAX Counter
        ACCESS read-only
        STATUS mandatory
        DESCRIPTION
            "The number of calls to system service routines. This object is equivalent to numSyscalls(kernelperf.16)"
    ::= { ntSystemPerf 16 }

    ntInterrupts OBJECT-TYPE
        SYNTAX Counter
        ACCESS read-only
        STATUS mandatory
        DESCRIPTION
            "The number of hardware interrupts that have occurred.  This object is equivalent to
            numInterrupts(kernelperf.17)"
    ::= { ntSystemPerf 17 }


------------------------------------------------------------
--  The NT Cache Performance Group
------------------------------------------------------------

    ntCachePerf OBJECT IDENTIFIER ::= { ntPerformance 2 }

    ntAsyncCopyReads OBJECT-TYPE
        SYNTAX Counter
        ACCESS read-only
        STATUS mandatory
        DESCRIPTION
            "Number of async reads from Cache pages involving a memory copy of the data from the Cache to the
            application's buffer."
    ::= { ntCachePerf 1 }

    ntAsyncDataMaps OBJECT-TYPE
        SYNTAX Counter
        ACCESS read-only
        STATUS mandatory
        DESCRIPTION
            "Number of async data maps of file pages into the Cache."
    ::= { ntCachePerf 2 }

    ntAsyncFastReads OBJECT-TYPE
        SYNTAX Counter
        ACCESS read-only
        STATUS mandatory
        DESCRIPTION
            "Number of direct-to-Cache async read operations."
    ::= { ntCachePerf 3 }

    ntAsyncMDLReads OBJECT-TYPE
        SYNTAX Counter
        ACCESS read-only
        STATUS mandatory
        DESCRIPTION
            "Number of async memory descriptor list (MDL) reads from the Cache.  The MDL contains the physical
            address of each page in the transfer thus permitting DMA of the pages."
    ::= { ntCachePerf 4 }

    ntAsyncPinReads OBJECT-TYPE
        SYNTAX Counter
        ACCESS read-only
        STATUS mandatory
        DESCRIPTION
            "Number of async reads from the Cache in preparation to writing the data back to disk. Pages read in this
            fashion are pinned in memory at the completion of the read."
    ::= { ntCachePerf 5 }

    ntCopyReadHits OBJECT-TYPE
        SYNTAX Counter
        ACCESS read-only
        STATUS mandatory
        DESCRIPTION
            "Number of Cache Copy Read requests that hit the cache and did not require a disk read."
    ::= { ntCachePerf 6 }

    ntCopyReads OBJECT-TYPE
        SYNTAX Counter
        ACCESS read-only
        STATUS mandatory
        DESCRIPTION
            "The number of reads from Cache pages that involved a memory copy of data from the Cache to the
            application's buffer."
    ::= { ntCachePerf 7 }

    ntDataFlushPages OBJECT-TYPE
        SYNTAX Counter
        ACCESS read-only
        STATUS mandatory
        DESCRIPTION
            "Number of pages of the Cache flushed to disk as a result of a flush request or to satisfy a
            write-through request."
    ::= { ntCachePerf 8 }

    ntDataFlushes OBJECT-TYPE
        SYNTAX Counter
        ACCESS read-only
        STATUS mandatory
        DESCRIPTION
            "Number of Cache data flush operations."
    ::= { ntCachePerf 9 }

    ntDataMapHits OBJECT-TYPE
        SYNTAX Counter
        ACCESS read-only
        STATUS mandatory
        DESCRIPTION
            "Numberof data maps in the Cache that could be resolved without retrieval from disk."
    ::= { ntCachePerf 10 }

    ntDataMapPins OBJECT-TYPE
        SYNTAX Counter
        ACCESS read-only
        STATUS mandatory
        DESCRIPTION
            "Number of data maps in the Cache that resulted in pinning a page in main memory."
    ::= { ntCachePerf 11 }

    ntDataMaps OBJECT-TYPE
        SYNTAX Counter
        ACCESS read-only
        STATUS mandatory
        DESCRIPTION
            "Number of times a file system such as NTFS or HPFS has mapped a page of a file into the Cache to read
            the page."
    ::= { ntCachePerf 12 }

    ntFastReadNotPossible OBJECT-TYPE
        SYNTAX Counter
        ACCESS read-only
        STATUS mandatory
        DESCRIPTION
            "Number of times an API function call to bypass the file system to get at Cache data could not be honored
            without invoking the file system after all."
    ::= { ntCachePerf 13 }

    ntFastReadResourceMisses OBJECT-TYPE
        SYNTAX Counter
        ACCESS read-only
        STATUS mandatory
        DESCRIPTION
            "Number of Cache misses necessitated by the lack of available resources to satisfy the request."
    ::= { ntCachePerf 14 }

    ntFastReads OBJECT-TYPE
        SYNTAX Counter
        ACCESS read-only
        STATUS mandatory
        DESCRIPTION
            "Number of reads from Cache pages that bypass installed file systems and read from the Cache directly."
    ::= { ntCachePerf 15 }

    ntLazyWriteFlushes OBJECT-TYPE
        SYNTAX Counter
        ACCESS read-only
        STATUS mandatory
        DESCRIPTION
            "The number of times the Cache's Lazy Write thread has written to disk."
    ::= { ntCachePerf 16 }

    ntLazyWritePages OBJECT-TYPE
        SYNTAX Counter
        ACCESS read-only
        STATUS mandatory
        DESCRIPTION
            "Number of pages the Cache's Lazy Write thread has written to disk.  Lazy Writing is the process of
            updating the disk after the page has been changed in memory so the application making the change to the
            file does not have to wait for the disk write to complete before proceeding."
    ::= { ntCachePerf 17 }

    ntMDLReadHits OBJECT-TYPE
        SYNTAX Counter
        ACCESS read-only
        STATUS mandatory
        DESCRIPTION
            "Number of Cache Memory Descriptor List (MDL) read requests that hit the Cache."
    ::= { ntCachePerf 18 }

    ntMDLReads OBJECT-TYPE
        SYNTAX Counter
        ACCESS read-only
        STATUS mandatory
        DESCRIPTION
            "Number of MDL Cache reads."
    ::= { ntCachePerf 19 }

    ntPinReadHits OBJECT-TYPE
        SYNTAX Counter
        ACCESS read-only
        STATUS mandatory
        DESCRIPTION
            "Number Cache Pin Read requests that hit the Cache."
    ::= { ntCachePerf 20 }

    ntPinReads OBJECT-TYPE
        SYNTAX Counter
        ACCESS read-only
        STATUS mandatory
        DESCRIPTION
            "Number of pages read from the Cache that have been pinned in memory."
    ::= { ntCachePerf 21 }

    ntSyncCopyReads OBJECT-TYPE
        SYNTAX Counter
        ACCESS read-only
        STATUS mandatory
        DESCRIPTION
            "Number of reads from Cache pages that wait for the copy operation to complete before proceeding."
    ::= { ntCachePerf 22 }

    ntSyncDataMaps OBJECT-TYPE
        SYNTAX Counter
        ACCESS read-only
        STATUS mandatory
        DESCRIPTION
            "Number of times that a file system such as NTFS or HPFS maps a page of a file into the Cache to read the
            page."
    ::= { ntCachePerf 23 }

    ntSyncFastReads OBJECT-TYPE
        SYNTAX Counter
        ACCESS read-only
        STATUS mandatory
        DESCRIPTION
            "Number of sync reads from Cache pages that bypass the installed file system and retrieve the data
            directly from the Cache."
    ::= { ntCachePerf 24 }

    ntSyncMDLReads OBJECT-TYPE
        SYNTAX Counter
        ACCESS read-only
        STATUS mandatory
        DESCRIPTION
            "Number of reads from Cache pages that use a Memory Descriptor List (MDL) to access the pages."
    ::= { ntCachePerf 25 }

    ntSyncPinReads OBJECT-TYPE
        SYNTAX Counter
        ACCESS read-only
        STATUS mandatory
        DESCRIPTION
            "Number of page reads that have resulted in the page being pinned in memory."
    ::= { ntCachePerf 26 }


------------------------------------------------------------
--  The NT Memory Performance Group
------------------------------------------------------------

    ntMemoryPerf OBJECT IDENTIFIER ::= { ntPerformance 3 }

    ntAvailKBytes OBJECT-TYPE
        SYNTAX Gauge
        ACCESS read-only
        STATUS mandatory
        DESCRIPTION
            "Number of KBytes of virtual memory currently on the Zeroed, Free, and Standby lists.  Zeroed and free
            memory is ready for use.  Standby memory is memory removed from a process's working set but still
            available."
    ::= { ntMemoryPerf 1 }

    ntCacheKBytes OBJECT-TYPE
        SYNTAX Gauge
        ACCESS read-only
        STATUS mandatory
        DESCRIPTION
            "Number of KBytes currently in use by the system Cache."
    ::= { ntMemoryPerf 2 }

    ntCacheKBytesPeak OBJECT-TYPE
        SYNTAX INTEGER
        ACCESS read-only
        STATUS mandatory
        DESCRIPTION
            "Maximum number of KBytes used by the system Cache."
    ::= { ntMemoryPerf 3 }

    ntCacheFaults OBJECT-TYPE
        SYNTAX Counter
        ACCESS read-only
        STATUS mandatory
        DESCRIPTION
            "Number of Cache faults whereby memory had to be located elsewhere."
    ::= { ntMemoryPerf 4 }

    ntCommitLimit OBJECT-TYPE
        SYNTAX INTEGER
        ACCESS read-only
        STATUS mandatory
        DESCRIPTION
            "Size in KBytes of virtual memory that can be committed without having to expand the paging file(s)."
    ::= { ntMemoryPerf 5 }

    ntCommittedKBytes OBJECT-TYPE
        SYNTAX Gauge
        ACCESS read-only
        STATUS mandatory
        DESCRIPTION
            "Number of KBytes of virtual memory that have been committed."
    ::= { ntMemoryPerf 6 }

    ntDemandZeroFaults OBJECT-TYPE
        SYNTAX Counter
        ACCESS read-only
        STATUS mandatory
        DESCRIPTION
            "Number of page faults for pages that must be filled with zeros before fault is satisifed."
    ::= { ntMemoryPerf 7 }

    ntFreeSysPageTableEntries OBJECT-TYPE
        SYNTAX Gauge
        ACCESS read-only
        STATUS mandatory
        DESCRIPTION
            "Number of Page Table entries not currently in use by the system."
    ::= { ntMemoryPerf 8 }

    ntPageFaults OBJECT-TYPE
        SYNTAX Counter
        ACCESS read-only
        STATUS mandatory
        DESCRIPTION
            "Number of page faults in the processor and is equivalent to numPageFaults(kernelperf.25)"
    ::= { ntMemoryPerf 9 }

    ntPageReads OBJECT-TYPE
        SYNTAX Counter
        ACCESS read-only
        STATUS mandatory
        DESCRIPTION
            "Number of times the disk was read to retrieve pages of virtual memory."
    ::= { ntMemoryPerf 10 }

    ntPageWrites OBJECT-TYPE
        SYNTAX Counter
        ACCESS read-only
        STATUS mandatory
        DESCRIPTION
            "Number of times pages have been written to disk."
    ::= { ntMemoryPerf 11 }

    ntPagesInput OBJECT-TYPE
        SYNTAX Counter
        ACCESS read-only
        STATUS mandatory
        DESCRIPTION
            "Number of pages read from disk to resolve memory references and is equivalent to numPageIns
            (kernelperf.22)"
    ::= { ntMemoryPerf 12 }

    ntPagesOutput OBJECT-TYPE
        SYNTAX Counter
        ACCESS read-only
        STATUS mandatory
        DESCRIPTION
            "Number of pages written to disk because the pages were modified and is equivalent to numPageOuts
            (kernelperf.23)."
    ::= { ntMemoryPerf 13 }

    ntPages OBJECT-TYPE
        SYNTAX Counter
        ACCESS read-only
        STATUS mandatory
        DESCRIPTION
            "Number of pages read or written from/to disk and is a sum of PagesInput(12) and PagesOutput(13)."
    ::= { ntMemoryPerf 14 }

    ntPoolNonPagedAllocs OBJECT-TYPE
        SYNTAX Gauge
        ACCESS read-only
        STATUS mandatory
        DESCRIPTION
            "Number of calls to allocate space in the system Nonpaged pool."
    ::= { ntMemoryPerf 15 }

    ntPoolNonPagedKBytes OBJECT-TYPE
        SYNTAX Gauge
        ACCESS read-only
        STATUS mandatory
        DESCRIPTION
            "Number of KBytes in the Nonpaged pool which is a system memory area where space is acquired by operating
            systems facilities as they accomplish their tasks.  These pages cannot be paged out to disk."
    ::= { ntMemoryPerf 16 }

    ntPoolPagedAllocs OBJECT-TYPE
        SYNTAX Gauge
        ACCESS read-only
        STATUS mandatory
        DESCRIPTION
            "Number of calls to allocate space in the system Paged Pool.  Paged Pool is a system memory area where
            space is acquired by operating systems facilities as they accomplish their tasks.  Paged Pool bytes may
            be paged out to disk when not ACCESSed by the system for sustained periods of time."
    ::= { ntMemoryPerf 17 }

    ntPoolPagedKBytes OBJECT-TYPE
        SYNTAX Gauge
        ACCESS read-only
        STATUS mandatory
        DESCRIPTION
            "Number of KBytes in the Paged Pool."
    ::= { ntMemoryPerf 18 }

    ntPagedResidentKBytes OBJECT-TYPE
        SYNTAX Gauge
        ACCESS read-only
        STATUS mandatory
        DESCRIPTION
            "Size of paged Pool resident in core memory in KBytes."
    ::= { ntMemoryPerf 19 }

    ntSysCacheResidentKBytes OBJECT-TYPE
        SYNTAX Gauge
        ACCESS read-only
        STATUS mandatory
        DESCRIPTION
            "Number of KBytes currently resident in the global disk cache."
    ::= { ntMemoryPerf 20 }

    ntSysCodeResidentKBytes OBJECT-TYPE
        SYNTAX Gauge
        ACCESS read-only
        STATUS mandatory
        DESCRIPTION
            "Number of KBytes of System Code Total Bytes currently resident in core memory.  This is the code working
            set of the pagable executive."
    ::= { ntMemoryPerf 21 }

    ntSysCodeTotalKBytes OBJECT-TYPE
        SYNTAX Gauge
        ACCESS read-only
        STATUS mandatory
        DESCRIPTION
            "Total number of KBytes of pageable pages in ntoskrnl.exe, hal.dll, and the boot drivers and file systems
            loaded by ntldr/osloader."
    ::= { ntMemoryPerf 22 }

    ntSysDriverResidentKBytes OBJECT-TYPE
        SYNTAX Gauge
        ACCESS read-only
        STATUS mandatory
        DESCRIPTION
            "Number of KBytes of System Driver Total KBytes currently resident in core memory.  The number is the
            code working set of the pagable drivers."
    ::= { ntMemoryPerf 23 }

    ntSysDriverTotalKBytes OBJECT-TYPE
        SYNTAX Gauge
        ACCESS read-only
        STATUS mandatory
        DESCRIPTION
            "Number of KBytes of pageable pages in all other loaded device drivers."
    ::= { ntMemoryPerf 24 }

    ntTransitionFaults OBJECT-TYPE
        SYNTAX Counter
        ACCESS read-only
        STATUS mandatory
        DESCRIPTION
            "Number of page faults resolved by recovering pages that were in transition to disk at time of page
            fault."
    ::= { ntMemoryPerf 25 }

    ntWriteCopies OBJECT-TYPE
        SYNTAX Counter
        ACCESS read-only
        STATUS mandatory
        DESCRIPTION
            "Number of page faults that have been satisfied by making a copy of a page when an attempt to write the
            page was made while it was shared."
    ::= { ntMemoryPerf 26 }


------------------------------------------------------------
--  The NT Paging-File Performance Group
------------------------------------------------------------

    ntPageFilePerf OBJECT IDENTIFIER ::= { ntPerformance 4 }

    ntPageFileUsage OBJECT-TYPE
        SYNTAX INTEGER (0..100)
        ACCESS read-only
        STATUS mandatory
        DESCRIPTION
            "The percentage of the page file(s) used."
    ::= { ntPageFilePerf 1 }

    ntPageFilePeakUsage OBJECT-TYPE
        SYNTAX INTEGER (0..100)
        ACCESS read-only
        STATUS mandatory
        DESCRIPTION
            "The peak usage of the page file(s)."
    ::= { ntPageFilePerf 2 }


------------------------------------------------------------
--  The NT Event Log Monitoring Group
------------------------------------------------------------
--  This group provides access to the agent's NT Event Log monitoring
--  capabilities.  Via the ntEventMonTable, managers can specify 
--  that the agent monitor certain event logs for certain patterns
--  or regular expressions.  When a match has occurred, the agent
--  sends a Trap to appropriate managers.  Entries can be placed
--  in the ntEventMonTable via two methods: through entries in the
--  agent configuration file (sysedge.cf) or via the SNMP.

    ntEvents OBJECT IDENTIFIER ::= { nt 6 }

    ntEventApplicationCount OBJECT-TYPE
        SYNTAX Counter
        ACCESS read-only
        STATUS mandatory
        DESCRIPTION
            "The number of events in the Application event log."
    ::= { ntEvents 1 }

    ntEventSecurityCount OBJECT-TYPE
        SYNTAX Counter
        ACCESS read-only
        STATUS mandatory
        DESCRIPTION
            "The number of events in the Security event log."
    ::= { ntEvents 2 }

    ntEventSystemCount OBJECT-TYPE
        SYNTAX Counter
        ACCESS read-only
        STATUS mandatory
        DESCRIPTION
            "The number of events in the System event log."
    ::= { ntEvents 3 }

--  ntEventMonTable OBJECT-TYPE
--      defined below
--  ::= { ntEvents 4 }

    ntEventApplicationMaxSize OBJECT-TYPE
        SYNTAX Gauge
        ACCESS read-only
        STATUS mandatory
        DESCRIPTION
            "The maximum size (in Bytes) of the Application event log."
    ::= { ntEvents 5 }

    ntEventApplicationRetention OBJECT-TYPE
        SYNTAX Gauge
        ACCESS read-only
        STATUS mandatory
        DESCRIPTION
            "The retention flag for the Application event log. This flag indicates the settings for the Event Log
            Wrapping settings."
    ::= { ntEvents 6 }

    ntEventSecurityMaxSize OBJECT-TYPE
        SYNTAX Gauge
        ACCESS read-only
        STATUS mandatory
        DESCRIPTION
            "The maximum size (in Bytes) of the Security event log."
    ::= { ntEvents 7 }

    ntEventSecurityRetention OBJECT-TYPE
        SYNTAX Gauge
        ACCESS read-only
        STATUS mandatory
        DESCRIPTION
            "The retention flag for the Security event log. This flag indicates the settings for the Event Log
            Wrapping settings."
    ::= { ntEvents 8 }

    ntEventSystemMaxSize OBJECT-TYPE
        SYNTAX Gauge
        ACCESS read-only
        STATUS mandatory
        DESCRIPTION
            "The maximum size (in Bytes) of the System event log."
    ::= { ntEvents 9 }

    ntEventSystemRetention OBJECT-TYPE
        SYNTAX Gauge
        ACCESS read-only
        STATUS mandatory
        DESCRIPTION
            "The retention flag for the System event log. This flag indicates the settings for the Event Log Wrapping
            settings."
    ::= { ntEvents 10 }

    ntEventUnusedIndex OBJECT-TYPE
        SYNTAX INTEGER (1..2147483647)
        ACCESS read-only
        STATUS mandatory
        DESCRIPTION
            "An SNMP Get of this MIB object returns an un-used NT event monitor Table index number.  It can be used
            for NT event monitor table row creation optimization."
    ::= { ntEvents 11 }

    ntEventMatchDescr OBJECT-TYPE
        SYNTAX SnmpAdminString
        ACCESS read-write
        STATUS mandatory
        DESCRIPTION
            "This MIB object, when used in conjunction with ntEventMatchIndex can be used to quickly determine the
            index number corresponding to a particular entry description.  SNMP Set'ing a description to this MIB
            object causes the agent to search through entries in the NT event monitor table and place the index value
            of the last entry whose description matches, in the ntEventMatchIndex MIB object."
    ::= { ntEvents 12 }

    ntEventMatchIndex OBJECT-TYPE
        SYNTAX INTEGER (1..2147483647)
        ACCESS read-only
        STATUS mandatory
        DESCRIPTION
            "See description for ntEventMatchDescr."
    ::= { ntEvents 13 }


------------------------------------------------------------
--  The NT Event Log Monitoring Table
------------------------------------------------------------

    ntEventMonTable OBJECT-TYPE
        SYNTAX SEQUENCE OF NtEventMonEntry
        ACCESS not-accessible
        STATUS mandatory
        DESCRIPTION
            "Table containing NT Event Log monitor entries; each entry specifies an Event Log and regular expression.
            The agent periodically stats the event logs to see if they have been updated.  If updated, the agent
            scans the new entries for the regular expressions.  When an entry is found that matches the regular
            expressions, a trap PDU is sent to appropriate managers."
    ::= { ntEvents 4 }

    ntEventMonEntry OBJECT-TYPE
        SYNTAX NtEventMonEntry
        ACCESS not-accessible
        STATUS mandatory
        DESCRIPTION
            "An entry in the ntEventMonTable."
        INDEX { ntEventMonIndex }
    ::= { ntEventMonTable 1 }

    NtEventMonEntry ::= SEQUENCE {
        ntEventMonIndex         INTEGER,
        ntEventMonLog           INTEGER,
        ntEventMonTime          TimeTicks,
        ntEventMonTraps         INTEGER,
        ntEventMonTypeLastMatch INTEGER,
        ntEventMonTypeFilter    INTEGER,
        ntEventMonSrcLastMatch  SnmpAdminString,
        ntEventMonSrcFilter     SnmpAdminString,
        ntEventMonDescLastMatch SnmpAdminString,
        ntEventMonDescFilter    SnmpAdminString,
        ntEventMonStatus        INTEGER,
        ntEventMonDescr         SnmpAdminString,
        ntEventMonAction        SnmpAdminString,
        ntEventMonFlags         INTEGER,
        ntEventMonMatches       Counter,
        ntEventMonSeverity      INTEGER
    }

    ntEventMonIndex OBJECT-TYPE
        SYNTAX INTEGER (1..2147483647)
        ACCESS read-only
        STATUS mandatory
        DESCRIPTION
            "An index that uniquely identifies an entry in the ntEventMonTable."
    ::= { ntEventMonEntry 1 } 

    ntEventMonLog OBJECT-TYPE
        SYNTAX INTEGER {
            application(1),
            security(2),
            system(3),
            dnsServer(4),      -- in 4.1+
            dirService(5),     -- in 4.1+
            fileRepService(6)  -- in 4.1+
        }
        ACCESS read-write
        STATUS mandatory
        DESCRIPTION
            "The number identifying the NT event log to scan for pattern matches. Possible values are Application(1),
            Security(2), and System(3).  On Win2k and higher, dnsServer(4), dirService(5), and fileRepService(6) are
            also possibly valid.  Not all win2k+ systems have these event logs."
    ::= { ntEventMonEntry 2 } 

    ntEventMonTime OBJECT-TYPE
        SYNTAX TimeTicks
        ACCESS read-only
        STATUS mandatory
        DESCRIPTION
            "The time when the agent last sent a trap for this monitor entry.
            This relative time (R) is given in hundredths of a second since the agent was started. It can be
            converted into an absolute time (A) using sysUpTime (from MIB-II) and hrSystemDate (from HR-MIB).
            sysUpTime (S) is the elapsed time (in hundredths of a second) since the agent was started.
            hrSysDate (H) is the current absolute date and time (in DateAndTime format) and must be converted
            to Unix Time format (seconds elapsed since 01.01.1970). Finally calculate: A = H - S/100 + R/100"
    ::= { ntEventMonEntry 3 } 

    ntEventMonTraps OBJECT-TYPE
        SYNTAX INTEGER
        ACCESS read-only
        STATUS mandatory
        DESCRIPTION
            "The number of traps sent for this monitor entry. One trap is sent for each match detected."
    ::= { ntEventMonEntry 4 } 

    ntEventMonTypeLastMatch OBJECT-TYPE
        SYNTAX INTEGER {
            error(1),
            warning(2),
            information(3),
            success(4),
            failure(5),
            noMatch(6)
        }
        ACCESS read-only
        STATUS mandatory
        DESCRIPTION
            "The number identifying the event type of the last event that matched the search criteria. Types 1
            through 5 are defined by Windows NT. Type noMatch(6) indicates that there has not yet been a matching
            event for this monitoring entry."
    ::= { ntEventMonEntry 5 } 

    ntEventMonTypeFilter OBJECT-TYPE
        SYNTAX INTEGER {
            error(1),
            warning(2),
            information(3),
            success(4),
            failure(5),
            all(6)
        }
        ACCESS read-write
        STATUS mandatory
        DESCRIPTION
            "The number identifying the event type to match. Types 1 through 5 are defined by Windows NT. Type all(6)
            indicates that all event types will match."
    ::= { ntEventMonEntry 6 } 

    ntEventMonSrcLastMatch OBJECT-TYPE
        SYNTAX SnmpAdminString (SIZE (0..256))
        ACCESS read-only
        STATUS mandatory
        DESCRIPTION
            "The source name of the last event log entry that matched this monitor entry. Each time a match occurs,
            this variable is updated."
    ::= { ntEventMonEntry 7 } 

    ntEventMonSrcFilter OBJECT-TYPE
        SYNTAX SnmpAdminString (SIZE (0..256))
        ACCESS read-write
        STATUS mandatory
        DESCRIPTION
            "The display string representation of the regular expression to match the source name in the event log.
            Valid regular expressions are those as defined in ed(1)."
    ::= { ntEventMonEntry 8 } 

    ntEventMonDescLastMatch OBJECT-TYPE
        SYNTAX SnmpAdminString (SIZE (0..512))
        ACCESS read-only
        STATUS mandatory
        DESCRIPTION
            "The text description message from the last event log entry that matched this monitor entry. Each time a
            match occurs, this variable is updated."
    ::= { ntEventMonEntry 9 } 

    ntEventMonDescFilter OBJECT-TYPE
        SYNTAX SnmpAdminString (SIZE (0..512))
        ACCESS read-write
        STATUS mandatory
        DESCRIPTION
            "The display string representation of the regular expression to match the description in the event log.
            Valid regular expressions are those as defined in ed(1)."
    ::= { ntEventMonEntry 10 } 

    ntEventMonStatus OBJECT-TYPE
        SYNTAX INTEGER {
            active(1),
            notInService(2),
            notReady(3),
            createAndGo(4),
            createAndWait(5),
            destroy(6)
        }
        ACCESS read-write
        STATUS mandatory
        DESCRIPTION
            "The status of this monitor entry according to the Textual Conventions for SNMPv2 (see RFC 1443).
            active(1)        - the row is available for usage
            notInService(2)  - setting to this value disables usage of the row
            notReady(3)      - an error occured during usage of the row
            createAndGo(4)   - setting to this value creates the row with row status set to active(1)
            createAndWait(5) - setting to this value creates the row with row status set to notInService(2)
            destroy(6)       - setting to this value deletes the row"
        DEFVAL { createAndWait } 
    ::= { ntEventMonEntry 11 } 

    ntEventMonDescr OBJECT-TYPE
        SYNTAX SnmpAdminString (SIZE (0..512))
        ACCESS read-write
        STATUS mandatory
        DESCRIPTION
            "A textual description of this entry possibly identifying the purpose of this entry and who created it."
    ::= { ntEventMonEntry 12 }

    ntEventMonAction OBJECT-TYPE
        SYNTAX SnmpAdminString (SIZE (0..2048))
        ACCESS read-write
        STATUS mandatory
        DESCRIPTION
            "The command (including parameters) to be executed concurrent to sending a trap."
    ::= { ntEventMonEntry 13 }

    ntEventMonFlags OBJECT-TYPE
        SYNTAX INTEGER
        ACCESS read-write
        STATUS mandatory
        DESCRIPTION
            "The flags is a bit field. Setting one or more bits changes the behavior of this monitor entry.
            000 000 01 - don't execute any actions (but send and log traps)
            000 000 02 - don't send any traps (but log traps and execute actions)
            000 000 04 - don't reinitialize notReady monitor
            000 000 08 - don't log any traps (but send traps and execute actions)
            000 000 10 - keep sending notReady traps
            000 000 20 - don't pass default arguments to actions
            000 000 40 - don't send notReady traps (including log and action)
            000 000 80 - entry was created by an AIM plugin (this flag is read-only)

            000 001 00 - pre-append event ID to description
            000 002 00 - apply logical 'not' operator"
    ::= { ntEventMonEntry 14 }

    ntEventMonMatches OBJECT-TYPE
        SYNTAX Counter
        ACCESS read-only
        STATUS mandatory
        DESCRIPTION
            "The number of nt-event matches detected by SystemEDGE.  This value is incremented regardless of whether
            Traps are sent for this entry or not. Polling this variable allows you to determine the rate or number of
            matches over time."
    ::= { ntEventMonEntry 15 } 

    ntEventMonSeverity OBJECT-TYPE
        SYNTAX INTEGER {
            none(1),
            ok(2),
            warning(3),
            minor(4),
            major(5),
            critical(6),
            fatal(7)
        }
        ACCESS read-write
        STATUS mandatory
        DESCRIPTION
            "The severity to use for this monitor entry. Event monitors do not implement an object state model,
            but they allow to specify a severity, that is sent with the corresponding SNMP traps."
        DEFVAL { none }
    ::= { ntEventMonEntry 16 }


------------------------------------------------------------
--  The NT Registry and Performance Group
------------------------------------------------------------
--  This group allows users of the Concord SystemEDGE Agent on Windows NT
--  to extend the Empire Enterprise MIB by adding new scalar variables. 
--  Each leaf in this group specifies a different MIB scalar value. 
--  The values for these variables are determined by querying the NT 
--  registry as specfied in the SystemEDGE configuration file (sysedge.cf)
--  See the SystemEDGE Agent User Manual for more information. 

    ntRegPerf OBJECT IDENTIFIER ::= { nt 7 }


------------------------------------------------------------
--  The Self Monitoring Table
------------------------------------------------------------

    monitorTable OBJECT-TYPE
        SYNTAX SEQUENCE OF MonitorEntry
        ACCESS not-accessible
        STATUS mandatory
        DESCRIPTION
            "The self monitor table describes monitoring activities of the agent.
           A row of this table causes the agent to monitor a particular MIB object."
    ::= { monitor 1 }

    monitorEntry OBJECT-TYPE
        SYNTAX MonitorEntry
        ACCESS not-accessible
        STATUS mandatory
        DESCRIPTION
            ""
        INDEX { monIndex }
    ::= { monitorTable 1 }

    MonitorEntry ::= SEQUENCE {
        monIndex          INTEGER,
        monDescr          SnmpAdminString,
        monInterval       INTEGER,
        monSampleType     INTEGER,
        monOID            OBJECT IDENTIFIER,
        monCurrVal        INTEGER,
        monOperator       INTEGER,
        monValue          INTEGER,
        monLastCall       TimeTicks,
        monNumTraps       INTEGER,
        monLastTrap       TimeTicks,
        monRowStatus      INTEGER,
        monMinValue       INTEGER,
        monMaxValue       INTEGER,
        monAction         SnmpAdminString,
        monFlags          INTEGER,
        monSupersededBy   INTEGER,
        monObjClass       SnmpAdminString,
        monObjInstance    SnmpAdminString,
        monObjAttribute   SnmpAdminString,
        monSeverity       INTEGER,
        monCurrState      INTEGER,
        monScale          INTEGER,
        monAutoWatchIndex INTEGER,
        monAutoWatchName  SnmpAdminString
    }

    monIndex OBJECT-TYPE
        SYNTAX INTEGER (1..2147483647)
        ACCESS read-only
        STATUS mandatory
        DESCRIPTION
            "A unique value for the table entry, not necessarily being contiguous, but unique."
    ::= { monitorEntry 1 }

    monDescr OBJECT-TYPE
        SYNTAX SnmpAdminString (SIZE (0..512))
        ACCESS read-write
        STATUS mandatory
        DESCRIPTION
            "A textual description of the entry, possibly identifying its purpose and who created it." 
    ::= { monitorEntry 2 }

    monInterval OBJECT-TYPE
        SYNTAX INTEGER (1..2147483647)
        ACCESS read-write
        STATUS mandatory
        DESCRIPTION
            "The interval, in seconds, between successive samples by the agent. It must be a multiple of 30 seconds.
            The sampling period is not exact but represents a best-effort by the agent." 
        DEFVAL { 60 }
    ::= { monitorEntry 3 }

    monSampleType OBJECT-TYPE
        SYNTAX INTEGER {
            absoluteValue(1),
            deltaValue(2)
        }
        ACCESS read-write
        STATUS mandatory
        DESCRIPTION
            "The type of sampling performed on the monitored object.
            To monitor the rate of change (e.g. for a Counter typed object) use deltaValue.
            To monitor the absolute value (e.g. for a Gauge typed object) use absoluteValue."
        DEFVAL { absoluteValue }
    ::= { monitorEntry 4 }

    monOID OBJECT-TYPE
        SYNTAX OBJECT IDENTIFIER
        ACCESS read-write
        STATUS mandatory
        DESCRIPTION
            "The object identifier (including instance) of the object being monitored.
           This object can represent both scalar and tabular objects as well. Examples:
           ifTable.ifEntry.ifInUcastPkts.1 or 1.3.6.1.2.1.2.2.1.11.1
           During row creation, the agent ensures that the object identifier is valid."
    ::= { monitorEntry 5 }

    monCurrVal OBJECT-TYPE
        SYNTAX INTEGER
        ACCESS read-only
        STATUS mandatory
        DESCRIPTION
            "The value of the monitored object as last sampled by the agent, if monSampleType is absoluteValue(1).
            If monSampleType is deltaValue(2), then this value is the difference between two successive samples."
    ::= { monitorEntry 6 }

    monOperator OBJECT-TYPE
        SYNTAX INTEGER {
            nop(1),
            gt(2),
            lt(3),
            ge(4),
            le(5),
            eq(6),
            ne(7)
        }
        ACCESS read-write
        STATUS mandatory
        DESCRIPTION
            "The boolean operator that is used to compare the current value to the threshold value.
            nop(1) is used to only track the current value, but do not compare to the threshold."
        DEFVAL { nop }
    ::= { monitorEntry 7 }

    monValue OBJECT-TYPE
        SYNTAX INTEGER
        ACCESS read-write
        STATUS mandatory
        DESCRIPTION
            "The threshold value against which the agent compares the current value."
    ::= { monitorEntry 8 }

    monLastCall OBJECT-TYPE
        SYNTAX TimeTicks
        ACCESS read-only
        STATUS mandatory
        DESCRIPTION
            "The time when the agent last sampled the monitored object.
            This relative time (R) is given in hundredths of a second since the agent was started. It can be
            converted into an absolute time (A) using sysUpTime (from MIB-II) and hrSystemDate (from HR-MIB).
            sysUpTime (S) is the elapsed time (in hundredths of a second) since the agent was started.
            hrSysDate (H) is the current absolute date and time (in DateAndTime format) and must be converted
            to Unix Time format (seconds elapsed since 01.01.1970). Finally calculate: A = H - S/100 + R/100"
    ::= { monitorEntry 9 }

    monNumTraps OBJECT-TYPE
        SYNTAX INTEGER
        ACCESS read-only
        STATUS mandatory
        DESCRIPTION
            "The number of traps sent for this monitor entry. Dependent from monFlags, it could
            represent a lower bound on the number of times the threshold has actually been crossed."
    ::= { monitorEntry 10 }

    monLastTrap OBJECT-TYPE
        SYNTAX TimeTicks
        ACCESS read-only
        STATUS mandatory
        DESCRIPTION
            "The time when the agent last sent a trap for this monitor entry.
            This relative time (R) is given in hundredths of a second since the agent was started. It can be
            converted into an absolute time (A) using sysUpTime (from MIB-II) and hrSystemDate (from HR-MIB).
            sysUpTime (S) is the elapsed time (in hundredths of a second) since the agent was started.
            hrSysDate (H) is the current absolute date and time (in DateAndTime format) and must be converted
            to Unix Time format (seconds elapsed since 01.01.1970). Finally calculate: A = H - S/100 + R/100"
    ::= { monitorEntry 11 }

    monRowStatus OBJECT-TYPE
        SYNTAX INTEGER {
            active(1),
            notInService(2),
            notReady(3),
            createAndGo(4),
            createAndWait(5),
            destroy(6)
        }
        ACCESS read-write
        STATUS mandatory
        DESCRIPTION
            "The status of this monitor entry according to the Textual Conventions for SNMPv2 (see RFC 1443).
            active(1)        - the row is available for usage
            notInService(2)  - setting to this value disables usage of the row
            notReady(3)      - an error occured during usage of the row
            createAndGo(4)   - setting to this value creates the row with row status set to active(1)
            createAndWait(5) - setting to this value creates the row with row status set to notInService(2)
            destroy(6)       - setting to this value deletes the row"
        DEFVAL { createAndWait } 
    ::= { monitorEntry 12 }

    monMinValue OBJECT-TYPE
        SYNTAX INTEGER 
        ACCESS read-only
        STATUS mandatory
        DESCRIPTION
            "The minimum value sampled."
    ::= { monitorEntry 13 }

    monMaxValue OBJECT-TYPE
        SYNTAX INTEGER 
        ACCESS read-only
        STATUS mandatory
        DESCRIPTION
            "The maximum value sampled."
    ::= { monitorEntry 14 }

    monAction OBJECT-TYPE
        SYNTAX SnmpAdminString (SIZE (0..2048))
        ACCESS read-write
        STATUS mandatory
        DESCRIPTION
            "The command (including parameters) to be executed concurrent to sending a trap."
    ::= { monitorEntry 15 }

    monFlags OBJECT-TYPE
        SYNTAX INTEGER 
        ACCESS read-write
        STATUS mandatory
        DESCRIPTION
            "The flags is a bit field. Setting one or more bits changes the behavior of this monitor entry.
            000 000 01 - don't execute any actions (but send and log traps)
            000 000 02 - don't send any traps (but log traps and execute actions)
            000 000 04 - don't reinitialize notReady monitor
            000 000 08 - don't log any traps (but send traps and execute actions)
            000 000 10 - keep sending notReady traps
            000 000 20 - don't pass default arguments to actions
            000 000 40 - don't send notReady traps (including log and action)
            000 000 80 - entry was created by an AIM plugin (this flag is read-only)

            000 001 00 - send monitorClear traps (including log and action)
            xxx 002 00 - send monitorThreshold traps after xxx consecutive breaches (including log and action)
            xxx 004 00 - send at most xxx consecutive monitorThreshold traps (including log and action)
            000 008 00 - aggregate state of all monitors with same severity as AND relation"
    ::= { monitorEntry 16 }

    monSupersededBy OBJECT-TYPE
        SYNTAX INTEGER (0..2147483647)
        ACCESS read-write
        STATUS mandatory
        DESCRIPTION
            "The index of the monitor that supersedes this entry. A superseding monitor is evaluated before
           this entry, and if the superseding monitor's threshold is crossed, this entry will no more be
           evaluated. With such a sequence of correlated monitors, useless sequences of traps can be ommited.
           A value of zero (0) indicates no monitor entry correlation will be done.
           Note that usage of the object state model obsoletes (and disables) this functionality."
        DEFVAL { 0 }
    ::= { monitorEntry 17 }

    monObjClass OBJECT-TYPE
        SYNTAX SnmpAdminString (SIZE (0..512))
        ACCESS read-write
        STATUS mandatory
        DESCRIPTION
            "The object class to use for the object state model. If the value is not configured and the agent
            cannot determine a default, the value is 'unknown'.
            This attribute cannot be set to an empty string or to '*'. Any such requests are ignored."
    ::= { monitorEntry 18 }

    monObjInstance OBJECT-TYPE
        SYNTAX SnmpAdminString (SIZE (0..512))
        ACCESS read-write
        STATUS mandatory
        DESCRIPTION
            "The object instance to use for the object state model. If the value is not configured and the agent
            cannot determine a default, the value is 'unknown'. The default for a non-tabular object is 'null'.
            For seamless monitoring of remote or virtual objects, instance names start with a prefix //hierarchy/.
            Additionally a name space can be prepended to better identify virtual objects (e.g. lpar:).
            For local objects the agent adds the prefix //./ to each instance name (including 'null').
            This attribute cannot be set to an empty string or to '*'. Any such requests are ignored."
    ::= { monitorEntry 19 }

    monObjAttribute OBJECT-TYPE
        SYNTAX SnmpAdminString (SIZE (0..512))
        ACCESS read-write
        STATUS mandatory
        DESCRIPTION
            "The object attribute to use for the object state model. If the value is not configured and the agent
            cannot determine a default, the value is 'unknown'.
            This attribute cannot be set to an empty string or to '*'. Any such requests are ignored."
    ::= { monitorEntry 20 }

    monSeverity OBJECT-TYPE
        SYNTAX INTEGER {
            none(1),
            ok(2),
            warning(3),
            minor(4),
            major(5),
            critical(6),
            fatal(7)
        }
        ACCESS read-write
        STATUS mandatory
        DESCRIPTION
            "The severity to use for the object state model.
            The value none(1) excludes this monitor entry from the object state model."
        DEFVAL { none }
    ::= { monitorEntry 21 }

    monCurrState OBJECT-TYPE
        SYNTAX INTEGER {
            unknown(1),
            ok(2),
            warning(3),
            minor(4),
            major(5),
            critical(6),
            fatal(7),
            up(11),
            down(12)
        }
        ACCESS read-only
        STATUS mandatory
        DESCRIPTION
            "The current state of this monitor entry, evaluated by the severity and the breach condition,
            respecting any lag value configured in monFlags. If the row status is notInService(2), the state
            evaluates to unknown(1). If the row status is notReady(3), the state is kept unchanged. 
            The values up(11) and down(12) are used if the severity is none(1)."
    ::= { monitorEntry 22 }

    monScale OBJECT-TYPE
        SYNTAX INTEGER 
        ACCESS read-write
        STATUS mandatory
        DESCRIPTION
            "Scale factor for monitor values. This scale factor allows monitoring variable in different units then is measured.
             For example scale factor 1024 allows to monitor in KiB variable that is measured in bytes. With this scaling factor 
             variables monCurrVal, monValue, monMinValue and monMaxValue will be reported in KiB.
             Note that the SYNTAX of this attribute actually is Counter64." 
    ::= { monitorEntry 23 }

    monAutoWatchIndex OBJECT-TYPE
        SYNTAX INTEGER (0..2147483647)
        ACCESS read-only
        STATUS mandatory
        DESCRIPTION
            "The table index of the auto-watcher (see autoWatchEntry.watchIndex) that created this monitor.  An index of zero(0) indicates that
             this monitor was not created using an auto-watcher."
    ::= { monitorEntry 24 }

    monAutoWatchName OBJECT-TYPE
        SYNTAX SnmpAdminString
        ACCESS read-only
        STATUS mandatory
        DESCRIPTION
            "The name of the auto-watcher (see autoWatchEntry.watchName) that created this monitor.  This attribute is left blank
             if this monitor was not created using an auto-watcher."
    ::= { monitorEntry 25 }


------------------------------------------------------------

    monUnusedIndex OBJECT-TYPE
        SYNTAX INTEGER (1..2147483647)
        ACCESS read-only
        STATUS mandatory
        DESCRIPTION
            "This attribute returns an unused monIndex, which can be used for row creation."
    ::= { monitor 2 }

    monMatchDescr OBJECT-TYPE
        SYNTAX DisplayString
        ACCESS read-write
        STATUS mandatory
        DESCRIPTION
            "This attribute can be used to determine the index of a particular row.
            Setting the attribute to a description, causes the agent to place the index of
            the last row, whose monDescr matches, in the monMatchIndex attribute."
    ::= { monitor 3 }

    monMatchIndex OBJECT-TYPE
        SYNTAX INTEGER (1..2147483647)
        ACCESS read-only
        STATUS mandatory
        DESCRIPTION
            "This attribute stores the index of the last row, whose monDescr matches monMatchDescr."
    ::= { monitor 4 }


------------------------------------------------------------
--  The Distributed Systems Group
------------------------------------------------------------
--  This group provides object necessary for the monitoring and management
--  of distributed systems facilities like NIS, RPC, and NFS.  Since they
--  these services are available on a variety of operating systems
--  platforms, they are placed under the general Empire MIB rather than
--  its UNIX or platform branches.

    rpc OBJECT IDENTIFIER ::= { distribsys 1 }
    nfs OBJECT IDENTIFIER ::= { distribsys 2 }
--  nis OBJECT IDENTIFIER ::= { distribsys 3 }  deprecated


------------------------------------------------------------
--  The RPC Stats Group
------------------------------------------------------------
--  This group provides statistics and counters relating to the use of 
--  RPC facilities.  While it should be independent of which RPC 
--  protocol is used, most often it represents counters and statistics
--  for the usage of Sun RPC.  Statistics and counters are divided 
--  according to their applicability towards client and server side
--  protocol operations.  Please refer to the SunRPC specification 
--  (RFC 1057) for more information.

    clientRPCCalls OBJECT-TYPE
        SYNTAX Counter
        ACCESS read-only
        STATUS mandatory
        DESCRIPTION
            "The total number of RPC calls sent by the RPC client protocol software."
    ::= { rpc 1 }

    clientRPCBadcalls OBJECT-TYPE
        SYNTAX Counter
        ACCESS read-only
        STATUS mandatory
        DESCRIPTION
            "The total number of RPC calls rejected by the RPC client protocol software."
    ::= { rpc 2 }

    clientRPCRetrans OBJECT-TYPE
        SYNTAX Counter
        ACCESS read-only
        STATUS mandatory
        DESCRIPTION
            "The total number of times an RPC call had to be retransmitted due to a timeout while waiting for an RPC
            server reply."
    ::= { rpc 3 }

    clientRPCBadxids OBJECT-TYPE
        SYNTAX Counter
        ACCESS read-only
        STATUS mandatory
        DESCRIPTION
            "The total number of times a server RPC reply was received for which no outstanding call exists."
    ::= { rpc 4 }

    clientRPCTimeouts OBJECT-TYPE
        SYNTAX Counter
        ACCESS read-only
        STATUS mandatory
        DESCRIPTION
            "The total number times an RPC call timed out while waiting for a reply from the RPC server."
    ::= { rpc 5 }

    clientRPCWaits OBJECT-TYPE
        SYNTAX Counter
        ACCESS read-only
        STATUS mandatory
        DESCRIPTION
            "The total number of times an RPC call has to wait because no client handle was available."
    ::= { rpc 6 }

    clientRPCNewcreds OBJECT-TYPE
        SYNTAX Counter
        ACCESS read-only
        STATUS mandatory
        DESCRIPTION
            "The total number of times authentication information had to be refreshed."
    ::= { rpc 7 }

    clientRPCTimers OBJECT-TYPE
        SYNTAX Counter
        ACCESS read-only
        STATUS mandatory
        DESCRIPTION
            "The total number of times the calculated time-out value was greater than or equal to the minimum
            specified time-out value for an RPC call."
    ::= { rpc 8 }

    serverRPCCalls OBJECT-TYPE
        SYNTAX Counter
        ACCESS read-only
        STATUS mandatory
        DESCRIPTION
            "The total number of RPC calls received by the RPC server protocol software."
    ::= { rpc 9 }

    serverRPCBadcalls OBJECT-TYPE 
        SYNTAX Counter
        ACCESS read-only
        STATUS mandatory
        DESCRIPTION
            "The total number of calls rejected by the RPC server protocol softeware; it is equivalent to the sum of
            the MIB objects serverRPCBadlen and serverRPCxdrcall."
    ::= { rpc 10 }

    serverRPCNullrecvs OBJECT-TYPE
        SYNTAX Counter
        ACCESS read-only
        STATUS mandatory
        DESCRIPTION
            "The number of RPC requests not available when it was thought to be received."
    ::= { rpc 11 }

    serverRPCBadlens OBJECT-TYPE
        SYNTAX Counter
        ACCESS read-only
        STATUS mandatory
        DESCRIPTION
            "The number of RPC requests whose lengths were shorter than the minimum size RPC message."
    ::= { rpc 12 }

    serverRPCXdrcalls OBJECT-TYPE
        SYNTAX Counter
        ACCESS read-only
        STATUS mandatory
        DESCRIPTION
            "The number of RPC requests whose header could not be XDR decoded."
    ::= { rpc 13 }

------------------------------------------------------------
--  The NFS Stats Group
------------------------------------------------------------
--  This group provides statistics and counters relating to the use of
--  the distributed file services utilizing the NFS protocol.
--  Statistics and counters are divided according to their
--  applicability towards client and server side protocol operations.
--  For more information, please refer to the NFS protocol
--  specification (RFC 1094).

    clientNFSCalls OBJECT-TYPE
        SYNTAX Counter
        ACCESS read-only
        STATUS mandatory
        DESCRIPTION
            "The total number of NFS calls sent by the NFS client protocol software."
    ::= { nfs 1 }

    clientNFSBadcalls OBJECT-TYPE
        SYNTAX Counter
        ACCESS read-only
        STATUS mandatory
        DESCRIPTION
            "The total number of times an NFS call was rejected by the underlying client RPC protocol software."
    ::= { nfs 2 }

    clientNFSNclgets OBJECT-TYPE
        SYNTAX Counter
        ACCESS read-only
        STATUS mandatory
        DESCRIPTION
            "The total number of times a client NFS handle was received by the NFS client protocol software."
    ::= { nfs 3 }

    clientNFSNclsleeps OBJECT-TYPE
        SYNTAX Counter
        ACCESS read-only
        STATUS mandatory
        DESCRIPTION
            "The total number of times a client NFS call had to sleep while waiting for a client NFS handle."
    ::= { nfs 4 }

    clientNFSNulls OBJECT-TYPE
        SYNTAX Counter
        ACCESS read-only
        STATUS mandatory
        DESCRIPTION
            "The total number of NFS 'NULL' procedure calls sent by the client NFS protocol software.  The 'NULL'
            procedure is often used to allow server response testing and timing."
    ::= { nfs 5 }

    clientNFSGetattrs OBJECT-TYPE
        SYNTAX Counter
        ACCESS read-only
        STATUS mandatory
        DESCRIPTION
            "The total number of NFS 'GetAttr' procedure calls sent by the client NFS protocol software.  This
            function is used to obtain attributes for a given file."
    ::= { nfs 6 }

    clientNFSSetattrs OBJECT-TYPE
        SYNTAX Counter
        ACCESS read-only
        STATUS mandatory
        DESCRIPTION
            "The total number of NFS 'SetAttr' procedure calls sent by the client NFS protocol software.  This
            function is used to set a file's attributes."
    ::= { nfs 7 }

    clientNFSRoots OBJECT-TYPE
        SYNTAX Counter
        ACCESS read-only
        STATUS mandatory
        DESCRIPTION
            "The total number of NFS 'Root' procedure calls sent by the client NFS protocol software.  This function
            has been declared deprecated."
    ::= { nfs 8 }

    clientNFSLookups OBJECT-TYPE
        SYNTAX Counter
        ACCESS read-only
        STATUS mandatory
        DESCRIPTION
            "The total number of NFS 'Lookup' procedure calls sent by the client NFS protocol software.  This
            function is used to retrieve a file's attributes and handle."
    ::= { nfs 9 }

    clientNFSReadlinks OBJECT-TYPE
        SYNTAX Counter
        ACCESS read-only
        STATUS mandatory
        DESCRIPTION
            "The total number of NFS 'Read link' procedure calls sent by the client NFS protocol software.  This
            function is used to read from a symbolic link."
    ::= { nfs 10 }

    clientNFSReads OBJECT-TYPE
        SYNTAX Counter
        ACCESS read-only
        STATUS mandatory
        DESCRIPTION
            "The total number of NFS 'Read' procedure calls sent by the client NFS protocol software.  This function
            is used to read data (in units of bytes) from a give file."
    ::= { nfs 11 }

    clientNFSWrcaches OBJECT-TYPE
        SYNTAX Counter
        ACCESS read-only
        STATUS mandatory
        DESCRIPTION
            "The total number of NFS 'Write Cache' procedure calls sent by the client NFS protocol software.   This
            function is to be used in future versions of the NFS protocol."
    ::= { nfs 12 }

    clientNFSWrites OBJECT-TYPE
        SYNTAX Counter
        ACCESS read-only
        STATUS mandatory
        DESCRIPTION
            "The total number of NFS 'Write' procedure calls sent by the client NFS protocol software.  This function
            is used to write data (in units of bytes) to a given file."
    ::= { nfs 13 }

    clientNFSCreates OBJECT-TYPE
        SYNTAX Counter
        ACCESS read-only
        STATUS mandatory
        DESCRIPTION
            "The total number of NFS 'Create' procedure calls sent by the client NFS protocol software.  This
            function is used to create a file in a given directory."
    ::= { nfs 14 }

    clientNFSRemoves OBJECT-TYPE
        SYNTAX Counter
        ACCESS read-only
        STATUS mandatory
        DESCRIPTION
            "The total number of NFS 'Remove' procedure calls sent by the client NFS protocol software.  This
            function is used to remove a file from a given directory."
    ::= { nfs 15 }

    clientNFSRenames OBJECT-TYPE
        SYNTAX Counter
        ACCESS read-only
        STATUS mandatory
        DESCRIPTION
            "The total number of NFS 'Rename' procedure calls sent by the client NFS protocol software.  This
            function is used to rename a given file."
    ::= { nfs 16 }

    clientNFSLinks OBJECT-TYPE
        SYNTAX Counter
        ACCESS read-only
        STATUS mandatory
        DESCRIPTION
            "The total number of NFS 'Create Link' procedure calls sent by the client NFS protocol software.  This
            function is used to create a link to a given file."
    ::= { nfs 17 }

    clientNFSSymlinks OBJECT-TYPE
        SYNTAX Counter
        ACCESS read-only
        STATUS mandatory
        DESCRIPTION
            "The total number of NFS 'Create Symbolic Link' procedure calls sent by the client NFS protocol software.
            This function is used to create a symbolic link to a given file."
    ::= { nfs 18 }

    clientNFSMkdirs OBJECT-TYPE
        SYNTAX Counter
        ACCESS read-only
        STATUS mandatory
        DESCRIPTION
            "The total number of NFS 'mkdir' procedure calls sent by the client NFS protocol software.  This function
            is used to create a directory within a given directory."
    ::= { nfs 19 }

    clientNFSRmdirs OBJECT-TYPE
        SYNTAX Counter
        ACCESS read-only
        STATUS mandatory
        DESCRIPTION
            "The total number of NFS 'rmdir' procedure calls sent by the client NFS protocol software.  This function
            is used to remove a given directory."
    ::= { nfs 20 }

    clientNFSReaddirs OBJECT-TYPE
        SYNTAX Counter
        ACCESS read-only
        STATUS mandatory
        DESCRIPTION
            "The total number of NFS 'readdir' procedure calls sent by the client NFS protocol software.  This
            function is used to read a variable number of directory entries from the given directory."
    ::= { nfs 21 }

    clientNFSFsstats OBJECT-TYPE
        SYNTAX Counter
        ACCESS read-only
        STATUS mandatory
        DESCRIPTION
            "The total number of NFS 'stat' procedure calls sent by the client NFS protocol software.  This function
            is used to retrieve file system statistics."
    ::= { nfs 22 }

    serverNFSCalls OBJECT-TYPE
        SYNTAX Counter
        ACCESS read-only
        STATUS mandatory
        DESCRIPTION
            "The total number of NFS calls received by the NFS server protocol software."
    ::= { nfs 23 }

    serverNFSBadcalls OBJECT-TYPE
        SYNTAX Counter
        ACCESS read-only
        STATUS mandatory
        DESCRIPTION
            "The total number of times an NFS call was rejected by the underlying server RPC protocol software."
    ::= { nfs 24 }

    serverNFSNulls OBJECT-TYPE
        SYNTAX Counter
        ACCESS read-only
        STATUS mandatory
        DESCRIPTION
            "The total number of NFS 'NULL' procedure calls received by the server NFS protocol software.  The 'NULL'
            procedure is often used to allow server response testing and timing."
    ::= { nfs 25 }

    serverNFSGetattrs OBJECT-TYPE
        SYNTAX Counter
        ACCESS read-only
        STATUS mandatory
        DESCRIPTION
            "The total number of NFS 'GetAttr' procedure calls received by the server NFS protocol software.  This
            function is used to obtain attributes for a given file."
    ::= { nfs 26 }

    serverNFSSetattrs OBJECT-TYPE
        SYNTAX Counter
        ACCESS read-only
        STATUS mandatory
        DESCRIPTION
            "The total number of NFS 'SetAttr' procedure calls received by the server NFS protocol software.  This
            function is used to set a file's attributes."
    ::= { nfs 27 }

    serverNFSRoots OBJECT-TYPE
        SYNTAX Counter
        ACCESS read-only
        STATUS mandatory
        DESCRIPTION
            "The total number of NFS 'Root' procedure calls received by the server NFS protocol software.  This
            function has been declared deprecated."
    ::= { nfs 28 }

    serverNFSLookups OBJECT-TYPE
        SYNTAX Counter
        ACCESS read-only
        STATUS mandatory
        DESCRIPTION
            "The total number of NFS 'Lookup' procedure calls received by the server NFS protocol software.  This
            function is used to retrieve a file's attributes and handle."
    ::= { nfs 29 }

    serverNFSReadlinks OBJECT-TYPE
        SYNTAX Counter
        ACCESS read-only
        STATUS mandatory
        DESCRIPTION
            "The total number of NFS 'Read link' procedure calls received by the server NFS protocol software.  This
            function is used to read from a symbolic link."
    ::= { nfs 30 }

    serverNFSReads OBJECT-TYPE
        SYNTAX Counter
        ACCESS read-only
        STATUS mandatory
        DESCRIPTION
            "The total number of NFS 'Read' procedure calls received by the server NFS protocol software.  This
            function is used to read data (in units of bytes) from a give file."
    ::= { nfs 31 }

    serverNFSWrcaches OBJECT-TYPE
        SYNTAX Counter
        ACCESS read-only
        STATUS mandatory
        DESCRIPTION
            "The total number of NFS 'Write Cache' procedure calls received by the server NFS protocol software.
            This function is to be used in future versions of the NFS protocol."
    ::= { nfs 32 }

    serverNFSWrites OBJECT-TYPE
        SYNTAX Counter
        ACCESS read-only
        STATUS mandatory
        DESCRIPTION
            "The total number of NFS 'Write' procedure calls received by the server NFS protocol software.  This
            function is used to write data (in units of bytes) to a given file."
    ::= { nfs 33 }

    serverNFSCreates OBJECT-TYPE
        SYNTAX Counter
        ACCESS read-only
        STATUS mandatory
        DESCRIPTION
            "The total number of NFS 'Create' procedure calls received by the server NFS protocol software.  This
            function is used to create a file in a given directory."
    ::= { nfs 34 }

    serverNFSRemoves OBJECT-TYPE
        SYNTAX Counter
        ACCESS read-only
        STATUS mandatory
        DESCRIPTION
            "The total number of NFS 'Remove' procedure calls received by the server NFS protocol software.  This
            function is used to remove a file from a given directory."
    ::= { nfs 35 }

    serverNFSRenames OBJECT-TYPE
        SYNTAX Counter
        ACCESS read-only
        STATUS mandatory
        DESCRIPTION
            "The total number of NFS 'Rename' procedure calls received by the server NFS protocol software.  This
            function is used to rename a given file."
    ::= { nfs 36 }

    serverNFSLinks OBJECT-TYPE
        SYNTAX Counter
        ACCESS read-only
        STATUS mandatory
        DESCRIPTION
            "The total number of NFS 'Create Link' procedure calls received by the server NFS protocol software.
            This function is used to create a link to a given file."
    ::= { nfs 37 }

    serverNFSSymlinks OBJECT-TYPE
        SYNTAX Counter
        ACCESS read-only
        STATUS mandatory
        DESCRIPTION
            "The total number of NFS 'Create Symbolic Link' procedure calls received by the server NFS protocol
            software.  This function is used to create a symbolic link to a given file."
    ::= { nfs 38 }

    serverNFSMkdirs OBJECT-TYPE
        SYNTAX Counter
        ACCESS read-only
        STATUS mandatory
        DESCRIPTION
            "The total number of NFS 'mkdir' procedure calls received by the server NFS protocol software.  This
            function is used to create a directory within a given directory."
    ::= { nfs 39 }

    serverNFSRmdirs OBJECT-TYPE
        SYNTAX Counter
        ACCESS read-only
        STATUS mandatory
        DESCRIPTION
            "The total number of NFS 'rmdir' procedure calls received by the server NFS protocol software.  This
            function is used to remove a given directory."
    ::= { nfs 40 }

    serverNFSReaddirs OBJECT-TYPE
        SYNTAX Counter
        ACCESS read-only
        STATUS mandatory
        DESCRIPTION
            "The total number of NFS 'readdir' procedure calls received by the server NFS protocol software.  This
            function is used to read a variable number of directory entries from the given directory."
    ::= { nfs 41 }

    serverNFSFsstats OBJECT-TYPE
        SYNTAX Counter
        ACCESS read-only
        STATUS mandatory
        DESCRIPTION
            "The total number of NFS 'stat' procedure calls received by the server NFS protocol software.  This
            function is used to retrieve file system statistics."
    ::= { nfs 42 }


------------------------------------------------------------
--  The History Control Table
------------------------------------------------------------
--  This group defines 'rmon-like' history control and history tables 
--  that enable the agent to track the value of an object over time.
--  Like the RMON MIB, the agent reserves buckets for each distinct
--  sampling or history control entry

    empireHistoryCtrlTable OBJECT-TYPE
        SYNTAX SEQUENCE OF EmpireHistoryCtrlEntry
        ACCESS not-accessible
        STATUS mandatory
        DESCRIPTION
            "Table describing/controlling the object history collection.  Adding rows to this table causes the agent
            to track the history of additional objects; deleting rows from the table causes the agent to cease
            tracking the value of an object.  Row creation follows the V2 SMI RowStatus textual convention (See RFC
            1443).  Further, the table is similar to the RMON HistoryControlTable in purpose (See RFC 1271)."
    ::= { empireHistory 1 }

    empireHistoryCtrlEntry OBJECT-TYPE
        SYNTAX EmpireHistoryCtrlEntry
        ACCESS not-accessible
        STATUS mandatory
        DESCRIPTION
            "A list of parameters that set up a periodic sampling of a single object value contained within the
            agent's internal MIB."
        INDEX { empireHistoryCtrlIndex } 
    ::= { empireHistoryCtrlTable 1 }

    EmpireHistoryCtrlEntry ::= SEQUENCE {
        empireHistoryCtrlIndex        INTEGER,
        empireHistoryCtrlDescr        SnmpAdminString,
        empireHistoryCtrlInterval     INTEGER,
        empireHistoryCtrlObjID        OBJECT IDENTIFIER,
        empireHistoryCtrlObjType      INTEGER,
        empireHistoryCtrlBucketsReq   INTEGER,
        empireHistoryCtrlBucketsGrant INTEGER,
        empireHistoryCtrlLastCall     TimeTicks,
        empireHistoryCtrlCreateTime   TimeTicks,
        empireHistoryCtrlStatus       INTEGER,
        empireHistoryCtrlFlags        INTEGER
    }

    empireHistoryCtrlIndex OBJECT-TYPE
        SYNTAX INTEGER (1..2147483647)
        ACCESS read-only
        STATUS mandatory
        DESCRIPTION
            "An index that uniquely identifies an entry in the empireHistoryCtrlTable.  Each such entry defines a
            periodic sampling/history that the agent performs.  The sample values can be obtained from the
            empireHistoryTable."
    ::= { empireHistoryCtrlEntry 1 } 

    empireHistoryCtrlDescr OBJECT-TYPE
        SYNTAX SnmpAdminString (SIZE (0..512))
        ACCESS read-write
        STATUS mandatory
        DESCRIPTION
            "A textual description of this entry possibly identifying the purpose of this entry and who created it."
    ::= { empireHistoryCtrlEntry 2 } 

    empireHistoryCtrlInterval OBJECT-TYPE
        SYNTAX INTEGER
        ACCESS read-write
        STATUS mandatory
        DESCRIPTION
            "The interval in seconds between successive samples.  The sample interval must be a multiple of 30
            seconds."
    ::= { empireHistoryCtrlEntry 3 } 

    empireHistoryCtrlObjID OBJECT-TYPE
        SYNTAX OBJECT IDENTIFIER
        ACCESS read-write
        STATUS mandatory
        DESCRIPTION
            "The object identifier of the particular object to be sampled.  This object identifier must refer to a
            valid object and be of base type INTEGER.  For example, objects of type Counter, INTEGER, and Gauge can
            be sampled, but objects of type DisplayString cannot."
    ::= { empireHistoryCtrlEntry 4 } 

    empireHistoryCtrlObjType OBJECT-TYPE
        SYNTAX INTEGER
        ACCESS read-only
        STATUS mandatory
        DESCRIPTION
            "The ASN1/SNMP tag value of the object being sampled.  For example, an SNMP Gauge would be 0x42 or 66
            decimal."
    ::= { empireHistoryCtrlEntry 5 } 

    empireHistoryCtrlBucketsReq OBJECT-TYPE
        SYNTAX INTEGER
        ACCESS read-write
        STATUS mandatory
        DESCRIPTION
            "The requested number of discrete samples of data to be saved in the empireHistoryTable. When this object
            is created or modified, the agent sets the empireHistoryCtrlBucketsGrant as close as possible."
    ::= { empireHistoryCtrlEntry 6 } 

    empireHistoryCtrlBucketsGrant OBJECT-TYPE
        SYNTAX INTEGER
        ACCESS read-only
        STATUS mandatory
        DESCRIPTION
            "The number of discrete samples of data which shall be saved in the empireHistoryCtrlTable."
    ::= { empireHistoryCtrlEntry 7 } 

    empireHistoryCtrlLastCall OBJECT-TYPE
        SYNTAX TimeTicks
        ACCESS read-only
        STATUS mandatory
        DESCRIPTION
            "The time when this entry was last evaluated by the agent.
            This relative time (R) is given in hundredths of a second since the agent was started. It can be
            converted into an absolute time (A) using sysUpTime (from MIB-II) and hrSystemDate (from HR-MIB).
            sysUpTime (S) is the elapsed time (in hundredths of a second) since the agent was started.
            hrSysDate (H) is the current absolute date and time (in DateAndTime format) and must be converted
            to Unix Time format (seconds elapsed since 01.01.1970). Finally calculate: A = H - S/100 + R/100"
    ::= { empireHistoryCtrlEntry 8 } 

    empireHistoryCtrlCreateTime OBJECT-TYPE
        SYNTAX TimeTicks
        ACCESS read-only
        STATUS mandatory
        DESCRIPTION
            "The time when this entry was created by the agent.
            This relative time (R) is given in hundredths of a second since the agent was started. It can be
            converted into an absolute time (A) using sysUpTime (from MIB-II) and hrSystemDate (from HR-MIB).
            sysUpTime (S) is the elapsed time (in hundredths of a second) since the agent was started.
            hrSysDate (H) is the current absolute date and time (in DateAndTime format) and must be converted
            to Unix Time format (seconds elapsed since 01.01.1970). Finally calculate: A = H - S/100 + R/100"
    ::= { empireHistoryCtrlEntry 9 } 

    empireHistoryCtrlStatus OBJECT-TYPE
        SYNTAX INTEGER {
            active(1),
            notInService(2),
            notReady(3),
            createAndGo(4),
            createAndWait(5),
            destroy(6)
        }
        ACCESS read-write
        STATUS mandatory
        DESCRIPTION
            "The status of this monitor entry according to the Textual Conventions for SNMPv2 (see RFC 1443).
            active(1)        - the row is available for usage
            notInService(2)  - setting to this value disables usage of the row
            notReady(3)      - an error occured during usage of the row
            createAndGo(4)   - setting to this value creates the row with row status set to active(1)
            createAndWait(5) - setting to this value creates the row with row status set to notInService(2)
            destroy(6)       - setting to this value deletes the row"
        DEFVAL { createAndWait } 
    ::= { empireHistoryCtrlEntry 10 } 

    empireHistoryCtrlFlags OBJECT-TYPE
        SYNTAX INTEGER 
        ACCESS read-write
        STATUS mandatory
        DESCRIPTION
            "The flags is a bit field. Setting one or more bits changes the behavior of this entry.
            000 000 80 - entry was created by an AIM plugin (this flag is read-only)

            000 001 00 - collect performance cube data"
    ::= { empireHistoryCtrlEntry 11 }


------------------------------------------------------------
--  The History Table
------------------------------------------------------------

    empireHistoryTable OBJECT-TYPE
        SYNTAX SEQUENCE OF EmpireHistoryEntry
        ACCESS not-accessible
        STATUS mandatory
        DESCRIPTION
            "Table containing the history samples corresponding to history control entries contained in the
            empireHistoryCtrlTable.  For each entry in the control table, a set of history samples will exist in this
            table.  Managers can index a particular sample by combining the corresponding index from the control
            table with a sample number."
    ::= { empireHistory 2 }

    empireHistoryEntry OBJECT-TYPE
        SYNTAX EmpireHistoryEntry
        ACCESS not-accessible
        STATUS mandatory
        DESCRIPTION
            "A historical sample of an object in the agent's MIB.  Each sample is associated with an entry in the
            empireHistoryCtrlTable which set up the parameters for a regular collection of these samples."
        INDEX { empireHistoryIndex, empireHistorySampleIndex }
    ::= { empireHistoryTable 1 }

    EmpireHistoryEntry ::= SEQUENCE {
        empireHistoryIndex       INTEGER,
        empireHistorySampleIndex INTEGER,
        empireHistoryStartTime   TimeTicks,
        empireHistorySampleTime  TimeTicks,
        empireHistoryValue       INTEGER
    }

    empireHistoryIndex OBJECT-TYPE
        SYNTAX INTEGER (1..2147483647)
        ACCESS read-only
        STATUS mandatory
        DESCRIPTION
            "The history of which this entry is a part.  This value identifies a row in the empireHistoryCtrlTable of
            which this sample is a part."
    ::= { empireHistoryEntry 1 } 

    empireHistorySampleIndex OBJECT-TYPE
        SYNTAX INTEGER (1..2147483647)
        ACCESS read-only
        STATUS mandatory
        DESCRIPTION
            "An index that uniquely identifies the particular sample this entry represents among all samples
             associated with the same history control entry. This index starts at 1 and increases by one as each new
             sample is taken."
    ::= { empireHistoryEntry 2 } 

    empireHistoryStartTime OBJECT-TYPE
        SYNTAX TimeTicks
        ACCESS read-only
        STATUS mandatory
        DESCRIPTION
            "The time when the first sample was taken.
            This relative time (R) is given in hundredths of a second since the agent was started. It can be
            converted into an absolute time (A) using sysUpTime (from MIB-II) and hrSystemDate (from HR-MIB).
            sysUpTime (S) is the elapsed time (in hundredths of a second) since the agent was started.
            hrSysDate (H) is the current absolute date and time (in DateAndTime format) and must be converted
            to Unix Time format (seconds elapsed since 01.01.1970). Finally calculate: A = H - S/100 + R/100"
    ::= { empireHistoryEntry 3 } 

    empireHistorySampleTime OBJECT-TYPE
        SYNTAX TimeTicks
        ACCESS read-only
        STATUS mandatory
        DESCRIPTION
            "The time when this particular sample was taken.
            This relative time (R) is given in hundredths of a second since the agent was started. It can be
            converted into an absolute time (A) using sysUpTime (from MIB-II) and hrSystemDate (from HR-MIB).
            sysUpTime (S) is the elapsed time (in hundredths of a second) since the agent was started.
            hrSysDate (H) is the current absolute date and time (in DateAndTime format) and must be converted
            to Unix Time format (seconds elapsed since 01.01.1970). Finally calculate: A = H - S/100 + R/100"
    ::= { empireHistoryEntry 4 } 

    empireHistoryValue OBJECT-TYPE
        SYNTAX INTEGER
        ACCESS read-only
        STATUS mandatory
        DESCRIPTION
            "The value of this sample. Note that the SYNTAX of this attribute actually is Counter64."
    ::= { empireHistoryEntry 5 } 


------------------------------------------------------------

    histCtrlUnusedIndex OBJECT-TYPE
        SYNTAX INTEGER (1..2147483647)
        ACCESS read-only
        STATUS mandatory
        DESCRIPTION
            "An SNMP Get of this MIB object returns an un-used history control index number.  It can be used for
            history control table row creation optimization."
    ::= { empireHistory 3 }

    histCtrlMatchDescr OBJECT-TYPE
        SYNTAX SnmpAdminString (SIZE (0..512)) 
        ACCESS read-write
        STATUS mandatory
        DESCRIPTION
            "This MIB object, when used in conjunction with histCtrlMatchIndex can be used to quickly determine the
            index number corresponding to a particular entry description.  SNMP Set'ing a description to this MIB
            object causes the agent to search through entries in the history control table and place the index value
            of the last entry whose description matches, in the histCtrlMatchIndex MIB object."
    ::= { empireHistory 4 }

    histCtrlMatchIndex OBJECT-TYPE
        SYNTAX INTEGER (1..2147483647)
        ACCESS read-only
        STATUS mandatory
        DESCRIPTION
            "See description for histCtrlMatchDescr."
    ::= { empireHistory 5 }


------------------------------------------------------------
--  The Log Monitoring Table
------------------------------------------------------------
--  This group provides access to the agent's logfile monitoring
--  capabilities.  Via the logMonitorTable, managers can specify 
--  that the agent monitor certain log files for certain patterns
--  or regular expressions.  When a match has occurred, the agent
--  sends a Trap to appropriate managers.  Entries can be placed
--  in the logMonitorTable via two methods: through entries in the
--  agent configuration file (sysedge.cf) or via the SNMP.

    logMonitorTable OBJECT-TYPE
        SYNTAX SEQUENCE OF LogMonitorEntry
        ACCESS not-accessible
        STATUS mandatory
        DESCRIPTION
            "Table containing log monitor entries; each entry specifies a log file and regular expression. The agent
            periodically stats the log files to see if they have been updated.  If updated, the agent scans the new
            entries for the regular expression.  When that regular expression is found (or matched) in the new
            entries, a trap PDU is sent to appropriate managers."
    ::= { logMonitor 1 }

    logMonitorEntry OBJECT-TYPE
        SYNTAX LogMonitorEntry
        ACCESS not-accessible
        STATUS mandatory
        DESCRIPTION
            "An entry in the logMonitorTable."
        INDEX { logMonitorIndex }
    ::= { logMonitorTable 1 }

    LogMonitorEntry ::= SEQUENCE {
        logMonitorIndex             INTEGER,
        logMonitorLogFile           SnmpAdminString,
        logMonitorRegularExpression SnmpAdminString,
        logMonitorNumberTraps       INTEGER,
        logMonitorLastTrap          TimeTicks,
        logMonitorLastMatch         SnmpAdminString,
        logMonitorStatus            INTEGER,
        logMonitorLogFileSize       INTEGER,
        logMonitorLogFileLastUpdate TimeTicks,
        logMonitorDescr             SnmpAdminString,
        logMonitorAction            SnmpAdminString,
        logMonitorFlags             INTEGER,
        logMonitorMatches           Counter,
        logMonitorInterval          INTEGER,
        logMonitorLogFileName       SnmpAdminString,
        logMonitorLogFileCount      INTEGER,
        logMonitorSeverity          INTEGER
    }

    logMonitorIndex OBJECT-TYPE
        SYNTAX INTEGER (1..2147483647)
        ACCESS read-only
        STATUS mandatory
        DESCRIPTION
            "An index that uniquely identifies an entry in the logMonitorTable."
    ::= { logMonitorEntry 1 }

    logMonitorLogFile OBJECT-TYPE
        SYNTAX SnmpAdminString (SIZE (0..512))
        ACCESS read-write
        STATUS mandatory
        DESCRIPTION
            "The name of the log file to scan for pattern matches or the directory to scan for size.
            This variable must name a valid file or directory.
            For log file monitoring, wildchars * and ? are supported."
    ::= { logMonitorEntry 2 }

    logMonitorRegularExpression OBJECT-TYPE
        SYNTAX SnmpAdminString (SIZE (0..512))
        ACCESS read-write
        STATUS mandatory
        DESCRIPTION
            "The display string representation of the regular expression to match in the corresponding log file.
            Valid regular expressions are those as defined in ed(1)."
    ::= { logMonitorEntry 3 }

    logMonitorNumberTraps OBJECT-TYPE
        SYNTAX INTEGER
        ACCESS read-only
        STATUS mandatory
        DESCRIPTION
            "The number of traps sent for this monitor entry. One trap is sent for each match detected."
    ::= { logMonitorEntry 4 }

    logMonitorLastTrap OBJECT-TYPE
        SYNTAX TimeTicks
        ACCESS read-only
        STATUS mandatory
        DESCRIPTION
            "The time when the agent last sent a trap for this monitor entry.
            This relative time (R) is given in hundredths of a second since the agent was started. It can be
            converted into an absolute time (A) using sysUpTime (from MIB-II) and hrSystemDate (from HR-MIB).
            sysUpTime (S) is the elapsed time (in hundredths of a second) since the agent was started.
            hrSysDate (H) is the current absolute date and time (in DateAndTime format) and must be converted
            to Unix Time format (seconds elapsed since 01.01.1970). Finally calculate: A = H - S/100 + R/100"
    ::= { logMonitorEntry 5 }

    logMonitorLastMatch OBJECT-TYPE
        SYNTAX SnmpAdminString (SIZE (0..512))
        ACCESS read-only
        STATUS mandatory
        DESCRIPTION
            "The last log file entry that matched the logMonitorRegularExpression.  Each time a match occurs, this
            variable is updated."
    ::= { logMonitorEntry 6 }

    logMonitorStatus OBJECT-TYPE
        SYNTAX INTEGER {
            active(1),
            notInService(2),
            notReady(3),
            createAndGo(4),
            createAndWait(5),
            destroy(6)
        }
        ACCESS read-write
        STATUS mandatory
        DESCRIPTION
            "The status of this monitor entry according to the Textual Conventions for SNMPv2 (see RFC 1443).
            active(1)        - the row is available for usage
            notInService(2)  - setting to this value disables usage of the row
            notReady(3)      - an error occured during usage of the row
            createAndGo(4)   - setting to this value creates the row with row status set to active(1)
            createAndWait(5) - setting to this value creates the row with row status set to notInService(2)
            destroy(6)       - setting to this value deletes the row"
        DEFVAL { createAndWait }
    ::= { logMonitorEntry 7 }

    logMonitorLogFileSize OBJECT-TYPE
        SYNTAX INTEGER
        ACCESS read-only
        STATUS mandatory
        DESCRIPTION
            "The size in bytes/kilobytes of the log file/directory at time of last sample.
            By querying this value, one can tell if the log file/directory is growing."
    ::= { logMonitorEntry 8 }

    logMonitorLogFileLastUpdate OBJECT-TYPE
        SYNTAX TimeTicks
        ACCESS read-only
        STATUS mandatory
        DESCRIPTION
            "The time when the log file/directory was last modified by a process. Monitoring this value can
            indicate if the process that log to this file/directory is active.
            This relative time (R) is given in hundredths of a second since the agent was started. It can be
            converted into an absolute time (A) using sysUpTime (from MIB-II) and hrSystemDate (from HR-MIB).
            sysUpTime (S) is the elapsed time (in hundredths of a second) since the agent was started.
            hrSysDate (H) is the current absolute date and time (in DateAndTime format) and must be converted
            to Unix Time format (seconds elapsed since 01.01.1970). Finally calculate: A = H - S/100 + R/100"
    ::= { logMonitorEntry 9 }

    logMonitorDescr OBJECT-TYPE
        SYNTAX SnmpAdminString (SIZE (0..512))
        ACCESS read-write
        STATUS mandatory
        DESCRIPTION
            "A textual description of this entry possibly identifying the purpose of this entry and who created it."
    ::= { logMonitorEntry 10 }

    logMonitorAction OBJECT-TYPE
        SYNTAX SnmpAdminString (SIZE (0..2048))
        ACCESS read-write
        STATUS mandatory
        DESCRIPTION
            "The command (including parameters) to be executed concurrent to sending a trap."
    ::= { logMonitorEntry 11 }

    logMonitorFlags OBJECT-TYPE
        SYNTAX INTEGER
        ACCESS read-write
        STATUS mandatory
        DESCRIPTION
            "The flags is a bit field. Setting one or more bits changes the behavior of this monitor entry.
            000 000 01 - don't execute any actions (but send and log traps)
            000 000 02 - don't send any traps (but log traps and execute actions)
            000 000 04 - don't reinitialize notReady monitor
            000 000 08 - don't log any traps (but send traps and execute actions)
            000 000 10 - keep sending notReady traps
            000 000 20 - don't pass default arguments to actions
            000 000 40 - don't send notReady traps (including log and action)
            000 000 80 - entry was created by an AIM plugin (this flag is read-only)

            000 001 00 - apply logical 'not' operator
            000 002 00 - determine only file size
            xxx 004 00 - send match traps if more than xxx matches per read
            000 008 00 - monitor a directory (instead a file)
            000 010 00 - monitor the directory recursively
            000 020 00 - do not follow symbolic links (only for directory monitoring)
            000 040 00 - report logMonitorLogFileSize variable in kilobytes (instead of bytes)"
    ::= { logMonitorEntry 12 }

    logMonitorMatches OBJECT-TYPE
        SYNTAX Counter
        ACCESS read-only
        STATUS mandatory
        DESCRIPTION
            "The number of logfile entries matching the regular expression; this value is incremented regardless of
             whether Traps are sent for this entry or not.  Polling this variable allows you to determine the rate or
             number of matches over time."
    ::= { logMonitorEntry 13 }

    logMonitorInterval OBJECT-TYPE
        SYNTAX INTEGER (1..1440)
        ACCESS read-write
        STATUS mandatory
        DESCRIPTION
            "The interval, in MINUTES, between successive scans of the log file. The sampling period is not exact but
            represents a best-effort by the agent."
        DEFVAL { 1 }
    ::= { logMonitorEntry 14 }

    logMonitorLogFileName OBJECT-TYPE
        SYNTAX SnmpAdminString (SIZE (0..512))
        ACCESS read-only
        STATUS mandatory
        DESCRIPTION
            "Actual filename that is monitored in case of wildchars are used for logMonitorLogFile."
    ::= { logMonitorEntry 15 }

    logMonitorLogFileCount OBJECT-TYPE
        SYNTAX INTEGER
        ACCESS read-only
        STATUS mandatory
        DESCRIPTION
            "In case of directory monitoring the total number of files and subdirectories,
            either recursive or not (see logMonitorFlags). In case of file monitoring
            the value is 0 or 1, depending on the existence of the monitored file."
    ::= { logMonitorEntry 16 }

    logMonitorSeverity OBJECT-TYPE
        SYNTAX INTEGER {
            none(1),
            ok(2),
            warning(3),
            minor(4),
            major(5),
            critical(6),
            fatal(7)
        }
        ACCESS read-write
        STATUS mandatory
        DESCRIPTION
            "The severity to use for this monitor entry. Logfile monitors do not implement an object state model,
            but they allow to specify a severity, that is sent with the corresponding SNMP traps."
        DEFVAL { none }
    ::= { logMonitorEntry 17 }

------------------------------------------------------------

    logmonUnusedIndex OBJECT-TYPE
        SYNTAX INTEGER (1..2147483647)
        ACCESS read-only
        STATUS mandatory
        DESCRIPTION
            "An SNMP Get of this MIB object returns an un-used logfile monitor index number.  It can be used for
            logfile monitor table row creation optimization."
    ::= { logMonitor 2 }

    logmonMatchDescr OBJECT-TYPE
        SYNTAX SnmpAdminString (SIZE (0..512))
        ACCESS read-write
        STATUS mandatory
        DESCRIPTION
            "This MIB object, when used in conjunction with logmonMatchIndex can be used to quickly determine the
            index number corresponding to a particular entry description.  SNMP Set'ing a description to this MIB
            object causes the agent to search through entries in the logfile monitor table and place the index value
            of the last entry whose description matches, in the logmonMatchIndex MIB object."
    ::= { logMonitor 3 }

    logmonMatchIndex OBJECT-TYPE
        SYNTAX INTEGER (1..2147483647)
        ACCESS read-only
        STATUS mandatory
        DESCRIPTION
            "See description for logmonMatchDescr."
    ::= { logMonitor 4 }


------------------------------------------------------------
--  The Disk Stats Table
------------------------------------------------------------
--  Includes table of disk I/O statistics.

    diskStatsTable OBJECT-TYPE
        SYNTAX SEQUENCE OF DiskStatsEntry
        ACCESS not-accessible
        STATUS mandatory
        DESCRIPTION
            "Table containing disk I/O stat entries; each entry provides the latest disk statistics for one disk. The
            agent periodically stats the system data structures for each disk and records the values in the table."
    ::= { diskGroup 1 }

    diskStatsEntry OBJECT-TYPE
        SYNTAX DiskStatsEntry
        ACCESS not-accessible
        STATUS mandatory
        DESCRIPTION
            "An entry in the diskStatsTable."
        INDEX { diskStatsIndex }
    ::= { diskStatsTable 1 }

    DiskStatsEntry ::= SEQUENCE {
        diskStatsIndex                INTEGER,
        diskStatsQueueLength          Gauge,
        diskStatsServiceTime          Gauge,
        diskStatsUtilization          INTEGER,
        diskStatsKBytesTransferred    Counter,
        diskStatsTransfers            Counter,
        diskStatsReads                Counter,
        diskStatsWrites               Counter,
        diskStatsHostmibDevTableIndex INTEGER,
        diskStatsLastUpdate           TimeTicks,
        diskStatsKBytesXferStr        DisplayString,
        diskStatsTransfersStr         DisplayString,
        diskStatsReadsStr             DisplayString,
        diskStatsWritesStr            DisplayString,
        diskStatsKBytesXferHi         Counter,
        diskStatsXferOpsHi            Counter,
        diskStatsReadsHi              Counter,
        diskStatsWritesHi             Counter,
        diskStatsAvgBytesRead         Gauge,
        diskStatsAvgBytesWrite        Gauge,
        diskStatsReadTime             INTEGER,
        diskStatsWriteTime            INTEGER,
        diskStatsReadBytessec         Gauge,
        diskStatsWriteBytessec        Gauge,
        diskStatsAvWait               Gauge,
        diskStatsBlkss                Gauge,
        diskStatsRWs                  Gauge,
        diskStatsDeviceDescr          DisplayString,
		diskStatsStorageCapacity      Gauge
    }

    diskStatsIndex OBJECT-TYPE
        SYNTAX INTEGER (1..2147483647)
        ACCESS read-only
        STATUS mandatory
        DESCRIPTION
            "An index that uniquely identifies an entry in the diskStatsTable."
    ::= { diskStatsEntry 1 } 

    diskStatsQueueLength OBJECT-TYPE
        SYNTAX Gauge
        ACCESS read-only
        STATUS mandatory
        DESCRIPTION
            "The average number of operations waiting in the disk's service queue over the last measurement period."
    ::= { diskStatsEntry 2 } 

    diskStatsServiceTime OBJECT-TYPE
        SYNTAX Gauge
        ACCESS read-only
        STATUS mandatory
        DESCRIPTION
            "The average service time in milliseconds for operations served on this disk over the last measurement
            period. This could be expressed as: disk-busy-time / number-of-transfers."
    ::= { diskStatsEntry 3 } 

    diskStatsUtilization OBJECT-TYPE
        SYNTAX INTEGER (0..100)
        ACCESS read-only
        STATUS mandatory
        DESCRIPTION
            "The utilization rate (percentage utilization) for this disk over the last measurement period. This could
            also be expressed as: (disk-busy-time / elapsed-time) * 100."
    ::= { diskStatsEntry 4 } 

    diskStatsKBytesTransferred OBJECT-TYPE
        SYNTAX Counter
        ACCESS read-only
        STATUS mandatory
        DESCRIPTION
            "The number of KBytes transferred to/from this disk."
    ::= { diskStatsEntry 5 } 

    diskStatsTransfers OBJECT-TYPE
        SYNTAX Counter
        ACCESS read-only
        STATUS mandatory
        DESCRIPTION
            "The number of transfer operations to/from this disk."
    ::= { diskStatsEntry 6 } 

    diskStatsReads OBJECT-TYPE
        SYNTAX Counter
        ACCESS read-only
        STATUS mandatory
        DESCRIPTION
            "The number of read operations from this disk."
    ::= { diskStatsEntry 7 } 

    diskStatsWrites OBJECT-TYPE
        SYNTAX Counter
        ACCESS read-only
        STATUS mandatory
        DESCRIPTION
            "The number of write operations to this disk."
    ::= { diskStatsEntry 8 } 

    diskStatsHostmibDevTableIndex OBJECT-TYPE
        SYNTAX INTEGER (1..2147483647)
        ACCESS read-only
        STATUS mandatory
        DESCRIPTION
            "The index of this disk device in the device table of the Host Resources MIB."
    ::= { diskStatsEntry 9 } 

    diskStatsLastUpdate OBJECT-TYPE
        SYNTAX TimeTicks
        ACCESS read-only
        STATUS mandatory
        DESCRIPTION
            "The time (in hundredths of a second since the agent was started) of the last update of
            this diskStatsTable entry."
    ::= { diskStatsEntry 10 } 

--  64-bit counters are support via high/low values and string representations

    diskStatsKBytesXferStr OBJECT-TYPE
        SYNTAX DisplayString
        ACCESS read-only
        STATUS mandatory
        DESCRIPTION
            "Number of KBbytes transfered to/from this disk in ascii string format so that 64-bit values can be
            passed w/o having to go through high/low order word calculations."
    ::= { diskStatsEntry 11 } 

    diskStatsTransfersStr OBJECT-TYPE
        SYNTAX DisplayString
        ACCESS read-only
        STATUS mandatory
        DESCRIPTION
            "Number of transfer operations to/from this disk in ascii string format so that 64-bit values can be
            passed w/o having to go through high/low order word calculations."
    ::= { diskStatsEntry 12 } 

    diskStatsReadsStr OBJECT-TYPE
        SYNTAX DisplayString
        ACCESS read-only
        STATUS mandatory
        DESCRIPTION
            "The number of read operations from this disk in ascii string format so that 64-bit values can be passed
            w/o having to go through high/low order word calculations. "
    ::= { diskStatsEntry 13 } 

    diskStatsWritesStr OBJECT-TYPE
        SYNTAX DisplayString
        ACCESS read-only
        STATUS mandatory
        DESCRIPTION
            "The number of write operations to this disk in ascii string format so that 64-bit values can be passed
            w/o having to go through high/low order word calculations."
    ::= { diskStatsEntry 14 } 

    diskStatsKBytesXferHi OBJECT-TYPE
        SYNTAX Counter
        ACCESS read-only
        STATUS mandatory
        DESCRIPTION
            "High-order 32-bits of diskStatsKBytesTransferred if the underlying system supports 64-bit disk stats;
            zero otherwise.  Recovering the 64-bit counter is as simple as: diskStatsKBytesXferHi << 32 |
            diskStatsKBytesTransferred"
    ::= { diskStatsEntry 15 }

    diskStatsXferOpsHi OBJECT-TYPE
        SYNTAX Counter
        ACCESS read-only
        STATUS mandatory
        DESCRIPTION
            "High-order 32-bits of diskStatsTransfers if the underlying system supports 64-bit disk stats; zero
            otherwise.  Recovering the 64-bit counter is as simple as: diskStatsXferOpsHi << 32 | diskStatsTransfers"
    ::= { diskStatsEntry 16 }

    diskStatsReadsHi OBJECT-TYPE
        SYNTAX Counter
        ACCESS read-only
        STATUS mandatory
        DESCRIPTION
            "High-order 32-bits of diskStatsReads if the underlying system supports 64-bit disk stats; zero
            otherwise.  Recovering the 64-bit counter is as simple as: diskStatsReadsHi << 32 | diskStatsReads"
    ::= { diskStatsEntry 17 }

    diskStatsWritesHi OBJECT-TYPE
        SYNTAX Counter
        ACCESS read-only
        STATUS mandatory
        DESCRIPTION
            "High-order 32-bits of diskStatsWrites if the underlying system supports 64-bit disk stats; zero
            otherwise.  Recovering the 64-bit counter is as simple as: diskStatsWritesHi << 32 | diskStatsWrites"
    ::= { diskStatsEntry 18 }

    diskStatsAvgBytesRead OBJECT-TYPE
        SYNTAX Gauge
        ACCESS read-only
        STATUS mandatory
        DESCRIPTION
            "Average number of bytes transferred from the disk during read operations."
    ::= { diskStatsEntry 19 } 

    diskStatsAvgBytesWrite OBJECT-TYPE
        SYNTAX Gauge
        ACCESS read-only
        STATUS mandatory
        DESCRIPTION
            "Average number of bytes transferred from the disk during write operations."
    ::= { diskStatsEntry 20 } 
	
    diskStatsReadTime OBJECT-TYPE
        SYNTAX INTEGER (0..100)
        ACCESS read-only
        STATUS mandatory
        DESCRIPTION
            "Percentage of elapsed time that the selected disk drive is busy servicing read requests."
    ::= { diskStatsEntry 21 } 

    diskStatsWriteTime OBJECT-TYPE
        SYNTAX INTEGER (0..100)
        ACCESS read-only
        STATUS mandatory
        DESCRIPTION
            "Percentage of elapsed time that the selected disk drive is busy servicing write requests."
    ::= { diskStatsEntry 22 } 

    diskStatsReadBytessec OBJECT-TYPE
        SYNTAX Gauge
        ACCESS read-only
        STATUS mandatory
        DESCRIPTION
            "The rate at which bytes are transferred from the disk during read operations."
    ::= { diskStatsEntry 23 } 	

    diskStatsWriteBytessec OBJECT-TYPE
        SYNTAX Gauge
        ACCESS read-only
        STATUS mandatory
        DESCRIPTION
            "The rate at which bytes are transferred to the disk during write operations."
    ::= { diskStatsEntry 24 } 	

    diskStatsAvWait OBJECT-TYPE
        SYNTAX Gauge
        ACCESS read-only
        STATUS mandatory
        DESCRIPTION
            "avwait - Average time in milliseconds that transfer requests waited idly on queue for the device."
    ::= { diskStatsEntry 25 }

    diskStatsBlkss OBJECT-TYPE
        SYNTAX Gauge
        ACCESS read-only
        STATUS mandatory
        DESCRIPTION
            "blks/s - Number of bytes transferred (in 512-byte units) from and to the device."
    ::= { diskStatsEntry 26 }

    diskStatsRWs OBJECT-TYPE
        SYNTAX Gauge
        ACCESS read-only
        STATUS mandatory
        DESCRIPTION
            "r+w/s - Number of data transfers per second (read and writes) from and to the device."
    ::= { diskStatsEntry 27 }
	
    diskStatsDeviceDescr OBJECT-TYPE
        SYNTAX DisplayString (SIZE (0..64))
        ACCESS read-only
        STATUS mandatory
        DESCRIPTION
            "A textual description of this device, including the device's manufacturer and
             revision, and optionally, its serial number.
             This is a duplicate of 'hrDeviceDescr' (1.3.6.1.2.1.25.3.2.1.3) for the specified disk."
    ::= { diskStatsEntry 28 } 

    diskStatsStorageCapacity OBJECT-TYPE
        SYNTAX Gauge 
        ACCESS read-write
        STATUS mandatory
        DESCRIPTION
            "The total size (in KBytes) for this device.
             This is a duplicate of 'hrDiskStorageCapacity' (1.3.6.1.2.1.25.3.6.1.4), but 
             can handle much larger disk sizes due to 64-bit counter implementation.
             Note that the SYNTAX of this attribute actually is Counter64."
    ::= { diskStatsEntry 29 }


------------------------------------------------------------
--  The CPU Stats Table
------------------------------------------------------------
--  Includes per-CPU statistics

    cpuStatsTable OBJECT-TYPE
        SYNTAX SEQUENCE OF CpuStatsEntry
        ACCESS not-accessible
        STATUS mandatory
        DESCRIPTION
            "This table provides per-cpu statistics and counters; the agent periodically (approximately every 60
            seconds) updates data contained in this table.  By periodically sampling entries in this table, one can
            determine the percentage of time spent by each CPU in their respective modes. This percentage can be
            calculated by summing the total 'ticks' spent in each mode and then dividing the 'ticks' spent in each
            mode by the total. 'Ticks' is a system-dependent quantity whose unit is not necessary when calculating
            the percentage of time spent in each CPU mode."
    ::= { cpuGroup 1 }

    cpuStatsEntry OBJECT-TYPE
        SYNTAX CpuStatsEntry
        ACCESS not-accessible
        STATUS mandatory
        DESCRIPTION
            "An entry in the cpuStatsTable"
        INDEX { cpuStatsIndex }
    ::= { cpuStatsTable 1 }

    CpuStatsEntry ::= SEQUENCE {
        cpuStatsIndex       INTEGER,
        cpuStatsDescr       DisplayString,
        cpuStatsIdle        Counter,
        cpuStatsUser        Counter,
        cpuStatsSys         Counter,
        cpuStatsWait        Counter,
        cpuStatsLastUpdate  TimeTicks,
        cpuStatsIdlePercent INTEGER,
        cpuStatsUserPercent INTEGER,
        cpuStatsSysPercent  INTEGER,
        cpuStatsWaitPercent INTEGER,
        cpuStatsPC          INTEGER,
        cpuStatsEC          INTEGER,
		cpuStatsUtilPercent	INTEGER	
    }

    cpuStatsIndex OBJECT-TYPE
        SYNTAX INTEGER (1..2147483647)
        ACCESS read-only
        STATUS mandatory
        DESCRIPTION
            "An index that uniquely identifies an entry in the cpuStatsTable."
    ::= { cpuStatsEntry 1 }

    cpuStatsDescr OBJECT-TYPE
        SYNTAX DisplayString (SIZE (0..64))
        ACCESS read-only
        STATUS mandatory
        DESCRIPTION
            "The type of CPU for which statistics are reported. On Solaris 2.x, this description also includes the
            CPU's clock speed."
    ::= { cpuStatsEntry 2 }

    cpuStatsIdle OBJECT-TYPE
        SYNTAX Counter
        ACCESS read-only
        STATUS mandatory
        DESCRIPTION
            "The total number of 'ticks' spent by this CPU in Idle mode.  This variable is not supported by NT. This
            value may wrap 32-bit counter."
    ::= { cpuStatsEntry 3 }

    cpuStatsUser OBJECT-TYPE
        SYNTAX Counter
        ACCESS read-only
        STATUS mandatory
        DESCRIPTION
            "The total number of 'ticks' spent by this CPU in User mode.  This value may wrap 32-bit counter."
    ::= { cpuStatsEntry 4 }

    cpuStatsSys OBJECT-TYPE
        SYNTAX Counter
        ACCESS read-only
        STATUS mandatory
        DESCRIPTION
            "The total number of 'ticks' spent by this CPU in Kernel or system mode.  This value may wrap a 32-bit
            counter."
    ::= { cpuStatsEntry 5 }

    cpuStatsWait OBJECT-TYPE
        SYNTAX Counter
        ACCESS read-only
        STATUS mandatory
        DESCRIPTION
            "The total number of 'ticks' spent by this CPU in Wait mode.  Wait mode is that time spent waiting on I/O
            or swap.  It may wrap a 32-bit counter."
    ::= { cpuStatsEntry 6 }

    cpuStatsLastUpdate OBJECT-TYPE
        SYNTAX TimeTicks
        ACCESS read-only
        STATUS mandatory
        DESCRIPTION
            "The time (in hundredths of a second since the agent was started) that the counters for this CPU were
            last updated. Because these values are cached periodically by the agent, the time of last update is
            important for determining the interval over which CPU mode percentages are calculated."
    ::= { cpuStatsEntry 7 }

    cpuStatsIdlePercent OBJECT-TYPE
        SYNTAX INTEGER (0..100)
        ACCESS read-only
        STATUS mandatory
        DESCRIPTION
            "The percentage of time (over the sample period) that the system's CPU was idle."
    ::= { cpuStatsEntry 8 }

    cpuStatsUserPercent OBJECT-TYPE
        SYNTAX INTEGER (0..100)
        ACCESS read-only
        STATUS mandatory
        DESCRIPTION
            "The percentage of time (over the sample period) that the system's CPU was executing in user mode."
    ::= { cpuStatsEntry 9 }

    cpuStatsSysPercent OBJECT-TYPE
        SYNTAX INTEGER (0..100)
        ACCESS read-only
        STATUS mandatory
        DESCRIPTION
            "The percentage of time (over the sample period) that the system's CPU was executing the kernel or
            operating system."
    ::= { cpuStatsEntry 10 }

    cpuStatsWaitPercent OBJECT-TYPE
        SYNTAX INTEGER (0..100)
        ACCESS read-only
        STATUS mandatory
        DESCRIPTION
            "The percentage of time (over the sample period) that the system's CPU was waiting for I/O.  This object
            may not be supported by the underlying operating system."
    ::= { cpuStatsEntry 11 }

    cpuStatsPC OBJECT-TYPE
         SYNTAX INTEGER
         ACCESS read-only
         STATUS mandatory
         DESCRIPTION
	     "Number of physical processors consumed (pc) by logical CPU. The value reported is 'pc'
	      multiplied by 100. For example, the value 80 represents 'pc' of 0.8.
	      Supported in SystemEDGE 4.3.4 and higher for AIX."
    ::= { cpuStatsEntry 12 }		


    cpuStatsEC OBJECT-TYPE
         SYNTAX INTEGER
         ACCESS read-only
         STATUS mandatory
         DESCRIPTION
              "The percentage of entitled capacity consumed (ec) by logical CPU.
               Supported in SystemEDGE 4.3.4 and higher for AIX."
    ::= { cpuStatsEntry 13 }		

    cpuStatsUtilPercent OBJECT-TYPE
         SYNTAX INTEGER
         ACCESS read-only
         STATUS mandatory
         DESCRIPTION
             "The percentage of time (over the sample period) that the system's CPU was utilized."
    ::= { cpuStatsEntry 14 }		

	
------------------------------------------------------------
--  The CPU Totals Group
------------------------------------------------------------

    cpuTotalIdle OBJECT-TYPE
        SYNTAX Counter
        ACCESS read-only
        STATUS mandatory
        DESCRIPTION
            "The total number of 'ticks' spent by all CPUs in Idle mode.  This variable is not supported by NT. This
            value may wrap 32-bit counter."
    ::= { cpuGroup 2 }

    cpuTotalUser OBJECT-TYPE
        SYNTAX Counter
        ACCESS read-only
        STATUS mandatory
        DESCRIPTION
            "The total number of 'ticks' spent by all CPUs in User mode.  This value may wrap 32-bit counter."
    ::= { cpuGroup 3 }

    cpuTotalSys OBJECT-TYPE
        SYNTAX Counter
        ACCESS read-only
        STATUS mandatory
        DESCRIPTION
            "The total number of 'ticks' spent by all CPUs in Kernel or system mode.  This value may wrap a 32-bit
            counter."
    ::= { cpuGroup 4 }

    cpuTotalWait OBJECT-TYPE
        SYNTAX Counter
        ACCESS read-only
        STATUS mandatory
        DESCRIPTION
            "The total number of 'ticks' spent by all CPUs in Wait mode.  Wait mode is that time spent waiting on I/O
            or swap.  It may wrap a 32-bit counter."
    ::= { cpuGroup 5 }

    cpuTotalLastUpdate OBJECT-TYPE
        SYNTAX TimeTicks
        ACCESS read-only
        STATUS mandatory
        DESCRIPTION
            "The time (in hundredths of a second since the agent was started) that these counters were last updated.
            Because these values are cached periodically by the agent, the time of last update is important for
            determining the interval over which CPU mode percentages are calculated."
    ::= { cpuGroup 6 }

    cpuTotalIdlePercent OBJECT-TYPE
        SYNTAX INTEGER (0..100)
        ACCESS read-only
        STATUS mandatory
        DESCRIPTION
            "The percentage of time (over the sample period) that the system's CPUs were idle."
    ::= { cpuGroup 7 }

    cpuTotalUserPercent OBJECT-TYPE
        SYNTAX INTEGER (0..100)
        ACCESS read-only
        STATUS mandatory
        DESCRIPTION
            "The percentage of time (over the sample period) that the system's CPUs were executing in user mode."
    ::= { cpuGroup 8 }

    cpuTotalSysPercent OBJECT-TYPE
        SYNTAX INTEGER (0..100)
        ACCESS read-only
        STATUS mandatory
        DESCRIPTION
            "The percentage of time (over the sample period) that the system's CPUs were executing the kernel or
            operating system."
    ::= { cpuGroup 9 }

    cpuTotalWaitPercent OBJECT-TYPE
        SYNTAX INTEGER (0..100)
        ACCESS read-only
        STATUS mandatory
        DESCRIPTION
            "The percentage of time (over the sample period) that the system's CPUs were waiting for I/O.  This
             object may not be supported by the underlying operating system."
    ::= { cpuGroup 10 }

    cpuTotalPC OBJECT-TYPE
         SYNTAX INTEGER
         ACCESS read-only
         STATUS mandatory
         DESCRIPTION
             "Number of physical processors consumed (pc) by all assigned logical CPUs. The value reported
              is 'pc' multiplied by 100. For example, the value 80 represents 'pc' of 0.8.
              Supported in SystemEDGE 4.3.4 and higher for AIX."
    ::= { cpuGroup 11 }		

    cpuTotalEC OBJECT-TYPE
         SYNTAX INTEGER
         ACCESS read-only
         STATUS mandatory
         DESCRIPTION
             "The percentage of entitled capacity consumed (ec) by all assigned logical CPUs.
              Supported in SystemEDGE 4.3.4 and higher for AIX."
    ::= { cpuGroup 12 }		

    cpuTotalUtilPercent OBJECT-TYPE
         SYNTAX INTEGER
         ACCESS read-only
         STATUS mandatory
         DESCRIPTION
             "The percentage of time (over the sample period) that the system's CPUs were utilized."
    ::= { cpuGroup 13 }		

	
------------------------------------------------------------
--  The Extension Group
------------------------------------------------------------
--  This group allows users of the SystemEDGE Agent to extend the
--  Concord/Empire Enterprise MIB by adding new scalar variables. Each
--  leaf in this group specifies a different MIB scalar value. The
--  values for these variables are determined by executing a command
--  on the host where the agent is running.  The command is specified
--  in the SystemEDGE configuration file (sysedge.cf) See the
--  SystemEDGE Agent User Manual for more information. 

--  extensionGroup OBJECT IDENTIFIER ::= { empire 14 }  defined above


------------------------------------------------------------
--  The Process Monitoring Table
------------------------------------------------------------

    processMonTable OBJECT-TYPE
        SYNTAX SEQUENCE OF ProcessMonEntry
        ACCESS not-accessible
        STATUS mandatory
        DESCRIPTION
            "The process monitor table is used for monitoring single instances of processes."
    ::= { processMonitor 1 }

    processMonEntry OBJECT-TYPE
        SYNTAX ProcessMonEntry
        ACCESS not-accessible
        STATUS mandatory
        DESCRIPTION
            ""
        INDEX { pmonIndex }
    ::= { processMonTable 1 }

    ProcessMonEntry ::= SEQUENCE {
        pmonIndex          INTEGER,
        pmonDescr          SnmpAdminString,
        pmonInterval       INTEGER,
        pmonSampleType     INTEGER,
        pmonAttribute      INTEGER,
        pmonCurrVal        INTEGER,
        pmonOperator       INTEGER,
        pmonValue          INTEGER,
        pmonLastCall       TimeTicks,
        pmonNumTraps       INTEGER,
        pmonLastTrap       TimeTicks,
        pmonFlags          INTEGER,
        pmonAction         SnmpAdminString,
        pmonRegExpr        SnmpAdminString,
        pmonMinValue       INTEGER,
        pmonMaxValue       INTEGER,
        pmonCurrentPID     INTEGER,
        pmonRowStatus      INTEGER,
        pmonNumEvents      Counter,
        pmonObjClass       SnmpAdminString,
        pmonObjInstance    SnmpAdminString,
        pmonObjAttribute   SnmpAdminString,
        pmonSeverity       INTEGER,
        pmonCurrState      INTEGER,
        pmonZoneRegExp     DisplayString,
        pmonProcName       SnmpAdminString,
        pmonAutoWatchIndex INTEGER,
        pmonAutoWatchName  SnmpAdminString
    }

    pmonIndex OBJECT-TYPE
        SYNTAX INTEGER (1..2147483647)
        ACCESS read-only
        STATUS mandatory
        DESCRIPTION
            "A unique value for the table entry, not necessarily being contiguous, but unique."
    ::= { processMonEntry 1 }

    pmonDescr OBJECT-TYPE
        SYNTAX SnmpAdminString (SIZE (0..512))
        ACCESS read-write
        STATUS mandatory
        DESCRIPTION
            "A textual description of the entry, possibly identifying its purpose and who created it." 
    ::= { processMonEntry 2 }

    pmonInterval OBJECT-TYPE
        SYNTAX INTEGER (1..2147483647)
        ACCESS read-write
        STATUS mandatory
        DESCRIPTION
            "The interval, in seconds, between successive samples by the agent. It must be a multiple of 30 seconds.
            The sampling period is not exact but represents a best-effort by the agent." 
        DEFVAL { 60 }
    ::= { processMonEntry 3 }

    pmonSampleType OBJECT-TYPE
        SYNTAX INTEGER {
            absoluteValue(1),
            deltaValue(2)
        }
        ACCESS read-write
        STATUS mandatory
        DESCRIPTION
            "The type of sampling performed on the monitored object.
            To monitor the rate of change (e.g. for a Counter typed object) use deltaValue.
            To monitor the absolute value (e.g. for a Gauge typed object) use absoluteValue."
        DEFVAL { absoluteValue }
    ::= { processMonEntry 4 }

    pmonAttribute OBJECT-TYPE
        SYNTAX INTEGER {
            procAlive(1),
            procMEM(2),
            procSize(3),
            procRSS(4),
            procTime(5),
            procInBlks(6),
            procOutBlks(7),
            procMsgsSent(8),
            procMsgsRecv(9),
            procNice(10),
            procNumThreads(11),
            procNumSwaps(12),
            procSysCalls(13),
            procMinorPgFlts(14),
            procMajorPgFlts(15),
            procVolCtx(16),
            procInvolCtx(17),
            procTimePermil(18)
        }
        ACCESS read-write
        STATUS mandatory
        DESCRIPTION
            "The process attribute being monitored, mapping directly to a column in the processTable.
            Please note that not all attributes are available on all OS. See the following list:
                procAlive(1)         -  all
                procMEM(2)           -  all
                procSize(3)          -  all 
                procRSS(4)           -  all
                procTime(5)          -  all
                procInBlks(6)        -  Solaris, AIX, Tru64
                procOutBlks(7)       -  Solaris, AIX, Tru64
                procMsgsSent(8)      -  Solaris, AIX, Tru64, HPUX
                procMsgsRecv(9)      -  Solaris, AIX, Tru64, HPUX
                procNice(10)         -  all
                procNumThreads(11)   -  Solaris, AIX,              Linux, Windows
                procNumSwaps(12)     -  Solaris, AIX, Tru64, HPUX
                procSysCalls(13)     -  Solaris,             HPUX
                procMinorPgFlts(14)  -  Solaris, AIX, Tru64, HPUX, Linux
                procMajorPgFlts(15)  -  all
                procVolCtx(16)       -  Solaris, AIX, Tru64
                procInvolCtx(17)     -  Solaris, AIX, Tru64
                procTimePermil(18)   -  all
            In case the attribute is not available, a SNMP SET operation returns 'Bad Value' error."
        DEFVAL { procAlive }
    ::= { processMonEntry 5 }

    pmonCurrVal OBJECT-TYPE
        SYNTAX INTEGER
        ACCESS read-only
        STATUS mandatory
        DESCRIPTION
            "The value of the monitored object as last sampled by the agent, if pmonSampleType is absoluteValue(1).
            If pmonSampleType is deltaValue(2), then this value is the difference between two successive samples."
    ::= { processMonEntry 6 }

    pmonOperator OBJECT-TYPE
        SYNTAX INTEGER {
            nop(1),
            gt(2),
            lt(3),
            ge(4),
            le(5),
            eq(6),
            ne(7)
        }
        ACCESS read-write
        STATUS mandatory
        DESCRIPTION
            "The boolean operator that is used to compare the current value to the threshold value.
            nop(1) is used to only track the current value, but do not compare to the threshold.
            For procAlive(1), the agent ignores this setting and sets it internally."
        DEFVAL { nop }
    ::= { processMonEntry 7 }

    pmonValue OBJECT-TYPE
        SYNTAX INTEGER
        ACCESS read-write
        STATUS mandatory
        DESCRIPTION
            "The threshold value against which the agent compares the current value.
            For procAlive(1), the agent ignores this setting and sets it internally."
    ::= { processMonEntry 8 }

    pmonLastCall OBJECT-TYPE
        SYNTAX TimeTicks
        ACCESS read-only
        STATUS mandatory
        DESCRIPTION
            "The time when the agent last sampled the monitored object.
            This relative time (R) is given in hundredths of a second since the agent was started. It can be
            converted into an absolute time (A) using sysUpTime (from MIB-II) and hrSystemDate (from HR-MIB).
            sysUpTime (S) is the elapsed time (in hundredths of a second) since the agent was started.
            hrSysDate (H) is the current absolute date and time (in DateAndTime format) and must be converted
            to Unix Time format (seconds elapsed since 01.01.1970). Finally calculate: A = H - S/100 + R/100"
    ::= { processMonEntry 9 }

    pmonNumTraps OBJECT-TYPE
        SYNTAX INTEGER
        ACCESS read-only
        STATUS mandatory
        DESCRIPTION
            "The number of traps sent for this monitor entry. Dependent from pmonFlags, it could
            represent a lower bound on the number of times the threshold has actually been crossed."
    ::= { processMonEntry 10 }

    pmonLastTrap OBJECT-TYPE
        SYNTAX TimeTicks
        ACCESS read-only
        STATUS mandatory
        DESCRIPTION
            "The time when the agent last sent a trap for this monitor entry.
            This relative time (R) is given in hundredths of a second since the agent was started. It can be
            converted into an absolute time (A) using sysUpTime (from MIB-II) and hrSystemDate (from HR-MIB).
            sysUpTime (S) is the elapsed time (in hundredths of a second) since the agent was started.
            hrSysDate (H) is the current absolute date and time (in DateAndTime format) and must be converted
            to Unix Time format (seconds elapsed since 01.01.1970). Finally calculate: A = H - S/100 + R/100"
    ::= { processMonEntry 11 }

    pmonFlags OBJECT-TYPE
        SYNTAX INTEGER 
        ACCESS read-write
        STATUS mandatory
        DESCRIPTION
            "The flags is a bit field. Setting one or more bits changes the behavior of this monitor entry.
            000 000 01 - don't execute any actions (but send and log traps)
            000 000 02 - don't send any traps (but log traps and execute actions)
            000 000 04 - don't reinitialize notReady monitor
            000 000 08 - don't log any traps (but send traps and execute actions)
            000 000 10 - keep sending notReady traps
            000 000 20 - don't pass default arguments to actions
            000 000 40 - don't send notReady traps (including log and action)
            000 000 80 - entry was created by an AIM plugin (this flag is read-only)

            000 001 00 - monitor parent process (parent must match regexpr too)
            000 002 00 - don't send processStart traps (including log and action)
            000 004 00 - send processClear traps (including log and action)
            000 008 00 - match process name and arguments
            xxx 010 00 - send processThreshold/Stop traps after xxx consecutive breaches (including log and action)
            xxx 020 00 - send at most xxx consecutive processThreshold/Stop traps (including log and action)
            xxx 040 00 - monitor for xxx processes to be alive (procAlive)
            000 080 00 - monitor Windows service to be running (procAlive) or process in Solaris Zone
            000 100 00 - effectively the same as 000 002 00 (for legacy support)
            000 200 00 - aggregate state of all monitors with same severity as AND relation"
    ::= { processMonEntry 12 }

    pmonAction OBJECT-TYPE
        SYNTAX SnmpAdminString (SIZE (0..2048))
        ACCESS read-write
        STATUS mandatory
        DESCRIPTION
            "The command (including parameters) to be executed concurrent to sending a trap."
    ::= { processMonEntry 13 }

    pmonRegExpr OBJECT-TYPE
        SYNTAX SnmpAdminString (SIZE (0..512))
        ACCESS read-write
        STATUS mandatory
        DESCRIPTION
            "Dependent from pmonFlags (0x8000), the regular expression to use for matching processes by name,
            processes in Solaris Zones (use ZoneRegExpr/ProcRegExpr), or Windows services by name."
    ::= { processMonEntry 14 }

    pmonMinValue OBJECT-TYPE
        SYNTAX INTEGER 
        ACCESS read-only
        STATUS mandatory
        DESCRIPTION
            "The minimum value sampled."
    ::= { processMonEntry 15 }

    pmonMaxValue OBJECT-TYPE
        SYNTAX INTEGER 
        ACCESS read-only
        STATUS mandatory
        DESCRIPTION
            "The maximum value sampled."
    ::= { processMonEntry 16 }

    pmonCurrentPID OBJECT-TYPE
        SYNTAX INTEGER 
        ACCESS read-write
        STATUS mandatory
        DESCRIPTION
            "The PID of the process being monitored. If monitoring a Windows service (see pmonFlags),
            this is index (ntServiceIndex) of the service in the ntServiceTable."
    ::= { processMonEntry 17 }

    pmonRowStatus OBJECT-TYPE
        SYNTAX INTEGER {
            active(1),
            notInService(2),
            notReady(3),
            createAndGo(4),
            createAndWait(5),
            destroy(6)
        }
        ACCESS read-write
        STATUS mandatory
        DESCRIPTION
            "The status of this monitor entry according to the Textual Conventions for SNMPv2 (see RFC 1443).
            active(1)        - the row is available for usage
            notInService(2)  - setting to this value disables usage of the row
            notReady(3)      - an error occured during usage of the row
            createAndGo(4)   - setting to this value creates the row with row status set to active(1)
            createAndWait(5) - setting to this value creates the row with row status set to notInService(2)
            destroy(6)       - setting to this value deletes the row"
        DEFVAL { createAndWait } 
    ::= { processMonEntry 18 }

    pmonNumEvents OBJECT-TYPE
        SYNTAX Counter
        ACCESS read-only
        STATUS mandatory
        DESCRIPTION
            "The number of events for this monitor entry. Dependent from pmonFlags, events not always imply traps."
    ::= { processMonEntry 19 }

    pmonObjClass OBJECT-TYPE
        SYNTAX SnmpAdminString (SIZE (0..512))
        ACCESS read-write
        STATUS mandatory
        DESCRIPTION
            "The object class to use for the object state model. If the value is not configured and the agent
            cannot determine a default, the value is 'unknown'.
            This attribute cannot be set to an empty string or to '*'. Any such requests are ignored."
    ::= { processMonEntry 20 }

    pmonObjInstance OBJECT-TYPE
        SYNTAX SnmpAdminString (SIZE (0..512))
        ACCESS read-write
        STATUS mandatory
        DESCRIPTION
            "The object instance to use for the object state model. If the value is not configured and the agent
            cannot determine a default, the value is 'unknown'. The default for a non-tabular object is 'null'.
            For seamless monitoring of remote or virtual objects, instance names start with a prefix //hierarchy/.
            Additionally a name space can be prepended to better identify virtual objects (e.g. lpar:).
            For local objects the agent adds the prefix //./ to each instance name (including 'null').
            Note that process monitors typically monitor local objects (namely the local processes).
            This attribute cannot be set to an empty string or to '*'. Any such requests are ignored."
    ::= { processMonEntry 21 }

    pmonObjAttribute OBJECT-TYPE
        SYNTAX SnmpAdminString (SIZE (0..512))
        ACCESS read-write
        STATUS mandatory
        DESCRIPTION
            "The object attribute to use for the object state model. If the value is not configured and the agent
            cannot determine a default, the value is 'unknown'.
            This attribute cannot be set to an empty string or to '*'. Any such requests are ignored."
    ::= { processMonEntry 22 }

    pmonSeverity OBJECT-TYPE
        SYNTAX INTEGER {
            none(1),
            ok(2),
            warning(3),
            minor(4),
            major(5),
            critical(6),
            fatal(7)
        }
        ACCESS read-write
        STATUS mandatory
        DESCRIPTION
            "The severity to use for the object state model.
            The value none(1) excludes this monitor entry from the object state model."
        DEFVAL { none }
    ::= { processMonEntry 23 }

    pmonCurrState OBJECT-TYPE
        SYNTAX INTEGER {
            unknown(1),
            ok(2),
            warning(3),
            minor(4),
            major(5),
            critical(6),
            fatal(7),
            up(11),
            down(12)
        }
        ACCESS read-only
        STATUS mandatory
        DESCRIPTION
            "The current state of this monitor entry, evaluated by the severity and the breach condition,
            respecting any lag value configured in pmonFlags. If the row status is notInService(2), the state
            evaluates to unknown(1). If the row status is notReady(3), the state is kept unchanged. 
            The values up(11) and down(12) are used if the severity is none(1)."
    ::= { processMonEntry 24 }

    pmonZoneRegExp OBJECT-TYPE
        SYNTAX DisplayString
        ACCESS read-write
        STATUS obsolete
        DESCRIPTION
            "This attribute is obsolete in SystemEDGE 5.0 and should not be used."
    ::= { processMonEntry 25 }

    pmonProcName OBJECT-TYPE
        SYNTAX SnmpAdminString
        ACCESS read-only
        STATUS mandatory
        DESCRIPTION
            "The process name that was actually matched by the regular expression. On Solaris 10 and newer,
            if Zone flag (pmonFlags 0x8000) has been used, the name has the format 'ZoneName/ProcName'."
    ::= { processMonEntry 26 }
    
    pmonAutoWatchIndex OBJECT-TYPE
        SYNTAX INTEGER (0..2147483647)
        ACCESS read-only
        STATUS mandatory
        DESCRIPTION
            "The table index of the auto-watcher (see autoWatchEntry.watchIndex) that created this monitor.  An index of zero(0) indicates that
             this monitor was not created using an auto-watcher."
    ::= { processMonEntry 27 }

    pmonAutoWatchName OBJECT-TYPE
        SYNTAX SnmpAdminString
        ACCESS read-only
        STATUS mandatory
        DESCRIPTION
            "The name of the auto-watcher (see autoWatchEntry.watchName) that created this monitor.  This attribute is left blank
             if this monitor was not created using an auto-watcher."
    ::= { processMonEntry 28 }

------------------------------------------------------------

    pmonUnusedIndex OBJECT-TYPE
        SYNTAX INTEGER (1..2147483647)
        ACCESS read-only
        STATUS mandatory
        DESCRIPTION
            "This attribute returns an unused pmonIndex, which can be used for row creation."
    ::= { processMonitor 2 }

    pmonMatchDescr OBJECT-TYPE
        SYNTAX SnmpAdminString (SIZE (0..512))
        ACCESS read-write
        STATUS mandatory
        DESCRIPTION
            "This attribute can be used to determine the index of a particular row.
            Setting the attribute to a description, causes the agent to place the index of
            the last row, whose pmonDescr matches, in the pmonMatchIndex attribute."
    ::= { processMonitor 3 }

    pmonMatchIndex OBJECT-TYPE
        SYNTAX INTEGER (1..2147483647)
        ACCESS read-only
        STATUS mandatory
        DESCRIPTION
            "This attribute stores the index of the last row, whose pmonDescr matches pmonMatchDescr."
    ::= { processMonitor 4 }


------------------------------------------------------------
--  The Process Group Monitoring Table
------------------------------------------------------------
--  Contains process group monitoring table for monitoring
--  arbitrary groups of processes as single entity.
--  Each row in the table represents a group of processes
--  that SystemEDGE will monitor; SystemEDGE will track
--  various attributes of the group of processes and maintain
--  historical and current statistics about the group.

    processGroupMonTable OBJECT-TYPE
        SYNTAX SEQUENCE OF ProcessGroupMonEntry
        ACCESS not-accessible
        STATUS mandatory
        DESCRIPTION
            "The process group monitor table used for monitoring arbitrary groups of processes."
    ::= { processMonitor 10 }

    processGroupMonEntry OBJECT-TYPE
        SYNTAX ProcessGroupMonEntry
        ACCESS not-accessible
        STATUS mandatory
        DESCRIPTION
            "A process group monitor entry; one entry per group of processes to monitor."
        INDEX { pgmonIndex }
    ::= { processGroupMonTable 1 }

    ProcessGroupMonEntry ::= SEQUENCE {
        pgmonIndex        INTEGER,
        pgmonDescr        SnmpAdminString,
        pgmonInterval     INTEGER,
        pgmonProcRegExpr  SnmpAdminString,
        pgmonFlags        INTEGER,
        pgmonNumProcs     Gauge,
        pgmonPIDList      DisplayString,
        pgmonStatusList   DisplayString,
        pgmonAction       SnmpAdminString,
        pgmonNumEvents    Counter,
        pgmonNumTraps     Counter,
        pgmonLastTrap     TimeTicks,
        pgmonRowStatus    INTEGER,
        pgmonRSS          Gauge,
        pgmonSize         Gauge,
        pgmonThreadCount  Gauge,
        pgmonMEM          Gauge,
        pgmonInBlks       Counter,
        pgmonOutBlks      Counter,
        pgmonMsgsSent     Counter,
        pgmonMsgsRecv     Counter,
        pgmonSysCalls     Counter,
        pgmonMinorPgFlts  Counter,
        pgmonMajorPgFlts  Counter,
        pgmonNumSwaps     Counter,
        pgmonVolCtx       Counter,
        pgmonInvolCtx     Counter,
        pgmonCPUSecs      Counter,
        pgmonMatchUser    DisplayString,
        pgmonMatchGroup   DisplayString,
        pgmonSeverity     INTEGER,
        pgmonZoneRegExpr  DisplayString,
        pgmonProcNameList SnmpAdminString
    }

    pgmonIndex OBJECT-TYPE
        SYNTAX INTEGER (1..2147483647)
        ACCESS read-only
        STATUS mandatory
        DESCRIPTION
            "A unique value for entry in the processGroupMonTable. The index values in the processGroupMonTable may
            not necessarily be contiguous, but are unique."
    ::= { processGroupMonEntry 1 }

    pgmonDescr OBJECT-TYPE
        SYNTAX SnmpAdminString (SIZE (0..512))
        ACCESS read-write
        STATUS mandatory
        DESCRIPTION
            "A textual description of this entry possibly identifying the purpose of this entry and who created it."
    ::= { processGroupMonEntry 2 }

    pgmonInterval OBJECT-TYPE
        SYNTAX INTEGER (1..2147483647)
        ACCESS read-write
        STATUS mandatory
        DESCRIPTION
            "The interval, in seconds, between successive samples by the agent.  It must be a multiple of 30 seconds.
            For example, if a manager wanted to sample the value of a particular variable every 30 seconds, then
            setting monInterval to 30 would instruct the agent to sample once very 30 seconds. The sampling period is
            not exact but represents a best-effort by the agent."
        DEFVAL { 60 }
    ::= { processGroupMonEntry 3 }

    pgmonProcRegExpr OBJECT-TYPE
        SYNTAX SnmpAdminString (SIZE (0..512))
        ACCESS read-write
        STATUS mandatory
        DESCRIPTION
            "Dependent from pgmonFlags (0x8000), the regular expression to use for matching processes by name, or
            processes in Solaris Zones (use ZoneRegExpr/ProcRegExpr)."
    ::= { processGroupMonEntry 4 }

    pgmonFlags OBJECT-TYPE
        SYNTAX INTEGER 
        ACCESS read-write
        STATUS mandatory
        DESCRIPTION
            "The flags is a bit field. Setting one or more bits changes the behavior of this monitor entry.
            000 000 01 - don't execute any actions (but send and log traps)
            000 000 02 - don't send any traps (but log traps and execute actions)
            000 000 04 - don't reinitialize notReady monitor
            000 000 08 - don't log any traps (but send traps and execute actions)
            000 000 10 - keep sending notReady traps
            000 000 20 - don't pass default arguments to actions
            000 000 40 - don't send notReady traps (including log and action)
            000 000 80 - entry was created by an AIM plugin (this flag is read-only)
            000 001 00 - match process name and arguments
            000 080 00 - monitor process in Solaris Zone"
    ::= { processGroupMonEntry 5 }

    pgmonNumProcs OBJECT-TYPE
        SYNTAX Gauge 
        ACCESS read-only
        STATUS mandatory
        DESCRIPTION
            "The current number of processes in the process group being tracked by this table entry.  A process
            belongs to the process-group if its name (and possibly args) match the regular expression configured for
            this entry."
    ::= { processGroupMonEntry 6 }

    pgmonPIDList OBJECT-TYPE
        SYNTAX DisplayString
        ACCESS read-only
        STATUS mandatory
        DESCRIPTION
            "A list of the numeric PIDs in this process group separated by space character."
    ::= { processGroupMonEntry 7 }

    pgmonStatusList OBJECT-TYPE
        SYNTAX DisplayString
        ACCESS read-only
        STATUS mandatory
        DESCRIPTION
            "A list of the process states in this process group separated by space character.  See processStateInt
             for explanation of the state of a process.  Entries in the status list have a one-to-one correspondence
             with entries in the PID list."
    ::= { processGroupMonEntry 8 }

    pgmonAction OBJECT-TYPE
        SYNTAX SnmpAdminString (SIZE (0..2048))
        ACCESS read-write
        STATUS mandatory
        DESCRIPTION
            "The command (including parameters) to be executed concurrent to sending a trap."
    ::= { processGroupMonEntry 9 }

    pgmonNumEvents OBJECT-TYPE
        SYNTAX Counter 
        ACCESS read-only
        STATUS mandatory
        DESCRIPTION
            "The number of events for this monitor entry. Dependent from pgmonFlags, events not always imply traps."
    ::= { processGroupMonEntry 10 }

    pgmonNumTraps OBJECT-TYPE
        SYNTAX Counter 
        ACCESS read-only
        STATUS mandatory
        DESCRIPTION
            "The number of traps sent for this monitor entry."
    ::= { processGroupMonEntry 11 }

    pgmonLastTrap OBJECT-TYPE
        SYNTAX TimeTicks
        ACCESS read-only
        STATUS mandatory
        DESCRIPTION
            "The time when the agent last sent a trap for this monitor entry.
            This relative time (R) is given in hundredths of a second since the agent was started. It can be
            converted into an absolute time (A) using sysUpTime (from MIB-II) and hrSystemDate (from HR-MIB).
            sysUpTime (S) is the elapsed time (in hundredths of a second) since the agent was started.
            hrSysDate (H) is the current absolute date and time (in DateAndTime format) and must be converted
            to Unix Time format (seconds elapsed since 01.01.1970). Finally calculate: A = H - S/100 + R/100"
    ::= { processGroupMonEntry 12 }

    pgmonRowStatus OBJECT-TYPE
        SYNTAX INTEGER {
            active(1),
            notInService(2),
            notReady(3),
            createAndGo(4),
            createAndWait(5),
            destroy(6)
        }
        ACCESS read-write
        STATUS mandatory
        DESCRIPTION
            "The status of this monitor entry according to the Textual Conventions for SNMPv2 (see RFC 1443).
            active(1)        - the row is available for usage
            notInService(2)  - setting to this value disables usage of the row
            notReady(3)      - an error occured during usage of the row
            createAndGo(4)   - setting to this value creates the row with row status set to active(1)
            createAndWait(5) - setting to this value creates the row with row status set to notInService(2)
            destroy(6)       - setting to this value deletes the row"
        DEFVAL { createAndWait } 
    ::= { processGroupMonEntry 13 }

    pgmonRSS OBJECT-TYPE
        SYNTAX Gauge 
        ACCESS read-only
        STATUS mandatory
        DESCRIPTION
            "The combined resident set size of the group of processes.  (See processRSS).  RSS for each process in
            the group is summed each interval and stored in this MIB variable.  Because RSS also includes
            shared-memory, the total RSS for a group could actually exceed total possible physical memory for the
            underlying system."
    ::= { processGroupMonEntry 14 }

    pgmonSize OBJECT-TYPE
        SYNTAX Gauge 
        ACCESS read-only
        STATUS mandatory
        DESCRIPTION
            "The cobmined size of text/data/stack segments of the group of processes.  (See processSize)  Size for
            each process in the group is summed each interval and stored in this MIB variable.  Because Size also
            includes shared-memory, the total Size for a group could actually exceed total virtual memory for the
            underlying system."
    ::= { processGroupMonEntry 15 }

    pgmonThreadCount OBJECT-TYPE
        SYNTAX Gauge 
        ACCESS read-only
        STATUS mandatory
        DESCRIPTION
            "The total number of threads for the group of processes.  (See processNumThreads)  The number of threads
            running in each process in the group is summed each interval and stored in this MIB variable."
    ::= { processGroupMonEntry 16 }

    pgmonMEM OBJECT-TYPE
        SYNTAX Gauge 
        ACCESS read-only
        STATUS mandatory
        DESCRIPTION
            "The total percentage of real memory used by the processes in this group.  The percentage of memory used
            by each process in the group is summed each interval and stored in this MIB variable.  Because memory
            usage includes shared memory (e.g. shared librarys and DLLs), the total percentage may exceed 100."
    ::= { processGroupMonEntry 17 }

    pgmonInBlks OBJECT-TYPE
        SYNTAX Counter 
        ACCESS read-only
        STATUS mandatory
        DESCRIPTION
            "Number of blocks of data input by processes in this group.  SystemEDGE maintains a 'history' of group
            membership and tracks process stats even after an individual process has left the group."
    ::= { processGroupMonEntry 18 }

    pgmonOutBlks OBJECT-TYPE
        SYNTAX Counter 
        ACCESS read-only
        STATUS mandatory
        DESCRIPTION
            "Number of blocks of data output by processes in this group.  SystemEDGE maintains a 'history' of group
            membership and tracks process stats even after an individual process has left the group."
    ::= { processGroupMonEntry 19 }

    pgmonMsgsSent OBJECT-TYPE
        SYNTAX Counter 
        ACCESS read-only
        STATUS mandatory
        DESCRIPTION
            "Number of messages sent by processes in this group.  SystemEDGE maintains a 'history' of group
            membership and tracks process stats even after an individual process has left the group."
    ::= { processGroupMonEntry 20 }

    pgmonMsgsRecv OBJECT-TYPE
        SYNTAX Counter 
        ACCESS read-only
        STATUS mandatory
        DESCRIPTION
            "Number of messages received by processes in this group. SystemEDGE maintains a 'history' of group
            membership and tracks process stats even after an individual process has left the group."
    ::= { processGroupMonEntry 21 }

    pgmonSysCalls OBJECT-TYPE
        SYNTAX Counter 
        ACCESS read-only
        STATUS mandatory
        DESCRIPTION
            "Number of system calls invoked by processes in this group.  SystemEDGE maintains a 'history' of group
            membership and tracks process stats even after an individual process has left the group."
    ::= { processGroupMonEntry 22 }

    pgmonMinorPgFlts OBJECT-TYPE
        SYNTAX Counter 
        ACCESS read-only
        STATUS mandatory
        DESCRIPTION
            "Number of minor page faults incurred by processes in this group.  SystemEDGE maintains a 'history' of
            group membership and tracks process stats even after an individual process has left the group."
    ::= { processGroupMonEntry 23 }

    pgmonMajorPgFlts OBJECT-TYPE
        SYNTAX Counter 
        ACCESS read-only
        STATUS mandatory
        DESCRIPTION
            "Number of major page faults incurred by processes in this group.  SystemEDGE maintains a 'history' of
            group membership and tracks process stats even after an individual process has left the group."
    ::= { processGroupMonEntry 24 }

    pgmonNumSwaps OBJECT-TYPE
        SYNTAX Counter 
        ACCESS read-only
        STATUS mandatory
        DESCRIPTION
            "Number of times processes in this gropu have been swapped.  SystemEDGE maintains a 'history' of group
            membership and tracks process stats even after an individual process has left the group."
    ::= { processGroupMonEntry 25 }

    pgmonVolCtx OBJECT-TYPE
        SYNTAX Counter 
        ACCESS read-only
        STATUS mandatory
        DESCRIPTION
            "Number of voluntary context switches incurred by processes in this group.  SystemEDGE maintains a
            'history' of group membership and tracks process stats even after an individual process has left the
            group."
    ::= { processGroupMonEntry 26 }

    pgmonInvolCtx OBJECT-TYPE
        SYNTAX Counter 
        ACCESS read-only
        STATUS mandatory
        DESCRIPTION
            "Number of involuntary context switches incurred by processes in this group.  SystemEDGE maintains a
            'history' of group membership and tracks process stats even after an individual process has left the
            group."
    ::= { processGroupMonEntry 27 }

    pgmonCPUSecs OBJECT-TYPE
        SYNTAX Counter 
        ACCESS read-only
        STATUS mandatory
        DESCRIPTION
            "Number of seconds of CPU time used by processes in this group.  SystemEDGE maintains a 'history' of
            group membership and tracks process stats even after an individual process has left the group."
    ::= { processGroupMonEntry 28 }

    pgmonMatchUser OBJECT-TYPE
        SYNTAX DisplayString (SIZE (0..256))
        ACCESS read-write
        STATUS mandatory
        DESCRIPTION
            "If set to a valid username, SystemEDGE will match running processes by username in addition to any
            process name regular expression. This feature is only supported on UNIX."
    ::= { processGroupMonEntry 29 }

    pgmonMatchGroup OBJECT-TYPE
        SYNTAX DisplayString (SIZE (0..256))
        ACCESS read-write
        STATUS mandatory
        DESCRIPTION
            "If set to a valid groupname, SystemEDGE will match running processes by group name in addition to any
            process name regular expression and username matching. This feature is only supported UNIX."
    ::= { processGroupMonEntry 30 }

    pgmonSeverity OBJECT-TYPE
        SYNTAX INTEGER {
            none(1),
            ok(2),
            warning(3),
            minor(4),
            major(5),
            critical(6),
            fatal(7)
        }
        ACCESS read-write
        STATUS mandatory
        DESCRIPTION
            "The severity to use for this monitor entry. Process group monitors do not implement an object state model,
            but they allow to specify a severity, that is sent with the corresponding SNMP traps."
        DEFVAL { none }
    ::= { processGroupMonEntry 31 }

    pgmonZoneRegExpr OBJECT-TYPE
        SYNTAX DisplayString
        ACCESS read-write
        STATUS obsolete
        DESCRIPTION
            "This attribute is obsolete in SystemEDGE 5.0 and should not be used."
    ::= { processGroupMonEntry 32 }

    pgmonProcNameList OBJECT-TYPE
        SYNTAX SnmpAdminString
        ACCESS read-only
        STATUS mandatory
        DESCRIPTION
            "The list of the process names that were actually matched by the regular expression. On Solaris 10 or
            newer, if Zone flag (pgmonFlags 0x8000) has been used, the names have the format 'ZoneName/ProcName'."
    ::= { processGroupMonEntry 33 }
    
------------------------------------------------------------

    pgmonUnusedIndex OBJECT-TYPE
        SYNTAX INTEGER (1..2147483647)
        ACCESS read-only
        STATUS mandatory
        DESCRIPTION
            "An SNMP Get of this MIB object returns an un-used processGroupMonitorTable index number.  It can be used
            for processMonitor table row creation optimization."
    ::= { processMonitor 11 }

    pgmonMatchDescr OBJECT-TYPE
        SYNTAX SnmpAdminString (SIZE (0..512))
        ACCESS read-write
        STATUS mandatory
        DESCRIPTION
            "This MIB object, when used in conjunction with pgmonMatchIndex can be used to quickly determine the
            index number corresponding to a particular entry description.  SNMP Set'ing a description to this MIB
            object causes the agent to search through entries in the process group monitor table and place the index
            value of the last entry whose description matches, in the pgmonMatchIndex MIB object."
    ::= { processMonitor 12 }

    pgmonMatchIndex OBJECT-TYPE
        SYNTAX INTEGER (1..2147483647)
        ACCESS read-only
        STATUS mandatory
        DESCRIPTION
            "See description for pgmonMatchDescr."
    ::= { processMonitor 13 }


------------------------------------------------------------
--  The Aggregate State Table
------------------------------------------------------------

    aggregateTable OBJECT-TYPE
        SYNTAX SEQUENCE OF AggregateEntry
        ACCESS not-accessible
        STATUS mandatory
        DESCRIPTION
            "This table aggregates all monitors of the monitorTable and the
            processMonTable with the same object class, instance and attribute."
    ::= { objectState 1 }

    aggregateEntry OBJECT-TYPE
        SYNTAX AggregateEntry
        ACCESS not-accessible
        STATUS mandatory
        DESCRIPTION
            "An entry of the aggregate table."
        INDEX { aggIndex }
    ::= { aggregateTable 1 }

    AggregateEntry ::= SEQUENCE {
        aggIndex        INTEGER,
        aggObjClass     SnmpAdminString,
        aggObjInstance  SnmpAdminString,
        aggObjAttribute SnmpAdminString,
        aggRowStatus    INTEGER,
        aggCurrState    INTEGER,
        aggPrevState    INTEGER,
        aggLastTrap     TimeTicks,
        aggNumTraps     INTEGER,
        aggTimeWarning  INTEGER,
        aggTimeMinor    INTEGER,
        aggTimeMajor    INTEGER,
        aggTimeCritical INTEGER,
        aggTimeFatal    INTEGER,
        aggMonTable     INTEGER,
        aggMonIndex     INTEGER,
        aggMonCurrVal   INTEGER,
        aggMonOperator  INTEGER,
        aggMonValue     INTEGER,
        aggMonLastCall  TimeTicks
    }

    aggIndex OBJECT-TYPE
        SYNTAX INTEGER (1..2147483647)
        ACCESS read-only
        STATUS mandatory
        DESCRIPTION
            "A unique value for the table entry, not necessarily being contiguous, but unique."
    ::= { aggregateEntry 1 }

    aggObjClass OBJECT-TYPE
        SYNTAX SnmpAdminString (SIZE (0..512))
        ACCESS read-only
        STATUS mandatory
        DESCRIPTION
            "The object class of the monitors aggregated by this entry.
            The asterisk '*' denotes the aggregate over all classes." 
    ::= { aggregateEntry 2 }

    aggObjInstance OBJECT-TYPE
        SYNTAX SnmpAdminString (SIZE (0..512))
        ACCESS read-only
        STATUS mandatory
        DESCRIPTION
            "The object instance of the monitors aggregated by this entry.
            For seamless monitoring of remote or virtual objects, instance names are build as //hierarchy/instance.
            Additionally a name space can be prepended to better identify virtual objects (e.g. lpar:).
            The asterisk '*' for a hierarchy tier or for instance denotes the aggregate over all related instances." 
    ::= { aggregateEntry 3 }

    aggObjAttribute OBJECT-TYPE
        SYNTAX SnmpAdminString (SIZE (0..512))
        ACCESS read-only
        STATUS mandatory
        DESCRIPTION
            "The object attribute of the monitors aggregated by this entry.
            The asterisk '*' denotes the aggregate over all attributes." 
    ::= { aggregateEntry 4 }

    aggRowStatus OBJECT-TYPE
        SYNTAX INTEGER {
            active(1),
            notInService(2),
            notReady(3),
            destroy(6)
        }
        ACCESS read-write
        STATUS mandatory
        DESCRIPTION
            "The status of this entry according to the Textual Conventions for SNMPv2 (see RFC 1443),
            with the exception, that the status can neither be set to createAndGo(4) nor to createAndWait(5).
            active(1)       - one or more aggregated monitors are active(1)
            notInService(2) - one or more aggregated monitors are notInService(2) and none is active(1)
            notReady(3)     - one or more aggregated monitors are notReady(3) and none is active(1) nor notInService(2)
                              Note: 'procAlive' process monitors are always handled as active(1)
            Setting to active(1) sets all aggregated monitors to active(1), consequently this entry too.
            Setting to notInService(2) sets all aggregated monitors to notInService(2), consequently this entry too.
            Setting to destroy(6) deletes all aggregated monitors, consequently this entry too."
        DEFVAL { active } 
    ::= { aggregateEntry 5 }

    aggCurrState OBJECT-TYPE
        SYNTAX INTEGER {
            unknown(1),
            ok(2),
            warning(3),
            minor(4),
            major(5),
            critical(6),
            fatal(7)
        }
        ACCESS read-only
        STATUS mandatory
        DESCRIPTION
            "The worst current state of the monitors aggregated by this entry.
            If one or more aggregated monitors are active(1), then the worst state is calculated from these monitors.
            Otherwise, if one or more are notInService(2), then the worst state is calculated from these monitors.
            Otherwise, if one or more are notReady(3), then the worst state is calculated from these monitors."
    ::= { aggregateEntry 6 }

    aggPrevState OBJECT-TYPE
        SYNTAX INTEGER {
            unknown(1),
            ok(2),
            warning(3),
            minor(4),
            major(5),
            critical(6),
            fatal(7)
        }
        ACCESS read-only
        STATUS mandatory
        DESCRIPTION
            "The value of aggCurrState of this entry previous to the last change of aggCurrState."
    ::= { aggregateEntry 7 }

    aggLastTrap OBJECT-TYPE
        SYNTAX TimeTicks
        ACCESS read-only
        STATUS mandatory
        DESCRIPTION
            "The time when the agent last sent an aggregateStateTrap(20) for this entry.
            This relative time (R) is given in hundredths of a second since the agent was started. It can be
            converted into an absolute time (A) using sysUpTime (from MIB-II) and hrSystemDate (from HR-MIB).
            sysUpTime (S) is the elapsed time (in hundredths of a second) since the agent was started.
            hrSysDate (H) is the current absolute date and time (in DateAndTime format) and must be converted
            to Unix Time format (seconds elapsed since 01.01.1970). Finally calculate: A = H - S/100 + R/100"
    ::= { aggregateEntry 8 }

    aggNumTraps OBJECT-TYPE
        SYNTAX INTEGER
        ACCESS read-only
        STATUS mandatory
        DESCRIPTION
            "The number of aggregateStateTrap(20) sent for this aggregate entry."
    ::= { aggregateEntry 9 }

    aggTimeWarning OBJECT-TYPE
        SYNTAX INTEGER
        ACCESS read-only
        STATUS mandatory
        DESCRIPTION
            "The time since agent start (in seconds), the aggCurrState of this entry has been warning(3)."
    ::= { aggregateEntry 10 }

    aggTimeMinor OBJECT-TYPE
        SYNTAX INTEGER
        ACCESS read-only
        STATUS mandatory
        DESCRIPTION
            "The time since agent start (in seconds), the aggCurrState of this entry has been minor(4)."
    ::= { aggregateEntry 11 }

    aggTimeMajor OBJECT-TYPE
        SYNTAX INTEGER
        ACCESS read-only
        STATUS mandatory
        DESCRIPTION
            "The time since agent start (in seconds), the aggCurrState of this entry has been major(5)."
    ::= { aggregateEntry 12 }

    aggTimeCritical OBJECT-TYPE
        SYNTAX INTEGER
        ACCESS read-only
        STATUS mandatory
        DESCRIPTION
            "The time since agent start (in seconds), the aggCurrState of this entry has been critical(6)."
    ::= { aggregateEntry 13 }

    aggTimeFatal OBJECT-TYPE
        SYNTAX INTEGER
        ACCESS read-only
        STATUS mandatory
        DESCRIPTION
            "The time since agent start (in seconds), the aggCurrState of this entry has been fatal(7)."
    ::= { aggregateEntry 14 }

    aggMonTable OBJECT-TYPE
        SYNTAX INTEGER {
            monitorTable(6),
            processMonTable(15)
        }
        ACCESS read-only
        STATUS mandatory
        DESCRIPTION
            "The table, i.e. the top level OID number, where the aggregated monitor with the worst state is an entry of."
    ::= { aggregateEntry 15 }

    aggMonIndex OBJECT-TYPE
        SYNTAX INTEGER (1..2147483647)
        ACCESS read-only
        STATUS mandatory
        DESCRIPTION
            "The table index of the aggregated monitor with the worst state, i.e. either monIndex or pmonIndex."
    ::= { aggregateEntry 16 }

    aggMonCurrVal OBJECT-TYPE
        SYNTAX INTEGER
        ACCESS read-only
        STATUS mandatory
        DESCRIPTION
            "The current value of the aggregated monitor with the worst state, i.e. either monCurrVal or pmonCurrVal."
    ::= { aggregateEntry 17 }

    aggMonOperator OBJECT-TYPE
        SYNTAX INTEGER {
            nop(1),
            gt(2),
            lt(3),
            ge(4),
            le(5),
            eq(6),
            ne(7)
        }
        ACCESS read-only
        STATUS mandatory
        DESCRIPTION
            "The boolean operator of the aggregated monitor with the worst state, i.e. either monOperator or pmonOperator."
        DEFVAL { nop }
    ::= { aggregateEntry 18 }

    aggMonValue OBJECT-TYPE
        SYNTAX INTEGER
        ACCESS read-only
        STATUS mandatory
        DESCRIPTION
            "The threshold value of the aggregated monitor with the worst state, i.e. either monValue or pmonValue."
    ::= { aggregateEntry 19 }

    aggMonLastCall OBJECT-TYPE
        SYNTAX TimeTicks
        ACCESS read-only
        STATUS mandatory
        DESCRIPTION
            "The last sample time of the aggregated monitor with the worst state, i.e. either monLastCall or pmonLastCall."
    ::= { aggregateEntry 20 }


------------------------------------------------------------
--  The Monitor Mirror Table
------------------------------------------------------------

    mirrorMonitorTable OBJECT-TYPE
        SYNTAX SEQUENCE OF MirrorMonitorEntry
        ACCESS not-accessible
        STATUS mandatory
        DESCRIPTION
            "This table mirrors each monitor using its class, instance and attribute as first indices.
            This allows a manager to query and display information about monitors in a special context."
    ::= { objectState 2 }

    mirrorMonitorEntry OBJECT-TYPE
        SYNTAX MirrorMonitorEntry
        ACCESS not-accessible
        STATUS mandatory
        DESCRIPTION
            ""
        INDEX { mirrMonObjClass, mirrMonObjInstance, mirrMonObjAttribute, mirrMonTable, mirrMonIndex }
    ::= { mirrorMonitorTable 1 }

    MirrorMonitorEntry ::= SEQUENCE {
        mirrMonObjClass     SnmpAdminString,
        mirrMonObjInstance  SnmpAdminString,
        mirrMonObjAttribute SnmpAdminString,
        mirrMonTable        INTEGER,
        mirrMonIndex        INTEGER,
        mirrMonRowStatus    INTEGER,
        mirrMonSeverity     INTEGER,
        mirrMonCurrState    INTEGER,
        mirrMonDescr        SnmpAdminString,
        mirrMonInterval     INTEGER,
        mirrMonSampleType   INTEGER,
        mirrMonOID          OBJECT IDENTIFIER,
        mirrMonRegExpr      SnmpAdminString,
        mirrMonAttribute    INTEGER,
        mirrMonCurrPID      INTEGER,
        mirrMonCurrVal      INTEGER,
        mirrMonMinValue     INTEGER,
        mirrMonMaxValue     INTEGER,
        mirrMonOperator     INTEGER,
        mirrMonValue        INTEGER,
        mirrMonLastCall     TimeTicks,
        mirrMonLastTrap     TimeTicks,
        mirrMonNumTraps     INTEGER,
        mirrMonAction       SnmpAdminString,
        mirrMonFlags        INTEGER,
        mirrMonProcName     SnmpAdminString
    }

    mirrMonObjClass OBJECT-TYPE
        SYNTAX SnmpAdminString (SIZE (0..512))
        ACCESS read-only
        STATUS mandatory
        DESCRIPTION
            "The object class of this mirrored monitor, i.e. either monObjClass or pmonObjClass."
    ::= { mirrorMonitorEntry 1 }

    mirrMonObjInstance OBJECT-TYPE
        SYNTAX SnmpAdminString (SIZE (0..512))
        ACCESS read-only
        STATUS mandatory
        DESCRIPTION
            "The object instance of this mirrored monitor, i.e. either monObjInstance or pmonObjInstance."
    ::= { mirrorMonitorEntry 2 }

    mirrMonObjAttribute OBJECT-TYPE
        SYNTAX SnmpAdminString (SIZE (0..512))
        ACCESS read-only
        STATUS mandatory
        DESCRIPTION
            "The object attribute of this mirrored monitor, i.e. either monObjAttribute or pmonObjAttribute."
    ::= { mirrorMonitorEntry 3 }

    mirrMonTable OBJECT-TYPE
        SYNTAX INTEGER {
            monitorTable(6),
            processMonTable(15)
        }
        ACCESS read-only
        STATUS mandatory
        DESCRIPTION
            "The table, i.e. the top level OID number, where this mirrored monitor is an entry of."
    ::= { mirrorMonitorEntry 4 }

    mirrMonIndex OBJECT-TYPE
        SYNTAX INTEGER (1..2147483647)
        ACCESS read-only
        STATUS mandatory
        DESCRIPTION
            "The table index of this mirrored monitor, i.e. either monIndex or pmonIndex."
    ::= { mirrorMonitorEntry 5 }

    mirrMonRowStatus OBJECT-TYPE
        SYNTAX INTEGER {
            active(1),
            notInService(2),
            notReady(3)
        }
        ACCESS read-only
        STATUS mandatory
        DESCRIPTION
            "The row status of this mirrored monitor, i.e. either monRowStatus or pmonRowStatus."
    ::= { mirrorMonitorEntry 6 }

    mirrMonSeverity OBJECT-TYPE
        SYNTAX INTEGER {
            none(1),
            ok(2),
            warning(3),
            minor(4),
            major(5),
            critical(6),
            fatal(7)
        }
        ACCESS read-only
        STATUS mandatory
        DESCRIPTION
            "The severity of this mirrored monitor, i.e. either monSeverity or pmonSeverity."
    ::= { mirrorMonitorEntry 7 }

    mirrMonCurrState OBJECT-TYPE
        SYNTAX INTEGER {
            unknown(1),
            ok(2),
            warning(3),
            minor(4),
            major(5),
            critical(6),
            fatal(7),
            up(11),
            down(12)
        }
        ACCESS read-only
        STATUS mandatory
        DESCRIPTION
            "The current state of this mirrored monitor, i.e. either monCurrState or pmonCurrState."
    ::= { mirrorMonitorEntry 8 }

    mirrMonDescr OBJECT-TYPE
        SYNTAX SnmpAdminString (SIZE (0..512))
        ACCESS read-only
        STATUS mandatory
        DESCRIPTION
            "The description of this mirrored monitor, i.e. either monDescr or pmonDescr."
    ::= { mirrorMonitorEntry 9 }

    mirrMonInterval OBJECT-TYPE
        SYNTAX INTEGER (1..2147483647)
        ACCESS read-only
        STATUS mandatory
        DESCRIPTION
            "The interval of this mirrored monitor, i.e. either monInterval or pmonInterval."
    ::= { mirrorMonitorEntry 10 }

    mirrMonSampleType OBJECT-TYPE
        SYNTAX INTEGER {
            absoluteValue(1),
            deltaValue(2)
        }
        ACCESS read-only
        STATUS mandatory
        DESCRIPTION
            "The type of sampling of this mirrored monitor, i.e. either monSampleType or pmonSampleType."
    ::= { mirrorMonitorEntry 11 }

    mirrMonOID OBJECT-TYPE
        SYNTAX OBJECT IDENTIFIER
        ACCESS read-only
        STATUS mandatory
        DESCRIPTION
            "The object identifier of this mirrored monitor (if a self monitor), i.e. monOID."
    ::= { mirrorMonitorEntry 12 }

    mirrMonRegExpr OBJECT-TYPE
        SYNTAX SnmpAdminString (SIZE (0..512))
        ACCESS read-only
        STATUS mandatory
        DESCRIPTION
            "The regular expression of this mirrored monitor (if a process monitor), i.e. pmonRegExpr."
    ::= { mirrorMonitorEntry 13 }

    mirrMonAttribute OBJECT-TYPE
        SYNTAX INTEGER {
            procAlive(1),
            procMEM(2),
            procSize(3),
            procRSS(4),
            procTime(5),
            procInBlks(6),
            procOutBlks(7),
            procMsgsSent(8),
            procMsgsRecv(9),
            procNice(10),
            procNumThreads(11),
            procNumSwaps(12),
            procSysCalls(13),
            procMinorPgFlts(14),
            procMajorPgFlts(15),
            procVolCtx(16),
            procInvolCtx(17),
            procTimePermil(18)
        }
        ACCESS read-only
        STATUS mandatory
        DESCRIPTION
            "The process attribute of this mirrored monitor (if a process monitor), i.e. pmonAttribute."
    ::= { mirrorMonitorEntry 14 }

    mirrMonCurrPID OBJECT-TYPE
        SYNTAX INTEGER 
        ACCESS read-only
        STATUS mandatory
        DESCRIPTION
            "The process PID of this mirrored monitor (if a process monitor), i.e. pmonCurrentPID."
    ::= { mirrorMonitorEntry 15 }

    mirrMonCurrVal OBJECT-TYPE
        SYNTAX INTEGER
        ACCESS read-only
        STATUS mandatory
        DESCRIPTION
            "The current value of this mirrored monitor, i.e. either monCurrVal or pmonCurrVal."
    ::= { mirrorMonitorEntry 16 }

    mirrMonMinValue OBJECT-TYPE
        SYNTAX INTEGER 
        ACCESS read-only
        STATUS mandatory
        DESCRIPTION
            "The minimum value of this mirrored monitor, i.e. either monMinValue or pmonMinValue."
    ::= { mirrorMonitorEntry 17 }

    mirrMonMaxValue OBJECT-TYPE
        SYNTAX INTEGER 
        ACCESS read-only
        STATUS mandatory
        DESCRIPTION
            "The maximum value of this mirrored monitor, i.e. either monMaxValue or pmonMaxValue."
    ::= { mirrorMonitorEntry 18 }

    mirrMonOperator OBJECT-TYPE
        SYNTAX INTEGER {
            nop(1),
            gt(2),
            lt(3),
            ge(4),
            le(5),
            eq(6),
            ne(7)
        }
        ACCESS read-only
        STATUS mandatory
        DESCRIPTION
            "The boolean operator of this mirrored monitor, i.e. either monOperator or pmonOperator."
    ::= { mirrorMonitorEntry 19 }

    mirrMonValue OBJECT-TYPE
        SYNTAX INTEGER
        ACCESS read-only
        STATUS mandatory
        DESCRIPTION
            "The threshold value of this mirrored monitor, i.e. either monValue or pmonValue."
    ::= { mirrorMonitorEntry 20 }

    mirrMonLastCall OBJECT-TYPE
        SYNTAX TimeTicks
        ACCESS read-only
        STATUS mandatory
        DESCRIPTION
            "The last sample time of this mirrored monitor, i.e. either monLastCall or pmonLastCall."
    ::= { mirrorMonitorEntry 21 }

    mirrMonLastTrap OBJECT-TYPE
        SYNTAX TimeTicks
        ACCESS read-only
        STATUS mandatory
        DESCRIPTION
            "The last trap sent time of this mirrored monitor, i.e. either monLastTrap or pmonLastTrap."
    ::= { mirrorMonitorEntry 22 }

    mirrMonNumTraps OBJECT-TYPE
        SYNTAX INTEGER
        ACCESS read-only
        STATUS mandatory
        DESCRIPTION
            "The number of traps sent of this mirrored monitor, i.e. either monNumTraps or pmonNumTraps."
    ::= { mirrorMonitorEntry 23 }

    mirrMonAction OBJECT-TYPE
        SYNTAX SnmpAdminString (SIZE (0..2048))
        ACCESS read-only
        STATUS mandatory
        DESCRIPTION
            "The command to be executed of this mirrored monitor, i.e. either monAction or pmonAction."
    ::= { mirrorMonitorEntry 24 }

    mirrMonFlags OBJECT-TYPE
        SYNTAX INTEGER 
        ACCESS read-only
        STATUS mandatory
        DESCRIPTION
            "The flags bit field of this mirrored monitor, i.e. either monFlags or pmonFlags."
    ::= { mirrorMonitorEntry 25 }

    mirrMonProcName OBJECT-TYPE
        SYNTAX SnmpAdminString (SIZE (0..512))
        ACCESS read-only
        STATUS mandatory
        DESCRIPTION
            "The matched process name of this mirrored monitor (if a process monitor), i.e. pmonProcName."
    ::= { mirrorMonitorEntry 26 }



------------------------------------------------------------
--  The Aggregate Mirror Table
------------------------------------------------------------

    mirrorAggregateTable OBJECT-TYPE
        SYNTAX SEQUENCE OF MirrorAggregateEntry
        ACCESS not-accessible
        STATUS mandatory
        DESCRIPTION
            "This table mirrors each aggregate using its class, instance and attribute as indices.
            This allows a manager to query and display information about aggregates in a special context."
    ::= { objectState 3 }

    mirrorAggregateEntry OBJECT-TYPE
        SYNTAX MirrorAggregateEntry
        ACCESS not-accessible
        STATUS mandatory
        DESCRIPTION
            ""
        INDEX { mirrAggObjClass, mirrAggObjInstance, mirrAggObjAttribute }
    ::= { mirrorAggregateTable 1 }

    MirrorAggregateEntry ::= SEQUENCE {
        mirrAggObjClass     SnmpAdminString,
        mirrAggObjInstance  SnmpAdminString,
        mirrAggObjAttribute SnmpAdminString,
        mirrAggIndex        INTEGER,
        mirrAggRowStatus    INTEGER,
        mirrAggCurrState    INTEGER,
        mirrAggPrevState    INTEGER,
        mirrAggLastTrap     TimeTicks,
        mirrAggNumTraps     INTEGER,
        mirrAggTimeWarning  INTEGER,
        mirrAggTimeMinor    INTEGER,
        mirrAggTimeMajor    INTEGER,
        mirrAggTimeCritical INTEGER,
        mirrAggTimeFatal    INTEGER,
        mirrAggMonTable     INTEGER,
        mirrAggMonIndex     INTEGER,
        mirrAggMonCurrVal   INTEGER,
        mirrAggMonOperator  INTEGER,
        mirrAggMonValue     INTEGER,
        mirrAggMonLastCall  TimeTicks
    }

    mirrAggObjClass OBJECT-TYPE
        SYNTAX SnmpAdminString (SIZE (0..512))
        ACCESS read-only
        STATUS mandatory
        DESCRIPTION
            "The object class of this mirrored aggregate, i.e. aggObjClass."
    ::= { mirrorAggregateEntry 1 }

    mirrAggObjInstance OBJECT-TYPE
        SYNTAX SnmpAdminString (SIZE (0..512))
        ACCESS read-only
        STATUS mandatory
        DESCRIPTION
            "The object instance of this mirrored aggregate, i.e. aggObjInstance."
    ::= { mirrorAggregateEntry 2 }

    mirrAggObjAttribute OBJECT-TYPE
        SYNTAX SnmpAdminString (SIZE (0..512))
        ACCESS read-only
        STATUS mandatory
        DESCRIPTION
            "The object attribute of this mirrored aggregate, i.e. aggObjAttribute."
    ::= { mirrorAggregateEntry 3 }

    mirrAggIndex OBJECT-TYPE
        SYNTAX INTEGER (1..2147483647)
        ACCESS read-only
        STATUS mandatory
        DESCRIPTION
            "The index of this mirrored aggregate, i.e. aggIndex."
    ::= { mirrorAggregateEntry 4 }

    mirrAggRowStatus OBJECT-TYPE
        SYNTAX INTEGER {
            active(1),
            notInService(2),
            notReady(3)
        }
        ACCESS read-only
        STATUS mandatory
        DESCRIPTION
            "The row status of this mirrored aggregate, i.e. aggRowStatus."
    ::= { mirrorAggregateEntry 5 }

    mirrAggCurrState OBJECT-TYPE
        SYNTAX INTEGER {
            unknown(1),
            ok(2),
            warning(3),
            minor(4),
            major(5),
            critical(6),
            fatal(7)
        }
        ACCESS read-only
        STATUS mandatory
        DESCRIPTION
            "The current state of this mirrored aggregate, i.e. aggCurrState."
    ::= { mirrorAggregateEntry 6 }

    mirrAggPrevState OBJECT-TYPE
        SYNTAX INTEGER {
            unknown(1),
            ok(2),
            warning(3),
            minor(4),
            major(5),
            critical(6),
            fatal(7)
        }
        ACCESS read-only
        STATUS mandatory
        DESCRIPTION
            "The previous state of this mirrored aggregate, i.e. aggPrevState."
    ::= { mirrorAggregateEntry 7 }

    mirrAggLastTrap OBJECT-TYPE
        SYNTAX TimeTicks
        ACCESS read-only
        STATUS mandatory
        DESCRIPTION
            "The last trap sent time of this mirrored aggregate, i.e. aggLastTrap."
    ::= { mirrorAggregateEntry 8 }

    mirrAggNumTraps OBJECT-TYPE
        SYNTAX INTEGER
        ACCESS read-only
        STATUS mandatory
        DESCRIPTION
            "The number of traps sent of this mirrored aggregate, i.e. aggNumTraps."
    ::= { mirrorAggregateEntry 9 }

    mirrAggTimeWarning OBJECT-TYPE
        SYNTAX INTEGER
        ACCESS read-only
        STATUS mandatory
        DESCRIPTION
            "The time in warning(3) state of this mirrored aggregate, i.e. aggTimeWarning."
    ::= { mirrorAggregateEntry 10 }

    mirrAggTimeMinor OBJECT-TYPE
        SYNTAX INTEGER
        ACCESS read-only
        STATUS mandatory
        DESCRIPTION
            "The time in minor(4) state of this mirrored aggregate, i.e. aggTimeMinor."
    ::= { mirrorAggregateEntry 11 }

    mirrAggTimeMajor OBJECT-TYPE
        SYNTAX INTEGER
        ACCESS read-only
        STATUS mandatory
        DESCRIPTION
            "The time in major(5) state of this mirrored aggregate, i.e. aggTimeMajor."
    ::= { mirrorAggregateEntry 12 }

    mirrAggTimeCritical OBJECT-TYPE
        SYNTAX INTEGER
        ACCESS read-only
        STATUS mandatory
        DESCRIPTION
            "The time in critical(6) state of this mirrored aggregate, i.e. aggTimeCritical."
    ::= { mirrorAggregateEntry 13 }

    mirrAggTimeFatal OBJECT-TYPE
        SYNTAX INTEGER
        ACCESS read-only
        STATUS mandatory
        DESCRIPTION
            "The time in fatal(7) state of this mirrored aggregate, i.e. aggTimeFatal."
    ::= { mirrorAggregateEntry 14 }

    mirrAggMonTable OBJECT-TYPE
        SYNTAX INTEGER {
            monitorTable(6),
            processMonTable(15)
        }
        ACCESS read-only
        STATUS mandatory
        DESCRIPTION
            "The worst state monitor's table, i.e. aggMonTable."
    ::= { mirrorAggregateEntry 15 }

    mirrAggMonIndex OBJECT-TYPE
        SYNTAX INTEGER (1..2147483647)
        ACCESS read-only
        STATUS mandatory
        DESCRIPTION
            "The worst state monitor's index, i.e. aggMonIndex."
    ::= { mirrorAggregateEntry 16 }

    mirrAggMonCurrVal OBJECT-TYPE
        SYNTAX INTEGER
        ACCESS read-only
        STATUS mandatory
        DESCRIPTION
            "The worst state monitor's current value, i.e. aggMonCurrVal."
    ::= { mirrorAggregateEntry 17 }

    mirrAggMonOperator OBJECT-TYPE
        SYNTAX INTEGER {
            nop(1),
            gt(2),
            lt(3),
            ge(4),
            le(5),
            eq(6),
            ne(7)
        }
        ACCESS read-only
        STATUS mandatory
        DESCRIPTION
            "The worst state monitor's boolean operator, i.e. aggMonOperator."
        DEFVAL { nop }
    ::= { mirrorAggregateEntry 18 }

    mirrAggMonValue OBJECT-TYPE
        SYNTAX INTEGER
        ACCESS read-only
        STATUS mandatory
        DESCRIPTION
            "The worst state monitor's threshold value, i.e. aggMonValue."
    ::= { mirrorAggregateEntry 19 }

    mirrAggMonLastCall OBJECT-TYPE
        SYNTAX TimeTicks
        ACCESS read-only
        STATUS mandatory
        DESCRIPTION
            "The worst state monitor's last sample time, i.e. aggMonLastCall."
    ::= { mirrorAggregateEntry 20 }


------------------------------------------------------------
--  The Auto-Watcher Table
------------------------------------------------------------

    autoWatchTable OBJECT-TYPE
        SYNTAX SEQUENCE OF AutoWatchEntry
        ACCESS not-accessible
        STATUS mandatory
        DESCRIPTION
            "The autowatcher table describes automatic monitoring activities of the agent.
             A row of this table causes the agent to automatically create monitor entries for
             all matching instances, based on the specified criteria."
    ::= { autoWatch 1 }

    autoWatchEntry OBJECT-TYPE
        SYNTAX AutoWatchEntry
        ACCESS not-accessible
        STATUS mandatory
        DESCRIPTION
            "Syntax of an autowatcher entry."
        INDEX { watchIndex }
    ::= { autoWatchTable 1 }

    AutoWatchEntry ::= SEQUENCE {
        watchIndex                     INTEGER,
        watchType                      INTEGER,
        watchName                      SnmpAdminString,
        watchMonTableEntry             SnmpAdminString,
        watchMonDescr                  SnmpAdminString,
        watchMonInterval               INTEGER,
        watchMonSampleType             INTEGER,
        watchMonAttribute              SnmpAdminString,
        watchMonOperator               INTEGER,
        watchMonValue                  INTEGER,
        watchMonAction                 SnmpAdminString,
        watchMonFlags                  INTEGER,
        watchMonObjClass               SnmpAdminString,
        watchMonObjAttribute           SnmpAdminString,
        watchMonSeverity               INTEGER,
        watchMonScale                  INTEGER,
        watchScanInterval              INTEGER,
        watchLastScan                  TimeTicks,
        watchNumTraps                  INTEGER,
        watchLastTrap                  TimeTicks,
        watchMaxInstances              INTEGER,
        watchNumInstances              INTEGER,
        watchFlags                     INTEGER,
        watchLossAction                INTEGER,
        watchRowStatus                 INTEGER,
        watchInstanceCriteriaRegex     SnmpAdminString,
        watchInstanceCriteriaMatchType INTEGER,
        watchCriteria2Column           SnmpAdminString,
        watchCriteria2Regex            SnmpAdminString,
        watchCriteria2MatchType        INTEGER,
        watchCriteria3Column           SnmpAdminString,
        watchCriteria3Regex            SnmpAdminString,
        watchCriteria3MatchType        INTEGER
    }

    watchIndex OBJECT-TYPE
        SYNTAX INTEGER (1..2147483647)
        ACCESS read-only
        STATUS mandatory
        DESCRIPTION
            "A unique value for the table entry, not necessarily being contiguous, but unique."
    ::= { autoWatchEntry 1 }

    watchType OBJECT-TYPE
        SYNTAX INTEGER {
            generic(1),
            service(2),
            process(3)
        }
        ACCESS read-write
        STATUS mandatory
        DESCRIPTION
            "The type of autowatcher being created.  Generic autowatchers utilize the empire.monitor table,
             while specialized auto-watchers may need to utilize other tables (e.g. empire.processMonitor, etc.)."
        DEFVAL { generic }
    ::= { autoWatchEntry 2 }

    watchName OBJECT-TYPE
        SYNTAX SnmpAdminString
        ACCESS read-write
        STATUS mandatory
        DESCRIPTION
            "A textual name for this auto-watcher.  This name is also published within all autowatch-generated 
             monitors, for ease of use."
    ::= { autoWatchEntry 3 }

    watchMonTableEntry OBJECT-TYPE
        SYNTAX SnmpAdminString (SIZE (0..512))
        ACCESS read-write
        STATUS mandatory
        DESCRIPTION
            "The textual MIB name of the table entry to be auto-watched (e.g. ifEntry).  This table entry must be
             specified as a class within sysedge.oid so that instance and attribute data can be properly processed.
             Ignored for auto-watchers of type 'service' or 'process'.
             NOTE: This attribute cannot be changed for existing autowatcher entries unless rowStatus is set to 
                   notInService(2)."
    ::= { autoWatchEntry 4 }

    watchMonDescr OBJECT-TYPE
        SYNTAX SnmpAdminString (SIZE (0..512))
        ACCESS read-write
        STATUS mandatory
        DESCRIPTION
            "A general, textual description, to be applied to all generated monitors."
    ::= { autoWatchEntry 5 }

    watchMonInterval OBJECT-TYPE
        SYNTAX INTEGER (1..2147483647)
        ACCESS read-write
        STATUS mandatory
        DESCRIPTION
            "The monitoring interval, in seconds, between successive samples by the agent. This is applied to all
             generated monitors, and must be a multiple of 30 seconds.  The sampling period is not exact but 
             represents a best-effort by the agent." 
        DEFVAL { 60 }
    ::= { autoWatchEntry 6 }

    watchMonSampleType OBJECT-TYPE
        SYNTAX INTEGER {
            absoluteValue(1),
            deltaValue(2)
        }
        ACCESS read-write
        STATUS mandatory
        DESCRIPTION
            "The type of sampling performed on each monitored object, applied to all generated monitors.
             To monitor the rate of change (e.g. for a Counter typed object) use deltaValue.
             To monitor the absolute value (e.g. for a Gauge typed object) use absoluteValue."
        DEFVAL { absoluteValue }
    ::= { autoWatchEntry 7 }

    watchMonAttribute OBJECT-TYPE
        SYNTAX SnmpAdminString (SIZE (0..512))
        ACCESS read-write
        STATUS mandatory
        DESCRIPTION
            "The textual MIB name of the table entry column to be auto-watched (e.g. ifOperStatus).
             NOTE: This attribute cannot be changed for existing autowatcher entries unless rowStatus is set to 
                   notInService(2)."
    ::= { autoWatchEntry 8 }

    watchMonOperator OBJECT-TYPE
        SYNTAX INTEGER {
            nop(1),
            gt(2),
            lt(3),
            ge(4),
            le(5),
            eq(6),
            ne(7)
        }
        ACCESS read-write
        STATUS mandatory
        DESCRIPTION
            "The boolean operator that is used to compare the current value to the threshold value, applied
             to all generated monitor.  nop(1) is used to only track the current value, but do not compare 
             to the threshold."
        DEFVAL { nop }
    ::= { autoWatchEntry 9 }

    watchMonValue OBJECT-TYPE
        SYNTAX INTEGER
        ACCESS read-write
        STATUS mandatory
        DESCRIPTION
            "The threshold value against which the agent compares the current value.  Applied to all
             generated monitors."
    ::= { autoWatchEntry 10 }

    watchMonAction OBJECT-TYPE
        SYNTAX SnmpAdminString (SIZE (0..2048))
        ACCESS read-write
        STATUS mandatory
        DESCRIPTION
            "The command (including parameters) to be executed concurrent to sending a trap, applied to all
             generated monitors."
    ::= { autoWatchEntry 11 }

    watchMonFlags OBJECT-TYPE
        SYNTAX INTEGER 
        ACCESS read-write
        STATUS mandatory
        DESCRIPTION
            "The flags is a bit field. Setting one or more bits changes the behavior of all generated monitor entries.
             000 000 01 - don't execute any actions (but send and log traps)
             000 000 02 - don't send any traps (but log traps and execute actions)
             000 000 04 - don't reinitialize notReady monitor
             000 000 08 - don't log any traps (but send traps and execute actions)
             000 000 10 - keep sending notReady traps
             000 000 20 - don't pass default arguments to actions
             000 000 40 - don't send notReady traps (including log and action)
             000 000 80 - entry was created by an AIM plugin (this flag is read-only)

             generic auto-watchers:
             000 001 00 - send monitorClear traps (including log and action)
             xxx 002 00 - send monitorThreshold traps after xxx consecutive breaches (including log and action)
             xxx 004 00 - send at most xxx consecutive monitorThreshold traps (including log and action)
             000 008 00 - aggregate state of all monitors with same severity as AND relation

             process/service auto-watchers:
             000 002 00 - don't send processStart traps (including log and action)
             000 004 00 - send processClear traps (including log and action)
             000 008 00 - match process name and arguments
             xxx 010 00 - send processThreshold/Stop traps after xxx consecutive breaches (including log and action)
             xxx 020 00 - send at most xxx consecutive processThreshold/Stop traps (including log and action)
             000 080 00 - monitor process in Solaris Zone
             000 100 00 - effectively the same as 000 002 00 (for legacy support)
             000 200 00 - aggregate state of all monitors with same severity as AND relation"
    ::= { autoWatchEntry 12 }

    watchMonObjClass OBJECT-TYPE
        SYNTAX SnmpAdminString (SIZE (0..512))
        ACCESS read-write
        STATUS mandatory
        DESCRIPTION
            "The object class to use for the object state model, applied to all generated monitors.  If 
             the value is not configured and the agent cannot determine a default, the value is 'unknown'.
             This attribute cannot be set to an empty string or to '*'. Any such requests are ignored."
    ::= { autoWatchEntry 13 }

    watchMonObjAttribute OBJECT-TYPE
        SYNTAX SnmpAdminString (SIZE (0..512))
        ACCESS read-write
        STATUS mandatory
        DESCRIPTION
            "The object attribute to use for the object state model, applied to all generated monitors. If 
             the value is not configured and the agent cannot determine a default, the value is 'unknown'.
             This attribute cannot be set to an empty string or to '*'. Any such requests are ignored."
    ::= { autoWatchEntry 14 }

    watchMonSeverity OBJECT-TYPE
        SYNTAX INTEGER {
            none(1),
            ok(2),
            warning(3),
            minor(4),
            major(5),
            critical(6),
            fatal(7)
        }
        ACCESS read-write
        STATUS mandatory
        DESCRIPTION
            "The severity to use for the object state model, applied to all generated monitors.
             The value none(1) excludes this monitor entry from the object state model."
        DEFVAL { none }
    ::= { autoWatchEntry 15 }

    watchMonScale OBJECT-TYPE
        SYNTAX INTEGER 
        ACCESS read-write
        STATUS mandatory
        DESCRIPTION
            "Scale factor for monitor values, applied to all generated monitors. This scale factor allows 
             monitoring variable in different units then is measured.  For example scale factor 1024 
             allows to monitor in KiB variable that is measured in bytes. With this scaling factor variables 
             monCurrVal, monValue, monMinValue and monMaxValue will be reported in KiB.
             Note that the SYNTAX of this attribute actually is Counter64." 
    ::= { autoWatchEntry 16 }

    watchScanInterval OBJECT-TYPE
        SYNTAX INTEGER (1..2147483647)
        ACCESS read-write
        STATUS mandatory
        DESCRIPTION
            "The interval, in seconds, between successive scans of the monitored table for row additions.
             This must be a multiple of 30 seconds.  The scan period is not exact but represents a best-effort 
             by the agent."
        DEFVAL { 300 }
    ::= { autoWatchEntry 17 }

    watchLastScan OBJECT-TYPE
        SYNTAX TimeTicks
        ACCESS read-only
        STATUS mandatory
        DESCRIPTION
            "The time when the agent last scanned the monitored table for row additions.
             This relative time (R) is given in hundredths of a second in the past."
    ::= { autoWatchEntry 18 }

    watchNumTraps OBJECT-TYPE
        SYNTAX INTEGER
        ACCESS read-only
        STATUS mandatory
        DESCRIPTION
            "The number of auto-watcher traps sent for this entry."
    ::= { autoWatchEntry 19 }

    watchLastTrap OBJECT-TYPE
        SYNTAX TimeTicks
        ACCESS read-only
        STATUS mandatory
        DESCRIPTION
            "The time when the agent last sent a trap for this auto-watcher entry.
             This relative time (R) is given in hundredths of a second in the past."
    ::= { autoWatchEntry 20 }

    watchMaxInstances OBJECT-TYPE
        SYNTAX INTEGER (1..2147483647)
        ACCESS read-write
        STATUS mandatory
        DESCRIPTION
            "The maximum number of generated monitor instances that this auto-watcher can create.  If this number
             will be crossed by additional required instances, this auto-watcher will be placed into notReady(3) 
             status."
        DEFVAL { 100 }
    ::= { autoWatchEntry 21 }

    watchNumInstances OBJECT-TYPE
        SYNTAX INTEGER
        ACCESS read-only
        STATUS mandatory
        DESCRIPTION
            "The current number of generated monitor instances that this auto-watcher has created."
    ::= { autoWatchEntry 22 }

    watchFlags OBJECT-TYPE
        SYNTAX INTEGER 
        ACCESS read-write
        STATUS mandatory
        DESCRIPTION
            "The flags is a bit field. Setting one or more bits changes the behavior of this auto-watcher.
             000 000 02 - don't send any traps (but log traps)
             000 000 04 - don't reinitialize notReady autowatcher
             000 000 08 - don't log any traps (but send traps)
             000 000 10 - keep sending notReady traps
             000 000 40 - don't send notReady traps (including log)
             000 000 80 - entry was created by an AIM plugin (this flag is read-only)
             000 00X 00 - specified NT service start type for service watchers
                           0 = all service start types
                           1 = 'Automatic'
                           2 = 'Manual'
                           3 = 'Disabled'
             000 010 00 - monitor processes by PID (default is to monitor processes by process name)"
    ::= { autoWatchEntry 23 }

    watchLossAction OBJECT-TYPE
        SYNTAX INTEGER {
            remove(1),
            ok(2),
            warning(3),
            minor(4),
            major(5),
            critical(6),
            fatal(7),
            up(11),
            down(12)
        }
        ACCESS read-write
        STATUS mandatory
        DESCRIPTION
            "This is the policy that the auto-watcher should perform when a monitored instance is detected 
             to be removed.  remove(1) indicates that the generated monitor will be removed when the 
             monitored instance is no longer available.  Other statuses will effectively 'force' the 
             current state to this value when a loss is detected.  Please note that this action takes place 
             on the generated monitor's processing interval, not the autowatcher scan interval, to avoid
             timing concerns."
        DEFVAL { fatal }
    ::= { autoWatchEntry 24 }

    watchRowStatus OBJECT-TYPE
        SYNTAX INTEGER {
            active(1),
            notInService(2),
            notReady(3),
            createAndGo(4),
            createAndWait(5),
            destroy(6)
        }
        ACCESS read-write
        STATUS mandatory
        DESCRIPTION
            "The status of all generated monitor entries according to the Textual Conventions for SNMPv2 (see RFC 1443).
            active(1)        - The row is actively executing.  Generated monitors will be created with active(1) status.
            notInService(2)  - Setting to this value disables usage of the row.  Monitors will no longer be generated, and
                               all previously generated monitors will also be placed into notInService(2) status.
            notReady(3)      - An error occured during usage of the row.  Previously generated monitors will continue to 
                               execute normally, but no new monitors will be generated.
            createAndGo(4)   - Setting to this value creates the row with row status set to active(1).  Generated monitors will
                               also be created with active(1) status.
            createAndWait(5) - Setting to this value creates the row with row status set to notInService(2).
            destroy(6)       - Setting to this value deletes the row.  All generated monitors for this row are deleted as well."
        DEFVAL { createAndGo } 
    ::= { autoWatchEntry 25 }

    watchInstanceCriteriaRegex OBJECT-TYPE
        SYNTAX SnmpAdminString (SIZE (0..512))
        ACCESS read-write
        STATUS mandatory
        DESCRIPTION
            "A regular expression used to query the instance for the table entry specified.  This instance 
             column(s) is/are pre-defined within sysedge.oid file for specific tables.
             NOTE: This attribute cannot be changed for existing autowatcher entries unless rowStatus is set to 
                   notInService(2)."
    ::= { autoWatchEntry 26 }

    watchInstanceCriteriaMatchType OBJECT-TYPE
        SYNTAX INTEGER {
            positive(1),
            negative(2)
        }
        ACCESS read-write
        STATUS mandatory
        DESCRIPTION
            "Regular Expression match type for watchInstanceCriteriaRegex.  Specifying negative match type
             will match instances that do not meet the specified criteria specified in the regular expression.
             NOTE: This attribute cannot be changed for existing autowatcher entries unless rowStatus is set to 
                   notInService(2)."
        DEFVAL { positive }
    ::= { autoWatchEntry 27 }

    watchCriteria2Column OBJECT-TYPE
        SYNTAX SnmpAdminString (SIZE (0..512))
        ACCESS read-write
        STATUS mandatory
        DESCRIPTION
            "The textual MIB name of the secondary table entry column to be used for criteria matching (if needed).
             NOTE: This attribute cannot be changed for existing autowatcher entries unless rowStatus is set to 
                   notInService(2)."
    ::= { autoWatchEntry 28 }

    watchCriteria2Regex OBJECT-TYPE
        SYNTAX SnmpAdminString (SIZE (0..512))
        ACCESS read-write
        STATUS mandatory
        DESCRIPTION
            "A regular expression to apply to the secondary table entry column for criteria matching.
             NOTE: This attribute cannot be changed for existing autowatcher entries unless rowStatus is set to 
                   notInService(2)."
    ::= { autoWatchEntry 29 }

    watchCriteria2MatchType OBJECT-TYPE
        SYNTAX INTEGER {
            positive(1),
            negative(2)
        }
        ACCESS read-write
        STATUS mandatory
        DESCRIPTION
            "Regular Expression match type for watchInstanceCriteria2Regex.  Specifying negative match type
             will match instances that do not meet the specified criteria specified in the regular expression.
             NOTE: This attribute cannot be changed for existing autowatcher entries unless rowStatus is set to 
                   notInService(2)."
        DEFVAL { positive }
    ::= { autoWatchEntry 30 }

    watchCriteria3Column OBJECT-TYPE
        SYNTAX SnmpAdminString (SIZE (0..512))
        ACCESS read-write
        STATUS mandatory
        DESCRIPTION
            "The textual MIB name of the tertiary table entry column to be used for criteria matching (if needed).
             NOTE: This attribute cannot be changed for existing autowatcher entries unless rowStatus is set to 
                   notInService(2)."
    ::= { autoWatchEntry 31 }

    watchCriteria3Regex OBJECT-TYPE
        SYNTAX SnmpAdminString (SIZE (0..512))
        ACCESS read-write
        STATUS mandatory
        DESCRIPTION
            "A regular expression to apply to the tertiary table entry column for criteria matching.
             NOTE: This attribute cannot be changed for existing autowatcher entries unless rowStatus is set to 
                   notInService(2)."
    ::= { autoWatchEntry 32 }

    watchCriteria3MatchType OBJECT-TYPE
        SYNTAX INTEGER {
            positive(1),
            negative(2)
        }
        ACCESS read-write
        STATUS mandatory
        DESCRIPTION
            "Regular Expression match type for watchInstanceCriteria3Regex.  Specifying negative match type
             will match instances that do not meet the specified criteria specified in the regular expression.
             NOTE: This attribute cannot be changed for existing autowatcher entries unless rowStatus is set to 
                   notInService(2)."
        DEFVAL { positive }
    ::= { autoWatchEntry 33 }

------------------------------------------------------------

    autoWatchUnusedIndex OBJECT-TYPE
        SYNTAX INTEGER (1..2147483647)
        ACCESS read-only
        STATUS mandatory
        DESCRIPTION
            "This attribute returns an unused watchIndex, which can be used for row creation."
    ::= { autoWatch 2 }

    autoWatchMatchName OBJECT-TYPE
        SYNTAX DisplayString
        ACCESS read-write
        STATUS mandatory
        DESCRIPTION
            "This attribute can be used to determine the index of a particular row.
            Setting the attribute to an auto-watcher name causes the agent to place the index of
            the last row, whose watchName matches, in the autoWatchMatchIndex attribute."
    ::= { autoWatch 3 }

    autoWatchMatchIndex OBJECT-TYPE
        SYNTAX INTEGER (1..2147483647)
        ACCESS read-only
        STATUS mandatory
        DESCRIPTION
            "This attribute stores the index of the last row, whose watchName matches autoWatchMatchName."
    ::= { autoWatch 4 }



------------------------------------------------------------
-- The TRAP-TYPE Definitions
------------------------------------------------------------
-- Each trap has a corresponding object identifier in the SystemEdge 'traps' group.

    monitorTrap TRAP-TYPE
        ENTERPRISE sysmgmt
        VARIABLES {
            monDescr,
            monOID,
            monCurrVal,
            monValue,
            monRowStatus,
            monOperator,
            monIndex,
            monFlags,
            monObjClass,
            monObjInstance,
            monObjAttribute,
            monCurrState,
            monAutoWatchIndex,
            monAutoWatchName
        }
        DESCRIPTION
            "The threshold condition of a self monitor (see monitorTable) is breached."
    ::= 1

--  kernelErrorTrap TRAP-TYPE
--      is deprecated
--  ::= 2

    monitorEntryNotReadyTrap TRAP-TYPE
        ENTERPRISE sysmgmt
        VARIABLES {
            monDescr,
            monOID,
            monCurrVal,
            monValue,
            monRowStatus,
            monOperator,
            monIndex,
            monFlags,
            monObjClass,
            monObjInstance,
            monObjAttribute,
            monCurrState,
            monAutoWatchIndex,
            monAutoWatchName
        }
        DESCRIPTION 
            "The row status of a self monitor (see monitorTable) has become notReady(3),
            typically because the monitored OID does not exist."
    ::= 3

    logMonMatchTrap TRAP-TYPE
        ENTERPRISE sysmgmt
        VARIABLES {
            logMonitorLogFile,
            logMonitorRegularExpression,
            logMonitorLastTrap,
            logMonitorLastMatch,
            logMonitorDescr,
            logMonitorIndex,
            logMonitorFlags,
            logMonitorLogFileName,
            logMonitorSeverity
        }
        DESCRIPTION
            "The regular expression pattern of a log file monitor (see logMonitorTable) matched."
    ::= 4

    logMonNotReadyTrap TRAP-TYPE
        ENTERPRISE sysmgmt
        VARIABLES {
            logMonitorLogFile,
            logMonitorRegularExpression,
            logMonitorLastTrap,
            logMonitorLastMatch,
            logMonitorDescr,
            logMonitorIndex,
            logMonitorFlags,
            logMonitorLogFileName,
            logMonitorSeverity
        }
        DESCRIPTION
            "The row status of a log file monitor (see logMonitorTable) has become notReady(3),
            typically because the log file does not exist."
    ::= 5

--  sendTrapTrap TRAP-TYPE
--      is deprecated
--  ::= 6

    ntEventMonMatchTrap  TRAP-TYPE
        ENTERPRISE sysmgmt
        VARIABLES {
            ntEventMonLog,
            ntEventMonTypeLastMatch,
            ntEventMonTime,
            ntEventMonSrcLastMatch,
            ntEventMonDescLastMatch,
            ntEventMonDescr,
            ntEventMonIndex,
            ntEventMonFlags,
            ntEventMonSeverity
        }
        DESCRIPTION
            "All filters (log, type, src, desc) of an Windows event log monitor (see ntEventMonTable) matched."
    ::= 7

    ntEventMonNotReadyTrap  TRAP-TYPE
        ENTERPRISE sysmgmt
        VARIABLES {
            ntEventMonLog,
            ntEventMonTypeFilter,
            ntEventMonSrcFilter,
            ntEventMonDescFilter,
            ntEventMonDescr,
            ntEventMonIndex,
            ntEventMonFlags,
            ntEventMonSeverity
        }
        DESCRIPTION
            "The row status of an Windows event log monitor (see ntEventMonTable) has become notReady(3),
            typically because an event log does not exist."
    ::= 8

    monitorClearTrap  TRAP-TYPE
        ENTERPRISE sysmgmt
        VARIABLES {
            monDescr,
            monOID,
            monCurrVal,
            monValue,
            monRowStatus,
            monOperator,
            monIndex,
            monFlags,
            monObjClass,
            monObjInstance,
            monObjAttribute,
            monCurrState,
            monAutoWatchIndex,
            monAutoWatchName
        }
        DESCRIPTION 
            "The threshold condition of a self monitor (see monitorTable) is no more breached."
    ::= 9

    processStopTrap TRAP-TYPE
        ENTERPRISE sysmgmt
        VARIABLES {
            pmonIndex,
            pmonDescr,
            pmonAttribute,
            pmonCurrVal,
            pmonOperator,
            pmonValue,
            pmonFlags,
            pmonRegExpr,
            pmonCurrentPID,
            pmonObjClass,
            pmonObjInstance,
            pmonObjAttribute,
            pmonCurrState,
            pmonProcName,
            pmonAutoWatchIndex,
            pmonAutoWatchName
        }
        DESCRIPTION
            "The process (or Windows service) monitored by a process monitor (see processMonTable) using procAlive is not running."
    ::= 10

    processStartTrap TRAP-TYPE
        ENTERPRISE sysmgmt
        VARIABLES {
            pmonIndex,
            pmonDescr,
            pmonAttribute,
            pmonCurrVal,
            pmonOperator,
            pmonValue,
            pmonFlags,
            pmonRegExpr,
            pmonCurrentPID,
            pmonObjClass,
            pmonObjInstance,
            pmonObjAttribute,
            pmonCurrState,
            pmonProcName,
            pmonAutoWatchIndex,
            pmonAutoWatchName
        }
        DESCRIPTION
            "The process (or Windows service) monitored by a process monitor (see processMonTable) using procAlive has been re-started."
    ::= 11

    processThresholdTrap TRAP-TYPE
        ENTERPRISE sysmgmt
        VARIABLES {
            pmonIndex,
            pmonDescr,
            pmonAttribute,
            pmonCurrVal,
            pmonOperator,
            pmonValue,
            pmonFlags,
            pmonRegExpr,
            pmonCurrentPID,
            pmonObjClass,
            pmonObjInstance,
            pmonObjAttribute,
            pmonCurrState,
            pmonProcName,
            pmonAutoWatchIndex,
            pmonAutoWatchName
        }
        DESCRIPTION
            "The threshold condition of a process monitor (see processMonTable) is breached."
    ::= 12

    processClearTrap TRAP-TYPE
        ENTERPRISE sysmgmt
        VARIABLES {
            pmonIndex,
            pmonDescr,
            pmonAttribute,
            pmonCurrVal,
            pmonOperator,
            pmonValue,
            pmonFlags,
            pmonRegExpr,
            pmonCurrentPID,
            pmonObjClass,
            pmonObjInstance,
            pmonObjAttribute,
            pmonCurrState,
            pmonProcName,
            pmonAutoWatchIndex,
            pmonAutoWatchName
        }
        DESCRIPTION
            "The threshold condition of a process monitor (see processMonTable) is no more breached."
    ::= 13

    processNotReadyTrap TRAP-TYPE
        ENTERPRISE sysmgmt
        VARIABLES {
            pmonIndex,
            pmonDescr,
            pmonAttribute,
            pmonCurrVal,
            pmonOperator,
            pmonValue,
            pmonFlags,
            pmonRegExpr,
            pmonCurrentPID,
            pmonObjClass,
            pmonObjInstance,
            pmonObjAttribute,
            pmonCurrState,
            pmonProcName,
            pmonAutoWatchIndex,
            pmonAutoWatchName
        }
        DESCRIPTION
            "The row status of a process monitor (see processMonTable) not using procAlive has become notReady(3),
            typically because the process does not exist."
    ::= 14

--  logMonReinitTrap TRAP-TYPE
--      is deprecated
--  ::= 15

--  licenseTrap TRAP-TYPE
--      is deprecated
--  ::= 16

--  fwLogmonTrap TRAP-TYPE
--      is deprecated
--  ::= 17

    addrChangeTrap TRAP-TYPE
        ENTERPRISE sysmgmt
        VARIABLES {
            nodename,
            sysedgeAddressList
        }
        DESCRIPTION
            "The IP address of the agent's machine has changed, typically due to DHCP or other administrative means."
    ::= 18

    procGroupChangeTrap TRAP-TYPE
        ENTERPRISE sysmgmt
        VARIABLES {
            pgmonIndex,
            pgmonDescr,
            pgmonFlags,
            pgmonNumProcs,
            pgmonProcRegExpr,
            pgmonRowStatus,
            pgmonPIDList,
            pgmonStatusList,
            pgmonSeverity,
            pgmonProcNameList
        }
        DESCRIPTION
            "The membership of a process group monitor (see processGroupMonTable) has changed,
            typically because processes have joined or left."
    ::= 19

    aggregateStateTrap TRAP-TYPE
        ENTERPRISE sysmgmt
        VARIABLES {
            aggIndex,
            aggObjClass,
            aggObjInstance,
            aggObjAttribute,
            aggCurrState,
            aggPrevState,
            aggMonTable,
            aggMonIndex,
            aggMonCurrVal,
            aggMonOperator,
            aggMonValue,
            aggRowStatus
        }
        DESCRIPTION
            "The state of an aggregate (see aggregateTable) has changed."
    ::= 20

    aggregateAddTrap TRAP-TYPE
        ENTERPRISE sysmgmt
        VARIABLES {
            aggIndex,
            aggObjClass,
            aggObjInstance,
            aggObjAttribute
        }
        DESCRIPTION
            "A new aggregate (see aggregateTable) has been added."
    ::= 21

    aggregateDeleteTrap TRAP-TYPE
        ENTERPRISE sysmgmt
        VARIABLES {
            aggIndex,
            aggObjClass,
            aggObjInstance,
            aggObjAttribute
        }
        DESCRIPTION
            "An aggregate (see aggregateTable) has been deleted."
    ::= 22

    autowatchInstanceAddedTrap TRAP-TYPE
        ENTERPRISE sysmgmt
        VARIABLES {
            watchType,
            watchName,
            watchMonTableEntry,
            watchMonDescr,
            watchMonObjClass,
            watchMonObjAttribute,
            monIndex,
            monOID,
            monRowStatus,
            monObjInstance,
            pmonIndex,
            pmonAttribute,
            pmonRowStatus,
            pmonObjInstance
        }
        DESCRIPTION
            "An autowatch-generated monitor has been created.
             Depending upon watchType, either the monitor or process monitor entries would be specified 
             (and the others would be invalid)."
    ::= 23

    autowatchInstanceRemovedTrap TRAP-TYPE
        ENTERPRISE sysmgmt
        VARIABLES {
            watchType,
            watchName,
            watchMonTableEntry,
            watchMonDescr,
            watchMonObjClass,
            watchMonObjAttribute,
            monIndex,
            monOID,
            monRowStatus,
            monObjInstance,
            pmonIndex,
            pmonAttribute,
            pmonRowStatus,
            pmonObjInstance
        }
        DESCRIPTION
            "An autowatch-generated monitor has been deleted, either due to a change to the autowatch criteria
             or due to the watchLossAction=remove being triggered.
             Depending upon watchType, either the monitor or process monitor entries would be specified 
             (and the others would be invalid)."
    ::= 24

    autowatchInstanceLostTrap TRAP-TYPE
        ENTERPRISE sysmgmt
        VARIABLES {
            watchType,
            watchName,
            watchMonTableEntry,
            watchMonDescr,
            watchMonObjClass,
            watchMonObjAttribute,
            monIndex,
            monOID,
            monRowStatus,
            monObjInstance,
            monCurrState,
            pmonIndex,
            pmonAttribute,
            pmonRowStatus,
            pmonObjInstance,
            pmonCurrState
        }
        DESCRIPTION
            "An autowatch-generated monitor has detected a lost instance.  If watchLossAction=remove is specified,
             an autowatchInstanceRemoved trap may also be sent.  If watchLossAction!=remove, the state of the 
             generated monitor will be modified based on the watchLossAction specification.
             Depending upon watchType, either the monitor or process monitor entries would be specified 
             (and the others would be invalid)."
    ::= 25

    autowatchNotReadyTrap TRAP-TYPE
        ENTERPRISE sysmgmt
        VARIABLES {
            watchType,
            watchName,
            watchMonTableEntry,
            watchMonDescr,
            watchMonObjClass,
            watchMonObjAttribute,
            watchMaxInstances,
            watchNumInstances,
            watchCriteria2Column,
            watchCriteria3Column
        }
        DESCRIPTION
            "An autowatcher has been placed into notReady(3) status, due to a restriction to its functionality.
             At present, an autowatcher is placed into notReady status if any of the criteria is invalid, if the 
             number of generated instances would be exceeded, or if the autowatcher cannot create a monitor due 
             to a restricted monitor table index limit."
    ::= 26

END
