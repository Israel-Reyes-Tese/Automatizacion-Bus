--
-- This SMIv2 module has been generated by smidump 0.2-cvs. Do not edit.
--

RFC1155-SMI DEFINITIONS ::= BEGIN

ObjectName ::=
    OBJECT IDENTIFIER

NetworkAddress ::=
    IpAddress

IpAddress ::=
    OCTET STRING (SIZE(4))

Counter ::=
    Unsigned32 (0..4294967295)

Gauge ::=
    Unsigned32 (0..4294967295)

TimeTicks ::=
    Unsigned32 (0..4294967295)

Opaque ::=
    OCTET STRING

org OBJECT IDENTIFIER
    ::= { iso 3 }

dod OBJECT IDENTIFIER
    ::= { org 6 }

internet OBJECT IDENTIFIER
    ::= { dod 1 }

directory OBJECT IDENTIFIER
    ::= { internet 1 }

mgmt OBJECT IDENTIFIER
    ::= { internet 2 }

experimental OBJECT IDENTIFIER
    ::= { internet 3 }

private OBJECT IDENTIFIER
    ::= { internet 4 }

enterprises OBJECT IDENTIFIER
    ::= { private 1 }

END -- end of module RFC1155-SMI.
