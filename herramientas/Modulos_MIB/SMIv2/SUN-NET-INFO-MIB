--
-- This SMIv2 module has been generated by smidump 0.2-cvs. Do not edit.
--

SUN-NET-INFO-MIB DEFINITIONS ::= BEGIN

IMPORTS
    entPhysicalIndex
        FROM ENTITY-MIB
    SnmpAdminString
        FROM SNMP-FRAMEWORK-MIB
    Integer32, MODULE-IDENTITY, NOTIFICATION-TYPE, OBJECT-IDENTITY, 
    OBJECT-TYPE, Unsigned32, enterprises
        FROM SNMPv2-SMI
    DateAndTime, RowPointer, RowStatus, TAddress, TDomain, 
    TEXTUAL-CONVENTION, TestAndIncr, TruthValue
        FROM SNMPv2-TC;

sunNimMIB MODULE-IDENTITY
    LAST-UPDATED    "197001010000Z"
    ORGANIZATION    
            "Sun Microsystems, Inc."
    CONTACT-INFO    
            ""
    DESCRIPTION     
            "SUN-NET-INFO-MIB.mib Version 1.46
             Copyright (c) 2000, by Sun Microsystems, Inc.
             All rights reserved.
             
             This MIB module is an SNMP version of the Generic Network
             Information Model (NIM) presented in ITU-T M.3100.
             
             The containment hierarchy is modelled using the ENTITY-MIB (RFC2737)
             where each physical entity modelled in the system is represented by
             means of extensions to the entPhyscialTable.
             
             Where an entity is an instance of a managed object class which is
             sub-classed from another, the attributes of each class are modelled 
             in a separate table extension. For example for an entity with an 
             entPhysicalClass of module(9), which corresponds to a Circuit Pack, 
             sub-classed from Equipment, an entry will exist in the 
             sunNimEquipmentTable, with additional attributes in the 
             sunNimCircuitPackTable.
             
             The entries in the entPhysicalTable have the following significance
             with respect to the NIM model:
             
             entPhysicalIndex           containment, M.3100, fig. 2
             entPhysicalDescr           n/a
             entPhysicalVendorType      n/a
             entPhysicalContainedIn     containment, M.3100, fig. 2
             entPhysicalClass           Managed Object Class, M.3100, Table 1
             entPhysicalParentRelPos    containment, M.3100, fig. 2
             entPhysicalName            n/a
             entPhysicalHardwareRev     version, M.3100, sec. 5.71
             entPhysicalFirmwareRev     version, M.3100, sec. 5.71
             entPhysicalSoftwareRev     version, M.3100, sec. 5.71
             entPhysicalSerialNum       n/a
             entPhysicalMfgName         vendorName, M.3100, sec. 5.70
             entPhysicalModelName       n/a
             entPhysicalAlias           userLabel, M.3100, sec. 5.69
             entPhysicalAssetID         n/a
             entPhysicalIsFRU           n/a
             
             The entries marked n/a may be used for other purposes such as
             FRU asset/inventory control, but that is beyond the scope of this
             MIB.
             
             In particular note that the entPhysicalDescr object may, for
             an entPhysicalClass of port(10), be set to match the ifDescr in the
             ifTable of the IF-MIB to allow a manager to identify the port
             associated with a given interface. Typical identifiers are 'lo0'
             or 'hme1'.
             
             References are made to the following recommendations/revisions:
             
                 ITU-T M.3100 (07/95)
                 CCITT X.721 (1992 E)
                 CCITT X.731 (1992 E) (01/92)
                 CCITT X.733 (1992 E)
                 CCITT X.734 (1992 E)
                 CCITT X.735 (1992 E) (09/92)"
    REVISION        "197001010000Z"
    DESCRIPTION     
            "Initial version of MIB module SUN-NET-INFO-MIB."
    ::= { netra-test 2 }


SunNimLogAdministrativeState ::= TEXTUAL-CONVENTION
    STATUS          current
    DESCRIPTION     
            "An enumerated value which describes the Administrative
             State of the log as defined in X.735, sec. 8.1.1.1.3."
    SYNTAX          INTEGER { locked(1), unlocked(2) }

SunNimAdministrativeState ::= TEXTUAL-CONVENTION
    STATUS          current
    DESCRIPTION     
            "An enumerated value which describes the Administrative
             State of the managed object as defined in X.731, sec. 8.1.1.3."
    SYNTAX          INTEGER { locked(1), unlocked(2), shuttingDown(3) }

SunNimOperationalState ::= TEXTUAL-CONVENTION
    STATUS          current
    DESCRIPTION     
            "An enumerated value which describes the Operational
             State of the managed object as defined in X.731, sec. 8.1.1.1."
    SYNTAX          INTEGER { disabled(1), enabled(2) }

SunNimAlarmPerceivedSeverity ::= TEXTUAL-CONVENTION
    STATUS          current
    DESCRIPTION     
            "The value of this object identifies the Perceived Severity of
             an alarm in the log, including 'cleared' as defined in X.733,
             sec. 8.1.2.3."
    SYNTAX          INTEGER { indeterminate(1), critical(2), major(3), 
                        minor(4), warning(5), cleared(6) }

SunNimAlarmStatus ::= TEXTUAL-CONVENTION
    STATUS          current
    DESCRIPTION     
            "The value of this object identifies the Alarm Status of the
             managed object as defined in M.3100, sec. 5.8."
    SYNTAX          INTEGER { critical(1), major(2), minor(3), 
                        indeterminate(4), warning(5), pending(6), 
                        cleared(7) }

SunNimEquipmentHolderType ::= TEXTUAL-CONVENTION
    STATUS          current
    DESCRIPTION     
            "The Equipment Holder Type as defined in M.3100, sec. 5.26."
    SYNTAX          INTEGER { bay(1), shelf(2), drawer(3), slot(4), 
                        rack(5) }

SunNimEquipmentHolderStatus ::= TEXTUAL-CONVENTION
    STATUS          current
    DESCRIPTION     
            "This attribute identifies whether or not a Circuit Pack is
             present in the slot and if so, is it recognised/acceptable as
             defined as Holder Status in M.3100, sec. 5.32."
    SYNTAX          INTEGER { holderEmpty(1), inTheAcceptableList(2), 
                        notInTheAcceptableList(3), unknownType(4) }

SunNimLogFullAction ::= TEXTUAL-CONVENTION
    STATUS          current
    DESCRIPTION     
            "Indicates the action that should be performed when no
             more log entries can be created due to a log-full
             condition.  If the value of this object is wrap(2),
             each new log entry will cause the deletion of the oldest
             entry still in the log, for as long as the log is still
             full. This is as defined as Log Full Action in X.735,
             sec. 8.1.1.1.5."
    SYNTAX          INTEGER { halt(1), wrap(2) }

SunNimProbableCause ::= TEXTUAL-CONVENTION
    STATUS          current
    DESCRIPTION     
            "A Probable Cause which provides additional information
             associated with and alarm notification as per ITU-T M.3100 sec. 10.2."
    SYNTAX          INTEGER { indeterminate(0), aIS(1), 
                        callSetUpFailure(2), degradedSignal(3), 
                        farEndReceiverFailure(4), framingError(5), 
                        lossOfFrame(6), lossOfPointer(7), 
                        lossOfSignal(8), payloadTypeMismatch(9), 
                        transmissionError(10), remoteAlarmInterface(11), 
                        excessiveBER(12), pathTraceMismatch(13), 
                        unavailable(14), signalLabelMismatch(15), 
                        lossOfMultiFrame(16), backplaneFailure(51), 
                        dataSetProblem(52), 
                        equipmentIdentifierDuplication(53), 
                        externalIFDeviceProblem(54), lineCardProblem(55), 
                        multiplexerProblem(56), 
                        nEIdentifierDuplication(57), powerProblem(58), 
                        processorProblem(59), protectionPathFailure(60), 
                        receiverFailure(61), replaceableUnitMissing(62), 
                        replaceableUnitTypeMismatch(63), 
                        synchronizationSourceMismatch(64), 
                        terminalProblem(65), timingProblem(66), 
                        transmitterFailure(67), trunkCardProblem(68), 
                        replaceableUnitProblem(69), 
                        airCompressorFailure(101), 
                        airConditioningFailure(102), 
                        airDryerFailure(103), batteryDischarging(104), 
                        batteryFailure(105), commercialPowerFailure(106), 
                        coolingFanFailure(107), engineFailure(108), 
                        fireDetectorFailure(109), fuseFailure(110), 
                        generatorFailure(111), lowBatteryThreshold(112), 
                        pumpFailure(113), rectifierFailure(114), 
                        rectifierHighVoltage(115), 
                        rectifierLowFVoltage(116), 
                        ventilationsSystemFailure(117), 
                        enclosureDoorOpen(118), explosiveGas(119), 
                        fire(120), flood(121), highHumidity(122), 
                        highTemperature(123), highWind(124), 
                        iceBuildUp(125), intrusionDetection(126), 
                        lowFuel(127), lowHumidity(128), 
                        lowCablePressure(129), lowTemperatue(130), 
                        lowWater(131), smoke(132), toxicGas(133), 
                        storageCapacityProblem(151), memoryMismatch(152), 
                        corruptData(153), outOfCPUCycles(154), 
                        sfwrEnvironmentProblem(155), 
                        sfwrDownloadFailure(156) }

SunNimPercentage ::= TEXTUAL-CONVENTION
    STATUS          current
    DESCRIPTION     
            "Used to express a value, in %."
    SYNTAX          Integer32 (0..100)

sun OBJECT IDENTIFIER
    ::= { enterprises 42 }

products OBJECT IDENTIFIER
    ::= { enterprises 42 2 }

netra OBJECT IDENTIFIER
    ::= { enterprises 42 2 25 }

netra-test OBJECT IDENTIFIER
    ::= { netra 99 }

sunNimMIBObjects OBJECT IDENTIFIER
    ::= { sunNimMIB 1 }

sunNimStartTime OBJECT-TYPE
    SYNTAX          DateAndTime
    MAX-ACCESS      read-only
    STATUS          current
    DESCRIPTION     
            "The time at which the agent was last started; in other
             words, the time at which sysUpTime was zero."
    ::= { sunNimMIBObjects 1 }

sunNimEquipmentTable OBJECT-TYPE
    SYNTAX          SEQUENCE OF SunNimEquipmentEntry
    MAX-ACCESS      not-accessible
    STATUS          current
    DESCRIPTION     
            "The NIM Equipment table.  This table augments the
             entPhysicalTable to provide the attributes defined for
             equipment under M.3100, sec. 3.2.2.
             
             Additional packages may be supported using further table
             extensions.
             
             The sunNimEquipmentTable is valid for entPhysicalClass values of
             chassis(3), backplane(4), container(5), powerSupply(6), fan(7),
             sensor(8), module(9), and other(1)."
    ::= { sunNimMIBObjects 2 }

sunNimEquipmentEntry OBJECT-TYPE
    SYNTAX          SunNimEquipmentEntry
    MAX-ACCESS      not-accessible
    STATUS          current
    DESCRIPTION     
            "An entry in the NIM Equipment table.  Each entry
             of this table represents a piece of equipment within the 
             network element of the type specified by entPhysicalClass."
    INDEX           { entPhysicalIndex }
    ::= { sunNimEquipmentTable 1 }

SunNimEquipmentEntry ::=
    SEQUENCE {
        sunNimEquipmentAdministrativeState  SunNimAdministrativeState,
        sunNimEquipmentOperationalState SunNimOperationalState,
        sunNimEquipmentAlarmStatus      SunNimAlarmStatus,
        sunNimEquipmentUnknownStatus    TruthValue,
        sunNimEquipmentLocationName     SnmpAdminString,
        sunNimEquipmentAlarmSeverityProfileIndex        Integer32
    }

sunNimEquipmentAdministrativeState OBJECT-TYPE
    SYNTAX          SunNimAdministrativeState
    MAX-ACCESS      read-write
    STATUS          current
    DESCRIPTION     
            "An enumerated value which describes the Administrative
             State of the managed object as defined in X.731, sec. 8.1.1.3."
    ::= { sunNimEquipmentEntry 1 }

sunNimEquipmentOperationalState OBJECT-TYPE
    SYNTAX          SunNimOperationalState
    MAX-ACCESS      read-only
    STATUS          current
    DESCRIPTION     
            "An enumerated value which describes the Operational
             State of the managed object as defined in X.731, sec. 8.1.1.1."
    ::= { sunNimEquipmentEntry 2 }

sunNimEquipmentAlarmStatus OBJECT-TYPE
    SYNTAX          SunNimAlarmStatus
    MAX-ACCESS      read-only
    STATUS          current
    DESCRIPTION     
            "The value of this object identifies the Alarm Status of the
             managed object as defined in M.3100, sec. 5.8."
    ::= { sunNimEquipmentEntry 3 }

sunNimEquipmentUnknownStatus OBJECT-TYPE
    SYNTAX          TruthValue
    MAX-ACCESS      read-only
    STATUS          current
    DESCRIPTION     
            "This attribute identifies whether or not the state
             of the entity is known as defined as Unknown Status in X.731,
             sec. 8.1.2.6."
    DEFVAL          { true }
    ::= { sunNimEquipmentEntry 4 }

sunNimEquipmentLocationName OBJECT-TYPE
    SYNTAX          SnmpAdminString
    MAX-ACCESS      read-write
    STATUS          current
    DESCRIPTION     
            "The specific or general location of the component as defined
             as Location Name in M.3100, sec. 5.37."
    ::= { sunNimEquipmentEntry 5 }

sunNimEquipmentAlarmSeverityProfileIndex OBJECT-TYPE
    SYNTAX          Integer32
    MAX-ACCESS      read-write
    STATUS          current
    DESCRIPTION     
            "An index into the alarm severity profile table, specifying
             the severity assignments for alarms reported for this
             component.  The default value of this object is zero.
             
             This object provides the alarmSeverityAssignmentPointerPackage
             required by M.3100, sec. 3.2.4."
    ::= { sunNimEquipmentEntry 10 }

sunNimEquipmentHolderTable OBJECT-TYPE
    SYNTAX          SEQUENCE OF SunNimEquipmentHolderEntry
    MAX-ACCESS      not-accessible
    STATUS          current
    DESCRIPTION     
            "The NIM Equipment-Holder table.  This table augments the
             entPhysicalTable to provide the attributes defined for
             equipmentHolder under M.3100, sec. 3.2.3.
             
             It is valid for an entPhysicalClass of container(5)."
    ::= { sunNimMIBObjects 3 }

sunNimEquipmentHolderEntry OBJECT-TYPE
    SYNTAX          SunNimEquipmentHolderEntry
    MAX-ACCESS      not-accessible
    STATUS          current
    DESCRIPTION     
            "An entry in the NIM Equipment-Holder table.  Each
             entry of this table represents a component within the 
             network element that accepts a replaceable Circuit Pack."
    INDEX           { entPhysicalIndex }
    ::= { sunNimEquipmentHolderTable 1 }

SunNimEquipmentHolderEntry ::=
    SEQUENCE {
        sunNimEquipmentHolderType       SunNimEquipmentHolderType,
        sunNimEquipmentHolderAcceptableTypes    SnmpAdminString,
        sunNimEquipmentHolderStatus     SunNimEquipmentHolderStatus
    }

sunNimEquipmentHolderType OBJECT-TYPE
    SYNTAX          SunNimEquipmentHolderType
    MAX-ACCESS      read-only
    STATUS          current
    DESCRIPTION     
            "The type of the component as defined in M.3100, sec. 5.26."
    ::= { sunNimEquipmentHolderEntry 1 }

sunNimEquipmentHolderAcceptableTypes OBJECT-TYPE
    SYNTAX          SnmpAdminString
    MAX-ACCESS      read-only
    STATUS          current
    DESCRIPTION     
            "The types of Circuit Pack that can be supported by the
             slot, separated by newline characters as defined in M.3100, sec. 5.2."
    ::= { sunNimEquipmentHolderEntry 2 }

sunNimEquipmentHolderStatus OBJECT-TYPE
    SYNTAX          SunNimEquipmentHolderStatus
    MAX-ACCESS      read-only
    STATUS          current
    DESCRIPTION     
            "This attributes identifies whether or not a Circuit Pack is
             present in the slot as defined in M.3100, sec. 5.32."
    ::= { sunNimEquipmentHolderEntry 3 }

sunNimCircuitPackTable OBJECT-TYPE
    SYNTAX          SEQUENCE OF SunNimCircuitPackEntry
    MAX-ACCESS      not-accessible
    STATUS          current
    DESCRIPTION     
            "The NIM Circuit-Pack table.  This table augments
             the entPhysicalTable to provide the attributes defined for
             circuitPack under M.3100, sec. 3.2.1.
             
             It is valid for an entPhysicalClass of module(9)."
    ::= { sunNimMIBObjects 4 }

sunNimCircuitPackEntry OBJECT-TYPE
    SYNTAX          SunNimCircuitPackEntry
    MAX-ACCESS      not-accessible
    STATUS          current
    DESCRIPTION     
            "An entry in the NIM Circuit-Pack table.  Each
             entry of this table represents a piece of equipment within
             the network element that is inserted into and removed from 
             an Equipment-Holder."
    INDEX           { entPhysicalIndex }
    ::= { sunNimCircuitPackTable 1 }

SunNimCircuitPackEntry ::=
    SEQUENCE {
        sunNimCircuitPackType           SnmpAdminString,
        sunNimCircuitPackAvailabilityStatusInTest         TruthValue,
        sunNimCircuitPackAvailabilityStatusFailed         TruthValue,
        sunNimCircuitPackAvailabilityStatusPowerOff           TruthValue,
        sunNimCircuitPackAvailabilityStatusOffLine          TruthValue,
        sunNimCircuitPackAvailabilityStatusOffDuty          TruthValue,
        sunNimCircuitPackAvailabilityStatusDependency             TruthValue,
        sunNimCircuitPackAvailabilityStatusDegraded           TruthValue,
        sunNimCircuitPackAvailabilityStatusNotInstalled               TruthValue
    }

sunNimCircuitPackType OBJECT-TYPE
    SYNTAX          SnmpAdminString
    MAX-ACCESS      read-only
    STATUS          current
    DESCRIPTION     
            "The type of this circuit pack as defined in M.3100, sec. 5.13."
    ::= { sunNimCircuitPackEntry 1 }

sunNimCircuitPackAvailabilityStatusInTest OBJECT-TYPE
    SYNTAX          TruthValue
    MAX-ACCESS      read-only
    STATUS          current
    DESCRIPTION     
            "The availabiltyStatus 'in test' attribute as defined in X.731,
             sec. 8.1.2.3."
    ::= { sunNimCircuitPackEntry 2 }

sunNimCircuitPackAvailabilityStatusFailed OBJECT-TYPE
    SYNTAX          TruthValue
    MAX-ACCESS      read-only
    STATUS          current
    DESCRIPTION     
            "The availabiltyStatus 'failed' attribute as defined in X.731, 
             sec. 8.1.2.3."
    ::= { sunNimCircuitPackEntry 3 }

sunNimCircuitPackAvailabilityStatusPowerOff OBJECT-TYPE
    SYNTAX          TruthValue
    MAX-ACCESS      read-only
    STATUS          current
    DESCRIPTION     
            "The availabiltyStatus 'power off' attribute as defined in X.731, 
             sec. 8.1.2.3."
    ::= { sunNimCircuitPackEntry 4 }

sunNimCircuitPackAvailabilityStatusOffLine OBJECT-TYPE
    SYNTAX          TruthValue
    MAX-ACCESS      read-only
    STATUS          current
    DESCRIPTION     
            "The availabiltyStatus 'off line' attribute as defined in X.731, 
             sec. 8.1.2.3."
    ::= { sunNimCircuitPackEntry 5 }

sunNimCircuitPackAvailabilityStatusOffDuty OBJECT-TYPE
    SYNTAX          TruthValue
    MAX-ACCESS      read-only
    STATUS          current
    DESCRIPTION     
            "The availabiltyStatus 'off duty' attribute as defined in X.731,
             sec. 8.1.2.3."
    ::= { sunNimCircuitPackEntry 6 }

sunNimCircuitPackAvailabilityStatusDependency OBJECT-TYPE
    SYNTAX          TruthValue
    MAX-ACCESS      read-only
    STATUS          current
    DESCRIPTION     
            "The availabiltyStatus 'dependency' attribute as defined in X.731,
             sec. 8.1.2.3."
    ::= { sunNimCircuitPackEntry 7 }

sunNimCircuitPackAvailabilityStatusDegraded OBJECT-TYPE
    SYNTAX          TruthValue
    MAX-ACCESS      read-only
    STATUS          current
    DESCRIPTION     
            "The availabiltyStatus 'degraded' attribute as defined in X.731,
             sec. 8.1.2.3."
    ::= { sunNimCircuitPackEntry 8 }

sunNimCircuitPackAvailabilityStatusNotInstalled OBJECT-TYPE
    SYNTAX          TruthValue
    MAX-ACCESS      read-only
    STATUS          current
    DESCRIPTION     
            "The availabiltyStatus 'not installed' attribute as defined in X.731,
             sec. 8.1.2.3."
    ::= { sunNimCircuitPackEntry 9 }

sunNimTerminationPointTable OBJECT-TYPE
    SYNTAX          SEQUENCE OF SunNimTerminationPointEntry
    MAX-ACCESS      not-accessible
    STATUS          current
    DESCRIPTION     
            "The NIM Termination Point table. This table augments the
             entPhysicalTable to provide the attributes defined for
             terminationPoint under M.3100, sec. 3.3.4.
             
             This table models only the operational state of the port to
             effectively provide link up/link down information.
             
             No connection information is maintained in this table.
             
             It is valid for an entPhysicalClass of port(10)."
    ::= { sunNimMIBObjects 5 }

sunNimTerminationPointEntry OBJECT-TYPE
    SYNTAX          SunNimTerminationPointEntry
    MAX-ACCESS      not-accessible
    STATUS          current
    DESCRIPTION     
            "An entry in the NIM Termination Point table.  Each
             entry of this table represents a port within the 
             network element."
    INDEX           { entPhysicalIndex }
    ::= { sunNimTerminationPointTable 1 }

SunNimTerminationPointEntry ::=
    SEQUENCE {
        sunNimTerminationPointOperationalState      SunNimOperationalState,
        sunNimTerminationPointAlarmStatus SunNimAlarmStatus,
        sunNimTerminationPointUnknownStatus   TruthValue,
        sunNimTerminationPointAlarmSeverityProfileIndex               Integer32
    }

sunNimTerminationPointOperationalState OBJECT-TYPE
    SYNTAX          SunNimOperationalState
    MAX-ACCESS      read-only
    STATUS          current
    DESCRIPTION     
            "An enumerated value which describes the Operational
             State of the port as defined in X.731, sec. 8.1.1.1."
    ::= { sunNimTerminationPointEntry 1 }

sunNimTerminationPointAlarmStatus OBJECT-TYPE
    SYNTAX          SunNimAlarmStatus
    MAX-ACCESS      read-only
    STATUS          current
    DESCRIPTION     
            "The value of this object identifies the Alarm Status of the
             managed object as defined in M.3100, sec. 5.8."
    ::= { sunNimTerminationPointEntry 2 }

sunNimTerminationPointUnknownStatus OBJECT-TYPE
    SYNTAX          TruthValue
    MAX-ACCESS      read-only
    STATUS          current
    DESCRIPTION     
            "This attribute identifies whether or not the state
             of the entity is known as defined as Unknown Status in X.731,
             sec. 8.1.2.6."
    DEFVAL          { true }
    ::= { sunNimTerminationPointEntry 3 }

sunNimTerminationPointAlarmSeverityProfileIndex OBJECT-TYPE
    SYNTAX          Integer32
    MAX-ACCESS      read-write
    STATUS          current
    DESCRIPTION     
            "Specifies the index of the entry in the communications
             alarm severity profile table that should be used.  The default
             value of this object is zero.
             
             This object provides the alarmSeverityAssignmentPointerPackage
             required by M.3100, sec. 3.3.4."
    ::= { sunNimTerminationPointEntry 4 }

sunNimAlarmSevDefault OBJECT-TYPE
    SYNTAX          SunNimAlarmPerceivedSeverity
    MAX-ACCESS      read-write
    STATUS          current
    DESCRIPTION     
            "This value is used whenever an object's alarm
             severity profile index is set to 0.  The default value
             of this object is minor(3)."
    DEFVAL          { minor }
    ::= { sunNimMIBObjects 6 }

sunNimAlarmSevProfileIndexNext OBJECT-TYPE
    SYNTAX          TestAndIncr
    MAX-ACCESS      read-only
    STATUS          current
    DESCRIPTION     
            "This object contains an appropriate value to be used for
             sunNimAlarmSevProfileIndex when creating entries in the
             sunNimAlarmSevProfileTable.
             
             The value -1 indicates that no unassigned entries are
             available.
             
             To obtain the index value for a new entry, the manager
             issues a management protocol retrieval operation to obtain
             the current value of this object.  After each retrieval, the
             agent should modify the value to the next unassigned index
             (or -1)."
    ::= { sunNimMIBObjects 7 }

sunNimAlarmSevProfileTable OBJECT-TYPE
    SYNTAX          SEQUENCE OF SunNimAlarmSevProfileEntry
    MAX-ACCESS      not-accessible
    STATUS          current
    DESCRIPTION     
            "The NIM alarm severity profile table. This table specifies which
             profiles exist. Creating or deleting an entry in this table
             automatically creates or deletes the corresponding entries in the
             sunNimAlarmPerceivedSeverityTable.
             
             This table corresponds to the alarmSeverityAssignmentProfile as
             defined in M.3100, sec. 3.6.2."
    ::= { sunNimMIBObjects 8 }

sunNimAlarmSevProfileEntry OBJECT-TYPE
    SYNTAX          SunNimAlarmSevProfileEntry
    MAX-ACCESS      not-accessible
    STATUS          current
    DESCRIPTION     
            "Each entry corresponds to a separate alarmSeverityAssignmentList."
    INDEX           { sunNimAlarmSevProfileIndex }
    ::= { sunNimAlarmSevProfileTable 1 }

SunNimAlarmSevProfileEntry ::=
    SEQUENCE {
        sunNimAlarmSevProfileIndex      Integer32,
        sunNimAlarmSevProfileRowStatus  RowStatus
    }

sunNimAlarmSevProfileIndex OBJECT-TYPE
    SYNTAX          Integer32 (1..2147483647)
    MAX-ACCESS      not-accessible
    STATUS          current
    DESCRIPTION     
            "A number identifying this alarm severity profile."
    ::= { sunNimAlarmSevProfileEntry 1 }

sunNimAlarmSevProfileRowStatus OBJECT-TYPE
    SYNTAX          RowStatus
    MAX-ACCESS      read-create
    STATUS          current
    DESCRIPTION     
            "This object is used to create a new row or to delete
             an existing row in the table."
    ::= { sunNimAlarmSevProfileEntry 2 }

sunNimAlarmSeverityAssignmentListTable OBJECT-TYPE
    SYNTAX          SEQUENCE OF SunNimAlarmSeverityAssignmentListEntry
    MAX-ACCESS      not-accessible
    STATUS          current
    DESCRIPTION     
            "The NIM alarm severity assignment list table. This table associates
             profile index and trap ID (probable cause) pairs with severities to
             be used for alarm traps that have occurred.
             
             This table implements the alarmSeverityAssignmentList defined in
             M.3100, sec. 5.5."
    ::= { sunNimMIBObjects 9 }

sunNimAlarmSeverityAssignmentListEntry OBJECT-TYPE
    SYNTAX          SunNimAlarmSeverityAssignmentListEntry
    MAX-ACCESS      not-accessible
    STATUS          current
    DESCRIPTION     
            "An entry in this table associates an alarm severity
             profile index/probableCause pair with a severity.
             
             Deleting a particular profile's row in the alarm severity
             profile table deletes all rows in this table with the
             same profile index."
    INDEX           { sunNimAlarmSevProfileIndex, 
                      sunNimAlarmSeverityAssignmentProbableCause }
    ::= { sunNimAlarmSeverityAssignmentListTable 1 }

SunNimAlarmSeverityAssignmentListEntry ::=
    SEQUENCE {
        sunNimAlarmSeverityAssignmentProbableCause          SunNimProbableCause,
        sunNimAlarmPerceivedSeverity    SunNimAlarmPerceivedSeverity
    }

sunNimAlarmSeverityAssignmentProbableCause OBJECT-TYPE
    SYNTAX          SunNimProbableCause
    MAX-ACCESS      not-accessible
    STATUS          current
    DESCRIPTION     
            "An probable cause which provides additional information
             relevant to this notification as per ITU-T M.3100 sec. 10.2."
    ::= { sunNimAlarmSeverityAssignmentListEntry 1 }

sunNimAlarmPerceivedSeverity OBJECT-TYPE
    SYNTAX          SunNimAlarmPerceivedSeverity
    MAX-ACCESS      read-create
    STATUS          current
    DESCRIPTION     
            "The severity to be used for this probable cause.
             
             If no value for this object has ever been set since
             the corresponding profile was created, the agent should
             return the value of the object sunNimAlarmSevDefault."
    ::= { sunNimAlarmSeverityAssignmentListEntry 2 }

sunNimDiscriminatorTable OBJECT-TYPE
    SYNTAX          SEQUENCE OF SunNimDiscriminatorEntry
    MAX-ACCESS      not-accessible
    STATUS          current
    DESCRIPTION     
            "The NIM trap forwarding discriminator table.
             This table specifies which traps will be sent to
             which management system as per X.721, sec. 6.4."
    ::= { sunNimMIBObjects 10 }

sunNimDiscriminatorEntry OBJECT-TYPE
    SYNTAX          SunNimDiscriminatorEntry
    MAX-ACCESS      not-accessible
    STATUS          current
    DESCRIPTION     
            "Information about a group of traps to be sent to
             a particular IP address.
             
             If the sunNimDiscriminatorProbableCause is specified
             as indeterminate(0), the assignment applies to all traps of
             type sunNimDiscriminatorTrapId unless another entry explicitly
             describes it.
             
             A new entry must have values for all attributes that
             do not have default values before its RowStatus column
             can be set to active(1).
             
             The operation of the discriminator is essentially as defined
             in X.734, sec. 8.1.1.1 except that the discriminators have
             no Operational or Administrative State and filter solely on
             the basis of the perceived alarm severity."
    INDEX           { sunNimDiscriminatorTrapId, 
                      sunNimDiscriminatorProbableCause, 
                      sunNimDiscriminatorTDomain, 
                      sunNimDiscriminatorTAddress }
    ::= { sunNimDiscriminatorTable 1 }

SunNimDiscriminatorEntry ::=
    SEQUENCE {
        sunNimDiscriminatorTrapId       OBJECT IDENTIFIER,
        sunNimDiscriminatorProbableCause SunNimProbableCause,
        sunNimDiscriminatorTDomain      TDomain,
        sunNimDiscriminatorTAddress     TAddress,
        sunNimLowestForwardedSeverity   SunNimAlarmPerceivedSeverity,
        sunNimForwardIndeterminate      TruthValue,
        sunNimDiscriminatorRowStatus    RowStatus
    }

sunNimDiscriminatorTrapId OBJECT-TYPE
    SYNTAX          OBJECT IDENTIFIER
    MAX-ACCESS      not-accessible
    STATUS          current
    DESCRIPTION     
            "The OID of the notification to which this entry applies."
    ::= { sunNimDiscriminatorEntry 1 }

sunNimDiscriminatorProbableCause OBJECT-TYPE
    SYNTAX          SunNimProbableCause
    MAX-ACCESS      not-accessible
    STATUS          current
    DESCRIPTION     
            "An optional probable cause which provides additional information
             relevant to this notification as per ITU-T M.3100 sec. 10.2."
    ::= { sunNimDiscriminatorEntry 2 }

sunNimDiscriminatorTDomain OBJECT-TYPE
    SYNTAX          TDomain
    MAX-ACCESS      not-accessible
    STATUS          current
    DESCRIPTION     
            "Indicates the kind of transport service by which
             notifications are sent.
             
             Possible values for this object are presently found in the
             Transport Mappings for SNMPv2 document (RFC1906)."
    ::= { sunNimDiscriminatorEntry 3 }

sunNimDiscriminatorTAddress OBJECT-TYPE
    SYNTAX          TAddress
    MAX-ACCESS      not-accessible
    STATUS          current
    DESCRIPTION     
            "The transport service address to which notifications are sent,
             formatted according to the corresponding value of entLogicalTDomain.
             
             For snmpUDPDomain, a TAddress is 6 octets long, the initial
             4 octets containing the IP-address in network-byte order and
             the last 2 containing the UDP port in network-byte order.
             Consult 'Transport Mappings for Version 2 of the Simple
             Network Management Protocol' (RFC1906) for
             further information on snmpUDPDomain.
             
             A value of 0.0.0.0:0, in a TDomain of snmpUDPDomain, is used to
             specify that the destination is the log."
    ::= { sunNimDiscriminatorEntry 4 }

sunNimLowestForwardedSeverity OBJECT-TYPE
    SYNTAX          SunNimAlarmPerceivedSeverity
    MAX-ACCESS      read-create
    STATUS          current
    DESCRIPTION     
            "The lowest severity of traps of this type that should be
             sent to this address.
             
             This object has significance only if the trap type
             specified has a severity associated with it."
    DEFVAL          { minor }
    ::= { sunNimDiscriminatorEntry 5 }

sunNimForwardIndeterminate OBJECT-TYPE
    SYNTAX          TruthValue
    MAX-ACCESS      read-create
    STATUS          current
    DESCRIPTION     
            "When this object has the value TRUE, traps with
             indeterminate severity will be forwarded to the
             specified destination.
             
             This object has significance only if the trap type
             specified has a severity associated with it."
    DEFVAL          { false }
    ::= { sunNimDiscriminatorEntry 6 }

sunNimDiscriminatorRowStatus OBJECT-TYPE
    SYNTAX          RowStatus
    MAX-ACCESS      read-create
    STATUS          current
    DESCRIPTION     
            "This object is used to create a new row or to delete
             an existing row in the table."
    ::= { sunNimDiscriminatorEntry 7 }

sunNimLogTable OBJECT-TYPE
    SYNTAX          SEQUENCE OF SunNimLogEntry
    MAX-ACCESS      not-accessible
    STATUS          current
    DESCRIPTION     
            "The NIM log table.
             
             This table defines the trap logs currently maintained
             by the agent as per X.721, sec. 6.6.
             
             It is also used to maintain a currentProblemList for each managed
             object as per M.3100, sec. 5.22.
             
             The management system creates entries in this table to
             specify which types of traps, from which managed object, 
             should be logged.
             
             Deleting an entry in this table deletes all entries in
             the corresponding log.
             
             There are separate logs for each notification type/managed object."
    ::= { sunNimMIBObjects 11 }

sunNimLogEntry OBJECT-TYPE
    SYNTAX          SunNimLogEntry
    MAX-ACCESS      not-accessible
    STATUS          current
    DESCRIPTION     
            "Information about a single trap log as defined in X.735 8.1.1."
    INDEX           { sunNimLogType }
    ::= { sunNimLogTable 1 }

SunNimLogEntry ::=
    SEQUENCE {
        sunNimLogType                   OBJECT IDENTIFIER,
        sunNimLogAdministrativeState    SunNimLogAdministrativeState,
        sunNimLogOperationalState       SunNimOperationalState,
        sunNimLogFullStatus             TruthValue,
        sunNimLogFullAction             SunNimLogFullAction,
        sunNimLogCapacityThreshold      SunNimPercentage,
        sunNimLogSeverityProfileIndex   Integer32,
        sunNimLogRowStatus              RowStatus
    }

sunNimLogType OBJECT-TYPE
    SYNTAX          OBJECT IDENTIFIER
    MAX-ACCESS      not-accessible
    STATUS          current
    DESCRIPTION     
            "The type of notifications stored in this log.
             
             For trap logs, the sunNimLogType is set to the type of
             notification stored in the log. This will be one of the
             notifications defined in the sunNimMIBTrapPrefix group.
             
             For currentProblemList alarm entries, the sunNimLogType is set to 
             the sunNimLogRecordManagedObjectInstance OID value."
    ::= { sunNimLogEntry 1 }

sunNimLogAdministrativeState OBJECT-TYPE
    SYNTAX          SunNimLogAdministrativeState
    MAX-ACCESS      read-create
    STATUS          current
    DESCRIPTION     
            "The management system uses this object to stop and
             start the operations of this object as per X.735, sec. 8.1.1.1.3."
    DEFVAL          { unlocked }
    ::= { sunNimLogEntry 2 }

sunNimLogOperationalState OBJECT-TYPE
    SYNTAX          SunNimOperationalState
    MAX-ACCESS      read-only
    STATUS          current
    DESCRIPTION     
            "Indicates whether or not the log is capable of
             performing its normal operations as per X.735, sec. 8.1.1.1.4."
    ::= { sunNimLogEntry 3 }

sunNimLogFullStatus OBJECT-TYPE
    SYNTAX          TruthValue
    MAX-ACCESS      read-only
    STATUS          current
    DESCRIPTION     
            "If the log is full, this attribute is true."
    ::= { sunNimLogEntry 4 }

sunNimLogFullAction OBJECT-TYPE
    SYNTAX          SunNimLogFullAction
    MAX-ACCESS      read-create
    STATUS          current
    DESCRIPTION     
            "Indicates the action that should be performed when no
             more log entries can be created due to a log-full
             condition.  If the value of this object is wrap(2),
             each new log entry will cause the deletion of the oldest
             entry still in the log, for as long as the log is still
             full.
             
             This operation is described in X.735, sec. 8.1.1.5."
    DEFVAL          { wrap }
    ::= { sunNimLogEntry 5 }

sunNimLogCapacityThreshold OBJECT-TYPE
    SYNTAX          SunNimPercentage
    MAX-ACCESS      read-create
    STATUS          current
    DESCRIPTION     
            "Indicates the threshold, expressed in %, at which the
             log will generate a capacity alarm as per X.735, sec. 8.1.1.3."
    ::= { sunNimLogEntry 6 }

sunNimLogSeverityProfileIndex OBJECT-TYPE
    SYNTAX          Integer32
    MAX-ACCESS      read-create
    STATUS          current
    DESCRIPTION     
            "Specifies the index of the entry in the alarm severity profile
             table that should be used.  The default value of this object is zero.
             
             This allows the creation or deletion of a log to generate a
             notification and also provides for the generation of capacity alarms."
    ::= { sunNimLogEntry 7 }

sunNimLogRowStatus OBJECT-TYPE
    SYNTAX          RowStatus
    MAX-ACCESS      read-create
    STATUS          current
    DESCRIPTION     
            "This object is used to create a new row or to delete
             an existing row in the table."
    ::= { sunNimLogEntry 8 }

sunNimLogRecordTable OBJECT-TYPE
    SYNTAX          SEQUENCE OF SunNimLogRecordEntry
    MAX-ACCESS      not-accessible
    STATUS          current
    DESCRIPTION     
            "The NIM log record table.
             
             This table is used to maintain the traps logged for a given
             notification type as per X.721, sec. 6.5.
             
             It is also used to maintain a currentProblemList for each managed
             object as per M.3100, sec. 5.22."
    ::= { sunNimMIBObjects 12 }

sunNimLogRecordEntry OBJECT-TYPE
    SYNTAX          SunNimLogRecordEntry
    MAX-ACCESS      not-accessible
    STATUS          current
    DESCRIPTION     
            "Information about a single notification associated either with
             a log, or, in the case of a currentProblemList entry, a specific 
             managed object.
             
             Entries in this table are created automatically but
             can be deleted by the management system.
             
             currentProblemList entries are augmented by the 
             sunNimLogRecordAdditionalEntry and sunNimLogRecordAlarmEntry tables.
             They are automatically deleted when the associated alarm condition 
             is cleared.
             
             Entries that represent object creation/deletion alarm log types
             are augmented by the sunNimLogRecordAdditionalEntry table.
             
             Entries that represent alarm log types are also augmented
             by the sunNimLogRecordAlarmEntry table.
             
             Entries that represent attribute/state change log types are augmented
             by the sunNimLogRecordChangeEntry table."
    INDEX           { sunNimLogType, sunNimLogRecordId }
    ::= { sunNimLogRecordTable 1 }

SunNimLogRecordEntry ::=
    SEQUENCE {
        sunNimLogRecordId               Unsigned32,
        sunNimLogRecordLoggingTime      DateAndTime,
        sunNimLogRecordManagedObjectInstance    RowPointer,
        sunNimLogRecordRowStatus        RowStatus
    }

sunNimLogRecordId OBJECT-TYPE
    SYNTAX          Unsigned32
    MAX-ACCESS      not-accessible
    STATUS          current
    DESCRIPTION     
            "A unique number identifying this event as per X.735, sec. 8.1.2.2.1."
    ::= { sunNimLogRecordEntry 1 }

sunNimLogRecordLoggingTime OBJECT-TYPE
    SYNTAX          DateAndTime
    MAX-ACCESS      read-only
    STATUS          current
    DESCRIPTION     
            "The time at which this trap was logged as per X.735, sec. 8.1.2.2.2."
    ::= { sunNimLogRecordEntry 2 }

sunNimLogRecordManagedObjectInstance OBJECT-TYPE
    SYNTAX          RowPointer
    MAX-ACCESS      read-only
    STATUS          current
    DESCRIPTION     
            "The object to which this entry applies as defined in X.721,
             sec. 10.7.4.13.
             
             By convention, this is the name of the first object in
             the row in the table referenced."
    ::= { sunNimLogRecordEntry 3 }

sunNimLogRecordRowStatus OBJECT-TYPE
    SYNTAX          RowStatus
    MAX-ACCESS      read-write
    STATUS          current
    DESCRIPTION     
            "This object is used to delete an existing row in the
             table. Note that the only value to which a management
             system can set this object is destroy(6)."
    ::= { sunNimLogRecordEntry 4 }

sunNimLogRecordAdditionalTable OBJECT-TYPE
    SYNTAX          SEQUENCE OF SunNimLogRecordAdditionalEntry
    MAX-ACCESS      not-accessible
    STATUS          current
    DESCRIPTION     
            "The NIM Trap Agent additional information table.
             
             This table is used to maintain extra information for
             logged notifications that represent alarm or object creation/deletion
             types as per X.721, sec. 6.
             
             It is also used to maintain a currentProblemList for each managed
             object as per M.3100, sec. 5.22."
    ::= { sunNimMIBObjects 13 }

sunNimLogRecordAdditionalEntry OBJECT-TYPE
    SYNTAX          SunNimLogRecordAdditionalEntry
    MAX-ACCESS      not-accessible
    STATUS          current
    DESCRIPTION     
            "Information text/OID providing further information relating to
             alarm and object creation/deletion log records."
    INDEX           { sunNimLogType, sunNimLogRecordId }
    ::= { sunNimLogRecordAdditionalTable 1 }

SunNimLogRecordAdditionalEntry ::=
    SEQUENCE {
        sunNimLogRecordAdditionalInfo   OBJECT IDENTIFIER,
        sunNimLogRecordAdditionalText   SnmpAdminString
    }

sunNimLogRecordAdditionalInfo OBJECT-TYPE
    SYNTAX          OBJECT IDENTIFIER
    MAX-ACCESS      read-only
    STATUS          current
    DESCRIPTION     
            "An optional OID of an object which provides additional
             information relevant to this notification as per X.733,
             sec. 8.1.2.14.
             
             This object is only present if it was included in the
             notification corresponding to this log entry."
    ::= { sunNimLogRecordAdditionalEntry 1 }

sunNimLogRecordAdditionalText OBJECT-TYPE
    SYNTAX          SnmpAdminString
    MAX-ACCESS      read-only
    STATUS          current
    DESCRIPTION     
            "An optional textual description which provides additional
             information relevant to this notification as per X.733,
             sec. 8.1.2.13.
             
             This object is only present if it was included in the
             notification corresponding to this log entry."
    ::= { sunNimLogRecordAdditionalEntry 2 }

sunNimLogRecordAlarmTable OBJECT-TYPE
    SYNTAX          SEQUENCE OF SunNimLogRecordAlarmEntry
    MAX-ACCESS      not-accessible
    STATUS          current
    DESCRIPTION     
            "The NIM Trap Agent logged alarm trap table.
             
             This table is used to maintain extra information for
             log records that represent alarm types as per X.721, sec. 6.1.
             
             It is also used to maintain a currentProblemList for each managed
             object as per M.3100, sec. 5.22."
    ::= { sunNimMIBObjects 14 }

sunNimLogRecordAlarmEntry OBJECT-TYPE
    SYNTAX          SunNimLogRecordAlarmEntry
    MAX-ACCESS      not-accessible
    STATUS          current
    DESCRIPTION     
            "Information about the alarm-specific attributes of
             a single trap in the log."
    INDEX           { sunNimLogType, sunNimLogRecordId }
    ::= { sunNimLogRecordAlarmTable 1 }

SunNimLogRecordAlarmEntry ::=
    SEQUENCE {
        sunNimLogRecordAlarmPerceivedSeverity     SunNimAlarmPerceivedSeverity,
        sunNimLogRecordAlarmProbableCause SunNimProbableCause,
        sunNimLogRecordAlarmSpecificProblem   SnmpAdminString,
        sunNimLogRecordAlarmRepairAction TruthValue
    }

sunNimLogRecordAlarmPerceivedSeverity OBJECT-TYPE
    SYNTAX          SunNimAlarmPerceivedSeverity
    MAX-ACCESS      read-only
    STATUS          current
    DESCRIPTION     
            "The perceived severity of the alarm, as specified by
             the agent that generated it in accordance with X.733,
             sec. 8.1.2.3.
             
             In the case of logged traps, this attribute will be set to
             critical(2) when the associated alarm condition is cleared."
    ::= { sunNimLogRecordAlarmEntry 1 }

sunNimLogRecordAlarmProbableCause OBJECT-TYPE
    SYNTAX          SunNimProbableCause
    MAX-ACCESS      read-only
    STATUS          current
    DESCRIPTION     
            "An optional probable cause which provides additional information
             relevant to this notification as per ITU-T M.3100 sec. 10.2."
    ::= { sunNimLogRecordAlarmEntry 2 }

sunNimLogRecordAlarmSpecificProblem OBJECT-TYPE
    SYNTAX          SnmpAdminString
    MAX-ACCESS      read-only
    STATUS          current
    DESCRIPTION     
            "Indicates further refinements to the problem identified
             by the alarm type corresponding to X.733, sec. 8.1.2.2. If more
             than one specific problem is described in this object, the
             problem descriptions are separated by newline characters.
             
             This object is only present if it was included in the
             alarm trap corresponding to this log entry."
    ::= { sunNimLogRecordAlarmEntry 3 }

sunNimLogRecordAlarmRepairAction OBJECT-TYPE
    SYNTAX          TruthValue
    MAX-ACCESS      read-only
    STATUS          current
    DESCRIPTION     
            "This is set to true if this notification requires repair action
             as per X.733, sec. 8.1.2.12."
    ::= { sunNimLogRecordAlarmEntry 4 }

sunNimLogRecordChangeTable OBJECT-TYPE
    SYNTAX          SEQUENCE OF SunNimLogRecordChangeEntry
    MAX-ACCESS      not-accessible
    STATUS          current
    DESCRIPTION     
            "The NIM Trap Agent logged change trap table.
             This table is used to maintain extra information for
             log records that represent attribute or state changes as per X.721,
             sec. 6.2."
    ::= { sunNimMIBObjects 15 }

sunNimLogRecordChangeEntry OBJECT-TYPE
    SYNTAX          SunNimLogRecordChangeEntry
    MAX-ACCESS      not-accessible
    STATUS          current
    DESCRIPTION     
            "Information about the attribute/state change specific
             attributes of a single trap in the log.
             
             Each of the fields will be present according to the type
             of the attribute changed. State changes will be indicated
             using the sunNimLogRecordChangeNewInteger and
             sunNimLogRecordChangeOldInteger objects."
    INDEX           { sunNimLogType, sunNimLogRecordId }
    ::= { sunNimLogRecordChangeTable 1 }

SunNimLogRecordChangeEntry ::=
    SEQUENCE {
        sunNimLogRecordChangeChangedOID OBJECT IDENTIFIER,
        sunNimLogRecordChangeNewInteger Integer32,
        sunNimLogRecordChangeOldInteger Integer32,
        sunNimLogRecordChangeNewString  SnmpAdminString,
        sunNimLogRecordChangeOldString  SnmpAdminString,
        sunNimLogRecordChangeNewOID     OBJECT IDENTIFIER,
        sunNimLogRecordChangeOldOID     OBJECT IDENTIFIER
    }

sunNimLogRecordChangeChangedOID OBJECT-TYPE
    SYNTAX          OBJECT IDENTIFIER
    MAX-ACCESS      read-only
    STATUS          current
    DESCRIPTION     
            "The changed object's OBJECT IDENTIFIER value in an
             attribute/state change notification."
    ::= { sunNimLogRecordChangeEntry 1 }

sunNimLogRecordChangeNewInteger OBJECT-TYPE
    SYNTAX          Integer32
    MAX-ACCESS      read-only
    STATUS          current
    DESCRIPTION     
            "The new INTEGER value in an attribute/state change notification."
    ::= { sunNimLogRecordChangeEntry 2 }

sunNimLogRecordChangeOldInteger OBJECT-TYPE
    SYNTAX          Integer32
    MAX-ACCESS      read-only
    STATUS          current
    DESCRIPTION     
            "The old INTEGER value in an attribute/state change notification."
    ::= { sunNimLogRecordChangeEntry 3 }

sunNimLogRecordChangeNewString OBJECT-TYPE
    SYNTAX          SnmpAdminString
    MAX-ACCESS      read-only
    STATUS          current
    DESCRIPTION     
            "The new SnmpAdminString value in an attribute change
             notification."
    ::= { sunNimLogRecordChangeEntry 4 }

sunNimLogRecordChangeOldString OBJECT-TYPE
    SYNTAX          SnmpAdminString
    MAX-ACCESS      read-only
    STATUS          current
    DESCRIPTION     
            "The old SnmpAdminString value in an attribute change
             notification."
    ::= { sunNimLogRecordChangeEntry 5 }

sunNimLogRecordChangeNewOID OBJECT-TYPE
    SYNTAX          OBJECT IDENTIFIER
    MAX-ACCESS      read-only
    STATUS          current
    DESCRIPTION     
            "The new OBJECT IDENTIFIER value in an attribute change
             notification."
    ::= { sunNimLogRecordChangeEntry 6 }

sunNimLogRecordChangeOldOID OBJECT-TYPE
    SYNTAX          OBJECT IDENTIFIER
    MAX-ACCESS      read-only
    STATUS          current
    DESCRIPTION     
            "The old OBJECT IDENTIFIER value in an attribute change
             notification."
    ::= { sunNimLogRecordChangeEntry 7 }

sunNimMIBTraps OBJECT IDENTIFIER
    ::= { sunNimMIB 2 }

sunNimMIBTrapPrefix OBJECT IDENTIFIER
    ::= { sunNimMIBTraps 0 }

sunNimMIBTrapData OBJECT IDENTIFIER
    ::= { sunNimMIBTraps 1 }

sunNimNotificationEventId OBJECT-TYPE
    SYNTAX          Integer32
    MAX-ACCESS      accessible-for-notify
    STATUS          current
    DESCRIPTION     
            "A unique ID for this notification."
    ::= { sunNimMIBTrapData 1 }

sunNimNotificationTime OBJECT-TYPE
    SYNTAX          DateAndTime
    MAX-ACCESS      accessible-for-notify
    STATUS          current
    DESCRIPTION     
            "The time that this notification was generated."
    ::= { sunNimMIBTrapData 2 }

sunNimNotificationObject OBJECT-TYPE
    SYNTAX          RowPointer
    MAX-ACCESS      accessible-for-notify
    STATUS          current
    DESCRIPTION     
            "The object to which this notification applies.
             By convention, this is the name of the first object in
             the row in the table referenced."
    ::= { sunNimMIBTrapData 3 }

sunNimNotificationPerceivedSeverity OBJECT-TYPE
    SYNTAX          SunNimAlarmPerceivedSeverity
    MAX-ACCESS      accessible-for-notify
    STATUS          current
    DESCRIPTION     
            "The perceived severity of the alarm, as specified by
             the agent that generated it in accordance with X.733,
             sec. 8.1.2.3."
    ::= { sunNimMIBTrapData 4 }

sunNimNotificationProbableCause OBJECT-TYPE
    SYNTAX          SunNimProbableCause
    MAX-ACCESS      accessible-for-notify
    STATUS          current
    DESCRIPTION     
            "An optional probable cause which provides additional information
             relevant to this notification as per ITU-T M.3100 sec. 10.2."
    ::= { sunNimMIBTrapData 5 }

sunNimNotificationSpecificProblem OBJECT-TYPE
    SYNTAX          SnmpAdminString
    MAX-ACCESS      accessible-for-notify
    STATUS          current
    DESCRIPTION     
            "An optional textual description which provides additional
             information concerning the cause of this notification."
    ::= { sunNimMIBTrapData 6 }

sunNimNotificationRepairAction OBJECT-TYPE
    SYNTAX          TruthValue
    MAX-ACCESS      accessible-for-notify
    STATUS          current
    DESCRIPTION     
            "This is set to true if this notification requires repair action."
    ::= { sunNimMIBTrapData 7 }

sunNimNotificationAdditionalInfo OBJECT-TYPE
    SYNTAX          OBJECT IDENTIFIER
    MAX-ACCESS      accessible-for-notify
    STATUS          current
    DESCRIPTION     
            "An optional OID of an object which provides additional
             information relevant to this notification."
    ::= { sunNimMIBTrapData 8 }

sunNimNotificationAdditionalText OBJECT-TYPE
    SYNTAX          SnmpAdminString
    MAX-ACCESS      accessible-for-notify
    STATUS          current
    DESCRIPTION     
            "An optional textual description which provides additional
             information relevant to this notification."
    ::= { sunNimMIBTrapData 9 }

sunNimNotificationChangedOID OBJECT-TYPE
    SYNTAX          OBJECT IDENTIFIER
    MAX-ACCESS      accessible-for-notify
    STATUS          current
    DESCRIPTION     
            "The changed object's OBJECT IDENTIFIER value in an
             attribute/state change notification."
    ::= { sunNimMIBTrapData 10 }

sunNimNotificationNewInteger OBJECT-TYPE
    SYNTAX          Integer32
    MAX-ACCESS      accessible-for-notify
    STATUS          current
    DESCRIPTION     
            "The new INTEGER value in an attribute/state change notification."
    ::= { sunNimMIBTrapData 11 }

sunNimNotificationOldInteger OBJECT-TYPE
    SYNTAX          Integer32
    MAX-ACCESS      accessible-for-notify
    STATUS          current
    DESCRIPTION     
            "The old INTEGER value in an attribute/state change notification."
    ::= { sunNimMIBTrapData 12 }

sunNimNotificationNewString OBJECT-TYPE
    SYNTAX          SnmpAdminString
    MAX-ACCESS      accessible-for-notify
    STATUS          current
    DESCRIPTION     
            "The new SnmpAdminString value in an attribute change
             notification."
    ::= { sunNimMIBTrapData 13 }

sunNimNotificationOldString OBJECT-TYPE
    SYNTAX          SnmpAdminString
    MAX-ACCESS      accessible-for-notify
    STATUS          current
    DESCRIPTION     
            "The old SnmpAdminString value in an attribute change
             notification."
    ::= { sunNimMIBTrapData 14 }

sunNimNotificationNewOID OBJECT-TYPE
    SYNTAX          OBJECT IDENTIFIER
    MAX-ACCESS      accessible-for-notify
    STATUS          current
    DESCRIPTION     
            "The new OBJECT IDENTIFIER value in an attribute change
             notification."
    ::= { sunNimMIBTrapData 15 }

sunNimNotificationOldOID OBJECT-TYPE
    SYNTAX          OBJECT IDENTIFIER
    MAX-ACCESS      accessible-for-notify
    STATUS          current
    DESCRIPTION     
            "The old OBJECT IDENTIFIER value in an attribute change
             notification."
    ::= { sunNimMIBTrapData 16 }

sunNimObjectCreation NOTIFICATION-TYPE
    OBJECTS         { sunNimNotificationEventId, sunNimNotificationTime, 
                      sunNimNotificationObject, 
                      sunNimNotificationAdditionalInfo, 
                      sunNimNotificationAdditionalText }
    STATUS          current
    DESCRIPTION     
            "Indicates that an object, indicated by sunNimNotificationObject,
             has been created as defined in X.721, sec. 13.6."
    ::= { sunNimMIBTrapPrefix 1 }

sunNimObjectDeletion NOTIFICATION-TYPE
    OBJECTS         { sunNimNotificationEventId, sunNimNotificationTime, 
                      sunNimNotificationObject, 
                      sunNimNotificationAdditionalInfo, 
                      sunNimNotificationAdditionalText }
    STATUS          current
    DESCRIPTION     
            "Indicates that an object, indicated by sunNimNotificationObject,
             has been deleted as defined in X.721, sec. 13.7."
    ::= { sunNimMIBTrapPrefix 2 }

sunNimCommunicationsAlarm NOTIFICATION-TYPE
    OBJECTS         { sunNimNotificationEventId, sunNimNotificationTime, 
                      sunNimNotificationObject, 
                      sunNimNotificationAdditionalInfo, 
                      sunNimNotificationAdditionalText, 
                      sunNimNotificationPerceivedSeverity, 
                      sunNimNotificationProbableCause, 
                      sunNimNotificationSpecificProblem, 
                      sunNimNotificationRepairAction }
    STATUS          current
    DESCRIPTION     
            "Indicates that a communication alarm has occurred as defined
             in X.721, sec. 13.2."
    ::= { sunNimMIBTrapPrefix 3 }

sunNimEnvironmentalAlarm NOTIFICATION-TYPE
    OBJECTS         { sunNimNotificationEventId, sunNimNotificationTime, 
                      sunNimNotificationObject, 
                      sunNimNotificationAdditionalInfo, 
                      sunNimNotificationAdditionalText, 
                      sunNimNotificationPerceivedSeverity, 
                      sunNimNotificationProbableCause, 
                      sunNimNotificationSpecificProblem, 
                      sunNimNotificationRepairAction }
    STATUS          current
    DESCRIPTION     
            "Indicates that an environment alarm has occurred as defined
             in X.721, sec. 13.3."
    ::= { sunNimMIBTrapPrefix 4 }

sunNimEquipmentAlarm NOTIFICATION-TYPE
    OBJECTS         { sunNimNotificationEventId, sunNimNotificationTime, 
                      sunNimNotificationObject, 
                      sunNimNotificationAdditionalInfo, 
                      sunNimNotificationAdditionalText, 
                      sunNimNotificationPerceivedSeverity, 
                      sunNimNotificationProbableCause, 
                      sunNimNotificationSpecificProblem, 
                      sunNimNotificationRepairAction }
    STATUS          current
    DESCRIPTION     
            "Indicates that an equipment alarm has occurred as defined
             in X.721, sec. 13.4."
    ::= { sunNimMIBTrapPrefix 5 }

sunNimProcessingErrorAlarm NOTIFICATION-TYPE
    OBJECTS         { sunNimNotificationEventId, sunNimNotificationTime, 
                      sunNimNotificationObject, 
                      sunNimNotificationAdditionalInfo, 
                      sunNimNotificationAdditionalText, 
                      sunNimNotificationPerceivedSeverity, 
                      sunNimNotificationProbableCause, 
                      sunNimNotificationSpecificProblem, 
                      sunNimNotificationRepairAction }
    STATUS          current
    DESCRIPTION     
            "Indicates that a processing error alarm has occurred as defined
             in X.721, sec. 13.10."
    ::= { sunNimMIBTrapPrefix 6 }

sunNimStateChange NOTIFICATION-TYPE
    OBJECTS         { sunNimNotificationEventId, sunNimNotificationTime, 
                      sunNimNotificationObject, 
                      sunNimNotificationChangedOID, 
                      sunNimNotificationOldInteger, 
                      sunNimNotificationNewInteger }
    STATUS          current
    DESCRIPTION     
            "Indicates that a state change has occurred on the state attribute
             identified by sunNimNotificationChangedOID. As states are
             enumerations of type INTEGER, the old and new states are passed in
             sunNimNotificationOldInteger and sunNimNotificationNewInteger
             respectively.
             
             This is as defined in X.721, sec. 13.14."
    ::= { sunNimMIBTrapPrefix 7 }

sunNimAttributeChangeInteger NOTIFICATION-TYPE
    OBJECTS         { sunNimNotificationEventId, sunNimNotificationTime, 
                      sunNimNotificationObject, 
                      sunNimNotificationChangedOID, 
                      sunNimNotificationOldInteger, 
                      sunNimNotificationNewInteger }
    STATUS          current
    DESCRIPTION     
            "Indicates that attribute identified by sunNimNotificationChangedOID
             has changed from the value in sunNimNotificationOldInteger to the
             value in sunNimNotificationNewInteger.
             
             This is as defined in X.721, sec. 13.1."
    ::= { sunNimMIBTrapPrefix 8 }

sunNimAttributeChangeString NOTIFICATION-TYPE
    OBJECTS         { sunNimNotificationEventId, sunNimNotificationTime, 
                      sunNimNotificationObject, 
                      sunNimNotificationChangedOID, 
                      sunNimNotificationOldString, 
                      sunNimNotificationNewString }
    STATUS          current
    DESCRIPTION     
            "Indicates that attribute identified by sunNimNotificationChangedOID
             has changed from the value in sunNimNotificationOldString to the
             value in sunNimNotificationNewString.
             
             This is as defined in X.721, sec. 13.1."
    ::= { sunNimMIBTrapPrefix 9 }

sunNimAttributeChangeOID NOTIFICATION-TYPE
    OBJECTS         { sunNimNotificationEventId, sunNimNotificationTime, 
                      sunNimNotificationObject, 
                      sunNimNotificationChangedOID, 
                      sunNimNotificationOldOID, sunNimNotificationNewOID }
    STATUS          current
    DESCRIPTION     
            "Indicates that attribute identified by sunNimNotificationChangedOID
             has changed from the value in sunNimNotificationOldOID to the
             value in sunNimNotificationNewOID.
             
             This is as defined in X.721, sec. 13.1."
    ::= { sunNimMIBTrapPrefix 10 }

END -- end of module SUN-NET-INFO-MIB.
