--
-- This SMIv2 module has been generated by smidump 0.2-cvs. Do not edit.
--

CTRON-SSR-SMI-MIB DEFINITIONS ::= BEGIN

IMPORTS
    cabletron
        FROM CTRON-OIDS
    MODULE-IDENTITY, OBJECT-IDENTITY
        FROM SNMPv2-SMI;

ssr MODULE-IDENTITY
    LAST-UPDATED    "200006270000Z"
    ORGANIZATION    
            "Cabletron Systems, Inc"
    CONTACT-INFO    
            "Riverstone Networks, Inc
             5200 Great America Parkway
             Santa Clara, CA 95054
             (408) 878-6500
             nms-eng@riverstonenet.com
             http://www.riverstonenet.com"
    DESCRIPTION     
            "This mib module defines enterprise MIBs under Cabletron
             enterprise OID that manage Enterasys SmartSwitch Routers 
             and Riverstone Networks RS product Line."
    REVISION        "200006270000Z"
    DESCRIPTION     
            "Update contact information for Riverstone Networks as this mib
             is found on the Riverstione RS product line and Enterasys SSR product line."
    ::= { cabletron 2501 }


ssrMibs OBJECT-IDENTITY
    STATUS          current
    DESCRIPTION     
            "All Smart Switch Router (SSR) enterprise MIBs are defined under mibs"
    ::= { ssr 1 }

ssrTraps OBJECT-IDENTITY
    STATUS          current
    DESCRIPTION     
            "All enterprise traps are defined under this branch."
    ::= { ssr 10 }

END -- end of module CTRON-SSR-SMI-MIB.
