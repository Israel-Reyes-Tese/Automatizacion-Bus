--
-- This SMIv2 module has been generated by smidump 0.2-cvs. Do not edit.
--

SONUS-TRANSPORT-RESOURCES-MIB DEFINITIONS ::= BEGIN

IMPORTS
    Ipv6Address
        FROM IPV6-TC
    Counter32, Counter64, Integer32, IpAddress, MODULE-IDENTITY, 
    NOTIFICATION-TYPE, OBJECT-TYPE, Unsigned32
        FROM SNMPv2-SMI
    RowStatus
        FROM SNMPv2-TC
    sonusEventClass, sonusEventDescription, sonusEventLevel, 
    sonusEventTime, sonusSequenceId
        FROM SONUS-COMMON-MIB
    sonusResourcesMIBs
        FROM SONUS-SMI
    SonusName, SonusShelfIndex, SonusSlotIndex
        FROM SONUS-TC;

sonusTransportResourcesMIB MODULE-IDENTITY
    LAST-UPDATED    "201404270000Z"
    ORGANIZATION    
            "Sonus Networks, Inc."
    CONTACT-INFO    
            "   Customer Support    
             Sonus Networks, Inc.
             7 Technology Park Drive
             Westford, MA 01886
             USA
             
             Tel: 978-614-8100
             Fax: 978-614-8609"
    DESCRIPTION     
            "The MIB Module for Transport Reources Management."
    ::= { sonusResourcesMIBs 4 }


sonusTransportResourcesMIBObjects OBJECT IDENTIFIER
    ::= { sonusTransportResourcesMIB 1 }

sonusNifStatTable OBJECT-TYPE
    SYNTAX          SEQUENCE OF SonusNifStatEntry
    MAX-ACCESS      not-accessible
    STATUS          current
    DESCRIPTION     
            "This table contains status information about each NIF"
    ::= { sonusTransportResourcesMIBObjects 1 }

sonusNifStatEntry OBJECT-TYPE
    SYNTAX          SonusNifStatEntry
    MAX-ACCESS      not-accessible
    STATUS          current
    DESCRIPTION     
            "This table describes the NIF status"
    INDEX           { sonusNifStatNifIndex }
    ::= { sonusNifStatTable 1 }

SonusNifStatEntry ::=
    SEQUENCE {
        sonusNifStatNifIndex            Integer32,
        sonusNifStatState               INTEGER,
        sonusNifStatCallNum             Integer32,
        sonusNifStatResNum              Integer32,
        sonusNifStatSpeedCur            Integer32,
        sonusNifStatSpeedMax            Integer32,
        sonusNifStatSpeedActual         Integer32,
        sonusNifStatSpeedDeviation      Integer32,
        sonusNifStatSpeedLoad           Integer32
    }

sonusNifStatNifIndex OBJECT-TYPE
    SYNTAX          Integer32
    MAX-ACCESS      read-only
    STATUS          current
    DESCRIPTION     
            "Nif's ifIndex that identifies the NIF"
    ::= { sonusNifStatEntry 1 }

sonusNifStatState OBJECT-TYPE
    SYNTAX          INTEGER { outOfService(1), inService(2), dryUp(3), 
                        force(4), notApplicable(5) }
    MAX-ACCESS      read-only
    STATUS          current
    DESCRIPTION     
            "The state of this NIF"
    ::= { sonusNifStatEntry 2 }

sonusNifStatCallNum OBJECT-TYPE
    SYNTAX          Integer32
    MAX-ACCESS      read-only
    STATUS          current
    DESCRIPTION     
            "The number of calls on this NIF"
    ::= { sonusNifStatEntry 3 }

sonusNifStatResNum OBJECT-TYPE
    SYNTAX          Integer32
    MAX-ACCESS      read-only
    STATUS          current
    DESCRIPTION     
            "The number of xres allocated on this NIF"
    ::= { sonusNifStatEntry 4 }

sonusNifStatSpeedCur OBJECT-TYPE
    SYNTAX          Integer32
    MAX-ACCESS      read-only
    STATUS          current
    DESCRIPTION     
            "The current speed(bandwidth) allocated on this NIF"
    ::= { sonusNifStatEntry 5 }

sonusNifStatSpeedMax OBJECT-TYPE
    SYNTAX          Integer32
    MAX-ACCESS      read-only
    STATUS          current
    DESCRIPTION     
            "The maximum speed allowed on this NIF"
    ::= { sonusNifStatEntry 6 }

sonusNifStatSpeedActual OBJECT-TYPE
    SYNTAX          Integer32
    MAX-ACCESS      read-only
    STATUS          current
    DESCRIPTION     
            "The actual speed(bandwidth) on this NIF"
    ::= { sonusNifStatEntry 7 }

sonusNifStatSpeedDeviation OBJECT-TYPE
    SYNTAX          Integer32
    MAX-ACCESS      read-only
    STATUS          current
    DESCRIPTION     
            "The actual speed(bandwidth) deviation on this NIF"
    ::= { sonusNifStatEntry 8 }

sonusNifStatSpeedLoad OBJECT-TYPE
    SYNTAX          Integer32
    MAX-ACCESS      read-only
    STATUS          current
    DESCRIPTION     
            "The current allocated (not actual) load on this NIF"
    ::= { sonusNifStatEntry 9 }

sonusPnsAdmnTable OBJECT-TYPE
    SYNTAX          SEQUENCE OF SonusPnsAdmnEntry
    MAX-ACCESS      not-accessible
    STATUS          current
    DESCRIPTION     
            "This table contains admin information about each PNS"
    ::= { sonusTransportResourcesMIBObjects 2 }

sonusPnsAdmnEntry OBJECT-TYPE
    SYNTAX          SonusPnsAdmnEntry
    MAX-ACCESS      not-accessible
    STATUS          current
    DESCRIPTION     
            "This table describes the PNS admin objects"
    INDEX           { sonusPnsAdmnShelf, sonusPnsAdmnSlot }
    ::= { sonusPnsAdmnTable 1 }

SonusPnsAdmnEntry ::=
    SEQUENCE {
        sonusPnsAdmnShelf               SonusShelfIndex,
        sonusPnsAdmnSlot                SonusSlotIndex,
        sonusPnsAdmnReservedUdpPorts    Integer32,
        sonusPnsAdmnRowStatus           RowStatus
    }

sonusPnsAdmnShelf OBJECT-TYPE
    SYNTAX          SonusShelfIndex
    MAX-ACCESS      read-only
    STATUS          current
    DESCRIPTION     
            "A 32-bit integer identifying the shelf of the PNS"
    ::= { sonusPnsAdmnEntry 1 }

sonusPnsAdmnSlot OBJECT-TYPE
    SYNTAX          SonusSlotIndex
    MAX-ACCESS      read-only
    STATUS          current
    DESCRIPTION     
            "A 32-bit integer identifying the slot of the PNS"
    ::= { sonusPnsAdmnEntry 2 }

sonusPnsAdmnReservedUdpPorts OBJECT-TYPE
    SYNTAX          Integer32 (1..65535)
    MAX-ACCESS      read-write
    STATUS          current
    DESCRIPTION     
            "The number UDP ports on this PNS are reserved for IPDC or MGSG usage"
    DEFVAL          { 5120 }
    ::= { sonusPnsAdmnEntry 3 }

sonusPnsAdmnRowStatus OBJECT-TYPE
    SYNTAX          RowStatus
    MAX-ACCESS      read-write
    STATUS          current
    DESCRIPTION     
            ""
    ::= { sonusPnsAdmnEntry 4 }

sonusRtpPortBaseObject OBJECT IDENTIFIER
    ::= { sonusTransportResourcesMIBObjects 3 }

sonusRtpPortBase OBJECT-TYPE
    SYNTAX          Integer32 (1..65535)
    MAX-ACCESS      read-write
    STATUS          current
    DESCRIPTION     
            "The RTP port base shall be used for IP calls. The default is set to 5000. User
             can only specify an even value and in the range from 5000 to 17000.
             Port numbers starting from 40000 and beyond are used for system sockets. 12k is the 
             maximum lookup entries supported by PNS40. Each entry uses two consecutive ports"
    DEFVAL          { 5000 }
    ::= { sonusRtpPortBaseObject 1 }

sonusSubInterfaceStatTable OBJECT-TYPE
    SYNTAX          SEQUENCE OF SonusSubInterfaceStatEntry
    MAX-ACCESS      not-accessible
    STATUS          current
    DESCRIPTION     
            "The collection of sub-interfaces status"
    ::= { sonusTransportResourcesMIBObjects 4 }

sonusSubInterfaceStatEntry OBJECT-TYPE
    SYNTAX          SonusSubInterfaceStatEntry
    MAX-ACCESS      not-accessible
    STATUS          current
    DESCRIPTION     
            ""
    INDEX           { sonusSubInterfaceStatIfIndex }
    ::= { sonusSubInterfaceStatTable 1 }

SonusSubInterfaceStatEntry ::=
    SEQUENCE {
        sonusSubInterfaceStatIfIndex    Integer32,
        sonusSubInterfaceStatState      INTEGER,
        sonusSubInterfaceStatCallNum    Integer32,
        sonusSubInterfaceStatSpeedCur   Integer32,
        sonusSubInterfaceStatSpeedMax   Integer32,
        sonusSubInterfaceStatSpeedActual Integer32,
        sonusSubInterfaceStatSpeedDeviation   Integer32,
        sonusSubInterfaceStatSpeedLoad  Integer32
    }

sonusSubInterfaceStatIfIndex OBJECT-TYPE
    SYNTAX          Integer32
    MAX-ACCESS      read-only
    STATUS          current
    DESCRIPTION     
            "The ifindex to identify the sub-interface"
    ::= { sonusSubInterfaceStatEntry 1 }

sonusSubInterfaceStatState OBJECT-TYPE
    SYNTAX          INTEGER { outOfService(1), inService(2), dryUp(3), 
                        force(4), notApplicable(5) }
    MAX-ACCESS      read-only
    STATUS          current
    DESCRIPTION     
            "The state of the sub-interface."
    ::= { sonusSubInterfaceStatEntry 2 }

sonusSubInterfaceStatCallNum OBJECT-TYPE
    SYNTAX          Integer32
    MAX-ACCESS      read-only
    STATUS          current
    DESCRIPTION     
            "The number of calls on this sub-interface."
    ::= { sonusSubInterfaceStatEntry 3 }

sonusSubInterfaceStatSpeedCur OBJECT-TYPE
    SYNTAX          Integer32
    MAX-ACCESS      read-only
    STATUS          current
    DESCRIPTION     
            "The current speed allocated on the sub-interface"
    ::= { sonusSubInterfaceStatEntry 4 }

sonusSubInterfaceStatSpeedMax OBJECT-TYPE
    SYNTAX          Integer32
    MAX-ACCESS      read-only
    STATUS          current
    DESCRIPTION     
            "The maximum speed allowed on this SIF"
    ::= { sonusSubInterfaceStatEntry 5 }

sonusSubInterfaceStatSpeedActual OBJECT-TYPE
    SYNTAX          Integer32
    MAX-ACCESS      read-only
    STATUS          current
    DESCRIPTION     
            "The actual speed(bandwidth) on this SIF"
    ::= { sonusSubInterfaceStatEntry 6 }

sonusSubInterfaceStatSpeedDeviation OBJECT-TYPE
    SYNTAX          Integer32
    MAX-ACCESS      read-only
    STATUS          current
    DESCRIPTION     
            "The actual speed(bandwidth) deviation on this SIF"
    ::= { sonusSubInterfaceStatEntry 7 }

sonusSubInterfaceStatSpeedLoad OBJECT-TYPE
    SYNTAX          Integer32
    MAX-ACCESS      read-only
    STATUS          current
    DESCRIPTION     
            "The current allocated (not actual) load on this SIF"
    ::= { sonusSubInterfaceStatEntry 8 }

sonusPolicer OBJECT IDENTIFIER
    ::= { sonusTransportResourcesMIBObjects 5 }

sonusPolicerNextIndex OBJECT-TYPE
    SYNTAX          Integer32
    MAX-ACCESS      read-only
    STATUS          current
    DESCRIPTION     
            "The next valid index to use when creating an entry in
             the sonusPolicerTable."
    ::= { sonusPolicer 1 }

sonusPolicerTable OBJECT-TYPE
    SYNTAX          SEQUENCE OF SonusPolicerEntry
    MAX-ACCESS      not-accessible
    STATUS          current
    DESCRIPTION     
            "The collection of DOS white/black list policers."
    ::= { sonusPolicer 2 }

sonusPolicerEntry OBJECT-TYPE
    SYNTAX          SonusPolicerEntry
    MAX-ACCESS      not-accessible
    STATUS          current
    DESCRIPTION     
            "The collection of DOS white/black list policers."
    INDEX           { sonusPolicerIndex }
    ::= { sonusPolicerTable 1 }

SonusPolicerEntry ::=
    SEQUENCE {
        sonusPolicerIndex               Unsigned32,
        sonusPolicerName                SonusName,
        sonusPolicerType                INTEGER,
        sonusPolicerIfIndex             Integer32,
        sonusPolicerSrcIpAddress        IpAddress,
        sonusPolicerBucketSize          Integer32,
        sonusPolicerFillRate            Integer32,
        sonusPolicerAdmnState           INTEGER,
        sonusPolicerRowStatus           RowStatus,
        sonusPolicerShelf               SonusShelfIndex,
        sonusPolicerSlot                SonusSlotIndex,
        sonusPolicerSrcIp6Address       Ipv6Address,
        sonusPolicerSrcIpVer            INTEGER,
        sonusPolicerSrcIpMask           IpAddress,
        sonusPolicerSrcIpPrefixLength   Integer32
    }

sonusPolicerIndex OBJECT-TYPE
    SYNTAX          Unsigned32
    MAX-ACCESS      read-only
    STATUS          current
    DESCRIPTION     
            "The unique per server assigned index when it was created."
    ::= { sonusPolicerEntry 1 }

sonusPolicerName OBJECT-TYPE
    SYNTAX          SonusName
    MAX-ACCESS      read-write
    STATUS          current
    DESCRIPTION     
            "The administrative name of the policer."
    ::= { sonusPolicerEntry 2 }

sonusPolicerType OBJECT-TYPE
    SYNTAX          INTEGER { white(1), black(2) }
    MAX-ACCESS      read-write
    STATUS          current
    DESCRIPTION     
            "The policer type."
    ::= { sonusPolicerEntry 3 }

sonusPolicerIfIndex OBJECT-TYPE
    SYNTAX          Integer32
    MAX-ACCESS      read-write
    STATUS          current
    DESCRIPTION     
            "The ifIndex of the specified interface, NIF or SIF."
    ::= { sonusPolicerEntry 4 }

sonusPolicerSrcIpAddress OBJECT-TYPE
    SYNTAX          IpAddress
    MAX-ACCESS      read-write
    STATUS          current
    DESCRIPTION     
            "The source IPv4 address to be policed."
    ::= { sonusPolicerEntry 5 }

sonusPolicerBucketSize OBJECT-TYPE
    SYNTAX          Integer32 (2048..65520)
    MAX-ACCESS      read-write
    STATUS          current
    DESCRIPTION     
            "The maximum number of credits(in bytes). N/A for black policers"
    DEFVAL          { 2048 }
    ::= { sonusPolicerEntry 6 }

sonusPolicerFillRate OBJECT-TYPE
    SYNTAX          Integer32 (512..16777215)
    MAX-ACCESS      read-write
    STATUS          current
    DESCRIPTION     
            "The rate at which credits are restored to bucket(in bytes/sec)
             N/A for black policers"
    DEFVAL          { 512 }
    ::= { sonusPolicerEntry 7 }

sonusPolicerAdmnState OBJECT-TYPE
    SYNTAX          INTEGER { disabled(1), enabled(2) }
    MAX-ACCESS      read-write
    STATUS          current
    DESCRIPTION     
            "Administrative state of the policer."
    DEFVAL          { disabled }
    ::= { sonusPolicerEntry 8 }

sonusPolicerRowStatus OBJECT-TYPE
    SYNTAX          RowStatus
    MAX-ACCESS      read-write
    STATUS          current
    DESCRIPTION     
            ""
    ::= { sonusPolicerEntry 9 }

sonusPolicerShelf OBJECT-TYPE
    SYNTAX          SonusShelfIndex
    MAX-ACCESS      read-write
    STATUS          current
    DESCRIPTION     
            "The shelf index of this policer."
    ::= { sonusPolicerEntry 10 }

sonusPolicerSlot OBJECT-TYPE
    SYNTAX          SonusSlotIndex
    MAX-ACCESS      read-write
    STATUS          current
    DESCRIPTION     
            "The slot index of this policer."
    ::= { sonusPolicerEntry 11 }

sonusPolicerSrcIp6Address OBJECT-TYPE
    SYNTAX          Ipv6Address
    MAX-ACCESS      read-write
    STATUS          current
    DESCRIPTION     
            "IPv6 Address source address. "
    ::= { sonusPolicerEntry 12 }

sonusPolicerSrcIpVer OBJECT-TYPE
    SYNTAX          INTEGER { afInet(2), afInet6(24) }
    MAX-ACCESS      read-only
    STATUS          current
    DESCRIPTION     
            "IP Address Type"
    ::= { sonusPolicerEntry 13 }

sonusPolicerSrcIpMask OBJECT-TYPE
    SYNTAX          IpAddress
    MAX-ACCESS      read-write
    STATUS          current
    DESCRIPTION     
            "The subnet mask for the source IPv4 addresses to be policed."
    ::= { sonusPolicerEntry 14 }

sonusPolicerSrcIpPrefixLength OBJECT-TYPE
    SYNTAX          Integer32
    MAX-ACCESS      read-write
    STATUS          current
    DESCRIPTION     
            "The Prefix Length for the source IPv6 addresses to be policed."
    ::= { sonusPolicerEntry 15 }

sonusPolicerStatTable OBJECT-TYPE
    SYNTAX          SEQUENCE OF SonusPolicerStatEntry
    MAX-ACCESS      not-accessible
    STATUS          current
    DESCRIPTION     
            "The collection of DOS while/black list policer status."
    ::= { sonusTransportResourcesMIBObjects 6 }

sonusPolicerStatEntry OBJECT-TYPE
    SYNTAX          SonusPolicerStatEntry
    MAX-ACCESS      not-accessible
    STATUS          current
    DESCRIPTION     
            "The collection of DOS while/black list policer status."
    INDEX           { sonusPolicerStatIndex }
    ::= { sonusPolicerStatTable 1 }

SonusPolicerStatEntry ::=
    SEQUENCE {
        sonusPolicerStatIndex           Unsigned32,
        sonusPolicerStatIfIndex         Integer32,
        sonusPolicerStatSrcIpAddress    IpAddress,
        sonusPolicerStatNpId            Integer32,
        sonusPolicerStatTotalPkts       Integer32,
        sonusPolicerStatTotalDiscards   Integer32,
        sonusPolicerStatShelf           SonusShelfIndex,
        sonusPolicerStatSlot            SonusSlotIndex,
        sonusPolicerStatSrcIp6Address   Ipv6Address,
        sonusPolicerStatSrcIpVer        INTEGER,
        sonusPolicerStatSrcIpMask       IpAddress,
        sonusPolicerStatSrcIpPrefixLength Integer32
    }

sonusPolicerStatIndex OBJECT-TYPE
    SYNTAX          Unsigned32
    MAX-ACCESS      read-only
    STATUS          current
    DESCRIPTION     
            "The unique per server assigned index when it was created."
    ::= { sonusPolicerStatEntry 1 }

sonusPolicerStatIfIndex OBJECT-TYPE
    SYNTAX          Integer32
    MAX-ACCESS      read-only
    STATUS          current
    DESCRIPTION     
            "The ifIndex of the specified interface, NIF or SIF."
    ::= { sonusPolicerStatEntry 2 }

sonusPolicerStatSrcIpAddress OBJECT-TYPE
    SYNTAX          IpAddress
    MAX-ACCESS      read-only
    STATUS          current
    DESCRIPTION     
            "The source IPv4 address to be policed."
    ::= { sonusPolicerStatEntry 3 }

sonusPolicerStatNpId OBJECT-TYPE
    SYNTAX          Integer32
    MAX-ACCESS      read-only
    STATUS          current
    DESCRIPTION     
            "The physical NP policer ID."
    ::= { sonusPolicerStatEntry 4 }

sonusPolicerStatTotalPkts OBJECT-TYPE
    SYNTAX          Integer32
    MAX-ACCESS      read-only
    STATUS          current
    DESCRIPTION     
            "The total packets received"
    ::= { sonusPolicerStatEntry 5 }

sonusPolicerStatTotalDiscards OBJECT-TYPE
    SYNTAX          Integer32
    MAX-ACCESS      read-only
    STATUS          current
    DESCRIPTION     
            "The total packets discarded."
    ::= { sonusPolicerStatEntry 6 }

sonusPolicerStatShelf OBJECT-TYPE
    SYNTAX          SonusShelfIndex
    MAX-ACCESS      read-only
    STATUS          current
    DESCRIPTION     
            "The shelf index."
    ::= { sonusPolicerStatEntry 7 }

sonusPolicerStatSlot OBJECT-TYPE
    SYNTAX          SonusSlotIndex
    MAX-ACCESS      read-only
    STATUS          current
    DESCRIPTION     
            "The slot index."
    ::= { sonusPolicerStatEntry 8 }

sonusPolicerStatSrcIp6Address OBJECT-TYPE
    SYNTAX          Ipv6Address
    MAX-ACCESS      read-write
    STATUS          current
    DESCRIPTION     
            "IPv6 Address source address. "
    ::= { sonusPolicerStatEntry 9 }

sonusPolicerStatSrcIpVer OBJECT-TYPE
    SYNTAX          INTEGER { afInet(2), afInet6(24) }
    MAX-ACCESS      read-only
    STATUS          current
    DESCRIPTION     
            "IP Address Type"
    ::= { sonusPolicerStatEntry 10 }

sonusPolicerStatSrcIpMask OBJECT-TYPE
    SYNTAX          IpAddress
    MAX-ACCESS      read-only
    STATUS          current
    DESCRIPTION     
            "The mask for IPv4 addresses to be policed."
    ::= { sonusPolicerStatEntry 11 }

sonusPolicerStatSrcIpPrefixLength OBJECT-TYPE
    SYNTAX          Integer32
    MAX-ACCESS      read-write
    STATUS          current
    DESCRIPTION     
            "The prefix length for IPv6 addresses to be policed."
    ::= { sonusPolicerStatEntry 12 }

sonusNodePolicerAdminTable OBJECT-TYPE
    SYNTAX          SEQUENCE OF SonusNodePolicerAdminEntry
    MAX-ACCESS      not-accessible
    STATUS          current
    DESCRIPTION     
            "This table contains per shelf node specific policer
             configuration."
    ::= { sonusTransportResourcesMIBObjects 7 }

sonusNodePolicerAdminEntry OBJECT-TYPE
    SYNTAX          SonusNodePolicerAdminEntry
    MAX-ACCESS      not-accessible
    STATUS          current
    DESCRIPTION     
            "This table contains per shelf node specific policer
             configuration."
    INDEX           { sonusNodePolicerAdminShelf }
    ::= { sonusNodePolicerAdminTable 1 }

SonusNodePolicerAdminEntry ::=
    SEQUENCE {
        sonusNodePolicerAdminShelf      SonusShelfIndex,
        sonusNodePolicerAdminState      INTEGER,
        sonusNodePolicerRogueMediaGracePeriod     Integer32,
        sonusNodePolicerSetThreshold    Integer32,
        sonusNodePolicerClearThreshold  Integer32,
        sonusNodePolicerAdminRowStatus  RowStatus,
        sonusNodePolicerLGPBucketSize   Integer32,
        sonusNodePolicerLGPFillRate     Integer32
    }

sonusNodePolicerAdminShelf OBJECT-TYPE
    SYNTAX          SonusShelfIndex
    MAX-ACCESS      read-write
    STATUS          current
    DESCRIPTION     
            "A 32-bit integer identifying the shelf"
    ::= { sonusNodePolicerAdminEntry 1 }

sonusNodePolicerAdminState OBJECT-TYPE
    SYNTAX          INTEGER { disabled(1), enabled(2) }
    MAX-ACCESS      read-write
    STATUS          current
    DESCRIPTION     
            "Administrative state of the node specific policer."
    DEFVAL          { enabled }
    ::= { sonusNodePolicerAdminEntry 2 }

sonusNodePolicerRogueMediaGracePeriod OBJECT-TYPE
    SYNTAX          Integer32 (0..16)
    MAX-ACCESS      read-write
    STATUS          current
    DESCRIPTION     
            "duration after which a port is deactivated that received RTP is
             ignore. RTP received after this period is considered rogue media
             on an unallocated port."
    DEFVAL          { 6 }
    ::= { sonusNodePolicerAdminEntry 3 }

sonusNodePolicerSetThreshold OBJECT-TYPE
    SYNTAX          Integer32 (1..100)
    MAX-ACCESS      read-write
    STATUS          current
    DESCRIPTION     
            "percentage of policer utilization which would set the policer
             resource utilization alarm."
    DEFVAL          { 90 }
    ::= { sonusNodePolicerAdminEntry 4 }

sonusNodePolicerClearThreshold OBJECT-TYPE
    SYNTAX          Integer32 (1..100)
    MAX-ACCESS      read-write
    STATUS          current
    DESCRIPTION     
            "percentage of policer utilization which would clear the policer
             resource utilization alarm."
    DEFVAL          { 75 }
    ::= { sonusNodePolicerAdminEntry 5 }

sonusNodePolicerAdminRowStatus OBJECT-TYPE
    SYNTAX          RowStatus
    MAX-ACCESS      read-write
    STATUS          current
    DESCRIPTION     
            ""
    ::= { sonusNodePolicerAdminEntry 6 }

sonusNodePolicerLGPBucketSize OBJECT-TYPE
    SYNTAX          Integer32 (0..31)
    MAX-ACCESS      read-write
    STATUS          current
    DESCRIPTION     
            "The system wide light gray policer bucket size, in packets,
             used to policing packets matching a light gray entry.
             The range is 0 to 31 packets."
    DEFVAL          { 15 }
    ::= { sonusNodePolicerAdminEntry 7 }

sonusNodePolicerLGPFillRate OBJECT-TYPE
    SYNTAX          Integer32 (0..400)
    MAX-ACCESS      read-write
    STATUS          current
    DESCRIPTION     
            "The system wide light gray policer fill rate in 
             packets per 10 seconds.  The configurable fill rate is
             0, 1, 2, 5, 10, 25, 50, 100, 200, 400 packets/10 seconds."
    DEFVAL          { 20 }
    ::= { sonusNodePolicerAdminEntry 8 }

sonusDBLProfileObj OBJECT IDENTIFIER
    ::= { sonusTransportResourcesMIBObjects 8 }

sonusDBLProfileNextIndex OBJECT-TYPE
    SYNTAX          Integer32
    MAX-ACCESS      read-only
    STATUS          current
    DESCRIPTION     
            "The next valid index to use when creating an entry in
             the sonusDBLProfileTable."
    ::= { sonusDBLProfileObj 1 }

sonusDBLProfileTable OBJECT-TYPE
    SYNTAX          SEQUENCE OF SonusDBLProfileEntry
    MAX-ACCESS      not-accessible
    STATUS          current
    DESCRIPTION     
            "The collection of DBL policers."
    ::= { sonusDBLProfileObj 2 }

sonusDBLProfileEntry OBJECT-TYPE
    SYNTAX          SonusDBLProfileEntry
    MAX-ACCESS      not-accessible
    STATUS          current
    DESCRIPTION     
            "The collection of DBL policer profiles"
    INDEX           { sonusDBLProfileIndex }
    ::= { sonusDBLProfileTable 1 }

SonusDBLProfileEntry ::=
    SEQUENCE {
        sonusDBLProfileIndex            Unsigned32,
        sonusDBLProfileName             SonusName,
        sonusDBLProfileRowStatus        RowStatus,
        sonusDBLProfileApplicationType  INTEGER
    }

sonusDBLProfileIndex OBJECT-TYPE
    SYNTAX          Unsigned32 (1..10)
    MAX-ACCESS      read-only
    STATUS          current
    DESCRIPTION     
            "The unique assigned index when it was created."
    ::= { sonusDBLProfileEntry 1 }

sonusDBLProfileName OBJECT-TYPE
    SYNTAX          SonusName
    MAX-ACCESS      read-write
    STATUS          current
    DESCRIPTION     
            "The administrative name of the DBL profile."
    ::= { sonusDBLProfileEntry 2 }

sonusDBLProfileRowStatus OBJECT-TYPE
    SYNTAX          RowStatus
    MAX-ACCESS      read-write
    STATUS          current
    DESCRIPTION     
            "RowStatus of the current row of the table."
    ::= { sonusDBLProfileEntry 3 }

sonusDBLProfileApplicationType OBJECT-TYPE
    SYNTAX          INTEGER { sip(1) }
    MAX-ACCESS      read-write
    STATUS          current
    DESCRIPTION     
            "The unique assigned index when it was created."
    ::= { sonusDBLProfileEntry 4 }

sonusDBLRuleObj OBJECT IDENTIFIER
    ::= { sonusTransportResourcesMIBObjects 9 }

sonusDBLRuleTable OBJECT-TYPE
    SYNTAX          SEQUENCE OF SonusDBLRuleEntry
    MAX-ACCESS      not-accessible
    STATUS          current
    DESCRIPTION     
            "The collection of DBL Rules."
    ::= { sonusDBLRuleObj 1 }

sonusDBLRuleEntry OBJECT-TYPE
    SYNTAX          SonusDBLRuleEntry
    MAX-ACCESS      not-accessible
    STATUS          current
    DESCRIPTION     
            "The defintion of a DBL rule."
    INDEX           { sonusDBLRuleProfileIndex, sonusDBLRuleIndex }
    ::= { sonusDBLRuleTable 1 }

SonusDBLRuleEntry ::=
    SEQUENCE {
        sonusDBLRuleProfileIndex        Unsigned32,
        sonusDBLRuleIndex               Unsigned32,
        sonusDBLRuleEventType           INTEGER,
        sonusDBLRuleActionType          INTEGER,
        sonusDBLRuleActionDBLExcludeWhiteState      INTEGER,
        sonusDBLRuleEventPerDayThreshold Unsigned32,
        sonusDBLRuleActionEffectivePeriod Unsigned32,
        sonusDBLRuleRowStatus           RowStatus
    }

sonusDBLRuleProfileIndex OBJECT-TYPE
    SYNTAX          Unsigned32 (1..10)
    MAX-ACCESS      read-only
    STATUS          current
    DESCRIPTION     
            "The index of the parent profile for this rule."
    ::= { sonusDBLRuleEntry 1 }

sonusDBLRuleIndex OBJECT-TYPE
    SYNTAX          Unsigned32 (1..2)
    MAX-ACCESS      read-only
    STATUS          current
    DESCRIPTION     
            "Identifies the DBL rule within a DBL profile."
    ::= { sonusDBLRuleEntry 2 }

sonusDBLRuleEventType OBJECT-TYPE
    SYNTAX          INTEGER { sipRegistFailure(1), badSipMessage(2), 
                        sipEpCacAggrRej(3) }
    MAX-ACCESS      read-write
    STATUS          current
    DESCRIPTION     
            "The DBL rule event type."
    ::= { sonusDBLRuleEntry 3 }

sonusDBLRuleActionType OBJECT-TYPE
    SYNTAX          INTEGER { watch(1), blacklist(2) }
    MAX-ACCESS      read-write
    STATUS          current
    DESCRIPTION     
            "The action to take when a specified event meets the criteria for this rule."
    ::= { sonusDBLRuleEntry 4 }

sonusDBLRuleActionDBLExcludeWhiteState OBJECT-TYPE
    SYNTAX          INTEGER { disabled(1), enabled(2) }
    MAX-ACCESS      read-write
    STATUS          current
    DESCRIPTION     
            "The behavior whether to DBL an entry when the entry is in static white list.
             When enabled, entry will not be in the DBL list if it is already in white list.
             When disabled, entry will be in the DBL list regardless whether it's in whitelist or not."
    DEFVAL          { disabled }
    ::= { sonusDBLRuleEntry 5 }

sonusDBLRuleEventPerDayThreshold OBJECT-TYPE
    SYNTAX          Unsigned32 (0..86400)
    MAX-ACCESS      read-write
    STATUS          current
    DESCRIPTION     
            "The number of events per day which is used as fillrate of token bucket policer. Value 0 means zero tolerance, the DBL agent takes action immediately if gets an event."
    DEFVAL          { 0 }
    ::= { sonusDBLRuleEntry 6 }

sonusDBLRuleActionEffectivePeriod OBJECT-TYPE
    SYNTAX          Unsigned32 (60..86400)
    MAX-ACCESS      read-write
    STATUS          current
    DESCRIPTION     
            "The DBL action enforcement period (in seconds) the DBL policer entry remains effective."
    DEFVAL          { 60 }
    ::= { sonusDBLRuleEntry 7 }

sonusDBLRuleRowStatus OBJECT-TYPE
    SYNTAX          RowStatus
    MAX-ACCESS      read-write
    STATUS          current
    DESCRIPTION     
            "The Row Status of this entry used by SNMP only."
    ::= { sonusDBLRuleEntry 8 }

sonusDBLEndpointStatTable OBJECT-TYPE
    SYNTAX          SEQUENCE OF SonusDBLEndpointStatEntry
    MAX-ACCESS      not-accessible
    STATUS          current
    DESCRIPTION     
            "The collection of DBL list endpoint policer status."
    ::= { sonusTransportResourcesMIBObjects 10 }

sonusDBLEndpointStatEntry OBJECT-TYPE
    SYNTAX          SonusDBLEndpointStatEntry
    MAX-ACCESS      not-accessible
    STATUS          current
    DESCRIPTION     
            "The collection of DBL list policer status."
    INDEX           { sonusDBLEndpointStatIfIndex, 
                      sonusDBLEndpointStatSrcIpAddress, 
                      sonusDBLEndpointStatSrcIp6Address, 
                      sonusDBLEndpointStatSrcIpVer }
    ::= { sonusDBLEndpointStatTable 1 }

SonusDBLEndpointStatEntry ::=
    SEQUENCE {
        sonusDBLEndpointStatIfIndex     Unsigned32,
        sonusDBLEndpointStatSrcIpAddress IpAddress,
        sonusDBLEndpointStatTriggerRule Unsigned32,
        sonusDBLEndpointStatApplicationType   Unsigned32,
        sonusDBLEndpointStatApplicationIndex    Unsigned32,
        sonusDBLEndpointStatSlot        SonusSlotIndex,
        sonusDBLEndpointStatCurrentDBLState   INTEGER,
        sonusDBLEndpointStatRemainEffectivePeriod         Unsigned32,
        sonusDBLEndpointStatDiscardPacketCnt    Counter32,
        sonusDBLEndpointStatAction      INTEGER,
        sonusDBLEndpointStatTriggerEvent INTEGER,
        sonusDBLEndpointStatSrcIp6Address Ipv6Address,
        sonusDBLEndpointStatSrcIpVer    INTEGER
    }

sonusDBLEndpointStatIfIndex OBJECT-TYPE
    SYNTAX          Unsigned32 (1..65535)
    MAX-ACCESS      not-accessible
    STATUS          current
    DESCRIPTION     
            "The LIF ifIndex of the ingress NIF or SIF where the DBL is created"
    ::= { sonusDBLEndpointStatEntry 1 }

sonusDBLEndpointStatSrcIpAddress OBJECT-TYPE
    SYNTAX          IpAddress
    MAX-ACCESS      read-only
    STATUS          current
    DESCRIPTION     
            "The source IPv4 address being policed."
    ::= { sonusDBLEndpointStatEntry 2 }

sonusDBLEndpointStatTriggerRule OBJECT-TYPE
    SYNTAX          Unsigned32 (1..2)
    MAX-ACCESS      read-only
    STATUS          current
    DESCRIPTION     
            "The DBL profile rule this entry is created against."
    ::= { sonusDBLEndpointStatEntry 3 }

sonusDBLEndpointStatApplicationType OBJECT-TYPE
    SYNTAX          Unsigned32 (1)
    MAX-ACCESS      read-only
    STATUS          current
    DESCRIPTION     
            "The application type.
             sip(1) "
    ::= { sonusDBLEndpointStatEntry 4 }

sonusDBLEndpointStatApplicationIndex OBJECT-TYPE
    SYNTAX          Unsigned32 (1..2048)
    MAX-ACCESS      read-only
    STATUS          current
    DESCRIPTION     
            "The unique per server assigned application index when it was created."
    ::= { sonusDBLEndpointStatEntry 5 }

sonusDBLEndpointStatSlot OBJECT-TYPE
    SYNTAX          SonusSlotIndex
    MAX-ACCESS      read-only
    STATUS          current
    DESCRIPTION     
            "The slot of the ingress NIF or SIF where the event is detected, and
             where BL would be installed"
    ::= { sonusDBLEndpointStatEntry 6 }

sonusDBLEndpointStatCurrentDBLState OBJECT-TYPE
    SYNTAX          INTEGER { watch(1), blacklist(2), record(3) }
    MAX-ACCESS      read-only
    STATUS          current
    DESCRIPTION     
            "current action pertinent to this policer entry, either endpoint has been
             black listed or it is not (just an entry in DBL data structure.)."
    ::= { sonusDBLEndpointStatEntry 7 }

sonusDBLEndpointStatRemainEffectivePeriod OBJECT-TYPE
    SYNTAX          Unsigned32 (60..86400)
    MAX-ACCESS      read-only
    STATUS          current
    DESCRIPTION     
            "The remaining period of time the DBL policer entry remains effective."
    ::= { sonusDBLEndpointStatEntry 8 }

sonusDBLEndpointStatDiscardPacketCnt OBJECT-TYPE
    SYNTAX          Counter32
    MAX-ACCESS      read-only
    STATUS          current
    DESCRIPTION     
            "The number of packets dropped due to NP black listing of this endpoint."
    ::= { sonusDBLEndpointStatEntry 9 }

sonusDBLEndpointStatAction OBJECT-TYPE
    SYNTAX          INTEGER { unblacklist(1) }
    MAX-ACCESS      read-write
    STATUS          current
    DESCRIPTION     
            "The action to unblacklist the DBL endpoint from XNS."
    ::= { sonusDBLEndpointStatEntry 10 }

sonusDBLEndpointStatTriggerEvent OBJECT-TYPE
    SYNTAX          INTEGER { sipRegistFailure(1), badSipMessage(2), 
                        sipEpCacAggrRej(3) }
    MAX-ACCESS      read-only
    STATUS          current
    DESCRIPTION     
            "The trigger event of this DBL endpoint."
    ::= { sonusDBLEndpointStatEntry 11 }

sonusDBLEndpointStatSrcIp6Address OBJECT-TYPE
    SYNTAX          Ipv6Address
    MAX-ACCESS      read-write
    STATUS          current
    DESCRIPTION     
            "IPv6 Address source address. "
    ::= { sonusDBLEndpointStatEntry 12 }

sonusDBLEndpointStatSrcIpVer OBJECT-TYPE
    SYNTAX          INTEGER { afInet(2), afInet6(24) }
    MAX-ACCESS      read-only
    STATUS          current
    DESCRIPTION     
            "IP Address Type"
    ::= { sonusDBLEndpointStatEntry 13 }

sonusDBLApplicationRuleStatTable OBJECT-TYPE
    SYNTAX          SEQUENCE OF SonusDBLApplicationRuleStatEntry
    MAX-ACCESS      not-accessible
    STATUS          current
    DESCRIPTION     
            "The collection of DBL list policer status."
    ::= { sonusTransportResourcesMIBObjects 11 }

sonusDBLApplicationRuleStatEntry OBJECT-TYPE
    SYNTAX          SonusDBLApplicationRuleStatEntry
    MAX-ACCESS      not-accessible
    STATUS          current
    DESCRIPTION     
            "The collection of DBL list policer status."
    INDEX           { sonusDBLAppRuleStatAppType, 
                      sonusDBLAppRuleStatAppIndex, 
                      sonusDBLAppRuleStatRuleIndex }
    ::= { sonusDBLApplicationRuleStatTable 1 }

SonusDBLApplicationRuleStatEntry ::=
    SEQUENCE {
        sonusDBLAppRuleStatAppType      Unsigned32,
        sonusDBLAppRuleStatAppIndex     Unsigned32,
        sonusDBLAppRuleStatRuleIndex    Unsigned32,
        sonusDBLAppRuleStatCumulativeEnforcements         Counter64,
        sonusDBLAppRuleStatCurrentPolicerEnforcements             Counter32,
        sonusDBLAppRuleStatPreemptedPolicerEnforcements               Counter32
    }

sonusDBLAppRuleStatAppType OBJECT-TYPE
    SYNTAX          Unsigned32 (1)
    MAX-ACCESS      not-accessible
    STATUS          current
    DESCRIPTION     
            "Application type. 
             -- sip (1) "
    ::= { sonusDBLApplicationRuleStatEntry 1 }

sonusDBLAppRuleStatAppIndex OBJECT-TYPE
    SYNTAX          Unsigned32 (1..2048)
    MAX-ACCESS      not-accessible
    STATUS          current
    DESCRIPTION     
            "The unique per server assigned application index when it was created.
             For SIP application type, this index is the same as SIP service group index."
    ::= { sonusDBLApplicationRuleStatEntry 2 }

sonusDBLAppRuleStatRuleIndex OBJECT-TYPE
    SYNTAX          Unsigned32 (1..2)
    MAX-ACCESS      not-accessible
    STATUS          current
    DESCRIPTION     
            "The Index of the DBL profile rule of this entry."
    ::= { sonusDBLApplicationRuleStatEntry 3 }

sonusDBLAppRuleStatCumulativeEnforcements OBJECT-TYPE
    SYNTAX          Counter64
    MAX-ACCESS      read-only
    STATUS          current
    DESCRIPTION     
            "The cumulative DBL policer enforcements during the lifetime of the effective profile/rule."
    ::= { sonusDBLApplicationRuleStatEntry 4 }

sonusDBLAppRuleStatCurrentPolicerEnforcements OBJECT-TYPE
    SYNTAX          Counter32
    MAX-ACCESS      read-only
    STATUS          current
    DESCRIPTION     
            " The current DBL policer enforcements (black list on NP) ."
    ::= { sonusDBLApplicationRuleStatEntry 5 }

sonusDBLAppRuleStatPreemptedPolicerEnforcements OBJECT-TYPE
    SYNTAX          Counter32
    MAX-ACCESS      read-only
    STATUS          current
    DESCRIPTION     
            "The preempted/overridden DBL policer enforcements due to 
             the (endpoint, AC) is already on the white list."
    ::= { sonusDBLApplicationRuleStatEntry 6 }

sonusDBLApplicationPolicerStatTable OBJECT-TYPE
    SYNTAX          SEQUENCE OF SonusDBLApplicationPolicerStatEntry
    MAX-ACCESS      not-accessible
    STATUS          current
    DESCRIPTION     
            "The collection of DBL list policer status."
    ::= { sonusTransportResourcesMIBObjects 12 }

sonusDBLApplicationPolicerStatEntry OBJECT-TYPE
    SYNTAX          SonusDBLApplicationPolicerStatEntry
    MAX-ACCESS      not-accessible
    STATUS          current
    DESCRIPTION     
            "The collection of DBL list policer status."
    INDEX           { sonusDBLAppPolicerStatAppType, 
                      sonusDBLAppPolicerStatAppIndex, 
                      sonusDBLAppPolicerStatSlotIndex, 
                      sonusDBLAppPolicerStatTableIndex, 
                      sonusDBLAppPolicerStatPolicerHashIndex, 
                      sonusDBLAppPolicerStatPolicerSubIndex }
    ::= { sonusDBLApplicationPolicerStatTable 1 }

SonusDBLApplicationPolicerStatEntry ::=
    SEQUENCE {
        sonusDBLAppPolicerStatAppType   Unsigned32,
        sonusDBLAppPolicerStatAppIndex  Unsigned32,
        sonusDBLAppPolicerStatSlotIndex SonusSlotIndex,
        sonusDBLAppPolicerStatTableIndex Unsigned32,
        sonusDBLAppPolicerStatPolicerHashIndex      Unsigned32,
        sonusDBLAppPolicerStatPolicerSubIndex     Unsigned32,
        sonusDBLAppPolicerStatTriggerEvent  INTEGER,
        sonusDBLAppPolicerStatSrcIpAddress  IpAddress,
        sonusDBLAppPolicerStatIfIndex   Unsigned32,
        sonusDBLAppPolicerStatRemainEffectivePeriod           Unsigned32,
        sonusDBLAppPolicerStatNPDiscardCnt  Counter32,
        sonusDBLAppPolicerStatSrcIp6Address   Ipv6Address,
        sonusDBLAppPolicerStatSrcIpVer  INTEGER
    }

sonusDBLAppPolicerStatAppType OBJECT-TYPE
    SYNTAX          Unsigned32 (1)
    MAX-ACCESS      not-accessible
    STATUS          current
    DESCRIPTION     
            "The application type.
             ApplicationType 1 is for SIP."
    ::= { sonusDBLApplicationPolicerStatEntry 1 }

sonusDBLAppPolicerStatAppIndex OBJECT-TYPE
    SYNTAX          Unsigned32 (1..2048)
    MAX-ACCESS      not-accessible
    STATUS          current
    DESCRIPTION     
            "The unique per server assigned application index when it was created.
             For SIP application type, this index is the same as SIP service group index."
    ::= { sonusDBLApplicationPolicerStatEntry 2 }

sonusDBLAppPolicerStatSlotIndex OBJECT-TYPE
    SYNTAX          SonusSlotIndex
    MAX-ACCESS      not-accessible
    STATUS          current
    DESCRIPTION     
            "The slot of the ingress NIF or SIF where the event is detected, and
             where BL would be installed"
    ::= { sonusDBLApplicationPolicerStatEntry 3 }

sonusDBLAppPolicerStatTableIndex OBJECT-TYPE
    SYNTAX          Unsigned32 (1..2)
    MAX-ACCESS      not-accessible
    STATUS          current
    DESCRIPTION     
            "Application specific table index indicating a DBL manager or agent.
             DBL manager and DBL agent maitains different set of policers, 
             and DBL manager and DBL agent may coexists on same server card.
                  - index 1 refers to DBL manager policer table,
                  - index 2 refers to DBL agent policer table"
    ::= { sonusDBLApplicationPolicerStatEntry 4 }

sonusDBLAppPolicerStatPolicerHashIndex OBJECT-TYPE
    SYNTAX          Unsigned32 (1..1024)
    MAX-ACCESS      not-accessible
    STATUS          current
    DESCRIPTION     
            "Application specific hash index of a pociler hash table."
    ::= { sonusDBLApplicationPolicerStatEntry 5 }

sonusDBLAppPolicerStatPolicerSubIndex OBJECT-TYPE
    SYNTAX          Unsigned32 (1..100)
    MAX-ACCESS      not-accessible
    STATUS          current
    DESCRIPTION     
            "Application specific sub-index of the policers of a policer hash table."
    ::= { sonusDBLApplicationPolicerStatEntry 6 }

sonusDBLAppPolicerStatTriggerEvent OBJECT-TYPE
    SYNTAX          INTEGER { sipRegistFailure(1), badSipMessage(2), 
                        sipEpCacAggrRej(3) }
    MAX-ACCESS      read-only
    STATUS          current
    DESCRIPTION     
            "The event type of this policer entry."
    ::= { sonusDBLApplicationPolicerStatEntry 7 }

sonusDBLAppPolicerStatSrcIpAddress OBJECT-TYPE
    SYNTAX          IpAddress
    MAX-ACCESS      read-only
    STATUS          current
    DESCRIPTION     
            "The source IPv4 address being policed."
    ::= { sonusDBLApplicationPolicerStatEntry 8 }

sonusDBLAppPolicerStatIfIndex OBJECT-TYPE
    SYNTAX          Unsigned32 (1..65535)
    MAX-ACCESS      read-only
    STATUS          current
    DESCRIPTION     
            "The LIF ifIndex of the ingress NIF or SIF where the DBL is created"
    ::= { sonusDBLApplicationPolicerStatEntry 9 }

sonusDBLAppPolicerStatRemainEffectivePeriod OBJECT-TYPE
    SYNTAX          Unsigned32 (60..86400)
    MAX-ACCESS      read-only
    STATUS          current
    DESCRIPTION     
            "The remaining period of time the DBL policer entry remains effective."
    ::= { sonusDBLApplicationPolicerStatEntry 10 }

sonusDBLAppPolicerStatNPDiscardCnt OBJECT-TYPE
    SYNTAX          Counter32
    MAX-ACCESS      read-only
    STATUS          current
    DESCRIPTION     
            "The packet discard count by NP policer."
    ::= { sonusDBLApplicationPolicerStatEntry 11 }

sonusDBLAppPolicerStatSrcIp6Address OBJECT-TYPE
    SYNTAX          Ipv6Address
    MAX-ACCESS      read-only
    STATUS          current
    DESCRIPTION     
            "IPv6 Address source address. "
    ::= { sonusDBLApplicationPolicerStatEntry 12 }

sonusDBLAppPolicerStatSrcIpVer OBJECT-TYPE
    SYNTAX          INTEGER { afInet(2), afInet6(24) }
    MAX-ACCESS      read-only
    STATUS          current
    DESCRIPTION     
            "IP Address Type"
    ::= { sonusDBLApplicationPolicerStatEntry 13 }

sonusTransportResourcesMIBNotifications OBJECT IDENTIFIER
    ::= { sonusTransportResourcesMIB 2 }

sonusTransportResourcesMIBNotificationsPrefix OBJECT IDENTIFIER
    ::= { sonusTransportResourcesMIBNotifications 0 }

sonusTransportResourcesMIBNotificationsObjects OBJECT IDENTIFIER
    ::= { sonusTransportResourcesMIBNotifications 1 }

sonusNodePolicerSetThresholdNotification NOTIFICATION-TYPE
    OBJECTS         { sonusPolicerShelf, sonusPolicerSlot, 
                      sonusEventDescription, sonusEventClass, 
                      sonusEventLevel, sonusSequenceId, sonusEventTime }
    STATUS          current
    DESCRIPTION     
            "This trap indicates that node policer set threshold has been reached."
    ::= { sonusTransportResourcesMIBNotificationsPrefix 1 }

sonusNodePolicerClearThresholdNotification NOTIFICATION-TYPE
    OBJECTS         { sonusPolicerShelf, sonusPolicerSlot, 
                      sonusEventDescription, sonusEventClass, 
                      sonusEventLevel, sonusSequenceId, sonusEventTime }
    STATUS          current
    DESCRIPTION     
            "This trap indicates that node policer clear threshold has been reached."
    ::= { sonusTransportResourcesMIBNotificationsPrefix 2 }

sonusDBLNPPoolExhaustNotification NOTIFICATION-TYPE
    OBJECTS         { sonusPolicerShelf, sonusPolicerSlot, 
                      sonusEventDescription, sonusEventClass, 
                      sonusEventLevel, sonusSequenceId, sonusEventTime }
    STATUS          current
    DESCRIPTION     
            "This trap indicates that NP policer pool has run out of resource for DBL"
    ::= { sonusTransportResourcesMIBNotificationsPrefix 3 }

sonusDBLAddPolicerThresholdNotify NOTIFICATION-TYPE
    OBJECTS         { sonusEventDescription, sonusEventClass, 
                      sonusEventLevel, sonusSequenceId, sonusEventTime }
    STATUS          current
    DESCRIPTION     
            "This trap indicates that DBL Threshold set for an endpoint has reached"
    ::= { sonusTransportResourcesMIBNotificationsPrefix 4 }

END -- end of module SONUS-TRANSPORT-RESOURCES-MIB.
