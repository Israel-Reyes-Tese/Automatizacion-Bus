--
-- This SMIv1 module has been generated by smidump 0.2-cvs. Do not edit.
--

RIVERSTONE-STP-MIB DEFINITIONS ::= BEGIN

IMPORTS
    dot1dBasePortEntry
        FROM BRIDGE-MIB
    OBJECT-TYPE
        FROM RFC-1212
    Counter, TimeTicks
        FROM RFC1155-SMI
    riverstoneMibs
        FROM RIVERSTONE-SMI-MIB
    SnmpAdminString
        FROM SNMP-FRAMEWORK-MIB
    TruthValue
        FROM SNMPv2-TC;

rsStpMib OBJECT IDENTIFIER
    ::= { riverstoneMibs 12 }

-- rsStpMib MODULE-IDENTITY
--     LAST-UPDATED    "200007160000Z"
--     ORGANIZATION    
--             "Riverstone Networks, Inc"
--     CONTACT-INFO    
--             "Riverstone Networks, Inc
--              5200 Great America Parkway
--              Santa Clara CA USA 95054
--              PHONE:+1 408.878.6500
--              EMAIL: nms-eng@riverstonenet.com
--              WEB: http://www.riverstonenet.com"
--     DESCRIPTION     
--             "This mib module defines addtional configuration and statistics
--              for Spanning Tree Protocol Management as defined in RFC 1493
--              Copyright (C) Riverstone Networks, Inc 2000"
--     REVISION        "200007090000Z"
--     DESCRIPTION     
--             "Initial version of of RIVERSTONE-STP-MIB."
--     ::= { riverstoneMibs 12 }


RSStpProtocolVersion ::=
    INTEGER { unknown(1), ieee802(2), fastSTP(4) }

-- RSStpProtocolVersion ::= TEXTUAL-CONVENTION
--     STATUS          mandatory
--     DESCRIPTION     
--             "An identifier exists for each type of protocol supported.
--              command variable. Each addtional enumeration should be a
--              power of two."
--     SYNTAX          INTEGER
--                       { unknown(1), ieee802(2), fastSTP(4) }

rsStpGlobals OBJECT IDENTIFIER
    ::= { rsStpMib 1 }

rsStpStatus OBJECT-TYPE
    SYNTAX          TruthValue
    ACCESS          read-write
    STATUS          mandatory
    DESCRIPTION     
            "The global state of spanning tree protocol on this system. Individual ports may 
             be enabled or disabled as necessary or this master switch can be used to turn 
             all ports on or off. This object will cause a loss of convergence when set."
    ::= { rsStpGlobals 1 }

rsStpProtocol OBJECT-TYPE
    SYNTAX          RSStpProtocolVersion
    ACCESS          read-write
    STATUS          mandatory
    DESCRIPTION     
            "Specify the type of Spanning tree to run for the default instance of Spanning Tree. 
             Changing this object has the effect of causing an existing spanning tree to 
             lose convergence. "
    ::= { rsStpGlobals 2 }

rsStpProtocolsSupported OBJECT-TYPE
    SYNTAX          INTEGER
    ACCESS          read-only
    STATUS          mandatory
    DESCRIPTION     
            "Represents range of STP protocols supported. For example the value 6 would
             mean the switch is capable of both fastSTP(4) + ieee802(2) protocols."
    ::= { rsStpGlobals 3 }

rsStpLastSetErrorReason OBJECT-TYPE
    SYNTAX          SnmpAdminString
    ACCESS          read-only
    STATUS          mandatory
    DESCRIPTION     
            "Reports the agent error code and reason for last failure to set any 
             writable object in this mib. Format of the error code is NNN - reason string 
             where NNN is a numeric identifer."
    ::= { rsStpGlobals 4 }

rsStpPortsLevel OBJECT IDENTIFIER
    ::= { rsStpMib 2 }

rsStpLastChanged OBJECT-TYPE
    SYNTAX          TimeTicks
    ACCESS          read-only
    STATUS          mandatory
    DESCRIPTION     
            "The last time any object in this table was changed
             by SNMP or other local management means."
    ::= { rsStpPortsLevel 1 }

rsStpBaseTable OBJECT-TYPE
    SYNTAX          SEQUENCE OF RsStpBaseEntry
    ACCESS          not-accessible
    STATUS          mandatory
    DESCRIPTION     
            "This table provides per port control of spanning tree protocol."
    ::= { rsStpPortsLevel 2 }

rsStpBaseEntry OBJECT-TYPE
    SYNTAX          RsStpBaseEntry
    ACCESS          not-accessible
    STATUS          mandatory
    DESCRIPTION     
            "Additional configuration capabilities not found in standard mibs
             such as configuring STP to run on a given port. 
             All ports shown in dot1dBasePortEntry are  capable of bridging,
             and thus can run STP."
    INDEX           { dot1dBasePort }
--     AUGMENTS        { dot1dBasePortEntry }
    ::= { rsStpBaseTable 1 }

RsStpBaseEntry ::=
    SEQUENCE {
        rsStpBaseEnableProtocol         TruthValue,
        rsStpBaseBlockBpdu              TruthValue,
        rsStpBaseBpduSends              Counter,
        rsStpBaseBpduReceives           Counter
    }

rsStpBaseEnableProtocol OBJECT-TYPE
    SYNTAX          TruthValue
    ACCESS          read-write
    STATUS          mandatory
    DESCRIPTION     
            "Set or get the state of spanning tree 
             protocol (send/receive) on the port."
    ::= { rsStpBaseEntry 1 }

rsStpBaseBlockBpdu OBJECT-TYPE
    SYNTAX          TruthValue
    ACCESS          read-write
    STATUS          mandatory
    DESCRIPTION     
            "Set or get the state of BPDU filtering on this port."
    ::= { rsStpBaseEntry 2 }

rsStpBaseBpduSends OBJECT-TYPE
    SYNTAX          Counter
    ACCESS          read-only
    STATUS          mandatory
    DESCRIPTION     
            "The number of BPDUs sent out on this port."
    ::= { rsStpBaseEntry 3 }

rsStpBaseBpduReceives OBJECT-TYPE
    SYNTAX          Counter
    ACCESS          read-only
    STATUS          mandatory
    DESCRIPTION     
            "The number of BPDUs received on this port."
    ::= { rsStpBaseEntry 4 }

rsStpConformance OBJECT IDENTIFIER
    ::= { rsStpMib 10 }

rsStpGroups OBJECT IDENTIFIER
    ::= { rsStpConformance 1 }

rsStpCompliances OBJECT IDENTIFIER
    ::= { rsStpConformance 2 }

rsStpBaseGroup OBJECT IDENTIFIER
    ::= { rsStpGroups 1 }

-- rsStpBaseGroup OBJECT-GROUP
--     OBJECTS         { rsStpStatus, rsStpLastChanged, 
--                       rsStpBaseEnableProtocol, rsStpBaseBlockBpdu, 
--                       rsStpBaseBpduSends, rsStpBaseBpduReceives, 
--                       rsStpProtocol, rsStpProtocolsSupported, 
--                       rsStpLastSetErrorReason }
--     STATUS          mandatory
--     DESCRIPTION     
--             "A collection of objects providing 
--              configuration and monitoring capabilites of Spanning Tree
--              Protocol on a given switch."
--     ::= { rsStpGroups 1 }

rsStpMibCompliance OBJECT IDENTIFIER
    ::= { rsStpCompliances 1 }

-- rsStpMibCompliance MODULE-COMPLIANCE
--     STATUS          mandatory
--     DESCRIPTION     
--             "The compliance statement for device support of Priority
--              and Multicast Filtering extended bridging services."

--     MODULE          -- -- this module

--         MANDATORY-GROUPS    { rsStpBaseGroup }

--     ::= { rsStpCompliances 1 }

END -- end of module RIVERSTONE-STP-MIB.
