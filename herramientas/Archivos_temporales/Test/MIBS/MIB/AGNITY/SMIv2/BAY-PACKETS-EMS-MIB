--
-- This SMIv2 module has been generated by smidump 0.2-cvs. Do not edit.
--

BAY-PACKETS-EMS-MIB DEFINITIONS ::= BEGIN

IMPORTS
    Counter32, Integer32, MODULE-IDENTITY, NOTIFICATION-TYPE, 
    OBJECT-TYPE, Unsigned32, enterprises
        FROM SNMPv2-SMI
    DisplayString, RowStatus, TEXTUAL-CONVENTION
        FROM SNMPv2-TC;

rsiCommonMib MODULE-IDENTITY
    LAST-UPDATED    "197001010000Z"
    ORGANIZATION    
            "BayPackets, Inc."
    CONTACT-INFO    
            " Technical Support
             Postal: 47266 Benicia Street, 2nd Floor
                     Fremont, CA 94538
             Tel   : +1 510 743 2500
             Fax   : +1 510 743 2505
             E-mail: support@baypackets.com "
    DESCRIPTION     
            "The MIB represents an RSI agent. It enables the
             externalapplication to do SNMP get and set requests:
              1. to start/stop different components
              2. to get/set configurable parameters of components
                 as well as performance parameters
              3. to receive alarms generated by the system (sent as
                 traps)
             
              There are some Oids which are configurable only statically,
              i.e. when the system is stopped.
              These OIDs have two type of values: 
                (a) New and 
                (b) Current 
              The New Value is read-write, and gets read/used by the
              subsystem after a restart.
              The Current Value is read-only, and is the value being
              used by the subsystem currently. i.e., the value of the
              OID set before this subsystem was started.
             
              The oids in subsystem tables are grouped in 5 groups :
              1. performance oids. These set of OIDs are read only 
                 (with values 2xx)
              2. Oids which are configurable statically as well as
                 at run time. These set of OIDs are read-write
                 (with values 3xx)
              3. New value of the Non-Runtime Configurable OIDs 
                 These set of OIDs are read-write 
                 (with values 4xx)
              4. Oids which are not configurable. .These sets of OIDs are
                 read only. 
                 (with values 5xx)
              5. Current value of the Non-Runtime Configurable OIDs 
                 These set of OIDs are read-only 
                 (with values 6xx)"
    ::= { rsiMib 1 }


TimeOfDay ::= TEXTUAL-CONVENTION
    STATUS          current
    DESCRIPTION     
            "A value in the format hh:mm:ss. The time is
             expressed as a 24 hour clock. "
    SYNTAX          DisplayString (SIZE(8))

bayPackets OBJECT IDENTIFIER
    ::= { enterprises 7186 }

bpPrivate OBJECT IDENTIFIER
    ::= { bayPackets 1 }

bpGeneric OBJECT IDENTIFIER
    ::= { bayPackets 2 }

bpPublic OBJECT IDENTIFIER
    ::= { bayPackets 3 }

rsiMib OBJECT IDENTIFIER
    ::= { bpPublic 1 }

rsiComponentTable OBJECT-TYPE
    SYNTAX          SEQUENCE OF RsiComponentEntry
    MAX-ACCESS      not-accessible
    STATUS          current
    DESCRIPTION     
            "This table stores the RSI components. This is the
             master table which contains information about all
             the components. A component is uniquely idenitified
             by a component id. The component type and subtype
             help identify the hierarchy at which the component
             is located. This table contains the generic information
             corresponding to a component. Given the component
             type, the specific table needs to be referred for
             component type specific information. For ex: if the
             component type is 'subsystem' and component sub type
             is 'SLEE', then the 'rsiSubsystem' table needs to 
             be referred for generic subsystem specific details. 
             For detailed SLEE specific details, rsiSlee table
             needs to be referred."
    ::= { rsiCommonMib 2 }

rsiComponentEntry OBJECT-TYPE
    SYNTAX          RsiComponentEntry
    MAX-ACCESS      not-accessible
    STATUS          current
    DESCRIPTION     
            "Description of an RSI component"
    INDEX           { rsiCompId }
    ::= { rsiComponentTable 1 }

RsiComponentEntry ::=
    SEQUENCE {
        rsiCompId                       Integer32,
        rsiCompName                     OCTET STRING,
        rsiCompType                     INTEGER,
        rsiCompSubType                  INTEGER,
        rsiCompChildren                 OCTET STRING,
        rsiCompParent                   Integer32,
        rsiCompHosts                    OCTET STRING,
        rsiCompAdminState               INTEGER,
        rsiCompOperState                INTEGER,
        rsiCompAlarmCount               OCTET STRING,
        rsiCompUsageState               INTEGER
    }

rsiCompId OBJECT-TYPE
    SYNTAX          Integer32
    MAX-ACCESS      read-only
    STATUS          current
    DESCRIPTION     
            "This is the unique id of a component"
    ::= { rsiComponentEntry 1 }

rsiCompName OBJECT-TYPE
    SYNTAX          OCTET STRING
    MAX-ACCESS      read-only
    STATUS          current
    DESCRIPTION     
            "This is the display name of a component,
             and will be unique within its parent structure"
    ::= { rsiComponentEntry 2 }

rsiCompType OBJECT-TYPE
    SYNTAX          INTEGER { domain(0), cluster(1), system(2), 
                        functionalUnitGroup(3), functionalUnit(4), 
                        subsystem(5), subcomponent(7), host(6) }
    MAX-ACCESS      read-only
    STATUS          current
    DESCRIPTION     
            "This is the type of the component"
    ::= { rsiComponentEntry 3 }

rsiCompSubType OBJECT-TYPE
    SYNTAX          INTEGER { noSubtype(0), mediatePlatform(1), 
                        networkServicesPlatform(2), ems(3), reports(4), 
                        callProcessingUnitGroup(5), 
                        applicationUnitGroup(6), 
                        provisioningUnitGroup(7), messageStoreGroup(8), 
                        messagingUnitGroup(9), databaseGroup(10), 
                        mediationUnitGroup(11), adapterUnitGroup(12), 
                        networkResourceGroup(13), mediationUnit(14), 
                        adapterUnit(15), callProcessingUnit(16), 
                        applicationUnit(17), provisioningUnit(18), 
                        messagingUnit(19), databaseUnit(20), 
                        messageStoreUnit(21), ivrUnit(22), 
                        mediatePlatformNetworkResource(23), 
                        networkServicesNetworkResource(24), 
                        bayMediator(25), bayCorrelator(26), 
                        bayNEAdapter(27), bayManager(28), daiAdapter(29), 
                        tibcoAdapter(30), serviceLogicExecutionEnv(31), 
                        serviceProvisioningSubscriptionInterface(32), 
                        callModelManager(33), messagingManager(34), 
                        soapAdapter(35), provider(36), switch(37), 
                        ivr(38), networkElement(39), realTimeAdapter(40), 
                        iPlanet(41), database(42), popUpServer(43), 
                        host(44), 
                        simpleMessagingDeskInterfaceApplication(45), 
                        lecSwitch(46), smpp(47), sipSwitch(48), 
                        directoryServer(49) }
    MAX-ACCESS      read-only
    STATUS          current
    DESCRIPTION     
            "This is the Sub type of the component, i.e., 
             a subsystem can be bayMediator/bayNEAdapter, etc.
             Similarly a Functional Unit can be Call Processing
             Unit (CPU), Application Unit (AU), etc."
    ::= { rsiComponentEntry 4 }

rsiCompChildren OBJECT-TYPE
    SYNTAX          OCTET STRING
    MAX-ACCESS      read-only
    STATUS          current
    DESCRIPTION     
            "This is the list of child components for a given
             component. For ex: for a cluster instance, it
             contains the list of systems in the given cluster.
             This is a comma seperated list, and could have 
             been described as sequence of integers."
    ::= { rsiComponentEntry 5 }

rsiCompParent OBJECT-TYPE
    SYNTAX          Integer32
    MAX-ACCESS      read-only
    STATUS          current
    DESCRIPTION     
            "This is the parent component for a given
             component. For ex: for a cluster instance, this 
             contains the domain which contains this cluster."
    ::= { rsiComponentEntry 6 }

rsiCompHosts OBJECT-TYPE
    SYNTAX          OCTET STRING
    MAX-ACCESS      read-only
    STATUS          current
    DESCRIPTION     
            "This is the list of hosts on which the given  
             component is running. 
             This will be a comma seperated list, and could have 
             been described as sequence of integers."
    ::= { rsiComponentEntry 7 }

rsiCompAdminState OBJECT-TYPE
    SYNTAX          INTEGER { locked(0), unlocked(1), shuttingdown(2), 
                        unknown(3) }
    MAX-ACCESS      read-write
    STATUS          current
    DESCRIPTION     
            "This reflects the intended state of a component. 
             Setting this status to 'down' stops the component and 
             its children. Setting this status to 'up' starts the 
             component and its children. "
    ::= { rsiComponentEntry 8 }

rsiCompOperState OBJECT-TYPE
    SYNTAX          INTEGER { loaded(0), running(1), stopped(2), 
                        partiallyDegraded(3), unknown(4), error(5) }
    MAX-ACCESS      read-only
    STATUS          current
    DESCRIPTION     
            "This reflects the current operational state of a 
             component. "
    ::= { rsiComponentEntry 9 }

rsiCompAlarmCount OBJECT-TYPE
    SYNTAX          OCTET STRING
    MAX-ACCESS      read-only
    STATUS          current
    DESCRIPTION     
            "This is a comma seperated list of alarm counts based
             on their severity. The order of the alarm counts will
             be critical, major, minor, warning, normal.
             This will be a comma seperated list, and can 
             be described as sequence of integers."
    ::= { rsiComponentEntry 10 }

rsiCompUsageState OBJECT-TYPE
    SYNTAX          INTEGER { idle(0), active(1), busy(2) }
    MAX-ACCESS      read-only
    STATUS          current
    DESCRIPTION     
            "This reflects the current usage state of a component. "
    ::= { rsiComponentEntry 11 }

rsiLinkTable OBJECT-TYPE
    SYNTAX          SEQUENCE OF RsiLinkEntry
    MAX-ACCESS      not-accessible
    STATUS          current
    DESCRIPTION     
            "This table stores the link info between RSI components"
    ::= { rsiCommonMib 3 }

rsiLinkEntry OBJECT-TYPE
    SYNTAX          RsiLinkEntry
    MAX-ACCESS      not-accessible
    STATUS          current
    DESCRIPTION     
            "Description of one link between 2 RSI components"
    INDEX           { rsiLinkEndPoint1CompId, rsiLinkEndPoint2CompId }
    ::= { rsiLinkTable 1 }

RsiLinkEntry ::=
    SEQUENCE {
        rsiLinkEndPoint1CompId          Integer32,
        rsiLinkEndPoint2CompId          Integer32,
        rsiLinkStatus                   INTEGER
    }

rsiLinkEndPoint1CompId OBJECT-TYPE
    SYNTAX          Integer32
    MAX-ACCESS      read-only
    STATUS          current
    DESCRIPTION     
            "This is the component id of LinkEndPoint1"
    ::= { rsiLinkEntry 1 }

rsiLinkEndPoint2CompId OBJECT-TYPE
    SYNTAX          Integer32
    MAX-ACCESS      read-only
    STATUS          current
    DESCRIPTION     
            "This is the component id of EndPoint2"
    ::= { rsiLinkEntry 2 }

rsiLinkStatus OBJECT-TYPE
    SYNTAX          INTEGER { down(0), up(1), partial(2), unknown(3) }
    MAX-ACCESS      read-only
    STATUS          current
    DESCRIPTION     
            "This is the type of the component"
    ::= { rsiLinkEntry 3 }

rsiAlarmTable OBJECT-TYPE
    SYNTAX          SEQUENCE OF RsiAlarmEntry
    MAX-ACCESS      not-accessible
    STATUS          current
    DESCRIPTION     
            "This table stores the RSI alarms. These alarms have
             already been notified as traps."
    ::= { rsiCommonMib 4 }

rsiAlarmEntry OBJECT-TYPE
    SYNTAX          RsiAlarmEntry
    MAX-ACCESS      not-accessible
    STATUS          current
    DESCRIPTION     
            "Description of an alarm raised by a RSI component"
    INDEX           { rsiAlarmId }
    ::= { rsiAlarmTable 1 }

RsiAlarmEntry ::=
    SEQUENCE {
        rsiAlarmId                      Integer32,
        rsiRelatedAlarmId               Integer32,
        rsiAlarmDateTime                DisplayString,
        rsiAlarmErrorCode               Integer32,
        rsiAlarmContent                 OCTET STRING,
        rsiOriginatingSubsystemId       Integer32,
        rsiOriginatingSubsystemName     OCTET STRING,
        rsiTroublingSubsystemId         Integer32,
        rsiTroublingSubsystemName       OCTET STRING,
        rsiAlarmStatus                  INTEGER,
        rsiAlarmSeverity                INTEGER,
        rsiAlarmAcknowledgedBy          OCTET STRING,
        rsiAcknowledgementDateTime      DisplayString,
        rsiAlarmClearedBy               OCTET STRING,
        rsiClearingDateTime             DisplayString,
        rsiOrigSystemId                 Integer32,
        rsiOrigSystemName               OCTET STRING,
        rsiOrigHostId                   Integer32,
        rsiOrigHostName                 OCTET STRING
    }

rsiAlarmId OBJECT-TYPE
    SYNTAX          Integer32
    MAX-ACCESS      read-only
    STATUS          current
    DESCRIPTION     
            "This is the unique id of the alarm."
    ::= { rsiAlarmEntry 1 }

rsiRelatedAlarmId OBJECT-TYPE
    SYNTAX          Integer32
    MAX-ACCESS      read-only
    STATUS          current
    DESCRIPTION     
            "If the severity of this alarm is 'clear', then this
             entry will have meaningful value. In that case, this
             entry will contain the alarm id of the alarm, for which
             this clear has been raised."
    ::= { rsiAlarmEntry 2 }

rsiAlarmDateTime OBJECT-TYPE
    SYNTAX          DisplayString (SIZE(19))
    MAX-ACCESS      read-only
    STATUS          current
    DESCRIPTION     
            "This is the time of the alarm in 
             'YYYY:MM:DD HH:MM:SS' format"
    ::= { rsiAlarmEntry 3 }

rsiAlarmErrorCode OBJECT-TYPE
    SYNTAX          Integer32
    MAX-ACCESS      read-only
    STATUS          current
    DESCRIPTION     
            "This is the errorCode of the alarm"
    ::= { rsiAlarmEntry 4 }

rsiAlarmContent OBJECT-TYPE
    SYNTAX          OCTET STRING
    MAX-ACCESS      read-only
    STATUS          current
    DESCRIPTION     
            "This is the content string of the alarm, in i18n form"
    ::= { rsiAlarmEntry 5 }

rsiOriginatingSubsystemId OBJECT-TYPE
    SYNTAX          Integer32
    MAX-ACCESS      read-only
    STATUS          current
    DESCRIPTION     
            "This is the Id of the subsystem raising the alarm"
    ::= { rsiAlarmEntry 6 }

rsiOriginatingSubsystemName OBJECT-TYPE
    SYNTAX          OCTET STRING
    MAX-ACCESS      read-only
    STATUS          current
    DESCRIPTION     
            "This is the name of the subsystem raising the alarm"
    ::= { rsiAlarmEntry 7 }

rsiTroublingSubsystemId OBJECT-TYPE
    SYNTAX          Integer32
    MAX-ACCESS      read-only
    STATUS          current
    DESCRIPTION     
            "This is the Id of the subsystem which has failed, and
             because of which this alarm has been raised"
    ::= { rsiAlarmEntry 8 }

rsiTroublingSubsystemName OBJECT-TYPE
    SYNTAX          OCTET STRING
    MAX-ACCESS      read-only
    STATUS          current
    DESCRIPTION     
            "This is the name of the subsystem which has failed, and
             because of which this alarm has been raised"
    ::= { rsiAlarmEntry 9 }

rsiAlarmStatus OBJECT-TYPE
    SYNTAX          INTEGER { rsiAlarmAcked(1), rsiAlarmUnacked(0), 
                        rsiAlarmCleared(2), rsiAlarmUnknown(3) }
    MAX-ACCESS      read-write
    STATUS          current
    DESCRIPTION     
            "The status of the alarm"
    ::= { rsiAlarmEntry 10 }

rsiAlarmSeverity OBJECT-TYPE
    SYNTAX          INTEGER { critical(0), major(1), minor(2), 
                        warning(3), normal(4), unknown(5), clear(6) }
    MAX-ACCESS      read-only
    STATUS          current
    DESCRIPTION     
            "This is the severity level of the alarm.  The unknown sevrity is depricated. normal severity relates to informational alarms."
    ::= { rsiAlarmEntry 11 }

rsiAlarmAcknowledgedBy OBJECT-TYPE
    SYNTAX          OCTET STRING
    MAX-ACCESS      read-only
    STATUS          current
    DESCRIPTION     
            "Name of the person who acknowledged the alarm "
    ::= { rsiAlarmEntry 12 }

rsiAcknowledgementDateTime OBJECT-TYPE
    SYNTAX          DisplayString (SIZE(19))
    MAX-ACCESS      read-only
    STATUS          current
    DESCRIPTION     
            "This is the time when this alarm was acknowledged, in
             'YYYY:MM:DD HH:MM:SS' format"
    ::= { rsiAlarmEntry 13 }

rsiAlarmClearedBy OBJECT-TYPE
    SYNTAX          OCTET STRING
    MAX-ACCESS      read-only
    STATUS          current
    DESCRIPTION     
            " Name of the person who cleared the alarm "
    ::= { rsiAlarmEntry 14 }

rsiClearingDateTime OBJECT-TYPE
    SYNTAX          DisplayString (SIZE(19))
    MAX-ACCESS      read-only
    STATUS          current
    DESCRIPTION     
            "This is the time when this alarm was cleared, in
             'YYYY:MM:DD HH:MM:SS' format"
    ::= { rsiAlarmEntry 15 }

rsiOrigSystemId OBJECT-TYPE
    SYNTAX          Integer32
    MAX-ACCESS      read-only
    STATUS          current
    DESCRIPTION     
            "This is the Id of the system which contains the
             subsystem which has raised this alarm"
    ::= { rsiAlarmEntry 16 }

rsiOrigSystemName OBJECT-TYPE
    SYNTAX          OCTET STRING
    MAX-ACCESS      read-only
    STATUS          current
    DESCRIPTION     
            "This is the name of the system which contains the
             subsystem which has raised this alarm"
    ::= { rsiAlarmEntry 17 }

rsiOrigHostId OBJECT-TYPE
    SYNTAX          Integer32
    MAX-ACCESS      read-only
    STATUS          current
    DESCRIPTION     
            "This is the Id of the host on which the 
             subsystem which has raised this alarm is running"
    ::= { rsiAlarmEntry 18 }

rsiOrigHostName OBJECT-TYPE
    SYNTAX          OCTET STRING
    MAX-ACCESS      read-only
    STATUS          current
    DESCRIPTION     
            "This is the name of the host on which the 
             subsystem which has raised this alarm is running"
    ::= { rsiAlarmEntry 19 }

rsiAlarmSeverityTable OBJECT-TYPE
    SYNTAX          SEQUENCE OF RsiAlarmSeverityEntry
    MAX-ACCESS      not-accessible
    STATUS          current
    DESCRIPTION     
            "This table stores the table of alarm severity"
    ::= { rsiCommonMib 5 }

rsiAlarmSeverityEntry OBJECT-TYPE
    SYNTAX          RsiAlarmSeverityEntry
    MAX-ACCESS      not-accessible
    STATUS          current
    DESCRIPTION     
            "Description of an alarm severity entry"
    INDEX           { rsiErrorCode }
    ::= { rsiAlarmSeverityTable 1 }

RsiAlarmSeverityEntry ::=
    SEQUENCE {
        rsiErrorCode                    Integer32,
        rsiSeverity                     INTEGER,
        rsiToBeClearedErrorCode         Integer32,
        rsiTrapGenerationFlag           INTEGER,
        rsiTrapCategory                 INTEGER,
        rsiErrorCodeDesc                OCTET STRING,
        rsiAlarmSeverityRowStatus       RowStatus
    }

rsiErrorCode OBJECT-TYPE
    SYNTAX          Integer32
    MAX-ACCESS      read-create
    STATUS          current
    DESCRIPTION     
            "This is the errorCode of the alarm"
    ::= { rsiAlarmSeverityEntry 1 }

rsiSeverity OBJECT-TYPE
    SYNTAX          INTEGER { critical(0), major(1), minor(2), 
                        warning(3), normal(4), unknown(5), clear(6) }
    MAX-ACCESS      read-create
    STATUS          current
    DESCRIPTION     
            "This is the severity level of the alarm. 
             This severity can be modified at run time. By changing 
             this severity, any NEW alarm raised for this error code,
             will have this new severity. All existing alarms for the
             given error code will have the old severity.
             If the severity of an alarm is CLEAR, then this denotes
             that this alarm will act as an auto-clear for an existing
             alarm with error code same as the value of 
             rsiToBeClearedErrorCode for this entry. 
             Also, in this case the severity cannot be modified. 
              The unknown sevrity is depricated. normal severity relates 
             to informational alarms"
    ::= { rsiAlarmSeverityEntry 2 }

rsiToBeClearedErrorCode OBJECT-TYPE
    SYNTAX          Integer32
    MAX-ACCESS      read-create
    STATUS          current
    DESCRIPTION     
            "If the severity of this alarm is CLEAR, then this alarm
             will act as an auto-clear for an alarm with this error 
             code.
             If the severity of this alarm is not CLEAR, then this
             will have the value of 0."
    ::= { rsiAlarmSeverityEntry 3 }

rsiTrapGenerationFlag OBJECT-TYPE
    SYNTAX          INTEGER { trapToBeGenerated(1), 
                        trapNotToBeGenerated(2) }
    MAX-ACCESS      read-create
    STATUS          obsolete
    DESCRIPTION     
            "Flag to indicate whether trap is to be generated
             for an alarm with this error code.
             
             This object is deprecated and is kept here for backward compatibility
             All get to this object will result in zero and all set will fail"
    ::= { rsiAlarmSeverityEntry 4 }

rsiTrapCategory OBJECT-TYPE
    SYNTAX          INTEGER { communicationFailureTrap(0), 
                        configurationErrorTrap(1), systemFaultsTrap(2), 
                        systemCapacityTrap(3), resourceFailureTrap(4), 
                        applicationErrorTrap(5), thresholdAlarmTrap(6), 
                        securityAlarmTrap(7) }
    MAX-ACCESS      read-create
    STATUS          current
    DESCRIPTION     
            " It describes the trap category."
    ::= { rsiAlarmSeverityEntry 5 }

rsiErrorCodeDesc OBJECT-TYPE
    SYNTAX          OCTET STRING
    MAX-ACCESS      read-create
    STATUS          current
    DESCRIPTION     
            "It describes the error code"
    ::= { rsiAlarmSeverityEntry 6 }

rsiAlarmSeverityRowStatus OBJECT-TYPE
    SYNTAX          RowStatus
    MAX-ACCESS      read-create
    STATUS          current
    DESCRIPTION     
            "This is for dynamic addition/deletion of error codes.
             For creating a new error code, only 'createAndGo' is
             supported. Deletion an alarm is currently not 
             supported"
    ::= { rsiAlarmSeverityEntry 7 }

rsiSystemTable OBJECT-TYPE
    SYNTAX          SEQUENCE OF RsiSystemEntry
    MAX-ACCESS      not-accessible
    STATUS          current
    DESCRIPTION     
            "This table stores info about all RSI systems"
    ::= { rsiCommonMib 6 }

rsiSystemEntry OBJECT-TYPE
    SYNTAX          RsiSystemEntry
    MAX-ACCESS      not-accessible
    STATUS          current
    DESCRIPTION     
            "Description of an RSI system"
    INDEX           { rsiSystemId }
    ::= { rsiSystemTable 1 }

RsiSystemEntry ::=
    SEQUENCE {
        rsiSystemId                     Integer32,
        rsiSystemDescription            OCTET STRING,
        rsiSystemContactLocation        OCTET STRING,
        rsiSystemContactPerson          OCTET STRING,
        rsiSystemContactPhoneNo         OCTET STRING,
        rsiSystemVersionId              OCTET STRING,
        rsiSystemInstallationDateTime   DisplayString,
        rsiSystemActiveSince            DisplayString
    }

rsiSystemId OBJECT-TYPE
    SYNTAX          Integer32
    MAX-ACCESS      read-only
    STATUS          current
    DESCRIPTION     
            "This is the component id of the system"
    ::= { rsiSystemEntry 1 }

rsiSystemDescription OBJECT-TYPE
    SYNTAX          OCTET STRING
    MAX-ACCESS      read-write
    STATUS          current
    DESCRIPTION     
            "Textual Description of the System"
    ::= { rsiSystemEntry 2 }

rsiSystemContactLocation OBJECT-TYPE
    SYNTAX          OCTET STRING
    MAX-ACCESS      read-write
    STATUS          current
    DESCRIPTION     
            "Address of the Contact Location for this System"
    ::= { rsiSystemEntry 3 }

rsiSystemContactPerson OBJECT-TYPE
    SYNTAX          OCTET STRING
    MAX-ACCESS      read-write
    STATUS          current
    DESCRIPTION     
            "Name of the Contact Person for this System in the above
             mentioned Location"
    ::= { rsiSystemEntry 4 }

rsiSystemContactPhoneNo OBJECT-TYPE
    SYNTAX          OCTET STRING
    MAX-ACCESS      read-write
    STATUS          current
    DESCRIPTION     
            "Phone No. of the Contact Person for this System"
    ::= { rsiSystemEntry 5 }

rsiSystemVersionId OBJECT-TYPE
    SYNTAX          OCTET STRING
    MAX-ACCESS      read-only
    STATUS          current
    DESCRIPTION     
            "Version Id of the software installed on this System"
    ::= { rsiSystemEntry 6 }

rsiSystemInstallationDateTime OBJECT-TYPE
    SYNTAX          DisplayString
    MAX-ACCESS      read-only
    STATUS          current
    DESCRIPTION     
            "Date of installation of the current sofware for this 
             System"
    ::= { rsiSystemEntry 7 }

rsiSystemActiveSince OBJECT-TYPE
    SYNTAX          DisplayString
    MAX-ACCESS      read-only
    STATUS          current
    DESCRIPTION     
            "Date since which this System is active"
    ::= { rsiSystemEntry 8 }

rsiFunctionalUnitTable OBJECT-TYPE
    SYNTAX          SEQUENCE OF RsiFunctionalUnitEntry
    MAX-ACCESS      not-accessible
    STATUS          current
    DESCRIPTION     
            "This table stores the information about all RSI FUs"
    ::= { rsiCommonMib 7 }

rsiFunctionalUnitEntry OBJECT-TYPE
    SYNTAX          RsiFunctionalUnitEntry
    MAX-ACCESS      not-accessible
    STATUS          current
    DESCRIPTION     
            "Description of an RSI FU"
    INDEX           { rsiFunctionalUnitId }
    ::= { rsiFunctionalUnitTable 1 }

RsiFunctionalUnitEntry ::=
    SEQUENCE {
        rsiFunctionalUnitId             Integer32,
        rsiFUVersionId                  OCTET STRING,
        rsiFUInstallationDateTime       DisplayString
    }

rsiFunctionalUnitId OBJECT-TYPE
    SYNTAX          Integer32
    MAX-ACCESS      read-only
    STATUS          current
    DESCRIPTION     
            "This is the component id of the Functional Unit"
    ::= { rsiFunctionalUnitEntry 1 }

rsiFUVersionId OBJECT-TYPE
    SYNTAX          OCTET STRING
    MAX-ACCESS      read-only
    STATUS          current
    DESCRIPTION     
            "Version Id of the software installed on this FU"
    ::= { rsiFunctionalUnitEntry 2 }

rsiFUInstallationDateTime OBJECT-TYPE
    SYNTAX          DisplayString
    MAX-ACCESS      read-only
    STATUS          current
    DESCRIPTION     
            "Date of installation of the current sofware for this FU"
    ::= { rsiFunctionalUnitEntry 3 }

rsiSubsystemTable OBJECT-TYPE
    SYNTAX          SEQUENCE OF RsiSubsystemEntry
    MAX-ACCESS      not-accessible
    STATUS          current
    DESCRIPTION     
            "This table stores the information about all RSI 
             Subsystems"
    ::= { rsiCommonMib 8 }

rsiSubsystemEntry OBJECT-TYPE
    SYNTAX          RsiSubsystemEntry
    MAX-ACCESS      not-accessible
    STATUS          current
    DESCRIPTION     
            "Description of an RSI Subsystem"
    INDEX           { rsiSubsystemId }
    ::= { rsiSubsystemTable 1 }

RsiSubsystemEntry ::=
    SEQUENCE {
        rsiSubsystemId                  Integer32,
        rsiSubsystemVersionId           OCTET STRING,
        rsiSubsystemInstallationDateTime DisplayString,
        rsiSubsystemActiveSince         DisplayString,
        rsiSubsystemRole                DisplayString
    }

rsiSubsystemId OBJECT-TYPE
    SYNTAX          Integer32
    MAX-ACCESS      read-only
    STATUS          current
    DESCRIPTION     
            "This is the component id of the Subsystem"
    ::= { rsiSubsystemEntry 1 }

rsiSubsystemVersionId OBJECT-TYPE
    SYNTAX          OCTET STRING
    MAX-ACCESS      read-only
    STATUS          current
    DESCRIPTION     
            "Version Id of the software installed on this Subsystem"
    ::= { rsiSubsystemEntry 2 }

rsiSubsystemInstallationDateTime OBJECT-TYPE
    SYNTAX          DisplayString
    MAX-ACCESS      read-only
    STATUS          current
    DESCRIPTION     
            "Date of installation of the current sofware for this 
             Subsystem"
    ::= { rsiSubsystemEntry 3 }

rsiSubsystemActiveSince OBJECT-TYPE
    SYNTAX          DisplayString
    MAX-ACCESS      read-only
    STATUS          current
    DESCRIPTION     
            "Date since which this Subsystem is active"
    ::= { rsiSubsystemEntry 4 }

rsiSubsystemRole OBJECT-TYPE
    SYNTAX          DisplayString
    MAX-ACCESS      read-only
    STATUS          current
    DESCRIPTION     
            "whether this Subsystem is active/standby"
    ::= { rsiSubsystemEntry 5 }

rsiUserSecurityPolicyTable OBJECT-TYPE
    SYNTAX          SEQUENCE OF RsiUserSecurityPolicyEntry
    MAX-ACCESS      not-accessible
    STATUS          current
    DESCRIPTION     
            "This table stores the information about the 
             security policies available for a user "
    ::= { rsiCommonMib 9 }

rsiUserSecurityPolicyEntry OBJECT-TYPE
    SYNTAX          RsiUserSecurityPolicyEntry
    MAX-ACCESS      not-accessible
    STATUS          current
    DESCRIPTION     
            "Description of a User Security Policy Entry"
    INDEX           { rsiUserSecurityPolicyName }
    ::= { rsiUserSecurityPolicyTable 1 }

RsiUserSecurityPolicyEntry ::=
    SEQUENCE {
        rsiUserSecurityPolicyName       OCTET STRING,
        rsiUserSecurityPolicyId         Integer32,
        rsiUserSecurityPasswdExpiryDays Integer32,
        rsiUserSecurityMaxFailedAttempts Integer32,
        rsiUserSecurityMinPasswordLen   Integer32,
        rsiUserSecurityPasswdRecylingPolicy   INTEGER,
        rsiUserSecurityPasswdRecylingMinDaysToUse         Integer32,
        rsiUserSecurityPasswdRecylingNumOfPasswds         Integer32,
        rsiUserSecurityMinNumberOfNumericCharInPasswd             Integer32,
        rsiUserSecurityMinNumberOfSpecialCharInPasswd             Integer32,
        rsiNumberOfLoginsAllowed        Integer32,
        rsiUserSecurityPolicyRowStatus  RowStatus
    }

rsiUserSecurityPolicyName OBJECT-TYPE
    SYNTAX          OCTET STRING
    MAX-ACCESS      read-only
    STATUS          current
    DESCRIPTION     
            "This is the human readable name for this policy"
    ::= { rsiUserSecurityPolicyEntry 1 }

rsiUserSecurityPolicyId OBJECT-TYPE
    SYNTAX          Integer32
    MAX-ACCESS      read-only
    STATUS          current
    DESCRIPTION     
            "This is the unique id associated with this policy"
    ::= { rsiUserSecurityPolicyEntry 2 }

rsiUserSecurityPasswdExpiryDays OBJECT-TYPE
    SYNTAX          Integer32
    MAX-ACCESS      read-create
    STATUS          current
    DESCRIPTION     
            "Days after which the currentpassword would expire.
             Default Value - 30 days."
    ::= { rsiUserSecurityPolicyEntry 3 }

rsiUserSecurityMaxFailedAttempts OBJECT-TYPE
    SYNTAX          Integer32
    MAX-ACCESS      read-create
    STATUS          current
    DESCRIPTION     
            "Maximum no. of failed login attempts at one go, 
             after which the user account will be locked. 
             Default Value - 3 attempts."
    ::= { rsiUserSecurityPolicyEntry 4 }

rsiUserSecurityMinPasswordLen OBJECT-TYPE
    SYNTAX          Integer32
    MAX-ACCESS      read-create
    STATUS          current
    DESCRIPTION     
            "Maximum no. of failed login attempts at one go, 
             after which the user account will be locked. 
             Default Value - 6 characters."
    ::= { rsiUserSecurityPolicyEntry 5 }

rsiUserSecurityPasswdRecylingPolicy OBJECT-TYPE
    SYNTAX          INTEGER { timeBased(0), numberBased(1), 
                        timeAndNumberBased(2) }
    MAX-ACCESS      read-create
    STATUS          current
    DESCRIPTION     
            "Old passwords of a user are saved, and based 
             on the recycling policy, the old password can be 
             reused. 
             Time Based Password Recycling: no. of days after 
             which the new password can have the same value as 
             the old password which had been previously modified. 
             Number Based Password Recycling: no. of passwords 
             that have have been changed, after which an 
             old password can be reused. 
             Default Value - timeAndNumberBased"
    ::= { rsiUserSecurityPolicyEntry 6 }

rsiUserSecurityPasswdRecylingMinDaysToUse OBJECT-TYPE
    SYNTAX          Integer32
    MAX-ACCESS      read-create
    STATUS          current
    DESCRIPTION     
            "If the Password Recycling Policy is Time Based, 
             then the number of days after which the old password 
             can be reused. 
             Default Value - 0."
    ::= { rsiUserSecurityPolicyEntry 7 }

rsiUserSecurityPasswdRecylingNumOfPasswds OBJECT-TYPE
    SYNTAX          Integer32
    MAX-ACCESS      read-create
    STATUS          current
    DESCRIPTION     
            "If the Password Recycling Policy is Number Based, 
             then the number of password changes after which the 
             old password can be reused. 
             Default Value - 0"
    ::= { rsiUserSecurityPolicyEntry 8 }

rsiUserSecurityMinNumberOfNumericCharInPasswd OBJECT-TYPE
    SYNTAX          Integer32
    MAX-ACCESS      read-create
    STATUS          current
    DESCRIPTION     
            "This defines the minimum number of numeric characters
             that need to be present in a password.
             Default Value - 0"
    ::= { rsiUserSecurityPolicyEntry 9 }

rsiUserSecurityMinNumberOfSpecialCharInPasswd OBJECT-TYPE
    SYNTAX          Integer32
    MAX-ACCESS      read-create
    STATUS          current
    DESCRIPTION     
            "This defines the minimum number of special characters
             that need to be present in a password.
             Default Value - 0"
    ::= { rsiUserSecurityPolicyEntry 10 }

rsiNumberOfLoginsAllowed OBJECT-TYPE
    SYNTAX          Integer32
    MAX-ACCESS      read-create
    STATUS          current
    DESCRIPTION     
            "This defines the maximum number of logins allowed simultaneousl"
    ::= { rsiUserSecurityPolicyEntry 11 }

rsiUserSecurityPolicyRowStatus OBJECT-TYPE
    SYNTAX          RowStatus
    MAX-ACCESS      read-create
    STATUS          current
    DESCRIPTION     
            "This is for dynamic addition/deletion of policies.
             For creating a new policy, only 'createAndGo' is
             supported. For deleting an existing row, 'delete'
             is supported"
    ::= { rsiUserSecurityPolicyEntry 12 }

rsiFeatureTable OBJECT-TYPE
    SYNTAX          SEQUENCE OF RsiFeatureEntry
    MAX-ACCESS      not-accessible
    STATUS          current
    DESCRIPTION     
            "This table stores the information about the
             features supported for management purposes."
    ::= { rsiCommonMib 10 }

rsiFeatureEntry OBJECT-TYPE
    SYNTAX          RsiFeatureEntry
    MAX-ACCESS      not-accessible
    STATUS          current
    DESCRIPTION     
            "Description of a User Security Policy Entry"
    INDEX           { rsiFeatureId }
    ::= { rsiFeatureTable 1 }

RsiFeatureEntry ::=
    SEQUENCE {
        rsiFeatureId                    Integer32,
        rsiFeatureName                  OCTET STRING,
        rsiAPINames                     OCTET STRING
    }

rsiFeatureId OBJECT-TYPE
    SYNTAX          Integer32
    MAX-ACCESS      read-only
    STATUS          current
    DESCRIPTION     
            "This is the unique id of the feature"
    ::= { rsiFeatureEntry 1 }

rsiFeatureName OBJECT-TYPE
    SYNTAX          OCTET STRING
    MAX-ACCESS      read-only
    STATUS          current
    DESCRIPTION     
            "Name assigned to this feature"
    ::= { rsiFeatureEntry 2 }

rsiAPINames OBJECT-TYPE
    SYNTAX          OCTET STRING
    MAX-ACCESS      read-only
    STATUS          current
    DESCRIPTION     
            "List of API Names which belong to the given feature.
             This will be a comma seperated list, and could have
             been described as sequence of strings."
    ::= { rsiFeatureEntry 3 }

rsiRoleTable OBJECT-TYPE
    SYNTAX          SEQUENCE OF RsiRoleEntry
    MAX-ACCESS      not-accessible
    STATUS          current
    DESCRIPTION     
            "This table stores the information about the
             possible user roles."
    ::= { rsiCommonMib 11 }

rsiRoleEntry OBJECT-TYPE
    SYNTAX          RsiRoleEntry
    MAX-ACCESS      not-accessible
    STATUS          current
    DESCRIPTION     
            "Description of a Role"
    INDEX           { rsiRoleName }
    ::= { rsiRoleTable 1 }

RsiRoleEntry ::=
    SEQUENCE {
        rsiRoleName                     OCTET STRING,
        rsiRoleId                       Integer32,
        rsiFeatureIds                   OCTET STRING,
        rsiRoleRowStatus                RowStatus
    }

rsiRoleName OBJECT-TYPE
    SYNTAX          OCTET STRING
    MAX-ACCESS      read-only
    STATUS          current
    DESCRIPTION     
            "Unique Name assigned to this role"
    ::= { rsiRoleEntry 1 }

rsiRoleId OBJECT-TYPE
    SYNTAX          Integer32
    MAX-ACCESS      read-only
    STATUS          current
    DESCRIPTION     
            "This is the unique id associated with this role."
    ::= { rsiRoleEntry 2 }

rsiFeatureIds OBJECT-TYPE
    SYNTAX          OCTET STRING
    MAX-ACCESS      read-create
    STATUS          current
    DESCRIPTION     
            "List of Feature Ids which belong to the given role.
             This will be a comma seperated list, and could have
             been described as sequence of strings."
    ::= { rsiRoleEntry 3 }

rsiRoleRowStatus OBJECT-TYPE
    SYNTAX          RowStatus
    MAX-ACCESS      read-create
    STATUS          current
    DESCRIPTION     
            "This is for dynamic addition/deletion of roles.
             For creating a new role entry, only 'createAndGo' is
             supported. For deleting an existing row, 'delete'
             is supported"
    ::= { rsiRoleEntry 4 }

rsiUserTable OBJECT-TYPE
    SYNTAX          SEQUENCE OF RsiUserEntry
    MAX-ACCESS      not-accessible
    STATUS          current
    DESCRIPTION     
            "This table stores the information about all users 
             accessing the RSI solution"
    ::= { rsiCommonMib 12 }

rsiUserEntry OBJECT-TYPE
    SYNTAX          RsiUserEntry
    MAX-ACCESS      not-accessible
    STATUS          current
    DESCRIPTION     
            "Description of an RSI Subsystem"
    INDEX           { rsiUserId }
    ::= { rsiUserTable 1 }

RsiUserEntry ::=
    SEQUENCE {
        rsiUserId                       OCTET STRING,
        rsiUserFirstName                OCTET STRING,
        rsiUserMiddleName               OCTET STRING,
        rsiUserLastName                 OCTET STRING,
        rsiUserActivationDate           DisplayString,
        rsiUserExpiryDate               DisplayString,
        rsiUserStatus                   INTEGER,
        rsiUserPolicyId                 Integer32,
        rsiUserRoles                    OCTET STRING,
        rsiLoggingEnableOption          Integer32,
        rsiUserRowStatus                RowStatus
    }

rsiUserId OBJECT-TYPE
    SYNTAX          OCTET STRING
    MAX-ACCESS      read-only
    STATUS          current
    DESCRIPTION     
            "This is the unique id of a user"
    ::= { rsiUserEntry 1 }

rsiUserFirstName OBJECT-TYPE
    SYNTAX          OCTET STRING
    MAX-ACCESS      read-create
    STATUS          current
    DESCRIPTION     
            "This is the First Name of the user. 
             Mandatory field for creating a new user"
    ::= { rsiUserEntry 2 }

rsiUserMiddleName OBJECT-TYPE
    SYNTAX          OCTET STRING
    MAX-ACCESS      read-create
    STATUS          current
    DESCRIPTION     
            "This is the Middle Name of the user.
             Mandatory field for creating a new user"
    ::= { rsiUserEntry 3 }

rsiUserLastName OBJECT-TYPE
    SYNTAX          OCTET STRING
    MAX-ACCESS      read-create
    STATUS          current
    DESCRIPTION     
            "This is the Last Name of the user.
             Mandatory field for creating a new user"
    ::= { rsiUserEntry 4 }

rsiUserActivationDate OBJECT-TYPE
    SYNTAX          DisplayString (SIZE(19))
    MAX-ACCESS      read-only
    STATUS          current
    DESCRIPTION     
            "This is the time at which the user account was created.
             format is 'YYYY:MM:DD HH:MM:SS'.
             This attribute cannot be modified."
    ::= { rsiUserEntry 5 }

rsiUserExpiryDate OBJECT-TYPE
    SYNTAX          DisplayString (SIZE(19))
    MAX-ACCESS      read-only
    STATUS          current
    DESCRIPTION     
            "This is the time at which the user account will expire.
             format is 'YYYY:MM:DD HH:MM:SS'. 
             This attribute cannot be modified."
    ::= { rsiUserEntry 6 }

rsiUserStatus OBJECT-TYPE
    SYNTAX          INTEGER { new(0), active(1), locked(2), inactive(3), 
                        deleted(4) }
    MAX-ACCESS      read-create
    STATUS          current
    DESCRIPTION     
            "This is the user account status.
             This attribute is not needed while creating a user,
             but can be modified.
             This field holds no importance for creating a new user,
             because by default the value of status will be new."
    ::= { rsiUserEntry 7 }

rsiUserPolicyId OBJECT-TYPE
    SYNTAX          Integer32
    MAX-ACCESS      read-create
    STATUS          current
    DESCRIPTION     
            "This identifies the security policy opted for the user.
             Mandatory field for creating a new user"
    ::= { rsiUserEntry 8 }

rsiUserRoles OBJECT-TYPE
    SYNTAX          OCTET STRING
    MAX-ACCESS      read-only
    STATUS          current
    DESCRIPTION     
            "This is the list of role ids assigned to a given user. 
             This will be a comma seperated list, and could have
             been described as sequence of integers.
             This attribute cannot be modified.
             By default when a user is created, he is assigned a
             role, and if a new role needs to be assigned to a
             user, then entries should be manipulated at the
             user-role table (rsiUserRoleTable)"
    ::= { rsiUserEntry 9 }

rsiLoggingEnableOption OBJECT-TYPE
    SYNTAX          Integer32
    MAX-ACCESS      read-create
    STATUS          current
    DESCRIPTION     
            "To Enable logging set the LSB to 1 and to disable logging set the LSB to 0."
    ::= { rsiUserEntry 10 }

rsiUserRowStatus OBJECT-TYPE
    SYNTAX          RowStatus
    MAX-ACCESS      read-create
    STATUS          current
    DESCRIPTION     
            "This is for dynamic addition/deletion of users.
             For creating a new user entry, only 'createAndGo' is
             supported. For deleting an existing row, 'delete'
             is supported"
    ::= { rsiUserEntry 11 }

rsiUserRoleTable OBJECT-TYPE
    SYNTAX          SEQUENCE OF RsiUserRoleEntry
    MAX-ACCESS      not-accessible
    STATUS          current
    DESCRIPTION     
            "This table contains the list of component Ids,
             which have been assigned to a given user for a
             given role. "
    ::= { rsiCommonMib 13 }

rsiUserRoleEntry OBJECT-TYPE
    SYNTAX          RsiUserRoleEntry
    MAX-ACCESS      not-accessible
    STATUS          current
    DESCRIPTION     
            "Description of a user-role association. Note UserId
             and RoleId are index of foreign tables"
    INDEX           { rsiUserId, rsiRoleId }
    ::= { rsiUserRoleTable 1 }

RsiUserRoleEntry ::=
    SEQUENCE {
        rsiComponentIdList              OCTET STRING,
        rsiUserRoleRowStatus            RowStatus
    }

rsiComponentIdList OBJECT-TYPE
    SYNTAX          OCTET STRING
    MAX-ACCESS      read-create
    STATUS          current
    DESCRIPTION     
            "This is a comma separated list of component Ids
             which can be managed by the given user with the
             given role.
             This attribute is not modifiable"
    ::= { rsiUserRoleEntry 1 }

rsiUserRoleRowStatus OBJECT-TYPE
    SYNTAX          RowStatus
    MAX-ACCESS      read-create
    STATUS          current
    DESCRIPTION     
            "This is for dynamic addition/deletion of roles
             associated with a user.
             For creating a new user-role entry, only 'createAndGo' 
             is supported. For deleting an existing row, 'delete'
             is supported"
    ::= { rsiUserRoleEntry 2 }

rsiPerformanceHistoryTable OBJECT-TYPE
    SYNTAX          SEQUENCE OF RsiPerformanceHistoryEntry
    MAX-ACCESS      not-accessible
    STATUS          current
    DESCRIPTION     
            "This table contains the performance history of all
             the components."
    ::= { rsiCommonMib 14 }

rsiPerformanceHistoryEntry OBJECT-TYPE
    SYNTAX          RsiPerformanceHistoryEntry
    MAX-ACCESS      not-accessible
    STATUS          current
    DESCRIPTION     
            "Description of the performance oid and its value for
             a given component at a give time. 
             This table will give the value of a performance OID
             for a given component, at the given time.
             Note: rsiCompId is index of a foreign table."
    INDEX           { rsiCompId, rsiPerfOid, rsiPerfTimestamp }
    ::= { rsiPerformanceHistoryTable 1 }

RsiPerformanceHistoryEntry ::=
    SEQUENCE {
        rsiPerfTimestamp                Integer32,
        rsiPerfOid                      OBJECT IDENTIFIER,
        rsiPerfValue                    DisplayString
    }

rsiPerfTimestamp OBJECT-TYPE
    SYNTAX          Integer32
    MAX-ACCESS      read-only
    STATUS          current
    DESCRIPTION     
            "Time at which the performance was measured.
             This is the time in seconds since the Epoch 
             (00:00:00 UTC, January 1, 1970)."
    ::= { rsiPerformanceHistoryEntry 1 }

rsiPerfOid OBJECT-TYPE
    SYNTAX          OBJECT IDENTIFIER
    MAX-ACCESS      read-only
    STATUS          current
    DESCRIPTION     
            "OID in MIB for which the performance was measured."
    ::= { rsiPerformanceHistoryEntry 2 }

rsiPerfValue OBJECT-TYPE
    SYNTAX          DisplayString
    MAX-ACCESS      read-only
    STATUS          current
    DESCRIPTION     
            "value of the OID for which performance was measured."
    ::= { rsiPerformanceHistoryEntry 3 }

rsiPerformanceThresholdTable OBJECT-TYPE
    SYNTAX          SEQUENCE OF RsiPerformanceThresholdEntry
    MAX-ACCESS      not-accessible
    STATUS          current
    DESCRIPTION     
            "This table contains the performance thresholds for all
             the OIDs."
    ::= { rsiCommonMib 15 }

rsiPerformanceThresholdEntry OBJECT-TYPE
    SYNTAX          RsiPerformanceThresholdEntry
    MAX-ACCESS      not-accessible
    STATUS          current
    DESCRIPTION     
            "Description of the performance oid and its rising
             and falling threshold values, along with the alarm
             severity of the alarm to be raised."
    INDEX           { rsiPerfThresholdOid, rsiPerfThresholdId }
    ::= { rsiPerformanceThresholdTable 1 }

RsiPerformanceThresholdEntry ::=
    SEQUENCE {
        rsiPerfThresholdOid             OBJECT IDENTIFIER,
        rsiPerfThresholdId              Integer32,
        rsiPerfThresholdRisingVal       Integer32,
        rsiPerfThresholdFallingVal      Integer32,
        rsiPerfThresholdSeverity        INTEGER,
        rsiPerfThresholdRowStatus       RowStatus
    }

rsiPerfThresholdOid OBJECT-TYPE
    SYNTAX          OBJECT IDENTIFIER
    MAX-ACCESS      read-only
    STATUS          current
    DESCRIPTION     
            "OID in MIB for which the performance threshold has
             been defined."
    ::= { rsiPerformanceThresholdEntry 1 }

rsiPerfThresholdId OBJECT-TYPE
    SYNTAX          Integer32
    MAX-ACCESS      read-only
    STATUS          current
    DESCRIPTION     
            "Unique identifier of the given performance threshold."
    ::= { rsiPerformanceThresholdEntry 2 }

rsiPerfThresholdRisingVal OBJECT-TYPE
    SYNTAX          Integer32
    MAX-ACCESS      read-create
    STATUS          current
    DESCRIPTION     
            "High Water Mark for the given threshold"
    ::= { rsiPerformanceThresholdEntry 3 }

rsiPerfThresholdFallingVal OBJECT-TYPE
    SYNTAX          Integer32
    MAX-ACCESS      read-create
    STATUS          current
    DESCRIPTION     
            "Low Water Mark for the given threshold"
    ::= { rsiPerformanceThresholdEntry 4 }

rsiPerfThresholdSeverity OBJECT-TYPE
    SYNTAX          INTEGER { critical(0), major(1), minor(2), 
                        warning(3), normal(4) }
    MAX-ACCESS      read-create
    STATUS          current
    DESCRIPTION     
            "Severity of the alarm to be raised on crossing the
             threshold."
    ::= { rsiPerformanceThresholdEntry 5 }

rsiPerfThresholdRowStatus OBJECT-TYPE
    SYNTAX          RowStatus
    MAX-ACCESS      read-create
    STATUS          current
    DESCRIPTION     
            "This is for dynamic addition/deletion of performance
             thresholds.
             For creating a new threshold entry, only 'createAndGo' is
             supported. For deleting an existing row, 'destroy'
             is supported"
    ::= { rsiPerformanceThresholdEntry 6 }

rsiAlarmPoliciesTable OBJECT-TYPE
    SYNTAX          SEQUENCE OF RsiAlarmPoliciesEntry
    MAX-ACCESS      not-accessible
    STATUS          current
    DESCRIPTION     
            "This table contains the performance thresholds for all
             the OIDs."
    ::= { rsiCommonMib 16 }

rsiAlarmPoliciesEntry OBJECT-TYPE
    SYNTAX          RsiAlarmPoliciesEntry
    MAX-ACCESS      not-accessible
    STATUS          current
    DESCRIPTION     
            "Description of the alarm policies associated with a 
             severity."
    INDEX           { rsiAlarmPolicySeverity }
    ::= { rsiAlarmPoliciesTable 1 }

RsiAlarmPoliciesEntry ::=
    SEQUENCE {
        rsiAlarmPolicySeverity          INTEGER,
        rsiAlarmSeverityEscalationTimeInterval      Integer32,
        rsiAlarmAutoAckUpperThresholdLimit  Integer32,
        rsiAlarmAutoAckRetentionTimeInterval    Integer32
    }

rsiAlarmPolicySeverity OBJECT-TYPE
    SYNTAX          INTEGER { critical(0), major(1), minor(2), 
                        warning(3), normal(4) }
    MAX-ACCESS      read-only
    STATUS          current
    DESCRIPTION     
            "severity of the alarm for which this policy has 
             been defined."
    ::= { rsiAlarmPoliciesEntry 1 }

rsiAlarmSeverityEscalationTimeInterval OBJECT-TYPE
    SYNTAX          Integer32
    MAX-ACCESS      read-write
    STATUS          current
    DESCRIPTION     
            "This signifies the time interval for which an un-acked
             alarms' severity may not be raised to the next level.
             Note the unit of this time interval is hrs.This can not be
             set for critical severity"
    ::= { rsiAlarmPoliciesEntry 2 }

rsiAlarmAutoAckUpperThresholdLimit OBJECT-TYPE
    SYNTAX          Integer32
    MAX-ACCESS      read-write
    STATUS          current
    DESCRIPTION     
            "The number of un-acked alarms that are to be retained
             for the given severity at any time."
    ::= { rsiAlarmPoliciesEntry 3 }

rsiAlarmAutoAckRetentionTimeInterval OBJECT-TYPE
    SYNTAX          Integer32
    MAX-ACCESS      read-write
    STATUS          current
    DESCRIPTION     
            "This signifies that the time interval for which all
             un-acked alarms are not auto acked.
             Note the unit of this time interval is hrs."
    ::= { rsiAlarmPoliciesEntry 4 }

rsiLoggedInUsersTable OBJECT-TYPE
    SYNTAX          SEQUENCE OF RsiLoggedInUsersEntry
    MAX-ACCESS      not-accessible
    STATUS          current
    DESCRIPTION     
            "This table contains the information about the currently
             logged in users. "
    ::= { rsiCommonMib 17 }

rsiLoggedInUsersEntry OBJECT-TYPE
    SYNTAX          RsiLoggedInUsersEntry
    MAX-ACCESS      not-accessible
    STATUS          current
    DESCRIPTION     
            "Description of a currently logged-in user. "
    INDEX           { rsiUserId }
    ::= { rsiLoggedInUsersTable 1 }

RsiLoggedInUsersEntry ::=
    SEQUENCE {
        rsiLoggedInUserSessionLoginTime DisplayString,
        rsiLoggedInUserLastCommandTime  DisplayString,
        rsiLoggedInUserRowStatus        RowStatus
    }

rsiLoggedInUserSessionLoginTime OBJECT-TYPE
    SYNTAX          DisplayString (SIZE(19))
    MAX-ACCESS      read-only
    STATUS          current
    DESCRIPTION     
            "This is the time at which this user logged in, and is in
             'YYYY:MM:DD HH:MM:SS' format. "
    ::= { rsiLoggedInUsersEntry 1 }

rsiLoggedInUserLastCommandTime OBJECT-TYPE
    SYNTAX          DisplayString (SIZE(19))
    MAX-ACCESS      read-only
    STATUS          current
    DESCRIPTION     
            "This is the time at which this user issued the last 
             command, and is in 'YYYY:MM:DD HH:MM:SS' format. "
    ::= { rsiLoggedInUsersEntry 2 }

rsiLoggedInUserRowStatus OBJECT-TYPE
    SYNTAX          RowStatus
    MAX-ACCESS      read-create
    STATUS          current
    DESCRIPTION     
            "This is for forcefully logging-off a user. When set
             to 'destroy', this user will be logged off. No other
             value can be set for this RowStatus. "
    ::= { rsiLoggedInUsersEntry 3 }

rsiSessionLogTable OBJECT-TYPE
    SYNTAX          SEQUENCE OF RsiSessionLogEntry
    MAX-ACCESS      not-accessible
    STATUS          current
    DESCRIPTION     
            "This table contains the information about all the
             sessions that existed or are existing in the system. "
    ::= { rsiCommonMib 18 }

rsiSessionLogEntry OBJECT-TYPE
    SYNTAX          RsiSessionLogEntry
    MAX-ACCESS      not-accessible
    STATUS          current
    DESCRIPTION     
            "Description of a Session log."
    INDEX           { rsiSessionLogUser, rsiSessionLogTime, 
                      rsiSessionLogId }
    ::= { rsiSessionLogTable 1 }

RsiSessionLogEntry ::=
    SEQUENCE {
        rsiSessionLogUser               DisplayString,
        rsiSessionLogTime               Integer32,
        rsiSessionLogId                 Integer32,
        rsiSessionLogDisplayTime        DisplayString,
        rsiSessionLogApiName            DisplayString,
        rsiSessionLogStatus             DisplayString
    }

rsiSessionLogUser OBJECT-TYPE
    SYNTAX          DisplayString
    MAX-ACCESS      read-only
    STATUS          current
    DESCRIPTION     
            "This is the name of the user for which this session log
             was created. "
    ::= { rsiSessionLogEntry 1 }

rsiSessionLogTime OBJECT-TYPE
    SYNTAX          Integer32
    MAX-ACCESS      read-only
    STATUS          current
    DESCRIPTION     
            "This is the time at which this session log was created, 
             and is in integer format. This is the time in seconds 
             since the Epoch (00:00:00 UTC, January 1, 1970). "
    ::= { rsiSessionLogEntry 2 }

rsiSessionLogId OBJECT-TYPE
    SYNTAX          Integer32
    MAX-ACCESS      read-only
    STATUS          current
    DESCRIPTION     
            "This is the unique id associated with this session log."
    ::= { rsiSessionLogEntry 3 }

rsiSessionLogDisplayTime OBJECT-TYPE
    SYNTAX          DisplayString (SIZE(19))
    MAX-ACCESS      read-only
    STATUS          current
    DESCRIPTION     
            "This is the time at which this session log was created, 
             and is in 'YYYY:MM:DD HH:MM:SS' format. same as
             rsiSessionLogTime"
    ::= { rsiSessionLogEntry 4 }

rsiSessionLogApiName OBJECT-TYPE
    SYNTAX          DisplayString
    MAX-ACCESS      read-only
    STATUS          current
    DESCRIPTION     
            "This is the name of the API that was invoked for this
             session log."
    ::= { rsiSessionLogEntry 5 }

rsiSessionLogStatus OBJECT-TYPE
    SYNTAX          DisplayString
    MAX-ACCESS      read-only
    STATUS          current
    DESCRIPTION     
            "This is the status of this session log. It can have
             values like: AUTHORIZED, NOT AUTHORIZED, 
             OPERATION SUCCEEDED, OPERATION FAILED, AUTHENTICATED, 
             NOT AUTHENTICATED "
    ::= { rsiSessionLogEntry 6 }

rsiAuditLogTable OBJECT-TYPE
    SYNTAX          SEQUENCE OF RsiAuditLogEntry
    MAX-ACCESS      not-accessible
    STATUS          current
    DESCRIPTION     
            "This table contains the information about all the
             sessions that existed or are existing in the system. "
    ::= { rsiCommonMib 19 }

rsiAuditLogEntry OBJECT-TYPE
    SYNTAX          RsiAuditLogEntry
    MAX-ACCESS      not-accessible
    STATUS          current
    DESCRIPTION     
            "Description of an audit log."
    INDEX           { rsiSessionLogId }
    ::= { rsiAuditLogTable 1 }

RsiAuditLogEntry ::=
    SEQUENCE {
        rsiAuditChangeInfo              DisplayString
    }

rsiAuditChangeInfo OBJECT-TYPE
    SYNTAX          DisplayString
    MAX-ACCESS      read-only
    STATUS          current
    DESCRIPTION     
            "This is the description of the change done by the user."
    ::= { rsiAuditLogEntry 1 }

rsiCLLICodeTable OBJECT-TYPE
    SYNTAX          SEQUENCE OF RsiCLLICodeEntry
    MAX-ACCESS      not-accessible
    STATUS          current
    DESCRIPTION     
            "This table contains the information about all the
             CLLI Codes existing in the system. "
    ::= { rsiCommonMib 20 }

rsiCLLICodeEntry OBJECT-TYPE
    SYNTAX          RsiCLLICodeEntry
    MAX-ACCESS      not-accessible
    STATUS          current
    DESCRIPTION     
            "Description of a CLLI Code."
    INDEX           { rsiCompId }
    ::= { rsiCLLICodeTable 1 }

RsiCLLICodeEntry ::=
    SEQUENCE {
        rsiCLLICodeHostName             DisplayString,
        rsiCLLICode                     DisplayString
    }

rsiCLLICodeHostName OBJECT-TYPE
    SYNTAX          DisplayString
    MAX-ACCESS      read-only
    STATUS          current
    DESCRIPTION     
            "This is the host name of the machine to which the CLLI
             Code has been assigned."
    ::= { rsiCLLICodeEntry 1 }

rsiCLLICode OBJECT-TYPE
    SYNTAX          DisplayString
    MAX-ACCESS      read-only
    STATUS          current
    DESCRIPTION     
            "This is the CLLI Code that has been assigned to this 
             host."
    ::= { rsiCLLICodeEntry 2 }

rsiAutoAckAlgoExecInterval OBJECT-TYPE
    SYNTAX          Integer32
    MAX-ACCESS      read-write
    STATUS          current
    DESCRIPTION     
            "The interval after which the algo for auto-acking 
             alarms is executed at regular time.
             Note the unit of this time interval is seconds."
    ::= { rsiCommonMib 31 }

rsiSevEscalationAlgoExecInterval OBJECT-TYPE
    SYNTAX          Integer32
    MAX-ACCESS      read-write
    STATUS          current
    DESCRIPTION     
            "The interval after which the algo for alarm severity 
             escalation is executed at regular time.
             Note the unit of this time interval is seconds."
    ::= { rsiCommonMib 32 }

rsiInactiveUserLogOffTimeInterval OBJECT-TYPE
    SYNTAX          Integer32
    MAX-ACCESS      read-write
    STATUS          current
    DESCRIPTION     
            "The interval for which if a user remains inactive, he/she
             will be logged off.
             Note the unit of this time interval is seconds."
    ::= { rsiCommonMib 33 }

rsiPerformanceCollectionInterval OBJECT-TYPE
    SYNTAX          Integer32
    MAX-ACCESS      read-write
    STATUS          current
    DESCRIPTION     
            "The interval after which the performance statistics of
             components will be fetched and put in as performance
             history data. 
             Note the unit of this time interval is seconds."
    ::= { rsiCommonMib 34 }

rsiCLEICode OBJECT-TYPE
    SYNTAX          DisplayString
    MAX-ACCESS      read-only
    STATUS          current
    DESCRIPTION     
            "COMMON LANGUAGE Equipment Identification Code."
    ::= { rsiCommonMib 35 }

rsiAlarmGroupTable OBJECT-TYPE
    SYNTAX          SEQUENCE OF RsiAlarmGroupEntry
    MAX-ACCESS      not-accessible
    STATUS          current
    DESCRIPTION     
            "This table stores the information about the defined Alarm Groups."
    ::= { rsiCommonMib 36 }

rsiAlarmGroupEntry OBJECT-TYPE
    SYNTAX          RsiAlarmGroupEntry
    MAX-ACCESS      not-accessible
    STATUS          current
    DESCRIPTION     
            "Description of a AlarmGroup"
    INDEX           { rsiAlarmGroupId }
    ::= { rsiAlarmGroupTable 1 }

RsiAlarmGroupEntry ::=
    SEQUENCE {
        rsiAlarmGroupId                 Integer32,
        rsiAlarmGroupName               DisplayString,
        rsiAlarmGroupRowStatus          RowStatus
    }

rsiAlarmGroupId OBJECT-TYPE
    SYNTAX          Integer32
    MAX-ACCESS      not-accessible
    STATUS          current
    DESCRIPTION     
            "This is the unique id associated with this Alarm Group."
    ::= { rsiAlarmGroupEntry 1 }

rsiAlarmGroupName OBJECT-TYPE
    SYNTAX          DisplayString
    MAX-ACCESS      read-create
    STATUS          current
    DESCRIPTION     
            "Name assigned to the Alarm Group"
    ::= { rsiAlarmGroupEntry 2 }

rsiAlarmGroupRowStatus OBJECT-TYPE
    SYNTAX          RowStatus
    MAX-ACCESS      read-create
    STATUS          current
    DESCRIPTION     
            "This is for dynamic addition/deletion of Alarm Group(s). For creating a new Alarm Group entry, only 'createAndGo' is supported. For deleting an existing row, 'delete' is supported"
    ::= { rsiAlarmGroupEntry 3 }

rsiAlarmGroupErrorMapTable OBJECT-TYPE
    SYNTAX          SEQUENCE OF RsiAlarmGroupErrorMapEntry
    MAX-ACCESS      not-accessible
    STATUS          current
    DESCRIPTION     
            "This table stores the information of the mapping between the Alarm Group and the Error Codes, where Alarm Group is from rsiAlarmGroupTable and the ErrorCode is from rsiAlarmTable."
    ::= { rsiCommonMib 37 }

rsiAlarmGroupErrorMapEntry OBJECT-TYPE
    SYNTAX          RsiAlarmGroupErrorMapEntry
    MAX-ACCESS      not-accessible
    STATUS          current
    DESCRIPTION     
            "Description of the mapping between the Alarm Group and the Error Code, where Alarm Group is from rsiAlarmGroupTable and the ErrorCode is from rsiAlarmTable. "
    INDEX           { rsiAlarmGroupId, rsiAlarmErrorCode }
    ::= { rsiAlarmGroupErrorMapTable 1 }

RsiAlarmGroupErrorMapEntry ::=
    SEQUENCE {
        rsiAlarmGroupErrorMapRowStatus  RowStatus
    }

rsiAlarmGroupErrorMapRowStatus OBJECT-TYPE
    SYNTAX          RowStatus
    MAX-ACCESS      read-create
    STATUS          current
    DESCRIPTION     
            "This is for dynamic addition/deletion of Alarm Group Error Map. For creating a new Alarm Group Error Map entry, only 'createAndGo' is supported. For deleting an existing row, 'delete' is supported"
    ::= { rsiAlarmGroupErrorMapEntry 1 }

rsiAlarmDestTable OBJECT-TYPE
    SYNTAX          SEQUENCE OF RsiAlarmDestEntry
    MAX-ACCESS      not-accessible
    STATUS          current
    DESCRIPTION     
            "This table contains the alarm  destination information."
    ::= { rsiCommonMib 38 }

rsiAlarmDestEntry OBJECT-TYPE
    SYNTAX          RsiAlarmDestEntry
    MAX-ACCESS      not-accessible
    STATUS          current
    DESCRIPTION     
            "Description of a Alarm Destination"
    INDEX           { rsiAlarmDestId }
    ::= { rsiAlarmDestTable 1 }

RsiAlarmDestEntry ::=
    SEQUENCE {
        rsiAlarmDestId                  Integer32,
        rsiAlarmDestGroupId             Integer32,
        rsiAlarmDestTODStart            DisplayString,
        rsiAlarmDestTODEnd              DisplayString,
        rsiAlarmDestDOFWeek             DisplayString,
        rsiAlarmDestEntryType           INTEGER,
        rsiAlarmDestType                INTEGER,
        rsiAlarmDest                    DisplayString,
        rsiAlarmDestRowStatus           RowStatus
    }

rsiAlarmDestId OBJECT-TYPE
    SYNTAX          Integer32
    MAX-ACCESS      not-accessible
    STATUS          current
    DESCRIPTION     
            "This is autogenerated Identifier for the Alarm Destination."
    ::= { rsiAlarmDestEntry 1 }

rsiAlarmDestGroupId OBJECT-TYPE
    SYNTAX          Integer32
    MAX-ACCESS      read-create
    STATUS          current
    DESCRIPTION     
            "This is Alarm Group Id."
    ::= { rsiAlarmDestEntry 2 }

rsiAlarmDestTODStart OBJECT-TYPE
    SYNTAX          DisplayString (SIZE(19))
    MAX-ACCESS      read-create
    STATUS          current
    DESCRIPTION     
            "Start time: For exactRule Format is YYYY:MM:DD HH:MM:SS. For dowRule and alldays Format is XXXX:XX:XX HH:MM:SS"
    ::= { rsiAlarmDestEntry 3 }

rsiAlarmDestTODEnd OBJECT-TYPE
    SYNTAX          DisplayString (SIZE(19))
    MAX-ACCESS      read-create
    STATUS          current
    DESCRIPTION     
            "End time: For exactRule Format is YYYY:MM:DD HH:MM:SS. For dowRule and alldays Format is XXXX:XX:XX HH:MM:SS"
    ::= { rsiAlarmDestEntry 4 }

rsiAlarmDestDOFWeek OBJECT-TYPE
    SYNTAX          DisplayString
    MAX-ACCESS      read-create
    STATUS          current
    DESCRIPTION     
            "This is a hexadecimal bit mask field depending on the day of the week. The bit mask is as per the rule ALL 0x0, MON 0x0001, TUE 0x0002, WED 0x0004, THU 0x0008, FRI 0x0010, SAT 0x0020, SUN 0x0040"
    ::= { rsiAlarmDestEntry 5 }

rsiAlarmDestEntryType OBJECT-TYPE
    SYNTAX          INTEGER { exactRule(0), dowRule(1), alldays(2) }
    MAX-ACCESS      read-create
    STATUS          current
    DESCRIPTION     
            "This is entry type of the rule.exactRule is on the basis of exact timing,dowRule is on the basis of day of week and time of the day and alldays is on the basis of time of the day for all days."
    ::= { rsiAlarmDestEntry 6 }

rsiAlarmDestType OBJECT-TYPE
    SYNTAX          INTEGER { snmpTrap(0), smtpMail(1) }
    MAX-ACCESS      read-create
    STATUS          current
    DESCRIPTION     
            "This is Destination Type for the alarm."
    ::= { rsiAlarmDestEntry 7 }

rsiAlarmDest OBJECT-TYPE
    SYNTAX          DisplayString
    MAX-ACCESS      read-create
    STATUS          current
    DESCRIPTION     
            "This is the alarm destination.For SNMP Trap it will be a IP Address and for SMTP Mail it will be a Mail Id."
    ::= { rsiAlarmDestEntry 8 }

rsiAlarmDestRowStatus OBJECT-TYPE
    SYNTAX          RowStatus
    MAX-ACCESS      read-create
    STATUS          current
    DESCRIPTION     
            "."
    ::= { rsiAlarmDestEntry 10 }

rsiInventoryProductRepositoryTable OBJECT-TYPE
    SYNTAX          SEQUENCE OF RsiInventoryProductRepositoryEntry
    MAX-ACCESS      not-accessible
    STATUS          current
    DESCRIPTION     
            "This table contains the information of the products which are there in the repository."
    ::= { rsiCommonMib 39 }

rsiInventoryProductRepositoryEntry OBJECT-TYPE
    SYNTAX          RsiInventoryProductRepositoryEntry
    MAX-ACCESS      not-accessible
    STATUS          current
    DESCRIPTION     
            "Description of a product entry in the repository"
    INDEX           { rsiProductId, rsiProductVersion, rsiSystemType }
    ::= { rsiInventoryProductRepositoryTable 1 }

RsiInventoryProductRepositoryEntry ::=
    SEQUENCE {
        rsiProductId                    DisplayString,
        rsiProductVersion               DisplayString,
        rsiSystemType                   Integer32,
        rsiProductName                  DisplayString,
        rsiProductCLEICode              DisplayString,
        rsiProductAcceptanceDate        DisplayString,
        rsiProductWarrantyPeriod        Integer32,
        rsiProductExpiryDate            DisplayString,
        rsiProductLicenseKey            DisplayString,
        rsiProductVendor                DisplayString,
        rsiProductState                 Integer32,
        rsiProductDescription           DisplayString,
        rsiProductBinaryPath            DisplayString,
        rsiProductBinaryType            Integer32,
        rsiInventoryProductRepositoryRowStatus      RowStatus
    }

rsiProductId OBJECT-TYPE
    SYNTAX          DisplayString
    MAX-ACCESS      read-create
    STATUS          current
    DESCRIPTION     
            "The Product identifier."
    ::= { rsiInventoryProductRepositoryEntry 1 }

rsiProductVersion OBJECT-TYPE
    SYNTAX          DisplayString
    MAX-ACCESS      read-create
    STATUS          current
    DESCRIPTION     
            "The Product Version."
    ::= { rsiInventoryProductRepositoryEntry 2 }

rsiSystemType OBJECT-TYPE
    SYNTAX          Integer32
    MAX-ACCESS      read-create
    STATUS          current
    DESCRIPTION     
            "Type of the System."
    ::= { rsiInventoryProductRepositoryEntry 3 }

rsiProductName OBJECT-TYPE
    SYNTAX          DisplayString
    MAX-ACCESS      read-create
    STATUS          current
    DESCRIPTION     
            "Name of the Product."
    ::= { rsiInventoryProductRepositoryEntry 4 }

rsiProductCLEICode OBJECT-TYPE
    SYNTAX          DisplayString
    MAX-ACCESS      read-create
    STATUS          current
    DESCRIPTION     
            "CLEI code for the Product."
    ::= { rsiInventoryProductRepositoryEntry 5 }

rsiProductAcceptanceDate OBJECT-TYPE
    SYNTAX          DisplayString (SIZE(19))
    MAX-ACCESS      read-create
    STATUS          current
    DESCRIPTION     
            "Acceptance date by the user. Format YYYY:MM:DD HH:MM:SS"
    ::= { rsiInventoryProductRepositoryEntry 6 }

rsiProductWarrantyPeriod OBJECT-TYPE
    SYNTAX          Integer32
    MAX-ACCESS      read-create
    STATUS          current
    DESCRIPTION     
            "Warranty Period Given to the User."
    ::= { rsiInventoryProductRepositoryEntry 7 }

rsiProductExpiryDate OBJECT-TYPE
    SYNTAX          DisplayString (SIZE(19))
    MAX-ACCESS      read-create
    STATUS          current
    DESCRIPTION     
            "Expiry date of the Product. Format YYYY:MM:DD HH:MM:SS"
    ::= { rsiInventoryProductRepositoryEntry 8 }

rsiProductLicenseKey OBJECT-TYPE
    SYNTAX          DisplayString
    MAX-ACCESS      read-create
    STATUS          current
    DESCRIPTION     
            "License key for the Product. This is now depricated and any request to fetch it will return NONE and any request to set it will fail."
    ::= { rsiInventoryProductRepositoryEntry 9 }

rsiProductVendor OBJECT-TYPE
    SYNTAX          DisplayString
    MAX-ACCESS      read-create
    STATUS          current
    DESCRIPTION     
            "Name of the Product vendor."
    ::= { rsiInventoryProductRepositoryEntry 10 }

rsiProductState OBJECT-TYPE
    SYNTAX          Integer32
    MAX-ACCESS      read-create
    STATUS          current
    DESCRIPTION     
            "State of the Product."
    ::= { rsiInventoryProductRepositoryEntry 11 }

rsiProductDescription OBJECT-TYPE
    SYNTAX          DisplayString
    MAX-ACCESS      read-create
    STATUS          current
    DESCRIPTION     
            "Description of the Product."
    ::= { rsiInventoryProductRepositoryEntry 12 }

rsiProductBinaryPath OBJECT-TYPE
    SYNTAX          DisplayString
    MAX-ACCESS      read-create
    STATUS          current
    DESCRIPTION     
            "Path where the Product binary is kept."
    ::= { rsiInventoryProductRepositoryEntry 13 }

rsiProductBinaryType OBJECT-TYPE
    SYNTAX          Integer32
    MAX-ACCESS      read-create
    STATUS          current
    DESCRIPTION     
            "Type of binary."
    ::= { rsiInventoryProductRepositoryEntry 14 }

rsiInventoryProductRepositoryRowStatus OBJECT-TYPE
    SYNTAX          RowStatus
    MAX-ACCESS      read-create
    STATUS          current
    DESCRIPTION     
            "This is for dynamic addition/deletion of Products in the inventory. For creating a new Products entry in the inventory, only 'createAndGo' is supported. For deleting an existing row, 'delete' is supported."
    ::= { rsiInventoryProductRepositoryEntry 15 }

rsiInventoryInstalledProductTable OBJECT-TYPE
    SYNTAX          SEQUENCE OF RsiInventoryInstalledProductEntry
    MAX-ACCESS      not-accessible
    STATUS          current
    DESCRIPTION     
            "This table contains the information of the products which are installed somewhere in the domain, the rsiProductId, rsiProductVersion, rsiSystemType are taken from the rsiInventoryProductRepositoryTable."
    ::= { rsiCommonMib 40 }

rsiInventoryInstalledProductEntry OBJECT-TYPE
    SYNTAX          RsiInventoryInstalledProductEntry
    MAX-ACCESS      not-accessible
    STATUS          current
    DESCRIPTION     
            "Description of a product entry installed in the domain"
    INDEX           { rsiProductId, rsiProductVersion, rsiSystemType, 
                      rsiClusterId }
    ::= { rsiInventoryInstalledProductTable 1 }

RsiInventoryInstalledProductEntry ::=
    SEQUENCE {
        rsiClusterId                    Integer32,
        rsiInsSystemId                  Integer32,
        rsiInstallTime                  DisplayString,
        rsiInstallRoot                  DisplayString
    }

rsiClusterId OBJECT-TYPE
    SYNTAX          Integer32
    MAX-ACCESS      read-only
    STATUS          current
    DESCRIPTION     
            "Cluster in which the product is installed."
    ::= { rsiInventoryInstalledProductEntry 1 }

rsiInsSystemId OBJECT-TYPE
    SYNTAX          Integer32
    MAX-ACCESS      read-only
    STATUS          current
    DESCRIPTION     
            "System ID in which the product is installed."
    ::= { rsiInventoryInstalledProductEntry 2 }

rsiInstallTime OBJECT-TYPE
    SYNTAX          DisplayString (SIZE(19))
    MAX-ACCESS      read-only
    STATUS          current
    DESCRIPTION     
            "Time at which the product is installed. Format is YYYY:MM:DD HH:MM:SS"
    ::= { rsiInventoryInstalledProductEntry 3 }

rsiInstallRoot OBJECT-TYPE
    SYNTAX          DisplayString
    MAX-ACCESS      read-only
    STATUS          current
    DESCRIPTION     
            "Location where the product is installed"
    ::= { rsiInventoryInstalledProductEntry 4 }

rsiInventoryHostDetailTable OBJECT-TYPE
    SYNTAX          SEQUENCE OF RsiInventoryHostDetailEntry
    MAX-ACCESS      not-accessible
    STATUS          current
    DESCRIPTION     
            "This table contains the information of the hosts present in the domain."
    ::= { rsiCommonMib 41 }

rsiInventoryHostDetailEntry OBJECT-TYPE
    SYNTAX          RsiInventoryHostDetailEntry
    MAX-ACCESS      not-accessible
    STATUS          current
    DESCRIPTION     
            "Description of the hosts installed in the domain"
    INDEX           { rsiHostId, rsiHostAttribName }
    ::= { rsiInventoryHostDetailTable 1 }

RsiInventoryHostDetailEntry ::=
    SEQUENCE {
        rsiHostId                       Integer32,
        rsiHostAttribName               DisplayString,
        rsiHostAttribValue              DisplayString
    }

rsiHostId OBJECT-TYPE
    SYNTAX          Integer32
    MAX-ACCESS      read-only
    STATUS          current
    DESCRIPTION     
            "Identifier of the host installed in the domain."
    ::= { rsiInventoryHostDetailEntry 1 }

rsiHostAttribName OBJECT-TYPE
    SYNTAX          DisplayString
    MAX-ACCESS      read-only
    STATUS          current
    DESCRIPTION     
            "Name of the Attribute."
    ::= { rsiInventoryHostDetailEntry 2 }

rsiHostAttribValue OBJECT-TYPE
    SYNTAX          DisplayString
    MAX-ACCESS      read-write
    STATUS          current
    DESCRIPTION     
            "Value of the Attribute.Value for 'state' attribute can be 0-3 only.
             0 is for 'In Service',1 for 'Out Of Service',2 for 'Manually Out Of Service'
             and 3 for 'Unit Under Test'."
    ::= { rsiInventoryHostDetailEntry 3 }

rsiInventoryInstalledModulesTable OBJECT-TYPE
    SYNTAX          SEQUENCE OF RsiInventoryInstalledModulesEntry
    MAX-ACCESS      not-accessible
    STATUS          current
    DESCRIPTION     
            "This table contains the information of the installed modules. The rsiProductId, rsiProductVersion, rsiSystemType are taken from the rsiInventoryProductRepositoryTable, rsiSystemId from rsiSystemTable and rsiSubsystemId from rsiSubsystemTable."
    ::= { rsiCommonMib 42 }

rsiInventoryInstalledModulesEntry OBJECT-TYPE
    SYNTAX          RsiInventoryInstalledModulesEntry
    MAX-ACCESS      not-accessible
    STATUS          current
    DESCRIPTION     
            "Description of an installed module."
    INDEX           { rsiProductId, rsiProductVersion, rsiSystemType, 
                      rsiClusterId, rsiSystemId, rsiSubsystemId }
    ::= { rsiInventoryInstalledModulesTable 1 }

RsiInventoryInstalledModulesEntry ::=
    SEQUENCE {
        rsiInvModuleName                DisplayString,
        rsiInvModuleHostId              Integer32,
        rsiInvModuleStatus              Integer32,
        rsiInvModuleVersion             DisplayString,
        rsiInvModuleThirdPartyFlag      Integer32
    }

rsiInvModuleName OBJECT-TYPE
    SYNTAX          DisplayString
    MAX-ACCESS      read-only
    STATUS          current
    DESCRIPTION     
            "The Name of the Module."
    ::= { rsiInventoryInstalledModulesEntry 1 }

rsiInvModuleHostId OBJECT-TYPE
    SYNTAX          Integer32
    MAX-ACCESS      read-only
    STATUS          current
    DESCRIPTION     
            "The identifier of the host on which the Module is installed."
    ::= { rsiInventoryInstalledModulesEntry 2 }

rsiInvModuleStatus OBJECT-TYPE
    SYNTAX          Integer32
    MAX-ACCESS      read-only
    STATUS          current
    DESCRIPTION     
            "The Status of the Module."
    ::= { rsiInventoryInstalledModulesEntry 3 }

rsiInvModuleVersion OBJECT-TYPE
    SYNTAX          DisplayString
    MAX-ACCESS      read-only
    STATUS          current
    DESCRIPTION     
            "Version of the Module."
    ::= { rsiInventoryInstalledModulesEntry 4 }

rsiInvModuleThirdPartyFlag OBJECT-TYPE
    SYNTAX          Integer32
    MAX-ACCESS      read-only
    STATUS          current
    DESCRIPTION     
            "If it is a Third Party Module."
    ::= { rsiInventoryInstalledModulesEntry 5 }

rsiInventoryInstalledServicesTable OBJECT-TYPE
    SYNTAX          SEQUENCE OF RsiInventoryInstalledServicesEntry
    MAX-ACCESS      not-accessible
    STATUS          current
    DESCRIPTION     
            "This table contains the information of the installed services. The rsiProductId, rsiProductVersion, rsiSystemType are taken from the rsiInventoryProductRepositoryTable, rsiSystemId from rsiSystemTable and rsiSubsystemId from rsiSubsystemTable."
    ::= { rsiCommonMib 43 }

rsiInventoryInstalledServicesEntry OBJECT-TYPE
    SYNTAX          RsiInventoryInstalledServicesEntry
    MAX-ACCESS      not-accessible
    STATUS          current
    DESCRIPTION     
            "Description of an installed service."
    INDEX           { rsiProductId, rsiProductVersion, rsiSystemType, 
                      rsiClusterId, rsiSystemId, rsiSubsystemId, 
                      rsiSubcomponentId }
    ::= { rsiInventoryInstalledServicesTable 1 }

RsiInventoryInstalledServicesEntry ::=
    SEQUENCE {
        rsiSubcomponentId               Integer32,
        rsiInvServiceName               DisplayString,
        rsiInvServiceHostId             Integer32,
        rsiInvServiceAdminStatus        INTEGER,
        rsiInvServiceOperStatus         INTEGER,
        rsiInvServiceVersion            DisplayString,
        rsiInvServiceThirdPartyFlag     Integer32
    }

rsiSubcomponentId OBJECT-TYPE
    SYNTAX          Integer32
    MAX-ACCESS      read-only
    STATUS          current
    DESCRIPTION     
            "Identifier of the subcomponent to which the service belongs."
    ::= { rsiInventoryInstalledServicesEntry 1 }

rsiInvServiceName OBJECT-TYPE
    SYNTAX          DisplayString
    MAX-ACCESS      read-only
    STATUS          current
    DESCRIPTION     
            "Name of the Service."
    ::= { rsiInventoryInstalledServicesEntry 2 }

rsiInvServiceHostId OBJECT-TYPE
    SYNTAX          Integer32
    MAX-ACCESS      read-only
    STATUS          current
    DESCRIPTION     
            "Identifier of the subcomponent to which the service belongs."
    ::= { rsiInventoryInstalledServicesEntry 3 }

rsiInvServiceAdminStatus OBJECT-TYPE
    SYNTAX          INTEGER { installed(0), ready(1), active(2) }
    MAX-ACCESS      read-write
    STATUS          current
    DESCRIPTION     
            "Admin Status of the Service. transition from installed to ready is equivalent to startService; transition from Active to ready is equivalent to deactivateService; Direct transition from  installed to active not allowed abd vice-versa, transition from ready to active is equivalent to activateService; transition from ready to installed is equivalent to stopService"
    ::= { rsiInventoryInstalledServicesEntry 4 }

rsiInvServiceOperStatus OBJECT-TYPE
    SYNTAX          INTEGER { installed(0), ready(1), active(2) }
    MAX-ACCESS      read-only
    STATUS          current
    DESCRIPTION     
            "Oper Status of the Service."
    ::= { rsiInventoryInstalledServicesEntry 5 }

rsiInvServiceVersion OBJECT-TYPE
    SYNTAX          DisplayString
    MAX-ACCESS      read-only
    STATUS          current
    DESCRIPTION     
            "Version of the Service."
    ::= { rsiInventoryInstalledServicesEntry 6 }

rsiInvServiceThirdPartyFlag OBJECT-TYPE
    SYNTAX          Integer32
    MAX-ACCESS      read-only
    STATUS          current
    DESCRIPTION     
            "If the service is a third party service."
    ::= { rsiInventoryInstalledServicesEntry 7 }

rsiInventoryCardDetailTable OBJECT-TYPE
    SYNTAX          SEQUENCE OF RsiInventoryCardDetailEntry
    MAX-ACCESS      not-accessible
    STATUS          current
    DESCRIPTION     
            "This table contains the information of the cards present in the domain. rsiCardHostId is from table rsiInventoryHostDetailTable"
    ::= { rsiCommonMib 44 }

rsiInventoryCardDetailEntry OBJECT-TYPE
    SYNTAX          RsiInventoryCardDetailEntry
    MAX-ACCESS      not-accessible
    STATUS          current
    DESCRIPTION     
            "Description of the cards installed in the domain"
    INDEX           { rsiCardId, rsiCardAttribName }
    ::= { rsiInventoryCardDetailTable 1 }

RsiInventoryCardDetailEntry ::=
    SEQUENCE {
        rsiCardHostId                   Integer32,
        rsiCardId                       Integer32,
        rsiCardAttribName               DisplayString,
        rsiCardAttribValue              DisplayString
    }

rsiCardHostId OBJECT-TYPE
    SYNTAX          Integer32
    MAX-ACCESS      read-write
    STATUS          current
    DESCRIPTION     
            "Identifier of the host on which the card is installed."
    ::= { rsiInventoryCardDetailEntry 1 }

rsiCardId OBJECT-TYPE
    SYNTAX          Integer32
    MAX-ACCESS      read-only
    STATUS          current
    DESCRIPTION     
            "Identifier of the card installed in the domain."
    ::= { rsiInventoryCardDetailEntry 2 }

rsiCardAttribName OBJECT-TYPE
    SYNTAX          DisplayString
    MAX-ACCESS      read-only
    STATUS          current
    DESCRIPTION     
            "Name of the Attribute."
    ::= { rsiInventoryCardDetailEntry 3 }

rsiCardAttribValue OBJECT-TYPE
    SYNTAX          DisplayString
    MAX-ACCESS      read-write
    STATUS          current
    DESCRIPTION     
            "Value of the Attribute.Value for 'state' attribute can be 0-3 only.
             0 is for 'In Service',1 for 'Out Of Service',2 for 'Manually Out Of Service'
             and 3 for 'Unit Under Test'."
    ::= { rsiInventoryCardDetailEntry 4 }

rsiInventoryHwHistoryTable OBJECT-TYPE
    SYNTAX          SEQUENCE OF RsiInventoryHwHistoryEntry
    MAX-ACCESS      not-accessible
    STATUS          current
    DESCRIPTION     
            "This table contains the history of all the hardware, whether it be a card or a host"
    ::= { rsiCommonMib 45 }

rsiInventoryHwHistoryEntry OBJECT-TYPE
    SYNTAX          RsiInventoryHwHistoryEntry
    MAX-ACCESS      not-accessible
    STATUS          current
    DESCRIPTION     
            "Description of the HOST/CARD modification in the Domain"
    INDEX           { rsiHostCardFlag, rsiHwId, rsiHwModificationTime, 
                      rsiHwSeqNum }
    ::= { rsiInventoryHwHistoryTable 1 }

RsiInventoryHwHistoryEntry ::=
    SEQUENCE {
        rsiHostCardFlag                 INTEGER,
        rsiHwId                         Integer32,
        rsiHwSeqNum                     Integer32,
        rsiHwState                      INTEGER,
        rsiHwModificationTime           DisplayString,
        rsiHwHistLog                    DisplayString
    }

rsiHostCardFlag OBJECT-TYPE
    SYNTAX          INTEGER { card(1), host(2) }
    MAX-ACCESS      read-only
    STATUS          current
    DESCRIPTION     
            "Shows if the entry represents a CARD or a HOST."
    ::= { rsiInventoryHwHistoryEntry 1 }

rsiHwId OBJECT-TYPE
    SYNTAX          Integer32
    MAX-ACCESS      read-only
    STATUS          current
    DESCRIPTION     
            "Identifier of the CARD or the HOST depending on rsiHostCardFlag."
    ::= { rsiInventoryHwHistoryEntry 2 }

rsiHwSeqNum OBJECT-TYPE
    SYNTAX          Integer32
    MAX-ACCESS      read-only
    STATUS          current
    DESCRIPTION     
            "Sequence number to differentiate entries made at the same time."
    ::= { rsiInventoryHwHistoryEntry 3 }

rsiHwState OBJECT-TYPE
    SYNTAX          INTEGER { inService(0), outOfService(1), 
                        manuallyOutOfService(2), unitUnderTest(3) }
    MAX-ACCESS      read-only
    STATUS          current
    DESCRIPTION     
            "State of the hardware unit."
    ::= { rsiInventoryHwHistoryEntry 4 }

rsiHwModificationTime OBJECT-TYPE
    SYNTAX          DisplayString (SIZE(19))
    MAX-ACCESS      read-only
    STATUS          current
    DESCRIPTION     
            "Time at which the modification is made to the hardware unit. Format is YYYY:MM:DD HH:MM:SS."
    ::= { rsiInventoryHwHistoryEntry 5 }

rsiHwHistLog OBJECT-TYPE
    SYNTAX          DisplayString
    MAX-ACCESS      read-only
    STATUS          current
    DESCRIPTION     
            " Description of the change."
    ::= { rsiInventoryHwHistoryEntry 6 }

rsiInventorySwHistoryTable OBJECT-TYPE
    SYNTAX          SEQUENCE OF RsiInventorySwHistoryEntry
    MAX-ACCESS      not-accessible
    STATUS          current
    DESCRIPTION     
            "This table contains the history of all the hardware, whether it be a card or a host"
    ::= { rsiCommonMib 46 }

rsiInventorySwHistoryEntry OBJECT-TYPE
    SYNTAX          RsiInventorySwHistoryEntry
    MAX-ACCESS      not-accessible
    STATUS          current
    DESCRIPTION     
            "Description of the HOST/CARD modification in the Domain"
    INDEX           { rsiModuleServiceFlag, rsiProductId, 
                      rsiProductVersion, rsiSystemType, rsiClusterId, 
                      rsiSystemId, rsiSubsystemId, rsiSubcomponentId, 
                      rsiSwModificationTime, rsiSwSeqNum }
    ::= { rsiInventorySwHistoryTable 1 }

RsiInventorySwHistoryEntry ::=
    SEQUENCE {
        rsiModuleServiceFlag            INTEGER,
        rsiSwSeqNum                     Integer32,
        rsiHistHostId                   Integer32,
        rsiSwState                      Integer32,
        rsiSwModificationTime           DisplayString,
        rsiSwHistLog                    DisplayString
    }

rsiModuleServiceFlag OBJECT-TYPE
    SYNTAX          INTEGER { module(3), service(4), installedProduct(5), 
                        repositoryProduct(6) }
    MAX-ACCESS      read-only
    STATUS          current
    DESCRIPTION     
            "Shows if the entry represents a MODULE, SERVICE or a PRODUCT."
    ::= { rsiInventorySwHistoryEntry 1 }

rsiSwSeqNum OBJECT-TYPE
    SYNTAX          Integer32
    MAX-ACCESS      read-only
    STATUS          current
    DESCRIPTION     
            "Sequence number to differentiate entries made at the same time."
    ::= { rsiInventorySwHistoryEntry 2 }

rsiHistHostId OBJECT-TYPE
    SYNTAX          Integer32
    MAX-ACCESS      read-only
    STATUS          current
    DESCRIPTION     
            "Identifier of the HOST over which the MODULE, SERVICE or the PRODUCT is installed."
    ::= { rsiInventorySwHistoryEntry 3 }

rsiSwState OBJECT-TYPE
    SYNTAX          Integer32
    MAX-ACCESS      read-only
    STATUS          current
    DESCRIPTION     
            "State of the Software unit."
    ::= { rsiInventorySwHistoryEntry 4 }

rsiSwModificationTime OBJECT-TYPE
    SYNTAX          DisplayString (SIZE(19))
    MAX-ACCESS      read-only
    STATUS          current
    DESCRIPTION     
            "Time at which the modification is made to the Software unit. Format is YYYY:MM:DD HH:MM:SS."
    ::= { rsiInventorySwHistoryEntry 5 }

rsiSwHistLog OBJECT-TYPE
    SYNTAX          DisplayString
    MAX-ACCESS      read-only
    STATUS          current
    DESCRIPTION     
            " Description of the change."
    ::= { rsiInventorySwHistoryEntry 6 }

rsiTODRuleTable OBJECT-TYPE
    SYNTAX          SEQUENCE OF RsiTODRuleEntry
    MAX-ACCESS      not-accessible
    STATUS          current
    DESCRIPTION     
            "This table contains the rules for system access depending upon the time of the day"
    ::= { rsiCommonMib 47 }

rsiTODRuleEntry OBJECT-TYPE
    SYNTAX          RsiTODRuleEntry
    MAX-ACCESS      not-accessible
    STATUS          current
    DESCRIPTION     
            "Description of the rules for system access depending upon the time of the day"
    INDEX           { rsiRuleName }
    ::= { rsiTODRuleTable 1 }

RsiTODRuleEntry ::=
    SEQUENCE {
        rsiRuleName                     DisplayString,
        rsiRuleId                       Integer32,
        rsiRuleType                     INTEGER,
        rsiStartTime                    DisplayString,
        rsiEndTime                      DisplayString,
        rsiDOW                          DisplayString,
        rsiTODRuleRowStatus             RowStatus
    }

rsiRuleName OBJECT-TYPE
    SYNTAX          DisplayString
    MAX-ACCESS      read-create
    STATUS          current
    DESCRIPTION     
            "Name for the Rule."
    ::= { rsiTODRuleEntry 1 }

rsiRuleId OBJECT-TYPE
    SYNTAX          Integer32
    MAX-ACCESS      read-only
    STATUS          current
    DESCRIPTION     
            "Autogenerated Identifier for the Rule."
    ::= { rsiTODRuleEntry 2 }

rsiRuleType OBJECT-TYPE
    SYNTAX          INTEGER { exactRule(0), dowRule(1), alldays(2) }
    MAX-ACCESS      read-create
    STATUS          current
    DESCRIPTION     
            "Type of the rule. exactRule is on the basis of exact timing and the dowRule is on the basis of day of week and depend on the time of the day. And alldays depend on the time of the day only."
    ::= { rsiTODRuleEntry 3 }

rsiStartTime OBJECT-TYPE
    SYNTAX          DisplayString (SIZE(19))
    MAX-ACCESS      read-create
    STATUS          current
    DESCRIPTION     
            "Start time: For exactRule Format is YYYY:MM:DD HH:MM:SS. For dowRule and alldays Format is XXXX:XX:XX HH:MM:SS"
    ::= { rsiTODRuleEntry 4 }

rsiEndTime OBJECT-TYPE
    SYNTAX          DisplayString (SIZE(19))
    MAX-ACCESS      read-create
    STATUS          current
    DESCRIPTION     
            "End time: For exactRule Format is YYYY:MM:DD HH:MM:SS. For dowRule and alldays Format is XXXX:XX:XX HH:MM:SS"
    ::= { rsiTODRuleEntry 5 }

rsiDOW OBJECT-TYPE
    SYNTAX          DisplayString
    MAX-ACCESS      read-create
    STATUS          current
    DESCRIPTION     
            " This is a hexadecimal bit mask field depending on the day of the week. The bit mask is as per the rule ALL 0x0, MON 0x0001, TUE 0x0002, WED 0x0004, THU 0x0008, FRI 0x0010, SAT 0x0020, SUN 0x0040"
    ::= { rsiTODRuleEntry 6 }

rsiTODRuleRowStatus OBJECT-TYPE
    SYNTAX          RowStatus
    MAX-ACCESS      read-create
    STATUS          current
    DESCRIPTION     
            "This is for dynamic addition/deletion of TOD Rules.
             For creating a new TOD Rules, only 'createAndGo' is
             supported. For deleting an existing row, 'delete'
             is supported"
    ::= { rsiTODRuleEntry 7 }

rsiUserRoleTODRuleTable OBJECT-TYPE
    SYNTAX          SEQUENCE OF RsiUserRoleTODRuleEntry
    MAX-ACCESS      not-accessible
    STATUS          current
    DESCRIPTION     
            "This table contains the mapping of the User, his role and the rules for system access depending upon the time of the day. rsiUserId id from the table rsiUserTable rsiRoleId is from the table rsiRoleId and rsiRuleId is from the table rsiTODRuleTable"
    ::= { rsiCommonMib 48 }

rsiUserRoleTODRuleEntry OBJECT-TYPE
    SYNTAX          RsiUserRoleTODRuleEntry
    MAX-ACCESS      not-accessible
    STATUS          current
    DESCRIPTION     
            "Description of the mapping of the User, his role and the rules for system access depending upon the time of the day"
    INDEX           { rsiUserId, rsiRoleId, rsiRuleId }
    ::= { rsiUserRoleTODRuleTable 1 }

RsiUserRoleTODRuleEntry ::=
    SEQUENCE {
        rsiUserRoleTODRuleRowStatus     RowStatus
    }

rsiUserRoleTODRuleRowStatus OBJECT-TYPE
    SYNTAX          RowStatus
    MAX-ACCESS      read-create
    STATUS          current
    DESCRIPTION     
            "This is for dynamic addition/deletion of the mapping of TOD Rules with the User and his role.
             For creating a new TOD Rules, only 'createAndGo' is
             supported. For deleting an existing row, 'delete'
             is supported"
    ::= { rsiUserRoleTODRuleEntry 1 }

rsiServiceStateTable OBJECT-TYPE
    SYNTAX          SEQUENCE OF RsiServiceStateEntry
    MAX-ACCESS      not-accessible
    STATUS          current
    DESCRIPTION     
            "This table contains the information of different services on different subsystems."
    ::= { rsiCommonMib 51 }

rsiServiceStateEntry OBJECT-TYPE
    SYNTAX          RsiServiceStateEntry
    MAX-ACCESS      not-accessible
    STATUS          current
    DESCRIPTION     
            "Description of an installed service on a particular subsystem."
    INDEX           { rsiServiceID, rsiServiceVer, rsiSystemID }
    ::= { rsiServiceStateTable 1 }

RsiServiceStateEntry ::=
    SEQUENCE {
        rsiServiceID                    DisplayString,
        rsiServiceVer                   DisplayString,
        rsiSystemID                     Integer32,
        rsiSubsystemID                  Integer32,
        rsiServiceAdminStatus           INTEGER,
        rsiServiceOperStatus            INTEGER,
        rsiServiceStatusOnSubsys        Integer32
    }

rsiServiceID OBJECT-TYPE
    SYNTAX          DisplayString
    MAX-ACCESS      read-only
    STATUS          current
    DESCRIPTION     
            "The Product identifier."
    ::= { rsiServiceStateEntry 1 }

rsiServiceVer OBJECT-TYPE
    SYNTAX          DisplayString
    MAX-ACCESS      read-only
    STATUS          current
    DESCRIPTION     
            "The Product Version."
    ::= { rsiServiceStateEntry 2 }

rsiSystemID OBJECT-TYPE
    SYNTAX          Integer32
    MAX-ACCESS      read-only
    STATUS          current
    DESCRIPTION     
            "System on which the service is deployed."
    ::= { rsiServiceStateEntry 3 }

rsiSubsystemID OBJECT-TYPE
    SYNTAX          Integer32
    MAX-ACCESS      read-only
    STATUS          current
    DESCRIPTION     
            "Subsystem on which the status of the service is maintained."
    ::= { rsiServiceStateEntry 4 }

rsiServiceAdminStatus OBJECT-TYPE
    SYNTAX          INTEGER { installed(0), ready(1), active(2) }
    MAX-ACCESS      read-only
    STATUS          current
    DESCRIPTION     
            "Admin Status of the Service."
    ::= { rsiServiceStateEntry 5 }

rsiServiceOperStatus OBJECT-TYPE
    SYNTAX          INTEGER { installed(0), ready(1), active(2) }
    MAX-ACCESS      read-only
    STATUS          current
    DESCRIPTION     
            "Oper Status of the Service."
    ::= { rsiServiceStateEntry 6 }

rsiServiceStatusOnSubsys OBJECT-TYPE
    SYNTAX          Integer32
    MAX-ACCESS      read-only
    STATUS          current
    DESCRIPTION     
            "Status of the servie on that particular subsystem."
    ::= { rsiServiceStateEntry 7 }

rsiMeasurementCounterTable OBJECT-TYPE
    SYNTAX          SEQUENCE OF RsiMeasurementCounterEntry
    MAX-ACCESS      not-accessible
    STATUS          current
    DESCRIPTION     
            "This table contains the information of different measurement 
             counters on different subsystems.It contains rsiSubsystemID 
             from rsiSubsystemTable."
    ::= { rsiCommonMib 52 }

rsiMeasurementCounterEntry OBJECT-TYPE
    SYNTAX          RsiMeasurementCounterEntry
    MAX-ACCESS      not-accessible
    STATUS          current
    DESCRIPTION     
            "Description of a measurement counter of a particular subsystem."
    INDEX           { rsiSubsystemId, rsiMeasurementCounterID }
    ::= { rsiMeasurementCounterTable 1 }

RsiMeasurementCounterEntry ::=
    SEQUENCE {
        rsiMeasurementCounterID         DisplayString,
        rsiMeasurementCounterRefType    INTEGER,
        rsiMeasurementCounterType       INTEGER,
        rsiMeasurementCounterMeasMode   INTEGER,
        rsiMeasurementCounterScanInterval Integer32,
        rsiMeasurementCounterOid        DisplayString,
        rsiMeasurementCounterEnable     INTEGER
    }

rsiMeasurementCounterID OBJECT-TYPE
    SYNTAX          DisplayString
    MAX-ACCESS      read-only
    STATUS          current
    DESCRIPTION     
            "Measurement Counter Identifier"
    ::= { rsiMeasurementCounterEntry 1 }

rsiMeasurementCounterRefType OBJECT-TYPE
    SYNTAX          INTEGER { name(0), index(1) }
    MAX-ACCESS      read-only
    STATUS          current
    DESCRIPTION     
            "Measurement Counter Reference Type.If the reference type 
             is 'name' then the platform shall enable the measurement 
             values to be referenced by measurement value names else
             by index."
    ::= { rsiMeasurementCounterEntry 2 }

rsiMeasurementCounterType OBJECT-TYPE
    SYNTAX          INTEGER { inconly(0), incdec(1) }
    MAX-ACCESS      read-only
    STATUS          current
    DESCRIPTION     
            "Measurement Counter Type.'inconly' specifies that this counter 
             will increment only and 'incdec' specifies that this counter can
             increment and decrement both."
    ::= { rsiMeasurementCounterEntry 3 }

rsiMeasurementCounterMeasMode OBJECT-TYPE
    SYNTAX          INTEGER { event(0), usage(1), instantaneous(2) }
    MAX-ACCESS      read-only
    STATUS          current
    DESCRIPTION     
            "This identifies the mode of a particular counter.The 
             possible values are event, usage and instantaneous."
    ::= { rsiMeasurementCounterEntry 4 }

rsiMeasurementCounterScanInterval OBJECT-TYPE
    SYNTAX          Integer32
    MAX-ACCESS      read-only
    STATUS          current
    DESCRIPTION     
            "Measurement Counter Scan Interval"
    ::= { rsiMeasurementCounterEntry 5 }

rsiMeasurementCounterOid OBJECT-TYPE
    SYNTAX          DisplayString
    MAX-ACCESS      read-only
    STATUS          current
    DESCRIPTION     
            "Measurement Counter Oid"
    ::= { rsiMeasurementCounterEntry 6 }

rsiMeasurementCounterEnable OBJECT-TYPE
    SYNTAX          INTEGER { false(0), true(1) }
    MAX-ACCESS      read-only
    STATUS          current
    DESCRIPTION     
            "It specifies whether a particular Measurement Counter 
             is enable or disable"
    ::= { rsiMeasurementCounterEntry 7 }

rsiMeasurementSetBaseTable OBJECT-TYPE
    SYNTAX          SEQUENCE OF RsiMeasurementSetBaseEntry
    MAX-ACCESS      not-accessible
    STATUS          current
    DESCRIPTION     
            "This table contains the basic information of different measurement sets."
    ::= { rsiCommonMib 53 }

rsiMeasurementSetBaseEntry OBJECT-TYPE
    SYNTAX          RsiMeasurementSetBaseEntry
    MAX-ACCESS      not-accessible
    STATUS          current
    DESCRIPTION     
            "Description of a measurement set."
    INDEX           { rsiMeasurementSetID, rsiMeasurementSetVersionId }
    ::= { rsiMeasurementSetBaseTable 1 }

RsiMeasurementSetBaseEntry ::=
    SEQUENCE {
        rsiMeasurementSetID             DisplayString,
        rsiMeasurementSetVersionId      DisplayString,
        rsiMeasurementSetAccuInterval   Integer32,
        rsiMeasurementSetBaseRowStatus  RowStatus
    }

rsiMeasurementSetID OBJECT-TYPE
    SYNTAX          DisplayString
    MAX-ACCESS      read-create
    STATUS          current
    DESCRIPTION     
            "Measurement Set Identifier"
    ::= { rsiMeasurementSetBaseEntry 1 }

rsiMeasurementSetVersionId OBJECT-TYPE
    SYNTAX          DisplayString
    MAX-ACCESS      read-only
    STATUS          current
    DESCRIPTION     
            "Measurement Set Version Id.BayManager will generate unique
             version id."
    ::= { rsiMeasurementSetBaseEntry 2 }

rsiMeasurementSetAccuInterval OBJECT-TYPE
    SYNTAX          Integer32
    MAX-ACCESS      read-create
    STATUS          current
    DESCRIPTION     
            "Measurement Set Accumulation Interval"
    ::= { rsiMeasurementSetBaseEntry 3 }

rsiMeasurementSetBaseRowStatus OBJECT-TYPE
    SYNTAX          RowStatus
    MAX-ACCESS      read-create
    STATUS          current
    DESCRIPTION     
            "This is for dynamic addition/deletion of Measurement
             sets.
             For creating a new row, only 'createAndGo' is 
             supported. For deleting an existing row, 'delete'
             is supported"
    ::= { rsiMeasurementSetBaseEntry 4 }

rsiMeasurementSetExtnFTPTable OBJECT-TYPE
    SYNTAX          SEQUENCE OF RsiMeasurementSetExtnFTPEntry
    MAX-ACCESS      not-accessible
    STATUS          current
    DESCRIPTION     
            "This table contains the information of different FTP sites for a 
             Measurement set.It contains rsiMeasurementSetID and 
             rsiMeasurementSetVersionId from rsiMeasurementSetBaseTable"
    ::= { rsiCommonMib 54 }

rsiMeasurementSetExtnFTPEntry OBJECT-TYPE
    SYNTAX          RsiMeasurementSetExtnFTPEntry
    MAX-ACCESS      not-accessible
    STATUS          current
    DESCRIPTION     
            "Description of a FTP site of a measurement set."
    INDEX           { rsiMeasurementSetID, rsiMeasurementSetVersionId, 
                      rsiMeasurementSetFTPHost, 
                      rsiMeasurementSetFTPUserId, 
                      rsiMeasurementSetFTPPasswd, 
                      rsiMeasurementSetFTPLocation }
    ::= { rsiMeasurementSetExtnFTPTable 1 }

RsiMeasurementSetExtnFTPEntry ::=
    SEQUENCE {
        rsiMeasurementSetFTPHost        DisplayString,
        rsiMeasurementSetFTPUserId      DisplayString,
        rsiMeasurementSetFTPPasswd      DisplayString,
        rsiMeasurementSetFTPLocation    DisplayString,
        rsiMeasurementSetFTPRowStatus   RowStatus
    }

rsiMeasurementSetFTPHost OBJECT-TYPE
    SYNTAX          DisplayString
    MAX-ACCESS      read-create
    STATUS          current
    DESCRIPTION     
            "This is Host name of FTP site"
    ::= { rsiMeasurementSetExtnFTPEntry 1 }

rsiMeasurementSetFTPUserId OBJECT-TYPE
    SYNTAX          DisplayString
    MAX-ACCESS      read-create
    STATUS          current
    DESCRIPTION     
            "This is user id for FTP site"
    ::= { rsiMeasurementSetExtnFTPEntry 2 }

rsiMeasurementSetFTPPasswd OBJECT-TYPE
    SYNTAX          DisplayString
    MAX-ACCESS      read-create
    STATUS          current
    DESCRIPTION     
            "This is password for FTP site"
    ::= { rsiMeasurementSetExtnFTPEntry 3 }

rsiMeasurementSetFTPLocation OBJECT-TYPE
    SYNTAX          DisplayString
    MAX-ACCESS      read-create
    STATUS          current
    DESCRIPTION     
            "This is directory location for FTP site"
    ::= { rsiMeasurementSetExtnFTPEntry 4 }

rsiMeasurementSetFTPRowStatus OBJECT-TYPE
    SYNTAX          RowStatus
    MAX-ACCESS      read-create
    STATUS          current
    DESCRIPTION     
            "This is for dynamic addition/deletion of FTP sites 
             for Measurement Set.
             For creating a new row, only 'createAndGo' is 
             supported. For deleting an existing row, 'delete'
             is supported"
    ::= { rsiMeasurementSetExtnFTPEntry 5 }

rsiMeasurementSetExtnCounterTable OBJECT-TYPE
    SYNTAX          SEQUENCE OF RsiMeasurementSetExtnCounterEntry
    MAX-ACCESS      not-accessible
    STATUS          current
    DESCRIPTION     
            "This table contains the information of different Measurement counters
             associated with a Measurement set.
             It contains rsiMeasurementSetID and rsiMeasurementSetVersionId from 
             rsiMeasurementSetBaseTable,rsiSubsystemID from rsiSubsystemTable and
             rsiMeasurementCounterID from rsiMeasurementCounterTable."
    ::= { rsiCommonMib 55 }

rsiMeasurementSetExtnCounterEntry OBJECT-TYPE
    SYNTAX          RsiMeasurementSetExtnCounterEntry
    MAX-ACCESS      not-accessible
    STATUS          current
    DESCRIPTION     
            "Description of a measurement set."
    INDEX           { rsiMeasurementSetID, rsiMeasurementSetVersionId, 
                      rsiSubsystemID, rsiMeasurementCounterID }
    ::= { rsiMeasurementSetExtnCounterTable 1 }

RsiMeasurementSetExtnCounterEntry ::=
    SEQUENCE {
        rsiMeasurementSetExtnCounterRowStatus     RowStatus
    }

rsiMeasurementSetExtnCounterRowStatus OBJECT-TYPE
    SYNTAX          RowStatus
    MAX-ACCESS      read-create
    STATUS          current
    DESCRIPTION     
            "This is for dynamic addition/deletion of Measurement
             counter within Measurement Sets.
             For creating a new row, only 'createAndGo' is 
             supported. For deleting an existing row, 'delete'
             is supported"
    ::= { rsiMeasurementSetExtnCounterEntry 1 }

rsiMeasurementSetDataCollectionTable OBJECT-TYPE
    SYNTAX          SEQUENCE OF RsiMeasurementSetDataCollectionEntry
    MAX-ACCESS      not-accessible
    STATUS          current
    DESCRIPTION     
            "This table contains measurement set data timestamps.It contains 
             rsiMeasurementSetID from rsiMeasurementSetBaseTable."
    ::= { rsiCommonMib 56 }

rsiMeasurementSetDataCollectionEntry OBJECT-TYPE
    SYNTAX          RsiMeasurementSetDataCollectionEntry
    MAX-ACCESS      not-accessible
    STATUS          current
    DESCRIPTION     
            "Description of a measurement set data timestamps"
    INDEX           { rsiMeasurementSetID, rsiMeasurementSetVersionId, 
                      rsiMeasurementSetDataTimeStamp }
    ::= { rsiMeasurementSetDataCollectionTable 1 }

RsiMeasurementSetDataCollectionEntry ::=
    SEQUENCE {
        rsiMeasurementSetDataTimeStamp  Integer32
    }

rsiMeasurementSetDataTimeStamp OBJECT-TYPE
    SYNTAX          Integer32
    MAX-ACCESS      read-only
    STATUS          current
    DESCRIPTION     
            "This is timestamp of measurement counter data in UTC"
    ::= { rsiMeasurementSetDataCollectionEntry 1 }

rsiMeasurementSetDataTable OBJECT-TYPE
    SYNTAX          SEQUENCE OF RsiMeasurementSetDataEntry
    MAX-ACCESS      not-accessible
    STATUS          current
    DESCRIPTION     
            "This table contains measurement counter data.It contains rsiMeasurementSetID
             and rsiMeasurementSetDataTimeStamp from rsiMeasurementSetBaseTable, 
             rsiSubsystemID from SubsystemTable, rsiMeasurementCounterID from 
             rsiMeasurementCounterTable."
    ::= { rsiCommonMib 57 }

rsiMeasurementSetDataEntry OBJECT-TYPE
    SYNTAX          RsiMeasurementSetDataEntry
    MAX-ACCESS      not-accessible
    STATUS          current
    DESCRIPTION     
            "Description of a measurement counter data."
    INDEX           { rsiMeasurementSetID, rsiMeasurementSetVersionId, 
                      rsiMeasurementSetDataTimeStamp, 
                      rsiMeasurementSetEntityId, rsiSubsystemID, 
                      rsiMeasurementCounterID, 
                      rsiMeasurementCounterValueId }
    ::= { rsiMeasurementSetDataTable 1 }

RsiMeasurementSetDataEntry ::=
    SEQUENCE {
        rsiMeasurementSetEntityId       DisplayString,
        rsiMeasurementCounterValueId    DisplayString,
        rsiMeasurementCounterValue      Integer32,
        rsiMeasurementSetDataFlags      Integer32
    }

rsiMeasurementSetEntityId OBJECT-TYPE
    SYNTAX          DisplayString
    MAX-ACCESS      read-only
    STATUS          current
    DESCRIPTION     
            "This is entity Id"
    ::= { rsiMeasurementSetDataEntry 1 }

rsiMeasurementCounterValueId OBJECT-TYPE
    SYNTAX          DisplayString
    MAX-ACCESS      read-only
    STATUS          current
    DESCRIPTION     
            "This is value id"
    ::= { rsiMeasurementSetDataEntry 2 }

rsiMeasurementCounterValue OBJECT-TYPE
    SYNTAX          Integer32
    MAX-ACCESS      read-only
    STATUS          current
    DESCRIPTION     
            "This is value of rsiMeasurementCounterID/rsiSystemID/rsiMeasurementCounterValueId"
    ::= { rsiMeasurementSetDataEntry 3 }

rsiMeasurementSetDataFlags OBJECT-TYPE
    SYNTAX          Integer32
    MAX-ACCESS      read-only
    STATUS          current
    DESCRIPTION     
            "This is flags of measurement counter data"
    ::= { rsiMeasurementSetDataEntry 5 }

rsiThresholdCounterTable OBJECT-TYPE
    SYNTAX          SEQUENCE OF RsiThresholdCounterEntry
    MAX-ACCESS      not-accessible
    STATUS          current
    DESCRIPTION     
            "This table contains threshold counter information.It contains 
             rsiSubsystemID from rsiSubsystemTable and rsiAlarmId from rsiAlarmTable"
    ::= { rsiCommonMib 58 }

rsiThresholdCounterEntry OBJECT-TYPE
    SYNTAX          RsiThresholdCounterEntry
    MAX-ACCESS      not-accessible
    STATUS          current
    DESCRIPTION     
            "Description of a threshold counter."
    INDEX           { rsiSubsystemID, rsiThresholdID }
    ::= { rsiThresholdCounterTable 1 }

RsiThresholdCounterEntry ::=
    SEQUENCE {
        rsiThresholdID                  DisplayString,
        rsiThresholdOid                 DisplayString,
        rsiThresholdType                INTEGER,
        rsiThresholdMode                INTEGER,
        rsiThresholdLeakValue           Integer32,
        rsiThresholdLowValue            Integer32,
        rsiThresholdValue               Integer32,
        rsiThresholdAssociatedId        DisplayString,
        rsiThresholdAction              INTEGER,
        rsiThresholdTimeDifference      Integer32,
        rsiThresholdScanInterval        Integer32,
        rsiThresholdModeInterval        Integer32,
        rsiThresholdEntityType          DisplayString,
        rsiThresholdEntityId            DisplayString,
        rsiThresholdDeferredProcessing  INTEGER,
        rsiThresholdEnable              INTEGER
    }

rsiThresholdID OBJECT-TYPE
    SYNTAX          DisplayString
    MAX-ACCESS      read-only
    STATUS          current
    DESCRIPTION     
            "This is threshold id"
    ::= { rsiThresholdCounterEntry 1 }

rsiThresholdOid OBJECT-TYPE
    SYNTAX          DisplayString
    MAX-ACCESS      read-only
    STATUS          current
    DESCRIPTION     
            "This is threshold oid"
    ::= { rsiThresholdCounterEntry 2 }

rsiThresholdType OBJECT-TYPE
    SYNTAX          INTEGER { absolute(0), timediff(1), percent(2), 
                        timediffpercent(3) }
    MAX-ACCESS      read-only
    STATUS          current
    DESCRIPTION     
            "This identifies the type of a particular threshold.The 
             possible values are absolute, timediff, percent and timediffpercent"
    ::= { rsiThresholdCounterEntry 3 }

rsiThresholdMode OBJECT-TYPE
    SYNTAX          INTEGER { reset(0), leak(1), none(2) }
    MAX-ACCESS      read-only
    STATUS          current
    DESCRIPTION     
            "This identifies the threshold mode .The 
             possible values are reset, leak and none."
    ::= { rsiThresholdCounterEntry 4 }

rsiThresholdLeakValue OBJECT-TYPE
    SYNTAX          Integer32
    MAX-ACCESS      read-write
    STATUS          current
    DESCRIPTION     
            "This identifies the threshold leak value.It will always be greater than zero."
    ::= { rsiThresholdCounterEntry 5 }

rsiThresholdLowValue OBJECT-TYPE
    SYNTAX          Integer32
    MAX-ACCESS      read-write
    STATUS          current
    DESCRIPTION     
            "This identifies the threshold's low value.It will always less than 
             rsiThresholdValue.If it is equal to rsiThresholdValue and rsiThresholdDeferredProcessing 
             is true,then alarms can be sent at regular intervals"
    ::= { rsiThresholdCounterEntry 6 }

rsiThresholdValue OBJECT-TYPE
    SYNTAX          Integer32
    MAX-ACCESS      read-write
    STATUS          current
    DESCRIPTION     
            "This identifies the threshold's value.It will always be greater than zero."
    ::= { rsiThresholdCounterEntry 7 }

rsiThresholdAssociatedId OBJECT-TYPE
    SYNTAX          DisplayString
    MAX-ACCESS      read-only
    STATUS          current
    DESCRIPTION     
            "This identifies the threshold's associated id.This is used for 'percent'
             and 'timediffpercent' resiThresholdType only."
    ::= { rsiThresholdCounterEntry 8 }

rsiThresholdAction OBJECT-TYPE
    SYNTAX          INTEGER { alarmAndLog(0), logOnly(1) }
    MAX-ACCESS      read-write
    STATUS          current
    DESCRIPTION     
            "This identifies the threshold action .The 
             possible values are alarm and log."
    ::= { rsiThresholdCounterEntry 9 }

rsiThresholdTimeDifference OBJECT-TYPE
    SYNTAX          Integer32
    MAX-ACCESS      read-only
    STATUS          current
    DESCRIPTION     
            "This identifies the threshold's time difference."
    ::= { rsiThresholdCounterEntry 11 }

rsiThresholdScanInterval OBJECT-TYPE
    SYNTAX          Integer32
    MAX-ACCESS      read-write
    STATUS          current
    DESCRIPTION     
            "This identifies the threshold's scan interval."
    ::= { rsiThresholdCounterEntry 12 }

rsiThresholdModeInterval OBJECT-TYPE
    SYNTAX          Integer32
    MAX-ACCESS      read-write
    STATUS          current
    DESCRIPTION     
            "This identifies the threshold's mode interval.It is used for 'leak' and 
             'reset' modes only.It will always be greater than zero."
    ::= { rsiThresholdCounterEntry 13 }

rsiThresholdEntityType OBJECT-TYPE
    SYNTAX          DisplayString
    MAX-ACCESS      read-only
    STATUS          current
    DESCRIPTION     
            "This identifies the threshold's entity type"
    ::= { rsiThresholdCounterEntry 14 }

rsiThresholdEntityId OBJECT-TYPE
    SYNTAX          DisplayString
    MAX-ACCESS      read-only
    STATUS          current
    DESCRIPTION     
            "This identifies the threshold's entity id"
    ::= { rsiThresholdCounterEntry 15 }

rsiThresholdDeferredProcessing OBJECT-TYPE
    SYNTAX          INTEGER { false(0), true(1) }
    MAX-ACCESS      read-write
    STATUS          current
    DESCRIPTION     
            "It specifies whether subsystem will generate repeat alarms before crossing
             high / low threshold or not"
    ::= { rsiThresholdCounterEntry 16 }

rsiThresholdEnable OBJECT-TYPE
    SYNTAX          INTEGER { false(0), true(1) }
    MAX-ACCESS      read-write
    STATUS          current
    DESCRIPTION     
            "It specifies whether a particulat threshold is enable or not."
    ::= { rsiThresholdCounterEntry 17 }

rsiThresholdCounterReportMapTable OBJECT-TYPE
    SYNTAX          SEQUENCE OF RsiThresholdCounterReportMapEntry
    MAX-ACCESS      not-accessible
    STATUS          current
    DESCRIPTION     
            "This table contains threshold counter report map.It contains
             rsiAlarmErrorCode from rsiAlarmEntry,rsiThresholdID from 
             rsiThresholdCounterTable and rsiSubsystemID from rsiSubsystemTable"
    ::= { rsiCommonMib 59 }

rsiThresholdCounterReportMapEntry OBJECT-TYPE
    SYNTAX          RsiThresholdCounterReportMapEntry
    MAX-ACCESS      not-accessible
    STATUS          current
    DESCRIPTION     
            "Description of a measurement counter report map"
    INDEX           { rsiSubsystemID, rsiThresholdID, rsiAlarmErrorCode }
    ::= { rsiThresholdCounterReportMapTable 1 }

RsiThresholdCounterReportMapEntry ::=
    SEQUENCE {
        rsiThresholdCounterReportMapRowStatus     RowStatus
    }

rsiThresholdCounterReportMapRowStatus OBJECT-TYPE
    SYNTAX          RowStatus
    MAX-ACCESS      read-create
    STATUS          current
    DESCRIPTION     
            "
             For creating a new policy, only 'createAndGo' is
             supported. For deleting an existing row, 'delete'
             is supported"
    ::= { rsiThresholdCounterReportMapEntry 5 }

rsiAlarmRetentionInterval OBJECT-TYPE
    SYNTAX          Integer32
    MAX-ACCESS      read-write
    STATUS          current
    DESCRIPTION     
            "The interval after which the alarms
             will be cleared from the database.
             Note the unit of this time interval is days."
    ::= { rsiCommonMib 60 }

rsiAINTrunkTable OBJECT-TYPE
    SYNTAX          SEQUENCE OF RsiAINTrunkEntry
    MAX-ACCESS      not-accessible
    STATUS          current
    DESCRIPTION     
            "This table contains information about AIN Trunks.
             It contains rsiHostId from rsiInventoryHostDetailTable
             table"
    ::= { rsiCommonMib 61 }

rsiAINTrunkEntry OBJECT-TYPE
    SYNTAX          RsiAINTrunkEntry
    MAX-ACCESS      not-accessible
    STATUS          current
    DESCRIPTION     
            "Description of a AIN Trunks"
    INDEX           { rsiAINTrunkName }
    ::= { rsiAINTrunkTable 1 }

RsiAINTrunkEntry ::=
    SEQUENCE {
        rsiAINTrunkName                 DisplayString,
        rsiAINHostName                  DisplayString,
        rsiAINPort                      Integer32,
        rsiAINCardId                    Integer32,
        rsiAINTrunkType                 INTEGER,
        rsiAINBaudRate                  INTEGER,
        rsiAINFraming                   INTEGER,
        rsiAINLineCoding                INTEGER,
        rsiAINTDMAmode                  INTEGER,
        rsiAINClockSource               INTEGER,
        rsiAINTrunkConfigStatus         INTEGER,
        rsiAINTrunkRowStatus            RowStatus
    }

rsiAINTrunkName OBJECT-TYPE
    SYNTAX          DisplayString
    MAX-ACCESS      read-create
    STATUS          current
    DESCRIPTION     
            "This identifies a unique name for a trunk"
    ::= { rsiAINTrunkEntry 1 }

rsiAINHostName OBJECT-TYPE
    SYNTAX          DisplayString
    MAX-ACCESS      read-create
    STATUS          current
    DESCRIPTION     
            "This is the name of the host on which the trunk exists"
    ::= { rsiAINTrunkEntry 2 }

rsiAINPort OBJECT-TYPE
    SYNTAX          Integer32
    MAX-ACCESS      read-create
    STATUS          current
    DESCRIPTION     
            "It specifies port associated with a trunk"
    ::= { rsiAINTrunkEntry 3 }

rsiAINCardId OBJECT-TYPE
    SYNTAX          Integer32
    MAX-ACCESS      read-create
    STATUS          current
    DESCRIPTION     
            "It specifies the Id of card associated with trunk"
    ::= { rsiAINTrunkEntry 4 }

rsiAINTrunkType OBJECT-TYPE
    SYNTAX          INTEGER { e1(0), t1(1) }
    MAX-ACCESS      read-create
    STATUS          current
    DESCRIPTION     
            "It specifies type of trunk"
    ::= { rsiAINTrunkEntry 5 }

rsiAINBaudRate OBJECT-TYPE
    SYNTAX          INTEGER { baud64(0), baud56(1), baud48(2) }
    MAX-ACCESS      read-create
    STATUS          current
    DESCRIPTION     
            "It specifies baud rate"
    ::= { rsiAINTrunkEntry 6 }

rsiAINFraming OBJECT-TYPE
    SYNTAX          INTEGER { esf(0), d4(1), e1(2), crc4(3) }
    MAX-ACCESS      read-create
    STATUS          current
    DESCRIPTION     
            "It specifies type of framing"
    ::= { rsiAINTrunkEntry 7 }

rsiAINLineCoding OBJECT-TYPE
    SYNTAX          INTEGER { b8zs(0), ami(1), hdb3(2) }
    MAX-ACCESS      read-create
    STATUS          current
    DESCRIPTION     
            "It specifies type of line encoding"
    ::= { rsiAINTrunkEntry 8 }

rsiAINTDMAmode OBJECT-TYPE
    SYNTAX          INTEGER { twomhz(0), eightmhzm(1), eightmhznm(2) }
    MAX-ACCESS      read-create
    STATUS          current
    DESCRIPTION     
            "It specifies TDMA mode"
    ::= { rsiAINTrunkEntry 9 }

rsiAINClockSource OBJECT-TYPE
    SYNTAX          INTEGER { adaxexttrunk1(0), adaxexttrunk2(1), 
                        adaxexttrunk3(2), adaxexttrunk4(3), 
                        adaxsrcinternal(4), trunkall(6) }
    MAX-ACCESS      read-create
    STATUS          current
    DESCRIPTION     
            "It specifies type of clock source"
    ::= { rsiAINTrunkEntry 10 }

rsiAINTrunkConfigStatus OBJECT-TYPE
    SYNTAX          INTEGER { addinprogress(0), addok(1), adderror(2), 
                        addpartial(3), delinprogress(4), delok(5), 
                        delerror(6), delpartial(7), modinprogress(8), 
                        modok(9), moderror(10), modpartial(11) }
    MAX-ACCESS      read-only
    STATUS          current
    DESCRIPTION     
            "It specifies trunk status"
    ::= { rsiAINTrunkEntry 11 }

rsiAINTrunkRowStatus OBJECT-TYPE
    SYNTAX          RowStatus
    MAX-ACCESS      read-create
    STATUS          current
    DESCRIPTION     
            "
             For creating a new AIN Trunk, only 'createAndGo' is
             supported. For deleting an existing row, 'delete'
             is supported"
    ::= { rsiAINTrunkEntry 12 }

rsiAINLinkSetTable OBJECT-TYPE
    SYNTAX          SEQUENCE OF RsiAINLinkSetEntry
    MAX-ACCESS      not-accessible
    STATUS          current
    DESCRIPTION     
            "This table contains information about AIN Link Sets.
             It contains rsiCompId from rsiComponentTable table where component
             is a functional unit group"
    ::= { rsiCommonMib 62 }

rsiAINLinkSetEntry OBJECT-TYPE
    SYNTAX          RsiAINLinkSetEntry
    MAX-ACCESS      not-accessible
    STATUS          current
    DESCRIPTION     
            "Description of a AIN Link Set"
    INDEX           { rsiCompId, rsiAINLinkSetName }
    ::= { rsiAINLinkSetTable 1 }

RsiAINLinkSetEntry ::=
    SEQUENCE {
        rsiAINLinkSetName               DisplayString,
        rsiAINLinkSetFamily             INTEGER,
        rsiAINLinkSetNI                 INTEGER,
        rsiAINLocalPC                   DisplayString,
        rsiAINAdjacantPC                DisplayString,
        rsiAINIsSTP                     INTEGER,
        rsiAINNumLoadedLinks            Integer32,
        rsiAINLinkSetStatus             INTEGER,
        rsiAINLinkSetConfigStatus       INTEGER,
        rsiAINLinkSetRowStatus          RowStatus
    }

rsiAINLinkSetName OBJECT-TYPE
    SYNTAX          DisplayString
    MAX-ACCESS      read-create
    STATUS          current
    DESCRIPTION     
            "This identifies a unique name for a link set"
    ::= { rsiAINLinkSetEntry 2 }

rsiAINLinkSetFamily OBJECT-TYPE
    SYNTAX          INTEGER { ansi(0) }
    MAX-ACCESS      read-create
    STATUS          current
    DESCRIPTION     
            "It specifies family of link set"
    ::= { rsiAINLinkSetEntry 3 }

rsiAINLinkSetNI OBJECT-TYPE
    SYNTAX          INTEGER { national(0) }
    MAX-ACCESS      read-create
    STATUS          current
    DESCRIPTION     
            "It specifies network indicator"
    ::= { rsiAINLinkSetEntry 4 }

rsiAINLocalPC OBJECT-TYPE
    SYNTAX          DisplayString
    MAX-ACCESS      read-create
    STATUS          current
    DESCRIPTION     
            "It specifies local point code.It has sytax as x-x-x"
    ::= { rsiAINLinkSetEntry 5 }

rsiAINAdjacantPC OBJECT-TYPE
    SYNTAX          DisplayString
    MAX-ACCESS      read-create
    STATUS          current
    DESCRIPTION     
            "It specifies adjacant point code.It has sytax as x-x-x"
    ::= { rsiAINLinkSetEntry 6 }

rsiAINIsSTP OBJECT-TYPE
    SYNTAX          INTEGER { false(0), true(1) }
    MAX-ACCESS      read-create
    STATUS          current
    DESCRIPTION     
            "It specifies  whether this is STP"
    ::= { rsiAINLinkSetEntry 7 }

rsiAINNumLoadedLinks OBJECT-TYPE
    SYNTAX          Integer32
    MAX-ACCESS      read-only
    STATUS          current
    DESCRIPTION     
            "It specifies no of loaded links in this link set"
    ::= { rsiAINLinkSetEntry 8 }

rsiAINLinkSetStatus OBJECT-TYPE
    SYNTAX          INTEGER { active(0), inactive(1) }
    MAX-ACCESS      read-create
    STATUS          current
    DESCRIPTION     
            "It specifies status of this link set"
    ::= { rsiAINLinkSetEntry 9 }

rsiAINLinkSetConfigStatus OBJECT-TYPE
    SYNTAX          INTEGER { addinprogress(0), addok(1), adderror(2), 
                        addpartial(3), delinprogress(4), delok(5), 
                        delerror(6), delpartial(7), modinprogress(8), 
                        modok(9), moderror(10), modpartial(11) }
    MAX-ACCESS      read-only
    STATUS          current
    DESCRIPTION     
            "It specifies configured status of this link set"
    ::= { rsiAINLinkSetEntry 10 }

rsiAINLinkSetRowStatus OBJECT-TYPE
    SYNTAX          RowStatus
    MAX-ACCESS      read-create
    STATUS          current
    DESCRIPTION     
            "
             For creating a new AIN Link Set, only 'createAndGo' is
             supported. For deleting an existing row, 'delete'
             is supported"
    ::= { rsiAINLinkSetEntry 11 }

rsiAINLinkSetDetailTable OBJECT-TYPE
    SYNTAX          SEQUENCE OF RsiAINLinkSetDetailEntry
    MAX-ACCESS      not-accessible
    STATUS          current
    DESCRIPTION     
            "This table contains detail information about AIN Link Sets.
             It contains rsiCompId from rsiComponentTable table where component
             is a functional unit group. It contains rsiAINLinkSetName from 
             rsiAINLinkSetTable."
    ::= { rsiCommonMib 63 }

rsiAINLinkSetDetailEntry OBJECT-TYPE
    SYNTAX          RsiAINLinkSetDetailEntry
    MAX-ACCESS      not-accessible
    STATUS          current
    DESCRIPTION     
            "Detail Description of a AIN Link Set"
    INDEX           { rsiAINLinkSetName, rsiCompId, rsiLinkSetOMCCompId }
    ::= { rsiAINLinkSetDetailTable 1 }

RsiAINLinkSetDetailEntry ::=
    SEQUENCE {
        rsiLinkSetOMCCompId             Integer32,
        rsiAINLinkSetDetailStatus       INTEGER,
        rsiAINLinkSetDetailConfigStatus INTEGER
    }

rsiLinkSetOMCCompId OBJECT-TYPE
    SYNTAX          Integer32
    MAX-ACCESS      read-only
    STATUS          current
    DESCRIPTION     
            "It specifies component id of OMC"
    ::= { rsiAINLinkSetDetailEntry 1 }

rsiAINLinkSetDetailStatus OBJECT-TYPE
    SYNTAX          INTEGER { active(0), inactive(1) }
    MAX-ACCESS      read-only
    STATUS          current
    DESCRIPTION     
            "It specifies status of this link set"
    ::= { rsiAINLinkSetDetailEntry 2 }

rsiAINLinkSetDetailConfigStatus OBJECT-TYPE
    SYNTAX          INTEGER { addinprogress(0), addok(1), adderror(2), 
                        delinprogress(4), delok(5), delerror(6), 
                        modinprogress(8), modok(9), moderror(10) }
    MAX-ACCESS      read-only
    STATUS          current
    DESCRIPTION     
            "It specifies configured status of this link set"
    ::= { rsiAINLinkSetDetailEntry 3 }

rsiAINLinkTable OBJECT-TYPE
    SYNTAX          SEQUENCE OF RsiAINLinkEntry
    MAX-ACCESS      not-accessible
    STATUS          current
    DESCRIPTION     
            "This table contains information about AIN Link.
             .It contains rsiAINTrunkName from rsiAINTrunkTable 
             table and rsiAINLinkSetName from rsiAINLinkSetTable."
    ::= { rsiCommonMib 64 }

rsiAINLinkEntry OBJECT-TYPE
    SYNTAX          RsiAINLinkEntry
    MAX-ACCESS      not-accessible
    STATUS          current
    DESCRIPTION     
            "Description of a AIN Link"
    INDEX           { rsiAINTrunkName, rsiAINLinkSetName, rsiAINLinkName }
    ::= { rsiAINLinkTable 1 }

RsiAINLinkEntry ::=
    SEQUENCE {
        rsiAINLinkName                  DisplayString,
        rsiAINLinkTimeSlot              Integer32,
        rsiAINLinkPriority              Integer32,
        rsiAINLinkStatus                INTEGER,
        rsiAINLinkConfigStatus          INTEGER,
        rsiAINLinkRowStatus             RowStatus
    }

rsiAINLinkName OBJECT-TYPE
    SYNTAX          DisplayString
    MAX-ACCESS      read-create
    STATUS          current
    DESCRIPTION     
            "This identifies a unique name for a link"
    ::= { rsiAINLinkEntry 2 }

rsiAINLinkTimeSlot OBJECT-TYPE
    SYNTAX          Integer32
    MAX-ACCESS      read-create
    STATUS          current
    DESCRIPTION     
            "It specifies time slot"
    ::= { rsiAINLinkEntry 3 }

rsiAINLinkPriority OBJECT-TYPE
    SYNTAX          Integer32
    MAX-ACCESS      read-create
    STATUS          current
    DESCRIPTION     
            "It specifies priority"
    ::= { rsiAINLinkEntry 4 }

rsiAINLinkStatus OBJECT-TYPE
    SYNTAX          INTEGER { active(0), inactive(1) }
    MAX-ACCESS      read-create
    STATUS          current
    DESCRIPTION     
            "It specifies status of link"
    ::= { rsiAINLinkEntry 5 }

rsiAINLinkConfigStatus OBJECT-TYPE
    SYNTAX          INTEGER { addinprogress(0), addok(1), adderror(2), 
                        addpartial(3), delinprogress(4), delok(5), 
                        delerror(6), delpartial(7), modinprogress(8), 
                        modok(9), moderror(10), modpartial(11) }
    MAX-ACCESS      read-only
    STATUS          current
    DESCRIPTION     
            "It specifies configured status of link"
    ::= { rsiAINLinkEntry 6 }

rsiAINLinkRowStatus OBJECT-TYPE
    SYNTAX          RowStatus
    MAX-ACCESS      read-create
    STATUS          current
    DESCRIPTION     
            "
             For creating a new AIN Link, only 'createAndGo' is
             supported. For deleting an existing row, 'delete'
             is supported"
    ::= { rsiAINLinkEntry 7 }

rsiAINRouteSetTable OBJECT-TYPE
    SYNTAX          SEQUENCE OF RsiAINRouteSetEntry
    MAX-ACCESS      not-accessible
    STATUS          current
    DESCRIPTION     
            "This table contains information about AIN Route Sets."
    ::= { rsiCommonMib 65 }

rsiAINRouteSetEntry OBJECT-TYPE
    SYNTAX          RsiAINRouteSetEntry
    MAX-ACCESS      not-accessible
    STATUS          current
    DESCRIPTION     
            "Description of a AIN Route Set"
    INDEX           { rsiAINRouteSetName }
    ::= { rsiAINRouteSetTable 1 }

RsiAINRouteSetEntry ::=
    SEQUENCE {
        rsiAINRouteSetName              DisplayString,
        rsiAINRouteSetDPC               DisplayString,
        rsiAINRouteSetRowStatus         RowStatus
    }

rsiAINRouteSetName OBJECT-TYPE
    SYNTAX          DisplayString
    MAX-ACCESS      read-create
    STATUS          current
    DESCRIPTION     
            "This identifies a unique name for a route set"
    ::= { rsiAINRouteSetEntry 2 }

rsiAINRouteSetDPC OBJECT-TYPE
    SYNTAX          DisplayString
    MAX-ACCESS      read-create
    STATUS          current
    DESCRIPTION     
            "It specifies DPC for this route set.It has sytax as x-x-x"
    ::= { rsiAINRouteSetEntry 3 }

rsiAINRouteSetRowStatus OBJECT-TYPE
    SYNTAX          RowStatus
    MAX-ACCESS      read-create
    STATUS          current
    DESCRIPTION     
            "
             For creating a new AIN Route Set, only 'createAndGo' is
             supported. For deleting an existing row, 'delete'
             is supported"
    ::= { rsiAINRouteSetEntry 4 }

rsiAINRouteTable OBJECT-TYPE
    SYNTAX          SEQUENCE OF RsiAINRouteEntry
    MAX-ACCESS      not-accessible
    STATUS          current
    DESCRIPTION     
            "This table contains information about AIN Route.
             It contains rsiCompId from rsiComponentTable table where component
             is a functional unit group.It contains rsiAINTrunkName from rsiAINTrunkTable
             table and rsiAINRouteSetName from rsiAINRouteSetTable."
    ::= { rsiCommonMib 66 }

rsiAINRouteEntry OBJECT-TYPE
    SYNTAX          RsiAINRouteEntry
    MAX-ACCESS      not-accessible
    STATUS          current
    DESCRIPTION     
            "Description of a AIN Route"
    INDEX           { rsiCompId, rsiAINRouteName, rsiAINRouteSetName, 
                      rsiAINLinkSetName }
    ::= { rsiAINRouteTable 1 }

RsiAINRouteEntry ::=
    SEQUENCE {
        rsiAINRouteName                 DisplayString,
        rsiAINRoutePriority             Integer32,
        rsiAINRouteSIO                  Integer32,
        rsiAINRouteSSN                  Integer32,
        rsiAINRoutehasSSN               Integer32,
        rsiAINRouteDPC                  DisplayString,
        rsiAINRouteStatus               INTEGER,
        rsiAINRouteRowStatus            RowStatus
    }

rsiAINRouteName OBJECT-TYPE
    SYNTAX          DisplayString
    MAX-ACCESS      read-create
    STATUS          current
    DESCRIPTION     
            "This identifies a unique name for a route"
    ::= { rsiAINRouteEntry 2 }

rsiAINRoutePriority OBJECT-TYPE
    SYNTAX          Integer32
    MAX-ACCESS      read-create
    STATUS          current
    DESCRIPTION     
            "It specifies priority"
    ::= { rsiAINRouteEntry 3 }

rsiAINRouteSIO OBJECT-TYPE
    SYNTAX          Integer32
    MAX-ACCESS      read-create
    STATUS          current
    DESCRIPTION     
            "It specifies SIO"
    ::= { rsiAINRouteEntry 4 }

rsiAINRouteSSN OBJECT-TYPE
    SYNTAX          Integer32
    MAX-ACCESS      read-create
    STATUS          current
    DESCRIPTION     
            "It specifies SSN"
    ::= { rsiAINRouteEntry 5 }

rsiAINRoutehasSSN OBJECT-TYPE
    SYNTAX          Integer32
    MAX-ACCESS      read-create
    STATUS          current
    DESCRIPTION     
            "It specifies whether route has SSN"
    ::= { rsiAINRouteEntry 6 }

rsiAINRouteDPC OBJECT-TYPE
    SYNTAX          DisplayString
    MAX-ACCESS      read-create
    STATUS          current
    DESCRIPTION     
            "It specifies Distant point code.It has sytax as x-x-x"
    ::= { rsiAINRouteEntry 7 }

rsiAINRouteStatus OBJECT-TYPE
    SYNTAX          INTEGER { addinprogress(0), addok(1), adderror(2), 
                        addpartial(3), delinprogress(4), delok(5), 
                        delerror(6), delpartial(7), modinprogress(8), 
                        modok(9), moderror(10), modpartial(11) }
    MAX-ACCESS      read-only
    STATUS          current
    DESCRIPTION     
            "It specifies status of route"
    ::= { rsiAINRouteEntry 8 }

rsiAINRouteRowStatus OBJECT-TYPE
    SYNTAX          RowStatus
    MAX-ACCESS      read-create
    STATUS          current
    DESCRIPTION     
            "
             For creating a new AIN Route, only 'createAndGo' is
             supported. For deleting an existing row, 'delete'
             is supported"
    ::= { rsiAINRouteEntry 9 }

rsiAINRouteDetailTable OBJECT-TYPE
    SYNTAX          SEQUENCE OF RsiAINRouteDetailEntry
    MAX-ACCESS      not-accessible
    STATUS          current
    DESCRIPTION     
            "This table contains detail information about AIN Route.
             It contains rsiCompId from rsiComponentTable table where component
             is a OMC.It contains rsiAINTrunkName from rsiAINTrunkTable
             table and rsiAINRouteSetName from rsiAINRouteSetTable."
    ::= { rsiCommonMib 67 }

rsiAINRouteDetailEntry OBJECT-TYPE
    SYNTAX          RsiAINRouteDetailEntry
    MAX-ACCESS      not-accessible
    STATUS          current
    DESCRIPTION     
            "Description of a AIN Route"
    INDEX           { rsiAINRouteName, rsiCompId, rsiRouteOMCCompId }
    ::= { rsiAINRouteDetailTable 1 }

RsiAINRouteDetailEntry ::=
    SEQUENCE {
        rsiRouteOMCCompId               Integer32,
        rsiAINRouteDetailStatus         INTEGER
    }

rsiRouteOMCCompId OBJECT-TYPE
    SYNTAX          Integer32
    MAX-ACCESS      read-only
    STATUS          current
    DESCRIPTION     
            "It specifies component id of OMC"
    ::= { rsiAINRouteDetailEntry 1 }

rsiAINRouteDetailStatus OBJECT-TYPE
    SYNTAX          INTEGER { addinprogress(0), addok(1), adderror(2), 
                        delinprogress(4), delok(5), delerror(6), 
                        modinprogress(8), modok(9), moderror(10) }
    MAX-ACCESS      read-only
    STATUS          current
    DESCRIPTION     
            "It specifies status of route"
    ::= { rsiAINRouteDetailEntry 2 }

rsiSasGeneralPerfCounters OBJECT-TYPE
    SYNTAX          SEQUENCE OF RsiSasGeneralPerfCountersEntry
    MAX-ACCESS      not-accessible
    STATUS          current
    DESCRIPTION     
            "This table contains the information of General Perf measurement
             counters on different subsystems.It contains rsiSubsystemID
             from rsiSubsystemTable."
    ::= { rsiCommonMib 68 }

rsiSasGeneralPerfCountersEntry OBJECT-TYPE
    SYNTAX          RsiSasGeneralPerfCountersEntry
    MAX-ACCESS      not-accessible
    STATUS          current
    DESCRIPTION     
            "Description of a General measurement counter of a particular subsystem."
    INDEX           { rsisubsysid }
    ::= { rsiSasGeneralPerfCounters 1 }

RsiSasGeneralPerfCountersEntry ::=
    SEQUENCE {
        rsisubsysid                     Integer32,
        rsiSasNumActAppSessions         Integer32,
        rsiSasNumActSipSessions         Integer32,
        rsiSasNumRejectReq              Integer32,
        rsiSasNumCallsCurrReplicated    Integer32,
        rsiSasNumReqFailedTrig          Integer32,
        rsiSasNum1XXResIn               Integer32,
        rsiSasNum1XXResOut              Integer32,
        rsiSasNum2XXResIn               Integer32,
        rsiSasNum2XXResOut              Integer32,
        rsiSasNum3XXResIn               Integer32,
        rsiSasNum3XXResOut              Integer32,
        rsiSasNum4XXResIn               Integer32,
        rsiSasNum4XXResOut              Integer32,
        rsiSasNum5XXResIn               Integer32,
        rsiSasNum5XXResOut              Integer32,
        rsiSasNum6XXResIn               Integer32,
        rsiSasNum6XXResOut              Integer32,
        rsiSasNumACKTimeout             Integer32,
        rsiSasNumACKsIn                 Integer32,
        rsiSasNumACKsOut                Integer32,
        rsiSasNumAppSessions            Integer32,
        rsiSasNumBYEsIn                 Integer32,
        rsiSasNuBYEsOut                 Integer32,
        rsiSasNumCancelsIn              Integer32,
        rsiSasNumCancelsOut             Integer32,
        rsiSasNumDeserialFail           Integer32,
        rsiSasNumInfosIn                Integer32,
        rsiSasNumInforsOut              Integer32,
        rsiSasNumInvitesIn              Integer32,
        rsiSasNumInvitesOut             Integer32,
        rsiSasNumMsgIn                  Integer32,
        rsiSasNumMsgOut                 Integer32,
        rsiSasNumNotifysIn              Integer32,
        rsiSasNumNotifysOut             Integer32,
        rsiSasNumOptionsIn              Integer32,
        rsiSasNumOptionsOut             Integer32,
        rsiSasNumPrackTimedout          Integer32,
        rsiSasNumPracksIn               Integer32,
        rsiSasNumPracksOut              Integer32,
        rsiSasNumPublishsIn             Integer32,
        rsiSasNumPublishsOut            Integer32,
        rsiSasNumRefersIn               Integer32,
        rsiSasNumRefersOut              Integer32,
        rsiSasNumRegistersIn            Integer32,
        rsiSasNumRegistersOut           Integer32,
        rsiSasNumRequestsIn             Integer32,
        rsiSasNumRequestsOut            Integer32,
        rsiSasNumResponsesIn            Integer32,
        rsiSasNumResponsesOut           Integer32,
        rsiSasNumSIPSessions            Integer32,
        rsiSasNumSubscribesIn           Integer32,
        rsiSasNumSubscribesOut          Integer32,
        rsiSasNumSerializationFailures  Integer32,
        rsiSasNumTimedoutAppSessions    Integer32,
        rsiSasNumUpdatesIn              Integer32,
        rsiSasNumUpdatesOut             Integer32,
        rsiSasNumcallsActivated         Integer32,
        rsiSasNumcallsCleanedup         Integer32,
        rsiSasNumcallsReplicated        Integer32
    }

rsisubsysid OBJECT-TYPE
    SYNTAX          Integer32
    MAX-ACCESS      read-only
    STATUS          current
    DESCRIPTION     
            "Subsystem for which measurement counter is needed"
    ::= { rsiSasGeneralPerfCountersEntry 1 }

rsiSasNumActAppSessions OBJECT-TYPE
    SYNTAX          Integer32
    MAX-ACCESS      read-only
    STATUS          current
    DESCRIPTION     
            "Number of active application sessions"
    ::= { rsiSasGeneralPerfCountersEntry 2 }

rsiSasNumActSipSessions OBJECT-TYPE
    SYNTAX          Integer32
    MAX-ACCESS      read-only
    STATUS          current
    DESCRIPTION     
            "Number of active SIP sessions"
    ::= { rsiSasGeneralPerfCountersEntry 3 }

rsiSasNumRejectReq OBJECT-TYPE
    SYNTAX          Integer32
    MAX-ACCESS      read-only
    STATUS          current
    DESCRIPTION     
            "Number of Rejected Requests"
    ::= { rsiSasGeneralPerfCountersEntry 4 }

rsiSasNumCallsCurrReplicated OBJECT-TYPE
    SYNTAX          Integer32
    MAX-ACCESS      read-only
    STATUS          current
    DESCRIPTION     
            "Number of Calls Currently Replicated"
    ::= { rsiSasGeneralPerfCountersEntry 5 }

rsiSasNumReqFailedTrig OBJECT-TYPE
    SYNTAX          Integer32
    MAX-ACCESS      read-only
    STATUS          current
    DESCRIPTION     
            "Number of active Request Failed to Trigger"
    ::= { rsiSasGeneralPerfCountersEntry 6 }

rsiSasNum1XXResIn OBJECT-TYPE
    SYNTAX          Integer32
    MAX-ACCESS      read-only
    STATUS          current
    DESCRIPTION     
            "Number of 1XX Responses In"
    ::= { rsiSasGeneralPerfCountersEntry 7 }

rsiSasNum1XXResOut OBJECT-TYPE
    SYNTAX          Integer32
    MAX-ACCESS      read-only
    STATUS          current
    DESCRIPTION     
            "Number of 1XX Responses Out"
    ::= { rsiSasGeneralPerfCountersEntry 8 }

rsiSasNum2XXResIn OBJECT-TYPE
    SYNTAX          Integer32
    MAX-ACCESS      read-only
    STATUS          current
    DESCRIPTION     
            "Number of 2XX Responses In"
    ::= { rsiSasGeneralPerfCountersEntry 9 }

rsiSasNum2XXResOut OBJECT-TYPE
    SYNTAX          Integer32
    MAX-ACCESS      read-only
    STATUS          current
    DESCRIPTION     
            "Number of 2XX Responses Out"
    ::= { rsiSasGeneralPerfCountersEntry 10 }

rsiSasNum3XXResIn OBJECT-TYPE
    SYNTAX          Integer32
    MAX-ACCESS      read-only
    STATUS          current
    DESCRIPTION     
            "Number of  3XX Responses In"
    ::= { rsiSasGeneralPerfCountersEntry 11 }

rsiSasNum3XXResOut OBJECT-TYPE
    SYNTAX          Integer32
    MAX-ACCESS      read-only
    STATUS          current
    DESCRIPTION     
            "Number of 3XX Responses Out"
    ::= { rsiSasGeneralPerfCountersEntry 12 }

rsiSasNum4XXResIn OBJECT-TYPE
    SYNTAX          Integer32
    MAX-ACCESS      read-only
    STATUS          current
    DESCRIPTION     
            "Number of 4XX Responses In"
    ::= { rsiSasGeneralPerfCountersEntry 13 }

rsiSasNum4XXResOut OBJECT-TYPE
    SYNTAX          Integer32
    MAX-ACCESS      read-only
    STATUS          current
    DESCRIPTION     
            "Number of 4XX Responses Out"
    ::= { rsiSasGeneralPerfCountersEntry 14 }

rsiSasNum5XXResIn OBJECT-TYPE
    SYNTAX          Integer32
    MAX-ACCESS      read-only
    STATUS          current
    DESCRIPTION     
            "Number of 5XX Responses In"
    ::= { rsiSasGeneralPerfCountersEntry 15 }

rsiSasNum5XXResOut OBJECT-TYPE
    SYNTAX          Integer32
    MAX-ACCESS      read-only
    STATUS          current
    DESCRIPTION     
            "Number of 5XX Responses Out"
    ::= { rsiSasGeneralPerfCountersEntry 16 }

rsiSasNum6XXResIn OBJECT-TYPE
    SYNTAX          Integer32
    MAX-ACCESS      read-only
    STATUS          current
    DESCRIPTION     
            "Number of  6XX Responses In"
    ::= { rsiSasGeneralPerfCountersEntry 17 }

rsiSasNum6XXResOut OBJECT-TYPE
    SYNTAX          Integer32
    MAX-ACCESS      read-only
    STATUS          current
    DESCRIPTION     
            "Number of 6XX Responses Out"
    ::= { rsiSasGeneralPerfCountersEntry 18 }

rsiSasNumACKTimeout OBJECT-TYPE
    SYNTAX          Integer32
    MAX-ACCESS      read-only
    STATUS          current
    DESCRIPTION     
            "Number of ACK TImed Out"
    ::= { rsiSasGeneralPerfCountersEntry 19 }

rsiSasNumACKsIn OBJECT-TYPE
    SYNTAX          Integer32
    MAX-ACCESS      read-only
    STATUS          current
    DESCRIPTION     
            "Number of ACKs In"
    ::= { rsiSasGeneralPerfCountersEntry 20 }

rsiSasNumACKsOut OBJECT-TYPE
    SYNTAX          Integer32
    MAX-ACCESS      read-only
    STATUS          current
    DESCRIPTION     
            "Number of ACKs Out"
    ::= { rsiSasGeneralPerfCountersEntry 21 }

rsiSasNumAppSessions OBJECT-TYPE
    SYNTAX          Integer32
    MAX-ACCESS      read-only
    STATUS          current
    DESCRIPTION     
            "Number of application sessions"
    ::= { rsiSasGeneralPerfCountersEntry 22 }

rsiSasNumBYEsIn OBJECT-TYPE
    SYNTAX          Integer32
    MAX-ACCESS      read-only
    STATUS          current
    DESCRIPTION     
            "Number of BYEs In"
    ::= { rsiSasGeneralPerfCountersEntry 23 }

rsiSasNuBYEsOut OBJECT-TYPE
    SYNTAX          Integer32
    MAX-ACCESS      read-only
    STATUS          current
    DESCRIPTION     
            "Number of BYEs Out"
    ::= { rsiSasGeneralPerfCountersEntry 24 }

rsiSasNumCancelsIn OBJECT-TYPE
    SYNTAX          Integer32
    MAX-ACCESS      read-only
    STATUS          current
    DESCRIPTION     
            "Number of Cancels In"
    ::= { rsiSasGeneralPerfCountersEntry 25 }

rsiSasNumCancelsOut OBJECT-TYPE
    SYNTAX          Integer32
    MAX-ACCESS      read-only
    STATUS          current
    DESCRIPTION     
            "Number of Cancels Out"
    ::= { rsiSasGeneralPerfCountersEntry 26 }

rsiSasNumDeserialFail OBJECT-TYPE
    SYNTAX          Integer32
    MAX-ACCESS      read-only
    STATUS          current
    DESCRIPTION     
            "Number of Deserialization Failures"
    ::= { rsiSasGeneralPerfCountersEntry 27 }

rsiSasNumInfosIn OBJECT-TYPE
    SYNTAX          Integer32
    MAX-ACCESS      read-only
    STATUS          current
    DESCRIPTION     
            "Number of INFOs In"
    ::= { rsiSasGeneralPerfCountersEntry 28 }

rsiSasNumInforsOut OBJECT-TYPE
    SYNTAX          Integer32
    MAX-ACCESS      read-only
    STATUS          current
    DESCRIPTION     
            "Number of INFOs Out"
    ::= { rsiSasGeneralPerfCountersEntry 29 }

rsiSasNumInvitesIn OBJECT-TYPE
    SYNTAX          Integer32
    MAX-ACCESS      read-only
    STATUS          current
    DESCRIPTION     
            "Number of INVITEs In"
    ::= { rsiSasGeneralPerfCountersEntry 30 }

rsiSasNumInvitesOut OBJECT-TYPE
    SYNTAX          Integer32
    MAX-ACCESS      read-only
    STATUS          current
    DESCRIPTION     
            "Number of INVITEs Out"
    ::= { rsiSasGeneralPerfCountersEntry 31 }

rsiSasNumMsgIn OBJECT-TYPE
    SYNTAX          Integer32
    MAX-ACCESS      read-only
    STATUS          current
    DESCRIPTION     
            "Number of Message In"
    ::= { rsiSasGeneralPerfCountersEntry 32 }

rsiSasNumMsgOut OBJECT-TYPE
    SYNTAX          Integer32
    MAX-ACCESS      read-only
    STATUS          current
    DESCRIPTION     
            "Number of Message Out"
    ::= { rsiSasGeneralPerfCountersEntry 33 }

rsiSasNumNotifysIn OBJECT-TYPE
    SYNTAX          Integer32
    MAX-ACCESS      read-only
    STATUS          current
    DESCRIPTION     
            "Number of Notify In"
    ::= { rsiSasGeneralPerfCountersEntry 34 }

rsiSasNumNotifysOut OBJECT-TYPE
    SYNTAX          Integer32
    MAX-ACCESS      read-only
    STATUS          current
    DESCRIPTION     
            "Number of Notify Out"
    ::= { rsiSasGeneralPerfCountersEntry 35 }

rsiSasNumOptionsIn OBJECT-TYPE
    SYNTAX          Integer32
    MAX-ACCESS      read-only
    STATUS          current
    DESCRIPTION     
            "Number of active Option In"
    ::= { rsiSasGeneralPerfCountersEntry 36 }

rsiSasNumOptionsOut OBJECT-TYPE
    SYNTAX          Integer32
    MAX-ACCESS      read-only
    STATUS          current
    DESCRIPTION     
            "Number of Option Out"
    ::= { rsiSasGeneralPerfCountersEntry 37 }

rsiSasNumPrackTimedout OBJECT-TYPE
    SYNTAX          Integer32
    MAX-ACCESS      read-only
    STATUS          current
    DESCRIPTION     
            "Number of Pracks TimeOut"
    ::= { rsiSasGeneralPerfCountersEntry 38 }

rsiSasNumPracksIn OBJECT-TYPE
    SYNTAX          Integer32
    MAX-ACCESS      read-only
    STATUS          current
    DESCRIPTION     
            "Number of Pracks In"
    ::= { rsiSasGeneralPerfCountersEntry 39 }

rsiSasNumPracksOut OBJECT-TYPE
    SYNTAX          Integer32
    MAX-ACCESS      read-only
    STATUS          current
    DESCRIPTION     
            "Number of Pracks Out"
    ::= { rsiSasGeneralPerfCountersEntry 40 }

rsiSasNumPublishsIn OBJECT-TYPE
    SYNTAX          Integer32
    MAX-ACCESS      read-only
    STATUS          current
    DESCRIPTION     
            "Number of  Publishes In"
    ::= { rsiSasGeneralPerfCountersEntry 41 }

rsiSasNumPublishsOut OBJECT-TYPE
    SYNTAX          Integer32
    MAX-ACCESS      read-only
    STATUS          current
    DESCRIPTION     
            "Number of Publishes Out"
    ::= { rsiSasGeneralPerfCountersEntry 42 }

rsiSasNumRefersIn OBJECT-TYPE
    SYNTAX          Integer32
    MAX-ACCESS      read-only
    STATUS          current
    DESCRIPTION     
            "Number of 4XX Responses In"
    ::= { rsiSasGeneralPerfCountersEntry 43 }

rsiSasNumRefersOut OBJECT-TYPE
    SYNTAX          Integer32
    MAX-ACCESS      read-only
    STATUS          current
    DESCRIPTION     
            "Number of Refer Out"
    ::= { rsiSasGeneralPerfCountersEntry 44 }

rsiSasNumRegistersIn OBJECT-TYPE
    SYNTAX          Integer32
    MAX-ACCESS      read-only
    STATUS          current
    DESCRIPTION     
            "Number of Register In"
    ::= { rsiSasGeneralPerfCountersEntry 45 }

rsiSasNumRegistersOut OBJECT-TYPE
    SYNTAX          Integer32
    MAX-ACCESS      read-only
    STATUS          current
    DESCRIPTION     
            "Number of Register Out"
    ::= { rsiSasGeneralPerfCountersEntry 46 }

rsiSasNumRequestsIn OBJECT-TYPE
    SYNTAX          Integer32
    MAX-ACCESS      read-only
    STATUS          current
    DESCRIPTION     
            "Number of  Requests In"
    ::= { rsiSasGeneralPerfCountersEntry 47 }

rsiSasNumRequestsOut OBJECT-TYPE
    SYNTAX          Integer32
    MAX-ACCESS      read-only
    STATUS          current
    DESCRIPTION     
            "Number of Requested Out"
    ::= { rsiSasGeneralPerfCountersEntry 48 }

rsiSasNumResponsesIn OBJECT-TYPE
    SYNTAX          Integer32
    MAX-ACCESS      read-only
    STATUS          current
    DESCRIPTION     
            "Number of Responses In"
    ::= { rsiSasGeneralPerfCountersEntry 49 }

rsiSasNumResponsesOut OBJECT-TYPE
    SYNTAX          Integer32
    MAX-ACCESS      read-only
    STATUS          current
    DESCRIPTION     
            "Number of ACKs In"
    ::= { rsiSasGeneralPerfCountersEntry 50 }

rsiSasNumSIPSessions OBJECT-TYPE
    SYNTAX          Integer32
    MAX-ACCESS      read-only
    STATUS          current
    DESCRIPTION     
            "Number of SIP Session"
    ::= { rsiSasGeneralPerfCountersEntry 51 }

rsiSasNumSubscribesIn OBJECT-TYPE
    SYNTAX          Integer32
    MAX-ACCESS      read-only
    STATUS          current
    DESCRIPTION     
            "Number of Subscriber In"
    ::= { rsiSasGeneralPerfCountersEntry 52 }

rsiSasNumSubscribesOut OBJECT-TYPE
    SYNTAX          Integer32
    MAX-ACCESS      read-only
    STATUS          current
    DESCRIPTION     
            "Number of Subcribers Out"
    ::= { rsiSasGeneralPerfCountersEntry 53 }

rsiSasNumSerializationFailures OBJECT-TYPE
    SYNTAX          Integer32
    MAX-ACCESS      read-only
    STATUS          current
    DESCRIPTION     
            "Number of Serialization Failures"
    ::= { rsiSasGeneralPerfCountersEntry 54 }

rsiSasNumTimedoutAppSessions OBJECT-TYPE
    SYNTAX          Integer32
    MAX-ACCESS      read-only
    STATUS          current
    DESCRIPTION     
            "Number of Timed Out App Session"
    ::= { rsiSasGeneralPerfCountersEntry 55 }

rsiSasNumUpdatesIn OBJECT-TYPE
    SYNTAX          Integer32
    MAX-ACCESS      read-only
    STATUS          current
    DESCRIPTION     
            "Number of Updates In"
    ::= { rsiSasGeneralPerfCountersEntry 56 }

rsiSasNumUpdatesOut OBJECT-TYPE
    SYNTAX          Integer32
    MAX-ACCESS      read-only
    STATUS          current
    DESCRIPTION     
            "Number of Updates Out"
    ::= { rsiSasGeneralPerfCountersEntry 57 }

rsiSasNumcallsActivated OBJECT-TYPE
    SYNTAX          Integer32
    MAX-ACCESS      read-only
    STATUS          current
    DESCRIPTION     
            "Number of Calls Activated"
    ::= { rsiSasGeneralPerfCountersEntry 58 }

rsiSasNumcallsCleanedup OBJECT-TYPE
    SYNTAX          Integer32
    MAX-ACCESS      read-only
    STATUS          current
    DESCRIPTION     
            "Number of Calls Cleaned Up"
    ::= { rsiSasGeneralPerfCountersEntry 59 }

rsiSasNumcallsReplicated OBJECT-TYPE
    SYNTAX          Integer32
    MAX-ACCESS      read-only
    STATUS          current
    DESCRIPTION     
            "Number of Calls Replicated"
    ::= { rsiSasGeneralPerfCountersEntry 60 }

rsiSasPriorityCallPerfCounters OBJECT-TYPE
    SYNTAX          SEQUENCE OF RsiSasPriorityCallPerfCountersEntry
    MAX-ACCESS      not-accessible
    STATUS          current
    DESCRIPTION     
            "This table contains the information of Priority Call Perf measurement
             counters on different subsystems.It contains rsiSubsystemID
             from rsiSubsystemTable."
    ::= { rsiCommonMib 69 }

rsiSasPriorityCallPerfCountersEntry OBJECT-TYPE
    SYNTAX          RsiSasPriorityCallPerfCountersEntry
    MAX-ACCESS      not-accessible
    STATUS          current
    DESCRIPTION     
            "Description of a Priority Call measurement counter of a particular subsystem."
    INDEX           { rsiSubsystemId }
    ::= { rsiSasPriorityCallPerfCounters 1 }

RsiSasPriorityCallPerfCountersEntry ::=
    SEQUENCE {
        rsiMeasurementPriCallCounterValueId   DisplayString,
        rsiMeasurementPriCallCounterValue Integer32
    }

rsiMeasurementPriCallCounterValueId OBJECT-TYPE
    SYNTAX          DisplayString
    MAX-ACCESS      read-only
    STATUS          current
    DESCRIPTION     
            "Measurement Priority Call Counter Identifier"
    ::= { rsiSasPriorityCallPerfCountersEntry 1 }

rsiMeasurementPriCallCounterValue OBJECT-TYPE
    SYNTAX          Integer32
    MAX-ACCESS      read-only
    STATUS          current
    DESCRIPTION     
            "This is value of rsiMeasurementCounterID/rsiSystemID/rsiMeasurementCounterValueId"
    ::= { rsiSasPriorityCallPerfCountersEntry 2 }

rsiTraps OBJECT IDENTIFIER
    ::= { rsiMib 10 }

rsiCommunicationFailure NOTIFICATION-TYPE
    OBJECTS         { rsiAlarmId, rsiRelatedAlarmId, rsiAlarmDateTime, 
                      rsiAlarmErrorCode, rsiAlarmContent, 
                      rsiOriginatingSubsystemId, 
                      rsiOriginatingSubsystemName, 
                      rsiTroublingSubsystemId, rsiTroublingSubsystemName, 
                      rsiAlarmSeverity, rsiOrigSystemId, 
                      rsiOrigSystemName, rsiOrigHostId, rsiOrigHostName }
    STATUS          current
    DESCRIPTION     
            "This defines the alarms corresponding to communication 
             failure between two subsystems"
    ::= { rsiTraps 1 }

rsiConfigurationError NOTIFICATION-TYPE
    OBJECTS         { rsiAlarmId, rsiRelatedAlarmId, rsiAlarmDateTime, 
                      rsiAlarmErrorCode, rsiAlarmContent, 
                      rsiOriginatingSubsystemId, 
                      rsiOriginatingSubsystemName, 
                      rsiTroublingSubsystemId, rsiTroublingSubsystemName, 
                      rsiAlarmSeverity, rsiOrigSystemId, 
                      rsiOrigSystemName, rsiOrigHostId, rsiOrigHostName }
    STATUS          current
    DESCRIPTION     
            "This defines the alarms raised because of configuration
             errors of a subsystem. For ex: a directory not found"
    ::= { rsiTraps 2 }

rsiSystemFaults NOTIFICATION-TYPE
    OBJECTS         { rsiAlarmId, rsiRelatedAlarmId, rsiAlarmDateTime, 
                      rsiAlarmErrorCode, rsiAlarmContent, 
                      rsiOriginatingSubsystemId, 
                      rsiOriginatingSubsystemName, 
                      rsiTroublingSubsystemId, rsiTroublingSubsystemName, 
                      rsiAlarmSeverity, rsiOrigSystemId, 
                      rsiOrigSystemName, rsiOrigHostId, rsiOrigHostName }
    STATUS          current
    DESCRIPTION     
            "This defines the alarms rasied by subsystems. For ex:
             subsystem is up/down, etc"
    ::= { rsiTraps 3 }

rsiSystemCapacity NOTIFICATION-TYPE
    OBJECTS         { rsiAlarmId, rsiRelatedAlarmId, rsiAlarmDateTime, 
                      rsiAlarmErrorCode, rsiAlarmContent, 
                      rsiOriginatingSubsystemId, 
                      rsiOriginatingSubsystemName, 
                      rsiTroublingSubsystemId, rsiTroublingSubsystemName, 
                      rsiAlarmSeverity, rsiOrigSystemId, 
                      rsiOrigSystemName, rsiOrigHostId, rsiOrigHostName }
    STATUS          current
    DESCRIPTION     
            "This defines the alarms corresponding to system capacity 
             overflow. For ex: buffer overflow, max. no of service
             instances exceeded."
    ::= { rsiTraps 4 }

rsiResourceFailure NOTIFICATION-TYPE
    OBJECTS         { rsiAlarmId, rsiRelatedAlarmId, rsiAlarmDateTime, 
                      rsiAlarmErrorCode, rsiAlarmContent, 
                      rsiOriginatingSubsystemId, 
                      rsiOriginatingSubsystemName, 
                      rsiTroublingSubsystemId, rsiTroublingSubsystemName, 
                      rsiAlarmSeverity, rsiOrigSystemId, 
                      rsiOrigSystemName, rsiOrigHostId, rsiOrigHostName }
    STATUS          current
    DESCRIPTION     
            "This defines the alarms corresponding to Resource Failure. 
             For ex: database write failed, file open failed, etc"
    ::= { rsiTraps 5 }

rsiApplicationError NOTIFICATION-TYPE
    OBJECTS         { rsiAlarmId, rsiRelatedAlarmId, rsiAlarmDateTime, 
                      rsiAlarmErrorCode, rsiAlarmContent, 
                      rsiOriginatingSubsystemId, 
                      rsiOriginatingSubsystemName, 
                      rsiTroublingSubsystemId, rsiTroublingSubsystemName, 
                      rsiAlarmSeverity, rsiOrigSystemId, 
                      rsiOrigSystemName, rsiOrigHostId, rsiOrigHostName }
    STATUS          current
    DESCRIPTION     
            "This defines the alarms corresponding to application errors. 
             For ex: wrong format of input CDR, incomplete input CDR, etc"
    ::= { rsiTraps 6 }

rsiThresholdAlarm NOTIFICATION-TYPE
    OBJECTS         { rsiAlarmId, rsiRelatedAlarmId, rsiAlarmDateTime, 
                      rsiAlarmErrorCode, rsiAlarmContent, 
                      rsiOriginatingSubsystemId, 
                      rsiOriginatingSubsystemName, 
                      rsiTroublingSubsystemId, rsiTroublingSubsystemName, 
                      rsiAlarmSeverity, rsiOrigSystemId, 
                      rsiOrigSystemName, rsiOrigHostId, rsiOrigHostName }
    STATUS          current
    DESCRIPTION     
            "This defines the alarms corresponding to threshold errors. 
             For ex: CPU usage exceeded a given threshold"
    ::= { rsiTraps 7 }

rsiSecurityAlarm NOTIFICATION-TYPE
    OBJECTS         { rsiAlarmId, rsiRelatedAlarmId, rsiAlarmDateTime, 
                      rsiAlarmErrorCode, rsiAlarmContent, 
                      rsiOriginatingSubsystemId, 
                      rsiOriginatingSubsystemName, 
                      rsiTroublingSubsystemId, rsiTroublingSubsystemName, 
                      rsiAlarmSeverity, rsiOrigSystemId, 
                      rsiOrigSystemName, rsiOrigHostId, rsiOrigHostName, 
                      rsiUserId }
    STATUS          current
    DESCRIPTION     
            "This defines the security alarms. For ex: if a user tries
             to login in for 3 consecutive times, and enters a wrong
             password, then an alarm would be raised."
    ::= { rsiTraps 8 }

END -- end of module BAY-PACKETS-EMS-MIB.
