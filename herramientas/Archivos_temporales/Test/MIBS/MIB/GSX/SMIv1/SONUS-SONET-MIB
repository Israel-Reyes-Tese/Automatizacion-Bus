--
-- This SMIv1 module has been generated by smidump 0.2-cvs. Do not edit.
--

SONUS-SONET-MIB DEFINITIONS ::= BEGIN

IMPORTS
    ifIndex
        FROM IF-MIB
    PerfCurrentCount, PerfIntervalCount
        FROM PerfHist-TC-MIB
    OBJECT-TYPE
        FROM RFC-1212
    TRAP-TYPE
        FROM RFC-1215
    RowStatus, TruthValue
        FROM SNMPv2-TC
    sonusEventClass, sonusEventDescription, sonusEventLevel, 
    sonusEventTime, sonusPimIndex, sonusPortIndex, sonusSequenceId, 
    sonusShelfIndex, sonusSlotIndex
        FROM SONUS-COMMON-MIB
    sonusCircuitMIBs
        FROM SONUS-SMI
    SonusAdminAction, SonusAdminState, SonusName, SonusServiceState, 
    SonusShelfIndex, SonusSlotIndex
        FROM SONUS-TC;

sonusSonetMIB OBJECT IDENTIFIER
    ::= { sonusCircuitMIBs 3 }

-- sonusSonetMIB MODULE-IDENTITY
--     LAST-UPDATED    "201706130000Z"
--     ORGANIZATION    
--             "Sonus Networks, Inc."
--     CONTACT-INFO    
--             "   Customer Support    
--              Sonus Networks, Inc.
--              7 Technology Park Drive
--              Westford, MA 01886
--              USA
--              
--              Tel: 978-614-8100
--              Fax: 978-614-8609"
--     DESCRIPTION     
--             "The MIB Module for Sonus SONET/SDH extensions."
--     ::= { sonusCircuitMIBs 3 }


sonusSonetObjects OBJECT IDENTIFIER
    ::= { sonusSonetMIB 1 }

sonusSonetPortAdmn OBJECT IDENTIFIER
    ::= { sonusSonetObjects 1 }

sonusSonetPortAdmnTable OBJECT-TYPE
    SYNTAX          SEQUENCE OF SonusSonetPortAdmnEntry
    ACCESS          not-accessible
    STATUS          mandatory
    DESCRIPTION     
            "The Sonus SONET Port Admn Table."
    ::= { sonusSonetPortAdmn 1 }

sonusSonetPortAdmnEntry OBJECT-TYPE
    SYNTAX          SonusSonetPortAdmnEntry
    ACCESS          not-accessible
    STATUS          mandatory
    DESCRIPTION     
            "An entry in the Sonus SONET Port Admn table."
    INDEX           { sonusSonetPortAdmnIfIndex }
    ::= { sonusSonetPortAdmnTable 1 }

SonusSonetPortAdmnEntry ::=
    SEQUENCE {
        sonusSonetPortAdmnIfIndex       INTEGER,
        sonusSonetPortAdmnShelfIndex    SonusShelfIndex,
        sonusSonetPortAdmnSlotIndex     SonusSlotIndex,
        sonusSonetPortAdmnPortIndex     INTEGER,
        sonusSonetPortAdmnRowStatus     RowStatus,
        sonusSonetPortAdmnName          SonusName,
        sonusSonetPortAdmnState         SonusAdminState,
        sonusSonetPortAdmnMode          SonusServiceState,
        sonusSonetPortAdmnAction        SonusAdminAction,
        sonusSonetPortAdmnTimeout       INTEGER,
        sonusSonetPortAdmnStatAction    INTEGER,
        sonusSonetPortAdmnLaserState    INTEGER,
        sonusSonetPortAdmn24hTimeElapsed INTEGER,
        sonusSonetPortAdmnOperStatus    INTEGER,
        sonusSonetPortAdmnDs3ModeOverride SonusAdminState,
        sonusSonetPortAdmnStsXmtScramble SonusAdminState,
        sonusSonetPortAdmnStsRcvDescramble  SonusAdminState,
        sonusSonetPortAdmnAtmXmtScramble SonusAdminState,
        sonusSonetPortAdmnAtmRcvDescramble  SonusAdminState,
        sonusSonetPortAdmnPayloadMapping INTEGER,
        sonusSonetPortAdmnApsChannelIndex INTEGER,
        sonusSonetPortAdmnNetworkType   INTEGER,
        sonusSonetPortAdmnApsChannelStatus  INTEGER,
        sonusSonetPortAdmnAlarmHierarchy SonusAdminState,
        sonusSonetPortAdmnInitStatistics SonusAdminState,
        sonusSonetPortAdmnTraceState    SonusAdminState,
        sonusSonetPortAdmnTraceExpMsg   DisplayString,
        sonusSonetPortAdmnTraceXmtMsg   DisplayString,
        sonusSonetPortAdmnTraceRcvMsg   DisplayString,
        sonusSonetPortAdmnSigMultiplexMode  INTEGER,
        sonusSonetPortAdmnSignalStruct  DisplayString,
        sonusSonetPortAdmnTribMappingMode INTEGER
    }

sonusSonetPortAdmnIfIndex OBJECT-TYPE
    SYNTAX          INTEGER
    ACCESS          not-accessible
    STATUS          mandatory
    DESCRIPTION     
            "The ifIndex assigned to this port when it was created.
             This will not change until the port is deleted."
    ::= { sonusSonetPortAdmnEntry 1 }

sonusSonetPortAdmnShelfIndex OBJECT-TYPE
    SYNTAX          SonusShelfIndex
    ACCESS          read-write
    STATUS          mandatory
    DESCRIPTION     
            "Shelf index for this table."
    ::= { sonusSonetPortAdmnEntry 2 }

sonusSonetPortAdmnSlotIndex OBJECT-TYPE
    SYNTAX          SonusSlotIndex
    ACCESS          read-write
    STATUS          mandatory
    DESCRIPTION     
            "Slot index for this table."
    ::= { sonusSonetPortAdmnEntry 3 }

sonusSonetPortAdmnPortIndex OBJECT-TYPE
    SYNTAX          INTEGER (1..4)
    ACCESS          read-write
    STATUS          mandatory
    DESCRIPTION     
            "OC3 port index for this table."
    ::= { sonusSonetPortAdmnEntry 4 }

sonusSonetPortAdmnRowStatus OBJECT-TYPE
    SYNTAX          RowStatus
    ACCESS          read-write
    STATUS          mandatory
    DESCRIPTION     
            "This object is used to create, delete, or modify a row in this table."
    ::= { sonusSonetPortAdmnEntry 5 }

sonusSonetPortAdmnName OBJECT-TYPE
    SYNTAX          SonusName
    ACCESS          read-write
    STATUS          mandatory
    DESCRIPTION     
            "Name of this STS3"
    ::= { sonusSonetPortAdmnEntry 6 }

sonusSonetPortAdmnState OBJECT-TYPE
    SYNTAX          SonusAdminState
    ACCESS          read-write
    STATUS          mandatory
    DESCRIPTION     
            "State of STS3, Enabled/Disabled"
    DEFVAL          { disabled }
    ::= { sonusSonetPortAdmnEntry 7 }

sonusSonetPortAdmnMode OBJECT-TYPE
    SYNTAX          SonusServiceState
    ACCESS          read-write
    STATUS          mandatory
    DESCRIPTION     
            "SONET port entries are created with a mode of outOfService. A
             SONET port which is outOfService has had all active calls
             terminated. A SOENT port must be outOfService in order to change
             its state to disabled."
    DEFVAL          { outOfService }
    ::= { sonusSonetPortAdmnEntry 8 }

sonusSonetPortAdmnAction OBJECT-TYPE
    SYNTAX          SonusAdminAction
    ACCESS          read-write
    STATUS          mandatory
    DESCRIPTION     
            "The type of action to perform when a SONET port is taken out of 
             service. The SONET port can be dried up, or it can be forced
             out of service."
    DEFVAL          { dryUp }
    ::= { sonusSonetPortAdmnEntry 9 }

sonusSonetPortAdmnTimeout OBJECT-TYPE
    SYNTAX          INTEGER (0..1440)
    ACCESS          read-write
    STATUS          mandatory
    DESCRIPTION     
            "The Dryup Timeout specifies the maximum amount of time to wait for
             all active calls to terminate on a SONET port before the port
             		 should be taken out-of-service."
    DEFVAL          { 5 }
    ::= { sonusSonetPortAdmnEntry 10 }

sonusSonetPortAdmnStatAction OBJECT-TYPE
    SYNTAX          INTEGER { init15MinuteNearEnd(1), 
                        init15MinuteFarEnd(2), init24HourNearEnd(4), 
                        init24HourFarEnd(8) }
    ACCESS          read-write
    STATUS          mandatory
    DESCRIPTION     
            "Initialize Performance Monitoring Statistics. A PM initialization
             action initiates one request for the action. Requests to initialize
             more than one group of statistics can be accomplished by OR-ing the 
             appropriate bits (e.g., to initialize all 15 minute PM statistics, 
             set bits 1 and 2). Reading this variable always returns zero."
    ::= { sonusSonetPortAdmnEntry 11 }

sonusSonetPortAdmnLaserState OBJECT-TYPE
    SYNTAX          INTEGER { on(1), off(2) }
    ACCESS          read-write
    STATUS          mandatory
    DESCRIPTION     
            "Controls whether the fiber-optic laser is On or Off."
    DEFVAL          { on }
    ::= { sonusSonetPortAdmnEntry 12 }

sonusSonetPortAdmn24hTimeElapsed OBJECT-TYPE
    SYNTAX          INTEGER (0..86400)
    ACCESS          read-only
    STATUS          mandatory
    DESCRIPTION     
            "The number of seconds, including partial seconds,
             that have elapsed since the beginning of the current
             24 hour measurement period."
    ::= { sonusSonetPortAdmnEntry 13 }

sonusSonetPortAdmnOperStatus OBJECT-TYPE
    SYNTAX          INTEGER { enabledInService(1), 
                        enabledOutOfService(2), enabledDown(3), 
                        dryingUp(4), disabled(5), up(6), down(7), 
                        remoteDown(8) }
    ACCESS          read-only
    STATUS          mandatory
    DESCRIPTION     
            "The actual status of the Sonet interface. Interface is 
             Up if it is administratively in service and there are no
             line failures or hardware failures. Interface is Down if
             it is administratively in service and there are line
             failures or hardware failures, or if it is administratively
             out of service. Interface is DryingUp if it is administratively
             out of service and is drying up (no new	calls, still carrying
             in-progress calls). OTHER VALUES ARE NO LONGER SUPPORTED"
    ::= { sonusSonetPortAdmnEntry 14 }

sonusSonetPortAdmnDs3ModeOverride OBJECT-TYPE
    SYNTAX          SonusAdminState
    ACCESS          read-write
    STATUS          mandatory
    DESCRIPTION     
            "This flag controls whether the mode and state of the Paths
             carried in an OC3 are modified when the mode and state of
             the OC3 is modified. If this flag is set to Enabled, the Path
             state and mode are not changed when the OC3 mode and state
             are changed."
    DEFVAL          { disabled }
    ::= { sonusSonetPortAdmnEntry 15 }

sonusSonetPortAdmnStsXmtScramble OBJECT-TYPE
    SYNTAX          SonusAdminState
    ACCESS          read-write
    STATUS          mandatory
    DESCRIPTION     
            "Controls whether the transmitted STS-N data stream is scrambled.
             If this flag is set to Enabled, the data is scrambled."
    DEFVAL          { enabled }
    ::= { sonusSonetPortAdmnEntry 16 }

sonusSonetPortAdmnStsRcvDescramble OBJECT-TYPE
    SYNTAX          SonusAdminState
    ACCESS          read-write
    STATUS          mandatory
    DESCRIPTION     
            "Controls whether the received STS-N data stream is descrambled.
             If this flag is set to Enabled, the data is descrambled."
    DEFVAL          { enabled }
    ::= { sonusSonetPortAdmnEntry 17 }

sonusSonetPortAdmnAtmXmtScramble OBJECT-TYPE
    SYNTAX          SonusAdminState
    ACCESS          read-write
    STATUS          mandatory
    DESCRIPTION     
            "Controls whether the transmitted ATM payload data is scrambled.
             If this flag is set to Enabled, the data is scrambled. This
             object only pertains to interfaces carrying ATM."
    DEFVAL          { enabled }
    ::= { sonusSonetPortAdmnEntry 18 }

sonusSonetPortAdmnAtmRcvDescramble OBJECT-TYPE
    SYNTAX          SonusAdminState
    ACCESS          read-write
    STATUS          mandatory
    DESCRIPTION     
            "Controls whether the received ATM payload data is descrambled.
             If this flag is set to Enabled, the data is descrambled. This
             object only pertains to interfaces carrying ATM."
    DEFVAL          { enabled }
    ::= { sonusSonetPortAdmnEntry 19 }

sonusSonetPortAdmnPayloadMapping OBJECT-TYPE
    SYNTAX          INTEGER { notConfigured(1), t1BitAsync(2), 
                        t1ByteSync(3), e1BitAsync(4), e1ByteSync(5), 
                        ds3Async(6), stFrame(7), t1Tu12BitAsync(8) }
    ACCESS          read-write
    STATUS          mandatory
    DESCRIPTION     
            "Specifies the signal payload mapping of the Sonet/SDH signal.
             t1BitAsync (SONET): T1 bit async -> VT1.5 -> VTG
             t1BitAsync (SDH):   T1 bit async -> VC11 -> TU11 -> TUG2
             e1BitAsync (SONET): E1 bit async -> VT2 -> VTG
             e1BitAsync (SDH):   E1 bit async -> VC12 -> TU12 -> TUG2
             t1ByteSync (SONET): T1 byte sync -> VT1.5 -> VTG
             t1ByteSync (SDH):   T1 byte sync -> VC11 -> TU11 -> TUG2
             e1ByteSync (SONET): E1 byte sync -> VT2 -> VTG
             e1ByteSync (SDH):   E1 byte sync -> VC12 -> TU12 -> TUG2
             stFrame (SDH only): T1 byte sync -> VC11 -> TU11 -> TUG2 with W-Byte overhead
             t1Tu12BitAsync (SDH only): T1 bit async -> VC11 - TU12 -> TUG2"
    DEFVAL          { notConfigured }
    ::= { sonusSonetPortAdmnEntry 20 }

sonusSonetPortAdmnApsChannelIndex OBJECT-TYPE
    SYNTAX          INTEGER { upper(1), lower(2) }
    ACCESS          read-write
    STATUS          mandatory
    DESCRIPTION     
            "Physical adapter location of the optical port "
    ::= { sonusSonetPortAdmnEntry 21 }

sonusSonetPortAdmnNetworkType OBJECT-TYPE
    SYNTAX          INTEGER { notConfigured(1), sonet(2), sdh(3) }
    ACCESS          read-write
    STATUS          mandatory
    DESCRIPTION     
            "Identifies whether a SONET	or SDH signal is used across this interface."
    DEFVAL          { notConfigured }
    ::= { sonusSonetPortAdmnEntry 22 }

sonusSonetPortAdmnApsChannelStatus OBJECT-TYPE
    SYNTAX          INTEGER { active(1), notActive(2) }
    ACCESS          read-only
    STATUS          mandatory
    DESCRIPTION     
            "Indicates whether the port is currently the APS Active Channel
             (carrying traffic) or APS Not Active Channel (not carrying traffic)."
    ::= { sonusSonetPortAdmnEntry 23 }

sonusSonetPortAdmnAlarmHierarchy OBJECT-TYPE
    SYNTAX          SonusAdminState
    ACCESS          read-write
    STATUS          mandatory
    DESCRIPTION     
            "Controls whether only the root-cause alarm is reported (via
             an event log and trap) and all lower-layer interface alarms
             are supressed. For example, if a Section-layer alarm is
             detected, it will be reported, while the resulting Line/Path/VT/DSx
             alarms will not be reported."
    DEFVAL          { enabled }
    ::= { sonusSonetPortAdmnEntry 24 }

sonusSonetPortAdmnInitStatistics OBJECT-TYPE
    SYNTAX          SonusAdminState
    ACCESS          read-write
    STATUS          mandatory
    DESCRIPTION     
            "Initializes Section/Line error statistics counts to zero."
    DEFVAL          { disabled }
    ::= { sonusSonetPortAdmnEntry 25 }

sonusSonetPortAdmnTraceState OBJECT-TYPE
    SYNTAX          SonusAdminState
    ACCESS          read-write
    STATUS          mandatory
    DESCRIPTION     
            "The desired state of SONET Section Trace.
             (1) enabled - Enables the generation of SONET Section Trace Messages
             in the J0 bytes of the Section overhead, and enables the reception and
             checking of received Section Trace Messages with the Expected Section Trace
             Message.
             (2) disabled - Transmits all zero's in the J0 bytes of the Section
             overhead, and disables the reception and checking of received
             Section Trace Messages with the Expected Section Trace Message."
    DEFVAL          { disabled }
    ::= { sonusSonetPortAdmnEntry 26 }

sonusSonetPortAdmnTraceExpMsg OBJECT-TYPE
    SYNTAX          DisplayString (SIZE(0..15))
    ACCESS          read-write
    STATUS          mandatory
    DESCRIPTION     
            "The expected Section trace string to be received on the SONET port in the
             J0 bytes of the Section overhead."
    ::= { sonusSonetPortAdmnEntry 27 }

sonusSonetPortAdmnTraceXmtMsg OBJECT-TYPE
    SYNTAX          DisplayString (SIZE(0..15))
    ACCESS          read-write
    STATUS          mandatory
    DESCRIPTION     
            "The Section trace string to be transmitted on the SONET port in the J0
             bytes of the Section overhead."
    ::= { sonusSonetPortAdmnEntry 28 }

sonusSonetPortAdmnTraceRcvMsg OBJECT-TYPE
    SYNTAX          DisplayString (SIZE(0..15))
    ACCESS          read-only
    STATUS          mandatory
    DESCRIPTION     
            "The Section trace string received on the SONET port in the J0
             bytes of the Section overhead."
    ::= { sonusSonetPortAdmnEntry 29 }

sonusSonetPortAdmnSigMultiplexMode OBJECT-TYPE
    SYNTAX          INTEGER { notConfigured(1), auto(2), au3Sts1(3), 
                        au4Sts3c(4) }
    ACCESS          read-write
    STATUS          mandatory
    DESCRIPTION     
            "Specifies VC-3/AU-3 or VC-4/AU-4 signal multiplex structure for
             SDH. Specifies STS1 or STS3c signal multiplex structure for SONET.
             If set to 'auto', the 'standard' signal multiplex structure is
             automatically selected by software, based on configured value of
             sonusSonetPortAdmnPayloadMapping.
             	t1BitAsync		au3Sts1
             	t1ByteSync		au3Sts1
             	e1BitAsync		au4Sts3c for SDH, au3Sts1 for SONET
             	e1ByteSync		au4Sts3c for SDH, au3Sts1 for SONET
             	t1Tu12BitAsync	au4 (SDH only)
             	stFrame			au3 (SDH only)"
    DEFVAL          { notConfigured }
    ::= { sonusSonetPortAdmnEntry 30 }

sonusSonetPortAdmnSignalStruct OBJECT-TYPE
    SYNTAX          DisplayString (SIZE(0..64))
    ACCESS          read-only
    STATUS          mandatory
    DESCRIPTION     
            "String displays the configured signal multiplexing structure."
    ::= { sonusSonetPortAdmnEntry 31 }

sonusSonetPortAdmnTribMappingMode OBJECT-TYPE
    SYNTAX          INTEGER { notConfigured(1), auto(2), standard(3), 
                        stdTransposed(4), sequential(5), 
                        seqTransposed(6) }
    ACCESS          read-write
    STATUS          mandatory
    DESCRIPTION     
            "Specifies the mapping of T1/E1 tributaries into VT/TU structure.
             If set to 'auto', the tributary mapping mode is automatically
             selected by software, based on the configured value of
             sonusSonetPortAdmnPayloadMapping:
             	t1BitAsync		standard
             	t1ByteSync		standard
             	e1BitAsync		sequential
             	e1ByteSync		sequential
             	t1Tu12BitAsync	sequential
             	stFrame			standard"
    DEFVAL          { notConfigured }
    ::= { sonusSonetPortAdmnEntry 32 }

sonusSonetSection OBJECT IDENTIFIER
    ::= { sonusSonetObjects 2 }

sonusSonetSectionThresholdTable OBJECT-TYPE
    SYNTAX          SEQUENCE OF SonusSonetSectionThresholdEntry
    ACCESS          not-accessible
    STATUS          mandatory
    DESCRIPTION     
            "The Sonus SONET Section Threshold Table. This table adds objects
             to set the Performance Monitoring thresholds for generating a
             Threshold Crossing Alert."
    ::= { sonusSonetSection 1 }

sonusSonetSectionThresholdEntry OBJECT-TYPE
    SYNTAX          SonusSonetSectionThresholdEntry
    ACCESS          not-accessible
    STATUS          mandatory
    DESCRIPTION     
            "An entry in the Sonus SONET Section Threshold table."
    INDEX           { sonusSonetSectionThresholdIfIndex }
    ::= { sonusSonetSectionThresholdTable 1 }

SonusSonetSectionThresholdEntry ::=
    SEQUENCE {
        sonusSonetSectionThresholdIfIndex INTEGER,
        sonusSonetSectionThreshold15mCVs INTEGER,
        sonusSonetSectionThreshold15mESs INTEGER,
        sonusSonetSectionThreshold15mSESs INTEGER,
        sonusSonetSectionThreshold15mSEFSs  INTEGER,
        sonusSonetSectionThreshold24hCVs INTEGER,
        sonusSonetSectionThreshold24hESs INTEGER,
        sonusSonetSectionThreshold24hSESs INTEGER,
        sonusSonetSectionThreshold24hSEFSs  INTEGER,
        sonusSonetSectionThresholdCVTcaFilter     SonusAdminState,
        sonusSonetSectionThresholdESTcaFilter     SonusAdminState,
        sonusSonetSectionThresholdSESTcaFilter      SonusAdminState,
        sonusSonetSectionThresholdSEFSTcaFilter       SonusAdminState
    }

sonusSonetSectionThresholdIfIndex OBJECT-TYPE
    SYNTAX          INTEGER
    ACCESS          not-accessible
    STATUS          mandatory
    DESCRIPTION     
            "The ifIndex assigned to this port when it was created.
             This will not change until the port is deleted."
    ::= { sonusSonetSectionThresholdEntry 1 }

sonusSonetSectionThreshold15mCVs OBJECT-TYPE
    SYNTAX          INTEGER (0..16383)
    ACCESS          read-write
    STATUS          mandatory
    DESCRIPTION     
            "Threshold for 15 minute interval Section layer Coding Violations."
    ::= { sonusSonetSectionThresholdEntry 2 }

sonusSonetSectionThreshold15mESs OBJECT-TYPE
    SYNTAX          INTEGER (0..16383)
    ACCESS          read-write
    STATUS          mandatory
    DESCRIPTION     
            "Threshold for 15 minute interval Section layer Errored Seconds."
    ::= { sonusSonetSectionThresholdEntry 3 }

sonusSonetSectionThreshold15mSESs OBJECT-TYPE
    SYNTAX          INTEGER (0..900)
    ACCESS          read-write
    STATUS          mandatory
    DESCRIPTION     
            "Threshold for 15 minute interval Section layer Severely Errored
             Seconds."
    ::= { sonusSonetSectionThresholdEntry 4 }

sonusSonetSectionThreshold15mSEFSs OBJECT-TYPE
    SYNTAX          INTEGER (0..900)
    ACCESS          read-write
    STATUS          mandatory
    DESCRIPTION     
            "Threshold for 15 minute interval Section layer Severely Errored
             Frame Seconds."
    ::= { sonusSonetSectionThresholdEntry 5 }

sonusSonetSectionThreshold24hCVs OBJECT-TYPE
    SYNTAX          INTEGER (0..1048575)
    ACCESS          read-write
    STATUS          mandatory
    DESCRIPTION     
            "Threshold for 24 hour interval Section layer Coding Violations."
    ::= { sonusSonetSectionThresholdEntry 6 }

sonusSonetSectionThreshold24hESs OBJECT-TYPE
    SYNTAX          INTEGER (0..65535)
    ACCESS          read-write
    STATUS          mandatory
    DESCRIPTION     
            "Threshold for 24 hour interval Section layer Errored Seconds."
    ::= { sonusSonetSectionThresholdEntry 7 }

sonusSonetSectionThreshold24hSESs OBJECT-TYPE
    SYNTAX          INTEGER (0..65535)
    ACCESS          read-write
    STATUS          mandatory
    DESCRIPTION     
            "Threshold for 24 hour interval Section layer Severely Errored
             Seconds."
    ::= { sonusSonetSectionThresholdEntry 8 }

sonusSonetSectionThreshold24hSEFSs OBJECT-TYPE
    SYNTAX          INTEGER (0..65535)
    ACCESS          read-write
    STATUS          mandatory
    DESCRIPTION     
            "Threshold for 24 hour interval Section layer Severely Errored
             Frame Seconds."
    ::= { sonusSonetSectionThresholdEntry 9 }

sonusSonetSectionThresholdCVTcaFilter OBJECT-TYPE
    SYNTAX          SonusAdminState
    ACCESS          read-write
    STATUS          mandatory
    DESCRIPTION     
            "Controls whether a threshold Crossing Alert (TCA) is reported (via
             an event log and trap). Setting this object to Enabled will prevent
             the TCA from being reported (i.e will Filter the TCA report)."
    DEFVAL          { disabled }
    ::= { sonusSonetSectionThresholdEntry 10 }

sonusSonetSectionThresholdESTcaFilter OBJECT-TYPE
    SYNTAX          SonusAdminState
    ACCESS          read-write
    STATUS          mandatory
    DESCRIPTION     
            "Controls whether a threshold Crossing Alert (TCA) is reported (via
             an event log and trap). Setting this object to Enabled will prevent
             the TCA from being reported (i.e will Filter the TCA report)."
    DEFVAL          { disabled }
    ::= { sonusSonetSectionThresholdEntry 11 }

sonusSonetSectionThresholdSESTcaFilter OBJECT-TYPE
    SYNTAX          SonusAdminState
    ACCESS          read-write
    STATUS          mandatory
    DESCRIPTION     
            "Controls whether a threshold Crossing Alert (TCA) is reported (via
             an event log and trap). Setting this object to Enabled will prevent
             the TCA from being reported (i.e will Filter the TCA report)."
    DEFVAL          { disabled }
    ::= { sonusSonetSectionThresholdEntry 12 }

sonusSonetSectionThresholdSEFSTcaFilter OBJECT-TYPE
    SYNTAX          SonusAdminState
    ACCESS          read-write
    STATUS          mandatory
    DESCRIPTION     
            "Controls whether a threshold Crossing Alert (TCA) is reported (via
             an event log and trap). Setting this object to Enabled will prevent
             the TCA from being reported (i.e will Filter the TCA report)."
    DEFVAL          { disabled }
    ::= { sonusSonetSectionThresholdEntry 13 }

sonusSonetSectionCurrentTable OBJECT-TYPE
    SYNTAX          SEQUENCE OF SonusSonetSectionCurrentEntry
    ACCESS          not-accessible
    STATUS          mandatory
    DESCRIPTION     
            "The Sonus SONET Section Current table."
    ::= { sonusSonetSection 2 }

sonusSonetSectionCurrentEntry OBJECT-TYPE
    SYNTAX          SonusSonetSectionCurrentEntry
    ACCESS          not-accessible
    STATUS          mandatory
    DESCRIPTION     
            "An entry in the Sonus SONET Section Current table."
    INDEX           { sonusSonetSectionCurrentIfIndex }
    ::= { sonusSonetSectionCurrentTable 1 }

SonusSonetSectionCurrentEntry ::=
    SEQUENCE {
        sonusSonetSectionCurrentIfIndex INTEGER,
        sonusSonetSectionCurrentStatus  INTEGER,
        sonusSonetSectionCurrentESs     PerfCurrentCount,
        sonusSonetSectionCurrentSESs    PerfCurrentCount,
        sonusSonetSectionCurrentSEFSs   PerfCurrentCount,
        sonusSonetSectionCurrentCVs     PerfCurrentCount,
        sonusSonetSectionCurrentElapsedTime   INTEGER,
        sonusSonetSectionCurrentDayElapsedTime      INTEGER
    }

sonusSonetSectionCurrentIfIndex OBJECT-TYPE
    SYNTAX          INTEGER
    ACCESS          not-accessible
    STATUS          mandatory
    DESCRIPTION     
            "The ifIndex assigned to this port when it was created.
             This will not change until the port is deleted."
    ::= { sonusSonetSectionCurrentEntry 1 }

sonusSonetSectionCurrentStatus OBJECT-TYPE
    SYNTAX          INTEGER (1..8)
    ACCESS          read-only
    STATUS          mandatory
    DESCRIPTION     
            "This variable indicates the status of the interface. It is
             a bit map represented as a sum, therefore, it can represent
             multiple defects simultaneously. The sonetSectionNoDefect
             should be set if and only if no other flag is set.
             
             The various bit positions are:
             1   sonetSectionNoDefect
             2   sonetSectionLOS
             4   sonetSectionLOF
             8   sonetSectionNotMonitored
             16  sonetSectionTIM"
    ::= { sonusSonetSectionCurrentEntry 2 }

sonusSonetSectionCurrentESs OBJECT-TYPE
    SYNTAX          PerfCurrentCount
    ACCESS          read-only
    STATUS          mandatory
    DESCRIPTION     
            "The counter associated with the number of Errored Seconds
             encountered by a SONET/SDH Section in the current 24 hour
             interval."
    ::= { sonusSonetSectionCurrentEntry 3 }

sonusSonetSectionCurrentSESs OBJECT-TYPE
    SYNTAX          PerfCurrentCount
    ACCESS          read-only
    STATUS          mandatory
    DESCRIPTION     
            "The counter associated with the number of Severely Errored
             Seconds encountered by a SONET/SDH Section in the current 
             24 hour interval."
    ::= { sonusSonetSectionCurrentEntry 4 }

sonusSonetSectionCurrentSEFSs OBJECT-TYPE
    SYNTAX          PerfCurrentCount
    ACCESS          read-only
    STATUS          mandatory
    DESCRIPTION     
            "The counter associated with the number of Severely Errored
             Framing Seconds encountered by a SONET/SDH Section in the
             current 24 hour interval."
    ::= { sonusSonetSectionCurrentEntry 5 }

sonusSonetSectionCurrentCVs OBJECT-TYPE
    SYNTAX          PerfCurrentCount
    ACCESS          read-only
    STATUS          mandatory
    DESCRIPTION     
            "The counter associated with the number of Coding Violations
             encountered by a SONET/SDH Section in the current 24 hour
             	 interval."
    ::= { sonusSonetSectionCurrentEntry 6 }

sonusSonetSectionCurrentElapsedTime OBJECT-TYPE
    SYNTAX          INTEGER
    ACCESS          read-only
    STATUS          mandatory
    DESCRIPTION     
            "Elapsed time in the current period"
    ::= { sonusSonetSectionCurrentEntry 7 }

sonusSonetSectionCurrentDayElapsedTime OBJECT-TYPE
    SYNTAX          INTEGER
    ACCESS          read-only
    STATUS          mandatory
    DESCRIPTION     
            "Elapsed time in the current period"
    ::= { sonusSonetSectionCurrentEntry 8 }

sonusSonetSectionIntervalTable OBJECT-TYPE
    SYNTAX          SEQUENCE OF SonusSonetSectionIntervalEntry
    ACCESS          not-accessible
    STATUS          mandatory
    DESCRIPTION     
            "The Sonus SONET Section Interval table."
    ::= { sonusSonetSection 3 }

sonusSonetSectionIntervalEntry OBJECT-TYPE
    SYNTAX          SonusSonetSectionIntervalEntry
    ACCESS          not-accessible
    STATUS          mandatory
    DESCRIPTION     
            "An entry in the Sonus SONET Section Interval table."
    INDEX           { sonusSonetSectionIntervalIfIndex, 
                      sonusSonetSectionIntervalNumber }
    ::= { sonusSonetSectionIntervalTable 1 }

SonusSonetSectionIntervalEntry ::=
    SEQUENCE {
        sonusSonetSectionIntervalIfIndex INTEGER,
        sonusSonetSectionIntervalNumber INTEGER,
        sonusSonetSectionIntervalESs    PerfCurrentCount,
        sonusSonetSectionIntervalSESs   PerfCurrentCount,
        sonusSonetSectionIntervalSEFSs  PerfCurrentCount,
        sonusSonetSectionIntervalCVs    PerfCurrentCount,
        sonusSonetSectionIntervalValidData  TruthValue
    }

sonusSonetSectionIntervalIfIndex OBJECT-TYPE
    SYNTAX          INTEGER
    ACCESS          not-accessible
    STATUS          mandatory
    DESCRIPTION     
            "The ifIndex assigned to this port when it was created.
             This will not change until the port is deleted."
    ::= { sonusSonetSectionIntervalEntry 1 }

sonusSonetSectionIntervalNumber OBJECT-TYPE
    SYNTAX          INTEGER (1)
    ACCESS          not-accessible
    STATUS          mandatory
    DESCRIPTION     
            "The number 1 identifies the most recently completed 24 hour
             interval. In the future if more 24 hour intervals are supported,
             the interval identified by N is the interval immediately
             preceding the one identified by N-1."
    ::= { sonusSonetSectionIntervalEntry 2 }

sonusSonetSectionIntervalESs OBJECT-TYPE
    SYNTAX          PerfCurrentCount
    ACCESS          read-only
    STATUS          mandatory
    DESCRIPTION     
            "The counter associated with the number of Errored Seconds
             encountered by a SONET/SDH Section in the previous 24 hour
             interval."
    ::= { sonusSonetSectionIntervalEntry 3 }

sonusSonetSectionIntervalSESs OBJECT-TYPE
    SYNTAX          PerfCurrentCount
    ACCESS          read-only
    STATUS          mandatory
    DESCRIPTION     
            "The counter associated with the number of Severely Errored
             Seconds encountered by a SONET/SDH Section in the previous 
             24 hour interval."
    ::= { sonusSonetSectionIntervalEntry 4 }

sonusSonetSectionIntervalSEFSs OBJECT-TYPE
    SYNTAX          PerfCurrentCount
    ACCESS          read-only
    STATUS          mandatory
    DESCRIPTION     
            "The counter associated with the number of Severely Errored
             Framing Seconds encountered by a SONET/SDH Section in the
             previous 24 hour interval."
    ::= { sonusSonetSectionIntervalEntry 5 }

sonusSonetSectionIntervalCVs OBJECT-TYPE
    SYNTAX          PerfCurrentCount
    ACCESS          read-only
    STATUS          mandatory
    DESCRIPTION     
            "The counter associated with the number of Coding Violations
             encountered by a SONET/SDH Section in the previous 24 hour
             	 interval."
    ::= { sonusSonetSectionIntervalEntry 6 }

sonusSonetSectionIntervalValidData OBJECT-TYPE
    SYNTAX          TruthValue
    ACCESS          read-only
    STATUS          mandatory
    DESCRIPTION     
            "This variable indicates if the data for this interval is valid."
    ::= { sonusSonetSectionIntervalEntry 7 }

sonusSonetSectionTcaTable OBJECT-TYPE
    SYNTAX          SEQUENCE OF SonusSonetSectionTcaEntry
    ACCESS          not-accessible
    STATUS          mandatory
    DESCRIPTION     
            "The Sonus SONET Section Threshold Crossing Alert table."
    ::= { sonusSonetSection 4 }

sonusSonetSectionTcaEntry OBJECT-TYPE
    SYNTAX          SonusSonetSectionTcaEntry
    ACCESS          not-accessible
    STATUS          mandatory
    DESCRIPTION     
            "An entry in the Sonus SONET Section Threshold Crossing Alert table."
    INDEX           { sonusSonetSectionTcaIfIndex }
    ::= { sonusSonetSectionTcaTable 1 }

SonusSonetSectionTcaEntry ::=
    SEQUENCE {
        sonusSonetSectionTcaIfIndex     INTEGER,
        sonusSonetSectionTca15mES       TruthValue,
        sonusSonetSectionTca15mSES      TruthValue,
        sonusSonetSectionTca15mSEFS     TruthValue,
        sonusSonetSectionTca15mCV       TruthValue,
        sonusSonetSectionTca24hES       TruthValue,
        sonusSonetSectionTca24hSES      TruthValue,
        sonusSonetSectionTca24hSEFS     TruthValue,
        sonusSonetSectionTca24hCV       TruthValue
    }

sonusSonetSectionTcaIfIndex OBJECT-TYPE
    SYNTAX          INTEGER
    ACCESS          not-accessible
    STATUS          mandatory
    DESCRIPTION     
            "The ifIndex assigned to this port when it was created.
             This will not change until the port is deleted."
    ::= { sonusSonetSectionTcaEntry 1 }

sonusSonetSectionTca15mES OBJECT-TYPE
    SYNTAX          TruthValue
    ACCESS          read-only
    STATUS          mandatory
    DESCRIPTION     
            "Indicates status of threshold crossing for Section Errored
             Seconds in the current 15 minute interval."
    ::= { sonusSonetSectionTcaEntry 2 }

sonusSonetSectionTca15mSES OBJECT-TYPE
    SYNTAX          TruthValue
    ACCESS          read-only
    STATUS          mandatory
    DESCRIPTION     
            "Indicates status of threshold crossing for Section Severely
             Errored Seconds in the current 15 minute interval."
    ::= { sonusSonetSectionTcaEntry 3 }

sonusSonetSectionTca15mSEFS OBJECT-TYPE
    SYNTAX          TruthValue
    ACCESS          read-only
    STATUS          mandatory
    DESCRIPTION     
            "Indicates status of threshold crossing for Section Severely
             Errored Frame Seconds in the current 15 minute interval."
    ::= { sonusSonetSectionTcaEntry 4 }

sonusSonetSectionTca15mCV OBJECT-TYPE
    SYNTAX          TruthValue
    ACCESS          read-only
    STATUS          mandatory
    DESCRIPTION     
            "Indicates status of threshold crossing for Section Coding
             Violations in the current 15 minute interval."
    ::= { sonusSonetSectionTcaEntry 5 }

sonusSonetSectionTca24hES OBJECT-TYPE
    SYNTAX          TruthValue
    ACCESS          read-only
    STATUS          mandatory
    DESCRIPTION     
            "Indicates status of threshold crossing for Section Errored
             Seconds in the current 24 hour interval."
    ::= { sonusSonetSectionTcaEntry 6 }

sonusSonetSectionTca24hSES OBJECT-TYPE
    SYNTAX          TruthValue
    ACCESS          read-only
    STATUS          mandatory
    DESCRIPTION     
            "Indicates status of threshold crossing for Section Severely
             Errored Seconds in the current 24 hour interval."
    ::= { sonusSonetSectionTcaEntry 7 }

sonusSonetSectionTca24hSEFS OBJECT-TYPE
    SYNTAX          TruthValue
    ACCESS          read-only
    STATUS          mandatory
    DESCRIPTION     
            "Indicates status of threshold crossing for Section Severely
             Errored Frame Seconds in the current 24 hour interval."
    ::= { sonusSonetSectionTcaEntry 8 }

sonusSonetSectionTca24hCV OBJECT-TYPE
    SYNTAX          TruthValue
    ACCESS          read-only
    STATUS          mandatory
    DESCRIPTION     
            "Indicates status of threshold crossing for Section Coding
             Violations in the current 24 hour interval."
    ::= { sonusSonetSectionTcaEntry 9 }

sonusSonetSectionStatisticsTable OBJECT-TYPE
    SYNTAX          SEQUENCE OF SonusSonetSectionStatisticsEntry
    ACCESS          not-accessible
    STATUS          mandatory
    DESCRIPTION     
            "The Sonus SONET Section Statistics table."
    ::= { sonusSonetSection 5 }

sonusSonetSectionStatisticsEntry OBJECT-TYPE
    SYNTAX          SonusSonetSectionStatisticsEntry
    ACCESS          not-accessible
    STATUS          mandatory
    DESCRIPTION     
            "An entry in the Sonus SONET Section STatistics table."
    INDEX           { sonusSonetSectionStatisticsIfIndex }
    ::= { sonusSonetSectionStatisticsTable 1 }

SonusSonetSectionStatisticsEntry ::=
    SEQUENCE {
        sonusSonetSectionStatisticsIfIndex  INTEGER,
        sonusSonetSectionStatisticsDefectLOS    INTEGER,
        sonusSonetSectionStatisticsDefectLOF    INTEGER,
        sonusSonetSectionStatisticsAlarmLOS   INTEGER,
        sonusSonetSectionStatisticsAlarmLOF   INTEGER,
        sonusSonetSectionStatisticsCodeViolation        INTEGER
    }

sonusSonetSectionStatisticsIfIndex OBJECT-TYPE
    SYNTAX          INTEGER
    ACCESS          not-accessible
    STATUS          mandatory
    DESCRIPTION     
            "The ifIndex assigned to this port when it was created.
             This will not change until the port is deleted."
    ::= { sonusSonetSectionStatisticsEntry 1 }

sonusSonetSectionStatisticsDefectLOS OBJECT-TYPE
    SYNTAX          INTEGER
    ACCESS          read-only
    STATUS          mandatory
    DESCRIPTION     
            "Count of Loss of Signal defects that have occured."
    ::= { sonusSonetSectionStatisticsEntry 2 }

sonusSonetSectionStatisticsDefectLOF OBJECT-TYPE
    SYNTAX          INTEGER
    ACCESS          read-only
    STATUS          mandatory
    DESCRIPTION     
            "Count of Loss of Frame defects that have occured."
    ::= { sonusSonetSectionStatisticsEntry 3 }

sonusSonetSectionStatisticsAlarmLOS OBJECT-TYPE
    SYNTAX          INTEGER
    ACCESS          read-only
    STATUS          mandatory
    DESCRIPTION     
            "Count of Loss of Signal alarms that have occured."
    ::= { sonusSonetSectionStatisticsEntry 4 }

sonusSonetSectionStatisticsAlarmLOF OBJECT-TYPE
    SYNTAX          INTEGER
    ACCESS          read-only
    STATUS          mandatory
    DESCRIPTION     
            "Count of Loss of Frame alarms that have occured."
    ::= { sonusSonetSectionStatisticsEntry 5 }

sonusSonetSectionStatisticsCodeViolation OBJECT-TYPE
    SYNTAX          INTEGER
    ACCESS          read-only
    STATUS          mandatory
    DESCRIPTION     
            "Count of code violations that have occured."
    ::= { sonusSonetSectionStatisticsEntry 6 }

sonusSonetLine OBJECT IDENTIFIER
    ::= { sonusSonetObjects 3 }

sonusSonetLineThresholdTable OBJECT-TYPE
    SYNTAX          SEQUENCE OF SonusSonetLineThresholdEntry
    ACCESS          not-accessible
    STATUS          mandatory
    DESCRIPTION     
            "The Sonus SONET Line Threshold Table. This table adds objects
             to set the Performance Monitoring thresholds for generating a
             Threshold Crossing Alert."
    ::= { sonusSonetLine 1 }

sonusSonetLineThresholdEntry OBJECT-TYPE
    SYNTAX          SonusSonetLineThresholdEntry
    ACCESS          not-accessible
    STATUS          mandatory
    DESCRIPTION     
            "An entry in the Sonus SONET Line Threshold table."
    INDEX           { sonusSonetLineThresholdIfIndex }
    ::= { sonusSonetLineThresholdTable 1 }

SonusSonetLineThresholdEntry ::=
    SEQUENCE {
        sonusSonetLineThresholdIfIndex  INTEGER,
        sonusSonetLineThreshold15mCVs   INTEGER,
        sonusSonetLineThreshold15mESs   INTEGER,
        sonusSonetLineThreshold15mSESs  INTEGER,
        sonusSonetLineThreshold15mUASs  INTEGER,
        sonusSonetLineThreshold24hCVs   INTEGER,
        sonusSonetLineThreshold24hESs   INTEGER,
        sonusSonetLineThreshold24hSESs  INTEGER,
        sonusSonetLineThreshold24hUASs  INTEGER,
        sonusSonetLineThresholdCVTcaFilter  SonusAdminState,
        sonusSonetLineThresholdESTcaFilter  SonusAdminState,
        sonusSonetLineThresholdSESTcaFilter   SonusAdminState,
        sonusSonetLineThresholdUASTcaFilter   SonusAdminState
    }

sonusSonetLineThresholdIfIndex OBJECT-TYPE
    SYNTAX          INTEGER
    ACCESS          not-accessible
    STATUS          mandatory
    DESCRIPTION     
            "The ifIndex assigned to this port when it was created.
             This will not change until the port is deleted."
    ::= { sonusSonetLineThresholdEntry 1 }

sonusSonetLineThreshold15mCVs OBJECT-TYPE
    SYNTAX          INTEGER (0..16383)
    ACCESS          read-write
    STATUS          mandatory
    DESCRIPTION     
            "Threshold for 15 minute interval Line layer Coding Violations."
    ::= { sonusSonetLineThresholdEntry 2 }

sonusSonetLineThreshold15mESs OBJECT-TYPE
    SYNTAX          INTEGER (0..900)
    ACCESS          read-write
    STATUS          mandatory
    DESCRIPTION     
            "Threshold for 15 minute interval Line layer Errored Seconds."
    ::= { sonusSonetLineThresholdEntry 3 }

sonusSonetLineThreshold15mSESs OBJECT-TYPE
    SYNTAX          INTEGER (0..900)
    ACCESS          read-write
    STATUS          mandatory
    DESCRIPTION     
            "Threshold for 15 minute interval Line layer Severely Errored
             Seconds."
    ::= { sonusSonetLineThresholdEntry 4 }

sonusSonetLineThreshold15mUASs OBJECT-TYPE
    SYNTAX          INTEGER (0..900)
    ACCESS          read-write
    STATUS          mandatory
    DESCRIPTION     
            "Threshold for 15 minute interval Line layer Unavailable Seconds."
    ::= { sonusSonetLineThresholdEntry 5 }

sonusSonetLineThreshold24hCVs OBJECT-TYPE
    SYNTAX          INTEGER (0..1048575)
    ACCESS          read-write
    STATUS          mandatory
    DESCRIPTION     
            "Threshold for 24 hour interval Line layer Coding Violations."
    ::= { sonusSonetLineThresholdEntry 6 }

sonusSonetLineThreshold24hESs OBJECT-TYPE
    SYNTAX          INTEGER (0..65535)
    ACCESS          read-write
    STATUS          mandatory
    DESCRIPTION     
            "Threshold for 24 hour interval Line layer Errored Seconds."
    ::= { sonusSonetLineThresholdEntry 7 }

sonusSonetLineThreshold24hSESs OBJECT-TYPE
    SYNTAX          INTEGER (0..65535)
    ACCESS          read-write
    STATUS          mandatory
    DESCRIPTION     
            "Threshold for 24 hour interval Line layer Severely Errored
             Seconds."
    ::= { sonusSonetLineThresholdEntry 8 }

sonusSonetLineThreshold24hUASs OBJECT-TYPE
    SYNTAX          INTEGER (0..65535)
    ACCESS          read-write
    STATUS          mandatory
    DESCRIPTION     
            "Threshold for 24 hour interval Line layer Unavailable Seconds."
    ::= { sonusSonetLineThresholdEntry 9 }

sonusSonetLineThresholdCVTcaFilter OBJECT-TYPE
    SYNTAX          SonusAdminState
    ACCESS          read-write
    STATUS          mandatory
    DESCRIPTION     
            "Controls whether a threshold Crossing Alert (TCA) is reported (via
             an event log and trap). Setting this object to Enabled will prevent
             the TCA from being reported (i.e will Filter the TCA report)."
    DEFVAL          { disabled }
    ::= { sonusSonetLineThresholdEntry 10 }

sonusSonetLineThresholdESTcaFilter OBJECT-TYPE
    SYNTAX          SonusAdminState
    ACCESS          read-write
    STATUS          mandatory
    DESCRIPTION     
            "Controls whether a threshold Crossing Alert (TCA) is reported (via
             an event log and trap). Setting this object to Enabled will prevent
             the TCA from being reported (i.e will Filter the TCA report)."
    DEFVAL          { disabled }
    ::= { sonusSonetLineThresholdEntry 11 }

sonusSonetLineThresholdSESTcaFilter OBJECT-TYPE
    SYNTAX          SonusAdminState
    ACCESS          read-write
    STATUS          mandatory
    DESCRIPTION     
            "Controls whether a threshold Crossing Alert (TCA) is reported (via
             an event log and trap). Setting this object to Enabled will prevent
             the TCA from being reported (i.e will Filter the TCA report)."
    DEFVAL          { disabled }
    ::= { sonusSonetLineThresholdEntry 12 }

sonusSonetLineThresholdUASTcaFilter OBJECT-TYPE
    SYNTAX          SonusAdminState
    ACCESS          read-write
    STATUS          mandatory
    DESCRIPTION     
            "Controls whether a threshold Crossing Alert (TCA) is reported (via
             an event log and trap). Setting this object to Enabled will prevent
             the TCA from being reported (i.e will Filter the TCA report)."
    DEFVAL          { disabled }
    ::= { sonusSonetLineThresholdEntry 13 }

sonusSonetLineCurrentTable OBJECT-TYPE
    SYNTAX          SEQUENCE OF SonusSonetLineCurrentEntry
    ACCESS          not-accessible
    STATUS          mandatory
    DESCRIPTION     
            "The Sonus SONET Line Current table."
    ::= { sonusSonetLine 2 }

sonusSonetLineCurrentEntry OBJECT-TYPE
    SYNTAX          SonusSonetLineCurrentEntry
    ACCESS          not-accessible
    STATUS          mandatory
    DESCRIPTION     
            "An entry in the Sonus SONET Line Current table."
    INDEX           { sonusSonetLineCurrentIfIndex }
    ::= { sonusSonetLineCurrentTable 1 }

SonusSonetLineCurrentEntry ::=
    SEQUENCE {
        sonusSonetLineCurrentIfIndex    INTEGER,
        sonusSonetLineCurrentStatus     INTEGER,
        sonusSonetLineCurrentESs        PerfCurrentCount,
        sonusSonetLineCurrentSESs       PerfCurrentCount,
        sonusSonetLineCurrentUASs       PerfCurrentCount,
        sonusSonetLineCurrentCVs        PerfCurrentCount,
        sonusSonetLineCurrentFCs        PerfCurrentCount,
        sonusSonetLineCurrentElapsedTime INTEGER,
        sonusSonetLineCurrentDayElapsedTime   INTEGER
    }

sonusSonetLineCurrentIfIndex OBJECT-TYPE
    SYNTAX          INTEGER
    ACCESS          not-accessible
    STATUS          mandatory
    DESCRIPTION     
            "The ifIndex assigned to this port when it was created.
             This will not change until the port is deleted."
    ::= { sonusSonetLineCurrentEntry 1 }

sonusSonetLineCurrentStatus OBJECT-TYPE
    SYNTAX          INTEGER (1..8)
    ACCESS          read-only
    STATUS          mandatory
    DESCRIPTION     
            "This variable indicates the status of the interface. It is
             a bit map represented as a sum, therefore, it can represent
             multiple defects simultaneously. The sonetLineNoDefect
             should be set if and only if no other flag is set.
             
             The various bit positions are:
             1   sonetLineNoDefect
             2   sonetLineAIS
             4   sonetLineRDI
             8   sonetLineNotMonitored"
    ::= { sonusSonetLineCurrentEntry 2 }

sonusSonetLineCurrentESs OBJECT-TYPE
    SYNTAX          PerfCurrentCount
    ACCESS          read-only
    STATUS          mandatory
    DESCRIPTION     
            "The counter associated with the number of Errored Seconds
             encountered by a SONET/SDH Line in the current 24 hour
             interval."
    ::= { sonusSonetLineCurrentEntry 3 }

sonusSonetLineCurrentSESs OBJECT-TYPE
    SYNTAX          PerfCurrentCount
    ACCESS          read-only
    STATUS          mandatory
    DESCRIPTION     
            "The counter associated with the number of Severely Errored
             Seconds encountered by a SONET/SDH Line in the current 
             24 hour interval."
    ::= { sonusSonetLineCurrentEntry 4 }

sonusSonetLineCurrentUASs OBJECT-TYPE
    SYNTAX          PerfCurrentCount
    ACCESS          read-only
    STATUS          mandatory
    DESCRIPTION     
            "The counter associated with the number of Unavailable
             Seconds encountered by a SONET/SDH Line in the current
             24 hour interval."
    ::= { sonusSonetLineCurrentEntry 5 }

sonusSonetLineCurrentCVs OBJECT-TYPE
    SYNTAX          PerfCurrentCount
    ACCESS          read-only
    STATUS          mandatory
    DESCRIPTION     
            "The counter associated with the number of Coding Violations
             encountered by a SONET/SDH Line in the current 24 hour
             	 interval."
    ::= { sonusSonetLineCurrentEntry 6 }

sonusSonetLineCurrentFCs OBJECT-TYPE
    SYNTAX          PerfCurrentCount
    ACCESS          read-only
    STATUS          mandatory
    DESCRIPTION     
            "The counter associated with the number of Failures encountered
             by a SONET/SDH Line in the current 24 hour interval."
    ::= { sonusSonetLineCurrentEntry 7 }

sonusSonetLineCurrentElapsedTime OBJECT-TYPE
    SYNTAX          INTEGER
    ACCESS          read-only
    STATUS          mandatory
    DESCRIPTION     
            "Elapsed time in the current period"
    ::= { sonusSonetLineCurrentEntry 8 }

sonusSonetLineCurrentDayElapsedTime OBJECT-TYPE
    SYNTAX          INTEGER
    ACCESS          read-only
    STATUS          mandatory
    DESCRIPTION     
            "Elapsed time in the current period"
    ::= { sonusSonetLineCurrentEntry 9 }

sonusSonetLineIntervalTable OBJECT-TYPE
    SYNTAX          SEQUENCE OF SonusSonetLineIntervalEntry
    ACCESS          not-accessible
    STATUS          mandatory
    DESCRIPTION     
            "The Sonus SONET Line Interval table."
    ::= { sonusSonetLine 3 }

sonusSonetLineIntervalEntry OBJECT-TYPE
    SYNTAX          SonusSonetLineIntervalEntry
    ACCESS          not-accessible
    STATUS          mandatory
    DESCRIPTION     
            "An entry in the Sonus SONET Line Interval table."
    INDEX           { sonusSonetLineIntervalIfIndex, 
                      sonusSonetLineIntervalNumber }
    ::= { sonusSonetLineIntervalTable 1 }

SonusSonetLineIntervalEntry ::=
    SEQUENCE {
        sonusSonetLineIntervalIfIndex   INTEGER,
        sonusSonetLineIntervalNumber    INTEGER,
        sonusSonetLineIntervalESs       PerfIntervalCount,
        sonusSonetLineIntervalSESs      PerfIntervalCount,
        sonusSonetLineIntervalUASs      PerfIntervalCount,
        sonusSonetLineIntervalCVs       PerfIntervalCount,
        sonusSonetLineIntervalFCs       PerfIntervalCount,
        sonusSonetLineIntervalValidData TruthValue
    }

sonusSonetLineIntervalIfIndex OBJECT-TYPE
    SYNTAX          INTEGER
    ACCESS          not-accessible
    STATUS          mandatory
    DESCRIPTION     
            "The ifIndex assigned to this port when it was created.
             This will not change until the port is deleted."
    ::= { sonusSonetLineIntervalEntry 1 }

sonusSonetLineIntervalNumber OBJECT-TYPE
    SYNTAX          INTEGER (1)
    ACCESS          not-accessible
    STATUS          mandatory
    DESCRIPTION     
            "The number 1 identifies the most recently completed 24 hour
             interval. In the future if more 24 hour intervals are supported,
             the interval identified by N is the interval immediately
             preceding the one identified by N-1."
    ::= { sonusSonetLineIntervalEntry 2 }

sonusSonetLineIntervalESs OBJECT-TYPE
    SYNTAX          PerfIntervalCount
    ACCESS          read-only
    STATUS          mandatory
    DESCRIPTION     
            "The counter associated with the number of Errored Seconds
             encountered by a SONET/SDH Line in the previous 24 hour
             interval."
    ::= { sonusSonetLineIntervalEntry 3 }

sonusSonetLineIntervalSESs OBJECT-TYPE
    SYNTAX          PerfIntervalCount
    ACCESS          read-only
    STATUS          mandatory
    DESCRIPTION     
            "The counter associated with the number of Severely Errored
             Seconds encountered by a SONET/SDH Line in the previous 
             24 hour interval."
    ::= { sonusSonetLineIntervalEntry 4 }

sonusSonetLineIntervalUASs OBJECT-TYPE
    SYNTAX          PerfIntervalCount
    ACCESS          read-only
    STATUS          mandatory
    DESCRIPTION     
            "The counter associated with the number of Unavailable
             Seconds encountered by a SONET/SDH Line in the previous
             24 hour interval."
    ::= { sonusSonetLineIntervalEntry 5 }

sonusSonetLineIntervalCVs OBJECT-TYPE
    SYNTAX          PerfIntervalCount
    ACCESS          read-only
    STATUS          mandatory
    DESCRIPTION     
            "The counter associated with the number of Coding Violations
             encountered by a SONET/SDH Line in the previous 24 hour
             	 interval."
    ::= { sonusSonetLineIntervalEntry 6 }

sonusSonetLineIntervalFCs OBJECT-TYPE
    SYNTAX          PerfIntervalCount
    ACCESS          read-only
    STATUS          mandatory
    DESCRIPTION     
            "The counter associated with the number of Failures encountered
             by a SONET/SDH Line in the previous 24 hour interval."
    ::= { sonusSonetLineIntervalEntry 7 }

sonusSonetLineIntervalValidData OBJECT-TYPE
    SYNTAX          TruthValue
    ACCESS          read-only
    STATUS          mandatory
    DESCRIPTION     
            "This variable indicates if the data for this interval is valid."
    ::= { sonusSonetLineIntervalEntry 8 }

sonusSonetFarEndLineCurrentTable OBJECT-TYPE
    SYNTAX          SEQUENCE OF SonusSonetFarEndLineCurrentEntry
    ACCESS          not-accessible
    STATUS          mandatory
    DESCRIPTION     
            "The Sonus SONET Far End Line Current table."
    ::= { sonusSonetLine 4 }

sonusSonetFarEndLineCurrentEntry OBJECT-TYPE
    SYNTAX          SonusSonetFarEndLineCurrentEntry
    ACCESS          not-accessible
    STATUS          mandatory
    DESCRIPTION     
            "An entry in the Sonus SONET Far End Line Current table."
    INDEX           { sonusSonetFarEndLineCurrentIfIndex }
    ::= { sonusSonetFarEndLineCurrentTable 1 }

SonusSonetFarEndLineCurrentEntry ::=
    SEQUENCE {
        sonusSonetFarEndLineCurrentIfIndex  INTEGER,
        sonusSonetFarEndLineCurrentESs  PerfCurrentCount,
        sonusSonetFarEndLineCurrentSESs PerfCurrentCount,
        sonusSonetFarEndLineCurrentUASs PerfCurrentCount,
        sonusSonetFarEndLineCurrentCVs  PerfCurrentCount,
        sonusSonetFarEndLineCurrentFCs  PerfCurrentCount
    }

sonusSonetFarEndLineCurrentIfIndex OBJECT-TYPE
    SYNTAX          INTEGER
    ACCESS          not-accessible
    STATUS          mandatory
    DESCRIPTION     
            "The ifIndex assigned to this port when it was created.
             This will not change until the port is deleted."
    ::= { sonusSonetFarEndLineCurrentEntry 1 }

sonusSonetFarEndLineCurrentESs OBJECT-TYPE
    SYNTAX          PerfCurrentCount
    ACCESS          read-only
    STATUS          mandatory
    DESCRIPTION     
            "The counter associated with the number of Far End Errored
             Seconds encountered by a SONET/SDH Line in the current
             24 hour interval."
    ::= { sonusSonetFarEndLineCurrentEntry 2 }

sonusSonetFarEndLineCurrentSESs OBJECT-TYPE
    SYNTAX          PerfCurrentCount
    ACCESS          read-only
    STATUS          mandatory
    DESCRIPTION     
            "The counter associated with the number of Far End Severely
             Errored Seconds encountered by a SONET/SDH Line in the
             current 24 hour interval."
    ::= { sonusSonetFarEndLineCurrentEntry 3 }

sonusSonetFarEndLineCurrentUASs OBJECT-TYPE
    SYNTAX          PerfCurrentCount
    ACCESS          read-only
    STATUS          mandatory
    DESCRIPTION     
            "The counter associated with the number of Far End 
             Unavailable Seconds encountered by a SONET/SDH Line in the
             current 24 hour interval."
    ::= { sonusSonetFarEndLineCurrentEntry 4 }

sonusSonetFarEndLineCurrentCVs OBJECT-TYPE
    SYNTAX          PerfCurrentCount
    ACCESS          read-only
    STATUS          mandatory
    DESCRIPTION     
            "The counter associated with the number of Far End Coding
             Violations encountered by a SONET/SDH Line in the current
             	 24 hour interval."
    ::= { sonusSonetFarEndLineCurrentEntry 5 }

sonusSonetFarEndLineCurrentFCs OBJECT-TYPE
    SYNTAX          PerfCurrentCount
    ACCESS          read-only
    STATUS          mandatory
    DESCRIPTION     
            "The counter associated with the number of Far End Failures
             encountered by a SONET/SDH Line in the current 24 hour
             interval."
    ::= { sonusSonetFarEndLineCurrentEntry 6 }

sonusSonetFarEndLineIntervalTable OBJECT-TYPE
    SYNTAX          SEQUENCE OF SonusSonetFarEndLineIntervalEntry
    ACCESS          not-accessible
    STATUS          mandatory
    DESCRIPTION     
            "The Sonus SONET Far End Line Interval table."
    ::= { sonusSonetLine 5 }

sonusSonetFarEndLineIntervalEntry OBJECT-TYPE
    SYNTAX          SonusSonetFarEndLineIntervalEntry
    ACCESS          not-accessible
    STATUS          mandatory
    DESCRIPTION     
            "An entry in the Sonus SONET Far End Line Interval table."
    INDEX           { sonusSonetFarEndLineIntervalIfIndex, 
                      sonusSonetFarEndLineIntervalNumber }
    ::= { sonusSonetFarEndLineIntervalTable 1 }

SonusSonetFarEndLineIntervalEntry ::=
    SEQUENCE {
        sonusSonetFarEndLineIntervalIfIndex   INTEGER,
        sonusSonetFarEndLineIntervalNumber  INTEGER,
        sonusSonetFarEndLineIntervalESs PerfIntervalCount,
        sonusSonetFarEndLineIntervalSESs PerfIntervalCount,
        sonusSonetFarEndLineIntervalUASs PerfIntervalCount,
        sonusSonetFarEndLineIntervalCVs PerfIntervalCount,
        sonusSonetFarEndLineIntervalFCs PerfIntervalCount,
        sonusSonetFarEndLineIntervalValidData     TruthValue
    }

sonusSonetFarEndLineIntervalIfIndex OBJECT-TYPE
    SYNTAX          INTEGER
    ACCESS          not-accessible
    STATUS          mandatory
    DESCRIPTION     
            "The ifIndex assigned to this port when it was created.
             This will not change until the port is deleted."
    ::= { sonusSonetFarEndLineIntervalEntry 1 }

sonusSonetFarEndLineIntervalNumber OBJECT-TYPE
    SYNTAX          INTEGER (1)
    ACCESS          not-accessible
    STATUS          mandatory
    DESCRIPTION     
            "The number 1 identifies the most recently completed 24 hour
             interval. In the future if more 24 hour intervals are supported,
             the interval identified by N is the interval immediately
             preceding the one identified by N-1."
    ::= { sonusSonetFarEndLineIntervalEntry 2 }

sonusSonetFarEndLineIntervalESs OBJECT-TYPE
    SYNTAX          PerfIntervalCount
    ACCESS          read-only
    STATUS          mandatory
    DESCRIPTION     
            "The counter associated with the number of Far End Errored
             Seconds encountered by a SONET/SDH Line in the current
             24 hour interval."
    ::= { sonusSonetFarEndLineIntervalEntry 3 }

sonusSonetFarEndLineIntervalSESs OBJECT-TYPE
    SYNTAX          PerfIntervalCount
    ACCESS          read-only
    STATUS          mandatory
    DESCRIPTION     
            "The counter associated with the number of Far End Severely
             Errored Seconds encountered by a SONET/SDH Line in the
             current 24 hour interval."
    ::= { sonusSonetFarEndLineIntervalEntry 4 }

sonusSonetFarEndLineIntervalUASs OBJECT-TYPE
    SYNTAX          PerfIntervalCount
    ACCESS          read-only
    STATUS          mandatory
    DESCRIPTION     
            "The counter associated with the number of Far End 
             Unavailable Seconds encountered by a SONET/SDH Line in the
             current 24 hour interval."
    ::= { sonusSonetFarEndLineIntervalEntry 5 }

sonusSonetFarEndLineIntervalCVs OBJECT-TYPE
    SYNTAX          PerfIntervalCount
    ACCESS          read-only
    STATUS          mandatory
    DESCRIPTION     
            "The counter associated with the number of Far End Coding
             Violations encountered by a SONET/SDH Line in the current
             	 24 hour interval."
    ::= { sonusSonetFarEndLineIntervalEntry 6 }

sonusSonetFarEndLineIntervalFCs OBJECT-TYPE
    SYNTAX          PerfIntervalCount
    ACCESS          read-only
    STATUS          mandatory
    DESCRIPTION     
            "The counter associated with the number of Far End Failures
             encountered by a SONET/SDH Line in the current 24 hour
             interval."
    ::= { sonusSonetFarEndLineIntervalEntry 7 }

sonusSonetFarEndLineIntervalValidData OBJECT-TYPE
    SYNTAX          TruthValue
    ACCESS          read-only
    STATUS          mandatory
    DESCRIPTION     
            "This variable indicates if the data for this interval is valid."
    ::= { sonusSonetFarEndLineIntervalEntry 8 }

sonusSonetLineFailureCurrentTable OBJECT-TYPE
    SYNTAX          SEQUENCE OF SonusSonetLineFailureCurrentEntry
    ACCESS          not-accessible
    STATUS          mandatory
    DESCRIPTION     
            "The Sonus SONET Line Failure Current table."
    ::= { sonusSonetLine 6 }

sonusSonetLineFailureCurrentEntry OBJECT-TYPE
    SYNTAX          SonusSonetLineFailureCurrentEntry
    ACCESS          not-accessible
    STATUS          mandatory
    DESCRIPTION     
            "An entry in the Sonus SONET Line Failure Current table."
    INDEX           { sonusSonetLineFailureCurrentIfIndex }
    ::= { sonusSonetLineFailureCurrentTable 1 }

SonusSonetLineFailureCurrentEntry ::=
    SEQUENCE {
        sonusSonetLineFailureCurrentIfIndex   INTEGER,
        sonusSonetLineFailureCurrentFCs PerfCurrentCount
    }

sonusSonetLineFailureCurrentIfIndex OBJECT-TYPE
    SYNTAX          INTEGER
    ACCESS          not-accessible
    STATUS          mandatory
    DESCRIPTION     
            "The ifIndex assigned to this port when it was created.
             This will not change until the port is deleted."
    ::= { sonusSonetLineFailureCurrentEntry 1 }

sonusSonetLineFailureCurrentFCs OBJECT-TYPE
    SYNTAX          PerfCurrentCount
    ACCESS          read-only
    STATUS          mandatory
    DESCRIPTION     
            "The counter associated with the number of Failures encountered
             by a SONET/SDH Line in the current 15 minute interval."
    ::= { sonusSonetLineFailureCurrentEntry 2 }

sonusSonetLineFailureIntervalTable OBJECT-TYPE
    SYNTAX          SEQUENCE OF SonusSonetLineFailureIntervalEntry
    ACCESS          not-accessible
    STATUS          mandatory
    DESCRIPTION     
            "The Sonus SONET Line Failure Interval table."
    ::= { sonusSonetLine 7 }

sonusSonetLineFailureIntervalEntry OBJECT-TYPE
    SYNTAX          SonusSonetLineFailureIntervalEntry
    ACCESS          not-accessible
    STATUS          mandatory
    DESCRIPTION     
            "An entry in the Sonus SONET Line Failure Interval table."
    INDEX           { sonusSonetLineFailureIntervalIfIndex, 
                      sonusSonetLineFailureIntervalNumber }
    ::= { sonusSonetLineFailureIntervalTable 1 }

SonusSonetLineFailureIntervalEntry ::=
    SEQUENCE {
        sonusSonetLineFailureIntervalIfIndex    INTEGER,
        sonusSonetLineFailureIntervalNumber   INTEGER,
        sonusSonetLineFailureIntervalFCs PerfCurrentCount
    }

sonusSonetLineFailureIntervalIfIndex OBJECT-TYPE
    SYNTAX          INTEGER
    ACCESS          not-accessible
    STATUS          mandatory
    DESCRIPTION     
            "The ifIndex assigned to this port when it was created.
             This will not change until the port is deleted."
    ::= { sonusSonetLineFailureIntervalEntry 1 }

sonusSonetLineFailureIntervalNumber OBJECT-TYPE
    SYNTAX          INTEGER
    ACCESS          not-accessible
    STATUS          mandatory
    DESCRIPTION     
            "A number between 1 and 32, which identifies the interval
             for which the set of statistics is available. The number 1
             identifies the most recently completed interval, and the
             interval identified by N is the interval immediately
             preceding the one identified by N-1."
    ::= { sonusSonetLineFailureIntervalEntry 2 }

sonusSonetLineFailureIntervalFCs OBJECT-TYPE
    SYNTAX          PerfCurrentCount
    ACCESS          read-only
    STATUS          mandatory
    DESCRIPTION     
            "The counter associated with the number of Failures encountered
             by a SONET/SDH Line in the current 15 minute interval."
    ::= { sonusSonetLineFailureIntervalEntry 3 }

sonusSonetFarEndLineFailureCurrentTable OBJECT-TYPE
    SYNTAX          SEQUENCE OF SonusSonetFarEndLineFailureCurrentEntry
    ACCESS          not-accessible
    STATUS          mandatory
    DESCRIPTION     
            "The Sonus SONET Far End Line Failure Current table."
    ::= { sonusSonetLine 8 }

sonusSonetFarEndLineFailureCurrentEntry OBJECT-TYPE
    SYNTAX          SonusSonetFarEndLineFailureCurrentEntry
    ACCESS          not-accessible
    STATUS          mandatory
    DESCRIPTION     
            "An entry in the Sonus SONET Far End Line Failure Current table."
    INDEX           { sonusSonetFarEndLineFailureCurrentIfIndex }
    ::= { sonusSonetFarEndLineFailureCurrentTable 1 }

SonusSonetFarEndLineFailureCurrentEntry ::=
    SEQUENCE {
        sonusSonetFarEndLineFailureCurrentIfIndex         INTEGER,
        sonusSonetFarEndLineFailureCurrentFCs     PerfCurrentCount
    }

sonusSonetFarEndLineFailureCurrentIfIndex OBJECT-TYPE
    SYNTAX          INTEGER
    ACCESS          not-accessible
    STATUS          mandatory
    DESCRIPTION     
            "The ifIndex assigned to this port when it was created.
             This will not change until the port is deleted."
    ::= { sonusSonetFarEndLineFailureCurrentEntry 1 }

sonusSonetFarEndLineFailureCurrentFCs OBJECT-TYPE
    SYNTAX          PerfCurrentCount
    ACCESS          read-only
    STATUS          mandatory
    DESCRIPTION     
            "The counter associated with the number of Failures encountered
             by a SONET/SDH Line in the current 15 minute interval."
    ::= { sonusSonetFarEndLineFailureCurrentEntry 2 }

sonusSonetFarEndLineFailureIntervalTable OBJECT-TYPE
    SYNTAX          SEQUENCE OF SonusSonetFarEndLineFailureIntervalEntry
    ACCESS          not-accessible
    STATUS          mandatory
    DESCRIPTION     
            "The Sonus SONET Far End Line Failure Interval table."
    ::= { sonusSonetLine 9 }

sonusSonetFarEndLineFailureIntervalEntry OBJECT-TYPE
    SYNTAX          SonusSonetFarEndLineFailureIntervalEntry
    ACCESS          not-accessible
    STATUS          mandatory
    DESCRIPTION     
            "An entry in the Sonus SONET Far End Line Failure Interval table."
    INDEX           { sonusSonetFarEndLineFailureIntervalIfIndex, 
                      sonusSonetFarEndLineFailureIntervalNumber }
    ::= { sonusSonetFarEndLineFailureIntervalTable 1 }

SonusSonetFarEndLineFailureIntervalEntry ::=
    SEQUENCE {
        sonusSonetFarEndLineFailureIntervalIfIndex          INTEGER,
        sonusSonetFarEndLineFailureIntervalNumber         INTEGER,
        sonusSonetFarEndLineFailureIntervalFCs      PerfCurrentCount
    }

sonusSonetFarEndLineFailureIntervalIfIndex OBJECT-TYPE
    SYNTAX          INTEGER
    ACCESS          not-accessible
    STATUS          mandatory
    DESCRIPTION     
            "The ifIndex assigned to this port when it was created.
             This will not change until the port is deleted."
    ::= { sonusSonetFarEndLineFailureIntervalEntry 1 }

sonusSonetFarEndLineFailureIntervalNumber OBJECT-TYPE
    SYNTAX          INTEGER
    ACCESS          not-accessible
    STATUS          mandatory
    DESCRIPTION     
            "A number between 1 and 32, which identifies the interval
             for which the set of statistics is available. The number 1
             identifies the most recently completed interval, and the
             interval identified by N is the interval immediately
             preceding the one identified by N-1."
    ::= { sonusSonetFarEndLineFailureIntervalEntry 2 }

sonusSonetFarEndLineFailureIntervalFCs OBJECT-TYPE
    SYNTAX          PerfCurrentCount
    ACCESS          read-only
    STATUS          mandatory
    DESCRIPTION     
            "The counter associated with the number of Failures encountered
             by a SONET/SDH Line in the current 15 minute interval."
    ::= { sonusSonetFarEndLineFailureIntervalEntry 3 }

sonusSonetLineTcaTable OBJECT-TYPE
    SYNTAX          SEQUENCE OF SonusSonetLineTcaEntry
    ACCESS          not-accessible
    STATUS          mandatory
    DESCRIPTION     
            "The Sonus SONET Line Threshold Crossing Alert table."
    ::= { sonusSonetLine 10 }

sonusSonetLineTcaEntry OBJECT-TYPE
    SYNTAX          SonusSonetLineTcaEntry
    ACCESS          not-accessible
    STATUS          mandatory
    DESCRIPTION     
            "An entry in the Sonus SONET Line Threshold Crossing Alert table."
    INDEX           { sonusSonetLineTcaIfIndex }
    ::= { sonusSonetLineTcaTable 1 }

SonusSonetLineTcaEntry ::=
    SEQUENCE {
        sonusSonetLineTcaIfIndex        INTEGER,
        sonusSonetLineTca15mES          TruthValue,
        sonusSonetLineTca15mSES         TruthValue,
        sonusSonetLineTca15mUAS         TruthValue,
        sonusSonetLineTca15mCV          TruthValue,
        sonusSonetLineTca24hES          TruthValue,
        sonusSonetLineTca24hSES         TruthValue,
        sonusSonetLineTca24hUAS         TruthValue,
        sonusSonetLineTca24hCV          TruthValue,
        sonusSonetLineTcaFarEnd15mES    TruthValue,
        sonusSonetLineTcaFarEnd15mSES   TruthValue,
        sonusSonetLineTcaFarEnd15mUAS   TruthValue,
        sonusSonetLineTcaFarEnd15mCV    TruthValue,
        sonusSonetLineTcaFarEnd24hES    TruthValue,
        sonusSonetLineTcaFarEnd24hSES   TruthValue,
        sonusSonetLineTcaFarEnd24hUAS   TruthValue,
        sonusSonetLineTcaFarEnd24hCV    TruthValue
    }

sonusSonetLineTcaIfIndex OBJECT-TYPE
    SYNTAX          INTEGER
    ACCESS          not-accessible
    STATUS          mandatory
    DESCRIPTION     
            "The ifIndex assigned to this port when it was created.
             This will not change until the port is deleted."
    ::= { sonusSonetLineTcaEntry 1 }

sonusSonetLineTca15mES OBJECT-TYPE
    SYNTAX          TruthValue
    ACCESS          read-only
    STATUS          mandatory
    DESCRIPTION     
            "Indicates status of threshold crossing for Line Errored
             Seconds in the current 15 minute interval."
    ::= { sonusSonetLineTcaEntry 2 }

sonusSonetLineTca15mSES OBJECT-TYPE
    SYNTAX          TruthValue
    ACCESS          read-only
    STATUS          mandatory
    DESCRIPTION     
            "Indicates status of threshold crossing for Line Severely
             Errored Seconds in the current 15 minute interval."
    ::= { sonusSonetLineTcaEntry 3 }

sonusSonetLineTca15mUAS OBJECT-TYPE
    SYNTAX          TruthValue
    ACCESS          read-only
    STATUS          mandatory
    DESCRIPTION     
            "Indicates status of threshold crossing for Line Unavailable
             Seconds in the current 15 minute interval."
    ::= { sonusSonetLineTcaEntry 4 }

sonusSonetLineTca15mCV OBJECT-TYPE
    SYNTAX          TruthValue
    ACCESS          read-only
    STATUS          mandatory
    DESCRIPTION     
            "Indicates status of threshold crossing for Line Coding
             Violations in the current 15 minute interval."
    ::= { sonusSonetLineTcaEntry 5 }

sonusSonetLineTca24hES OBJECT-TYPE
    SYNTAX          TruthValue
    ACCESS          read-only
    STATUS          mandatory
    DESCRIPTION     
            "Indicates status of threshold crossing for Line Errored
             Seconds in the current 24 hour interval."
    ::= { sonusSonetLineTcaEntry 6 }

sonusSonetLineTca24hSES OBJECT-TYPE
    SYNTAX          TruthValue
    ACCESS          read-only
    STATUS          mandatory
    DESCRIPTION     
            "Indicates status of threshold crossing for Line Severely
             Errored Seconds in the current 24 hour interval."
    ::= { sonusSonetLineTcaEntry 7 }

sonusSonetLineTca24hUAS OBJECT-TYPE
    SYNTAX          TruthValue
    ACCESS          read-only
    STATUS          mandatory
    DESCRIPTION     
            "Indicates status of threshold crossing for Line Unavailable
             Seconds in the current 24 hour interval."
    ::= { sonusSonetLineTcaEntry 8 }

sonusSonetLineTca24hCV OBJECT-TYPE
    SYNTAX          TruthValue
    ACCESS          read-only
    STATUS          mandatory
    DESCRIPTION     
            "Indicates status of threshold crossing for Line Coding
             Violations in the current 24 hour interval."
    ::= { sonusSonetLineTcaEntry 9 }

sonusSonetLineTcaFarEnd15mES OBJECT-TYPE
    SYNTAX          TruthValue
    ACCESS          read-only
    STATUS          mandatory
    DESCRIPTION     
            "Indicates status of threshold crossing for Far End Line Errored
             Seconds in the current 15 minute interval."
    ::= { sonusSonetLineTcaEntry 10 }

sonusSonetLineTcaFarEnd15mSES OBJECT-TYPE
    SYNTAX          TruthValue
    ACCESS          read-only
    STATUS          mandatory
    DESCRIPTION     
            "Indicates status of threshold crossing for Far End Line Severely
             Errored Seconds in the current 15 minute interval."
    ::= { sonusSonetLineTcaEntry 11 }

sonusSonetLineTcaFarEnd15mUAS OBJECT-TYPE
    SYNTAX          TruthValue
    ACCESS          read-only
    STATUS          mandatory
    DESCRIPTION     
            "Indicates status of threshold crossing for Far End Line Unavailable
             Seconds in the current 15 minute interval."
    ::= { sonusSonetLineTcaEntry 12 }

sonusSonetLineTcaFarEnd15mCV OBJECT-TYPE
    SYNTAX          TruthValue
    ACCESS          read-only
    STATUS          mandatory
    DESCRIPTION     
            "Indicates status of threshold crossing for Far End Line Coding
             Violations in the current 15 minute interval."
    ::= { sonusSonetLineTcaEntry 13 }

sonusSonetLineTcaFarEnd24hES OBJECT-TYPE
    SYNTAX          TruthValue
    ACCESS          read-only
    STATUS          mandatory
    DESCRIPTION     
            "Indicates status of threshold crossing for Far End Line Errored
             Seconds in the current 24 hour interval."
    ::= { sonusSonetLineTcaEntry 14 }

sonusSonetLineTcaFarEnd24hSES OBJECT-TYPE
    SYNTAX          TruthValue
    ACCESS          read-only
    STATUS          mandatory
    DESCRIPTION     
            "Indicates status of threshold crossing for Far End Line Severely
             Errored Seconds in the current 24 hour interval."
    ::= { sonusSonetLineTcaEntry 15 }

sonusSonetLineTcaFarEnd24hUAS OBJECT-TYPE
    SYNTAX          TruthValue
    ACCESS          read-only
    STATUS          mandatory
    DESCRIPTION     
            "Indicates status of threshold crossing for Far End Line Unavailable
             Seconds in the current 24 hour interval."
    ::= { sonusSonetLineTcaEntry 16 }

sonusSonetLineTcaFarEnd24hCV OBJECT-TYPE
    SYNTAX          TruthValue
    ACCESS          read-only
    STATUS          mandatory
    DESCRIPTION     
            "Indicates status of threshold crossing for Far End Line Coding
             Violations in the current 24 hour interval."
    ::= { sonusSonetLineTcaEntry 17 }

sonusSonetLineStatisticsTable OBJECT-TYPE
    SYNTAX          SEQUENCE OF SonusSonetLineStatisticsEntry
    ACCESS          not-accessible
    STATUS          mandatory
    DESCRIPTION     
            "The Sonus SONET Line Statistics table."
    ::= { sonusSonetLine 11 }

sonusSonetLineStatisticsEntry OBJECT-TYPE
    SYNTAX          SonusSonetLineStatisticsEntry
    ACCESS          not-accessible
    STATUS          mandatory
    DESCRIPTION     
            "An entry in the Sonus SONET Line Statistics table."
    INDEX           { sonusSonetLineStatisticsIfIndex }
    ::= { sonusSonetLineStatisticsTable 1 }

SonusSonetLineStatisticsEntry ::=
    SEQUENCE {
        sonusSonetLineStatisticsIfIndex INTEGER,
        sonusSonetLineStatisticsDefectAIS INTEGER,
        sonusSonetLineStatisticsDefectRDI INTEGER,
        sonusSonetLineStatisticsAlarmAIS INTEGER,
        sonusSonetLineStatisticsAlarmRFI INTEGER,
        sonusSonetLineStatisticsCodeViolation     INTEGER,
        sonusSonetLineStatisticsREI     INTEGER
    }

sonusSonetLineStatisticsIfIndex OBJECT-TYPE
    SYNTAX          INTEGER
    ACCESS          not-accessible
    STATUS          mandatory
    DESCRIPTION     
            "The ifIndex assigned to this port when it was created.
             This will not change until the port is deleted."
    ::= { sonusSonetLineStatisticsEntry 1 }

sonusSonetLineStatisticsDefectAIS OBJECT-TYPE
    SYNTAX          INTEGER
    ACCESS          read-only
    STATUS          mandatory
    DESCRIPTION     
            "Count of Alarm Indication Signal defects that have occured."
    ::= { sonusSonetLineStatisticsEntry 2 }

sonusSonetLineStatisticsDefectRDI OBJECT-TYPE
    SYNTAX          INTEGER
    ACCESS          read-only
    STATUS          mandatory
    DESCRIPTION     
            "Count of Remote Defect Indication defects that have occured."
    ::= { sonusSonetLineStatisticsEntry 3 }

sonusSonetLineStatisticsAlarmAIS OBJECT-TYPE
    SYNTAX          INTEGER
    ACCESS          read-only
    STATUS          mandatory
    DESCRIPTION     
            "Count of Alarm Indication Signal alarms that have occured."
    ::= { sonusSonetLineStatisticsEntry 4 }

sonusSonetLineStatisticsAlarmRFI OBJECT-TYPE
    SYNTAX          INTEGER
    ACCESS          read-only
    STATUS          mandatory
    DESCRIPTION     
            "Count of Remote Failure Indication alarms that have occured."
    ::= { sonusSonetLineStatisticsEntry 5 }

sonusSonetLineStatisticsCodeViolation OBJECT-TYPE
    SYNTAX          INTEGER
    ACCESS          read-only
    STATUS          mandatory
    DESCRIPTION     
            "Count of code violations that have occured."
    ::= { sonusSonetLineStatisticsEntry 6 }

sonusSonetLineStatisticsREI OBJECT-TYPE
    SYNTAX          INTEGER
    ACCESS          read-only
    STATUS          mandatory
    DESCRIPTION     
            "Count of Remote Error Indications that have occured."
    ::= { sonusSonetLineStatisticsEntry 7 }

sonusSonetLayer OBJECT IDENTIFIER
    ::= { sonusSonetObjects 4 }

sonusSonetLayerTable OBJECT-TYPE
    SYNTAX          SEQUENCE OF SonusSonetLayerEntry
    ACCESS          not-accessible
    STATUS          mandatory
    DESCRIPTION     
            "The SONET layer table.  This table maps SONET Interface ifIndex
             to a shelf, slot, and port."
    ::= { sonusSonetLayer 1 }

sonusSonetLayerEntry OBJECT-TYPE
    SYNTAX          SonusSonetLayerEntry
    ACCESS          not-accessible
    STATUS          mandatory
    DESCRIPTION     
            "An entry in the SONET layer table. This entry 
             maps the ifIndex of the SONET Interface to a shelf, slot
             and port.  A row is added to this table when a SONET
             port is created."
    INDEX           { sonusSonetLayerShelfIndex, 
                      sonusSonetLayerSlotIndex, sonusSonetLayerPortIndex }
    ::= { sonusSonetLayerTable 1 }

SonusSonetLayerEntry ::=
    SEQUENCE {
        sonusSonetLayerShelfIndex       SonusShelfIndex,
        sonusSonetLayerSlotIndex        SonusSlotIndex,
        sonusSonetLayerPortIndex        INTEGER,
        sonusSonetLayerIfIndex          INTEGER,
        sonusSonetLayerRowStatus        RowStatus
    }

sonusSonetLayerShelfIndex OBJECT-TYPE
    SYNTAX          SonusShelfIndex
    ACCESS          not-accessible
    STATUS          mandatory
    DESCRIPTION     
            "Shelf index for this table."
    ::= { sonusSonetLayerEntry 1 }

sonusSonetLayerSlotIndex OBJECT-TYPE
    SYNTAX          SonusSlotIndex
    ACCESS          not-accessible
    STATUS          mandatory
    DESCRIPTION     
            "Slot index for this table."
    ::= { sonusSonetLayerEntry 2 }

sonusSonetLayerPortIndex OBJECT-TYPE
    SYNTAX          INTEGER
    ACCESS          not-accessible
    STATUS          mandatory
    DESCRIPTION     
            "Port index for this table."
    ::= { sonusSonetLayerEntry 3 }

sonusSonetLayerIfIndex OBJECT-TYPE
    SYNTAX          INTEGER
    ACCESS          read-only
    STATUS          mandatory
    DESCRIPTION     
            "The ifIndex assigned to this shelf, slot, and port when the 
             SONET Interface was created."
    ::= { sonusSonetLayerEntry 4 }

sonusSonetLayerRowStatus OBJECT-TYPE
    SYNTAX          RowStatus
    ACCESS          read-write
    STATUS          mandatory
    DESCRIPTION     
            "This object is used to create, delete,
             or modify a row in this table."
    ::= { sonusSonetLayerEntry 5 }

sonusSonetObjectsPath OBJECT IDENTIFIER
    ::= { sonusSonetMIB 2 }

sonusSonetPathAdmn OBJECT IDENTIFIER
    ::= { sonusSonetObjectsPath 1 }

sonusSonetPathAdmnTable OBJECT-TYPE
    SYNTAX          SEQUENCE OF SonusSonetPathAdmnEntry
    ACCESS          not-accessible
    STATUS          mandatory
    DESCRIPTION     
            "The Sonus SONET Path Admn Table."
    ::= { sonusSonetPathAdmn 1 }

sonusSonetPathAdmnEntry OBJECT-TYPE
    SYNTAX          SonusSonetPathAdmnEntry
    ACCESS          not-accessible
    STATUS          mandatory
    DESCRIPTION     
            "An entry in the Sonus SONET Path Admn table."
    INDEX           { sonusSonetPathAdmnIfIndex }
    ::= { sonusSonetPathAdmnTable 1 }

SonusSonetPathAdmnEntry ::=
    SEQUENCE {
        sonusSonetPathAdmnIfIndex       INTEGER,
        sonusSonetPathAdmnShelfIndex    SonusShelfIndex,
        sonusSonetPathAdmnSlotIndex     SonusSlotIndex,
        sonusSonetPathAdmnPortIndex     INTEGER,
        sonusSonetPathAdmnPathIndex     INTEGER,
        sonusSonetPathAdmnRowStatus     RowStatus,
        sonusSonetPathAdmnState         SonusAdminState,
        sonusSonetPathAdmnMode          SonusServiceState,
        sonusSonetPathAdmnAction        SonusAdminAction,
        sonusSonetPathAdmnTimeout       INTEGER,
        sonusSonetPathAdmnStatAction    INTEGER,
        sonusSonetPathAdmnRDIMode       INTEGER,
        sonusSonetPathAdmnTraceState    SonusAdminState,
        sonusSonetPathAdmnTraceExpMsg   DisplayString,
        sonusSonetPathAdmnTraceXmtMsg   DisplayString,
        sonusSonetPathAdmnTraceRcvMsg   DisplayString,
        sonusSonetPathAdmnOperStatus    INTEGER,
        sonusSonetPathAdmnDs3ModeOverride SonusAdminState,
        sonusSonetPathAdmnEquippedState INTEGER,
        sonusSonetPathAdmnInitStatistics SonusAdminState,
        sonusSonetPathAdmnSendPattern   INTEGER,
        sonusSonetPathAdmnMonitorPattern INTEGER,
        sonusSonetPathAdmnPatternBER    INTEGER,
        sonusSonetPathAdmnInitPatternErrCnt   SonusAdminState
    }

sonusSonetPathAdmnIfIndex OBJECT-TYPE
    SYNTAX          INTEGER
    ACCESS          not-accessible
    STATUS          mandatory
    DESCRIPTION     
            "The ifIndex assigned to this path when it was created.
             This will not change until the path is deleted."
    ::= { sonusSonetPathAdmnEntry 1 }

sonusSonetPathAdmnShelfIndex OBJECT-TYPE
    SYNTAX          SonusShelfIndex
    ACCESS          read-write
    STATUS          mandatory
    DESCRIPTION     
            "Shelf index for this table."
    ::= { sonusSonetPathAdmnEntry 2 }

sonusSonetPathAdmnSlotIndex OBJECT-TYPE
    SYNTAX          SonusSlotIndex
    ACCESS          read-write
    STATUS          mandatory
    DESCRIPTION     
            "Slot index for this table."
    ::= { sonusSonetPathAdmnEntry 3 }

sonusSonetPathAdmnPortIndex OBJECT-TYPE
    SYNTAX          INTEGER (1..4)
    ACCESS          read-write
    STATUS          mandatory
    DESCRIPTION     
            "OC3 port index for this table."
    ::= { sonusSonetPathAdmnEntry 4 }

sonusSonetPathAdmnPathIndex OBJECT-TYPE
    SYNTAX          INTEGER (1..3)
    ACCESS          read-only
    STATUS          mandatory
    DESCRIPTION     
            "STS1 path index for this table."
    ::= { sonusSonetPathAdmnEntry 5 }

sonusSonetPathAdmnRowStatus OBJECT-TYPE
    SYNTAX          RowStatus
    ACCESS          read-write
    STATUS          mandatory
    DESCRIPTION     
            "This object is used to create, delete, or modify a row in this table."
    ::= { sonusSonetPathAdmnEntry 6 }

sonusSonetPathAdmnState OBJECT-TYPE
    SYNTAX          SonusAdminState
    ACCESS          read-write
    STATUS          mandatory
    DESCRIPTION     
            "State of STS1, Enabled/Disabled"
    DEFVAL          { disabled }
    ::= { sonusSonetPathAdmnEntry 7 }

sonusSonetPathAdmnMode OBJECT-TYPE
    SYNTAX          SonusServiceState
    ACCESS          read-write
    STATUS          mandatory
    DESCRIPTION     
            "STS1 in-service/out-of-service."
    DEFVAL          { outOfService }
    ::= { sonusSonetPathAdmnEntry 8 }

sonusSonetPathAdmnAction OBJECT-TYPE
    SYNTAX          SonusAdminAction
    ACCESS          read-write
    STATUS          mandatory
    DESCRIPTION     
            "The type of action to perform when a SONET path is taken out of 
             service. The SONET path can be dried up, or it can be forced
             out of service."
    DEFVAL          { dryUp }
    ::= { sonusSonetPathAdmnEntry 9 }

sonusSonetPathAdmnTimeout OBJECT-TYPE
    SYNTAX          INTEGER (0..1440)
    ACCESS          read-write
    STATUS          mandatory
    DESCRIPTION     
            "The Dryup Timeout specifies the maximum amount of time to wait for
             all active calls to terminate on a SONET path before the path
             		 should be taken out-of-service."
    DEFVAL          { 5 }
    ::= { sonusSonetPathAdmnEntry 10 }

sonusSonetPathAdmnStatAction OBJECT-TYPE
    SYNTAX          INTEGER { init15MinuteNearEnd(1), 
                        init15MinuteFarEnd(2), init24HourNearEnd(4), 
                        init24HourFarEnd(8) }
    ACCESS          read-write
    STATUS          mandatory
    DESCRIPTION     
            "Initialize Performance Monitoring Statistics.  A PM initialization
             action initiates one request for the action.  Requests to initialize
             more than one group of statistics can be accomplished by OR-ing the 
             appropriate bits (e.g., to initialize all 15 minute PM statistics, 
             set bits 1 and 2). Reading this variable always returns zero."
    ::= { sonusSonetPathAdmnEntry 11 }

sonusSonetPathAdmnRDIMode OBJECT-TYPE
    SYNTAX          INTEGER { normal(1), enhanced(2) }
    ACCESS          read-write
    STATUS          mandatory
    DESCRIPTION     
            "The desired type of SONET port Path Remote Defect Indication to
             use.
             		 (1) normal - Use one-bit RDI-P signalling using bit 5 of G1.
             		 (2) enhanced - Use three-bit RDI-P (ERDI-P) using bits 5-7 of G1."
    DEFVAL          { enhanced }
    ::= { sonusSonetPathAdmnEntry 12 }

sonusSonetPathAdmnTraceState OBJECT-TYPE
    SYNTAX          SonusAdminState
    ACCESS          read-write
    STATUS          mandatory
    DESCRIPTION     
            "The desired state of SONET Path Trace.
             (1) enabled - Enables the generation of SONET Path Trace Messages
             in the J1 bytes of the STS Path overhead, and enables the reception and
             checking of received Path Trace Messages with the Expected Path Trace
             Message.
             (2) disabled - Transmits all zero's in the J1 bytes of the STS Path
             overhead, and disables  the reception and checking of received
             Path Trace Messages with the Expected Path Trace Message."
    DEFVAL          { disabled }
    ::= { sonusSonetPathAdmnEntry 13 }

sonusSonetPathAdmnTraceExpMsg OBJECT-TYPE
    SYNTAX          DisplayString (SIZE(0..61))
    ACCESS          read-write
    STATUS          mandatory
    DESCRIPTION     
            "The expected path trace string to be received on the SONET port in the
             J1 bytes of the STS Path overhead."
    ::= { sonusSonetPathAdmnEntry 14 }

sonusSonetPathAdmnTraceXmtMsg OBJECT-TYPE
    SYNTAX          DisplayString (SIZE(0..61))
    ACCESS          read-write
    STATUS          mandatory
    DESCRIPTION     
            "The path trace string to be transmitted on the SONET port in the J1
             bytes of the STS Path overhead."
    ::= { sonusSonetPathAdmnEntry 15 }

sonusSonetPathAdmnTraceRcvMsg OBJECT-TYPE
    SYNTAX          DisplayString (SIZE(0..61))
    ACCESS          read-only
    STATUS          mandatory
    DESCRIPTION     
            "The path trace string received on the SONET port in the J1
             bytes of the STS Path overhead."
    ::= { sonusSonetPathAdmnEntry 16 }

sonusSonetPathAdmnOperStatus OBJECT-TYPE
    SYNTAX          INTEGER { enabledInService(1), 
                        enabledOutOfService(2), enabledDown(3), 
                        dryingUp(4), disabled(5), up(6), down(7), 
                        remoteDown(8) }
    ACCESS          read-only
    STATUS          mandatory
    DESCRIPTION     
            "The actual status of the Sonet path. Path is 
             Up if it is administratively in service and there are no
             line failures or hardware failures. Path is Down if
             it is administratively in service and there are line
             failures or hardware failures, or if it is administratively
             out of service. Path is DryingUp if it is administratively
             out of service and is drying up (no new	calls, still carrying
             in-progress calls) THE OTHER VALUES ARE NO LONGER SUPPORTED."
    ::= { sonusSonetPathAdmnEntry 17 }

sonusSonetPathAdmnDs3ModeOverride OBJECT-TYPE
    SYNTAX          SonusAdminState
    ACCESS          read-write
    STATUS          mandatory
    DESCRIPTION     
            "This flag controls whether the mode and state of the DS3
             carried in the Path are modified when the mode and state of
             the Path is modified. If this flag is set to Enabled, the DS3
             state and mode are not changed when the Path mode and state
             are changed."
    DEFVAL          { disabled }
    ::= { sonusSonetPathAdmnEntry 18 }

sonusSonetPathAdmnEquippedState OBJECT-TYPE
    SYNTAX          INTEGER { equipped(1), unequipped(2) }
    ACCESS          read-write
    STATUS          mandatory
    DESCRIPTION     
            "This object is used to set the Path to the Equipped or
             Unequipped state. If the Path is Unequipped, the Unequipped
             signal label is sent in the Path overhead, and AIS-P is
             forced."
    DEFVAL          { equipped }
    ::= { sonusSonetPathAdmnEntry 19 }

sonusSonetPathAdmnInitStatistics OBJECT-TYPE
    SYNTAX          SonusAdminState
    ACCESS          read-write
    STATUS          mandatory
    DESCRIPTION     
            "Initializes Path error statistics counts to zero."
    DEFVAL          { disabled }
    ::= { sonusSonetPathAdmnEntry 20 }

sonusSonetPathAdmnSendPattern OBJECT-TYPE
    SYNTAX          INTEGER { none(1), pn15(2), pn15Invert(3) }
    ACCESS          read-write
    STATUS          mandatory
    DESCRIPTION     
            "This object is used to send a PRBS test pattern
             in the Path. Currently 2^15 - 1 pattern is supported."
    DEFVAL          { none }
    ::= { sonusSonetPathAdmnEntry 21 }

sonusSonetPathAdmnMonitorPattern OBJECT-TYPE
    SYNTAX          INTEGER { none(1), pn15(2), pn15Invert(3) }
    ACCESS          read-write
    STATUS          mandatory
    DESCRIPTION     
            "This object is used to monitor a PRBS test pattern
             in the Path. Currently 2^15 - 1 pattern is supported."
    DEFVAL          { none }
    ::= { sonusSonetPathAdmnEntry 22 }

sonusSonetPathAdmnPatternBER OBJECT-TYPE
    SYNTAX          INTEGER { none(0), ber10E-3(1), ber10E-4(2), 
                        ber10E-5(3), ber10E-6(4), ber10E-7(5), 
                        singleBit(6) }
    ACCESS          read-write
    STATUS          mandatory
    DESCRIPTION     
            "This object is used to inject errors into the
             PRBS test pattern."
    DEFVAL          { none }
    ::= { sonusSonetPathAdmnEntry 23 }

sonusSonetPathAdmnInitPatternErrCnt OBJECT-TYPE
    SYNTAX          SonusAdminState
    ACCESS          read-write
    STATUS          mandatory
    DESCRIPTION     
            "Initializes Path test pattern error count to zero."
    DEFVAL          { disabled }
    ::= { sonusSonetPathAdmnEntry 24 }

sonusSonetPath OBJECT IDENTIFIER
    ::= { sonusSonetObjectsPath 2 }

sonusSonetPathThresholdTable OBJECT-TYPE
    SYNTAX          SEQUENCE OF SonusSonetPathThresholdEntry
    ACCESS          not-accessible
    STATUS          mandatory
    DESCRIPTION     
            "The Sonus SONET Path Threshold Table. This table adds objects to
             set the Performance Monitoring thresholds for generating a
             Threshold Crossing Alert."
    ::= { sonusSonetPath 1 }

sonusSonetPathThresholdEntry OBJECT-TYPE
    SYNTAX          SonusSonetPathThresholdEntry
    ACCESS          not-accessible
    STATUS          mandatory
    DESCRIPTION     
            "An entry in the Sonus SONET Path Threshold table."
    INDEX           { sonusSonetPathThresholdIfIndex }
    ::= { sonusSonetPathThresholdTable 1 }

SonusSonetPathThresholdEntry ::=
    SEQUENCE {
        sonusSonetPathThresholdIfIndex  INTEGER,
        sonusSonetPathThresholdPathIndex INTEGER,
        sonusSonetPathThreshold15mCVs   INTEGER,
        sonusSonetPathThreshold15mESs   INTEGER,
        sonusSonetPathThreshold15mSESs  INTEGER,
        sonusSonetPathThreshold15mUASs  INTEGER,
        sonusSonetPathThreshold24hCVs   INTEGER,
        sonusSonetPathThreshold24hESs   INTEGER,
        sonusSonetPathThreshold24hSESs  INTEGER,
        sonusSonetPathThreshold24hUASs  INTEGER,
        sonusSonetPathThresholdCVTcaFilter  SonusAdminState,
        sonusSonetPathThresholdESTcaFilter  SonusAdminState,
        sonusSonetPathThresholdSESTcaFilter   SonusAdminState,
        sonusSonetPathThresholdUASTcaFilter   SonusAdminState
    }

sonusSonetPathThresholdIfIndex OBJECT-TYPE
    SYNTAX          INTEGER
    ACCESS          not-accessible
    STATUS          mandatory
    DESCRIPTION     
            "The ifIndex assigned to this path when it was created.
             This will not change until the path is deleted."
    ::= { sonusSonetPathThresholdEntry 1 }

sonusSonetPathThresholdPathIndex OBJECT-TYPE
    SYNTAX          INTEGER (1..3)
    ACCESS          read-only
    STATUS          mandatory
    DESCRIPTION     
            "STS1 path index for this table."
    ::= { sonusSonetPathThresholdEntry 2 }

sonusSonetPathThreshold15mCVs OBJECT-TYPE
    SYNTAX          INTEGER (0..16383)
    ACCESS          read-write
    STATUS          mandatory
    DESCRIPTION     
            "Threshold for 15 minute interval Path layer Coding Violations."
    ::= { sonusSonetPathThresholdEntry 3 }

sonusSonetPathThreshold15mESs OBJECT-TYPE
    SYNTAX          INTEGER (0..900)
    ACCESS          read-write
    STATUS          mandatory
    DESCRIPTION     
            "Threshold for 15 minute interval Path layer Errored Seconds."
    ::= { sonusSonetPathThresholdEntry 4 }

sonusSonetPathThreshold15mSESs OBJECT-TYPE
    SYNTAX          INTEGER (0..900)
    ACCESS          read-write
    STATUS          mandatory
    DESCRIPTION     
            "Threshold for 15 minute interval Path layer Severely Errored
             Seconds."
    ::= { sonusSonetPathThresholdEntry 5 }

sonusSonetPathThreshold15mUASs OBJECT-TYPE
    SYNTAX          INTEGER (0..900)
    ACCESS          read-write
    STATUS          mandatory
    DESCRIPTION     
            "Threshold for 15 minute interval Path layer Unavailable Seconds."
    ::= { sonusSonetPathThresholdEntry 6 }

sonusSonetPathThreshold24hCVs OBJECT-TYPE
    SYNTAX          INTEGER (0..1048575)
    ACCESS          read-write
    STATUS          mandatory
    DESCRIPTION     
            "Threshold for 24 hour interval Path layer Coding Violations."
    ::= { sonusSonetPathThresholdEntry 7 }

sonusSonetPathThreshold24hESs OBJECT-TYPE
    SYNTAX          INTEGER (0..65535)
    ACCESS          read-write
    STATUS          mandatory
    DESCRIPTION     
            "Threshold for 24 hour interval Path layer Errored Seconds."
    ::= { sonusSonetPathThresholdEntry 8 }

sonusSonetPathThreshold24hSESs OBJECT-TYPE
    SYNTAX          INTEGER (0..65535)
    ACCESS          read-write
    STATUS          mandatory
    DESCRIPTION     
            "Threshold for 24 hour interval Path layer Severely Errored
             Seconds."
    ::= { sonusSonetPathThresholdEntry 9 }

sonusSonetPathThreshold24hUASs OBJECT-TYPE
    SYNTAX          INTEGER (0..65535)
    ACCESS          read-write
    STATUS          mandatory
    DESCRIPTION     
            "Threshold for 24 hour interval Path layer Unavailable Seconds."
    ::= { sonusSonetPathThresholdEntry 10 }

sonusSonetPathThresholdCVTcaFilter OBJECT-TYPE
    SYNTAX          SonusAdminState
    ACCESS          read-write
    STATUS          mandatory
    DESCRIPTION     
            "Controls whether a threshold Crossing Alert (TCA) is reported (via
             an event log and trap). Setting this object to Enabled will prevent
             the TCA from being reported (i.e will Filter the TCA report)."
    DEFVAL          { disabled }
    ::= { sonusSonetPathThresholdEntry 11 }

sonusSonetPathThresholdESTcaFilter OBJECT-TYPE
    SYNTAX          SonusAdminState
    ACCESS          read-write
    STATUS          mandatory
    DESCRIPTION     
            "Controls whether a threshold Crossing Alert (TCA) is reported (via
             an event log and trap). Setting this object to Enabled will prevent
             the TCA from being reported (i.e will Filter the TCA report)."
    DEFVAL          { disabled }
    ::= { sonusSonetPathThresholdEntry 12 }

sonusSonetPathThresholdSESTcaFilter OBJECT-TYPE
    SYNTAX          SonusAdminState
    ACCESS          read-write
    STATUS          mandatory
    DESCRIPTION     
            "Controls whether a threshold Crossing Alert (TCA) is reported (via
             an event log and trap). Setting this object to Enabled will prevent
             the TCA from being reported (i.e will Filter the TCA report)."
    DEFVAL          { disabled }
    ::= { sonusSonetPathThresholdEntry 13 }

sonusSonetPathThresholdUASTcaFilter OBJECT-TYPE
    SYNTAX          SonusAdminState
    ACCESS          read-write
    STATUS          mandatory
    DESCRIPTION     
            "Controls whether a threshold Crossing Alert (TCA) is reported (via
             an event log and trap). Setting this object to Enabled will prevent
             the TCA from being reported (i.e will Filter the TCA report)."
    DEFVAL          { disabled }
    ::= { sonusSonetPathThresholdEntry 14 }

sonusSonetPathCurrentTable OBJECT-TYPE
    SYNTAX          SEQUENCE OF SonusSonetPathCurrentEntry
    ACCESS          not-accessible
    STATUS          mandatory
    DESCRIPTION     
            "The Sonus SONET Path Current table."
    ::= { sonusSonetPath 2 }

sonusSonetPathCurrentEntry OBJECT-TYPE
    SYNTAX          SonusSonetPathCurrentEntry
    ACCESS          not-accessible
    STATUS          mandatory
    DESCRIPTION     
            "An entry in the Sonus SONET Path Current table."
    INDEX           { sonusSonetPathCurrentIfIndex }
    ::= { sonusSonetPathCurrentTable 1 }

SonusSonetPathCurrentEntry ::=
    SEQUENCE {
        sonusSonetPathCurrentIfIndex    INTEGER,
        sonusSonetPathCurrentPathIndex  INTEGER,
        sonusSonetPathCurrentWidth      INTEGER,
        sonusSonetPathCurrentStatus     INTEGER,
        sonusSonetPathCurrentESs        PerfCurrentCount,
        sonusSonetPathCurrentSESs       PerfCurrentCount,
        sonusSonetPathCurrentUASs       PerfCurrentCount,
        sonusSonetPathCurrentCVs        PerfCurrentCount,
        sonusSonetPathCurrentFCs        PerfCurrentCount,
        sonusSonetPathCurrentTraceStatus INTEGER,
        sonusSonetPathCurrentElapsedTime INTEGER,
        sonusSonetPathCurrentDayElapsedTime   INTEGER,
        sonusSonetPathCurrentERDICode   INTEGER,
        sonusSonetPathCurrentSignalLabel INTEGER,
        sonusSonetPathCurrentPatternMonitor   INTEGER,
        sonusSonetPathCurrentPatternBER INTEGER,
        sonusSonetPathCurrentPatternErrorCnt    INTEGER
    }

sonusSonetPathCurrentIfIndex OBJECT-TYPE
    SYNTAX          INTEGER
    ACCESS          not-accessible
    STATUS          mandatory
    DESCRIPTION     
            "The ifIndex assigned to this path when it was created.
             This will not change until the path is deleted."
    ::= { sonusSonetPathCurrentEntry 1 }

sonusSonetPathCurrentPathIndex OBJECT-TYPE
    SYNTAX          INTEGER (1..3)
    ACCESS          read-only
    STATUS          mandatory
    DESCRIPTION     
            "STS1 path index for this table."
    ::= { sonusSonetPathCurrentEntry 2 }

sonusSonetPathCurrentWidth OBJECT-TYPE
    SYNTAX          INTEGER { sts1(1), sts3cSTM1(2), sts12cSTM4(3), 
                        sts24c(4), sts48cSTM16(5) }
    ACCESS          read-only
    STATUS          mandatory
    DESCRIPTION     
            "A value that indicates the type of the SONET/SDH Path.
             For SONET, the assigned types are the STS-Nc SPEs,
             where N = 1, 3, 12, 24, and 48. STS-1 is equal to 51.84
             Mbps. For SDH, the assigned types are the STM-Nc VCs,
             where N = 1, 4, and 16."
    ::= { sonusSonetPathCurrentEntry 3 }

sonusSonetPathCurrentStatus OBJECT-TYPE
    SYNTAX          INTEGER (1..128)
    ACCESS          read-only
    STATUS          mandatory
    DESCRIPTION     
            "This variable indicates the status of the interface. It is
             a bit map represented as a sum, therefore, it can represent
             multiple defects simultaneously. The sonetPathNoDefect
             should be set if and only if no other flag is set.
             
             The various bit positions are:
             1   sonetPathNoDefect
             2   sonetPathSTSLOP
             4   sonetPathSTSAIS
             8   sonetPathSTSRDI
             16  sonetPathUnequiped
             32  sonetPathSignalLabelMismatch
             64  sonetPathTraceMismatch
             128 sonetPathNotMonitored"
    ::= { sonusSonetPathCurrentEntry 4 }

sonusSonetPathCurrentESs OBJECT-TYPE
    SYNTAX          PerfCurrentCount
    ACCESS          read-only
    STATUS          mandatory
    DESCRIPTION     
            "The counter associated with the number of Errored Seconds
             encountered by a SONET/SDH Path in the current 24 hour
             interval."
    ::= { sonusSonetPathCurrentEntry 5 }

sonusSonetPathCurrentSESs OBJECT-TYPE
    SYNTAX          PerfCurrentCount
    ACCESS          read-only
    STATUS          mandatory
    DESCRIPTION     
            "The counter associated with the number of Severely Errored
             Seconds encountered by a SONET/SDH Path in the current 
             24 hour interval."
    ::= { sonusSonetPathCurrentEntry 6 }

sonusSonetPathCurrentUASs OBJECT-TYPE
    SYNTAX          PerfCurrentCount
    ACCESS          read-only
    STATUS          mandatory
    DESCRIPTION     
            "The counter associated with the number of Unavailable
             Seconds encountered by a SONET/SDH Path in the current
             24 hour interval."
    ::= { sonusSonetPathCurrentEntry 7 }

sonusSonetPathCurrentCVs OBJECT-TYPE
    SYNTAX          PerfCurrentCount
    ACCESS          read-only
    STATUS          mandatory
    DESCRIPTION     
            "The counter associated with the number of Coding Violations
             encountered by a SONET/SDH Path in the current 24 hour
             	 interval."
    ::= { sonusSonetPathCurrentEntry 8 }

sonusSonetPathCurrentFCs OBJECT-TYPE
    SYNTAX          PerfCurrentCount
    ACCESS          read-only
    STATUS          mandatory
    DESCRIPTION     
            "The counter associated with the number of Failures encountered
             by a SONET/SDH Path in the current 24 hour interval."
    ::= { sonusSonetPathCurrentEntry 9 }

sonusSonetPathCurrentTraceStatus OBJECT-TYPE
    SYNTAX          INTEGER { nodefect(1), tracemismatch(2), disabled(3) }
    ACCESS          read-only
    STATUS          mandatory
    DESCRIPTION     
            "The status of the Trace Mismatch Failure."
    ::= { sonusSonetPathCurrentEntry 10 }

sonusSonetPathCurrentElapsedTime OBJECT-TYPE
    SYNTAX          INTEGER
    ACCESS          read-only
    STATUS          mandatory
    DESCRIPTION     
            "Elapsed time in the current period"
    ::= { sonusSonetPathCurrentEntry 11 }

sonusSonetPathCurrentDayElapsedTime OBJECT-TYPE
    SYNTAX          INTEGER
    ACCESS          read-only
    STATUS          mandatory
    DESCRIPTION     
            "Elapsed time in the current period"
    ::= { sonusSonetPathCurrentEntry 12 }

sonusSonetPathCurrentERDICode OBJECT-TYPE
    SYNTAX          INTEGER { noRemoteDefect(1), oneBitRdiDefect(2), 
                        erdiPayloadDefect(3), erdiServerDefect(4), 
                        erdiConnectivityDefect(5), notAvailable(6) }
    ACCESS          read-only
    STATUS          mandatory
    DESCRIPTION     
            "Enhanced RDI code currently being received"
    ::= { sonusSonetPathCurrentEntry 13 }

sonusSonetPathCurrentSignalLabel OBJECT-TYPE
    SYNTAX          INTEGER { unequipped(1), equippedNonSpecific(2), 
                        vtStructured(3), asyncDs3(4), lockedVT(5), 
                        asyncDs4(6), atm(7), dqdb(8), fddi(9), 
                        o181TestSignal(10), reserved(11), 
                        notAvailable(12) }
    ACCESS          read-only
    STATUS          mandatory
    DESCRIPTION     
            "Payload signal label currently being received"
    ::= { sonusSonetPathCurrentEntry 14 }

sonusSonetPathCurrentPatternMonitor OBJECT-TYPE
    SYNTAX          INTEGER { disabled(1), mismatch(2), pn15(3), 
                        pn15Invert(4) }
    ACCESS          read-only
    STATUS          mandatory
    DESCRIPTION     
            "The status of the pattern monitor."
    ::= { sonusSonetPathCurrentEntry 15 }

sonusSonetPathCurrentPatternBER OBJECT-TYPE
    SYNTAX          INTEGER { none(0), ber10E-3(1), ber10E-4(2), 
                        ber10E-5(3), ber10E-6(4), ber10E-7(5) }
    ACCESS          read-only
    STATUS          mandatory
    DESCRIPTION     
            "The bit error rate detected by the pattern monitor."
    ::= { sonusSonetPathCurrentEntry 16 }

sonusSonetPathCurrentPatternErrorCnt OBJECT-TYPE
    SYNTAX          INTEGER
    ACCESS          read-only
    STATUS          mandatory
    DESCRIPTION     
            "Count of bit errors detected by the pattern monitor."
    ::= { sonusSonetPathCurrentEntry 17 }

sonusSonetPathIntervalTable OBJECT-TYPE
    SYNTAX          SEQUENCE OF SonusSonetPathIntervalEntry
    ACCESS          not-accessible
    STATUS          mandatory
    DESCRIPTION     
            "The Sonus SONET Path Interval table."
    ::= { sonusSonetPath 3 }

sonusSonetPathIntervalEntry OBJECT-TYPE
    SYNTAX          SonusSonetPathIntervalEntry
    ACCESS          not-accessible
    STATUS          mandatory
    DESCRIPTION     
            "An entry in the Sonus SONET Path Interval table."
    INDEX           { sonusSonetPathIntervalIfIndex, 
                      sonusSonetPathIntervalNumber }
    ::= { sonusSonetPathIntervalTable 1 }

SonusSonetPathIntervalEntry ::=
    SEQUENCE {
        sonusSonetPathIntervalIfIndex   INTEGER,
        sonusSonetPathIntervalPathIndex INTEGER,
        sonusSonetPathIntervalNumber    INTEGER,
        sonusSonetPathIntervalESs       PerfIntervalCount,
        sonusSonetPathIntervalSESs      PerfIntervalCount,
        sonusSonetPathIntervalUASs      PerfIntervalCount,
        sonusSonetPathIntervalCVs       PerfIntervalCount,
        sonusSonetPathIntervalFCs       PerfIntervalCount,
        sonusSonetPathIntervalValidData TruthValue
    }

sonusSonetPathIntervalIfIndex OBJECT-TYPE
    SYNTAX          INTEGER
    ACCESS          not-accessible
    STATUS          mandatory
    DESCRIPTION     
            "The ifIndex assigned to this path when it was created.
             This will not change until the path is deleted."
    ::= { sonusSonetPathIntervalEntry 1 }

sonusSonetPathIntervalPathIndex OBJECT-TYPE
    SYNTAX          INTEGER (1..3)
    ACCESS          read-only
    STATUS          mandatory
    DESCRIPTION     
            "STS1 path index for this table."
    ::= { sonusSonetPathIntervalEntry 2 }

sonusSonetPathIntervalNumber OBJECT-TYPE
    SYNTAX          INTEGER (1)
    ACCESS          not-accessible
    STATUS          mandatory
    DESCRIPTION     
            "The number 1 identifies the most recently completed 24 hour
             interval. In the future if more 24 hour intervals are supported,
             the interval identified by N is the interval immediately
             preceding the one identified by N-1."
    ::= { sonusSonetPathIntervalEntry 3 }

sonusSonetPathIntervalESs OBJECT-TYPE
    SYNTAX          PerfIntervalCount
    ACCESS          read-only
    STATUS          mandatory
    DESCRIPTION     
            "The counter associated with the number of Errored Seconds
             encountered by a SONET/SDH Path in the previous 24 hour
             interval."
    ::= { sonusSonetPathIntervalEntry 4 }

sonusSonetPathIntervalSESs OBJECT-TYPE
    SYNTAX          PerfIntervalCount
    ACCESS          read-only
    STATUS          mandatory
    DESCRIPTION     
            "The counter associated with the number of Severely Errored
             Seconds encountered by a SONET/SDH Path in the previous 
             24 hour interval."
    ::= { sonusSonetPathIntervalEntry 5 }

sonusSonetPathIntervalUASs OBJECT-TYPE
    SYNTAX          PerfIntervalCount
    ACCESS          read-only
    STATUS          mandatory
    DESCRIPTION     
            "The counter associated with the number of Unavailable
             Seconds encountered by a SONET/SDH Path in the previous
             24 hour interval."
    ::= { sonusSonetPathIntervalEntry 6 }

sonusSonetPathIntervalCVs OBJECT-TYPE
    SYNTAX          PerfIntervalCount
    ACCESS          read-only
    STATUS          mandatory
    DESCRIPTION     
            "The counter associated with the number of Coding Violations
             encountered by a SONET/SDH Path in the previous 24 hour
             	 interval."
    ::= { sonusSonetPathIntervalEntry 7 }

sonusSonetPathIntervalFCs OBJECT-TYPE
    SYNTAX          PerfIntervalCount
    ACCESS          read-only
    STATUS          mandatory
    DESCRIPTION     
            "The counter associated with the number of Failures encountered
             by a SONET/SDH Path in the previous 24 hour interval."
    ::= { sonusSonetPathIntervalEntry 8 }

sonusSonetPathIntervalValidData OBJECT-TYPE
    SYNTAX          TruthValue
    ACCESS          read-only
    STATUS          mandatory
    DESCRIPTION     
            "This variable indicates if the data for this interval is valid."
    ::= { sonusSonetPathIntervalEntry 9 }

sonusSonetFarEndPathCurrentTable OBJECT-TYPE
    SYNTAX          SEQUENCE OF SonusSonetFarEndPathCurrentEntry
    ACCESS          not-accessible
    STATUS          mandatory
    DESCRIPTION     
            "The Sonus SONET Far End Path Current table."
    ::= { sonusSonetPath 4 }

sonusSonetFarEndPathCurrentEntry OBJECT-TYPE
    SYNTAX          SonusSonetFarEndPathCurrentEntry
    ACCESS          not-accessible
    STATUS          mandatory
    DESCRIPTION     
            "An entry in the Sonus SONET Far End Path Current table."
    INDEX           { sonusSonetFarEndPathCurrentIfIndex }
    ::= { sonusSonetFarEndPathCurrentTable 1 }

SonusSonetFarEndPathCurrentEntry ::=
    SEQUENCE {
        sonusSonetFarEndPathCurrentIfIndex  INTEGER,
        sonusSonetFarEndPathCurrentPathIndex    INTEGER,
        sonusSonetFarEndPathCurrentESs  PerfCurrentCount,
        sonusSonetFarEndPathCurrentSESs PerfCurrentCount,
        sonusSonetFarEndPathCurrentUASs PerfCurrentCount,
        sonusSonetFarEndPathCurrentCVs  PerfCurrentCount,
        sonusSonetFarEndPathCurrentFCs  PerfCurrentCount
    }

sonusSonetFarEndPathCurrentIfIndex OBJECT-TYPE
    SYNTAX          INTEGER
    ACCESS          not-accessible
    STATUS          mandatory
    DESCRIPTION     
            "The ifIndex assigned to this path when it was created.
             This will not change until the path is deleted."
    ::= { sonusSonetFarEndPathCurrentEntry 1 }

sonusSonetFarEndPathCurrentPathIndex OBJECT-TYPE
    SYNTAX          INTEGER (1..3)
    ACCESS          read-only
    STATUS          mandatory
    DESCRIPTION     
            "STS1 path index for this table."
    ::= { sonusSonetFarEndPathCurrentEntry 2 }

sonusSonetFarEndPathCurrentESs OBJECT-TYPE
    SYNTAX          PerfCurrentCount
    ACCESS          read-only
    STATUS          mandatory
    DESCRIPTION     
            "The counter associated with the number of Far End Errored
             Seconds encountered by a SONET/SDH Path in the current
             24 hour interval."
    ::= { sonusSonetFarEndPathCurrentEntry 3 }

sonusSonetFarEndPathCurrentSESs OBJECT-TYPE
    SYNTAX          PerfCurrentCount
    ACCESS          read-only
    STATUS          mandatory
    DESCRIPTION     
            "The counter associated with the number of Far End Severely
             Errored Seconds encountered by a SONET/SDH Path in the
             current 24 hour interval."
    ::= { sonusSonetFarEndPathCurrentEntry 4 }

sonusSonetFarEndPathCurrentUASs OBJECT-TYPE
    SYNTAX          PerfCurrentCount
    ACCESS          read-only
    STATUS          mandatory
    DESCRIPTION     
            "The counter associated with the number of Far End 
             Unavailable Seconds encountered by a SONET/SDH Path in the
             current 24 hour interval."
    ::= { sonusSonetFarEndPathCurrentEntry 5 }

sonusSonetFarEndPathCurrentCVs OBJECT-TYPE
    SYNTAX          PerfCurrentCount
    ACCESS          read-only
    STATUS          mandatory
    DESCRIPTION     
            "The counter associated with the number of Far End Coding
             Violations encountered by a SONET/SDH Path in the current
             	 24 hour interval."
    ::= { sonusSonetFarEndPathCurrentEntry 6 }

sonusSonetFarEndPathCurrentFCs OBJECT-TYPE
    SYNTAX          PerfCurrentCount
    ACCESS          read-only
    STATUS          mandatory
    DESCRIPTION     
            "The counter associated with the number of Far End Failures
             encountered by a SONET/SDH Path in the current 24 hour
             interval."
    ::= { sonusSonetFarEndPathCurrentEntry 7 }

sonusSonetFarEndPathIntervalTable OBJECT-TYPE
    SYNTAX          SEQUENCE OF SonusSonetFarEndPathIntervalEntry
    ACCESS          not-accessible
    STATUS          mandatory
    DESCRIPTION     
            "The Sonus SONET Far End Path Interval table."
    ::= { sonusSonetPath 5 }

sonusSonetFarEndPathIntervalEntry OBJECT-TYPE
    SYNTAX          SonusSonetFarEndPathIntervalEntry
    ACCESS          not-accessible
    STATUS          mandatory
    DESCRIPTION     
            "An entry in the Sonus SONET Far End Path Interval table."
    INDEX           { sonusSonetFarEndPathIntervalIfIndex, 
                      sonusSonetFarEndPathIntervalNumber }
    ::= { sonusSonetFarEndPathIntervalTable 1 }

SonusSonetFarEndPathIntervalEntry ::=
    SEQUENCE {
        sonusSonetFarEndPathIntervalIfIndex   INTEGER,
        sonusSonetFarEndPathIntervalPathIndex     INTEGER,
        sonusSonetFarEndPathIntervalNumber  INTEGER,
        sonusSonetFarEndPathIntervalESs PerfIntervalCount,
        sonusSonetFarEndPathIntervalSESs PerfIntervalCount,
        sonusSonetFarEndPathIntervalUASs PerfIntervalCount,
        sonusSonetFarEndPathIntervalCVs PerfIntervalCount,
        sonusSonetFarEndPathIntervalFCs PerfIntervalCount,
        sonusSonetFarEndPathIntervalValidData     TruthValue
    }

sonusSonetFarEndPathIntervalIfIndex OBJECT-TYPE
    SYNTAX          INTEGER
    ACCESS          not-accessible
    STATUS          mandatory
    DESCRIPTION     
            "The ifIndex assigned to this path when it was created.
             This will not change until the path is deleted."
    ::= { sonusSonetFarEndPathIntervalEntry 1 }

sonusSonetFarEndPathIntervalPathIndex OBJECT-TYPE
    SYNTAX          INTEGER (1..3)
    ACCESS          read-only
    STATUS          mandatory
    DESCRIPTION     
            "STS1 path index for this table."
    ::= { sonusSonetFarEndPathIntervalEntry 2 }

sonusSonetFarEndPathIntervalNumber OBJECT-TYPE
    SYNTAX          INTEGER (1)
    ACCESS          not-accessible
    STATUS          mandatory
    DESCRIPTION     
            "The number 1 identifies the most recently completed 24 hour
             interval. In the future if more 24 hour intervals are supported,
             the interval identified by N is the interval immediately
             preceding the one identified by N-1."
    ::= { sonusSonetFarEndPathIntervalEntry 3 }

sonusSonetFarEndPathIntervalESs OBJECT-TYPE
    SYNTAX          PerfIntervalCount
    ACCESS          read-only
    STATUS          mandatory
    DESCRIPTION     
            "The counter associated with the number of Far End Errored
             Seconds encountered by a SONET/SDH Path in the current
             24 hour interval."
    ::= { sonusSonetFarEndPathIntervalEntry 4 }

sonusSonetFarEndPathIntervalSESs OBJECT-TYPE
    SYNTAX          PerfIntervalCount
    ACCESS          read-only
    STATUS          mandatory
    DESCRIPTION     
            "The counter associated with the number of Far End Severely
             Errored Seconds encountered by a SONET/SDH Path in the
             current 24 hour interval."
    ::= { sonusSonetFarEndPathIntervalEntry 5 }

sonusSonetFarEndPathIntervalUASs OBJECT-TYPE
    SYNTAX          PerfIntervalCount
    ACCESS          read-only
    STATUS          mandatory
    DESCRIPTION     
            "The counter associated with the number of Far End 
             Unavailable Seconds encountered by a SONET/SDH Path in the
             current 24 hour interval."
    ::= { sonusSonetFarEndPathIntervalEntry 6 }

sonusSonetFarEndPathIntervalCVs OBJECT-TYPE
    SYNTAX          PerfIntervalCount
    ACCESS          read-only
    STATUS          mandatory
    DESCRIPTION     
            "The counter associated with the number of Far End Coding
             Violations encountered by a SONET/SDH Path in the current
             	 24 hour interval."
    ::= { sonusSonetFarEndPathIntervalEntry 7 }

sonusSonetFarEndPathIntervalFCs OBJECT-TYPE
    SYNTAX          PerfIntervalCount
    ACCESS          read-only
    STATUS          mandatory
    DESCRIPTION     
            "The counter associated with the number of Far End Failures
             encountered by a SONET/SDH Path in the current 24 hour
             interval."
    ::= { sonusSonetFarEndPathIntervalEntry 8 }

sonusSonetFarEndPathIntervalValidData OBJECT-TYPE
    SYNTAX          TruthValue
    ACCESS          read-only
    STATUS          mandatory
    DESCRIPTION     
            "This variable indicates if the data for this interval is valid."
    ::= { sonusSonetFarEndPathIntervalEntry 9 }

sonusSonetPathFailureCurrentTable OBJECT-TYPE
    SYNTAX          SEQUENCE OF SonusSonetPathFailureCurrentEntry
    ACCESS          not-accessible
    STATUS          mandatory
    DESCRIPTION     
            "The Sonus SONET Path Failure Current table."
    ::= { sonusSonetPath 6 }

sonusSonetPathFailureCurrentEntry OBJECT-TYPE
    SYNTAX          SonusSonetPathFailureCurrentEntry
    ACCESS          not-accessible
    STATUS          mandatory
    DESCRIPTION     
            "An entry in the Sonus SONET Path Failure Current table."
    INDEX           { sonusSonetPathFailureCurrentIfIndex }
    ::= { sonusSonetPathFailureCurrentTable 1 }

SonusSonetPathFailureCurrentEntry ::=
    SEQUENCE {
        sonusSonetPathFailureCurrentIfIndex   INTEGER,
        sonusSonetPathFailureCurrentPathIndex     INTEGER,
        sonusSonetPathFailureCurrentFCs PerfCurrentCount,
        sonusSonetPathFailureCurrentTraceStatus       INTEGER
    }

sonusSonetPathFailureCurrentIfIndex OBJECT-TYPE
    SYNTAX          INTEGER
    ACCESS          not-accessible
    STATUS          mandatory
    DESCRIPTION     
            "The ifIndex assigned to this path when it was created.
             This will not change until the path is deleted."
    ::= { sonusSonetPathFailureCurrentEntry 1 }

sonusSonetPathFailureCurrentPathIndex OBJECT-TYPE
    SYNTAX          INTEGER (1..3)
    ACCESS          read-only
    STATUS          mandatory
    DESCRIPTION     
            "STS1 path index for this table."
    ::= { sonusSonetPathFailureCurrentEntry 2 }

sonusSonetPathFailureCurrentFCs OBJECT-TYPE
    SYNTAX          PerfCurrentCount
    ACCESS          read-only
    STATUS          mandatory
    DESCRIPTION     
            "The counter associated with the number of Failures encountered
             by a SONET/SDH Path in the current 15 minute interval."
    ::= { sonusSonetPathFailureCurrentEntry 3 }

sonusSonetPathFailureCurrentTraceStatus OBJECT-TYPE
    SYNTAX          INTEGER { nodefect(1), tracemismatch(2) }
    ACCESS          read-only
    STATUS          mandatory
    DESCRIPTION     
            "The status of the Trace Mismatch Failure."
    ::= { sonusSonetPathFailureCurrentEntry 4 }

sonusSonetPathFailureIntervalTable OBJECT-TYPE
    SYNTAX          SEQUENCE OF SonusSonetPathFailureIntervalEntry
    ACCESS          not-accessible
    STATUS          mandatory
    DESCRIPTION     
            "The Sonus SONET Path Failure Interval table."
    ::= { sonusSonetPath 7 }

sonusSonetPathFailureIntervalEntry OBJECT-TYPE
    SYNTAX          SonusSonetPathFailureIntervalEntry
    ACCESS          not-accessible
    STATUS          mandatory
    DESCRIPTION     
            "An entry in the Sonus SONET Path Failure Interval table."
    INDEX           { sonusSonetPathFailureIntervalIfIndex, 
                      sonusSonetPathFailureIntervalNumber }
    ::= { sonusSonetPathFailureIntervalTable 1 }

SonusSonetPathFailureIntervalEntry ::=
    SEQUENCE {
        sonusSonetPathFailureIntervalIfIndex    INTEGER,
        sonusSonetPathFailureIntervalPathIndex      INTEGER,
        sonusSonetPathFailureIntervalNumber   INTEGER,
        sonusSonetPathFailureIntervalFCs PerfCurrentCount
    }

sonusSonetPathFailureIntervalIfIndex OBJECT-TYPE
    SYNTAX          INTEGER
    ACCESS          not-accessible
    STATUS          mandatory
    DESCRIPTION     
            "The ifIndex assigned to this path when it was created.
             This will not change until the path is deleted."
    ::= { sonusSonetPathFailureIntervalEntry 1 }

sonusSonetPathFailureIntervalPathIndex OBJECT-TYPE
    SYNTAX          INTEGER (1..3)
    ACCESS          read-only
    STATUS          mandatory
    DESCRIPTION     
            "STS1 path index for this table."
    ::= { sonusSonetPathFailureIntervalEntry 2 }

sonusSonetPathFailureIntervalNumber OBJECT-TYPE
    SYNTAX          INTEGER
    ACCESS          not-accessible
    STATUS          mandatory
    DESCRIPTION     
            "A number between 1 and 32, which identifies the interval
             for which the set of statistics is available. The number 1
             identifies the most recently completed interval, and the
             interval identified by N is the interval immediately
             preceding the one identified by N-1."
    ::= { sonusSonetPathFailureIntervalEntry 3 }

sonusSonetPathFailureIntervalFCs OBJECT-TYPE
    SYNTAX          PerfCurrentCount
    ACCESS          read-only
    STATUS          mandatory
    DESCRIPTION     
            "The counter associated with the number of Failures encountered
             by a SONET/SDH Path in the current 15 minute interval."
    ::= { sonusSonetPathFailureIntervalEntry 4 }

sonusSonetFarEndPathFailureCurrentTable OBJECT-TYPE
    SYNTAX          SEQUENCE OF SonusSonetFarEndPathFailureCurrentEntry
    ACCESS          not-accessible
    STATUS          mandatory
    DESCRIPTION     
            "The Sonus SONET Far End Path Failure Current table."
    ::= { sonusSonetPath 8 }

sonusSonetFarEndPathFailureCurrentEntry OBJECT-TYPE
    SYNTAX          SonusSonetFarEndPathFailureCurrentEntry
    ACCESS          not-accessible
    STATUS          mandatory
    DESCRIPTION     
            "An entry in the Sonus SONET Far End Path Failure Current table."
    INDEX           { sonusSonetFarEndPathFailureCurrentIfIndex }
    ::= { sonusSonetFarEndPathFailureCurrentTable 1 }

SonusSonetFarEndPathFailureCurrentEntry ::=
    SEQUENCE {
        sonusSonetFarEndPathFailureCurrentIfIndex         INTEGER,
        sonusSonetFarEndPathFailureCurrentPathIndex           INTEGER,
        sonusSonetFarEndPathFailureCurrentFCs     PerfCurrentCount
    }

sonusSonetFarEndPathFailureCurrentIfIndex OBJECT-TYPE
    SYNTAX          INTEGER
    ACCESS          not-accessible
    STATUS          mandatory
    DESCRIPTION     
            "The ifIndex assigned to this path when it was created.
             This will not change until the path is deleted."
    ::= { sonusSonetFarEndPathFailureCurrentEntry 1 }

sonusSonetFarEndPathFailureCurrentPathIndex OBJECT-TYPE
    SYNTAX          INTEGER (1..3)
    ACCESS          read-only
    STATUS          mandatory
    DESCRIPTION     
            "STS1 path index for this table."
    ::= { sonusSonetFarEndPathFailureCurrentEntry 2 }

sonusSonetFarEndPathFailureCurrentFCs OBJECT-TYPE
    SYNTAX          PerfCurrentCount
    ACCESS          read-only
    STATUS          mandatory
    DESCRIPTION     
            "The counter associated with the number of Failures encountered
             by a SONET/SDH Path in the current 15 minute interval."
    ::= { sonusSonetFarEndPathFailureCurrentEntry 3 }

sonusSonetFarEndPathFailureIntervalTable OBJECT-TYPE
    SYNTAX          SEQUENCE OF SonusSonetFarEndPathFailureIntervalEntry
    ACCESS          not-accessible
    STATUS          mandatory
    DESCRIPTION     
            "The Sonus SONET Far End Path Failure Interval table."
    ::= { sonusSonetPath 9 }

sonusSonetFarEndPathFailureIntervalEntry OBJECT-TYPE
    SYNTAX          SonusSonetFarEndPathFailureIntervalEntry
    ACCESS          not-accessible
    STATUS          mandatory
    DESCRIPTION     
            "An entry in the Sonus SONET Far End Path Failure Interval table."
    INDEX           { sonusSonetFarEndPathFailureIntervalIfIndex, 
                      sonusSonetFarEndPathFailureIntervalNumber }
    ::= { sonusSonetFarEndPathFailureIntervalTable 1 }

SonusSonetFarEndPathFailureIntervalEntry ::=
    SEQUENCE {
        sonusSonetFarEndPathFailureIntervalIfIndex          INTEGER,
        sonusSonetFarEndPathFailureIntervalPathIndex            INTEGER,
        sonusSonetFarEndPathFailureIntervalNumber         INTEGER,
        sonusSonetFarEndPathFailureIntervalFCs      PerfCurrentCount
    }

sonusSonetFarEndPathFailureIntervalIfIndex OBJECT-TYPE
    SYNTAX          INTEGER
    ACCESS          not-accessible
    STATUS          mandatory
    DESCRIPTION     
            "The ifIndex assigned to this path when it was created.
             This will not change until the path is deleted."
    ::= { sonusSonetFarEndPathFailureIntervalEntry 1 }

sonusSonetFarEndPathFailureIntervalPathIndex OBJECT-TYPE
    SYNTAX          INTEGER (1..3)
    ACCESS          read-only
    STATUS          mandatory
    DESCRIPTION     
            "STS1 path index for this table."
    ::= { sonusSonetFarEndPathFailureIntervalEntry 2 }

sonusSonetFarEndPathFailureIntervalNumber OBJECT-TYPE
    SYNTAX          INTEGER
    ACCESS          not-accessible
    STATUS          mandatory
    DESCRIPTION     
            "A number between 1 and 32, which identifies the interval
             for which the set of statistics is available. The number 1
             identifies the most recently completed interval, and the
             interval identified by N is the interval immediately
             preceding the one identified by N-1."
    ::= { sonusSonetFarEndPathFailureIntervalEntry 3 }

sonusSonetFarEndPathFailureIntervalFCs OBJECT-TYPE
    SYNTAX          PerfCurrentCount
    ACCESS          read-only
    STATUS          mandatory
    DESCRIPTION     
            "The counter associated with the number of Failures encountered
             by a SONET/SDH Path in the current 15 minute interval."
    ::= { sonusSonetFarEndPathFailureIntervalEntry 4 }

sonusSonetPathTcaTable OBJECT-TYPE
    SYNTAX          SEQUENCE OF SonusSonetPathTcaEntry
    ACCESS          not-accessible
    STATUS          mandatory
    DESCRIPTION     
            "The Sonus SONET Path Threshold Crossing Alert table."
    ::= { sonusSonetPath 10 }

sonusSonetPathTcaEntry OBJECT-TYPE
    SYNTAX          SonusSonetPathTcaEntry
    ACCESS          not-accessible
    STATUS          mandatory
    DESCRIPTION     
            "An entry in the Sonus SONET Path Threshold Crossing Alert table."
    INDEX           { sonusSonetPathTcaIfIndex }
    ::= { sonusSonetPathTcaTable 1 }

SonusSonetPathTcaEntry ::=
    SEQUENCE {
        sonusSonetPathTcaIfIndex        INTEGER,
        sonusSonetPathTca15mES          TruthValue,
        sonusSonetPathTca15mSES         TruthValue,
        sonusSonetPathTca15mUAS         TruthValue,
        sonusSonetPathTca15mCV          TruthValue,
        sonusSonetPathTca24hES          TruthValue,
        sonusSonetPathTca24hSES         TruthValue,
        sonusSonetPathTca24hUAS         TruthValue,
        sonusSonetPathTca24hCV          TruthValue,
        sonusSonetPathTcaFarEnd15mES    TruthValue,
        sonusSonetPathTcaFarEnd15mSES   TruthValue,
        sonusSonetPathTcaFarEnd15mUAS   TruthValue,
        sonusSonetPathTcaFarEnd15mCV    TruthValue,
        sonusSonetPathTcaFarEnd24hES    TruthValue,
        sonusSonetPathTcaFarEnd24hSES   TruthValue,
        sonusSonetPathTcaFarEnd24hUAS   TruthValue,
        sonusSonetPathTcaFarEnd24hCV    TruthValue
    }

sonusSonetPathTcaIfIndex OBJECT-TYPE
    SYNTAX          INTEGER
    ACCESS          not-accessible
    STATUS          mandatory
    DESCRIPTION     
            "The ifIndex assigned to this port when it was created.
             This will not change until the port is deleted."
    ::= { sonusSonetPathTcaEntry 1 }

sonusSonetPathTca15mES OBJECT-TYPE
    SYNTAX          TruthValue
    ACCESS          read-only
    STATUS          mandatory
    DESCRIPTION     
            "Indicates status of threshold crossing for Path Errored
             Seconds in the current 15 minute interval."
    ::= { sonusSonetPathTcaEntry 2 }

sonusSonetPathTca15mSES OBJECT-TYPE
    SYNTAX          TruthValue
    ACCESS          read-only
    STATUS          mandatory
    DESCRIPTION     
            "Indicates status of threshold crossing for Path Severely
             Errored Seconds in the current 15 minute interval."
    ::= { sonusSonetPathTcaEntry 3 }

sonusSonetPathTca15mUAS OBJECT-TYPE
    SYNTAX          TruthValue
    ACCESS          read-only
    STATUS          mandatory
    DESCRIPTION     
            "Indicates status of threshold crossing for Path Unavailable
             Seconds in the current 15 minute interval."
    ::= { sonusSonetPathTcaEntry 4 }

sonusSonetPathTca15mCV OBJECT-TYPE
    SYNTAX          TruthValue
    ACCESS          read-only
    STATUS          mandatory
    DESCRIPTION     
            "Indicates status of threshold crossing for Path Coding
             Violations in the current 15 minute interval."
    ::= { sonusSonetPathTcaEntry 5 }

sonusSonetPathTca24hES OBJECT-TYPE
    SYNTAX          TruthValue
    ACCESS          read-only
    STATUS          mandatory
    DESCRIPTION     
            "Indicates status of threshold crossing for Path Errored
             Seconds in the current 24 hour interval."
    ::= { sonusSonetPathTcaEntry 6 }

sonusSonetPathTca24hSES OBJECT-TYPE
    SYNTAX          TruthValue
    ACCESS          read-only
    STATUS          mandatory
    DESCRIPTION     
            "Indicates status of threshold crossing for Path Severely
             Errored Seconds in the current 24 hour interval."
    ::= { sonusSonetPathTcaEntry 7 }

sonusSonetPathTca24hUAS OBJECT-TYPE
    SYNTAX          TruthValue
    ACCESS          read-only
    STATUS          mandatory
    DESCRIPTION     
            "Indicates status of threshold crossing for Path Unavailable
             Seconds in the current 24 hour interval."
    ::= { sonusSonetPathTcaEntry 8 }

sonusSonetPathTca24hCV OBJECT-TYPE
    SYNTAX          TruthValue
    ACCESS          read-only
    STATUS          mandatory
    DESCRIPTION     
            "Indicates status of threshold crossing for Path Coding
             Violations in the current 24 hour interval."
    ::= { sonusSonetPathTcaEntry 9 }

sonusSonetPathTcaFarEnd15mES OBJECT-TYPE
    SYNTAX          TruthValue
    ACCESS          read-only
    STATUS          mandatory
    DESCRIPTION     
            "Indicates status of threshold crossing for Far End Path Errored
             Seconds in the current 15 minute interval."
    ::= { sonusSonetPathTcaEntry 10 }

sonusSonetPathTcaFarEnd15mSES OBJECT-TYPE
    SYNTAX          TruthValue
    ACCESS          read-only
    STATUS          mandatory
    DESCRIPTION     
            "Indicates status of threshold crossing for Far End Path Severely
             Errored Seconds in the current 15 minute interval."
    ::= { sonusSonetPathTcaEntry 11 }

sonusSonetPathTcaFarEnd15mUAS OBJECT-TYPE
    SYNTAX          TruthValue
    ACCESS          read-only
    STATUS          mandatory
    DESCRIPTION     
            "Indicates status of threshold crossing for Far End Path Unavailable
             Seconds in the current 15 minute interval."
    ::= { sonusSonetPathTcaEntry 12 }

sonusSonetPathTcaFarEnd15mCV OBJECT-TYPE
    SYNTAX          TruthValue
    ACCESS          read-only
    STATUS          mandatory
    DESCRIPTION     
            "Indicates status of threshold crossing for Far End Path Coding
             Violations in the current 15 minute interval."
    ::= { sonusSonetPathTcaEntry 13 }

sonusSonetPathTcaFarEnd24hES OBJECT-TYPE
    SYNTAX          TruthValue
    ACCESS          read-only
    STATUS          mandatory
    DESCRIPTION     
            "Indicates status of threshold crossing for Far End Path Errored
             Seconds in the current 24 hour interval."
    ::= { sonusSonetPathTcaEntry 14 }

sonusSonetPathTcaFarEnd24hSES OBJECT-TYPE
    SYNTAX          TruthValue
    ACCESS          read-only
    STATUS          mandatory
    DESCRIPTION     
            "Indicates status of threshold crossing for Far End Path Severely
             Errored Seconds in the current 24 hour interval."
    ::= { sonusSonetPathTcaEntry 15 }

sonusSonetPathTcaFarEnd24hUAS OBJECT-TYPE
    SYNTAX          TruthValue
    ACCESS          read-only
    STATUS          mandatory
    DESCRIPTION     
            "Indicates status of threshold crossing for Far End Path Unavailable
             Seconds in the current 24 hour interval."
    ::= { sonusSonetPathTcaEntry 16 }

sonusSonetPathTcaFarEnd24hCV OBJECT-TYPE
    SYNTAX          TruthValue
    ACCESS          read-only
    STATUS          mandatory
    DESCRIPTION     
            "Indicates status of threshold crossing for Far End Path Coding
             Violations in the current 24 hour interval."
    ::= { sonusSonetPathTcaEntry 17 }

sonusSonetPathStatisticsTable OBJECT-TYPE
    SYNTAX          SEQUENCE OF SonusSonetPathStatisticsEntry
    ACCESS          not-accessible
    STATUS          mandatory
    DESCRIPTION     
            "The Sonus SONET Path Statistics table."
    ::= { sonusSonetPath 11 }

sonusSonetPathStatisticsEntry OBJECT-TYPE
    SYNTAX          SonusSonetPathStatisticsEntry
    ACCESS          not-accessible
    STATUS          mandatory
    DESCRIPTION     
            "An entry in the Sonus SONET Path Statistics table."
    INDEX           { sonusSonetPathStatisticsIfIndex }
    ::= { sonusSonetPathStatisticsTable 1 }

SonusSonetPathStatisticsEntry ::=
    SEQUENCE {
        sonusSonetPathStatisticsIfIndex INTEGER,
        sonusSonetPathStatisticsDefectAIS INTEGER,
        sonusSonetPathStatisticsDefectLOP INTEGER,
        sonusSonetPathStatisticsDefectRDI INTEGER,
        sonusSonetPathStatisticsAlarmAIS INTEGER,
        sonusSonetPathStatisticsAlarmLOP INTEGER,
        sonusSonetPathStatisticsAlarmRFI INTEGER,
        sonusSonetPathStatisticsCodeViolation     INTEGER,
        sonusSonetPathStatisticsREI     INTEGER
    }

sonusSonetPathStatisticsIfIndex OBJECT-TYPE
    SYNTAX          INTEGER
    ACCESS          not-accessible
    STATUS          mandatory
    DESCRIPTION     
            "The ifIndex assigned to this port when it was created.
             This will not change until the port is deleted."
    ::= { sonusSonetPathStatisticsEntry 1 }

sonusSonetPathStatisticsDefectAIS OBJECT-TYPE
    SYNTAX          INTEGER
    ACCESS          read-only
    STATUS          mandatory
    DESCRIPTION     
            "Count of Alarm Indication Signal defects that have occured."
    ::= { sonusSonetPathStatisticsEntry 2 }

sonusSonetPathStatisticsDefectLOP OBJECT-TYPE
    SYNTAX          INTEGER
    ACCESS          read-only
    STATUS          mandatory
    DESCRIPTION     
            "Count of Loss of Pointer defects that have occured."
    ::= { sonusSonetPathStatisticsEntry 3 }

sonusSonetPathStatisticsDefectRDI OBJECT-TYPE
    SYNTAX          INTEGER
    ACCESS          read-only
    STATUS          mandatory
    DESCRIPTION     
            "Count of Remote Defect Indication defects that have occured."
    ::= { sonusSonetPathStatisticsEntry 4 }

sonusSonetPathStatisticsAlarmAIS OBJECT-TYPE
    SYNTAX          INTEGER
    ACCESS          read-only
    STATUS          mandatory
    DESCRIPTION     
            "Count of Alarm Indication Signal alarms that have occured."
    ::= { sonusSonetPathStatisticsEntry 5 }

sonusSonetPathStatisticsAlarmLOP OBJECT-TYPE
    SYNTAX          INTEGER
    ACCESS          read-only
    STATUS          mandatory
    DESCRIPTION     
            "Count of Loss of Pointer alarms that have occured."
    ::= { sonusSonetPathStatisticsEntry 6 }

sonusSonetPathStatisticsAlarmRFI OBJECT-TYPE
    SYNTAX          INTEGER
    ACCESS          read-only
    STATUS          mandatory
    DESCRIPTION     
            "Count of Remote Failure Indication alarms that have occured."
    ::= { sonusSonetPathStatisticsEntry 7 }

sonusSonetPathStatisticsCodeViolation OBJECT-TYPE
    SYNTAX          INTEGER
    ACCESS          read-only
    STATUS          mandatory
    DESCRIPTION     
            "Count of code violations that have occured."
    ::= { sonusSonetPathStatisticsEntry 8 }

sonusSonetPathStatisticsREI OBJECT-TYPE
    SYNTAX          INTEGER
    ACCESS          read-only
    STATUS          mandatory
    DESCRIPTION     
            "Count of Remote Error Indications that have occured."
    ::= { sonusSonetPathStatisticsEntry 9 }

sonusSonetPathLayer OBJECT IDENTIFIER
    ::= { sonusSonetObjectsPath 3 }

sonusSonetPathLayerTable OBJECT-TYPE
    SYNTAX          SEQUENCE OF SonusSonetPathLayerEntry
    ACCESS          not-accessible
    STATUS          mandatory
    DESCRIPTION     
            "The SONET PATH layer table.  This table maps SONET PATH ifIndex
             to a shelf, slot, port, and path."
    ::= { sonusSonetPathLayer 1 }

sonusSonetPathLayerEntry OBJECT-TYPE
    SYNTAX          SonusSonetPathLayerEntry
    ACCESS          not-accessible
    STATUS          mandatory
    DESCRIPTION     
            "An entry in the SONET PATH layer table. This entry 
             maps the ifIndex of the SONET PATH to a shelf, slot,
             port, and path.  A row is added to this table when a SONET
             port is created."
    INDEX           { sonusSonetPathLayerShelfIndex, 
                      sonusSonetPathLayerSlotIndex, 
                      sonusSonetPathLayerPortIndex, 
                      sonusSonetPathLayerPathIndex }
    ::= { sonusSonetPathLayerTable 1 }

SonusSonetPathLayerEntry ::=
    SEQUENCE {
        sonusSonetPathLayerShelfIndex   SonusShelfIndex,
        sonusSonetPathLayerSlotIndex    SonusSlotIndex,
        sonusSonetPathLayerPortIndex    INTEGER,
        sonusSonetPathLayerPathIndex    INTEGER,
        sonusSonetPathLayerIfIndex      INTEGER,
        sonusSonetPathLayerRowStatus    RowStatus
    }

sonusSonetPathLayerShelfIndex OBJECT-TYPE
    SYNTAX          SonusShelfIndex
    ACCESS          not-accessible
    STATUS          mandatory
    DESCRIPTION     
            "Shelf index for this table."
    ::= { sonusSonetPathLayerEntry 1 }

sonusSonetPathLayerSlotIndex OBJECT-TYPE
    SYNTAX          SonusSlotIndex
    ACCESS          not-accessible
    STATUS          mandatory
    DESCRIPTION     
            "Slot index for this table."
    ::= { sonusSonetPathLayerEntry 2 }

sonusSonetPathLayerPortIndex OBJECT-TYPE
    SYNTAX          INTEGER
    ACCESS          not-accessible
    STATUS          mandatory
    DESCRIPTION     
            "Port index for this table."
    ::= { sonusSonetPathLayerEntry 3 }

sonusSonetPathLayerPathIndex OBJECT-TYPE
    SYNTAX          INTEGER
    ACCESS          not-accessible
    STATUS          mandatory
    DESCRIPTION     
            "Path index for this table."
    ::= { sonusSonetPathLayerEntry 4 }

sonusSonetPathLayerIfIndex OBJECT-TYPE
    SYNTAX          INTEGER
    ACCESS          read-only
    STATUS          mandatory
    DESCRIPTION     
            "The ifIndex assigned to this shelf, slot, port, path when the 
             SONET PATH was created."
    ::= { sonusSonetPathLayerEntry 5 }

sonusSonetPathLayerRowStatus OBJECT-TYPE
    SYNTAX          RowStatus
    ACCESS          read-write
    STATUS          mandatory
    DESCRIPTION     
            "This object is used to create, delete,
             or modify a row in this table."
    ::= { sonusSonetPathLayerEntry 6 }

sonusSonetNextIndex OBJECT-TYPE
    SYNTAX          INTEGER
    ACCESS          read-only
    STATUS          mandatory
    DESCRIPTION     
            "The next valid index to use when creating an entry in
             the sonusSonetTable."
    ::= { sonusSonetMIB 3 }

sonusSonetMIBNotifications OBJECT IDENTIFIER
    ::= { sonusSonetMIB 4 }

sonusSonetMIBNotificationsPrefix OBJECT IDENTIFIER
    ::= { sonusSonetMIBNotifications 0 }

sonusSonetMIBNotificationsObjects OBJECT IDENTIFIER
    ::= { sonusSonetMIBNotifications 1 }

sonusSonetAdminStatus OBJECT-TYPE
    SYNTAX          INTEGER { enabledInService(1), 
                        enabledOutOfService(2), disabled(3), deleted(4), 
                        dryingUp(5), equipped(6), unequipped(7) }
    ACCESS          read-only
    STATUS          mandatory
    DESCRIPTION     
            "The administrative status of a Sonet port. EnabledInService
             means the port configuration is applied and the port is
             available to carry calls. EnabledOutOfService means the port
             configuration is applied and the port is not available to carry
             calls. Disabled means the port configuration is not applied
             and the port is not available to carry calls. DryingUp means
             the port is still carrying in-progress calls but is not available
             for new calls. Equipped and Unequipped only apply to STS Path
             and VT Path layers. Value deleted is NO LONGER SUPPORTED."
    ::= { sonusSonetMIBNotificationsObjects 1 }

sonusSonetOperStatus OBJECT-TYPE
    SYNTAX          INTEGER { inService(1), outOfService(2), dryingUp(3), 
                        inServiceDown(4), outOfServiceDown(5), 
                        disabled(6) }
    ACCESS          read-only
    STATUS          obsolete
    DESCRIPTION     
            "Operational status of the Sonet port. Port is inService 
             if the admin state is enabled and the admin mode is in
             service. Port is outOfService if admin state is enabled,
             admin mode is out of service, and port is no longer
             carrying calls (dried up). Port is dryingUp if admin
             state is enabled, admin mode is out of service, and 
             port is drying up (no new calls, still carrying
             in-progress calls). Port is inServiceDown if admin state
             is enabled, admin mode is in service, but physical link
             is not available due to alarm condition. Port is
             outOfServiceDown if admin state is enabled, admin mode is
             out of service, but physical link is not available due to
             alarm condition. Port is disabled if admin state is
             disabled, admin mode is out of service, and port is no
             longer carrying calls (dried up)."
    ::= { sonusSonetMIBNotificationsObjects 2 }

sonusSonetAlarmStatus OBJECT-TYPE
    SYNTAX          INTEGER { los(1), losClear(2), lof(3), lofClear(4), 
                        lAIS(5), lAISClear(6), lRFI(7), lRFIClear(8), 
                        pAIS(9), pAISClear(10), pRFI(11), pRFIClear(12), 
                        pLOP(13), pLOPClear(14), pUNEQ(15), 
                        pUNEQClear(16), pPLM(17), pPLMClear(18), 
                        pTIM(19), pTIMClear(20), vLOP(21), vLOPClear(22), 
                        vAIS(23), vAISClear(24), vRDI(25), vRDIClear(26), 
                        vRFI(27), vRFIClear(28), vUNEQ(29), 
                        vUNEQClear(30), vPLM(31), vPLMClear(32), 
                        vTIM(33), vTIMClear(34), sTIM(35), sTIMClear(36) }
    ACCESS          read-only
    STATUS          mandatory
    DESCRIPTION     
            "Alarm conditions."
    ::= { sonusSonetMIBNotificationsObjects 3 }

sonusSonetThresholdType OBJECT-TYPE
    SYNTAX          INTEGER { sectionNearendCodingViolation15min(1), 
                        sectionNearendErroredSec15min(2), 
                        sectionNearendSeverelyErroredSec15min(3), 
                        sectionNearendSeverelyErroredFrameSec15min(4), 
                        lineNearendCodingViolation15min(5), 
                        lineNearendErroredSec15min(6), 
                        lineNearendSeverelyErroredSec15min(7), 
                        lineNearendUnavailableSec15min(8), 
                        pathNearendCodingViolation15min(9), 
                        pathNearendErroredSec15min(10), 
                        pathNearendSeverelyErroredSec15min(11), 
                        pathNearendUnavailableSec15min(12), 
                        sectionNearendCodingViolation24hr(13), 
                        sectionNearendErroredSec24hr(14), 
                        sectionNearendSeverelyErroredSec24hr(15), 
                        sectionNearendSeverelyErroredFrameSec24hr(16), 
                        lineNearendCodingViolation24hr(17), 
                        lineNearendErroredSec24hr(18), 
                        lineNearendSeverelyErroredSec24hr(19), 
                        lineNearendUnavailableSec24hr(20), 
                        pathNearendCodingViolation24hr(21), 
                        pathNearendErroredSec24hr(22), 
                        pathNearendSeverelyErroredSec24hr(23), 
                        pathNearendUnavailableSec24hr(24), 
                        lineFarendCodingViolation15min(25), 
                        lineFarendErroredSec15min(26), 
                        lineFarendSeverelyErroredSec15min(27), 
                        lineFarendUnavailableSec15min(28), 
                        pathFarendCodingViolation15min(29), 
                        pathFarendErroredSec15min(30), 
                        pathFarendSeverelyErroredSec15min(31), 
                        pathFarendUnavailableSec15min(32), 
                        sectionFarendCodingViolation24hr(33), 
                        sectionFarendErroredSec24hr(34), 
                        sectionFarendSeverelyErroredSec24hr(35), 
                        sectionFarendSeverelyErroredFrameSec24hr(36), 
                        lineFarendCodingViolation24hr(37), 
                        lineFarendErroredSec24hr(38), 
                        lineFarendSeverelyErroredSec24hr(39), 
                        lineFarendUnavailableSec24hr(40), 
                        pathFarendCodingViolation24hr(41), 
                        pathFarendErroredSec24hr(42), 
                        pathFarendSeverelyErroredSec24hr(43), 
                        pathFarendUnavailableSec24hr(44), 
                        vtPathNearendCodingViolation15min(45), 
                        vtPathNearendErroredSec15min(46), 
                        vtPathNearendSeverelyErroredSec15min(47), 
                        vtPathNearendUnavailableSec15min(48), 
                        vtPathNearendCodingViolation24hr(49), 
                        vtPathNearendErroredSec24hr(50), 
                        vtPathNearendSeverelyErroredSec24hr(51), 
                        vtPathNearendUnavailableSec24hr(52), 
                        vtPathFarendCodingViolation15min(53), 
                        vtPathFarendErroredSec15min(54), 
                        vtPathFarendSeverelyErroredSec15min(55), 
                        vtPathFarendUnavailableSec15min(56), 
                        vtPathFarendCodingViolation24hr(57), 
                        vtPathFarendErroredSec24hr(58), 
                        vtPathFarendSeverelyErroredSec24hr(59), 
                        vtPathFarendUnavailableSec24hr(60) }
    ACCESS          read-only
    STATUS          mandatory
    DESCRIPTION     
            "Threshold crossing types."
    ::= { sonusSonetMIBNotificationsObjects 4 }

sonusPathIndex OBJECT-TYPE
    SYNTAX          INTEGER (1..3)
    ACCESS          read-only
    STATUS          mandatory
    DESCRIPTION     
            "STS1 path index."
    ::= { sonusSonetMIBNotificationsObjects 5 }

sonusSonetOutOfServiceReason OBJECT-TYPE
    SYNTAX          INTEGER { admin(1), hwFailure(2) }
    ACCESS          read-only
    STATUS          mandatory
    DESCRIPTION     
            "Reason the Sonet port/path went out of service."
    ::= { sonusSonetMIBNotificationsObjects 6 }

sonusVTIndex OBJECT-TYPE
    SYNTAX          INTEGER (1..84)
    ACCESS          read-only
    STATUS          mandatory
    DESCRIPTION     
            "VT path index."
    ::= { sonusSonetMIBNotificationsObjects 7 }

sonusSonetObjectsVT OBJECT IDENTIFIER
    ::= { sonusSonetMIB 5 }

sonusSonetVTAdmn OBJECT IDENTIFIER
    ::= { sonusSonetObjectsVT 1 }

sonusSonetVTAdmnTable OBJECT-TYPE
    SYNTAX          SEQUENCE OF SonusSonetVTAdmnEntry
    ACCESS          not-accessible
    STATUS          mandatory
    DESCRIPTION     
            "The Sonus SONET VT Admn Table."
    ::= { sonusSonetVTAdmn 1 }

sonusSonetVTAdmnEntry OBJECT-TYPE
    SYNTAX          SonusSonetVTAdmnEntry
    ACCESS          not-accessible
    STATUS          mandatory
    DESCRIPTION     
            "An entry in the Sonus SONET VT Admn table."
    INDEX           { sonusSonetVTAdmnIfIndex }
    ::= { sonusSonetVTAdmnTable 1 }

SonusSonetVTAdmnEntry ::=
    SEQUENCE {
        sonusSonetVTAdmnIfIndex         INTEGER,
        sonusSonetVTAdmnShelfIndex      SonusShelfIndex,
        sonusSonetVTAdmnSlotIndex       SonusSlotIndex,
        sonusSonetVTAdmnPortIndex       INTEGER,
        sonusSonetVTAdmnVTIndex         INTEGER,
        sonusSonetVTAdmnRowStatus       RowStatus,
        sonusSonetVTAdmnStatAction      INTEGER,
        sonusSonetVTAdmnRDIMode         INTEGER,
        sonusSonetVTAdmnTraceState      SonusAdminState,
        sonusSonetVTAdmnTraceExpMsg     DisplayString,
        sonusSonetVTAdmnTraceXmtMsg     DisplayString,
        sonusSonetVTAdmnTraceRcvMsg     DisplayString,
        sonusSonetVTAdmnOperStatus      INTEGER,
        sonusSonetVTAdmnEquippedState   INTEGER,
        sonusSonetVTAdmnSTS1Idx         INTEGER,
        sonusSonetVTAdmnVTGroupIdx      INTEGER,
        sonusSonetVTAdmnVTIdx           INTEGER,
        sonusSonetVTAdmnInitStatistics  SonusAdminState,
        sonusSonetVTAdmnSendPattern     INTEGER,
        sonusSonetVTAdmnMonitorPattern  INTEGER,
        sonusSonetVTAdmnPatternBER      INTEGER,
        sonusSonetVTAdmnInitPatternErrCnt SonusAdminState,
        sonusSonetVTAdmnSpanIndex       INTEGER,
        sonusSonetVTAdmnByteSyncDs1Framing  SonusAdminState
    }

sonusSonetVTAdmnIfIndex OBJECT-TYPE
    SYNTAX          INTEGER
    ACCESS          not-accessible
    STATUS          mandatory
    DESCRIPTION     
            "The ifIndex assigned to this VT when it was created.
             This will not change until the VT is deleted."
    ::= { sonusSonetVTAdmnEntry 1 }

sonusSonetVTAdmnShelfIndex OBJECT-TYPE
    SYNTAX          SonusShelfIndex
    ACCESS          read-write
    STATUS          mandatory
    DESCRIPTION     
            "Shelf index for this table."
    ::= { sonusSonetVTAdmnEntry 2 }

sonusSonetVTAdmnSlotIndex OBJECT-TYPE
    SYNTAX          SonusSlotIndex
    ACCESS          read-write
    STATUS          mandatory
    DESCRIPTION     
            "Slot index for this table."
    ::= { sonusSonetVTAdmnEntry 3 }

sonusSonetVTAdmnPortIndex OBJECT-TYPE
    SYNTAX          INTEGER (1..4)
    ACCESS          read-write
    STATUS          mandatory
    DESCRIPTION     
            "OC3 port index for this table."
    ::= { sonusSonetVTAdmnEntry 4 }

sonusSonetVTAdmnVTIndex OBJECT-TYPE
    SYNTAX          INTEGER (1..84)
    ACCESS          read-only
    STATUS          mandatory
    DESCRIPTION     
            "VT index for this table."
    ::= { sonusSonetVTAdmnEntry 5 }

sonusSonetVTAdmnRowStatus OBJECT-TYPE
    SYNTAX          RowStatus
    ACCESS          read-write
    STATUS          mandatory
    DESCRIPTION     
            "This object is used to create, delete, or modify a row in this table."
    ::= { sonusSonetVTAdmnEntry 6 }

sonusSonetVTAdmnStatAction OBJECT-TYPE
    SYNTAX          INTEGER { init15MinuteNearEnd(1), 
                        init15MinuteFarEnd(2), init24HourNearEnd(4), 
                        init24HourFarEnd(8) }
    ACCESS          read-write
    STATUS          mandatory
    DESCRIPTION     
            "Initialize Performance Monitoring Statistics.  A PM initialization
             action initiates one request for the action.  Requests to initialize
             more than one group of statistics can be accomplished by OR-ing the 
             appropriate bits (e.g., to initialize all 15 minute PM statistics, 
             set bits 1 and 2). Reading this variable always returns zero."
    ::= { sonusSonetVTAdmnEntry 7 }

sonusSonetVTAdmnRDIMode OBJECT-TYPE
    SYNTAX          INTEGER { normal(1), enhanced(2) }
    ACCESS          read-write
    STATUS          mandatory
    DESCRIPTION     
            "The desired type of SONET port VT Remote Defect Indication to
             use.
             		 (1) normal - Use one-bit RDI-V signalling using bit 5 of G1.
             		 (2) enhanced - Use three-bit RDI-V (ERDI-V) using bits 5-7 of G1."
    DEFVAL          { enhanced }
    ::= { sonusSonetVTAdmnEntry 8 }

sonusSonetVTAdmnTraceState OBJECT-TYPE
    SYNTAX          SonusAdminState
    ACCESS          read-write
    STATUS          mandatory
    DESCRIPTION     
            "The desired state of SONET VT Path Trace.
             (1) enabled - Enables the generation of SONET VT Path Trace Messages
             in the J1 bytes of the VT Path overhead, and enables the reception and
             checking of received VT Path Trace Messages with the Expected VT Path 
             Trace Message.
             (2) disabled - Transmits all zero's in the J1 bytes of the VT Path
             overhead, and disables the reception and checking of received VT
             Path Trace Messages with the Expected VT Path Trace Message."
    DEFVAL          { disabled }
    ::= { sonusSonetVTAdmnEntry 9 }

sonusSonetVTAdmnTraceExpMsg OBJECT-TYPE
    SYNTAX          DisplayString (SIZE(0..15))
    ACCESS          read-write
    STATUS          mandatory
    DESCRIPTION     
            "The expected VT path trace string to be received on the SONET port in the
             J1 bytes of the VT Path overhead."
    ::= { sonusSonetVTAdmnEntry 10 }

sonusSonetVTAdmnTraceXmtMsg OBJECT-TYPE
    SYNTAX          DisplayString (SIZE(0..15))
    ACCESS          read-write
    STATUS          mandatory
    DESCRIPTION     
            "The VT path trace string to be transmitted on the SONET port in the J1
             bytes of the VT Path overhead."
    ::= { sonusSonetVTAdmnEntry 11 }

sonusSonetVTAdmnTraceRcvMsg OBJECT-TYPE
    SYNTAX          DisplayString (SIZE(0..15))
    ACCESS          read-only
    STATUS          mandatory
    DESCRIPTION     
            "The VT path trace string received on the SONET port in the J1
             bytes of the VT Path overhead."
    ::= { sonusSonetVTAdmnEntry 12 }

sonusSonetVTAdmnOperStatus OBJECT-TYPE
    SYNTAX          INTEGER { up(1), down(2), dryingUp(3), remoteDown(4) }
    ACCESS          read-only
    STATUS          mandatory
    DESCRIPTION     
            "The actual status of the Sonet VT. VT is Up if its corresponding
             port is administratively in service and there are no VT layer 
             failures or hardware failures. VT is Down if the port is 
             administratively in service and there are VT layer failures or 
             hardware failures, or if the port is administratively out of service. 
             VT is DryingUp if the port is administratively out of service and is 
             drying up (no new calls, still carrying	in-progress calls)."
    ::= { sonusSonetVTAdmnEntry 13 }

sonusSonetVTAdmnEquippedState OBJECT-TYPE
    SYNTAX          INTEGER { equipped(1), unequipped(2) }
    ACCESS          read-write
    STATUS          mandatory
    DESCRIPTION     
            "This object is used to set the VT to the Equipped or
             Unequipped state. If the VT is Unequipped, the Unequipped
             signal label is sent in the VT overhead, and AIS-V is
             forced."
    DEFVAL          { equipped }
    ::= { sonusSonetVTAdmnEntry 14 }

sonusSonetVTAdmnSTS1Idx OBJECT-TYPE
    SYNTAX          INTEGER (1..3)
    ACCESS          read-only
    STATUS          mandatory
    DESCRIPTION     
            "STS-1/VC4 index for the VT."
    ::= { sonusSonetVTAdmnEntry 15 }

sonusSonetVTAdmnVTGroupIdx OBJECT-TYPE
    SYNTAX          INTEGER (1..7)
    ACCESS          read-only
    STATUS          mandatory
    DESCRIPTION     
            "VT Group index for the VT."
    ::= { sonusSonetVTAdmnEntry 16 }

sonusSonetVTAdmnVTIdx OBJECT-TYPE
    SYNTAX          INTEGER (1..4)
    ACCESS          read-only
    STATUS          mandatory
    DESCRIPTION     
            "VT index for the VT."
    ::= { sonusSonetVTAdmnEntry 17 }

sonusSonetVTAdmnInitStatistics OBJECT-TYPE
    SYNTAX          SonusAdminState
    ACCESS          read-write
    STATUS          mandatory
    DESCRIPTION     
            "Initializes VT error statistics counts to zero."
    DEFVAL          { disabled }
    ::= { sonusSonetVTAdmnEntry 18 }

sonusSonetVTAdmnSendPattern OBJECT-TYPE
    SYNTAX          INTEGER { none(1), pn15(2), pn15Invert(3) }
    ACCESS          read-write
    STATUS          mandatory
    DESCRIPTION     
            "This object is used to send a PRBS test pattern
             in the VT. Currently 2^15 - 1 pattern is supported."
    DEFVAL          { none }
    ::= { sonusSonetVTAdmnEntry 19 }

sonusSonetVTAdmnMonitorPattern OBJECT-TYPE
    SYNTAX          INTEGER { none(1), pn15(2), pn15Invert(3) }
    ACCESS          read-write
    STATUS          mandatory
    DESCRIPTION     
            "This object is used to monitor a PRBS test pattern
             in the VT. Currently 2^15 - 1 pattern is supported."
    DEFVAL          { none }
    ::= { sonusSonetVTAdmnEntry 20 }

sonusSonetVTAdmnPatternBER OBJECT-TYPE
    SYNTAX          INTEGER { none(0), ber10E-2(1), ber10E-3(2), 
                        ber10E-4(3), ber10E-5(4), ber10E-6(5), 
                        ber10E-7(6), singleBit(7) }
    ACCESS          read-write
    STATUS          mandatory
    DESCRIPTION     
            "This object is used to inject errors into the
             PRBS test pattern. Value ber10E-2 (1) is not supported."
    DEFVAL          { none }
    ::= { sonusSonetVTAdmnEntry 21 }

sonusSonetVTAdmnInitPatternErrCnt OBJECT-TYPE
    SYNTAX          SonusAdminState
    ACCESS          read-write
    STATUS          mandatory
    DESCRIPTION     
            "Initializes VT test pattern error count to zero."
    DEFVAL          { disabled }
    ::= { sonusSonetVTAdmnEntry 22 }

sonusSonetVTAdmnSpanIndex OBJECT-TYPE
    SYNTAX          INTEGER (1..84)
    ACCESS          read-only
    STATUS          mandatory
    DESCRIPTION     
            "Index of T1/E1 span carried in this VT/TU."
    ::= { sonusSonetVTAdmnEntry 23 }

sonusSonetVTAdmnByteSyncDs1Framing OBJECT-TYPE
    SYNTAX          SonusAdminState
    ACCESS          read-write
    STATUS          mandatory
    DESCRIPTION     
            "For byte synchronous mapped VT payloads, specifies
             if F-bit (for T1 payloads), or TS0 FAS (for E1 payloads)
             is carried in the VT structure. If set to Enabled,
             F-bit or TS0 FAS is expected to be received, and T1/E1
             performance and alarm monitoring will be performed. If
             set to Disabled, no T1/E1 performance or alarm monitoring
             will be performed. This configuration has no effect
             for ST Frame payload mapping."
    DEFVAL          { enabled }
    ::= { sonusSonetVTAdmnEntry 24 }

sonusSonetVT OBJECT IDENTIFIER
    ::= { sonusSonetObjectsVT 2 }

sonusSonetVTThresholdTable OBJECT-TYPE
    SYNTAX          SEQUENCE OF SonusSonetVTThresholdEntry
    ACCESS          not-accessible
    STATUS          mandatory
    DESCRIPTION     
            "The Sonus SONET VT Threshold Table. This table adds objects to
             set the Performance Monitoring thresholds for generating a
             Threshold Crossing Alert."
    ::= { sonusSonetVT 1 }

sonusSonetVTThresholdEntry OBJECT-TYPE
    SYNTAX          SonusSonetVTThresholdEntry
    ACCESS          not-accessible
    STATUS          mandatory
    DESCRIPTION     
            "An entry in the Sonus SONET VT Threshold table."
    INDEX           { sonusSonetVTThresholdIfIndex }
    ::= { sonusSonetVTThresholdTable 1 }

SonusSonetVTThresholdEntry ::=
    SEQUENCE {
        sonusSonetVTThresholdIfIndex    INTEGER,
        sonusSonetVTThreshold15mCVs     INTEGER,
        sonusSonetVTThreshold15mESs     INTEGER,
        sonusSonetVTThreshold15mSESs    INTEGER,
        sonusSonetVTThreshold15mUASs    INTEGER,
        sonusSonetVTThreshold24hCVs     INTEGER,
        sonusSonetVTThreshold24hESs     INTEGER,
        sonusSonetVTThreshold24hSESs    INTEGER,
        sonusSonetVTThreshold24hUASs    INTEGER,
        sonusSonetVTThresholdCVTcaFilter SonusAdminState,
        sonusSonetVTThresholdESTcaFilter SonusAdminState,
        sonusSonetVTThresholdSESTcaFilter SonusAdminState,
        sonusSonetVTThresholdUASTcaFilter SonusAdminState
    }

sonusSonetVTThresholdIfIndex OBJECT-TYPE
    SYNTAX          INTEGER
    ACCESS          not-accessible
    STATUS          mandatory
    DESCRIPTION     
            "The ifIndex assigned to this VT when it was created.
             This will not change until the VT is deleted."
    ::= { sonusSonetVTThresholdEntry 1 }

sonusSonetVTThreshold15mCVs OBJECT-TYPE
    SYNTAX          INTEGER (0..16383)
    ACCESS          read-write
    STATUS          mandatory
    DESCRIPTION     
            "Threshold for 15 minute interval VT layer Coding Violations."
    ::= { sonusSonetVTThresholdEntry 2 }

sonusSonetVTThreshold15mESs OBJECT-TYPE
    SYNTAX          INTEGER (0..900)
    ACCESS          read-write
    STATUS          mandatory
    DESCRIPTION     
            "Threshold for 15 minute interval VT layer Errored Seconds."
    ::= { sonusSonetVTThresholdEntry 3 }

sonusSonetVTThreshold15mSESs OBJECT-TYPE
    SYNTAX          INTEGER (0..900)
    ACCESS          read-write
    STATUS          mandatory
    DESCRIPTION     
            "Threshold for 15 minute interval VT layer Severely Errored
             Seconds."
    ::= { sonusSonetVTThresholdEntry 4 }

sonusSonetVTThreshold15mUASs OBJECT-TYPE
    SYNTAX          INTEGER (0..900)
    ACCESS          read-write
    STATUS          mandatory
    DESCRIPTION     
            "Threshold for 15 minute interval VT layer Unavailable Seconds."
    ::= { sonusSonetVTThresholdEntry 5 }

sonusSonetVTThreshold24hCVs OBJECT-TYPE
    SYNTAX          INTEGER (0..1048575)
    ACCESS          read-write
    STATUS          mandatory
    DESCRIPTION     
            "Threshold for 24 hour interval VT layer Coding Violations."
    ::= { sonusSonetVTThresholdEntry 6 }

sonusSonetVTThreshold24hESs OBJECT-TYPE
    SYNTAX          INTEGER (0..65535)
    ACCESS          read-write
    STATUS          mandatory
    DESCRIPTION     
            "Threshold for 24 hour interval VT layer Errored Seconds."
    ::= { sonusSonetVTThresholdEntry 7 }

sonusSonetVTThreshold24hSESs OBJECT-TYPE
    SYNTAX          INTEGER (0..65535)
    ACCESS          read-write
    STATUS          mandatory
    DESCRIPTION     
            "Threshold for 24 hour interval VT layer Severely Errored
             Seconds."
    ::= { sonusSonetVTThresholdEntry 8 }

sonusSonetVTThreshold24hUASs OBJECT-TYPE
    SYNTAX          INTEGER (0..65535)
    ACCESS          read-write
    STATUS          mandatory
    DESCRIPTION     
            "Threshold for 24 hour interval VT layer Unavailable Seconds."
    ::= { sonusSonetVTThresholdEntry 9 }

sonusSonetVTThresholdCVTcaFilter OBJECT-TYPE
    SYNTAX          SonusAdminState
    ACCESS          read-write
    STATUS          mandatory
    DESCRIPTION     
            "Controls whether a threshold Crossing Alert (TCA) is reported (via
             an event log and trap). Setting this object to Enabled will prevent
             the TCA from being reported (i.e will Filter the TCA report)."
    DEFVAL          { disabled }
    ::= { sonusSonetVTThresholdEntry 10 }

sonusSonetVTThresholdESTcaFilter OBJECT-TYPE
    SYNTAX          SonusAdminState
    ACCESS          read-write
    STATUS          mandatory
    DESCRIPTION     
            "Controls whether a threshold Crossing Alert (TCA) is reported (via
             an event log and trap). Setting this object to Enabled will prevent
             the TCA from being reported (i.e will Filter the TCA report)."
    DEFVAL          { disabled }
    ::= { sonusSonetVTThresholdEntry 11 }

sonusSonetVTThresholdSESTcaFilter OBJECT-TYPE
    SYNTAX          SonusAdminState
    ACCESS          read-write
    STATUS          mandatory
    DESCRIPTION     
            "Controls whether a threshold Crossing Alert (TCA) is reported (via
             an event log and trap). Setting this object to Enabled will prevent
             the TCA from being reported (i.e will Filter the TCA report)."
    DEFVAL          { disabled }
    ::= { sonusSonetVTThresholdEntry 12 }

sonusSonetVTThresholdUASTcaFilter OBJECT-TYPE
    SYNTAX          SonusAdminState
    ACCESS          read-write
    STATUS          mandatory
    DESCRIPTION     
            "Controls whether a threshold Crossing Alert (TCA) is reported (via
             an event log and trap). Setting this object to Enabled will prevent
             the TCA from being reported (i.e will Filter the TCA report)."
    DEFVAL          { disabled }
    ::= { sonusSonetVTThresholdEntry 13 }

sonusSonetVTCurrentTable OBJECT-TYPE
    SYNTAX          SEQUENCE OF SonusSonetVTCurrentEntry
    ACCESS          not-accessible
    STATUS          mandatory
    DESCRIPTION     
            "The Sonus SONET VT Current table."
    ::= { sonusSonetVT 2 }

sonusSonetVTCurrentEntry OBJECT-TYPE
    SYNTAX          SonusSonetVTCurrentEntry
    ACCESS          not-accessible
    STATUS          mandatory
    DESCRIPTION     
            "An entry in the Sonus SONET VT Current table."
    INDEX           { sonusSonetVTCurrentIfIndex }
    ::= { sonusSonetVTCurrentTable 1 }

SonusSonetVTCurrentEntry ::=
    SEQUENCE {
        sonusSonetVTCurrentIfIndex      INTEGER,
        sonusSonetVTCurrentStatus       INTEGER,
        sonusSonetVTCurrentESs          PerfCurrentCount,
        sonusSonetVTCurrentSESs         PerfCurrentCount,
        sonusSonetVTCurrentUASs         PerfCurrentCount,
        sonusSonetVTCurrentCVs          PerfCurrentCount,
        sonusSonetVTCurrentFCs          PerfCurrentCount,
        sonusSonetVTCurrentElapsedTime  INTEGER,
        sonusSonetVTCurrentDayElapsedTime INTEGER,
        sonusSonetVTCurrentERDICode     INTEGER,
        sonusSonetVTCurrentSignalLabel  INTEGER,
        sonusSonetVTCurrentTraceStatus  INTEGER,
        sonusSonetVTCurrentPatternMonitor INTEGER,
        sonusSonetVTCurrentPatternBER   INTEGER,
        sonusSonetVTCurrentPatternErrorCnt  INTEGER
    }

sonusSonetVTCurrentIfIndex OBJECT-TYPE
    SYNTAX          INTEGER
    ACCESS          not-accessible
    STATUS          mandatory
    DESCRIPTION     
            "The ifIndex assigned to this VT when it was created.
             This will not change until the VT is deleted."
    ::= { sonusSonetVTCurrentEntry 1 }

sonusSonetVTCurrentStatus OBJECT-TYPE
    SYNTAX          INTEGER (1..256)
    ACCESS          read-only
    STATUS          mandatory
    DESCRIPTION     
            "This variable indicates the status of the interface. It is
             a bit map represented as a sum, therefore, it can represent
             multiple defects and failures simultaneously. The 
             sonetVTNoDefect should be set if and only if no other flag 
             is set.
             
             The various bit positions are:
             1   sonetVTNoDefect
             2   sonetVTLOP
             4   sonetVTPathAIS
             8   sonetVTPathRDI
             16  sonetVTPathRFI
             32  sonetVTUnequiped
             64  sonetVTSignalLabelMismatch
             128 sonetVTTraceMismatch
             256 sonetVTNotMonitored"
    ::= { sonusSonetVTCurrentEntry 2 }

sonusSonetVTCurrentESs OBJECT-TYPE
    SYNTAX          PerfCurrentCount
    ACCESS          read-only
    STATUS          mandatory
    DESCRIPTION     
            "The counter associated with the number of Errored Seconds
             encountered by a SONET/SDH VT in the current 24 hour
             interval."
    ::= { sonusSonetVTCurrentEntry 3 }

sonusSonetVTCurrentSESs OBJECT-TYPE
    SYNTAX          PerfCurrentCount
    ACCESS          read-only
    STATUS          mandatory
    DESCRIPTION     
            "The counter associated with the number of Severely Errored
             Seconds encountered by a SONET/SDH VT in the current 
             24 hour interval."
    ::= { sonusSonetVTCurrentEntry 4 }

sonusSonetVTCurrentUASs OBJECT-TYPE
    SYNTAX          PerfCurrentCount
    ACCESS          read-only
    STATUS          mandatory
    DESCRIPTION     
            "The counter associated with the number of Unavailable
             Seconds encountered by a SONET/SDH VT in the current
             24 hour interval."
    ::= { sonusSonetVTCurrentEntry 5 }

sonusSonetVTCurrentCVs OBJECT-TYPE
    SYNTAX          PerfCurrentCount
    ACCESS          read-only
    STATUS          mandatory
    DESCRIPTION     
            "The counter associated with the number of Coding Violations
             encountered by a SONET/SDH VT in the current 24 hour
             	 interval."
    ::= { sonusSonetVTCurrentEntry 6 }

sonusSonetVTCurrentFCs OBJECT-TYPE
    SYNTAX          PerfCurrentCount
    ACCESS          read-only
    STATUS          mandatory
    DESCRIPTION     
            "The counter associated with the number of Failures encountered
             by a SONET/SDH VT in the current 24 hour interval."
    ::= { sonusSonetVTCurrentEntry 7 }

sonusSonetVTCurrentElapsedTime OBJECT-TYPE
    SYNTAX          INTEGER
    ACCESS          read-only
    STATUS          mandatory
    DESCRIPTION     
            "Elapsed time in the current period"
    ::= { sonusSonetVTCurrentEntry 8 }

sonusSonetVTCurrentDayElapsedTime OBJECT-TYPE
    SYNTAX          INTEGER
    ACCESS          read-only
    STATUS          mandatory
    DESCRIPTION     
            "Elapsed time in the current period"
    ::= { sonusSonetVTCurrentEntry 9 }

sonusSonetVTCurrentERDICode OBJECT-TYPE
    SYNTAX          INTEGER { noRemoteDefect(1), remoteDefect(2), 
                        erdiPayloadDefect(3), erdiServerDefect(4), 
                        erdiConnectivityDefect(5), notAvailable(6) }
    ACCESS          read-only
    STATUS          mandatory
    DESCRIPTION     
            "Enhanced RDI code currently being received"
    ::= { sonusSonetVTCurrentEntry 10 }

sonusSonetVTCurrentSignalLabel OBJECT-TYPE
    SYNTAX          INTEGER { unequipped(1), equippedNonSpecific(2), 
                        asynchronous(3), byteSynchronous(4), 
                        bitSynchronous(5), reserved(6), notAvailable(7) }
    ACCESS          read-only
    STATUS          mandatory
    DESCRIPTION     
            "Payload signal label currently being received"
    ::= { sonusSonetVTCurrentEntry 11 }

sonusSonetVTCurrentTraceStatus OBJECT-TYPE
    SYNTAX          INTEGER { nodefect(1), tracemismatch(2), disabled(3) }
    ACCESS          read-only
    STATUS          mandatory
    DESCRIPTION     
            "The status of the Trace Mismatch Failure."
    ::= { sonusSonetVTCurrentEntry 12 }

sonusSonetVTCurrentPatternMonitor OBJECT-TYPE
    SYNTAX          INTEGER { disabled(1), mismatch(2), pn15(3), 
                        pn15Invert(4) }
    ACCESS          read-only
    STATUS          mandatory
    DESCRIPTION     
            "The status of the pattern monitor."
    ::= { sonusSonetVTCurrentEntry 13 }

sonusSonetVTCurrentPatternBER OBJECT-TYPE
    SYNTAX          INTEGER { none(0), ber10E-2(1), ber10E-3(2), 
                        ber10E-4(3), ber10E-5(4), ber10E-6(5), 
                        ber10E-7(6) }
    ACCESS          read-only
    STATUS          mandatory
    DESCRIPTION     
            "The bit error rate detected by the pattern monitor."
    ::= { sonusSonetVTCurrentEntry 14 }

sonusSonetVTCurrentPatternErrorCnt OBJECT-TYPE
    SYNTAX          INTEGER
    ACCESS          read-only
    STATUS          mandatory
    DESCRIPTION     
            "Count of bit errors detected by the pattern monitor."
    ::= { sonusSonetVTCurrentEntry 15 }

sonusSonetVTIntervalTable OBJECT-TYPE
    SYNTAX          SEQUENCE OF SonusSonetVTIntervalEntry
    ACCESS          not-accessible
    STATUS          mandatory
    DESCRIPTION     
            "The Sonus SONET VT Interval table."
    ::= { sonusSonetVT 3 }

sonusSonetVTIntervalEntry OBJECT-TYPE
    SYNTAX          SonusSonetVTIntervalEntry
    ACCESS          not-accessible
    STATUS          mandatory
    DESCRIPTION     
            "An entry in the Sonus SONET VT Interval table."
    INDEX           { sonusSonetVTIntervalIfIndex, 
                      sonusSonetVTIntervalNumber }
    ::= { sonusSonetVTIntervalTable 1 }

SonusSonetVTIntervalEntry ::=
    SEQUENCE {
        sonusSonetVTIntervalIfIndex     INTEGER,
        sonusSonetVTIntervalNumber      INTEGER,
        sonusSonetVTIntervalESs         PerfIntervalCount,
        sonusSonetVTIntervalSESs        PerfIntervalCount,
        sonusSonetVTIntervalUASs        PerfIntervalCount,
        sonusSonetVTIntervalCVs         PerfIntervalCount,
        sonusSonetVTIntervalFCs         PerfIntervalCount,
        sonusSonetVTIntervalValidData   TruthValue
    }

sonusSonetVTIntervalIfIndex OBJECT-TYPE
    SYNTAX          INTEGER
    ACCESS          not-accessible
    STATUS          mandatory
    DESCRIPTION     
            "The ifIndex assigned to this VT when it was created.
             This will not change until the VT is deleted."
    ::= { sonusSonetVTIntervalEntry 1 }

sonusSonetVTIntervalNumber OBJECT-TYPE
    SYNTAX          INTEGER (1)
    ACCESS          not-accessible
    STATUS          mandatory
    DESCRIPTION     
            "The number 1 identifies the most recently completed 24 hour
             interval. In the future if more 24 hour intervals are supported,
             the interval identified by N is the interval immediately
             preceding the one identified by N-1."
    ::= { sonusSonetVTIntervalEntry 2 }

sonusSonetVTIntervalESs OBJECT-TYPE
    SYNTAX          PerfIntervalCount
    ACCESS          read-only
    STATUS          mandatory
    DESCRIPTION     
            "The counter associated with the number of Errored Seconds
             encountered by a SONET/SDH VT in the previous 24 hour
             interval."
    ::= { sonusSonetVTIntervalEntry 3 }

sonusSonetVTIntervalSESs OBJECT-TYPE
    SYNTAX          PerfIntervalCount
    ACCESS          read-only
    STATUS          mandatory
    DESCRIPTION     
            "The counter associated with the number of Severely Errored
             Seconds encountered by a SONET/SDH VT in the previous 
             24 hour interval."
    ::= { sonusSonetVTIntervalEntry 4 }

sonusSonetVTIntervalUASs OBJECT-TYPE
    SYNTAX          PerfIntervalCount
    ACCESS          read-only
    STATUS          mandatory
    DESCRIPTION     
            "The counter associated with the number of Unavailable
             Seconds encountered by a SONET/SDH VT in the previous
             24 hour interval."
    ::= { sonusSonetVTIntervalEntry 5 }

sonusSonetVTIntervalCVs OBJECT-TYPE
    SYNTAX          PerfIntervalCount
    ACCESS          read-only
    STATUS          mandatory
    DESCRIPTION     
            "The counter associated with the number of Coding Violations
             encountered by a SONET/SDH VT in the previous 24 hour
             	 interval."
    ::= { sonusSonetVTIntervalEntry 6 }

sonusSonetVTIntervalFCs OBJECT-TYPE
    SYNTAX          PerfIntervalCount
    ACCESS          read-only
    STATUS          mandatory
    DESCRIPTION     
            "The counter associated with the number of Failures encountered
             by a SONET/SDH VT in the previous 24 hour interval."
    ::= { sonusSonetVTIntervalEntry 7 }

sonusSonetVTIntervalValidData OBJECT-TYPE
    SYNTAX          TruthValue
    ACCESS          read-only
    STATUS          mandatory
    DESCRIPTION     
            "This variable indicates if the data for this interval is valid."
    ::= { sonusSonetVTIntervalEntry 8 }

sonusSonetFarEndVTCurrentTable OBJECT-TYPE
    SYNTAX          SEQUENCE OF SonusSonetFarEndVTCurrentEntry
    ACCESS          not-accessible
    STATUS          mandatory
    DESCRIPTION     
            "The Sonus SONET Far End VT Current table."
    ::= { sonusSonetVT 4 }

sonusSonetFarEndVTCurrentEntry OBJECT-TYPE
    SYNTAX          SonusSonetFarEndVTCurrentEntry
    ACCESS          not-accessible
    STATUS          mandatory
    DESCRIPTION     
            "An entry in the Sonus SONET Far End VT Current table."
    INDEX           { sonusSonetFarEndVTCurrentIfIndex }
    ::= { sonusSonetFarEndVTCurrentTable 1 }

SonusSonetFarEndVTCurrentEntry ::=
    SEQUENCE {
        sonusSonetFarEndVTCurrentIfIndex INTEGER,
        sonusSonetFarEndVTCurrentESs    PerfCurrentCount,
        sonusSonetFarEndVTCurrentSESs   PerfCurrentCount,
        sonusSonetFarEndVTCurrentUASs   PerfCurrentCount,
        sonusSonetFarEndVTCurrentCVs    PerfCurrentCount,
        sonusSonetFarEndVTCurrentFCs    PerfCurrentCount
    }

sonusSonetFarEndVTCurrentIfIndex OBJECT-TYPE
    SYNTAX          INTEGER
    ACCESS          not-accessible
    STATUS          mandatory
    DESCRIPTION     
            "The ifIndex assigned to this VT when it was created.
             This will not change until the VT is deleted."
    ::= { sonusSonetFarEndVTCurrentEntry 1 }

sonusSonetFarEndVTCurrentESs OBJECT-TYPE
    SYNTAX          PerfCurrentCount
    ACCESS          read-only
    STATUS          mandatory
    DESCRIPTION     
            "The counter associated with the number of Far End Errored
             Seconds encountered by a SONET/SDH VT in the current
             24 hour interval."
    ::= { sonusSonetFarEndVTCurrentEntry 2 }

sonusSonetFarEndVTCurrentSESs OBJECT-TYPE
    SYNTAX          PerfCurrentCount
    ACCESS          read-only
    STATUS          mandatory
    DESCRIPTION     
            "The counter associated with the number of Far End Severely
             Errored Seconds encountered by a SONET/SDH VT in the
             current 24 hour interval."
    ::= { sonusSonetFarEndVTCurrentEntry 3 }

sonusSonetFarEndVTCurrentUASs OBJECT-TYPE
    SYNTAX          PerfCurrentCount
    ACCESS          read-only
    STATUS          mandatory
    DESCRIPTION     
            "The counter associated with the number of Far End 
             Unavailable Seconds encountered by a SONET/SDH VT in the
             current 24 hour interval."
    ::= { sonusSonetFarEndVTCurrentEntry 4 }

sonusSonetFarEndVTCurrentCVs OBJECT-TYPE
    SYNTAX          PerfCurrentCount
    ACCESS          read-only
    STATUS          mandatory
    DESCRIPTION     
            "The counter associated with the number of Far End Coding
             Violations encountered by a SONET/SDH VT in the current
             	 24 hour interval."
    ::= { sonusSonetFarEndVTCurrentEntry 5 }

sonusSonetFarEndVTCurrentFCs OBJECT-TYPE
    SYNTAX          PerfCurrentCount
    ACCESS          read-only
    STATUS          mandatory
    DESCRIPTION     
            "The counter associated with the number of Far End Failures
             encountered by a SONET/SDH VT in the current 24 hour
             interval."
    ::= { sonusSonetFarEndVTCurrentEntry 6 }

sonusSonetFarEndVTIntervalTable OBJECT-TYPE
    SYNTAX          SEQUENCE OF SonusSonetFarEndVTIntervalEntry
    ACCESS          not-accessible
    STATUS          mandatory
    DESCRIPTION     
            "The Sonus SONET Far End VT Interval table."
    ::= { sonusSonetVT 5 }

sonusSonetFarEndVTIntervalEntry OBJECT-TYPE
    SYNTAX          SonusSonetFarEndVTIntervalEntry
    ACCESS          not-accessible
    STATUS          mandatory
    DESCRIPTION     
            "An entry in the Sonus SONET Far End VT Interval table."
    INDEX           { sonusSonetFarEndVTIntervalIfIndex, 
                      sonusSonetFarEndVTIntervalNumber }
    ::= { sonusSonetFarEndVTIntervalTable 1 }

SonusSonetFarEndVTIntervalEntry ::=
    SEQUENCE {
        sonusSonetFarEndVTIntervalIfIndex INTEGER,
        sonusSonetFarEndVTIntervalNumber INTEGER,
        sonusSonetFarEndVTIntervalESs   PerfIntervalCount,
        sonusSonetFarEndVTIntervalSESs  PerfIntervalCount,
        sonusSonetFarEndVTIntervalUASs  PerfIntervalCount,
        sonusSonetFarEndVTIntervalCVs   PerfIntervalCount,
        sonusSonetFarEndVTIntervalFCs   PerfIntervalCount,
        sonusSonetFarEndVTIntervalValidData   TruthValue
    }

sonusSonetFarEndVTIntervalIfIndex OBJECT-TYPE
    SYNTAX          INTEGER
    ACCESS          not-accessible
    STATUS          mandatory
    DESCRIPTION     
            "The ifIndex assigned to this VT when it was created.
             This will not change until the VT is deleted."
    ::= { sonusSonetFarEndVTIntervalEntry 1 }

sonusSonetFarEndVTIntervalNumber OBJECT-TYPE
    SYNTAX          INTEGER (1)
    ACCESS          not-accessible
    STATUS          mandatory
    DESCRIPTION     
            "The number 1 identifies the most recently completed 24 hour
             interval. In the future if more 24 hour intervals are supported,
             the interval identified by N is the interval immediately
             preceding the one identified by N-1."
    ::= { sonusSonetFarEndVTIntervalEntry 2 }

sonusSonetFarEndVTIntervalESs OBJECT-TYPE
    SYNTAX          PerfIntervalCount
    ACCESS          read-only
    STATUS          mandatory
    DESCRIPTION     
            "The counter associated with the number of Far End Errored
             Seconds encountered by a SONET/SDH VT in the current
             24 hour interval."
    ::= { sonusSonetFarEndVTIntervalEntry 3 }

sonusSonetFarEndVTIntervalSESs OBJECT-TYPE
    SYNTAX          PerfIntervalCount
    ACCESS          read-only
    STATUS          mandatory
    DESCRIPTION     
            "The counter associated with the number of Far End Severely
             Errored Seconds encountered by a SONET/SDH VT in the
             current 24 hour interval."
    ::= { sonusSonetFarEndVTIntervalEntry 4 }

sonusSonetFarEndVTIntervalUASs OBJECT-TYPE
    SYNTAX          PerfIntervalCount
    ACCESS          read-only
    STATUS          mandatory
    DESCRIPTION     
            "The counter associated with the number of Far End 
             Unavailable Seconds encountered by a SONET/SDH VT in the
             current 24 hour interval."
    ::= { sonusSonetFarEndVTIntervalEntry 5 }

sonusSonetFarEndVTIntervalCVs OBJECT-TYPE
    SYNTAX          PerfIntervalCount
    ACCESS          read-only
    STATUS          mandatory
    DESCRIPTION     
            "The counter associated with the number of Far End Coding
             Violations encountered by a SONET/SDH VT in the current
             	 24 hour interval."
    ::= { sonusSonetFarEndVTIntervalEntry 6 }

sonusSonetFarEndVTIntervalFCs OBJECT-TYPE
    SYNTAX          PerfIntervalCount
    ACCESS          read-only
    STATUS          mandatory
    DESCRIPTION     
            "The counter associated with the number of Far End Failures
             encountered by a SONET/SDH VT in the current 24 hour
             interval."
    ::= { sonusSonetFarEndVTIntervalEntry 7 }

sonusSonetFarEndVTIntervalValidData OBJECT-TYPE
    SYNTAX          TruthValue
    ACCESS          read-only
    STATUS          mandatory
    DESCRIPTION     
            "This variable indicates if the data for this interval is valid."
    ::= { sonusSonetFarEndVTIntervalEntry 8 }

sonusSonetVTFailureCurrentTable OBJECT-TYPE
    SYNTAX          SEQUENCE OF SonusSonetVTFailureCurrentEntry
    ACCESS          not-accessible
    STATUS          mandatory
    DESCRIPTION     
            "The Sonus SONET VT Failure Current table."
    ::= { sonusSonetVT 6 }

sonusSonetVTFailureCurrentEntry OBJECT-TYPE
    SYNTAX          SonusSonetVTFailureCurrentEntry
    ACCESS          not-accessible
    STATUS          mandatory
    DESCRIPTION     
            "An entry in the Sonus SONET VT Failure Current table."
    INDEX           { sonusSonetVTFailureCurrentIfIndex }
    ::= { sonusSonetVTFailureCurrentTable 1 }

SonusSonetVTFailureCurrentEntry ::=
    SEQUENCE {
        sonusSonetVTFailureCurrentIfIndex INTEGER,
        sonusSonetVTFailureCurrentFCs   PerfCurrentCount
    }

sonusSonetVTFailureCurrentIfIndex OBJECT-TYPE
    SYNTAX          INTEGER
    ACCESS          not-accessible
    STATUS          mandatory
    DESCRIPTION     
            "The ifIndex assigned to this VT when it was created.
             This will not change until the VT is deleted."
    ::= { sonusSonetVTFailureCurrentEntry 1 }

sonusSonetVTFailureCurrentFCs OBJECT-TYPE
    SYNTAX          PerfCurrentCount
    ACCESS          read-only
    STATUS          mandatory
    DESCRIPTION     
            "The counter associated with the number of Failures encountered
             by a SONET/SDH VT in the current 15 minute interval."
    ::= { sonusSonetVTFailureCurrentEntry 2 }

sonusSonetVTFailureIntervalTable OBJECT-TYPE
    SYNTAX          SEQUENCE OF SonusSonetVTFailureIntervalEntry
    ACCESS          not-accessible
    STATUS          mandatory
    DESCRIPTION     
            "The Sonus SONET VT Failure Interval table."
    ::= { sonusSonetVT 7 }

sonusSonetVTFailureIntervalEntry OBJECT-TYPE
    SYNTAX          SonusSonetVTFailureIntervalEntry
    ACCESS          not-accessible
    STATUS          mandatory
    DESCRIPTION     
            "An entry in the Sonus SONET VT Failure Interval table."
    INDEX           { sonusSonetVTFailureIntervalIfIndex, 
                      sonusSonetVTFailureIntervalNumber }
    ::= { sonusSonetVTFailureIntervalTable 1 }

SonusSonetVTFailureIntervalEntry ::=
    SEQUENCE {
        sonusSonetVTFailureIntervalIfIndex  INTEGER,
        sonusSonetVTFailureIntervalNumber INTEGER,
        sonusSonetVTFailureIntervalFCs  PerfCurrentCount
    }

sonusSonetVTFailureIntervalIfIndex OBJECT-TYPE
    SYNTAX          INTEGER
    ACCESS          not-accessible
    STATUS          mandatory
    DESCRIPTION     
            "The ifIndex assigned to this VT when it was created.
             This will not change until the VT is deleted."
    ::= { sonusSonetVTFailureIntervalEntry 1 }

sonusSonetVTFailureIntervalNumber OBJECT-TYPE
    SYNTAX          INTEGER
    ACCESS          not-accessible
    STATUS          mandatory
    DESCRIPTION     
            "A number between 1 and 32, which identifies the interval
             for which the set of statistics is available. The number 1
             identifies the most recently completed interval, and the
             interval identified by N is the interval immediately
             preceding the one identified by N-1."
    ::= { sonusSonetVTFailureIntervalEntry 2 }

sonusSonetVTFailureIntervalFCs OBJECT-TYPE
    SYNTAX          PerfCurrentCount
    ACCESS          read-only
    STATUS          mandatory
    DESCRIPTION     
            "The counter associated with the number of Failures encountered
             by a SONET/SDH VT in the current 15 minute interval."
    ::= { sonusSonetVTFailureIntervalEntry 3 }

sonusSonetFarEndVTFailureCurrentTable OBJECT-TYPE
    SYNTAX          SEQUENCE OF SonusSonetFarEndVTFailureCurrentEntry
    ACCESS          not-accessible
    STATUS          mandatory
    DESCRIPTION     
            "The Sonus SONET Far End VT Failure Current table."
    ::= { sonusSonetVT 8 }

sonusSonetFarEndVTFailureCurrentEntry OBJECT-TYPE
    SYNTAX          SonusSonetFarEndVTFailureCurrentEntry
    ACCESS          not-accessible
    STATUS          mandatory
    DESCRIPTION     
            "An entry in the Sonus SONET Far End VT Failure Current table."
    INDEX           { sonusSonetFarEndVTFailureCurrentIfIndex }
    ::= { sonusSonetFarEndVTFailureCurrentTable 1 }

SonusSonetFarEndVTFailureCurrentEntry ::=
    SEQUENCE {
        sonusSonetFarEndVTFailureCurrentIfIndex       INTEGER,
        sonusSonetFarEndVTFailureCurrentFCs   PerfCurrentCount
    }

sonusSonetFarEndVTFailureCurrentIfIndex OBJECT-TYPE
    SYNTAX          INTEGER
    ACCESS          not-accessible
    STATUS          mandatory
    DESCRIPTION     
            "The ifIndex assigned to this VT when it was created.
             This will not change until the VT is deleted."
    ::= { sonusSonetFarEndVTFailureCurrentEntry 1 }

sonusSonetFarEndVTFailureCurrentFCs OBJECT-TYPE
    SYNTAX          PerfCurrentCount
    ACCESS          read-only
    STATUS          mandatory
    DESCRIPTION     
            "The counter associated with the number of Failures encountered
             by a SONET/SDH VT in the current 15 minute interval."
    ::= { sonusSonetFarEndVTFailureCurrentEntry 2 }

sonusSonetFarEndVTFailureIntervalTable OBJECT-TYPE
    SYNTAX          SEQUENCE OF SonusSonetFarEndVTFailureIntervalEntry
    ACCESS          not-accessible
    STATUS          mandatory
    DESCRIPTION     
            "The Sonus SONET Far End VT Failure Interval table."
    ::= { sonusSonetVT 9 }

sonusSonetFarEndVTFailureIntervalEntry OBJECT-TYPE
    SYNTAX          SonusSonetFarEndVTFailureIntervalEntry
    ACCESS          not-accessible
    STATUS          mandatory
    DESCRIPTION     
            "An entry in the Sonus SONET Far End VT Failure Interval table."
    INDEX           { sonusSonetFarEndVTFailureIntervalIfIndex, 
                      sonusSonetFarEndVTFailureIntervalNumber }
    ::= { sonusSonetFarEndVTFailureIntervalTable 1 }

SonusSonetFarEndVTFailureIntervalEntry ::=
    SEQUENCE {
        sonusSonetFarEndVTFailureIntervalIfIndex        INTEGER,
        sonusSonetFarEndVTFailureIntervalNumber       INTEGER,
        sonusSonetFarEndVTFailureIntervalFCs    PerfCurrentCount
    }

sonusSonetFarEndVTFailureIntervalIfIndex OBJECT-TYPE
    SYNTAX          INTEGER
    ACCESS          not-accessible
    STATUS          mandatory
    DESCRIPTION     
            "The ifIndex assigned to this VT when it was created.
             This will not change until the VT is deleted."
    ::= { sonusSonetFarEndVTFailureIntervalEntry 1 }

sonusSonetFarEndVTFailureIntervalNumber OBJECT-TYPE
    SYNTAX          INTEGER
    ACCESS          not-accessible
    STATUS          mandatory
    DESCRIPTION     
            "A number between 1 and 32, which identifies the interval
             for which the set of statistics is available. The number 1
             identifies the most recently completed interval, and the
             interval identified by N is the interval immediately
             preceding the one identified by N-1."
    ::= { sonusSonetFarEndVTFailureIntervalEntry 2 }

sonusSonetFarEndVTFailureIntervalFCs OBJECT-TYPE
    SYNTAX          PerfCurrentCount
    ACCESS          read-only
    STATUS          mandatory
    DESCRIPTION     
            "The counter associated with the number of Failures encountered
             by a SONET/SDH VT in the current 15 minute interval."
    ::= { sonusSonetFarEndVTFailureIntervalEntry 3 }

sonusSonetVTTcaTable OBJECT-TYPE
    SYNTAX          SEQUENCE OF SonusSonetVTTcaEntry
    ACCESS          not-accessible
    STATUS          mandatory
    DESCRIPTION     
            "The Sonus SONET VT Threshold Crossing Alert table."
    ::= { sonusSonetVT 10 }

sonusSonetVTTcaEntry OBJECT-TYPE
    SYNTAX          SonusSonetVTTcaEntry
    ACCESS          not-accessible
    STATUS          mandatory
    DESCRIPTION     
            "An entry in the Sonus SONET VT Threshold Crossing Alert table."
    INDEX           { sonusSonetVTTcaIfIndex }
    ::= { sonusSonetVTTcaTable 1 }

SonusSonetVTTcaEntry ::=
    SEQUENCE {
        sonusSonetVTTcaIfIndex          INTEGER,
        sonusSonetVTTca15mES            TruthValue,
        sonusSonetVTTca15mSES           TruthValue,
        sonusSonetVTTca15mUAS           TruthValue,
        sonusSonetVTTca15mCV            TruthValue,
        sonusSonetVTTca24hES            TruthValue,
        sonusSonetVTTca24hSES           TruthValue,
        sonusSonetVTTca24hUAS           TruthValue,
        sonusSonetVTTca24hCV            TruthValue,
        sonusSonetVTTcaFarEnd15mES      TruthValue,
        sonusSonetVTTcaFarEnd15mSES     TruthValue,
        sonusSonetVTTcaFarEnd15mUAS     TruthValue,
        sonusSonetVTTcaFarEnd15mCV      TruthValue,
        sonusSonetVTTcaFarEnd24hES      TruthValue,
        sonusSonetVTTcaFarEnd24hSES     TruthValue,
        sonusSonetVTTcaFarEnd24hUAS     TruthValue,
        sonusSonetVTTcaFarEnd24hCV      TruthValue
    }

sonusSonetVTTcaIfIndex OBJECT-TYPE
    SYNTAX          INTEGER
    ACCESS          not-accessible
    STATUS          mandatory
    DESCRIPTION     
            "The ifIndex assigned to this port when it was created.
             This will not change until the port is deleted."
    ::= { sonusSonetVTTcaEntry 1 }

sonusSonetVTTca15mES OBJECT-TYPE
    SYNTAX          TruthValue
    ACCESS          read-only
    STATUS          mandatory
    DESCRIPTION     
            "Indicates status of threshold crossing for VT Errored
             Seconds in the current 15 minute interval."
    ::= { sonusSonetVTTcaEntry 2 }

sonusSonetVTTca15mSES OBJECT-TYPE
    SYNTAX          TruthValue
    ACCESS          read-only
    STATUS          mandatory
    DESCRIPTION     
            "Indicates status of threshold crossing for VT Severely
             Errored Seconds in the current 15 minute interval."
    ::= { sonusSonetVTTcaEntry 3 }

sonusSonetVTTca15mUAS OBJECT-TYPE
    SYNTAX          TruthValue
    ACCESS          read-only
    STATUS          mandatory
    DESCRIPTION     
            "Indicates status of threshold crossing for VT Unavailable
             Seconds in the current 15 minute interval."
    ::= { sonusSonetVTTcaEntry 4 }

sonusSonetVTTca15mCV OBJECT-TYPE
    SYNTAX          TruthValue
    ACCESS          read-only
    STATUS          mandatory
    DESCRIPTION     
            "Indicates status of threshold crossing for VT Coding
             Violations in the current 15 minute interval."
    ::= { sonusSonetVTTcaEntry 5 }

sonusSonetVTTca24hES OBJECT-TYPE
    SYNTAX          TruthValue
    ACCESS          read-only
    STATUS          mandatory
    DESCRIPTION     
            "Indicates status of threshold crossing for VT Errored
             Seconds in the current 24 hour interval."
    ::= { sonusSonetVTTcaEntry 6 }

sonusSonetVTTca24hSES OBJECT-TYPE
    SYNTAX          TruthValue
    ACCESS          read-only
    STATUS          mandatory
    DESCRIPTION     
            "Indicates status of threshold crossing for VT Severely
             Errored Seconds in the current 24 hour interval."
    ::= { sonusSonetVTTcaEntry 7 }

sonusSonetVTTca24hUAS OBJECT-TYPE
    SYNTAX          TruthValue
    ACCESS          read-only
    STATUS          mandatory
    DESCRIPTION     
            "Indicates status of threshold crossing for VT Unavailable
             Seconds in the current 24 hour interval."
    ::= { sonusSonetVTTcaEntry 8 }

sonusSonetVTTca24hCV OBJECT-TYPE
    SYNTAX          TruthValue
    ACCESS          read-only
    STATUS          mandatory
    DESCRIPTION     
            "Indicates status of threshold crossing for VT Coding
             Violations in the current 24 hour interval."
    ::= { sonusSonetVTTcaEntry 9 }

sonusSonetVTTcaFarEnd15mES OBJECT-TYPE
    SYNTAX          TruthValue
    ACCESS          read-only
    STATUS          mandatory
    DESCRIPTION     
            "Indicates status of threshold crossing for Far End VT Errored
             Seconds in the current 15 minute interval."
    ::= { sonusSonetVTTcaEntry 10 }

sonusSonetVTTcaFarEnd15mSES OBJECT-TYPE
    SYNTAX          TruthValue
    ACCESS          read-only
    STATUS          mandatory
    DESCRIPTION     
            "Indicates status of threshold crossing for Far End VT Severely
             Errored Seconds in the current 15 minute interval."
    ::= { sonusSonetVTTcaEntry 11 }

sonusSonetVTTcaFarEnd15mUAS OBJECT-TYPE
    SYNTAX          TruthValue
    ACCESS          read-only
    STATUS          mandatory
    DESCRIPTION     
            "Indicates status of threshold crossing for Far End VT Unavailable
             Seconds in the current 15 minute interval."
    ::= { sonusSonetVTTcaEntry 12 }

sonusSonetVTTcaFarEnd15mCV OBJECT-TYPE
    SYNTAX          TruthValue
    ACCESS          read-only
    STATUS          mandatory
    DESCRIPTION     
            "Indicates status of threshold crossing for Far End VT Coding
             Violations in the current 15 minute interval."
    ::= { sonusSonetVTTcaEntry 13 }

sonusSonetVTTcaFarEnd24hES OBJECT-TYPE
    SYNTAX          TruthValue
    ACCESS          read-only
    STATUS          mandatory
    DESCRIPTION     
            "Indicates status of threshold crossing for Far End VT Errored
             Seconds in the current 24 hour interval."
    ::= { sonusSonetVTTcaEntry 14 }

sonusSonetVTTcaFarEnd24hSES OBJECT-TYPE
    SYNTAX          TruthValue
    ACCESS          read-only
    STATUS          mandatory
    DESCRIPTION     
            "Indicates status of threshold crossing for Far End VT Severely
             Errored Seconds in the current 24 hour interval."
    ::= { sonusSonetVTTcaEntry 15 }

sonusSonetVTTcaFarEnd24hUAS OBJECT-TYPE
    SYNTAX          TruthValue
    ACCESS          read-only
    STATUS          mandatory
    DESCRIPTION     
            "Indicates status of threshold crossing for Far End VT Unavailable
             Seconds in the current 24 hour interval."
    ::= { sonusSonetVTTcaEntry 16 }

sonusSonetVTTcaFarEnd24hCV OBJECT-TYPE
    SYNTAX          TruthValue
    ACCESS          read-only
    STATUS          mandatory
    DESCRIPTION     
            "Indicates status of threshold crossing for Far End VT Coding
             Violations in the current 24 hour interval."
    ::= { sonusSonetVTTcaEntry 17 }

sonusSonetVTStatisticsTable OBJECT-TYPE
    SYNTAX          SEQUENCE OF SonusSonetVTStatisticsEntry
    ACCESS          not-accessible
    STATUS          mandatory
    DESCRIPTION     
            "The Sonus SONET VT Statistics table."
    ::= { sonusSonetVT 11 }

sonusSonetVTStatisticsEntry OBJECT-TYPE
    SYNTAX          SonusSonetVTStatisticsEntry
    ACCESS          not-accessible
    STATUS          mandatory
    DESCRIPTION     
            "An entry in the Sonus SONET VT Statistics table."
    INDEX           { sonusSonetVTStatisticsIfIndex }
    ::= { sonusSonetVTStatisticsTable 1 }

SonusSonetVTStatisticsEntry ::=
    SEQUENCE {
        sonusSonetVTStatisticsIfIndex   INTEGER,
        sonusSonetVTStatisticsDefectAIS INTEGER,
        sonusSonetVTStatisticsDefectLOP INTEGER,
        sonusSonetVTStatisticsDefectRDI INTEGER,
        sonusSonetVTStatisticsAlarmAIS  INTEGER,
        sonusSonetVTStatisticsAlarmLOP  INTEGER,
        sonusSonetVTStatisticsAlarmRFI  INTEGER,
        sonusSonetVTStatisticsCodeViolation   INTEGER,
        sonusSonetVTStatisticsREI       INTEGER
    }

sonusSonetVTStatisticsIfIndex OBJECT-TYPE
    SYNTAX          INTEGER
    ACCESS          not-accessible
    STATUS          mandatory
    DESCRIPTION     
            "The ifIndex assigned to this port when it was created.
             This will not change until the port is deleted."
    ::= { sonusSonetVTStatisticsEntry 1 }

sonusSonetVTStatisticsDefectAIS OBJECT-TYPE
    SYNTAX          INTEGER
    ACCESS          read-only
    STATUS          mandatory
    DESCRIPTION     
            "Count of Alarm Indication Signal defects that have occured."
    ::= { sonusSonetVTStatisticsEntry 2 }

sonusSonetVTStatisticsDefectLOP OBJECT-TYPE
    SYNTAX          INTEGER
    ACCESS          read-only
    STATUS          mandatory
    DESCRIPTION     
            "Count of Loss of Pointer defects that have occured."
    ::= { sonusSonetVTStatisticsEntry 3 }

sonusSonetVTStatisticsDefectRDI OBJECT-TYPE
    SYNTAX          INTEGER
    ACCESS          read-only
    STATUS          mandatory
    DESCRIPTION     
            "Count of Remote Defect Indication defects that have occured."
    ::= { sonusSonetVTStatisticsEntry 4 }

sonusSonetVTStatisticsAlarmAIS OBJECT-TYPE
    SYNTAX          INTEGER
    ACCESS          read-only
    STATUS          mandatory
    DESCRIPTION     
            "Count of Alarm Indication Signal alarms that have occured."
    ::= { sonusSonetVTStatisticsEntry 5 }

sonusSonetVTStatisticsAlarmLOP OBJECT-TYPE
    SYNTAX          INTEGER
    ACCESS          read-only
    STATUS          mandatory
    DESCRIPTION     
            "Count of Loss of Pointer alarms that have occured."
    ::= { sonusSonetVTStatisticsEntry 6 }

sonusSonetVTStatisticsAlarmRFI OBJECT-TYPE
    SYNTAX          INTEGER
    ACCESS          read-only
    STATUS          mandatory
    DESCRIPTION     
            "Count of Remote Failure Indication alarms that have occured."
    ::= { sonusSonetVTStatisticsEntry 7 }

sonusSonetVTStatisticsCodeViolation OBJECT-TYPE
    SYNTAX          INTEGER
    ACCESS          read-only
    STATUS          mandatory
    DESCRIPTION     
            "Count of code violations that have occured."
    ::= { sonusSonetVTStatisticsEntry 8 }

sonusSonetVTStatisticsREI OBJECT-TYPE
    SYNTAX          INTEGER
    ACCESS          read-only
    STATUS          mandatory
    DESCRIPTION     
            "Count of Remote Error Indications that have occured."
    ::= { sonusSonetVTStatisticsEntry 9 }

sonusSonetVTLayer OBJECT IDENTIFIER
    ::= { sonusSonetObjectsVT 3 }

sonusSonetVTLayerTable OBJECT-TYPE
    SYNTAX          SEQUENCE OF SonusSonetVTLayerEntry
    ACCESS          not-accessible
    STATUS          mandatory
    DESCRIPTION     
            "The SONET VT layer table.  This table maps SONET VT ifIndex
             to a shelf, slot, port, and vt."
    ::= { sonusSonetVTLayer 1 }

sonusSonetVTLayerEntry OBJECT-TYPE
    SYNTAX          SonusSonetVTLayerEntry
    ACCESS          not-accessible
    STATUS          mandatory
    DESCRIPTION     
            "An entry in the SONET VT layer table. This entry 
             maps the ifIndex of the SONET VT to a shelf, slot,
             port, and vt.  A row is added to this table when a SONET
             VT is created."
    INDEX           { sonusSonetVTLayerShelfIndex, 
                      sonusSonetVTLayerSlotIndex, 
                      sonusSonetVTLayerPortIndex, 
                      sonusSonetVTLayerVTIndex }
    ::= { sonusSonetVTLayerTable 1 }

SonusSonetVTLayerEntry ::=
    SEQUENCE {
        sonusSonetVTLayerShelfIndex     SonusShelfIndex,
        sonusSonetVTLayerSlotIndex      SonusSlotIndex,
        sonusSonetVTLayerPortIndex      INTEGER,
        sonusSonetVTLayerVTIndex        INTEGER,
        sonusSonetVTLayerIfIndex        INTEGER,
        sonusSonetVTLayerRowStatus      RowStatus
    }

sonusSonetVTLayerShelfIndex OBJECT-TYPE
    SYNTAX          SonusShelfIndex
    ACCESS          not-accessible
    STATUS          mandatory
    DESCRIPTION     
            "Shelf index for this table."
    ::= { sonusSonetVTLayerEntry 1 }

sonusSonetVTLayerSlotIndex OBJECT-TYPE
    SYNTAX          SonusSlotIndex
    ACCESS          not-accessible
    STATUS          mandatory
    DESCRIPTION     
            "Slot index for this table."
    ::= { sonusSonetVTLayerEntry 2 }

sonusSonetVTLayerPortIndex OBJECT-TYPE
    SYNTAX          INTEGER
    ACCESS          not-accessible
    STATUS          mandatory
    DESCRIPTION     
            "Port index for this table."
    ::= { sonusSonetVTLayerEntry 3 }

sonusSonetVTLayerVTIndex OBJECT-TYPE
    SYNTAX          INTEGER
    ACCESS          not-accessible
    STATUS          mandatory
    DESCRIPTION     
            "VT index for this table."
    ::= { sonusSonetVTLayerEntry 4 }

sonusSonetVTLayerIfIndex OBJECT-TYPE
    SYNTAX          INTEGER
    ACCESS          read-only
    STATUS          mandatory
    DESCRIPTION     
            "The ifIndex assigned to this shelf, slot, port, vt when the 
             SONET VT was created."
    ::= { sonusSonetVTLayerEntry 5 }

sonusSonetVTLayerRowStatus OBJECT-TYPE
    SYNTAX          RowStatus
    ACCESS          read-write
    STATUS          mandatory
    DESCRIPTION     
            "This object is used to create, delete,
             or modify a row in this table."
    ::= { sonusSonetVTLayerEntry 6 }

sonusSonetPortAdminStatusNotification TRAP-TYPE
    ENTERPRISE      sonusSonetMIBNotifications
    VARIABLES       { ifIndex, sonusShelfIndex, sonusSlotIndex, 
                      sonusPortIndex, sonusSonetAdminStatus, 
                      sonusEventDescription, sonusEventClass, 
                      sonusEventLevel, sonusSequenceId, sonusEventTime }
--     STATUS          mandatory
    DESCRIPTION     
            "This trap indicates the Sonet port's administrative status
             has changed due to an operator-initiated command. Possible
             admin status is EnabledInService, EnabledOutOfService,
             Disabled, and DryingUp."
    ::= 1

sonusSonetPortOperStatusNotification TRAP-TYPE
    ENTERPRISE      sonusSonetMIBNotifications
    VARIABLES       { ifIndex, sonusShelfIndex, sonusSlotIndex, 
                      sonusPortIndex, sonusSonetOperStatus, 
                      sonusEventDescription, sonusEventClass, 
                      sonusEventLevel }
--     STATUS          obsolete
    DESCRIPTION     
            "NO LONGER SUPPORTED. This trap indicates the Sonet
             port's operational status
             has changed."
    ::= 2

sonusSonetLineAlarmNotification TRAP-TYPE
    ENTERPRISE      sonusSonetMIBNotifications
    VARIABLES       { ifIndex, sonusShelfIndex, sonusSlotIndex, 
                      sonusPortIndex, sonusSonetAlarmStatus, 
                      sonusEventDescription, sonusEventClass, 
                      sonusEventLevel, sonusSequenceId, sonusEventTime, 
                      sonusPimIndex }
--     STATUS          mandatory
    DESCRIPTION     
            "This trap indicates the line Section/Line-layer alarm
             state of the Sonet port has changed."
    ::= 3

sonusSonetLineThresholdCrossNotification TRAP-TYPE
    ENTERPRISE      sonusSonetMIBNotifications
    VARIABLES       { ifIndex, sonusShelfIndex, sonusSlotIndex, 
                      sonusPortIndex, sonusSonetThresholdType, 
                      sonusEventDescription, sonusEventClass, 
                      sonusEventLevel, sonusSequenceId, sonusEventTime, 
                      sonusPimIndex }
--     STATUS          mandatory
    DESCRIPTION     
            "This trap indicates that a Section/Line-layer performance
             monitoring threshold has been crossed."
    ::= 4

sonusSonetPathAdminStatusNotification TRAP-TYPE
    ENTERPRISE      sonusSonetMIBNotifications
    VARIABLES       { ifIndex, sonusShelfIndex, sonusSlotIndex, 
                      sonusPortIndex, sonusPathIndex, 
                      sonusSonetAdminStatus, sonusEventDescription, 
                      sonusEventClass, sonusEventLevel, sonusSequenceId, 
                      sonusEventTime }
--     STATUS          mandatory
    DESCRIPTION     
            "This trap indicates the Sonet path's administrative status
             has changed due to an operator-initiated command. Possible
             admin status is Equipped or Unequipped."
    ::= 5

sonusSonetPathOperStatusNotification TRAP-TYPE
    ENTERPRISE      sonusSonetMIBNotifications
    VARIABLES       { ifIndex, sonusShelfIndex, sonusSlotIndex, 
                      sonusPortIndex, sonusPathIndex, 
                      sonusSonetOperStatus, sonusEventDescription, 
                      sonusEventClass, sonusEventLevel }
--     STATUS          obsolete
    DESCRIPTION     
            "NO LONGER SUPPORTED. This trap indicates the Sonet
             path's operational status has changed."
    ::= 6

sonusSonetPathAlarmNotification TRAP-TYPE
    ENTERPRISE      sonusSonetMIBNotifications
    VARIABLES       { ifIndex, sonusShelfIndex, sonusSlotIndex, 
                      sonusPortIndex, sonusPathIndex, 
                      sonusSonetAlarmStatus, sonusEventDescription, 
                      sonusEventClass, sonusEventLevel, sonusSequenceId, 
                      sonusEventTime }
--     STATUS          mandatory
    DESCRIPTION     
            "This trap indicates the line Path-layer alarm state
             of the Sonet path has changed."
    ::= 7

sonusSonetPathThresholdCrossNotification TRAP-TYPE
    ENTERPRISE      sonusSonetMIBNotifications
    VARIABLES       { ifIndex, sonusShelfIndex, sonusSlotIndex, 
                      sonusPortIndex, sonusPathIndex, 
                      sonusSonetThresholdType, sonusEventDescription, 
                      sonusEventClass, sonusEventLevel, sonusSequenceId, 
                      sonusEventTime }
--     STATUS          mandatory
    DESCRIPTION     
            "This trap indicates that a Path-layer performance
             monitoring threshold has been crossed."
    ::= 8

sonusSonetPortOutOfServiceNotification TRAP-TYPE
    ENTERPRISE      sonusSonetMIBNotifications
    VARIABLES       { ifIndex, sonusShelfIndex, sonusSlotIndex, 
                      sonusPortIndex, sonusSonetOutOfServiceReason, 
                      sonusEventDescription, sonusEventClass, 
                      sonusEventLevel, sonusSequenceId, sonusEventTime }
--     STATUS          mandatory
    DESCRIPTION     
            "This trap indicates the Sonet port went out of service.
             Reason indicates why the port went out of service. Possible
             reasons include admin or hardware failure."
    ::= 9

sonusSonetPathOutOfServiceNotification TRAP-TYPE
    ENTERPRISE      sonusSonetMIBNotifications
    VARIABLES       { ifIndex, sonusShelfIndex, sonusSlotIndex, 
                      sonusPortIndex, sonusPathIndex, 
                      sonusSonetOutOfServiceReason, 
                      sonusEventDescription, sonusEventClass, 
                      sonusEventLevel, sonusSequenceId, sonusEventTime }
--     STATUS          mandatory
    DESCRIPTION     
            "This trap indicates the Sonet path went out of service.
             Reason indicates why the port went out of service. Possible
             reasons include admin or hardware failure."
    ::= 10

sonusSonetVTAlarmNotification TRAP-TYPE
    ENTERPRISE      sonusSonetMIBNotifications
    VARIABLES       { ifIndex, sonusShelfIndex, sonusSlotIndex, 
                      sonusPortIndex, sonusVTIndex, 
                      sonusSonetAlarmStatus, sonusEventDescription, 
                      sonusEventClass, sonusEventLevel, sonusSequenceId, 
                      sonusEventTime }
--     STATUS          mandatory
    DESCRIPTION     
            "This trap indicates the line VT-layer alarm state
             of the Sonet VT has changed."
    ::= 11

sonusSonetVTThresholdCrossNotification TRAP-TYPE
    ENTERPRISE      sonusSonetMIBNotifications
    VARIABLES       { ifIndex, sonusShelfIndex, sonusSlotIndex, 
                      sonusPortIndex, sonusVTIndex, 
                      sonusSonetThresholdType, sonusEventDescription, 
                      sonusEventClass, sonusEventLevel, sonusSequenceId, 
                      sonusEventTime }
--     STATUS          mandatory
    DESCRIPTION     
            "This trap indicates that a VT-layer performance
             monitoring threshold has been crossed."
    ::= 12

sonusSonetVTOutOfServiceNotification TRAP-TYPE
    ENTERPRISE      sonusSonetMIBNotifications
    VARIABLES       { ifIndex, sonusShelfIndex, sonusSlotIndex, 
                      sonusPortIndex, sonusVTIndex, 
                      sonusSonetOutOfServiceReason, 
                      sonusEventDescription, sonusEventClass, 
                      sonusEventLevel, sonusSequenceId, sonusEventTime }
--     STATUS          mandatory
    DESCRIPTION     
            "This trap indicates the Sonet VT went out of service.
             Reason indicates why the port went out of service. Possible
             reasons include admin or hardware failure."
    ::= 13

sonusSonetVTAdminStatusNotification TRAP-TYPE
    ENTERPRISE      sonusSonetMIBNotifications
    VARIABLES       { ifIndex, sonusShelfIndex, sonusSlotIndex, 
                      sonusPortIndex, sonusVTIndex, 
                      sonusSonetAdminStatus, sonusEventDescription, 
                      sonusEventClass, sonusEventLevel, sonusSequenceId, 
                      sonusEventTime }
--     STATUS          mandatory
    DESCRIPTION     
            "This trap indicates the Sonet VT's administrative status
             has changed due to an operator-initiated command. Possible
             admin status is Equipped or Unequipped."
    ::= 14

sonusSonetPathAlarmNotificationWithPim TRAP-TYPE
    ENTERPRISE      sonusSonetMIBNotifications
    VARIABLES       { ifIndex, sonusShelfIndex, sonusSlotIndex, 
                      sonusPortIndex, sonusPathIndex, 
                      sonusSonetAlarmStatus, sonusEventDescription, 
                      sonusEventClass, sonusEventLevel, sonusSequenceId, 
                      sonusEventTime, sonusPimIndex }
--     STATUS          mandatory
    DESCRIPTION     
            "This trap indicates the line Section/Line-layer alarm
             state of the Sonet port has changed."
    ::= 15

END -- end of module SONUS-SONET-MIB.
