--
-- This SMIv2 module has been generated by smidump 0.2-cvs. Do not edit.
--

SONUS-SOFTSWITCH-MIB DEFINITIONS ::= BEGIN

IMPORTS
    MODULE-IDENTITY, NOTIFICATION-TYPE, OBJECT-TYPE
        FROM SNMPv2-SMI
    sonusEventClass, sonusEventDescription, sonusEventLevel, 
    sonusEventTime
        FROM SONUS-COMMON-MIB
    sonusSystemMIBs
        FROM SONUS-SMI
    SonusSoftSwitchDbOperationFailureReason, SonusTMIdentifier
        FROM SONUS-SOFTSWITCH-TC
    SonusSystemName
        FROM SONUS-TC;

sonusSoftSwitchMIB MODULE-IDENTITY
    LAST-UPDATED    "200004230000Z"
    ORGANIZATION    
            "Sonus Networks, Inc."
    CONTACT-INFO    
            "   Customer Support    
             Sonus Networks, Inc.
             250 Apollo Drive
             Chelmsford, MA 01824
             USA
             
             Tel: 978-614-8100
             Fax: 978-614-8609"
    DESCRIPTION     
            "The MIB Module for SoftSwitch Management."
    ::= { sonusSystemMIBs 4 }


sonusSoftSwitchMIBObjects OBJECT IDENTIFIER
    ::= { sonusSoftSwitchMIB 1 }

sonusSoftSwitchMIBNotifications OBJECT IDENTIFIER
    ::= { sonusSoftSwitchMIB 2 }

sonusSoftSwitchMIBNotificationsPrefix OBJECT IDENTIFIER
    ::= { sonusSoftSwitchMIBNotifications 0 }

sonusSoftSwitchMIBNotificationsObjects OBJECT IDENTIFIER
    ::= { sonusSoftSwitchMIBNotifications 1 }

sonusSoftSwitchServerName OBJECT-TYPE
    SYNTAX          SonusSystemName
    MAX-ACCESS      read-only
    STATUS          current
    DESCRIPTION     
            "Name of the SoftSwitch server."
    ::= { sonusSoftSwitchMIBNotificationsObjects 1 }

sonusSoftSwitchClientName OBJECT-TYPE
    SYNTAX          SonusSystemName
    MAX-ACCESS      read-only
    STATUS          current
    DESCRIPTION     
            "Name of the SoftSwitch client, usually a gateway."
    ::= { sonusSoftSwitchMIBNotificationsObjects 2 }

sonusSoftSwitchDbOperationFailureReason OBJECT-TYPE
    SYNTAX          SonusSoftSwitchDbOperationFailureReason
    MAX-ACCESS      read-only
    STATUS          current
    DESCRIPTION     
            "DB operation failure reason."
    ::= { sonusSoftSwitchMIBNotificationsObjects 3 }

sonusSoftSwitchTMIdentifier1 OBJECT-TYPE
    SYNTAX          SonusTMIdentifier
    MAX-ACCESS      read-only
    STATUS          current
    DESCRIPTION     
            "Identifies the control. For Destination and Origination element type this is the national number. For Trunkgroup type, it is the trunkgroup identifier"
    ::= { sonusSoftSwitchMIBNotificationsObjects 4 }

sonusSoftSwitchTMIdentifier2 OBJECT-TYPE
    SYNTAX          SonusTMIdentifier
    MAX-ACCESS      read-only
    STATUS          current
    DESCRIPTION     
            "Identifies the control.  For Destination and Origination element type this is the country code. For Trunkgroup type it is the gateway identifier. "
    ::= { sonusSoftSwitchMIBNotificationsObjects 5 }

sonusSoftSwitchTMElementType OBJECT-TYPE
    SYNTAX          INTEGER { destination(1), trunkgroup(2), 
                        origination(3), routingLabel(4) }
    MAX-ACCESS      read-only
    STATUS          current
    DESCRIPTION     
            "Type of element on which this traffic management control operates."
    ::= { sonusSoftSwitchMIBNotificationsObjects 6 }

sonusSoftSwitchTMProvControlType OBJECT-TYPE
    SYNTAX          INTEGER { unknown(0), canf(1), cantdr(2), skipdr(3), 
                        skipar(4), dialeddestination(5), 
                        translateddestination(6), cantar(7), strdr(8), 
                        strar(9), irrdr(10), sirrdr(11), orrdr(12), 
                        sorrdr(13), rralternate(14), irrar(15), 
                        sirrar(16), orrar(17), sorrar(18), 
                        origination(19), finalCallingNumber(20), 
                        finalDestination(21), 
                        contractorBasedOrigination(22), 
                        cdDNBasedDestination(23) }
    MAX-ACCESS      read-only
    STATUS          current
    DESCRIPTION     
            "Type of control provisioned."
    ::= { sonusSoftSwitchMIBNotificationsObjects 7 }

sonusSoftSwitchTMAppliedControlType OBJECT-TYPE
    SYNTAX          INTEGER { dialeddestination(1), 
                        translateddestination(2), origination(3), 
                        finalCallingNumber(4), finalDestination(5), 
                        contractorBasedOrigination(6), 
                        cdDNBasedDestination(7) }
    MAX-ACCESS      read-only
    STATUS          current
    DESCRIPTION     
            "Type of control applied."
    ::= { sonusSoftSwitchMIBNotificationsObjects 8 }

sonusSoftSwitchTMAddressNature OBJECT-TYPE
    SYNTAX          INTEGER { unknown(0), national(1), international(2), 
                        nochange(3), subscriber(4), networkspecific(5), 
                        natureunknown(6), subscriberoperator(7), 
                        nationaloperator(8), internationaloperator(9), 
                        testcode(10), nonumberoprequested(11), 
                        nonumbercutthrough(12), nature950(13), 
                        anicallingpartysubscriber(14), 
                        aninotavailable(15), anicallingpartynational(16), 
                        anicalledpartysubscriber(17), 
                        anicalledpartynonumber(18), 
                        anicalledpartynational(19), ss7reserved(20), 
                        nationalnotrestricted(21), 
                        nationalrestricted(22), 
                        internationalnotrestricted(23), 
                        internationalrestricted(24), 
                        partialcallinglineid(126), all(255) }
    MAX-ACCESS      read-only
    STATUS          current
    DESCRIPTION     
            "Specifies whether the call was national,international or any other type like network specific."
    ::= { sonusSoftSwitchMIBNotificationsObjects 9 }

sonusSoftSwitchUpNotification NOTIFICATION-TYPE
    OBJECTS         { sonusEventDescription, sonusEventClass, 
                      sonusEventLevel, sonusEventTime }
    STATUS          current
    DESCRIPTION     
            "SoftSwitch is up."
    ::= { sonusSoftSwitchMIBNotificationsPrefix 1 }

sonusSoftSwitchDownNotification NOTIFICATION-TYPE
    OBJECTS         { sonusEventDescription, sonusEventClass, 
                      sonusEventLevel, sonusEventTime }
    STATUS          current
    DESCRIPTION     
            "SoftSwitch is down."
    ::= { sonusSoftSwitchMIBNotificationsPrefix 2 }

sonusSoftSwitchThreadCountConfigChangeNotification NOTIFICATION-TYPE
    OBJECTS         { sonusEventDescription, sonusEventClass, 
                      sonusEventLevel, sonusEventTime }
    STATUS          deprecated
    DESCRIPTION     
            "SoftSwitch's total thread count have been changed."
    ::= { sonusSoftSwitchMIBNotificationsPrefix 3 }

sonusSoftSwitchThreadCountConfigOutOfRangeErrorNotification NOTIFICATION-TYPE
    OBJECTS         { sonusEventDescription, sonusEventClass, 
                      sonusEventLevel, sonusEventTime }
    STATUS          deprecated
    DESCRIPTION     
            "SoftSwitch is down."
    ::= { sonusSoftSwitchMIBNotificationsPrefix 4 }

sonusSoftSwitchThreadCountConfigOutOfRangeErrorCleanupNotification NOTIFICATION-TYPE
    OBJECTS         { sonusEventDescription, sonusEventClass, 
                      sonusEventLevel, sonusEventTime }
    STATUS          deprecated
    DESCRIPTION     
            "SoftSwitch is up."
    ::= { sonusSoftSwitchMIBNotificationsPrefix 5 }

sonusSoftSwitchCPSLicensingThresholdMajor NOTIFICATION-TYPE
    OBJECTS         { sonusEventDescription, sonusEventClass, 
                      sonusEventLevel, sonusEventTime }
    STATUS          current
    DESCRIPTION     
            "The PSX process CPS licensing threshold has reached or exceeded major threshold."
    ::= { sonusSoftSwitchMIBNotificationsPrefix 6 }

sonusSoftSwitchCPSLicensingThresholdCritical NOTIFICATION-TYPE
    OBJECTS         { sonusEventDescription, sonusEventClass, 
                      sonusEventLevel, sonusEventTime }
    STATUS          current
    DESCRIPTION     
            "The PSX process CPS licensing threshold has reached or exceeded critical threshold."
    ::= { sonusSoftSwitchMIBNotificationsPrefix 7 }

sonusSoftSwitchCPSLicenseGracePeriod NOTIFICATION-TYPE
    OBJECTS         { sonusEventDescription, sonusEventClass, 
                      sonusEventLevel, sonusEventTime }
    STATUS          current
    DESCRIPTION     
            "PSX CPS Base License is  unavailable and a grace period of 90 days is provided."
    ::= { sonusSoftSwitchMIBNotificationsPrefix 8 }

sonusSoftSwitchCPSLicenseUnavailable NOTIFICATION-TYPE
    OBJECTS         { sonusEventDescription, sonusEventClass, 
                      sonusEventLevel, sonusEventTime }
    STATUS          current
    DESCRIPTION     
            "PSX CPS Base License is  unavailable and calls will be dropped."
    ::= { sonusSoftSwitchMIBNotificationsPrefix 9 }

sonusSoftSwitchSwitchToDomainLockedLicensingFailedNotification NOTIFICATION-TYPE
    OBJECTS         { sonusEventDescription, sonusEventClass, 
                      sonusEventLevel, sonusEventTime }
    STATUS          current
    DESCRIPTION     
            "PSX Switching to domain locked licensing is failed."
    ::= { sonusSoftSwitchMIBNotificationsPrefix 10 }

END -- end of module SONUS-SOFTSWITCH-MIB.
