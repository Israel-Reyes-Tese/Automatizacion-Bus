--
-- This SMIv1 module has been generated by smidump 0.2-cvs. Do not edit.
--

SONUS-SOFTSWITCH-PLM-MIB DEFINITIONS ::= BEGIN

IMPORTS
    TRAP-TYPE
        FROM RFC-1215
    Counter, Gauge
        FROM RFC1155-SMI
    sonusEventClass, sonusEventDescription, sonusEventLevel, 
    sonusEventTime
        FROM SONUS-COMMON-MIB
    sonusServicesMIBs
        FROM SONUS-SMI;

sonusSoftSwitchProductLicenseManagerMIB OBJECT IDENTIFIER
    ::= { sonusServicesMIBs 42 }

-- sonusSoftSwitchProductLicenseManagerMIB MODULE-IDENTITY
--     LAST-UPDATED    "200205030000Z"
--     ORGANIZATION    
--             "Sonus Networks, Inc."
--     CONTACT-INFO    
--             " Customer Support
--              Sonus Networks, Inc.
--              250 Apollo Drive
--              Chelmsford, MA 01824
--              USA
--              Tel: 978-614-8100
--              Fax: 978-614-8609"
--     DESCRIPTION     
--             "The MIB Module for SoftSwitch Product License Manager."
--     ::= { sonusServicesMIBs 42 }


sonusSoftSwitchProductLicenseManagerMIBObjects OBJECT IDENTIFIER
    ::= { sonusSoftSwitchProductLicenseManagerMIB 1 }

sonusSoftSwitchPlmMIBNotifications OBJECT IDENTIFIER
    ::= { sonusSoftSwitchProductLicenseManagerMIB 2 }

sonusSoftSwitchPlmMIBNotificationsPrefix OBJECT IDENTIFIER
    ::= { sonusSoftSwitchPlmMIBNotifications 0 }

sonusSoftSwitchPlmMIBNotificationsObjects OBJECT IDENTIFIER
    ::= { sonusSoftSwitchPlmMIBNotifications 1 }

sonusSoftSwitchPlmUpNotification TRAP-TYPE
    ENTERPRISE      sonusSoftSwitchPlmMIBNotifications
    VARIABLES       { sonusEventDescription, sonusEventClass, 
                      sonusEventLevel, sonusEventTime }
--     STATUS          mandatory
    DESCRIPTION     
            "SoftSwitch PLM is up."
    ::= 1

sonusSoftSwitchPlmDownNotification TRAP-TYPE
    ENTERPRISE      sonusSoftSwitchPlmMIBNotifications
    VARIABLES       { sonusEventDescription, sonusEventClass, 
                      sonusEventLevel, sonusEventTime }
--     STATUS          mandatory
    DESCRIPTION     
            "SoftSwitch PLM is down."
    ::= 2

sonusSoftSwitchPlmServerUnreachable TRAP-TYPE
    ENTERPRISE      sonusSoftSwitchPlmMIBNotifications
    VARIABLES       { sonusEventDescription, sonusEventClass, 
                      sonusEventLevel, sonusEventTime }
--     STATUS          mandatory
    DESCRIPTION     
            "The PSX PLM process cannot set up a connection with the site license server."
    ::= 3

sonusSoftSwitchPlmServerReachable TRAP-TYPE
    ENTERPRISE      sonusSoftSwitchPlmMIBNotifications
    VARIABLES       { sonusEventDescription, sonusEventClass, 
                      sonusEventLevel, sonusEventTime }
--     STATUS          mandatory
    DESCRIPTION     
            "The PSX PLM process can set up a connection with the site license server."
    ::= 4

sonusSoftSwitchPlmLicenseUnavailable TRAP-TYPE
    ENTERPRISE      sonusSoftSwitchPlmMIBNotifications
    VARIABLES       { sonusEventDescription, sonusEventClass, 
                      sonusEventLevel, sonusEventTime }
--     STATUS          mandatory
    DESCRIPTION     
            "The PSX PLM process cannot fetch a License for a feature from the site license server."
    ::= 5

sonusSoftSwitchPlmLicenseAvailable TRAP-TYPE
    ENTERPRISE      sonusSoftSwitchPlmMIBNotifications
    VARIABLES       { sonusEventDescription, sonusEventClass, 
                      sonusEventLevel, sonusEventTime }
--     STATUS          mandatory
    DESCRIPTION     
            "The PSX PLM process can fetch a License for a feature from the site license server."
    ::= 6

sonusSoftSwitchPlmLicenseGraceMode TRAP-TYPE
    ENTERPRISE      sonusSoftSwitchPlmMIBNotifications
    VARIABLES       { sonusEventDescription, sonusEventClass, 
                      sonusEventLevel, sonusEventTime }
--     STATUS          mandatory
    DESCRIPTION     
            "The PSX Network based Licenses have transitioned to grace mode."
    ::= 7

sonusSoftSwitchPlmLicenseGraceModeCleared TRAP-TYPE
    ENTERPRISE      sonusSoftSwitchPlmMIBNotifications
    VARIABLES       { sonusEventDescription, sonusEventClass, 
                      sonusEventLevel, sonusEventTime }
--     STATUS          mandatory
    DESCRIPTION     
            "The PSX Network based Licenses are out of grace mode and getting into the network mode."
    ::= 8

sonusSoftSwitchPlmLicenseGraceExpiring TRAP-TYPE
    ENTERPRISE      sonusSoftSwitchPlmMIBNotifications
    VARIABLES       { sonusEventDescription, sonusEventClass, 
                      sonusEventLevel, sonusEventTime }
--     STATUS          mandatory
    DESCRIPTION     
            "The PSX Grace Licenses will expire in x days."
    ::= 9

sonusSoftSwitchPlmLicenseGraceExpired TRAP-TYPE
    ENTERPRISE      sonusSoftSwitchPlmMIBNotifications
    VARIABLES       { sonusEventDescription, sonusEventClass, 
                      sonusEventLevel, sonusEventTime }
--     STATUS          mandatory
    DESCRIPTION     
            "The PSX Grace Licenses have expired."
    ::= 10

sonusSoftSwitchPlmLicenseReleased TRAP-TYPE
    ENTERPRISE      sonusSoftSwitchPlmMIBNotifications
    VARIABLES       { sonusEventDescription, sonusEventClass, 
                      sonusEventLevel, sonusEventTime }
--     STATUS          mandatory
    DESCRIPTION     
            "The PSX has released the Network Based License."
    ::= 11

sonusSoftSwitchPlmMinimumLicenseCountThresholdNotReached TRAP-TYPE
    ENTERPRISE      sonusSoftSwitchPlmMIBNotifications
    VARIABLES       { sonusEventDescription, sonusEventClass, 
                      sonusEventLevel, sonusEventTime }
--     STATUS          mandatory
    DESCRIPTION     
            "The PSX feature license count has not reached the minimum license count threshold."
    ::= 12

sonusSoftSwitchPlmClearMinimumLicenseCountThresholdNotReached TRAP-TYPE
    ENTERPRISE      sonusSoftSwitchPlmMIBNotifications
    VARIABLES       { sonusEventDescription, sonusEventClass, 
                      sonusEventLevel, sonusEventTime }
--     STATUS          mandatory
    DESCRIPTION     
            "The PSX feature license count has reached the minimum license count threshold."
    ::= 13

sonusSoftSwitchPlmMaximumLicenseCountThresholdExceeded TRAP-TYPE
    ENTERPRISE      sonusSoftSwitchPlmMIBNotifications
    VARIABLES       { sonusEventDescription, sonusEventClass, 
                      sonusEventLevel, sonusEventTime }
--     STATUS          mandatory
    DESCRIPTION     
            "The PSX feature license count has exceeded the maximum license count threshold."
    ::= 14

sonusSoftSwitchPlmClearMaximumLicenseCountThresholdExceeded TRAP-TYPE
    ENTERPRISE      sonusSoftSwitchPlmMIBNotifications
    VARIABLES       { sonusEventDescription, sonusEventClass, 
                      sonusEventLevel, sonusEventTime }
--     STATUS          mandatory
    DESCRIPTION     
            "The PSX feature license count is below the maximum license count threshold."
    ::= 15

END -- end of module SONUS-SOFTSWITCH-PLM-MIB.
