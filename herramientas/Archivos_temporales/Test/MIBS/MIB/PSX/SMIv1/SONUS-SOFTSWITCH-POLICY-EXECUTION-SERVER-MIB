--
-- This SMIv1 module has been generated by smidump 0.2-cvs. Do not edit.
--

SONUS-SOFTSWITCH-POLICY-EXECUTION-SERVER-MIB DEFINITIONS ::= BEGIN

IMPORTS
    OBJECT-TYPE
        FROM RFC-1212
    TRAP-TYPE
        FROM RFC-1215
    Counter, Gauge, IpAddress, TimeTicks
        FROM RFC1155-SMI
    DisplayString
        FROM SNMPv2-TC
    sonusEventClass, sonusEventDescription, sonusEventLevel, 
    sonusEventTime
        FROM SONUS-COMMON-MIB
    sonusServicesMIBs
        FROM SONUS-SMI
    sonusSoftSwitchClientName, sonusSoftSwitchDbOperationFailureReason, 
    sonusSoftSwitchTMAddressNature, sonusSoftSwitchTMAppliedControlType, 
    sonusSoftSwitchTMElementType, sonusSoftSwitchTMIdentifier1, 
    sonusSoftSwitchTMIdentifier2
        FROM SONUS-SOFTSWITCH-MIB
    SonusName
        FROM SONUS-TC;

sonusSoftSwitchPolicyExecutionServerMIB OBJECT IDENTIFIER
    ::= { sonusServicesMIBs 10 }

-- sonusSoftSwitchPolicyExecutionServerMIB MODULE-IDENTITY
--     LAST-UPDATED    "200205030000Z"
--     ORGANIZATION    
--             "Sonus Networks, Inc."
--     CONTACT-INFO    
--             "   Customer Support    
--              Sonus Networks, Inc.
--              250 Apollo Drive
--              Chelmsford, MA 01824
--              USA
--              
--              Tel: 978-614-8100
--              Fax: 978-614-8609"
--     DESCRIPTION     
--             "The MIB Module for SoftSwitch Policy Execution Server Management."
--     ::= { sonusServicesMIBs 10 }


sonusSoftSwitchPolicyExecutionServerMIBObjects OBJECT IDENTIFIER
    ::= { sonusSoftSwitchPolicyExecutionServerMIB 1 }

sonusSoftSwitchPolicyExecutionServerStatistics OBJECT IDENTIFIER
    ::= { sonusSoftSwitchPolicyExecutionServerMIBObjects 1 }

sonusSoftSwitchPesPolicyReqCounters OBJECT IDENTIFIER
    ::= { sonusSoftSwitchPolicyExecutionServerStatistics 1 }

sonusSoftSwitchPesPrcTotalReqsNoExtSvc OBJECT-TYPE
    SYNTAX          Counter
    ACCESS          read-only
    STATUS          mandatory
    DESCRIPTION     
            "Total Requests (no ext service): Total number of
             policy requests (excluding those that needed external
             services, such as an SCP lookup) which were handled
             by the Soft Switch. Requests which timed out at the
             external interface are counted here."
    ::= { sonusSoftSwitchPesPolicyReqCounters 1 }

sonusSoftSwitchPesPrcTotalTimeNoExtSvc OBJECT-TYPE
    SYNTAX          Counter
    ACCESS          read-only
    STATUS          mandatory
    DESCRIPTION     
            "Total time (no ext service): Total time (number of
             milliseconds) taken to process these requests. Requests
             which timed out at the external interface are also counted here."
    ::= { sonusSoftSwitchPesPolicyReqCounters 2 }

sonusSoftSwitchPesPrcAverageTimeNoExtSvc OBJECT-TYPE
    SYNTAX          Gauge
    ACCESS          read-only
    STATUS          mandatory
    DESCRIPTION     
            "Average Time: Average amount of time (in milliseconds) taken
             to process each individual request. This is the average of the
             differences between the time a request was received and the time
             that the corresponding response was sent out."
    ::= { sonusSoftSwitchPesPolicyReqCounters 3 }

sonusSoftSwitchPesPrcTotalRequestsExtSvc OBJECT-TYPE
    SYNTAX          Counter
    ACCESS          read-only
    STATUS          mandatory
    DESCRIPTION     
            "Total requests (External Svc): The number of requests which used
             an external service. Currently the features which use external
             services are the LNP and Toll Free lookup."
    ::= { sonusSoftSwitchPesPolicyReqCounters 4 }

sonusSoftSwitchPesPrcTotalTimeExtSvc OBJECT-TYPE
    SYNTAX          Counter
    ACCESS          read-only
    STATUS          mandatory
    DESCRIPTION     
            "Total time: Total time (in milliseconds) it took to process
             the requests that required an external service. This time includes
             the time it took for the external service to execute. This time does
             not include requests that timed out."
    ::= { sonusSoftSwitchPesPolicyReqCounters 5 }

sonusSoftSwitchPesPrcAverageTimeExtSvc OBJECT-TYPE
    SYNTAX          Gauge
    ACCESS          read-only
    STATUS          mandatory
    DESCRIPTION     
            " Average: Average time (in milliseconds) it took to process
             each of these requests."
    ::= { sonusSoftSwitchPesPolicyReqCounters 6 }

sonusSoftSwitchPesPrcExtTime OBJECT-TYPE
    SYNTAX          Counter
    ACCESS          read-only
    STATUS          mandatory
    DESCRIPTION     
            " Ex time: Total time (in milliseconds) it took in the
             external service to process all of these requests."
    ::= { sonusSoftSwitchPesPolicyReqCounters 7 }

sonusSoftSwitchPesPrcAvgExtTime OBJECT-TYPE
    SYNTAX          Gauge
    ACCESS          read-only
    STATUS          mandatory
    DESCRIPTION     
            " Ave Ex Time: Average time (in milliseconds) that it
             took in the external service to process each request."
    ::= { sonusSoftSwitchPesPolicyReqCounters 8 }

sonusSoftSwitchPesPrcTotalTimeouts OBJECT-TYPE
    SYNTAX          Counter
    ACCESS          read-only
    STATUS          mandatory
    DESCRIPTION     
            "Total T/O:     Total number of external service requests which timed out.      "
    ::= { sonusSoftSwitchPesPolicyReqCounters 9 }

sonusSoftSwitchPesPrcTotalTimeTORequests OBJECT-TYPE
    SYNTAX          Counter
    ACCESS          read-only
    STATUS          mandatory
    DESCRIPTION     
            "Total time: Total time (in milliseconds) taken to process
             the timed out requests in the Softswitch. This total includes
             the timeout interval and the processing time."
    ::= { sonusSoftSwitchPesPolicyReqCounters 10 }

sonusSoftSwitchPesPrcAverageTimeTORequests OBJECT-TYPE
    SYNTAX          Counter
    ACCESS          read-only
    STATUS          mandatory
    DESCRIPTION     
            "Average (Time in milliseconds): Average time taken to
             process each timed out request. This time includes the
             timeout interval and the processing time."
    ::= { sonusSoftSwitchPesPolicyReqCounters 11 }

sonusSoftSwitchPesPrcTotalNonSsRequests OBJECT-TYPE
    SYNTAX          Counter
    ACCESS          read-only
    STATUS          mandatory
    DESCRIPTION     
            "Total non ss requests: Counts the total number of
             non-policy requests. These include heart beat
             (keep Alive) messages."
    ::= { sonusSoftSwitchPesPolicyReqCounters 12 }

sonusSoftSwitchPesPrcTotalTimeNonSsRequests OBJECT-TYPE
    SYNTAX          Counter
    ACCESS          read-only
    STATUS          mandatory
    DESCRIPTION     
            "Total time: Total time (in milliseconds) it
             took to process these non-policy requests."
    ::= { sonusSoftSwitchPesPolicyReqCounters 13 }

sonusSoftSwitchPesPrcAvgTimeNonSsRequests OBJECT-TYPE
    SYNTAX          Gauge
    ACCESS          read-only
    STATUS          mandatory
    DESCRIPTION     
            "Average (Time in milliseconds): The average time
             in milliseconds it took to process each of these non-policy requests."
    ::= { sonusSoftSwitchPesPolicyReqCounters 14 }

sonusSoftSwitchPesPolicyReqIntervalTime OBJECT-TYPE
    SYNTAX          TimeTicks
    ACCESS          read-only
    STATUS          mandatory
    DESCRIPTION     
            "This variable contains the end of interval time stamp for 
             the specified interval."
    ::= { sonusSoftSwitchPesPolicyReqCounters 15 }

sonusSoftSwitchPesServiceUsageCounters OBJECT IDENTIFIER
    ::= { sonusSoftSwitchPolicyExecutionServerStatistics 2 }

sonusSoftSwitchPesSucDefaultSvcs OBJECT-TYPE
    SYNTAX          Counter
    ACCESS          read-only
    STATUS          mandatory
    DESCRIPTION     
            "Default Service: This counter keeps track of how many times
             default service is executed. The counter is incremented when no
             service is provisioned and the default service is executed."
    ::= { sonusSoftSwitchPesServiceUsageCounters 1 }

sonusSoftSwitchPesSucSubsScreening OBJECT-TYPE
    SYNTAX          Counter
    ACCESS          read-only
    STATUS          mandatory
    DESCRIPTION     
            "Subscriber Screening: This counter keeps track of how many
             times Subscriber Screening Service is executed. The counter is
             incremented when screening service provisioned for subscriber is executed."
    ::= { sonusSoftSwitchPesServiceUsageCounters 2 }

sonusSoftSwitchPesSucSubsBlocking OBJECT-TYPE
    SYNTAX          Counter
    ACCESS          read-only
    STATUS          mandatory
    DESCRIPTION     
            "Subscriber Blocking: This counter keeps track of how many
             times Subscriber Blocking Service is executed. The counter
             is incremented when blocking service provisioned for subscriber
             is executed."
    ::= { sonusSoftSwitchPesServiceUsageCounters 3 }

sonusSoftSwitchPesSucNonSubsScreening OBJECT-TYPE
    SYNTAX          Counter
    ACCESS          read-only
    STATUS          mandatory
    DESCRIPTION     
            "Non Subscriber Screening: This counter keeps track of
             how many times Non Subscriber Screening Service is executed.
             This counter is incremented when the calling party is not
             present in the Subscriber database table and the non-subscriber
             call is screened."
    ::= { sonusSoftSwitchPesServiceUsageCounters 4 }

sonusSoftSwitchPesSucNonSubsBlocking OBJECT-TYPE
    SYNTAX          Counter
    ACCESS          read-only
    STATUS          mandatory
    DESCRIPTION     
            "Non Subscriber Blocking: This counter keeps track of
             how many times Subscriber Blocking Service is executed. This
             counter is incremented when the calling party is not present
             in the Subscriber database table and the non-subscriber call is blocked."
    ::= { sonusSoftSwitchPesServiceUsageCounters 5 }

sonusSoftSwitchPesSucSubsForcedRouting OBJECT-TYPE
    SYNTAX          Counter
    ACCESS          read-only
    STATUS          mandatory
    DESCRIPTION     
            "Subscriber Forced Routing: This counter keeps track of how many
             times Subscriber Forced Routing Service is executed. The counter is
             incremented when forced routing service provisioned for subscriber
             is executed."
    ::= { sonusSoftSwitchPesServiceUsageCounters 6 }

sonusSoftSwitchPesSucSubsHiFraudBlocking OBJECT-TYPE
    SYNTAX          Counter
    ACCESS          read-only
    STATUS          mandatory
    DESCRIPTION     
            "Subscriber HiFraud Blocking: This counter keeps track of how
             many times Subscriber HiFraud Blocking Service is executed.
             The counter is incremented when HiFraud Blocking service provisioned
             for subscriber is executed.     "
    ::= { sonusSoftSwitchPesServiceUsageCounters 7 }

sonusSoftSwitchPesSucSubsSacNonSacRoutes OBJECT-TYPE
    SYNTAX          Counter
    ACCESS          read-only
    STATUS          mandatory
    DESCRIPTION     
            "Subscriber SAC/Non-SAC Routes: This counter keeps track of how
             many times Subscriber SAC/Non-SAC Routing Service is executed.
             The counter is incremented when SAC/Non-SAC Routing service
             provisioned for subscriber is executed. "
    ::= { sonusSoftSwitchPesServiceUsageCounters 8 }

sonusSoftSwitchPesSucDestNumForcedRouting OBJECT-TYPE
    SYNTAX          Counter
    ACCESS          read-only
    STATUS          mandatory
    DESCRIPTION     
            "Destination Number Forced Routing: This counter keeps track of
             how many times Destination Number Forced Routing Service is executed.
             The counter is incremented when Destination Number Forced Routing
             service provisioned for subscriber, Carrier, Trunkgroup or Gateway
             is executed."
    ::= { sonusSoftSwitchPesServiceUsageCounters 9 }

sonusSoftSwitchPesSucCicPhoneScreening OBJECT-TYPE
    SYNTAX          Counter
    ACCESS          read-only
    STATUS          mandatory
    DESCRIPTION     
            "CIC Phone Screening: This counter keeps track of how many times
             incoming phone type calls are not allowed."
    ::= { sonusSoftSwitchPesServiceUsageCounters 10 }

sonusSoftSwitchPesSucCicScreening OBJECT-TYPE
    SYNTAX          Counter
    ACCESS          read-only
    STATUS          mandatory
    DESCRIPTION     
            "CIC Screening: This counter keeps track of how many times
             CIC Screening Service is executed. The counter is incremented
             when screening service provisioned for carrier is executed."
    ::= { sonusSoftSwitchPesServiceUsageCounters 11 }

sonusSoftSwitchPesSucCicBlocking OBJECT-TYPE
    SYNTAX          Counter
    ACCESS          read-only
    STATUS          mandatory
    DESCRIPTION     
            "CIC Blocking: This counter keeps track of how many times
             CIC Blocking Service is executed. The counter is incremented
             when blocking service provisioned for carrier is executed."
    ::= { sonusSoftSwitchPesServiceUsageCounters 12 }

sonusSoftSwitchPesSucCicForcedRouting OBJECT-TYPE
    SYNTAX          Counter
    ACCESS          read-only
    STATUS          mandatory
    DESCRIPTION     
            "CIC Forced Routing: This counter keeps track of how many
             times CIC Forced Routing Service is executed. The counter
             is incremented when Forced Routing service provisioned for
             carrier is executed."
    ::= { sonusSoftSwitchPesServiceUsageCounters 13 }

sonusSoftSwitchPesSucCicHiFraudBlocking OBJECT-TYPE
    SYNTAX          Counter
    ACCESS          read-only
    STATUS          mandatory
    DESCRIPTION     
            "CIC HiFraud Blocking: This counter keeps track of how
             many times CIC HiFraud Blocking Service is executed. The
             counter is incremented when HiFraud Blocking service
             provisioned for carrier is executed."
    ::= { sonusSoftSwitchPesServiceUsageCounters 14 }

sonusSoftSwitchPesSucCicSacNonSacRoutes OBJECT-TYPE
    SYNTAX          Counter
    ACCESS          read-only
    STATUS          mandatory
    DESCRIPTION     
            "CIC SAC/Non-SAC Routes: This counter keeps track of
             how many times CIC SAC/Non-SAC Routing Service is executed.
             The counter is incremented when SAC/Non-SAC Routing service
             provisioned for carrier is executed."
    ::= { sonusSoftSwitchPesServiceUsageCounters 15 }

sonusSoftSwitchPesSucTrunkgroupScreening OBJECT-TYPE
    SYNTAX          Counter
    ACCESS          read-only
    STATUS          mandatory
    DESCRIPTION     
            "Trunkgroup Screening: This counter keeps track of how
             many times Trunkgroup Screening Service is executed. The
             counter is incremented when screening service provisioned
             for trunkgroup is executed."
    ::= { sonusSoftSwitchPesServiceUsageCounters 16 }

sonusSoftSwitchPesSucTrunkgroupBlocking OBJECT-TYPE
    SYNTAX          Counter
    ACCESS          read-only
    STATUS          mandatory
    DESCRIPTION     
            "Trunkgroup Blocking: This counter keeps track of
             how many times Trunkgroup Blocking Service is executed.
             The counter is incremented when blocking service provisioned
             for trunkgroup is executed."
    ::= { sonusSoftSwitchPesServiceUsageCounters 17 }

sonusSoftSwitchPesSucTrunkgroupForcedRouting OBJECT-TYPE
    SYNTAX          Counter
    ACCESS          read-only
    STATUS          mandatory
    DESCRIPTION     
            "Trunkgroup Forced Routing: This counter keeps track of
             how many times Trunkgroup Forced Routing Service is executed.
             The counter is incremented when forced routing service
             provisioned for trunkgroup is executed."
    ::= { sonusSoftSwitchPesServiceUsageCounters 18 }

sonusSoftSwitchPesSucTrunkgroupHiFraudBlocking OBJECT-TYPE
    SYNTAX          Counter
    ACCESS          read-only
    STATUS          mandatory
    DESCRIPTION     
            "Trunkgroup HiFraud Blocking: This counter keeps track
             of how many times Trunkgroup HiFraud Blocking Service is
             executed. The counter is incremented when HiFraud service
             provisioned for trunkgroup is executed."
    ::= { sonusSoftSwitchPesServiceUsageCounters 19 }

sonusSoftSwitchPesSucTrunkgroupSacNonSacRoutes OBJECT-TYPE
    SYNTAX          Counter
    ACCESS          read-only
    STATUS          mandatory
    DESCRIPTION     
            "Trunkgroup SAC/Non-SAC Routes: This counter keeps
             track of how many times Trunkgroup SAC/Non-SAC Routing
             Service is executed. The counter is incremented when
             SAC/Non-SAC Routing service provisioned for trunkgroup
             is executed."
    ::= { sonusSoftSwitchPesServiceUsageCounters 20 }

sonusSoftSwitchPesSucCasualCallUnallowed OBJECT-TYPE
    SYNTAX          Counter
    ACCESS          read-only
    STATUS          mandatory
    DESCRIPTION     
            "Casual calls not allowed: This counter keeps track of
             how many times casual calls are not allowed through the
             network. The counter is incremented when the explicitly
             dialed carrier code incoming call type (for example, 1010321)
             is not allowed at one of the following levels of
             granularity: Infodigit, Carrier, Trunk group, Gateway,
             and SoftSwitch."
    ::= { sonusSoftSwitchPesServiceUsageCounters 21 }

sonusSoftSwitchPesSucNonSubscriberCallsUnallowed OBJECT-TYPE
    SYNTAX          Counter
    ACCESS          read-only
    STATUS          mandatory
    DESCRIPTION     
            "Non Subscriber calls not allowed: This counter keeps
             track of how many times non subscriber calls are not
             allowed through the network. This counter is incremented
             when a calling party is not present in the subscriber
             database and the casual routing is not allowed at Carrier,
             Trunkgroup, or Gateway level."
    ::= { sonusSoftSwitchPesServiceUsageCounters 22 }

sonusSoftSwitchPesSucGatewayScreening OBJECT-TYPE
    SYNTAX          Counter
    ACCESS          read-only
    STATUS          mandatory
    DESCRIPTION     
            "Gateway Screening: This counter keeps track of how
             many times Gateway Screening Service is executed. The
             counter is incremented when screening service provisioned
             for gateway is executed."
    ::= { sonusSoftSwitchPesServiceUsageCounters 23 }

sonusSoftSwitchPesSucGatewayBlocking OBJECT-TYPE
    SYNTAX          Counter
    ACCESS          read-only
    STATUS          mandatory
    DESCRIPTION     
            "Gateway Blocking: This counter keeps track of how
             many times Gateway Blocking Service is executed. The
             counter is incremented when blocking service provisioned
             for gateway is executed."
    ::= { sonusSoftSwitchPesServiceUsageCounters 24 }

sonusSoftSwitchPesSucGatewayForcedRouting OBJECT-TYPE
    SYNTAX          Counter
    ACCESS          read-only
    STATUS          mandatory
    DESCRIPTION     
            "Gateway Forced Routing: This counter keeps track of how
             many times Gateway Forced Routing Service is executed.
             The counter is incremented when Forced Routing service
             provisioned for gateway is executed."
    ::= { sonusSoftSwitchPesServiceUsageCounters 25 }

sonusSoftSwitchPesSucGatewayHiFraudBlocking OBJECT-TYPE
    SYNTAX          Counter
    ACCESS          read-only
    STATUS          mandatory
    DESCRIPTION     
            "Gateway HiFraud Blocking: This counter keeps track
             of how many times Gateway HiFraud Blocking Service
             is executed. The counter is incremented when
             HiFraud Blocking service provisioned for gateway
             is executed."
    ::= { sonusSoftSwitchPesServiceUsageCounters 26 }

sonusSoftSwitchPesSucGatewaySacNonSacRoutes OBJECT-TYPE
    SYNTAX          Counter
    ACCESS          read-only
    STATUS          mandatory
    DESCRIPTION     
            "Gateway SAC/Non-SAC Routes: This counter keeps
             track of how many times Gateway SAC/Non-SAC Routing
             Service is executed. The counter is incremented when
             SAC/Non-SAC Routing service provisioned for gateway
             is executed."
    ::= { sonusSoftSwitchPesServiceUsageCounters 27 }

sonusSoftSwitchPesSucAuthcodeScreening OBJECT-TYPE
    SYNTAX          Counter
    ACCESS          read-only
    STATUS          mandatory
    DESCRIPTION     
            "Authcode Screening: This counter keeps track of
             how many times the Authcode Screening Service is
             executed. The counter is incremented when the screening
             service provisioned for Authcode is executed."
    ::= { sonusSoftSwitchPesServiceUsageCounters 28 }

sonusSoftSwitchPesSucAuthcodeBlocking OBJECT-TYPE
    SYNTAX          Counter
    ACCESS          read-only
    STATUS          mandatory
    DESCRIPTION     
            "Authcode Blocking: This counter keeps track of how
             many times the Authcode Blocking service is executed.
             The counter is incremented when the blocking service
             provisioned for Authcode is executed."
    ::= { sonusSoftSwitchPesServiceUsageCounters 29 }

sonusSoftSwitchPesSucAuthcodeForcedRouting OBJECT-TYPE
    SYNTAX          Counter
    ACCESS          read-only
    STATUS          mandatory
    DESCRIPTION     
            "Authcode Forced Routing: This counter keeps track
             of how many times the Authcode Forced Routing service
             is executed. The counter is incremented when the Forced
             Routing service provisioned for Authcode is executed."
    ::= { sonusSoftSwitchPesServiceUsageCounters 30 }

sonusSoftSwitchPesSucAuthcodeHiFraudBlocking OBJECT-TYPE
    SYNTAX          Counter
    ACCESS          read-only
    STATUS          mandatory
    DESCRIPTION     
            "Authcode HiFraud Blocking: This counter keeps track of
             how many times the Authcode HiFraud Blocking service is
             executed. The counter is incremented when the HiFraud
             Blocking service provisioned for Authcode is executed."
    ::= { sonusSoftSwitchPesServiceUsageCounters 31 }

sonusSoftSwitchPesSucAuthcodeSacNonSacRoutes OBJECT-TYPE
    SYNTAX          Counter
    ACCESS          read-only
    STATUS          mandatory
    DESCRIPTION     
            "Authcode SAC/Non-SAC Routes: This counter keeps track
             of how many times the Authcode SAC/Non-SAC Routing service
             is executed. The counter is incremented when the SAC/Non-SAC
             Routing service provisioned for Authcode is executed."
    ::= { sonusSoftSwitchPesServiceUsageCounters 32 }

sonusSoftSwitchPesSucInfodigitScreening OBJECT-TYPE
    SYNTAX          Counter
    ACCESS          read-only
    STATUS          mandatory
    DESCRIPTION     
            "Infodigit Screening: This counter keeps track of
             how many times the Infodigit Screening Service is executed.
             The counter is incremented when the screening service
             provisioned for Infodigit is executed."
    ::= { sonusSoftSwitchPesServiceUsageCounters 33 }

sonusSoftSwitchPesSucInfodigitBlocking OBJECT-TYPE
    SYNTAX          Counter
    ACCESS          read-only
    STATUS          mandatory
    DESCRIPTION     
            "Infodigit Blocking: This counter keeps track of
             how many times the Infodigit Blocking service is
             executed. The counter is incremented when the blocking
             service provisioned for Infodigit is executed."
    ::= { sonusSoftSwitchPesServiceUsageCounters 34 }

sonusSoftSwitchPesSucInfodigitForcedRouting OBJECT-TYPE
    SYNTAX          Counter
    ACCESS          read-only
    STATUS          mandatory
    DESCRIPTION     
            "Infodigit Forced Routing: This counter keeps track
             of how many times the Infodigit Forced Routing service
             is executed. The counter is incremented when the Forced
             Routing service provisioned for Infodigit is executed."
    ::= { sonusSoftSwitchPesServiceUsageCounters 35 }

sonusSoftSwitchPesSucInfodigitHiFraudBlocking OBJECT-TYPE
    SYNTAX          Counter
    ACCESS          read-only
    STATUS          mandatory
    DESCRIPTION     
            "Infodigit HiFraud Blocking: This counter keeps
             track of how many times the Infodigit HiFraud Blocking
             service is executed. The counter is incremented when the
             HiFraud Blocking service provisioned for Infodigit
             is executed."
    ::= { sonusSoftSwitchPesServiceUsageCounters 36 }

sonusSoftSwitchPesSucInfodigitSacNonSacRoutes OBJECT-TYPE
    SYNTAX          Counter
    ACCESS          read-only
    STATUS          mandatory
    DESCRIPTION     
            "Infodigit SAC/Non-SAC Routes: This counter keeps
             track of how many times the Infodigit SAC/Non-SAC Routing
             service is executed. The counter is incremented when the
             SAC/Non-SAC Routing service provisioned for Infodigit is executed."
    ::= { sonusSoftSwitchPesServiceUsageCounters 37 }

sonusSoftSwitchPesSucSoftswitchScreening OBJECT-TYPE
    SYNTAX          Counter
    ACCESS          read-only
    STATUS          mandatory
    DESCRIPTION     
            "Softswitch Screening: This counter keeps track of how
             many times the SoftSwitch Screening Service is executed.
             The counter is incremented when the screening service
             provisioned for SoftSwitch is executed."
    ::= { sonusSoftSwitchPesServiceUsageCounters 38 }

sonusSoftSwitchPesSucSoftswitchBlocking OBJECT-TYPE
    SYNTAX          Counter
    ACCESS          read-only
    STATUS          mandatory
    DESCRIPTION     
            "Softswitch Blocking: This counter keeps track of
             how many times the SoftSwitch Blocking service is executed.
             The counter is incremented when the blocking service
             provisioned for SoftSwitch is executed."
    ::= { sonusSoftSwitchPesServiceUsageCounters 39 }

sonusSoftSwitchPesSucSoftswitchForcedRouting OBJECT-TYPE
    SYNTAX          Counter
    ACCESS          read-only
    STATUS          mandatory
    DESCRIPTION     
            "Softswitch Forced Routing: This counter keeps track
             of how many times the SoftSwitch Forced Routing service
             is executed. The counter is incremented when the Forced
             Routing service provisioned for SoftSwitch is executed."
    ::= { sonusSoftSwitchPesServiceUsageCounters 40 }

sonusSoftSwitchPesSucSoftswitchHiFraudBlocking OBJECT-TYPE
    SYNTAX          Counter
    ACCESS          read-only
    STATUS          mandatory
    DESCRIPTION     
            "Softswitch HiFraud Blocking: This counter keeps track
             of how many times the SoftSwitch HiFraud Blocking service
             is executed. The counter is incremented when the HiFraud
             Blocking service provisioned for SoftSwitch is executed."
    ::= { sonusSoftSwitchPesServiceUsageCounters 41 }

sonusSoftSwitchPesSucSoftswitchSacNonSacRoutes OBJECT-TYPE
    SYNTAX          Counter
    ACCESS          read-only
    STATUS          mandatory
    DESCRIPTION     
            "Softswitch SAC/Non-SAC Routes: This counter keeps track
             of how many times the SoftSwitch SAC/Non-SAC Routing
             service is executed. The counter is incremented when
             the SAC/Non-SAC Routing service provis ioned for
             SoftSwitch is executed."
    ::= { sonusSoftSwitchPesServiceUsageCounters 42 }

sonusSoftSwitchPesSvcIntervalTime OBJECT-TYPE
    SYNTAX          TimeTicks
    ACCESS          read-only
    STATUS          mandatory
    DESCRIPTION     
            "This variable contains the end of interval time stamp for 
             the specified interval."
    ::= { sonusSoftSwitchPesServiceUsageCounters 43 }

sonusSoftSwitchPesScpCounters OBJECT IDENTIFIER
    ::= { sonusSoftSwitchPolicyExecutionServerStatistics 3 }

sonusSoftSwitchPesLNPCountersGsxTable OBJECT-TYPE
    SYNTAX          SEQUENCE OF SonusSoftSwitchPesLNPCountersGsxEntry
    ACCESS          not-accessible
    STATUS          mandatory
    DESCRIPTION     
            "The LNP related counters per GSX table."
    ::= { sonusSoftSwitchPesScpCounters 1 }

sonusSoftSwitchPesLNPCountersGsxEntry OBJECT-TYPE
    SYNTAX          SonusSoftSwitchPesLNPCountersGsxEntry
    ACCESS          not-accessible
    STATUS          mandatory
    DESCRIPTION     
            "An entry in the Sonus MTP30 Link Interval table."
    INDEX           { sonusSoftSwitchPesLNPCountersGsxIp }
    ::= { sonusSoftSwitchPesLNPCountersGsxTable 1 }

SonusSoftSwitchPesLNPCountersGsxEntry ::=
    SEQUENCE {
        sonusSoftSwitchPesLNPCountersGsxIp  IpAddress,
        sonusSoftSwitchPesLNPCountersGsxName    SonusName,
        sonusSoftSwitchPesLNPCountersGsxMisroutedCalls              Counter,
        sonusSoftSwitchPesLNPCountersGsxInvalidNumbers              Counter,
        sonusSoftSwitchPesLNPCountersGsxIntervalTime            TimeTicks
    }

sonusSoftSwitchPesLNPCountersGsxIp OBJECT-TYPE
    SYNTAX          IpAddress
    ACCESS          read-only
    STATUS          mandatory
    DESCRIPTION     
            "The GSX IP Address that the LNP Counters apply to"
    ::= { sonusSoftSwitchPesLNPCountersGsxEntry 1 }

sonusSoftSwitchPesLNPCountersGsxName OBJECT-TYPE
    SYNTAX          SonusName
    ACCESS          read-only
    STATUS          mandatory
    DESCRIPTION     
            "The GSX Name that the LNP Counters apply to"
    ::= { sonusSoftSwitchPesLNPCountersGsxEntry 2 }

sonusSoftSwitchPesLNPCountersGsxMisroutedCalls OBJECT-TYPE
    SYNTAX          Counter
    ACCESS          read-only
    STATUS          mandatory
    DESCRIPTION     
            "Misrouted calls: Number of LNP-specific ISUP
             release messages received by the GSX9000 with
             cause 26 - misrouted call to a ported number."
    ::= { sonusSoftSwitchPesLNPCountersGsxEntry 3 }

sonusSoftSwitchPesLNPCountersGsxInvalidNumbers OBJECT-TYPE
    SYNTAX          Counter
    ACCESS          read-only
    STATUS          mandatory
    DESCRIPTION     
            "Invalid Number: Number of LNP-specific
             ISUP release messages received by the GSX9000
             with cause 28 - Invalid number format."
    ::= { sonusSoftSwitchPesLNPCountersGsxEntry 4 }

sonusSoftSwitchPesLNPCountersGsxIntervalTime OBJECT-TYPE
    SYNTAX          TimeTicks
    ACCESS          read-only
    STATUS          mandatory
    DESCRIPTION     
            "This variable contains the end of interval time stamp for 
             the specified interval."
    ::= { sonusSoftSwitchPesLNPCountersGsxEntry 5 }

sonusSoftSwitchPesLNPCountersNumLNPRequests OBJECT-TYPE
    SYNTAX          Counter
    ACCESS          read-only
    STATUS          mandatory
    DESCRIPTION     
            "Number of requests that need LNP: Total
             number of requests received by the Sonus
             SoftSwitch which require LNP translation."
    ::= { sonusSoftSwitchPesScpCounters 2 }

sonusSoftSwitchPesLNPCountersNumSCPRequests OBJECT-TYPE
    SYNTAX          Counter
    ACCESS          read-only
    STATUS          mandatory
    DESCRIPTION     
            "Number of LNP requests sent to SCP: Total
             number of requests sent to the SCP for LNP
             translation."
    ::= { sonusSoftSwitchPesScpCounters 3 }

sonusSoftSwitchPesLNPCountersNumDNRequests OBJECT-TYPE
    SYNTAX          Counter
    ACCESS          read-only
    STATUS          mandatory
    DESCRIPTION     
            "Number of LNP requests to ported DN's:
             The number of LNP requests made for ported DN's."
    ::= { sonusSoftSwitchPesScpCounters 4 }

sonusSoftSwitchPesLNPCountersNumTimedOutRequests OBJECT-TYPE
    SYNTAX          Counter
    ACCESS          read-only
    STATUS          mandatory
    DESCRIPTION     
            "Number of timed out LNP requests: Number of
             LNP requests that timed out."
    ::= { sonusSoftSwitchPesScpCounters 5 }

sonusSoftSwitchPesLNPCountersNumRequestErrors OBJECT-TYPE
    SYNTAX          Counter
    ACCESS          read-only
    STATUS          mandatory
    DESCRIPTION     
            "Number of LNP request Errors: Number of errors
             other than timeout received from the SCP."
    ::= { sonusSoftSwitchPesScpCounters 6 }

sonusSoftSwitchPesTfcNumRequests OBJECT-TYPE
    SYNTAX          Counter
    ACCESS          read-only
    STATUS          mandatory
    DESCRIPTION     
            "Number of requests that need Tollfree translation:
             Total number of requests received by the Sonus SoftSwitch
             which require toll free translation."
    ::= { sonusSoftSwitchPesScpCounters 7 }

sonusSoftSwitchPesTfcNumRequestsToScp OBJECT-TYPE
    SYNTAX          Counter
    ACCESS          read-only
    STATUS          mandatory
    DESCRIPTION     
            "Number of Toll free requests sent to SCP: Total number
             of requests sent to the SCP for translation."
    ::= { sonusSoftSwitchPesScpCounters 8 }

sonusSoftSwitchPesTfcNumRequestsTranslated OBJECT-TYPE
    SYNTAX          Counter
    ACCESS          read-only
    STATUS          mandatory
    DESCRIPTION     
            "Number of Toll free requests translated: The number of toll
             free requests that were successfully translated."
    ::= { sonusSoftSwitchPesScpCounters 9 }

sonusSoftSwitchPesTfcNumTimedOutRequests OBJECT-TYPE
    SYNTAX          Counter
    ACCESS          read-only
    STATUS          mandatory
    DESCRIPTION     
            "Number of timed out toll free requests: Number of toll free
             requests that timed out."
    ::= { sonusSoftSwitchPesScpCounters 10 }

ssonusSoftSwitchPesTfcNumRequestErrors OBJECT-TYPE
    SYNTAX          Counter
    ACCESS          read-only
    STATUS          mandatory
    DESCRIPTION     
            "Number of toll free request Errors: Number of toll free
             requests that resulted in an error."
    ::= { sonusSoftSwitchPesScpCounters 11 }

sonusSoftSwitchPesTfcLNPCountersIntervalTime OBJECT-TYPE
    SYNTAX          TimeTicks
    ACCESS          read-only
    STATUS          mandatory
    DESCRIPTION     
            "This variable contains the end of interval time stamp for 
             the specified interval."
    ::= { sonusSoftSwitchPesScpCounters 12 }

sonusSoftSwitchPesTrafficMgmtCounters OBJECT IDENTIFIER
    ::= { sonusSoftSwitchPolicyExecutionServerStatistics 4 }

sonusSoftswitchPesTMDialedDestinationCounters OBJECT IDENTIFIER
    ::= { sonusSoftSwitchPesTrafficMgmtCounters 1 }

sonusSoftswitchPesTMDialedDestinationCountersAllowedTable OBJECT-TYPE
    SYNTAX          SEQUENCE OF SonusSoftswitchPesTMDialedDestinationCountersAllowedEntry
    ACCESS          not-accessible
    STATUS          mandatory
    DESCRIPTION     
            "The Traffic Management related counters for allowed dialed destination number."
    ::= { sonusSoftswitchPesTMDialedDestinationCounters 1 }

sonusSoftswitchPesTMDialedDestinationCountersAllowedEntry OBJECT-TYPE
    SYNTAX          SonusSoftswitchPesTMDialedDestinationCountersAllowedEntry
    ACCESS          not-accessible
    STATUS          mandatory
    DESCRIPTION     
            "The Traffic Management related counters for allowed dialed destination number."
    INDEX           { 
                      sonusSoftswitchPesTMDialedDestinationCountersAllowedEntity, 
                      sonusSoftswitchPesTMDialedDestinationCountersAllowedEntity2 }
    ::= { sonusSoftswitchPesTMDialedDestinationCountersAllowedTable 1 }

SonusSoftswitchPesTMDialedDestinationCountersAllowedEntry ::=
    SEQUENCE {
        sonusSoftswitchPesTMDialedDestinationCountersAllowedEntity                          SonusName,
        sonusSoftswitchPesTMDialedDestinationCountersAllowedEntity2                           SonusName,
        sonusSoftswitchPesTMDialedDestinationCountersAllowedValue                         Counter,
        sonusSoftSwitchPesTMDialedDestinationAllowedIntervalTime                        TimeTicks
    }

sonusSoftswitchPesTMDialedDestinationCountersAllowedEntity OBJECT-TYPE
    SYNTAX          SonusName
    ACCESS          read-only
    STATUS          mandatory
    DESCRIPTION     
            "Entity Id (national number) for dialed destination with traffic control"
    ::= { sonusSoftswitchPesTMDialedDestinationCountersAllowedEntry 1 }

sonusSoftswitchPesTMDialedDestinationCountersAllowedEntity2 OBJECT-TYPE
    SYNTAX          SonusName
    ACCESS          read-only
    STATUS          mandatory
    DESCRIPTION     
            "Entity Id2 (country id) for dialed destination with traffic control"
    ::= { sonusSoftswitchPesTMDialedDestinationCountersAllowedEntry 2 }

sonusSoftswitchPesTMDialedDestinationCountersAllowedValue OBJECT-TYPE
    SYNTAX          Counter
    ACCESS          read-only
    STATUS          mandatory
    DESCRIPTION     
            "Number of allowed calls to dialed destination with traffic control"
    ::= { sonusSoftswitchPesTMDialedDestinationCountersAllowedEntry 3 }

sonusSoftSwitchPesTMDialedDestinationAllowedIntervalTime OBJECT-TYPE
    SYNTAX          TimeTicks
    ACCESS          read-only
    STATUS          obsolete
    DESCRIPTION     
            "This variable contains the end of interval time stamp for the specified interval."
    ::= { sonusSoftswitchPesTMDialedDestinationCountersAllowedEntry 4 }

sonusSoftswitchPesTMDialedDestinationCountersBlockedTable OBJECT-TYPE
    SYNTAX          SEQUENCE OF SonusSoftswitchPesTMDialedDestinationCountersBlockedEntry
    ACCESS          not-accessible
    STATUS          mandatory
    DESCRIPTION     
            "The Traffic Management related counters for blocked dialed destination number."
    ::= { sonusSoftswitchPesTMDialedDestinationCounters 2 }

sonusSoftswitchPesTMDialedDestinationCountersBlockedEntry OBJECT-TYPE
    SYNTAX          SonusSoftswitchPesTMDialedDestinationCountersBlockedEntry
    ACCESS          not-accessible
    STATUS          mandatory
    DESCRIPTION     
            "The Traffic Management related counters for blocked dialed destination number."
    INDEX           { 
                      sonusSoftswitchPesTMDialedDestinationCountersBlockedEntity, 
                      sonusSoftswitchPesTMDialedDestinationCountersBlockedEntity2 }
    ::= { sonusSoftswitchPesTMDialedDestinationCountersBlockedTable 1 }

SonusSoftswitchPesTMDialedDestinationCountersBlockedEntry ::=
    SEQUENCE {
        sonusSoftswitchPesTMDialedDestinationCountersBlockedEntity                          SonusName,
        sonusSoftswitchPesTMDialedDestinationCountersBlockedEntity2                           SonusName,
        sonusSoftswitchPesTMDialedDestinationCountersBlockedValue                         Counter,
        sonusSoftSwitchPesTMDialedDestinationBlockedIntervalTime                        TimeTicks
    }

sonusSoftswitchPesTMDialedDestinationCountersBlockedEntity OBJECT-TYPE
    SYNTAX          SonusName
    ACCESS          read-only
    STATUS          mandatory
    DESCRIPTION     
            "Entity Id (national number) for dialed destination with traffic control"
    ::= { sonusSoftswitchPesTMDialedDestinationCountersBlockedEntry 1 }

sonusSoftswitchPesTMDialedDestinationCountersBlockedEntity2 OBJECT-TYPE
    SYNTAX          SonusName
    ACCESS          read-only
    STATUS          mandatory
    DESCRIPTION     
            "Entity Id2 (country id) for dialed destination with traffic control"
    ::= { sonusSoftswitchPesTMDialedDestinationCountersBlockedEntry 2 }

sonusSoftswitchPesTMDialedDestinationCountersBlockedValue OBJECT-TYPE
    SYNTAX          Counter
    ACCESS          read-only
    STATUS          mandatory
    DESCRIPTION     
            "Number of blocked calls to dialed destination with traffic control"
    ::= { sonusSoftswitchPesTMDialedDestinationCountersBlockedEntry 3 }

sonusSoftSwitchPesTMDialedDestinationBlockedIntervalTime OBJECT-TYPE
    SYNTAX          TimeTicks
    ACCESS          read-only
    STATUS          obsolete
    DESCRIPTION     
            "This variable contains the end of interval time stamp for 
             the specified interval."
    ::= { sonusSoftswitchPesTMDialedDestinationCountersBlockedEntry 4 }

sonusSoftswitchPesTMTranslatedDestinationCounters OBJECT IDENTIFIER
    ::= { sonusSoftSwitchPesTrafficMgmtCounters 2 }

sonusSoftswitchPesTMTranslatedDestinationCountersAllowedTable OBJECT-TYPE
    SYNTAX          SEQUENCE OF SonusSoftswitchPesTMTranslatedDestinationCountersAllowedEntry
    ACCESS          not-accessible
    STATUS          mandatory
    DESCRIPTION     
            "The Traffic Management related counters for allowed translated destination number."
    ::= { sonusSoftswitchPesTMTranslatedDestinationCounters 1 }

sonusSoftswitchPesTMTranslatedDestinationCountersAllowedEntry OBJECT-TYPE
    SYNTAX          SonusSoftswitchPesTMTranslatedDestinationCountersAllowedEntry
    ACCESS          not-accessible
    STATUS          mandatory
    DESCRIPTION     
            "The Traffic Management related counters for allowed translated destination number."
    INDEX           { 
                      sonusSoftswitchPesTMTranslatedDestinationCountersAllowedEntity, 
                      sonusSoftswitchPesTMTranslatedDestinationCountersAllowedEntity2 }
    ::= { sonusSoftswitchPesTMTranslatedDestinationCountersAllowedTable 1 }

SonusSoftswitchPesTMTranslatedDestinationCountersAllowedEntry ::=
    SEQUENCE {
        sonusSoftswitchPesTMTranslatedDestinationCountersAllowedEntity                              SonusName,
        sonusSoftswitchPesTMTranslatedDestinationCountersAllowedEntity2                               SonusName,
        sonusSoftswitchPesTMTranslatedDestinationCountersAllowedValue                             Counter,
        sonusSoftSwitchPesTMTranslatedDestinationAllowedIntervalTime                            TimeTicks
    }

sonusSoftswitchPesTMTranslatedDestinationCountersAllowedEntity OBJECT-TYPE
    SYNTAX          SonusName
    ACCESS          read-only
    STATUS          mandatory
    DESCRIPTION     
            "Entity Id (national number) for translated destination with traffic control"
    ::= { sonusSoftswitchPesTMTranslatedDestinationCountersAllowedEntry 1 }

sonusSoftswitchPesTMTranslatedDestinationCountersAllowedEntity2 OBJECT-TYPE
    SYNTAX          SonusName
    ACCESS          read-only
    STATUS          mandatory
    DESCRIPTION     
            "Entity Id2 (country id) for translated destination with traffic control"
    ::= { sonusSoftswitchPesTMTranslatedDestinationCountersAllowedEntry 2 }

sonusSoftswitchPesTMTranslatedDestinationCountersAllowedValue OBJECT-TYPE
    SYNTAX          Counter
    ACCESS          read-only
    STATUS          mandatory
    DESCRIPTION     
            "Number of allowed calls to translated destination with traffic control"
    ::= { sonusSoftswitchPesTMTranslatedDestinationCountersAllowedEntry 3 }

sonusSoftSwitchPesTMTranslatedDestinationAllowedIntervalTime OBJECT-TYPE
    SYNTAX          TimeTicks
    ACCESS          read-only
    STATUS          obsolete
    DESCRIPTION     
            "This variable contains the end of interval time stamp for 
             the specified interval."
    ::= { sonusSoftswitchPesTMTranslatedDestinationCountersAllowedEntry 4 }

sonusSoftswitchPesTMTranslatedDestinationCountersBlockedTable OBJECT-TYPE
    SYNTAX          SEQUENCE OF SonusSoftswitchPesTMTranslatedDestinationCountersBlockedEntry
    ACCESS          not-accessible
    STATUS          mandatory
    DESCRIPTION     
            "The Traffic Management related counters for blocked translated destination number."
    ::= { sonusSoftswitchPesTMTranslatedDestinationCounters 2 }

sonusSoftswitchPesTMTranslatedDestinationCountersBlockedEntry OBJECT-TYPE
    SYNTAX          SonusSoftswitchPesTMTranslatedDestinationCountersBlockedEntry
    ACCESS          not-accessible
    STATUS          mandatory
    DESCRIPTION     
            "The Traffic Management related counters for blocked translated destination number."
    INDEX           { 
                      sonusSoftswitchPesTMTranslatedDestinationCountersBlockedEntity, 
                      sonusSoftswitchPesTMTranslatedDestinationCountersBlockedEntity2 }
    ::= { sonusSoftswitchPesTMTranslatedDestinationCountersBlockedTable 1 }

SonusSoftswitchPesTMTranslatedDestinationCountersBlockedEntry ::=
    SEQUENCE {
        sonusSoftswitchPesTMTranslatedDestinationCountersBlockedEntity                              SonusName,
        sonusSoftswitchPesTMTranslatedDestinationCountersBlockedEntity2                               SonusName,
        sonusSoftswitchPesTMTranslatedDestinationCountersBlockedValue                             Counter,
        sonusSoftSwitchPesTMTranslatedDestinationBlockedIntervalTime                            TimeTicks
    }

sonusSoftswitchPesTMTranslatedDestinationCountersBlockedEntity OBJECT-TYPE
    SYNTAX          SonusName
    ACCESS          read-only
    STATUS          mandatory
    DESCRIPTION     
            "Entity Id (national number) for translated destination with traffic control"
    ::= { sonusSoftswitchPesTMTranslatedDestinationCountersBlockedEntry 1 }

sonusSoftswitchPesTMTranslatedDestinationCountersBlockedEntity2 OBJECT-TYPE
    SYNTAX          SonusName
    ACCESS          read-only
    STATUS          mandatory
    DESCRIPTION     
            "Entity Id2 (country id) for translated destination with traffic control"
    ::= { sonusSoftswitchPesTMTranslatedDestinationCountersBlockedEntry 2 }

sonusSoftswitchPesTMTranslatedDestinationCountersBlockedValue OBJECT-TYPE
    SYNTAX          Counter
    ACCESS          read-only
    STATUS          mandatory
    DESCRIPTION     
            "Number of blocked calls to translated destination with traffic control"
    ::= { sonusSoftswitchPesTMTranslatedDestinationCountersBlockedEntry 3 }

sonusSoftSwitchPesTMTranslatedDestinationBlockedIntervalTime OBJECT-TYPE
    SYNTAX          TimeTicks
    ACCESS          read-only
    STATUS          obsolete
    DESCRIPTION     
            "This variable contains the end of interval time stamp for 
             the specified interval."
    ::= { sonusSoftswitchPesTMTranslatedDestinationCountersBlockedEntry 4 }

sonusSoftswitchPesTMAlternateRouteSKIPTgCounters OBJECT IDENTIFIER
    ::= { sonusSoftSwitchPesTrafficMgmtCounters 3 }

sonusSoftswitchPesTMAlternateRouteSKIPTgCountersAllowedTable OBJECT-TYPE
    SYNTAX          SEQUENCE OF SonusSoftswitchPesTMAlternateRouteSKIPTgCountersAllowedEntry
    ACCESS          not-accessible
    STATUS          deprecated
    DESCRIPTION     
            "The Traffic Management related counters for SKIP (Alternate) trunkgroup"
    ::= { sonusSoftswitchPesTMAlternateRouteSKIPTgCounters 1 }

sonusSoftswitchPesTMAlternateRouteSKIPTgCountersAllowedEntry OBJECT-TYPE
    SYNTAX          SonusSoftswitchPesTMAlternateRouteSKIPTgCountersAllowedEntry
    ACCESS          not-accessible
    STATUS          deprecated
    DESCRIPTION     
            "The Traffic Management related counters for SKIP (Alternate) trunkgroup"
    INDEX           { 
                      sonusSoftswitchPesTMAlternateRouteSKIPTgCountersAllowedEntity, 
                      sonusSoftswitchPesTMAlternateRouteSKIPTgCountersAllowedEntity2 }
    ::= { sonusSoftswitchPesTMAlternateRouteSKIPTgCountersAllowedTable 1 }

SonusSoftswitchPesTMAlternateRouteSKIPTgCountersAllowedEntry ::=
    SEQUENCE {
        sonusSoftswitchPesTMAlternateRouteSKIPTgCountersAllowedEntity                             SonusName,
        sonusSoftswitchPesTMAlternateRouteSKIPTgCountersAllowedEntity2                              SonusName,
        sonusSoftswitchPesTMAlternateRouteSKIPTgCountersAllowedValue                            Counter,
        sonusSoftSwitchPesTMAlternateRouteSKIPTgAllowedIntervalTime                           TimeTicks
    }

sonusSoftswitchPesTMAlternateRouteSKIPTgCountersAllowedEntity OBJECT-TYPE
    SYNTAX          SonusName
    ACCESS          read-only
    STATUS          deprecated
    DESCRIPTION     
            "Entity Id (trunkgroup id) for trunkgroup with SKIP (AR) traffic control"
    ::= { sonusSoftswitchPesTMAlternateRouteSKIPTgCountersAllowedEntry 1 }

sonusSoftswitchPesTMAlternateRouteSKIPTgCountersAllowedEntity2 OBJECT-TYPE
    SYNTAX          SonusName
    ACCESS          read-only
    STATUS          deprecated
    DESCRIPTION     
            "Entity Id2 (gateway id) for trunkgrop with SKIP (AR) traffic control"
    ::= { sonusSoftswitchPesTMAlternateRouteSKIPTgCountersAllowedEntry 2 }

sonusSoftswitchPesTMAlternateRouteSKIPTgCountersAllowedValue OBJECT-TYPE
    SYNTAX          Counter
    ACCESS          read-only
    STATUS          deprecated
    DESCRIPTION     
            "Number of allowed calls to trunkgroup with SKIP (AR) traffic control"
    ::= { sonusSoftswitchPesTMAlternateRouteSKIPTgCountersAllowedEntry 3 }

sonusSoftSwitchPesTMAlternateRouteSKIPTgAllowedIntervalTime OBJECT-TYPE
    SYNTAX          TimeTicks
    ACCESS          read-only
    STATUS          mandatory
    DESCRIPTION     
            "This variable contains the end of interval time stamp for 
             the specified interval."
    ::= { sonusSoftswitchPesTMAlternateRouteSKIPTgCountersAllowedEntry 4 }

sonusSoftswitchPesTMAlternateRouteSKIPTgCountersBlockedTable OBJECT-TYPE
    SYNTAX          SEQUENCE OF SonusSoftswitchPesTMAlternateRouteSKIPTgCountersBlockedEntry
    ACCESS          not-accessible
    STATUS          deprecated
    DESCRIPTION     
            "The Traffic Management related counters for SKIP (Alternate) trunkgroup"
    ::= { sonusSoftswitchPesTMAlternateRouteSKIPTgCounters 2 }

sonusSoftswitchPesTMAlternateRouteSKIPTgCountersBlockedEntry OBJECT-TYPE
    SYNTAX          SonusSoftswitchPesTMAlternateRouteSKIPTgCountersBlockedEntry
    ACCESS          not-accessible
    STATUS          deprecated
    DESCRIPTION     
            "The Traffic Management related counters for SKIP (Alternate) trunkgroup"
    INDEX           { 
                      sonusSoftswitchPesTMAlternateRouteSKIPTgCountersBlockedEntity, 
                      sonusSoftswitchPesTMAlternateRouteSKIPTgCountersBlockedEntity2 }
    ::= { sonusSoftswitchPesTMAlternateRouteSKIPTgCountersBlockedTable 1 }

SonusSoftswitchPesTMAlternateRouteSKIPTgCountersBlockedEntry ::=
    SEQUENCE {
        sonusSoftswitchPesTMAlternateRouteSKIPTgCountersBlockedEntity                             SonusName,
        sonusSoftswitchPesTMAlternateRouteSKIPTgCountersBlockedEntity2                              SonusName,
        sonusSoftswitchPesTMAlternateRouteSKIPTgCountersBlockedValue                            Counter,
        sonusSoftSwitchPesTMAlternateRouteSKIPTgBlockedIntervalTime                           TimeTicks
    }

sonusSoftswitchPesTMAlternateRouteSKIPTgCountersBlockedEntity OBJECT-TYPE
    SYNTAX          SonusName
    ACCESS          read-only
    STATUS          deprecated
    DESCRIPTION     
            "Entity Id (trunkgroup id) for trunkgroup with SKIP (AR) traffic control"
    ::= { sonusSoftswitchPesTMAlternateRouteSKIPTgCountersBlockedEntry 1 }

sonusSoftswitchPesTMAlternateRouteSKIPTgCountersBlockedEntity2 OBJECT-TYPE
    SYNTAX          SonusName
    ACCESS          read-only
    STATUS          deprecated
    DESCRIPTION     
            "Entity Id2 (gateway id) for trunkgrop with SKIP (AR) traffic control"
    ::= { sonusSoftswitchPesTMAlternateRouteSKIPTgCountersBlockedEntry 2 }

sonusSoftswitchPesTMAlternateRouteSKIPTgCountersBlockedValue OBJECT-TYPE
    SYNTAX          Counter
    ACCESS          read-only
    STATUS          deprecated
    DESCRIPTION     
            "Number of skipped calls to trunkgroup with SKIP (AR) traffic control"
    ::= { sonusSoftswitchPesTMAlternateRouteSKIPTgCountersBlockedEntry 3 }

sonusSoftSwitchPesTMAlternateRouteSKIPTgBlockedIntervalTime OBJECT-TYPE
    SYNTAX          TimeTicks
    ACCESS          read-only
    STATUS          mandatory
    DESCRIPTION     
            "This variable contains the end of interval time stamp for 
             the specified interval."
    ::= { sonusSoftswitchPesTMAlternateRouteSKIPTgCountersBlockedEntry 4 }

sonusSoftswitchPesTMDirectRouteSKIPTgCounters OBJECT IDENTIFIER
    ::= { sonusSoftSwitchPesTrafficMgmtCounters 4 }

sonusSoftswitchPesTMDirectRouteSKIPTgCountersAllowedTable OBJECT-TYPE
    SYNTAX          SEQUENCE OF SonusSoftswitchPesTMDirectRouteSKIPTgCountersAllowedEntry
    ACCESS          not-accessible
    STATUS          deprecated
    DESCRIPTION     
            "The Traffic Management related counters for SKIP (Direct) trunkgroup"
    ::= { sonusSoftswitchPesTMDirectRouteSKIPTgCounters 1 }

sonusSoftswitchPesTMDirectRouteSKIPTgCountersAllowedEntry OBJECT-TYPE
    SYNTAX          SonusSoftswitchPesTMDirectRouteSKIPTgCountersAllowedEntry
    ACCESS          not-accessible
    STATUS          deprecated
    DESCRIPTION     
            "The Traffic Management related counters for SKIP (Direct) trunkgroup"
    INDEX           { 
                      sonusSoftswitchPesTMDirectRouteSKIPTgCountersAllowedEntity, 
                      sonusSoftswitchPesTMDirectRouteSKIPTgCountersAllowedEntity2 }
    ::= { sonusSoftswitchPesTMDirectRouteSKIPTgCountersAllowedTable 1 }

SonusSoftswitchPesTMDirectRouteSKIPTgCountersAllowedEntry ::=
    SEQUENCE {
        sonusSoftswitchPesTMDirectRouteSKIPTgCountersAllowedEntity                          SonusName,
        sonusSoftswitchPesTMDirectRouteSKIPTgCountersAllowedEntity2                           SonusName,
        sonusSoftswitchPesTMDirectRouteSKIPTgCountersAllowedValue                         Counter,
        sonusSoftSwitchPesTMDirectRouteSKIPTgAllowedIntervalTime                        TimeTicks
    }

sonusSoftswitchPesTMDirectRouteSKIPTgCountersAllowedEntity OBJECT-TYPE
    SYNTAX          SonusName
    ACCESS          read-only
    STATUS          deprecated
    DESCRIPTION     
            "Entity Id (trunkgroup id) for trunkgroup with SKIP (DR) traffic control"
    ::= { sonusSoftswitchPesTMDirectRouteSKIPTgCountersAllowedEntry 1 }

sonusSoftswitchPesTMDirectRouteSKIPTgCountersAllowedEntity2 OBJECT-TYPE
    SYNTAX          SonusName
    ACCESS          read-only
    STATUS          deprecated
    DESCRIPTION     
            "Entity Id2 (gateway id) for trunkgrop with SKIP (DR) traffic control"
    ::= { sonusSoftswitchPesTMDirectRouteSKIPTgCountersAllowedEntry 2 }

sonusSoftswitchPesTMDirectRouteSKIPTgCountersAllowedValue OBJECT-TYPE
    SYNTAX          Counter
    ACCESS          read-only
    STATUS          deprecated
    DESCRIPTION     
            "Number of allowed calls to trunkgroup with SKIP (DR) traffic control"
    ::= { sonusSoftswitchPesTMDirectRouteSKIPTgCountersAllowedEntry 3 }

sonusSoftSwitchPesTMDirectRouteSKIPTgAllowedIntervalTime OBJECT-TYPE
    SYNTAX          TimeTicks
    ACCESS          read-only
    STATUS          mandatory
    DESCRIPTION     
            "This variable contains the end of interval time stamp for 
             the specified interval."
    ::= { sonusSoftswitchPesTMDirectRouteSKIPTgCountersAllowedEntry 4 }

sonusSoftswitchPesTMDirectRouteSKIPTgCountersBlockedTable OBJECT-TYPE
    SYNTAX          SEQUENCE OF SonusSoftswitchPesTMDirectRouteSKIPTgCountersBlockedEntry
    ACCESS          not-accessible
    STATUS          deprecated
    DESCRIPTION     
            "The Traffic Management related counters for SKIP (Direct) trunkgroup"
    ::= { sonusSoftswitchPesTMDirectRouteSKIPTgCounters 2 }

sonusSoftswitchPesTMDirectRouteSKIPTgCountersBlockedEntry OBJECT-TYPE
    SYNTAX          SonusSoftswitchPesTMDirectRouteSKIPTgCountersBlockedEntry
    ACCESS          not-accessible
    STATUS          deprecated
    DESCRIPTION     
            "The Traffic Management related counters for SKIP (Direct) trunkgroup"
    INDEX           { 
                      sonusSoftswitchPesTMDirectRouteSKIPTgCountersBlockedEntity, 
                      sonusSoftswitchPesTMDirectRouteSKIPTgCountersBlockedEntity2 }
    ::= { sonusSoftswitchPesTMDirectRouteSKIPTgCountersBlockedTable 1 }

SonusSoftswitchPesTMDirectRouteSKIPTgCountersBlockedEntry ::=
    SEQUENCE {
        sonusSoftswitchPesTMDirectRouteSKIPTgCountersBlockedEntity                          SonusName,
        sonusSoftswitchPesTMDirectRouteSKIPTgCountersBlockedEntity2                           SonusName,
        sonusSoftswitchPesTMDirectRouteSKIPTgCountersBlockedValue                         Counter,
        sonusSoftSwitchPesTMDirectRouteSKIPTgBlockedIntervalTime                        TimeTicks
    }

sonusSoftswitchPesTMDirectRouteSKIPTgCountersBlockedEntity OBJECT-TYPE
    SYNTAX          SonusName
    ACCESS          read-only
    STATUS          deprecated
    DESCRIPTION     
            "Entity Id (trunkgroup id) for trunkgroup with SKIP (DR) traffic control"
    ::= { sonusSoftswitchPesTMDirectRouteSKIPTgCountersBlockedEntry 1 }

sonusSoftswitchPesTMDirectRouteSKIPTgCountersBlockedEntity2 OBJECT-TYPE
    SYNTAX          SonusName
    ACCESS          read-only
    STATUS          deprecated
    DESCRIPTION     
            "Entity Id2 (gateway id) for trunkgrop with SKIP (DR) traffic control"
    ::= { sonusSoftswitchPesTMDirectRouteSKIPTgCountersBlockedEntry 2 }

sonusSoftswitchPesTMDirectRouteSKIPTgCountersBlockedValue OBJECT-TYPE
    SYNTAX          Counter
    ACCESS          read-only
    STATUS          deprecated
    DESCRIPTION     
            "Number of skipped calls to trunkgroup with SKIP (DR) traffic control"
    ::= { sonusSoftswitchPesTMDirectRouteSKIPTgCountersBlockedEntry 3 }

sonusSoftSwitchPesTMDirectRouteSKIPTgBlockedIntervalTime OBJECT-TYPE
    SYNTAX          TimeTicks
    ACCESS          read-only
    STATUS          mandatory
    DESCRIPTION     
            "This variable contains the end of interval time stamp for 
             the specified interval."
    ::= { sonusSoftswitchPesTMDirectRouteSKIPTgCountersBlockedEntry 4 }

sonusSoftswitchPesTMDirectRouteCANTTgCounters OBJECT IDENTIFIER
    ::= { sonusSoftSwitchPesTrafficMgmtCounters 5 }

sonusSoftswitchPesTMDirectRouteCANTTgCountersAllowedTable OBJECT-TYPE
    SYNTAX          SEQUENCE OF SonusSoftswitchPesTMDirectRouteCANTTgCountersAllowedEntry
    ACCESS          not-accessible
    STATUS          deprecated
    DESCRIPTION     
            "The Traffic Management related counters for CANT (Direct) trunkgroup"
    ::= { sonusSoftswitchPesTMDirectRouteCANTTgCounters 1 }

sonusSoftswitchPesTMDirectRouteCANTTgCountersAllowedEntry OBJECT-TYPE
    SYNTAX          SonusSoftswitchPesTMDirectRouteCANTTgCountersAllowedEntry
    ACCESS          not-accessible
    STATUS          deprecated
    DESCRIPTION     
            "The Traffic Management related counters for CANT (Direct) trunkgroup"
    INDEX           { 
                      sonusSoftswitchPesTMDirectRouteCANTTgCountersAllowedEntity, 
                      sonusSoftswitchPesTMDirectRouteCANTTgCountersAllowedEntity2 }
    ::= { sonusSoftswitchPesTMDirectRouteCANTTgCountersAllowedTable 1 }

SonusSoftswitchPesTMDirectRouteCANTTgCountersAllowedEntry ::=
    SEQUENCE {
        sonusSoftswitchPesTMDirectRouteCANTTgCountersAllowedEntity                          SonusName,
        sonusSoftswitchPesTMDirectRouteCANTTgCountersAllowedEntity2                           SonusName,
        sonusSoftswitchPesTMDirectRouteCANTTgCountersAllowedValue                         Counter,
        sonusSoftSwitchPesTMDirectRouteCANTTgAllowedIntervalTime                        TimeTicks
    }

sonusSoftswitchPesTMDirectRouteCANTTgCountersAllowedEntity OBJECT-TYPE
    SYNTAX          SonusName
    ACCESS          read-only
    STATUS          deprecated
    DESCRIPTION     
            "Entity Id (trunkgroup id) for trunkgroup with CANT (DR) traffic control"
    ::= { sonusSoftswitchPesTMDirectRouteCANTTgCountersAllowedEntry 1 }

sonusSoftswitchPesTMDirectRouteCANTTgCountersAllowedEntity2 OBJECT-TYPE
    SYNTAX          SonusName
    ACCESS          read-only
    STATUS          deprecated
    DESCRIPTION     
            "Entity Id2 (gateway id) for trunkgrop with CANT (DR) traffic control"
    ::= { sonusSoftswitchPesTMDirectRouteCANTTgCountersAllowedEntry 2 }

sonusSoftswitchPesTMDirectRouteCANTTgCountersAllowedValue OBJECT-TYPE
    SYNTAX          Counter
    ACCESS          read-only
    STATUS          deprecated
    DESCRIPTION     
            "Number of allowed calls to trunkgroup with CANT (DR) traffic control"
    ::= { sonusSoftswitchPesTMDirectRouteCANTTgCountersAllowedEntry 3 }

sonusSoftSwitchPesTMDirectRouteCANTTgAllowedIntervalTime OBJECT-TYPE
    SYNTAX          TimeTicks
    ACCESS          read-only
    STATUS          mandatory
    DESCRIPTION     
            "This variable contains the end of interval time stamp for 
             the specified interval."
    ::= { sonusSoftswitchPesTMDirectRouteCANTTgCountersAllowedEntry 4 }

sonusSoftswitchPesTMDirectRouteCANTTgCountersBlockedTable OBJECT-TYPE
    SYNTAX          SEQUENCE OF SonusSoftswitchPesTMDirectRouteCANTTgCountersBlockedEntry
    ACCESS          not-accessible
    STATUS          deprecated
    DESCRIPTION     
            "The Traffic Management related counters for CANT (Direct) trunkgroup"
    ::= { sonusSoftswitchPesTMDirectRouteCANTTgCounters 2 }

sonusSoftswitchPesTMDirectRouteCANTTgCountersBlockedEntry OBJECT-TYPE
    SYNTAX          SonusSoftswitchPesTMDirectRouteCANTTgCountersBlockedEntry
    ACCESS          not-accessible
    STATUS          deprecated
    DESCRIPTION     
            "The Traffic Management related counters for CANT (Direct) trunkgroup"
    INDEX           { 
                      sonusSoftswitchPesTMDirectRouteCANTTgCountersBlockedEntity, 
                      sonusSoftswitchPesTMDirectRouteCANTTgCountersBlockedEntity2 }
    ::= { sonusSoftswitchPesTMDirectRouteCANTTgCountersBlockedTable 1 }

SonusSoftswitchPesTMDirectRouteCANTTgCountersBlockedEntry ::=
    SEQUENCE {
        sonusSoftswitchPesTMDirectRouteCANTTgCountersBlockedEntity                          SonusName,
        sonusSoftswitchPesTMDirectRouteCANTTgCountersBlockedEntity2                           SonusName,
        sonusSoftswitchPesTMDirectRouteCANTTgCountersBlockedValue                         Counter,
        sonusSoftSwitchPesTMDirectRouteCANTTgBlockedIntervalTime                        TimeTicks
    }

sonusSoftswitchPesTMDirectRouteCANTTgCountersBlockedEntity OBJECT-TYPE
    SYNTAX          SonusName
    ACCESS          read-only
    STATUS          deprecated
    DESCRIPTION     
            "Entity Id (trunkgroup id) for trunkgroup with CANT (DR) traffic control"
    ::= { sonusSoftswitchPesTMDirectRouteCANTTgCountersBlockedEntry 1 }

sonusSoftswitchPesTMDirectRouteCANTTgCountersBlockedEntity2 OBJECT-TYPE
    SYNTAX          SonusName
    ACCESS          read-only
    STATUS          deprecated
    DESCRIPTION     
            "Entity Id2 (gateway id) for trunkgrop with CANT (DR) traffic control"
    ::= { sonusSoftswitchPesTMDirectRouteCANTTgCountersBlockedEntry 2 }

sonusSoftswitchPesTMDirectRouteCANTTgCountersBlockedValue OBJECT-TYPE
    SYNTAX          Counter
    ACCESS          read-only
    STATUS          deprecated
    DESCRIPTION     
            "Number of blocked calls to trunkgroup with CANT (DR) traffic control"
    ::= { sonusSoftswitchPesTMDirectRouteCANTTgCountersBlockedEntry 3 }

sonusSoftSwitchPesTMDirectRouteCANTTgBlockedIntervalTime OBJECT-TYPE
    SYNTAX          TimeTicks
    ACCESS          read-only
    STATUS          mandatory
    DESCRIPTION     
            "This variable contains the end of interval time stamp for 
             the specified interval."
    ::= { sonusSoftswitchPesTMDirectRouteCANTTgCountersBlockedEntry 4 }

sonusSoftswitchPesTMOriginationCounters OBJECT IDENTIFIER
    ::= { sonusSoftSwitchPesTrafficMgmtCounters 6 }

sonusSoftswitchPesTMOriginationCountersAllowedTable OBJECT-TYPE
    SYNTAX          SEQUENCE OF SonusSoftswitchPesTMOriginationCountersAllowedEntry
    ACCESS          not-accessible
    STATUS          mandatory
    DESCRIPTION     
            "The number of calls for which a origination number with 
             a provisioned Traffic control was allowed to complete."
    ::= { sonusSoftswitchPesTMOriginationCounters 1 }

sonusSoftswitchPesTMOriginationCountersAllowedEntry OBJECT-TYPE
    SYNTAX          SonusSoftswitchPesTMOriginationCountersAllowedEntry
    ACCESS          not-accessible
    STATUS          mandatory
    DESCRIPTION     
            "The number of calls for which a origination number with 
             a provisioned Traffic control was allowed to complete."
    INDEX           { 
                      sonusSoftswitchPesTMOriginationCountersAllowedEntity, 
                      sonusSoftswitchPesTMOriginationCountersAllowedEntity2 }
    ::= { sonusSoftswitchPesTMOriginationCountersAllowedTable 1 }

SonusSoftswitchPesTMOriginationCountersAllowedEntry ::=
    SEQUENCE {
        sonusSoftswitchPesTMOriginationCountersAllowedEntity                    SonusName,
        sonusSoftswitchPesTMOriginationCountersAllowedEntity2                     SonusName,
        sonusSoftswitchPesTMOriginationCountersAllowedValue                   Counter,
        sonusSoftSwitchPesTMOriginationAllowedIntervalTime                  TimeTicks
    }

sonusSoftswitchPesTMOriginationCountersAllowedEntity OBJECT-TYPE
    SYNTAX          SonusName
    ACCESS          read-only
    STATUS          mandatory
    DESCRIPTION     
            "Entity Id (national number) for origination with traffic control"
    ::= { sonusSoftswitchPesTMOriginationCountersAllowedEntry 1 }

sonusSoftswitchPesTMOriginationCountersAllowedEntity2 OBJECT-TYPE
    SYNTAX          SonusName
    ACCESS          read-only
    STATUS          mandatory
    DESCRIPTION     
            "Entity Id2 (country id) for origination with traffic control"
    ::= { sonusSoftswitchPesTMOriginationCountersAllowedEntry 2 }

sonusSoftswitchPesTMOriginationCountersAllowedValue OBJECT-TYPE
    SYNTAX          Counter
    ACCESS          read-only
    STATUS          mandatory
    DESCRIPTION     
            "Number of allowed calls from origination with traffic control"
    ::= { sonusSoftswitchPesTMOriginationCountersAllowedEntry 3 }

sonusSoftSwitchPesTMOriginationAllowedIntervalTime OBJECT-TYPE
    SYNTAX          TimeTicks
    ACCESS          read-only
    STATUS          obsolete
    DESCRIPTION     
            "This variable contains the end of interval time stamp for 
             the specified interval."
    ::= { sonusSoftswitchPesTMOriginationCountersAllowedEntry 4 }

sonusSoftswitchPesTMOriginationCountersBlockedTable OBJECT-TYPE
    SYNTAX          SEQUENCE OF SonusSoftswitchPesTMOriginationCountersBlockedEntry
    ACCESS          not-accessible
    STATUS          mandatory
    DESCRIPTION     
            "The number of calls for which a origination number with 
             a provisioned Traffic control was blocked."
    ::= { sonusSoftswitchPesTMOriginationCounters 2 }

sonusSoftswitchPesTMOriginationCountersBlockedEntry OBJECT-TYPE
    SYNTAX          SonusSoftswitchPesTMOriginationCountersBlockedEntry
    ACCESS          not-accessible
    STATUS          mandatory
    DESCRIPTION     
            "The number of calls for which a origination number with 
             a provisioned Traffic control was blocked."
    INDEX           { 
                      sonusSoftswitchPesTMOriginationCountersBlockedEntity, 
                      sonusSoftswitchPesTMOriginationCountersBlockedEntity2 }
    ::= { sonusSoftswitchPesTMOriginationCountersBlockedTable 1 }

SonusSoftswitchPesTMOriginationCountersBlockedEntry ::=
    SEQUENCE {
        sonusSoftswitchPesTMOriginationCountersBlockedEntity                    SonusName,
        sonusSoftswitchPesTMOriginationCountersBlockedEntity2                     SonusName,
        sonusSoftswitchPesTMOriginationCountersBlockedValue                   Counter,
        sonusSoftSwitchPesTMOriginationBlockedIntervalTime                  TimeTicks
    }

sonusSoftswitchPesTMOriginationCountersBlockedEntity OBJECT-TYPE
    SYNTAX          SonusName
    ACCESS          read-only
    STATUS          mandatory
    DESCRIPTION     
            "Entity Id (national number) for origination with traffic control"
    ::= { sonusSoftswitchPesTMOriginationCountersBlockedEntry 1 }

sonusSoftswitchPesTMOriginationCountersBlockedEntity2 OBJECT-TYPE
    SYNTAX          SonusName
    ACCESS          read-only
    STATUS          mandatory
    DESCRIPTION     
            "Entity Id2 (country id) for origination with traffic control"
    ::= { sonusSoftswitchPesTMOriginationCountersBlockedEntry 2 }

sonusSoftswitchPesTMOriginationCountersBlockedValue OBJECT-TYPE
    SYNTAX          Counter
    ACCESS          read-only
    STATUS          mandatory
    DESCRIPTION     
            "Number of blocked calls from origination with traffic control"
    ::= { sonusSoftswitchPesTMOriginationCountersBlockedEntry 3 }

sonusSoftSwitchPesTMOriginationBlockedIntervalTime OBJECT-TYPE
    SYNTAX          TimeTicks
    ACCESS          read-only
    STATUS          obsolete
    DESCRIPTION     
            "This variable contains the end of interval time stamp for 
             the specified interval."
    ::= { sonusSoftswitchPesTMOriginationCountersBlockedEntry 4 }

sonusSoftswitchPesTMFinalCallingNumberCounters OBJECT IDENTIFIER
    ::= { sonusSoftSwitchPesTrafficMgmtCounters 7 }

sonusSoftswitchPesTMFinalCallingNumberCountersAllowedTable OBJECT-TYPE
    SYNTAX          SEQUENCE OF SonusSoftswitchPesTMFinalCallingNumberCountersAllowedEntry
    ACCESS          not-accessible
    STATUS          mandatory
    DESCRIPTION     
            "The Traffic Management related counters for allowed final calling number."
    ::= { sonusSoftswitchPesTMFinalCallingNumberCounters 1 }

sonusSoftswitchPesTMFinalCallingNumberCountersAllowedEntry OBJECT-TYPE
    SYNTAX          SonusSoftswitchPesTMFinalCallingNumberCountersAllowedEntry
    ACCESS          not-accessible
    STATUS          mandatory
    DESCRIPTION     
            "The Traffic Management related counters for allowed final calling number."
    INDEX           { 
                      sonusSoftswitchPesTMFinalCallingNumberCountersAllowedEntity, 
                      sonusSoftswitchPesTMFinalCallingNumberCountersAllowedEntity2 }
    ::= { sonusSoftswitchPesTMFinalCallingNumberCountersAllowedTable 1 }

SonusSoftswitchPesTMFinalCallingNumberCountersAllowedEntry ::=
    SEQUENCE {
        sonusSoftswitchPesTMFinalCallingNumberCountersAllowedEntity                           SonusName,
        sonusSoftswitchPesTMFinalCallingNumberCountersAllowedEntity2                            SonusName,
        sonusSoftswitchPesTMFinalCallingNumberCountersAllowedValue                          Counter,
        sonusSoftSwitchPesTMFinalCallingNumberAllowedIntervalTime                         TimeTicks
    }

sonusSoftswitchPesTMFinalCallingNumberCountersAllowedEntity OBJECT-TYPE
    SYNTAX          SonusName
    ACCESS          read-only
    STATUS          mandatory
    DESCRIPTION     
            "Entity Id (national number) for final calling number with traffic control"
    ::= { sonusSoftswitchPesTMFinalCallingNumberCountersAllowedEntry 1 }

sonusSoftswitchPesTMFinalCallingNumberCountersAllowedEntity2 OBJECT-TYPE
    SYNTAX          SonusName
    ACCESS          read-only
    STATUS          mandatory
    DESCRIPTION     
            "Entity Id2 (country id) for final calling number with traffic control"
    ::= { sonusSoftswitchPesTMFinalCallingNumberCountersAllowedEntry 2 }

sonusSoftswitchPesTMFinalCallingNumberCountersAllowedValue OBJECT-TYPE
    SYNTAX          Counter
    ACCESS          read-only
    STATUS          mandatory
    DESCRIPTION     
            "Number of allowed calls from final calling number with traffic control"
    ::= { sonusSoftswitchPesTMFinalCallingNumberCountersAllowedEntry 3 }

sonusSoftSwitchPesTMFinalCallingNumberAllowedIntervalTime OBJECT-TYPE
    SYNTAX          TimeTicks
    ACCESS          read-only
    STATUS          obsolete
    DESCRIPTION     
            "This variable contains the end of interval time stamp for 
             the specified interval."
    ::= { sonusSoftswitchPesTMFinalCallingNumberCountersAllowedEntry 4 }

sonusSoftswitchPesTMFinalCallingNumberCountersBlockedTable OBJECT-TYPE
    SYNTAX          SEQUENCE OF SonusSoftswitchPesTMFinalCallingNumberCountersBlockedEntry
    ACCESS          not-accessible
    STATUS          mandatory
    DESCRIPTION     
            "The Traffic Management related counters for blocked final calling number."
    ::= { sonusSoftswitchPesTMFinalCallingNumberCounters 2 }

sonusSoftswitchPesTMFinalCallingNumberCountersBlockedEntry OBJECT-TYPE
    SYNTAX          SonusSoftswitchPesTMFinalCallingNumberCountersBlockedEntry
    ACCESS          not-accessible
    STATUS          mandatory
    DESCRIPTION     
            "The Traffic Management related counters for blocked final calling number."
    INDEX           { 
                      sonusSoftswitchPesTMFinalCallingNumberCountersBlockedEntity, 
                      sonusSoftswitchPesTMFinalCallingNumberCountersBlockedEntity2 }
    ::= { sonusSoftswitchPesTMFinalCallingNumberCountersBlockedTable 1 }

SonusSoftswitchPesTMFinalCallingNumberCountersBlockedEntry ::=
    SEQUENCE {
        sonusSoftswitchPesTMFinalCallingNumberCountersBlockedEntity                           SonusName,
        sonusSoftswitchPesTMFinalCallingNumberCountersBlockedEntity2                            SonusName,
        sonusSoftswitchPesTMFinalCallingNumberCountersBlockedValue                          Counter,
        sonusSoftSwitchPesTMFinalCallingNumberBlockedIntervalTime                         TimeTicks
    }

sonusSoftswitchPesTMFinalCallingNumberCountersBlockedEntity OBJECT-TYPE
    SYNTAX          SonusName
    ACCESS          read-only
    STATUS          mandatory
    DESCRIPTION     
            "Entity Id (national number) for final calling number with traffic control"
    ::= { sonusSoftswitchPesTMFinalCallingNumberCountersBlockedEntry 1 }

sonusSoftswitchPesTMFinalCallingNumberCountersBlockedEntity2 OBJECT-TYPE
    SYNTAX          SonusName
    ACCESS          read-only
    STATUS          mandatory
    DESCRIPTION     
            "Entity Id2 (country id) for final calling number with traffic control"
    ::= { sonusSoftswitchPesTMFinalCallingNumberCountersBlockedEntry 2 }

sonusSoftswitchPesTMFinalCallingNumberCountersBlockedValue OBJECT-TYPE
    SYNTAX          Counter
    ACCESS          read-only
    STATUS          mandatory
    DESCRIPTION     
            "Number of blocked calls from final calling number with traffic control"
    ::= { sonusSoftswitchPesTMFinalCallingNumberCountersBlockedEntry 3 }

sonusSoftSwitchPesTMFinalCallingNumberBlockedIntervalTime OBJECT-TYPE
    SYNTAX          TimeTicks
    ACCESS          read-only
    STATUS          obsolete
    DESCRIPTION     
            "This variable contains the end of interval time stamp for 
             the specified interval."
    ::= { sonusSoftswitchPesTMFinalCallingNumberCountersBlockedEntry 4 }

sonusSoftswitchPesTMFinalDestinationCounters OBJECT IDENTIFIER
    ::= { sonusSoftSwitchPesTrafficMgmtCounters 8 }

sonusSoftswitchPesTMFinalDestinationCountersAllowedTable OBJECT-TYPE
    SYNTAX          SEQUENCE OF SonusSoftswitchPesTMFinalDestinationCountersAllowedEntry
    ACCESS          not-accessible
    STATUS          mandatory
    DESCRIPTION     
            "The Traffic Management related counters for allowed final destination number."
    ::= { sonusSoftswitchPesTMFinalDestinationCounters 1 }

sonusSoftswitchPesTMFinalDestinationCountersAllowedEntry OBJECT-TYPE
    SYNTAX          SonusSoftswitchPesTMFinalDestinationCountersAllowedEntry
    ACCESS          not-accessible
    STATUS          mandatory
    DESCRIPTION     
            "The Traffic Management related counters for allowed final destination number."
    INDEX           { 
                      sonusSoftswitchPesTMFinalDestinationCountersAllowedEntity, 
                      sonusSoftswitchPesTMFinalDestinationCountersAllowedEntity2, 
                      sonusSoftswitchPesTMFinalDestinationCountersAllowedEntityType }
    ::= { sonusSoftswitchPesTMFinalDestinationCountersAllowedTable 1 }

SonusSoftswitchPesTMFinalDestinationCountersAllowedEntry ::=
    SEQUENCE {
        sonusSoftswitchPesTMFinalDestinationCountersAllowedEntity                         SonusName,
        sonusSoftswitchPesTMFinalDestinationCountersAllowedEntity2                          SonusName,
        sonusSoftswitchPesTMFinalDestinationCountersAllowedEntityType                             INTEGER,
        sonusSoftswitchPesTMFinalDestinationCountersAllowedValue                        Counter,
        sonusSoftSwitchPesTMFinalDestinationAllowedIntervalTime                       TimeTicks
    }

sonusSoftswitchPesTMFinalDestinationCountersAllowedEntity OBJECT-TYPE
    SYNTAX          SonusName
    ACCESS          read-only
    STATUS          mandatory
    DESCRIPTION     
            "Entity Id (national number) for final destination number with traffic control"
    ::= { sonusSoftswitchPesTMFinalDestinationCountersAllowedEntry 1 }

sonusSoftswitchPesTMFinalDestinationCountersAllowedEntity2 OBJECT-TYPE
    SYNTAX          SonusName
    ACCESS          read-only
    STATUS          mandatory
    DESCRIPTION     
            "Entity Id2 (country id) for final destination number with traffic control"
    ::= { sonusSoftswitchPesTMFinalDestinationCountersAllowedEntry 2 }

sonusSoftswitchPesTMFinalDestinationCountersAllowedEntityType OBJECT-TYPE
    SYNTAX          INTEGER { routingLabel(1), callingNumber(2), 
                        calledNumber(3) }
    ACCESS          read-only
    STATUS          mandatory
    DESCRIPTION     
            "Call Processing entity type to identify source of final destination allowed counter"
    ::= { sonusSoftswitchPesTMFinalDestinationCountersAllowedEntry 3 }

sonusSoftswitchPesTMFinalDestinationCountersAllowedValue OBJECT-TYPE
    SYNTAX          Counter
    ACCESS          read-only
    STATUS          mandatory
    DESCRIPTION     
            "Number of allowed calls to final destination number with traffic control"
    ::= { sonusSoftswitchPesTMFinalDestinationCountersAllowedEntry 4 }

sonusSoftSwitchPesTMFinalDestinationAllowedIntervalTime OBJECT-TYPE
    SYNTAX          TimeTicks
    ACCESS          read-only
    STATUS          obsolete
    DESCRIPTION     
            "This variable contains the end of interval time stamp for 
             the specified interval."
    ::= { sonusSoftswitchPesTMFinalDestinationCountersAllowedEntry 5 }

sonusSoftswitchPesTMFinalDestinationCountersBlockedTable OBJECT-TYPE
    SYNTAX          SEQUENCE OF SonusSoftswitchPesTMFinalDestinationCountersBlockedEntry
    ACCESS          not-accessible
    STATUS          mandatory
    DESCRIPTION     
            "The Traffic Management related counters for blocked final destination number."
    ::= { sonusSoftswitchPesTMFinalDestinationCounters 2 }

sonusSoftswitchPesTMFinalDestinationCountersBlockedEntry OBJECT-TYPE
    SYNTAX          SonusSoftswitchPesTMFinalDestinationCountersBlockedEntry
    ACCESS          not-accessible
    STATUS          mandatory
    DESCRIPTION     
            "The Traffic Management related counters for blocked final destination number."
    INDEX           { 
                      sonusSoftswitchPesTMFinalDestinationCountersBlockedEntity, 
                      sonusSoftswitchPesTMFinalDestinationCountersBlockedEntity2, 
                      sonusSoftswitchPesTMFinalDestinationCountersBlockedEntityType }
    ::= { sonusSoftswitchPesTMFinalDestinationCountersBlockedTable 1 }

SonusSoftswitchPesTMFinalDestinationCountersBlockedEntry ::=
    SEQUENCE {
        sonusSoftswitchPesTMFinalDestinationCountersBlockedEntity                         SonusName,
        sonusSoftswitchPesTMFinalDestinationCountersBlockedEntity2                          SonusName,
        sonusSoftswitchPesTMFinalDestinationCountersBlockedEntityType                             INTEGER,
        sonusSoftswitchPesTMFinalDestinationCountersBlockedValue                        Counter,
        sonusSoftSwitchPesTMFinalDestinationBlockedIntervalTime                       TimeTicks
    }

sonusSoftswitchPesTMFinalDestinationCountersBlockedEntity OBJECT-TYPE
    SYNTAX          SonusName
    ACCESS          read-only
    STATUS          mandatory
    DESCRIPTION     
            "Entity Id (national number) for final destination number with traffic control"
    ::= { sonusSoftswitchPesTMFinalDestinationCountersBlockedEntry 1 }

sonusSoftswitchPesTMFinalDestinationCountersBlockedEntity2 OBJECT-TYPE
    SYNTAX          SonusName
    ACCESS          read-only
    STATUS          mandatory
    DESCRIPTION     
            "Entity Id2 (country id) for final destination number with traffic control"
    ::= { sonusSoftswitchPesTMFinalDestinationCountersBlockedEntry 2 }

sonusSoftswitchPesTMFinalDestinationCountersBlockedEntityType OBJECT-TYPE
    SYNTAX          INTEGER { routingLabel(1), callingNumber(2), 
                        calledNumber(3) }
    ACCESS          read-only
    STATUS          mandatory
    DESCRIPTION     
            "Call Processing entity type to identify source of final destination counter"
    ::= { sonusSoftswitchPesTMFinalDestinationCountersBlockedEntry 3 }

sonusSoftswitchPesTMFinalDestinationCountersBlockedValue OBJECT-TYPE
    SYNTAX          Counter
    ACCESS          read-only
    STATUS          mandatory
    DESCRIPTION     
            "Number of blocked calls to final destination number with traffic control"
    ::= { sonusSoftswitchPesTMFinalDestinationCountersBlockedEntry 4 }

sonusSoftSwitchPesTMFinalDestinationBlockedIntervalTime OBJECT-TYPE
    SYNTAX          TimeTicks
    ACCESS          read-only
    STATUS          obsolete
    DESCRIPTION     
            "This variable contains the end of interval time stamp for 
             the specified interval."
    ::= { sonusSoftswitchPesTMFinalDestinationCountersBlockedEntry 5 }

sonusSoftswitchPesTMHpcExemptionCounters OBJECT IDENTIFIER
    ::= { sonusSoftSwitchPesTrafficMgmtCounters 9 }

sonusSoftSwitchPesTMHpcExemptionCountersGsxTable OBJECT-TYPE
    SYNTAX          SEQUENCE OF SonusSoftSwitchPesTMHpcExemptionCountersGsxEntry
    ACCESS          not-accessible
    STATUS          mandatory
    DESCRIPTION     
            "The Traffic Management HPC Exemption related counters per GSX table."
    ::= { sonusSoftswitchPesTMHpcExemptionCounters 1 }

sonusSoftSwitchPesTMHpcExemptionCountersGsxEntry OBJECT-TYPE
    SYNTAX          SonusSoftSwitchPesTMHpcExemptionCountersGsxEntry
    ACCESS          not-accessible
    STATUS          mandatory
    DESCRIPTION     
            "An entry in the Traffic Management HPC Exemption counters per GSX table."
    INDEX           { sonusSoftSwitchPesTMHpcExemptionCountersGsxIp }
    ::= { sonusSoftSwitchPesTMHpcExemptionCountersGsxTable 1 }

SonusSoftSwitchPesTMHpcExemptionCountersGsxEntry ::=
    SEQUENCE {
        sonusSoftSwitchPesTMHpcExemptionCountersGsxIp             IpAddress,
        sonusSoftSwitchPesTMHpcExemptionCountersGsxName               SonusName,
        sonusSoftSwitchPesTMHpcExemptionCountersGsxExemptedCalls                        Counter,
        sonusSoftSwitchPesTMHpcExemptionCountersGsxIntervalTime                       TimeTicks
    }

sonusSoftSwitchPesTMHpcExemptionCountersGsxIp OBJECT-TYPE
    SYNTAX          IpAddress
    ACCESS          read-only
    STATUS          mandatory
    DESCRIPTION     
            "The GSX IP Address that the Traffic Management HPC Exemption counters apply to"
    ::= { sonusSoftSwitchPesTMHpcExemptionCountersGsxEntry 1 }

sonusSoftSwitchPesTMHpcExemptionCountersGsxName OBJECT-TYPE
    SYNTAX          SonusName
    ACCESS          read-only
    STATUS          mandatory
    DESCRIPTION     
            "The GSX Name that the Traffic Management HPC Exemption counters apply to"
    ::= { sonusSoftSwitchPesTMHpcExemptionCountersGsxEntry 2 }

sonusSoftSwitchPesTMHpcExemptionCountersGsxExemptedCalls OBJECT-TYPE
    SYNTAX          Counter
    ACCESS          read-only
    STATUS          mandatory
    DESCRIPTION     
            "The Traffic Management HPC Exemption counters per GSX count exempted calls 
             that are traffic control exempted for any reason AND HPC call."
    ::= { sonusSoftSwitchPesTMHpcExemptionCountersGsxEntry 3 }

sonusSoftSwitchPesTMHpcExemptionCountersGsxIntervalTime OBJECT-TYPE
    SYNTAX          TimeTicks
    ACCESS          read-only
    STATUS          mandatory
    DESCRIPTION     
            "This variable contains the time stamp when the data is collected."
    ::= { sonusSoftSwitchPesTMHpcExemptionCountersGsxEntry 4 }

sonusSoftswitchPesTMContractorBasedOriginationCounters OBJECT IDENTIFIER
    ::= { sonusSoftSwitchPesTrafficMgmtCounters 10 }

sonusSoftswitchPesTMContractorBasedOriginationCountersAllowedTable OBJECT-TYPE
    SYNTAX          SEQUENCE OF SonusSoftswitchPesTMContractorBasedOriginationCountersAllowedEntry
    ACCESS          not-accessible
    STATUS          mandatory
    DESCRIPTION     
            "The Traffic Management related counters for allowed contractor number based origination. "
    ::= { sonusSoftswitchPesTMContractorBasedOriginationCounters 1 }

sonusSoftswitchPesTMContractorBasedOriginationCountersAllowedEntry OBJECT-TYPE
    SYNTAX          SonusSoftswitchPesTMContractorBasedOriginationCountersAllowedEntry
    ACCESS          not-accessible
    STATUS          mandatory
    DESCRIPTION     
            "The Traffic Management related counters for allowed contractor number based origination."
    INDEX           { 
                      sonusSoftswitchPesTMContractorBasedOriginationCountersAllowedEntity, 
                      sonusSoftswitchPesTMContractorBasedOriginationCountersAllowedEntity2 }
    ::= { sonusSoftswitchPesTMContractorBasedOriginationCountersAllowedTable 1 }

SonusSoftswitchPesTMContractorBasedOriginationCountersAllowedEntry ::=
    SEQUENCE {
        sonusSoftswitchPesTMContractorBasedOriginationCountersAllowedEntity                                   SonusName,
        sonusSoftswitchPesTMContractorBasedOriginationCountersAllowedEntity2                                    SonusName,
        sonusSoftswitchPesTMContractorBasedOriginationCountersAllowedValue                                  Counter
    }

sonusSoftswitchPesTMContractorBasedOriginationCountersAllowedEntity OBJECT-TYPE
    SYNTAX          SonusName
    ACCESS          read-only
    STATUS          mandatory
    DESCRIPTION     
            "Entity Id (national number) for contractor number based origination with traffic control"
    ::= { sonusSoftswitchPesTMContractorBasedOriginationCountersAllowedEntry 1 }

sonusSoftswitchPesTMContractorBasedOriginationCountersAllowedEntity2 OBJECT-TYPE
    SYNTAX          SonusName
    ACCESS          read-only
    STATUS          mandatory
    DESCRIPTION     
            "Entity Id2 (country id) for contractor number based origination with traffic control"
    ::= { sonusSoftswitchPesTMContractorBasedOriginationCountersAllowedEntry 2 }

sonusSoftswitchPesTMContractorBasedOriginationCountersAllowedValue OBJECT-TYPE
    SYNTAX          Counter
    ACCESS          read-only
    STATUS          mandatory
    DESCRIPTION     
            "Number of allowed calls from contractor number based origination with traffic control"
    ::= { sonusSoftswitchPesTMContractorBasedOriginationCountersAllowedEntry 3 }

sonusSoftswitchPesTMContractorBasedOriginationCountersBlockedTable OBJECT-TYPE
    SYNTAX          SEQUENCE OF SonusSoftswitchPesTMContractorBasedOriginationCountersBlockedEntry
    ACCESS          not-accessible
    STATUS          mandatory
    DESCRIPTION     
            "The Traffic Management related counters for blocked contractor number based origination. "
    ::= { sonusSoftswitchPesTMContractorBasedOriginationCounters 2 }

sonusSoftswitchPesTMContractorBasedOriginationCountersBlockedEntry OBJECT-TYPE
    SYNTAX          SonusSoftswitchPesTMContractorBasedOriginationCountersBlockedEntry
    ACCESS          not-accessible
    STATUS          mandatory
    DESCRIPTION     
            "The Traffic Management related counters for blocked contractor number based origination."
    INDEX           { 
                      sonusSoftswitchPesTMContractorBasedOriginationCountersBlockedEntity, 
                      sonusSoftswitchPesTMContractorBasedOriginationCountersBlockedEntity2 }
    ::= { sonusSoftswitchPesTMContractorBasedOriginationCountersBlockedTable 1 }

SonusSoftswitchPesTMContractorBasedOriginationCountersBlockedEntry ::=
    SEQUENCE {
        sonusSoftswitchPesTMContractorBasedOriginationCountersBlockedEntity                                   SonusName,
        sonusSoftswitchPesTMContractorBasedOriginationCountersBlockedEntity2                                    SonusName,
        sonusSoftswitchPesTMContractorBasedOriginationCountersBlockedValue                                  Counter
    }

sonusSoftswitchPesTMContractorBasedOriginationCountersBlockedEntity OBJECT-TYPE
    SYNTAX          SonusName
    ACCESS          read-only
    STATUS          mandatory
    DESCRIPTION     
            "Entity Id (national number) for contractor number based origination with traffic control"
    ::= { sonusSoftswitchPesTMContractorBasedOriginationCountersBlockedEntry 1 }

sonusSoftswitchPesTMContractorBasedOriginationCountersBlockedEntity2 OBJECT-TYPE
    SYNTAX          SonusName
    ACCESS          read-only
    STATUS          mandatory
    DESCRIPTION     
            "Entity Id2 (country id) for contractor number based origination with traffic control"
    ::= { sonusSoftswitchPesTMContractorBasedOriginationCountersBlockedEntry 2 }

sonusSoftswitchPesTMContractorBasedOriginationCountersBlockedValue OBJECT-TYPE
    SYNTAX          Counter
    ACCESS          read-only
    STATUS          mandatory
    DESCRIPTION     
            "Number of blocked calls from contractor number based origination with traffic control"
    ::= { sonusSoftswitchPesTMContractorBasedOriginationCountersBlockedEntry 3 }

sonusSoftswitchPesTMCdDNBasedDestinationCounters OBJECT IDENTIFIER
    ::= { sonusSoftSwitchPesTrafficMgmtCounters 11 }

sonusSoftswitchPesTMCdDNBasedDestinationCountersAllowedTable OBJECT-TYPE
    SYNTAX          SEQUENCE OF SonusSoftswitchPesTMCdDNBasedDestinationCountersAllowedEntry
    ACCESS          not-accessible
    STATUS          mandatory
    DESCRIPTION     
            "The Traffic Management related counters for allowed called DN based destination "
    ::= { sonusSoftswitchPesTMCdDNBasedDestinationCounters 1 }

sonusSoftswitchPesTMCdDNBasedDestinationCountersAllowedEntry OBJECT-TYPE
    SYNTAX          SonusSoftswitchPesTMCdDNBasedDestinationCountersAllowedEntry
    ACCESS          not-accessible
    STATUS          mandatory
    DESCRIPTION     
            "The Traffic Management related counters for allowed called DN based destination."
    INDEX           { 
                      sonusSoftswitchPesTMCdDNBasedDestinationCountersAllowedEntity, 
                      sonusSoftswitchPesTMCdDNBasedDestinationCountersAllowedEntity2 }
    ::= { sonusSoftswitchPesTMCdDNBasedDestinationCountersAllowedTable 1 }

SonusSoftswitchPesTMCdDNBasedDestinationCountersAllowedEntry ::=
    SEQUENCE {
        sonusSoftswitchPesTMCdDNBasedDestinationCountersAllowedEntity                             SonusName,
        sonusSoftswitchPesTMCdDNBasedDestinationCountersAllowedEntity2                              SonusName,
        sonusSoftswitchPesTMCdDNBasedDestinationCountersAllowedValue                            Counter
    }

sonusSoftswitchPesTMCdDNBasedDestinationCountersAllowedEntity OBJECT-TYPE
    SYNTAX          SonusName
    ACCESS          read-only
    STATUS          mandatory
    DESCRIPTION     
            "Entity Id (national number) for calledd DN based destination with traffic control"
    ::= { sonusSoftswitchPesTMCdDNBasedDestinationCountersAllowedEntry 1 }

sonusSoftswitchPesTMCdDNBasedDestinationCountersAllowedEntity2 OBJECT-TYPE
    SYNTAX          SonusName
    ACCESS          read-only
    STATUS          mandatory
    DESCRIPTION     
            "Entity Id2 (country id) for called DN based destination with traffic control"
    ::= { sonusSoftswitchPesTMCdDNBasedDestinationCountersAllowedEntry 2 }

sonusSoftswitchPesTMCdDNBasedDestinationCountersAllowedValue OBJECT-TYPE
    SYNTAX          Counter
    ACCESS          read-only
    STATUS          mandatory
    DESCRIPTION     
            "Number of allowed calls to called DN based destination with traffic control"
    ::= { sonusSoftswitchPesTMCdDNBasedDestinationCountersAllowedEntry 3 }

sonusSoftswitchPesTMCdDNBasedDestinationCountersBlockedTable OBJECT-TYPE
    SYNTAX          SEQUENCE OF SonusSoftswitchPesTMCdDNBasedDestinationCountersBlockedEntry
    ACCESS          not-accessible
    STATUS          mandatory
    DESCRIPTION     
            "The Traffic Management related counters for blocked called DN based destination."
    ::= { sonusSoftswitchPesTMCdDNBasedDestinationCounters 2 }

sonusSoftswitchPesTMCdDNBasedDestinationCountersBlockedEntry OBJECT-TYPE
    SYNTAX          SonusSoftswitchPesTMCdDNBasedDestinationCountersBlockedEntry
    ACCESS          not-accessible
    STATUS          mandatory
    DESCRIPTION     
            "The Traffic Management related counters for blocked called DN based destination."
    INDEX           { 
                      sonusSoftswitchPesTMCdDNBasedDestinationCountersBlockedEntity, 
                      sonusSoftswitchPesTMCdDNBasedDestinationCountersBlockedEntity2 }
    ::= { sonusSoftswitchPesTMCdDNBasedDestinationCountersBlockedTable 1 }

SonusSoftswitchPesTMCdDNBasedDestinationCountersBlockedEntry ::=
    SEQUENCE {
        sonusSoftswitchPesTMCdDNBasedDestinationCountersBlockedEntity                             SonusName,
        sonusSoftswitchPesTMCdDNBasedDestinationCountersBlockedEntity2                              SonusName,
        sonusSoftswitchPesTMCdDNBasedDestinationCountersBlockedValue                            Counter
    }

sonusSoftswitchPesTMCdDNBasedDestinationCountersBlockedEntity OBJECT-TYPE
    SYNTAX          SonusName
    ACCESS          read-only
    STATUS          mandatory
    DESCRIPTION     
            "Entity Id (national number) for called DN based destination with traffic control"
    ::= { sonusSoftswitchPesTMCdDNBasedDestinationCountersBlockedEntry 1 }

sonusSoftswitchPesTMCdDNBasedDestinationCountersBlockedEntity2 OBJECT-TYPE
    SYNTAX          SonusName
    ACCESS          read-only
    STATUS          mandatory
    DESCRIPTION     
            "Entity Id2 (country id) for called DN based destination with traffic control"
    ::= { sonusSoftswitchPesTMCdDNBasedDestinationCountersBlockedEntry 2 }

sonusSoftswitchPesTMCdDNBasedDestinationCountersBlockedValue OBJECT-TYPE
    SYNTAX          Counter
    ACCESS          read-only
    STATUS          mandatory
    DESCRIPTION     
            "Number of blocked calls to called DN based destination with traffic control"
    ::= { sonusSoftswitchPesTMCdDNBasedDestinationCountersBlockedEntry 3 }

sonusSoftswitchPesTMCPEGroupPreProcessingCounters OBJECT IDENTIFIER
    ::= { sonusSoftSwitchPesTrafficMgmtCounters 12 }

sonusSoftswitchPesTMCPEGroupPreProcessingCountersAllowedTable OBJECT-TYPE
    SYNTAX          SEQUENCE OF SonusSoftswitchPesTMCPEGroupPreProcessingCountersAllowedEntry
    ACCESS          not-accessible
    STATUS          mandatory
    DESCRIPTION     
            "The Traffic Management related counters for allowed CPE Group at Pre-Processing."
    ::= { sonusSoftswitchPesTMCPEGroupPreProcessingCounters 1 }

sonusSoftswitchPesTMCPEGroupPreProcessingCountersAllowedEntry OBJECT-TYPE
    SYNTAX          SonusSoftswitchPesTMCPEGroupPreProcessingCountersAllowedEntry
    ACCESS          not-accessible
    STATUS          mandatory
    DESCRIPTION     
            "The Traffic Management related counters for allowed CPE Group at Pre-Processing."
    INDEX           { 
                      sonusSoftswitchPesTMCPEGroupPreProcessingCountersAllowedEntity, 
                      sonusSoftswitchPesTMCPEGroupPreProcessingCountersAllowedEntity2 }
    ::= { sonusSoftswitchPesTMCPEGroupPreProcessingCountersAllowedTable 1 }

SonusSoftswitchPesTMCPEGroupPreProcessingCountersAllowedEntry ::=
    SEQUENCE {
        sonusSoftswitchPesTMCPEGroupPreProcessingCountersAllowedEntity                              SonusName,
        sonusSoftswitchPesTMCPEGroupPreProcessingCountersAllowedEntity2                               SonusName,
        sonusSoftswitchPesTMCPEGroupPreProcessingCountersAllowedValue                             Counter,
        sonusSoftSwitchPesTMCPEGroupPreProcessingAllowedIntervalTime                            TimeTicks
    }

sonusSoftswitchPesTMCPEGroupPreProcessingCountersAllowedEntity OBJECT-TYPE
    SYNTAX          SonusName
    ACCESS          read-only
    STATUS          mandatory
    DESCRIPTION     
            "Entity Id (Generic Criteria Group Profile) for CPE Group at Pre-Processing with traffic control"
    ::= { sonusSoftswitchPesTMCPEGroupPreProcessingCountersAllowedEntry 1 }

sonusSoftswitchPesTMCPEGroupPreProcessingCountersAllowedEntity2 OBJECT-TYPE
    SYNTAX          SonusName
    ACCESS          read-only
    STATUS          mandatory
    DESCRIPTION     
            "Entity Id2 (Sonus_NULL) for CPE Group at Pre-Processing with traffic control"
    ::= { sonusSoftswitchPesTMCPEGroupPreProcessingCountersAllowedEntry 2 }

sonusSoftswitchPesTMCPEGroupPreProcessingCountersAllowedValue OBJECT-TYPE
    SYNTAX          Counter
    ACCESS          read-only
    STATUS          mandatory
    DESCRIPTION     
            "Number of allowed calls to CPE Group at Pre-Processing with traffic control"
    ::= { sonusSoftswitchPesTMCPEGroupPreProcessingCountersAllowedEntry 3 }

sonusSoftSwitchPesTMCPEGroupPreProcessingAllowedIntervalTime OBJECT-TYPE
    SYNTAX          TimeTicks
    ACCESS          read-only
    STATUS          obsolete
    DESCRIPTION     
            "This variable contains the end of interval time stamp for the specified interval."
    ::= { sonusSoftswitchPesTMCPEGroupPreProcessingCountersAllowedEntry 4 }

sonusSoftswitchPesTMCPEGroupPreProcessingCountersBlockedTable OBJECT-TYPE
    SYNTAX          SEQUENCE OF SonusSoftswitchPesTMCPEGroupPreProcessingCountersBlockedEntry
    ACCESS          not-accessible
    STATUS          mandatory
    DESCRIPTION     
            "The Traffic Management related counters for blocked CPE Group at Pre-Processing."
    ::= { sonusSoftswitchPesTMCPEGroupPreProcessingCounters 2 }

sonusSoftswitchPesTMCPEGroupPreProcessingCountersBlockedEntry OBJECT-TYPE
    SYNTAX          SonusSoftswitchPesTMCPEGroupPreProcessingCountersBlockedEntry
    ACCESS          not-accessible
    STATUS          mandatory
    DESCRIPTION     
            "The Traffic Management related counters for blocked CPE Group at Pre-Processing."
    INDEX           { 
                      sonusSoftswitchPesTMCPEGroupPreProcessingCountersBlockedEntity, 
                      sonusSoftswitchPesTMCPEGroupPreProcessingCountersBlockedEntity2 }
    ::= { sonusSoftswitchPesTMCPEGroupPreProcessingCountersBlockedTable 1 }

SonusSoftswitchPesTMCPEGroupPreProcessingCountersBlockedEntry ::=
    SEQUENCE {
        sonusSoftswitchPesTMCPEGroupPreProcessingCountersBlockedEntity                              SonusName,
        sonusSoftswitchPesTMCPEGroupPreProcessingCountersBlockedEntity2                               SonusName,
        sonusSoftswitchPesTMCPEGroupPreProcessingCountersBlockedValue                             Counter,
        sonusSoftSwitchPesTMCPEGroupPreProcessingBlockedIntervalTime                            TimeTicks
    }

sonusSoftswitchPesTMCPEGroupPreProcessingCountersBlockedEntity OBJECT-TYPE
    SYNTAX          SonusName
    ACCESS          read-only
    STATUS          mandatory
    DESCRIPTION     
            "Entity Id (Generic Criteria Group Profile) for CPE Group at Pre-Processing with traffic control"
    ::= { sonusSoftswitchPesTMCPEGroupPreProcessingCountersBlockedEntry 1 }

sonusSoftswitchPesTMCPEGroupPreProcessingCountersBlockedEntity2 OBJECT-TYPE
    SYNTAX          SonusName
    ACCESS          read-only
    STATUS          mandatory
    DESCRIPTION     
            "Entity Id2 (Sonus_NULL) for CPE Group at Pre-Processing with traffic control"
    ::= { sonusSoftswitchPesTMCPEGroupPreProcessingCountersBlockedEntry 2 }

sonusSoftswitchPesTMCPEGroupPreProcessingCountersBlockedValue OBJECT-TYPE
    SYNTAX          Counter
    ACCESS          read-only
    STATUS          mandatory
    DESCRIPTION     
            "Number of blocked calls to CPE Group at Pre-Processing with traffic control"
    ::= { sonusSoftswitchPesTMCPEGroupPreProcessingCountersBlockedEntry 3 }

sonusSoftSwitchPesTMCPEGroupPreProcessingBlockedIntervalTime OBJECT-TYPE
    SYNTAX          TimeTicks
    ACCESS          read-only
    STATUS          obsolete
    DESCRIPTION     
            "This variable contains the end of interval time stamp for the specified interval."
    ::= { sonusSoftswitchPesTMCPEGroupPreProcessingCountersBlockedEntry 4 }

sonusSoftswitchPesTMCPEGroupPreRoutingCounters OBJECT IDENTIFIER
    ::= { sonusSoftSwitchPesTrafficMgmtCounters 13 }

sonusSoftswitchPesTMCPEGroupPreRoutingCountersAllowedTable OBJECT-TYPE
    SYNTAX          SEQUENCE OF SonusSoftswitchPesTMCPEGroupPreRoutingCountersAllowedEntry
    ACCESS          not-accessible
    STATUS          mandatory
    DESCRIPTION     
            "The Traffic Management related counters for allowed CPE Group at Pre-Routing."
    ::= { sonusSoftswitchPesTMCPEGroupPreRoutingCounters 1 }

sonusSoftswitchPesTMCPEGroupPreRoutingCountersAllowedEntry OBJECT-TYPE
    SYNTAX          SonusSoftswitchPesTMCPEGroupPreRoutingCountersAllowedEntry
    ACCESS          not-accessible
    STATUS          mandatory
    DESCRIPTION     
            "The Traffic Management related counters for allowed CPE Group at Pre-Routing."
    INDEX           { 
                      sonusSoftswitchPesTMCPEGroupPreRoutingCountersAllowedEntity, 
                      sonusSoftswitchPesTMCPEGroupPreRoutingCountersAllowedEntity2 }
    ::= { sonusSoftswitchPesTMCPEGroupPreRoutingCountersAllowedTable 1 }

SonusSoftswitchPesTMCPEGroupPreRoutingCountersAllowedEntry ::=
    SEQUENCE {
        sonusSoftswitchPesTMCPEGroupPreRoutingCountersAllowedEntity                           SonusName,
        sonusSoftswitchPesTMCPEGroupPreRoutingCountersAllowedEntity2                            SonusName,
        sonusSoftswitchPesTMCPEGroupPreRoutingCountersAllowedValue                          Counter,
        sonusSoftSwitchPesTMCPEGroupPreRoutingAllowedIntervalTime                         TimeTicks
    }

sonusSoftswitchPesTMCPEGroupPreRoutingCountersAllowedEntity OBJECT-TYPE
    SYNTAX          SonusName
    ACCESS          read-only
    STATUS          mandatory
    DESCRIPTION     
            "Entity Id (Generic Criteria Group Profile) for CPE Group at Pre-Routing with traffic control"
    ::= { sonusSoftswitchPesTMCPEGroupPreRoutingCountersAllowedEntry 1 }

sonusSoftswitchPesTMCPEGroupPreRoutingCountersAllowedEntity2 OBJECT-TYPE
    SYNTAX          SonusName
    ACCESS          read-only
    STATUS          mandatory
    DESCRIPTION     
            "Entity Id2 (Sonus_NULL) for CPE Group at Pre-Routing with traffic control"
    ::= { sonusSoftswitchPesTMCPEGroupPreRoutingCountersAllowedEntry 2 }

sonusSoftswitchPesTMCPEGroupPreRoutingCountersAllowedValue OBJECT-TYPE
    SYNTAX          Counter
    ACCESS          read-only
    STATUS          mandatory
    DESCRIPTION     
            "Number of allowed calls to CPE Group at Pre-Routing with traffic control"
    ::= { sonusSoftswitchPesTMCPEGroupPreRoutingCountersAllowedEntry 3 }

sonusSoftSwitchPesTMCPEGroupPreRoutingAllowedIntervalTime OBJECT-TYPE
    SYNTAX          TimeTicks
    ACCESS          read-only
    STATUS          obsolete
    DESCRIPTION     
            "This variable contains the end of interval time stamp for the specified interval."
    ::= { sonusSoftswitchPesTMCPEGroupPreRoutingCountersAllowedEntry 4 }

sonusSoftswitchPesTMCPEGroupPreRoutingCountersBlockedTable OBJECT-TYPE
    SYNTAX          SEQUENCE OF SonusSoftswitchPesTMCPEGroupPreRoutingCountersBlockedEntry
    ACCESS          not-accessible
    STATUS          mandatory
    DESCRIPTION     
            "The Traffic Management related counters for blocked CPE Group at Pre-Routing."
    ::= { sonusSoftswitchPesTMCPEGroupPreRoutingCounters 2 }

sonusSoftswitchPesTMCPEGroupPreRoutingCountersBlockedEntry OBJECT-TYPE
    SYNTAX          SonusSoftswitchPesTMCPEGroupPreRoutingCountersBlockedEntry
    ACCESS          not-accessible
    STATUS          mandatory
    DESCRIPTION     
            "The Traffic Management related counters for blocked CPE Group at Pre-Routing."
    INDEX           { 
                      sonusSoftswitchPesTMCPEGroupPreRoutingCountersBlockedEntity, 
                      sonusSoftswitchPesTMCPEGroupPreRoutingCountersBlockedEntity2 }
    ::= { sonusSoftswitchPesTMCPEGroupPreRoutingCountersBlockedTable 1 }

SonusSoftswitchPesTMCPEGroupPreRoutingCountersBlockedEntry ::=
    SEQUENCE {
        sonusSoftswitchPesTMCPEGroupPreRoutingCountersBlockedEntity                           SonusName,
        sonusSoftswitchPesTMCPEGroupPreRoutingCountersBlockedEntity2                            SonusName,
        sonusSoftswitchPesTMCPEGroupPreRoutingCountersBlockedValue                          Counter,
        sonusSoftSwitchPesTMCPEGroupPreRoutingBlockedIntervalTime                         TimeTicks
    }

sonusSoftswitchPesTMCPEGroupPreRoutingCountersBlockedEntity OBJECT-TYPE
    SYNTAX          SonusName
    ACCESS          read-only
    STATUS          mandatory
    DESCRIPTION     
            "Entity Id (Generic Criteria Group Profile) for CPE Group at Pre-Routing with traffic control"
    ::= { sonusSoftswitchPesTMCPEGroupPreRoutingCountersBlockedEntry 1 }

sonusSoftswitchPesTMCPEGroupPreRoutingCountersBlockedEntity2 OBJECT-TYPE
    SYNTAX          SonusName
    ACCESS          read-only
    STATUS          mandatory
    DESCRIPTION     
            "Entity Id2 (Sonus_NULL) for CPE Group at Pre-Routing with traffic control"
    ::= { sonusSoftswitchPesTMCPEGroupPreRoutingCountersBlockedEntry 2 }

sonusSoftswitchPesTMCPEGroupPreRoutingCountersBlockedValue OBJECT-TYPE
    SYNTAX          Counter
    ACCESS          read-only
    STATUS          mandatory
    DESCRIPTION     
            "Number of blocked calls to CPE Group at Pre-Routing with traffic control"
    ::= { sonusSoftswitchPesTMCPEGroupPreRoutingCountersBlockedEntry 3 }

sonusSoftSwitchPesTMCPEGroupPreRoutingBlockedIntervalTime OBJECT-TYPE
    SYNTAX          TimeTicks
    ACCESS          read-only
    STATUS          obsolete
    DESCRIPTION     
            "This variable contains the end of interval time stamp for the specified interval."
    ::= { sonusSoftswitchPesTMCPEGroupPreRoutingCountersBlockedEntry 4 }

sonusSoftswitchPesTMCPEGroupPostRoutingCounters OBJECT IDENTIFIER
    ::= { sonusSoftSwitchPesTrafficMgmtCounters 14 }

sonusSoftswitchPesTMCPEGroupPostRoutingCountersAllowedTable OBJECT-TYPE
    SYNTAX          SEQUENCE OF SonusSoftswitchPesTMCPEGroupPostRoutingCountersAllowedEntry
    ACCESS          not-accessible
    STATUS          mandatory
    DESCRIPTION     
            "The Traffic Management related counters for allowed CPE Group at Post-Routing."
    ::= { sonusSoftswitchPesTMCPEGroupPostRoutingCounters 1 }

sonusSoftswitchPesTMCPEGroupPostRoutingCountersAllowedEntry OBJECT-TYPE
    SYNTAX          SonusSoftswitchPesTMCPEGroupPostRoutingCountersAllowedEntry
    ACCESS          not-accessible
    STATUS          mandatory
    DESCRIPTION     
            "The Traffic Management related counters for allowed CPE Group at Post-Routing."
    INDEX           { 
                      sonusSoftswitchPesTMCPEGroupPostRoutingCountersAllowedEntity, 
                      sonusSoftswitchPesTMCPEGroupPostRoutingCountersAllowedEntity2 }
    ::= { sonusSoftswitchPesTMCPEGroupPostRoutingCountersAllowedTable 1 }

SonusSoftswitchPesTMCPEGroupPostRoutingCountersAllowedEntry ::=
    SEQUENCE {
        sonusSoftswitchPesTMCPEGroupPostRoutingCountersAllowedEntity                            SonusName,
        sonusSoftswitchPesTMCPEGroupPostRoutingCountersAllowedEntity2                             SonusName,
        sonusSoftswitchPesTMCPEGroupPostRoutingCountersAllowedValue                           Counter,
        sonusSoftSwitchPesTMCPEGroupPostRoutingAllowedIntervalTime                          TimeTicks
    }

sonusSoftswitchPesTMCPEGroupPostRoutingCountersAllowedEntity OBJECT-TYPE
    SYNTAX          SonusName
    ACCESS          read-only
    STATUS          mandatory
    DESCRIPTION     
            "Entity Id (Generic Criteria Group Profile) for CPE Group at Post-Routing with traffic control"
    ::= { sonusSoftswitchPesTMCPEGroupPostRoutingCountersAllowedEntry 1 }

sonusSoftswitchPesTMCPEGroupPostRoutingCountersAllowedEntity2 OBJECT-TYPE
    SYNTAX          SonusName
    ACCESS          read-only
    STATUS          mandatory
    DESCRIPTION     
            "Entity Id2 (Sonus_NULL) for CPE Group at Post-Routing with traffic control"
    ::= { sonusSoftswitchPesTMCPEGroupPostRoutingCountersAllowedEntry 2 }

sonusSoftswitchPesTMCPEGroupPostRoutingCountersAllowedValue OBJECT-TYPE
    SYNTAX          Counter
    ACCESS          read-only
    STATUS          mandatory
    DESCRIPTION     
            "Number of allowed calls to CPE Group at Post-Routing with traffic control"
    ::= { sonusSoftswitchPesTMCPEGroupPostRoutingCountersAllowedEntry 3 }

sonusSoftSwitchPesTMCPEGroupPostRoutingAllowedIntervalTime OBJECT-TYPE
    SYNTAX          TimeTicks
    ACCESS          read-only
    STATUS          obsolete
    DESCRIPTION     
            "This variable contains the end of interval time stamp for the specified interval."
    ::= { sonusSoftswitchPesTMCPEGroupPostRoutingCountersAllowedEntry 4 }

sonusSoftswitchPesTMCPEGroupPostRoutingCountersBlockedTable OBJECT-TYPE
    SYNTAX          SEQUENCE OF SonusSoftswitchPesTMCPEGroupPostRoutingCountersBlockedEntry
    ACCESS          not-accessible
    STATUS          mandatory
    DESCRIPTION     
            "The Traffic Management related counters for blocked CPE Group at Post-Routing."
    ::= { sonusSoftswitchPesTMCPEGroupPostRoutingCounters 2 }

sonusSoftswitchPesTMCPEGroupPostRoutingCountersBlockedEntry OBJECT-TYPE
    SYNTAX          SonusSoftswitchPesTMCPEGroupPostRoutingCountersBlockedEntry
    ACCESS          not-accessible
    STATUS          mandatory
    DESCRIPTION     
            "The Traffic Management related counters for blocked CPE Group at Post-Routing."
    INDEX           { 
                      sonusSoftswitchPesTMCPEGroupPostRoutingCountersBlockedEntity, 
                      sonusSoftswitchPesTMCPEGroupPostRoutingCountersBlockedEntity2 }
    ::= { sonusSoftswitchPesTMCPEGroupPostRoutingCountersBlockedTable 1 }

SonusSoftswitchPesTMCPEGroupPostRoutingCountersBlockedEntry ::=
    SEQUENCE {
        sonusSoftswitchPesTMCPEGroupPostRoutingCountersBlockedEntity                            SonusName,
        sonusSoftswitchPesTMCPEGroupPostRoutingCountersBlockedEntity2                             SonusName,
        sonusSoftswitchPesTMCPEGroupPostRoutingCountersBlockedValue                           Counter,
        sonusSoftSwitchPesTMCPEGroupPostRoutingBlockedIntervalTime                          TimeTicks
    }

sonusSoftswitchPesTMCPEGroupPostRoutingCountersBlockedEntity OBJECT-TYPE
    SYNTAX          SonusName
    ACCESS          read-only
    STATUS          mandatory
    DESCRIPTION     
            "Entity Id (Generic Criteria Group Profile) for CPE Group at Post-Routing with traffic control"
    ::= { sonusSoftswitchPesTMCPEGroupPostRoutingCountersBlockedEntry 1 }

sonusSoftswitchPesTMCPEGroupPostRoutingCountersBlockedEntity2 OBJECT-TYPE
    SYNTAX          SonusName
    ACCESS          read-only
    STATUS          mandatory
    DESCRIPTION     
            "Entity Id2 (Sonus_NULL) for CPE Group at Post-Routing with traffic control"
    ::= { sonusSoftswitchPesTMCPEGroupPostRoutingCountersBlockedEntry 2 }

sonusSoftswitchPesTMCPEGroupPostRoutingCountersBlockedValue OBJECT-TYPE
    SYNTAX          Counter
    ACCESS          read-only
    STATUS          mandatory
    DESCRIPTION     
            "Number of blocked calls to CPE Group at Post-Routing with traffic control"
    ::= { sonusSoftswitchPesTMCPEGroupPostRoutingCountersBlockedEntry 3 }

sonusSoftSwitchPesTMCPEGroupPostRoutingBlockedIntervalTime OBJECT-TYPE
    SYNTAX          TimeTicks
    ACCESS          read-only
    STATUS          obsolete
    DESCRIPTION     
            "This variable contains the end of interval time stamp for the specified interval."
    ::= { sonusSoftswitchPesTMCPEGroupPostRoutingCountersBlockedEntry 4 }

sonusSoftSwitchPesGsmMapCounters OBJECT IDENTIFIER
    ::= { sonusSoftSwitchPolicyExecutionServerStatistics 5 }

sonusSoftSwitchPesGsmMapCountersNumSRIRequests OBJECT-TYPE
    SYNTAX          Counter
    ACCESS          read-only
    STATUS          mandatory
    DESCRIPTION     
            "Number of Send Routing Information Request messages sent by the PSX."
    ::= { sonusSoftSwitchPesGsmMapCounters 1 }

sonusSoftSwitchPesGsmMapCountersNumSRIRouteResponses OBJECT-TYPE
    SYNTAX          Counter
    ACCESS          read-only
    STATUS          mandatory
    DESCRIPTION     
            " Number of Send Routing Information Response messages received by the PSX containing call delivery data."
    ::= { sonusSoftSwitchPesGsmMapCounters 2 }

sonusSoftSwitchPesGsmMapCountersNumSRIForwardResponses OBJECT-TYPE
    SYNTAX          Counter
    ACCESS          read-only
    STATUS          mandatory
    DESCRIPTION     
            "Number of Send Routing Information Response messages received by the PSX containing immediate call forwarding data."
    ::= { sonusSoftSwitchPesGsmMapCounters 3 }

sonusSoftSwitchPesGsmMapCountersNumSRIErrors OBJECT-TYPE
    SYNTAX          Counter
    ACCESS          read-only
    STATUS          mandatory
    DESCRIPTION     
            "Number of Send Routing Information fatal errors processed by the PSX."
    ::= { sonusSoftSwitchPesGsmMapCounters 4 }

sonusSoftSwitchPesGsmMapCountersNumSRITimeout OBJECT-TYPE
    SYNTAX          Counter
    ACCESS          read-only
    STATUS          mandatory
    DESCRIPTION     
            "Number of Send Routing Information Request messages that timed out without a response."
    ::= { sonusSoftSwitchPesGsmMapCounters 5 }

sonusSoftSwitchPesGsmMapCountersNumOR OBJECT-TYPE
    SYNTAX          Counter
    ACCESS          read-only
    STATUS          obsolete
    DESCRIPTION     
            "Number of Send Routing Information Request messages for Optimal Routing sent by the PSX."
    ::= { sonusSoftSwitchPesGsmMapCounters 6 }

sonusSoftSwitchPesGsmMapCountersNumRCHRequests OBJECT-TYPE
    SYNTAX          Counter
    ACCESS          read-only
    STATUS          mandatory
    DESCRIPTION     
            "Number of Resume Call Handling Request messages received by the PSX."
    ::= { sonusSoftSwitchPesGsmMapCounters 7 }

sonusSoftSwitchPesGsmMapCountersNumRCHErrors OBJECT-TYPE
    SYNTAX          Counter
    ACCESS          read-only
    STATUS          mandatory
    DESCRIPTION     
            "Number of Resume Call Handling Request message fatal errors detected by the PSX."
    ::= { sonusSoftSwitchPesGsmMapCounters 8 }

sonusSoftSwitchPesGsmMapCountersNumSRIResponses OBJECT-TYPE
    SYNTAX          Counter
    ACCESS          read-only
    STATUS          mandatory
    DESCRIPTION     
            "The total number of Send Routing Information responses received by the PSX."
    ::= { sonusSoftSwitchPesGsmMapCounters 9 }

sonusSoftSwitchPesGsmMapCountersIntervalTime OBJECT-TYPE
    SYNTAX          TimeTicks
    ACCESS          read-only
    STATUS          mandatory
    DESCRIPTION     
            "This variable contains the end of interval time stamp for 
             the specified interval."
    ::= { sonusSoftSwitchPesGsmMapCounters 10 }

sonusSoftSwitchPesGsmMapCountersNumMTRRSRIRequests OBJECT-TYPE
    SYNTAX          Counter
    ACCESS          read-only
    STATUS          mandatory
    DESCRIPTION     
            "Number of Resume Resume Call Handling Request with MTRR messages received by the PSX."
    ::= { sonusSoftSwitchPesGsmMapCounters 11 }

sonusSoftSwitchPesGsmMapCountersNumMTRRSRIResponses OBJECT-TYPE
    SYNTAX          Counter
    ACCESS          read-only
    STATUS          mandatory
    DESCRIPTION     
            "Number of Resume Send Routing Information responses with MTRR received by the PSX."
    ::= { sonusSoftSwitchPesGsmMapCounters 12 }

sonusSoftSwitchPesGsmMapCountersNumMTRRRCHRequests OBJECT-TYPE
    SYNTAX          Counter
    ACCESS          read-only
    STATUS          mandatory
    DESCRIPTION     
            "Number of Resume Call Handling Request messages with MTRR received by the PSX."
    ::= { sonusSoftSwitchPesGsmMapCounters 13 }

sonusSoftSwitchPesMWIServiceCounters OBJECT IDENTIFIER
    ::= { sonusSoftSwitchPolicyExecutionServerStatistics 6 }

sonusSoftSwitchPesMWIService OBJECT-TYPE
    SYNTAX          Counter
    ACCESS          read-only
    STATUS          mandatory
    DESCRIPTION     
            "This counter keeps track of calls that execute MWI service."
    ::= { sonusSoftSwitchPesMWIServiceCounters 1 }

sonusSoftSwitchPesMWIUpdateService OBJECT-TYPE
    SYNTAX          Counter
    ACCESS          read-only
    STATUS          mandatory
    DESCRIPTION     
            "This counter keeps track of calls that execute MWI Status Update service."
    ::= { sonusSoftSwitchPesMWIServiceCounters 2 }

sonusSoftSwitchPesMWIIntervalTime OBJECT-TYPE
    SYNTAX          TimeTicks
    ACCESS          read-only
    STATUS          mandatory
    DESCRIPTION     
            "This variable contains the end of interval time stamp for 
             the specified interval."
    ::= { sonusSoftSwitchPesMWIServiceCounters 3 }

sonusSoftSwitchPesDnsEnumCounters OBJECT IDENTIFIER
    ::= { sonusSoftSwitchPolicyExecutionServerStatistics 7 }

sonusSoftSwitchPesDnsEnumDNSRequestsSent OBJECT-TYPE
    SYNTAX          Counter
    ACCESS          read-only
    STATUS          mandatory
    DESCRIPTION     
            "Total number of DNS requests sent by PSX."
    ::= { sonusSoftSwitchPesDnsEnumCounters 1 }

sonusSoftSwitchPesDnsEnumDNSResponsesReceived OBJECT-TYPE
    SYNTAX          Counter
    ACCESS          read-only
    STATUS          mandatory
    DESCRIPTION     
            "Total number of DNS responses received by PSX."
    ::= { sonusSoftSwitchPesDnsEnumCounters 2 }

sonusSoftSwitchPesDnsEnumENUMRequestsSent OBJECT-TYPE
    SYNTAX          Counter
    ACCESS          read-only
    STATUS          mandatory
    DESCRIPTION     
            "Total number of ENUM requests sent for SIP AoR by PSX."
    ::= { sonusSoftSwitchPesDnsEnumCounters 3 }

sonusSoftSwitchPesDnsEnumENUMResponsesReceived OBJECT-TYPE
    SYNTAX          Counter
    ACCESS          read-only
    STATUS          mandatory
    DESCRIPTION     
            "Total number of ENUM responses received by PSX."
    ::= { sonusSoftSwitchPesDnsEnumCounters 4 }

sonusSoftSwitchPesDnsEnumKARequestsSent OBJECT-TYPE
    SYNTAX          Counter
    ACCESS          read-only
    STATUS          mandatory
    DESCRIPTION     
            "Total number of KeepAlive requests sent by PES."
    ::= { sonusSoftSwitchPesDnsEnumCounters 5 }

sonusSoftSwitchPesDnsEnumKAResponsesReceived OBJECT-TYPE
    SYNTAX          Counter
    ACCESS          read-only
    STATUS          mandatory
    DESCRIPTION     
            "Total number of KeepAlive responses received by PSX."
    ::= { sonusSoftSwitchPesDnsEnumCounters 6 }

sonusSoftSwitchPesDnsEnumENUMResponseSuccess OBJECT-TYPE
    SYNTAX          Counter
    ACCESS          read-only
    STATUS          mandatory
    DESCRIPTION     
            "Total number of Successful ENUM responses."
    ::= { sonusSoftSwitchPesDnsEnumCounters 7 }

sonusSoftSwitchPesDnsEnumENUMResponseGeneralFailure OBJECT-TYPE
    SYNTAX          Counter
    ACCESS          read-only
    STATUS          mandatory
    DESCRIPTION     
            "Total number of ENUM responses with General Failure."
    ::= { sonusSoftSwitchPesDnsEnumCounters 8 }

sonusSoftSwitchPesDnsEnumENUMResponseNoMemory OBJECT-TYPE
    SYNTAX          Counter
    ACCESS          read-only
    STATUS          mandatory
    DESCRIPTION     
            "Total number of ENUM responses with Memory_Unavailable Failure."
    ::= { sonusSoftSwitchPesDnsEnumCounters 9 }

sonusSoftSwitchPesDnsEnumENUMResponseInvalidParameter OBJECT-TYPE
    SYNTAX          Counter
    ACCESS          read-only
    STATUS          mandatory
    DESCRIPTION     
            "Total number of ENUM responses with Invalid_Parameter Failure."
    ::= { sonusSoftSwitchPesDnsEnumCounters 10 }

sonusSoftSwitchPesDnsEnumENUMResponseNoName OBJECT-TYPE
    SYNTAX          Counter
    ACCESS          read-only
    STATUS          mandatory
    DESCRIPTION     
            "Total number of ENUM responses with Name_Does_Not_Exist Failure."
    ::= { sonusSoftSwitchPesDnsEnumCounters 11 }

sonusSoftSwitchPesDnsEnumENUMResponseNoData OBJECT-TYPE
    SYNTAX          Counter
    ACCESS          read-only
    STATUS          mandatory
    DESCRIPTION     
            "Total number of ENUM responses with Valid_Name_But_No_Data_Record Failure."
    ::= { sonusSoftSwitchPesDnsEnumCounters 12 }

sonusSoftSwitchPesDnsEnumDNSResponseSuccess OBJECT-TYPE
    SYNTAX          Counter
    ACCESS          read-only
    STATUS          deprecated
    DESCRIPTION     
            "Total number of Successful DNS Responses."
    ::= { sonusSoftSwitchPesDnsEnumCounters 13 }

sonusSoftSwitchPesDnsEnumDNSResponseHostNotFound OBJECT-TYPE
    SYNTAX          Counter
    ACCESS          read-only
    STATUS          deprecated
    DESCRIPTION     
            "Total number of DNS Responses with Host_Not_Found Failure."
    ::= { sonusSoftSwitchPesDnsEnumCounters 14 }

sonusSoftSwitchPesDnsEnumDNSResponseTryAgain OBJECT-TYPE
    SYNTAX          Counter
    ACCESS          read-only
    STATUS          deprecated
    DESCRIPTION     
            "Total number of DNS Responses with Temporary_Server_Error_Try_Again Failure."
    ::= { sonusSoftSwitchPesDnsEnumCounters 15 }

sonusSoftSwitchPesDnsEnumDNSResponseNoRecovery OBJECT-TYPE
    SYNTAX          Counter
    ACCESS          read-only
    STATUS          deprecated
    DESCRIPTION     
            "Total number of DNS Responses with Non_Recoverable_Name_Server_Error Failure."
    ::= { sonusSoftSwitchPesDnsEnumCounters 16 }

sonusSoftSwitchPesDnsEnumDNSResponseNoData OBJECT-TYPE
    SYNTAX          Counter
    ACCESS          read-only
    STATUS          deprecated
    DESCRIPTION     
            "Total number of DNS Responses with Valid_Name_But_No_Data_Record Failure."
    ::= { sonusSoftSwitchPesDnsEnumCounters 17 }

sonusSoftSwitchPesDnsEnumDNSCanceledRequests OBJECT-TYPE
    SYNTAX          Counter
    ACCESS          read-only
    STATUS          mandatory
    DESCRIPTION     
            "Total number of DNS requests canceled by PSX."
    ::= { sonusSoftSwitchPesDnsEnumCounters 18 }

sonusSoftSwitchPesDnsEnumENUMCanceledRequests OBJECT-TYPE
    SYNTAX          Counter
    ACCESS          read-only
    STATUS          mandatory
    DESCRIPTION     
            "Total number of ENUM requests canceled by PSX."
    ::= { sonusSoftSwitchPesDnsEnumCounters 19 }

sonusSoftSwitchPesDnsEnumLongTermAverageTransactionTime OBJECT-TYPE
    SYNTAX          Gauge
    ACCESS          read-only
    STATUS          mandatory
    DESCRIPTION     
            "Long term average of transaction time."
    ::= { sonusSoftSwitchPesDnsEnumCounters 20 }

sonusSoftSwitchPesDnsEnumShortTermAverageTransactionTime OBJECT-TYPE
    SYNTAX          Gauge
    ACCESS          read-only
    STATUS          mandatory
    DESCRIPTION     
            "Short term average of transaction time."
    ::= { sonusSoftSwitchPesDnsEnumCounters 21 }

sonusSoftSwitchPesDnsEnumIntervalTime OBJECT-TYPE
    SYNTAX          TimeTicks
    ACCESS          read-only
    STATUS          obsolete
    DESCRIPTION     
            "This variable contains the end of interval time stamp for 
             the specified interval."
    ::= { sonusSoftSwitchPesDnsEnumCounters 22 }

sonusSoftSwitchPesDnsEnumDNSNAPTRResourceRecordRequestsSent OBJECT-TYPE
    SYNTAX          Counter
    ACCESS          read-only
    STATUS          mandatory
    DESCRIPTION     
            "Number of DNS NAPTR Resource Record requests sent by PSX."
    ::= { sonusSoftSwitchPesDnsEnumCounters 23 }

sonusSoftSwitchPesDnsEnumDNSNAPTRResourceRecordResponsesReceived OBJECT-TYPE
    SYNTAX          Counter
    ACCESS          read-only
    STATUS          mandatory
    DESCRIPTION     
            "Number of DNS NAPTR Resource Record responses received by PSX."
    ::= { sonusSoftSwitchPesDnsEnumCounters 24 }

sonusSoftSwitchPesDnsEnumDNSNAPTRResourceRecordCanceledRequests OBJECT-TYPE
    SYNTAX          Counter
    ACCESS          read-only
    STATUS          mandatory
    DESCRIPTION     
            "Number of DNS NAPTR Resource Record requests canceled by PSX."
    ::= { sonusSoftSwitchPesDnsEnumCounters 25 }

sonusSoftSwitchPesDnsEnumDNSNAPTRResourceRecordRspSuccess OBJECT-TYPE
    SYNTAX          Counter
    ACCESS          read-only
    STATUS          mandatory
    DESCRIPTION     
            "Number of Successful DNS NAPTR Resource Record responses."
    ::= { sonusSoftSwitchPesDnsEnumCounters 26 }

sonusSoftSwitchPesDnsEnumDNSNAPTRResourceRecordRspGeneralFailure OBJECT-TYPE
    SYNTAX          Counter
    ACCESS          read-only
    STATUS          mandatory
    DESCRIPTION     
            "Number of DNS NAPTR Resource Record responses with General Failure."
    ::= { sonusSoftSwitchPesDnsEnumCounters 27 }

sonusSoftSwitchPesDnsEnumDNSNAPTRResourceRecordRspNoMemory OBJECT-TYPE
    SYNTAX          Counter
    ACCESS          read-only
    STATUS          mandatory
    DESCRIPTION     
            "Number of DNS NAPTR Resource Record responses with Memory_Unavailable Failure."
    ::= { sonusSoftSwitchPesDnsEnumCounters 28 }

sonusSoftSwitchPesDnsEnumDNSNAPTRResourceRecordRspInvalidParam OBJECT-TYPE
    SYNTAX          Counter
    ACCESS          read-only
    STATUS          mandatory
    DESCRIPTION     
            "Number of DNS NAPTR Resource Record responses with Invalid_Parameter Failure."
    ::= { sonusSoftSwitchPesDnsEnumCounters 29 }

sonusSoftSwitchPesDnsEnumDNSNAPTRResourceRecordRspNoName OBJECT-TYPE
    SYNTAX          Counter
    ACCESS          read-only
    STATUS          mandatory
    DESCRIPTION     
            "Number of DNS NAPTR Resource Record responses with Name_Does_Not_Exist Failure."
    ::= { sonusSoftSwitchPesDnsEnumCounters 30 }

sonusSoftSwitchPesDnsEnumDNSNAPTRResourceRecordRspNoData OBJECT-TYPE
    SYNTAX          Counter
    ACCESS          read-only
    STATUS          mandatory
    DESCRIPTION     
            "Number of DNS NAPTR Resource Record responses with Valid_Name_But_No_Data_Record Failure."
    ::= { sonusSoftSwitchPesDnsEnumCounters 31 }

sonusSoftSwitchPesDnsEnumDNSSRVResourceRecordRequestsSent OBJECT-TYPE
    SYNTAX          Counter
    ACCESS          read-only
    STATUS          mandatory
    DESCRIPTION     
            "Number of DNS SRV Resource Record requests sent by PSX."
    ::= { sonusSoftSwitchPesDnsEnumCounters 32 }

sonusSoftSwitchPesDnsEnumDNSSRVResourceRecordResponsesReceived OBJECT-TYPE
    SYNTAX          Counter
    ACCESS          read-only
    STATUS          mandatory
    DESCRIPTION     
            "Number of DNS SRV Resource Record responses received by PSX."
    ::= { sonusSoftSwitchPesDnsEnumCounters 33 }

sonusSoftSwitchPesDnsEnumDNSSRVResourceRecordCanceledRequests OBJECT-TYPE
    SYNTAX          Counter
    ACCESS          read-only
    STATUS          mandatory
    DESCRIPTION     
            "Number of DNS SRV Resource Record requests canceled by PSX."
    ::= { sonusSoftSwitchPesDnsEnumCounters 34 }

sonusSoftSwitchPesDnsEnumDNSSRVResourceRecordRspSuccess OBJECT-TYPE
    SYNTAX          Counter
    ACCESS          read-only
    STATUS          mandatory
    DESCRIPTION     
            "Number of Successful DNS SRV Resource Record responses."
    ::= { sonusSoftSwitchPesDnsEnumCounters 35 }

sonusSoftSwitchPesDnsEnumDNSSRVResourceRecordRspGeneralFailure OBJECT-TYPE
    SYNTAX          Counter
    ACCESS          read-only
    STATUS          mandatory
    DESCRIPTION     
            "Number of DNS SRV Resource Record responses with General Failure."
    ::= { sonusSoftSwitchPesDnsEnumCounters 36 }

sonusSoftSwitchPesDnsEnumDNSSRVResourceRecordRspNoMemory OBJECT-TYPE
    SYNTAX          Counter
    ACCESS          read-only
    STATUS          mandatory
    DESCRIPTION     
            "Number of DNS SRV Resource Record responses with Memory_Unavailable Failure."
    ::= { sonusSoftSwitchPesDnsEnumCounters 37 }

sonusSoftSwitchPesDnsEnumDNSSRVResourceRecordRspInvalidParam OBJECT-TYPE
    SYNTAX          Counter
    ACCESS          read-only
    STATUS          mandatory
    DESCRIPTION     
            "Number of DNS SRV Resource Record responses with Invalid_Parameter Failure."
    ::= { sonusSoftSwitchPesDnsEnumCounters 38 }

sonusSoftSwitchPesDnsEnumDNSSRVResourceRecordRspNoName OBJECT-TYPE
    SYNTAX          Counter
    ACCESS          read-only
    STATUS          mandatory
    DESCRIPTION     
            "Number of DNS SRV Resource Record responses with Name_Does_Not_Exist Failure."
    ::= { sonusSoftSwitchPesDnsEnumCounters 39 }

sonusSoftSwitchPesDnsEnumDNSSRVResourceRecordRspNoData OBJECT-TYPE
    SYNTAX          Counter
    ACCESS          read-only
    STATUS          mandatory
    DESCRIPTION     
            "Number of DNS SRV Resource Record responses with Valid_Name_But_No_Data_Record Failure."
    ::= { sonusSoftSwitchPesDnsEnumCounters 40 }

sonusSoftSwitchPesDnsEnumDNSAResourceRecordRequestsSent OBJECT-TYPE
    SYNTAX          Counter
    ACCESS          read-only
    STATUS          mandatory
    DESCRIPTION     
            "Number of DNS A Resource Record requests sent by PSX."
    ::= { sonusSoftSwitchPesDnsEnumCounters 41 }

sonusSoftSwitchPesDnsEnumDNSAResourceRecordResponsesReceived OBJECT-TYPE
    SYNTAX          Counter
    ACCESS          read-only
    STATUS          mandatory
    DESCRIPTION     
            "Number of DNS A Resource Record responses received by PSX."
    ::= { sonusSoftSwitchPesDnsEnumCounters 42 }

sonusSoftSwitchPesDnsEnumDNSAResourceRecordCanceledRequests OBJECT-TYPE
    SYNTAX          Counter
    ACCESS          read-only
    STATUS          mandatory
    DESCRIPTION     
            "Number of DNS A Resource Record requests canceled by PSX."
    ::= { sonusSoftSwitchPesDnsEnumCounters 43 }

sonusSoftSwitchPesDnsEnumDNSAResourceRecordRspSuccess OBJECT-TYPE
    SYNTAX          Counter
    ACCESS          read-only
    STATUS          mandatory
    DESCRIPTION     
            "Number of Successful DNS A Resource Record Responses."
    ::= { sonusSoftSwitchPesDnsEnumCounters 44 }

sonusSoftSwitchPesDnsEnumDNSAResourceRecordRspHostNotFound OBJECT-TYPE
    SYNTAX          Counter
    ACCESS          read-only
    STATUS          mandatory
    DESCRIPTION     
            "Number of DNS A Resource Record Responses with Host_Not_Found Failure."
    ::= { sonusSoftSwitchPesDnsEnumCounters 45 }

sonusSoftSwitchPesDnsEnumDNSAResourceRecordRspTryAgain OBJECT-TYPE
    SYNTAX          Counter
    ACCESS          read-only
    STATUS          mandatory
    DESCRIPTION     
            "Number of DNS A Resource Record Responses with Temporary_Server_Error_Try_Again Failure."
    ::= { sonusSoftSwitchPesDnsEnumCounters 46 }

sonusSoftSwitchPesDnsEnumDNSAResourceRecordRspNoRecovery OBJECT-TYPE
    SYNTAX          Counter
    ACCESS          read-only
    STATUS          mandatory
    DESCRIPTION     
            "Number of DNS A Resource Record Responses with Non_Recoverable_Name_Server_Error Failure."
    ::= { sonusSoftSwitchPesDnsEnumCounters 47 }

sonusSoftSwitchPesDnsEnumDNSAResourceRecordRspNoData OBJECT-TYPE
    SYNTAX          Counter
    ACCESS          read-only
    STATUS          mandatory
    DESCRIPTION     
            "Number of DNS A Resource Record Responses with Valid_Name_But_No_Data_Record Failure."
    ::= { sonusSoftSwitchPesDnsEnumCounters 48 }

sonusSoftSwitchPesDnsEnumENUMLNPRequestsSent OBJECT-TYPE
    SYNTAX          Counter
    ACCESS          read-only
    STATUS          mandatory
    DESCRIPTION     
            "Total number of ENUM requests sent for LNP by PSX."
    ::= { sonusSoftSwitchPesDnsEnumCounters 49 }

sonusSoftSwitchPesDnsEnumENUMCNAMRequestsSent OBJECT-TYPE
    SYNTAX          Counter
    ACCESS          read-only
    STATUS          mandatory
    DESCRIPTION     
            "Total number of ENUM requests sent for CNAM by PSX."
    ::= { sonusSoftSwitchPesDnsEnumCounters 50 }

sonusSoftSwitchPesDnsEnumDNSAAAAResourceRecordRequestsSent OBJECT-TYPE
    SYNTAX          Counter
    ACCESS          read-only
    STATUS          mandatory
    DESCRIPTION     
            "Number of DNS AAAA Resource Record requests sent by PSX."
    ::= { sonusSoftSwitchPesDnsEnumCounters 51 }

sonusSoftSwitchPesDnsEnumDNSAAAAResourceRecordResponsesReceived OBJECT-TYPE
    SYNTAX          Counter
    ACCESS          read-only
    STATUS          mandatory
    DESCRIPTION     
            "Number of DNS AAAA Resource Record responses received by PSX."
    ::= { sonusSoftSwitchPesDnsEnumCounters 52 }

sonusSoftSwitchPesDnsEnumDNSAAAAResourceRecordCanceledRequests OBJECT-TYPE
    SYNTAX          Counter
    ACCESS          read-only
    STATUS          mandatory
    DESCRIPTION     
            "Number of DNS AAAA Resource Record requests canceled by PSX."
    ::= { sonusSoftSwitchPesDnsEnumCounters 53 }

sonusSoftSwitchPesDnsEnumDNSAAAAResourceRecordRspSuccess OBJECT-TYPE
    SYNTAX          Counter
    ACCESS          read-only
    STATUS          mandatory
    DESCRIPTION     
            "Number of Successful DNS AAAA Resource Record Responses."
    ::= { sonusSoftSwitchPesDnsEnumCounters 54 }

sonusSoftSwitchPesDnsEnumDNSAAAAResourceRecordRspHostNotFound OBJECT-TYPE
    SYNTAX          Counter
    ACCESS          read-only
    STATUS          mandatory
    DESCRIPTION     
            "Number of DNS AAAA Resource Record Responses with Host_Not_Found Failure."
    ::= { sonusSoftSwitchPesDnsEnumCounters 55 }

sonusSoftSwitchPesDnsEnumDNSAAAAResourceRecordRspTryAgain OBJECT-TYPE
    SYNTAX          Counter
    ACCESS          read-only
    STATUS          mandatory
    DESCRIPTION     
            "Number of DNS AAAA Resource Record Responses with Temporary_Server_Error_Try_Again Failure."
    ::= { sonusSoftSwitchPesDnsEnumCounters 56 }

sonusSoftSwitchPesDnsEnumDNSAAAAResourceRecordRspNoRecovery OBJECT-TYPE
    SYNTAX          Counter
    ACCESS          read-only
    STATUS          mandatory
    DESCRIPTION     
            "Number of DNS AAAA Resource Record Responses with Non_Recoverable_Name_Server_Error Failure."
    ::= { sonusSoftSwitchPesDnsEnumCounters 57 }

sonusSoftSwitchPesDnsEnumDNSAAAAResourceRecordRspNoData OBJECT-TYPE
    SYNTAX          Counter
    ACCESS          read-only
    STATUS          mandatory
    DESCRIPTION     
            "Number of DNS AAAA Resource Record Responses with Valid_Name_But_No_Data_Record Failure."
    ::= { sonusSoftSwitchPesDnsEnumCounters 58 }

sonusSoftSwitchPesHpcCallsCounters OBJECT IDENTIFIER
    ::= { sonusSoftSwitchPolicyExecutionServerStatistics 8 }

sonusSoftSwitchPesIngressPstnHpcCallsPerGsxTable OBJECT-TYPE
    SYNTAX          SEQUENCE OF SonusSoftSwitchPesHpcCallsCountersGsxEntry
    ACCESS          not-accessible
    STATUS          mandatory
    DESCRIPTION     
            "The HPC Calls related counters per GSX table."
    ::= { sonusSoftSwitchPesHpcCallsCounters 1 }

sonusSoftSwitchPesHpcCallsCountersGsxEntry OBJECT-TYPE
    SYNTAX          SonusSoftSwitchPesHpcCallsCountersGsxEntry
    ACCESS          not-accessible
    STATUS          mandatory
    DESCRIPTION     
            "An entry in the HPC Calls counters per GSX table."
    INDEX           { sonusSoftSwitchPesHpcCallsCountersGsxIp }
    ::= { sonusSoftSwitchPesIngressPstnHpcCallsPerGsxTable 1 }

SonusSoftSwitchPesHpcCallsCountersGsxEntry ::=
    SEQUENCE {
        sonusSoftSwitchPesHpcCallsCountersGsxIp       IpAddress,
        sonusSoftSwitchPesHpcCallsCountersGsxName         SonusName,
        sonusSoftSwitchPesHpcCallsCountersGsxIngressPstn                Counter
    }

sonusSoftSwitchPesHpcCallsCountersGsxIp OBJECT-TYPE
    SYNTAX          IpAddress
    ACCESS          read-only
    STATUS          mandatory
    DESCRIPTION     
            "The GSX IP Address that the HPC Calls counter apply to"
    ::= { sonusSoftSwitchPesHpcCallsCountersGsxEntry 1 }

sonusSoftSwitchPesHpcCallsCountersGsxName OBJECT-TYPE
    SYNTAX          SonusName
    ACCESS          read-only
    STATUS          mandatory
    DESCRIPTION     
            "The GSX Name that the HPC Calls counters apply to"
    ::= { sonusSoftSwitchPesHpcCallsCountersGsxEntry 2 }

sonusSoftSwitchPesHpcCallsCountersGsxIngressPstn OBJECT-TYPE
    SYNTAX          Counter
    ACCESS          read-only
    STATUS          mandatory
    DESCRIPTION     
            "The number of HPC Calls coming in from PSTN
             trunks"
    ::= { sonusSoftSwitchPesHpcCallsCountersGsxEntry 3 }

sonusSoftSwitchPesInapCounters OBJECT IDENTIFIER
    ::= { sonusSoftSwitchPolicyExecutionServerStatistics 9 }

sonusSoftSwitchPesInapCountersNumIdpSent OBJECT-TYPE
    SYNTAX          Counter
    ACCESS          read-only
    STATUS          mandatory
    DESCRIPTION     
            "Number of INAP Initial DP messages sent by the PSX."
    ::= { sonusSoftSwitchPesInapCounters 1 }

sonusSoftSwitchPesInapCountersNumIdpFailed OBJECT-TYPE
    SYNTAX          Counter
    ACCESS          read-only
    STATUS          mandatory
    DESCRIPTION     
            "Number of INAP Initial DP messages that failed."
    ::= { sonusSoftSwitchPesInapCounters 2 }

sonusSoftSwitchPesInapCountersNumReqTimeout OBJECT-TYPE
    SYNTAX          Counter
    ACCESS          read-only
    STATUS          mandatory
    DESCRIPTION     
            "Number of INAP TSSF timeouts for request messages sent by the PSX."
    ::= { sonusSoftSwitchPesInapCounters 3 }

sonusSoftSwitchPesInapCountersNumErrorRcvd OBJECT-TYPE
    SYNTAX          Counter
    ACCESS          read-only
    STATUS          mandatory
    DESCRIPTION     
            "Number of INAP User Error or Reject message received by the PSX."
    ::= { sonusSoftSwitchPesInapCounters 4 }

sonusSoftSwitchPesInapCountersNumErrorDetected OBJECT-TYPE
    SYNTAX          Counter
    ACCESS          read-only
    STATUS          mandatory
    DESCRIPTION     
            "Number of INAP User Error or Reject messages sent by the PSX."
    ::= { sonusSoftSwitchPesInapCounters 5 }

sonusSoftSwitchPesFailureCounters OBJECT IDENTIFIER
    ::= { sonusSoftSwitchPolicyExecutionServerStatistics 10 }

sonusSoftSwitchPesFailureCountersNumQueryError OBJECT-TYPE
    SYNTAX          Counter
    ACCESS          read-only
    STATUS          mandatory
    DESCRIPTION     
            "Number of requests that encountered an SQL Query Error."
    ::= { sonusSoftSwitchPesFailureCounters 1 }

sonusSoftSwitchPesFailureCountersNumInternalError OBJECT-TYPE
    SYNTAX          Counter
    ACCESS          read-only
    STATUS          mandatory
    DESCRIPTION     
            "Number of requests that encountered an Internal Error."
    ::= { sonusSoftSwitchPesFailureCounters 2 }

sonusSoftSwitchPesFailureCountersNumExternalError OBJECT-TYPE
    SYNTAX          Counter
    ACCESS          read-only
    STATUS          mandatory
    DESCRIPTION     
            "Number of requests that encountered an External Error."
    ::= { sonusSoftSwitchPesFailureCounters 3 }

sonusSoftSwitchPesNumOfCallsRecordedCounters OBJECT IDENTIFIER
    ::= { sonusSoftSwitchPolicyExecutionServerStatistics 11 }

sonusSoftSwitchPesNumCallsRecordedPerCRCTable OBJECT-TYPE
    SYNTAX          SEQUENCE OF SonusSoftSwitchPesNumOfCallsRecordedCountersCriteriaEntry
    ACCESS          not-accessible
    STATUS          mandatory
    DESCRIPTION     
            "Number of call recorded related counters per Call_recording_criteria table."
    ::= { sonusSoftSwitchPesNumOfCallsRecordedCounters 1 }

sonusSoftSwitchPesNumOfCallsRecordedCountersCriteriaEntry OBJECT-TYPE
    SYNTAX          SonusSoftSwitchPesNumOfCallsRecordedCountersCriteriaEntry
    ACCESS          not-accessible
    STATUS          mandatory
    DESCRIPTION     
            "An entry in the Call recording counters per CRC table."
    INDEX           { 
                      sonusSoftSwitchPesNumOfCallsRecordedCountersCriteriaName }
    ::= { sonusSoftSwitchPesNumCallsRecordedPerCRCTable 1 }

SonusSoftSwitchPesNumOfCallsRecordedCountersCriteriaEntry ::=
    SEQUENCE {
        sonusSoftSwitchPesNumOfCallsRecordedCountersCriteriaName                        SonusName,
        sonusSoftSwitchPesNumOfCallsRecordedCountersNumCalls                    Counter
    }

sonusSoftSwitchPesNumOfCallsRecordedCountersCriteriaName OBJECT-TYPE
    SYNTAX          SonusName
    ACCESS          read-only
    STATUS          mandatory
    DESCRIPTION     
            "The Crriteria Name that the Num Call recorded counter apply to"
    ::= { sonusSoftSwitchPesNumOfCallsRecordedCountersCriteriaEntry 1 }

sonusSoftSwitchPesNumOfCallsRecordedCountersNumCalls OBJECT-TYPE
    SYNTAX          Counter
    ACCESS          read-only
    STATUS          mandatory
    DESCRIPTION     
            "The Number of calls recorded for the criteria"
    ::= { sonusSoftSwitchPesNumOfCallsRecordedCountersCriteriaEntry 2 }

sonusSoftSwitchPesInboundEnumCounters OBJECT IDENTIFIER
    ::= { sonusSoftSwitchPolicyExecutionServerStatistics 12 }

sonusSoftSwitchPesInboundEnumTotalRequestsReceived OBJECT-TYPE
    SYNTAX          Counter
    ACCESS          read-only
    STATUS          mandatory
    DESCRIPTION     
            "Total number of Inbound ENUM requests received by PSX."
    ::= { sonusSoftSwitchPesInboundEnumCounters 1 }

sonusSoftSwitchPesInboundEnumTotalResponsesSent OBJECT-TYPE
    SYNTAX          Counter
    ACCESS          read-only
    STATUS          mandatory
    DESCRIPTION     
            "Total number of ENUME responses sent by PSX."
    ::= { sonusSoftSwitchPesInboundEnumCounters 2 }

sonusSoftSwitchPesInboundEnumTotalSuccessResponsesSent OBJECT-TYPE
    SYNTAX          Counter
    ACCESS          read-only
    STATUS          mandatory
    DESCRIPTION     
            "Total number of Successful ENUM responses sent by PSX."
    ::= { sonusSoftSwitchPesInboundEnumCounters 3 }

sonusSoftSwitchPesInboundEnumServFailureResponseSent OBJECT-TYPE
    SYNTAX          Counter
    ACCESS          read-only
    STATUS          mandatory
    DESCRIPTION     
            "Total number of Server Failure ENUM responses sent by PSX."
    ::= { sonusSoftSwitchPesInboundEnumCounters 4 }

sonusSoftSwitchPesInboundEnumNameErrorResponseSent OBJECT-TYPE
    SYNTAX          Counter
    ACCESS          read-only
    STATUS          mandatory
    DESCRIPTION     
            "Total number of Name Error ENUM responses sent by PSX."
    ::= { sonusSoftSwitchPesInboundEnumCounters 5 }

sonusSoftSwitchPesCallContextCounters OBJECT IDENTIFIER
    ::= { sonusSoftSwitchPolicyExecutionServerStatistics 13 }

sonusSoftSwitchPesCallContextCountersNumCCUsed OBJECT-TYPE
    SYNTAX          Gauge
    ACCESS          read-only
    STATUS          mandatory
    DESCRIPTION     
            "Number of call contexts that are currently in use."
    ::= { sonusSoftSwitchPesCallContextCounters 1 }

sonusSoftSwitchPesCallContextCountersNumCallsDropped OBJECT-TYPE
    SYNTAX          Counter
    ACCESS          read-only
    STATUS          mandatory
    DESCRIPTION     
            "Number of calls that are dropped due to a lack of
             the call context available."
    ::= { sonusSoftSwitchPesCallContextCounters 2 }

sonusSoftSwitchPesCallContextCountersNumEntriesInCCCache OBJECT-TYPE
    SYNTAX          Counter
    ACCESS          read-only
    STATUS          mandatory
    DESCRIPTION     
            "Number of Entries In Cache"
    ::= { sonusSoftSwitchPesCallContextCounters 3 }

sonusSoftSwitchPesCapCounters OBJECT IDENTIFIER
    ::= { sonusSoftSwitchPolicyExecutionServerStatistics 14 }

sonusSoftSwitchPesCapCounterTable OBJECT-TYPE
    SYNTAX          SEQUENCE OF SonusSoftSwitchPesCapCountersEntry
    ACCESS          not-accessible
    STATUS          mandatory
    DESCRIPTION     
            "Number of CAP counters."
    ::= { sonusSoftSwitchPesCapCounters 1 }

sonusSoftSwitchPesCapCountersEntry OBJECT-TYPE
    SYNTAX          SonusSoftSwitchPesCapCountersEntry
    ACCESS          not-accessible
    STATUS          mandatory
    DESCRIPTION     
            "An entry in the CAP Counters table."
    INDEX           { sonusSoftSwitchPesCapCountersSkValue, 
                      sonusSoftSwitchPesCapCountersServiceTypeValue }
    ::= { sonusSoftSwitchPesCapCounterTable 1 }

SonusSoftSwitchPesCapCountersEntry ::=
    SEQUENCE {
        sonusSoftSwitchPesCapCountersSkValue    INTEGER,
        sonusSoftSwitchPesCapCountersServiceTypeValue             INTEGER,
        sonusSoftSwitchPesCapCountersNumIdpSent       Counter,
        sonusSoftSwitchPesCapCountersNumConRcvd       Counter,
        sonusSoftSwitchPesCapCountersNumCueCwaRcvd          Counter,
        sonusSoftSwitchPesCapCountersNumEtcRcvd       Counter,
        sonusSoftSwitchPesCapCountersNumCapRelRcvd          Counter,
        sonusSoftSwitchPesCapCountersNumSsfErr      Counter,
        sonusSoftSwitchPesCapCountersNumScfErr      Counter,
        sonusSoftSwitchPesCapCountersNumCapAriSent          Counter,
        sonusSoftSwitchPesCapCountersNumCapCtrRcvd          Counter
    }

sonusSoftSwitchPesCapCountersSkValue OBJECT-TYPE
    SYNTAX          INTEGER
    ACCESS          read-only
    STATUS          mandatory
    DESCRIPTION     
            "Key1: Service Key"
    DEFVAL          { 0 }
    ::= { sonusSoftSwitchPesCapCountersEntry 1 }

sonusSoftSwitchPesCapCountersServiceTypeValue OBJECT-TYPE
    SYNTAX          INTEGER
    ACCESS          read-only
    STATUS          mandatory
    DESCRIPTION     
            "Key2: Service Type"
    DEFVAL          { 0 }
    ::= { sonusSoftSwitchPesCapCountersEntry 2 }

sonusSoftSwitchPesCapCountersNumIdpSent OBJECT-TYPE
    SYNTAX          Counter
    ACCESS          read-only
    STATUS          mandatory
    DESCRIPTION     
            "Number of CAP Initial DP messages sent by the PSX."
    DEFVAL          { 0 }
    ::= { sonusSoftSwitchPesCapCountersEntry 3 }

sonusSoftSwitchPesCapCountersNumConRcvd OBJECT-TYPE
    SYNTAX          Counter
    ACCESS          read-only
    STATUS          mandatory
    DESCRIPTION     
            "Number of CAMEL Connect messages received."
    DEFVAL          { 0 }
    ::= { sonusSoftSwitchPesCapCountersEntry 4 }

sonusSoftSwitchPesCapCountersNumCueCwaRcvd OBJECT-TYPE
    SYNTAX          Counter
    ACCESS          read-only
    STATUS          mandatory
    DESCRIPTION     
            "Number of CAP Continue and Continue with Argument messages received."
    DEFVAL          { 0 }
    ::= { sonusSoftSwitchPesCapCountersEntry 5 }

sonusSoftSwitchPesCapCountersNumEtcRcvd OBJECT-TYPE
    SYNTAX          Counter
    ACCESS          read-only
    STATUS          mandatory
    DESCRIPTION     
            "Number of CAP ETC messages received"
    DEFVAL          { 0 }
    ::= { sonusSoftSwitchPesCapCountersEntry 6 }

sonusSoftSwitchPesCapCountersNumCapRelRcvd OBJECT-TYPE
    SYNTAX          Counter
    ACCESS          read-only
    STATUS          mandatory
    DESCRIPTION     
            "Number of CAP RELEASE messages received"
    DEFVAL          { 0 }
    ::= { sonusSoftSwitchPesCapCountersEntry 7 }

sonusSoftSwitchPesCapCountersNumSsfErr OBJECT-TYPE
    SYNTAX          Counter
    ACCESS          read-only
    STATUS          mandatory
    DESCRIPTION     
            " Number of CAP Errors messages From SSF to SCF."
    DEFVAL          { 0 }
    ::= { sonusSoftSwitchPesCapCountersEntry 8 }

sonusSoftSwitchPesCapCountersNumScfErr OBJECT-TYPE
    SYNTAX          Counter
    ACCESS          read-only
    STATUS          mandatory
    DESCRIPTION     
            "Number of CAP Errors messages From SCF to SSF."
    DEFVAL          { 0 }
    ::= { sonusSoftSwitchPesCapCountersEntry 9 }

sonusSoftSwitchPesCapCountersNumCapAriSent OBJECT-TYPE
    SYNTAX          Counter
    ACCESS          read-only
    STATUS          mandatory
    DESCRIPTION     
            "Number of CAP ARI messages Sent by PSX"
    DEFVAL          { 0 }
    ::= { sonusSoftSwitchPesCapCountersEntry 10 }

sonusSoftSwitchPesCapCountersNumCapCtrRcvd OBJECT-TYPE
    SYNTAX          Counter
    ACCESS          read-only
    STATUS          mandatory
    DESCRIPTION     
            "Number of CAP CTR messages received"
    DEFVAL          { 0 }
    ::= { sonusSoftSwitchPesCapCountersEntry 11 }

sonusSoftSwitchPesLcrCounters OBJECT IDENTIFIER
    ::= { sonusSoftSwitchPolicyExecutionServerStatistics 15 }

sonusSoftSwitchPesLcrCallTypeIntraLata OBJECT-TYPE
    SYNTAX          Counter
    ACCESS          read-only
    STATUS          mandatory
    DESCRIPTION     
            "A count of how many LCR calls are identified as intra lata call type."
    ::= { sonusSoftSwitchPesLcrCounters 1 }

sonusSoftSwitchPesLcrCallTypeInterLata OBJECT-TYPE
    SYNTAX          Counter
    ACCESS          read-only
    STATUS          mandatory
    DESCRIPTION     
            "A count of how many LCR calls are identified as inter lata call type."
    ::= { sonusSoftSwitchPesLcrCounters 2 }

sonusSoftSwitchPesLcrCallTypeUnknown OBJECT-TYPE
    SYNTAX          Counter
    ACCESS          read-only
    STATUS          mandatory
    DESCRIPTION     
            "Number of A count of how many LCR calls are identified as unknown call type."
    ::= { sonusSoftSwitchPesLcrCounters 3 }

sonusSoftSwitchPesLcrTotalCalls OBJECT-TYPE
    SYNTAX          Counter
    ACCESS          read-only
    STATUS          mandatory
    DESCRIPTION     
            "The total number of LCR calls processed by the PSX."
    ::= { sonusSoftSwitchPesLcrCounters 4 }

sonusSoftSwitchPesLcrCallTypeIntraLataLocal OBJECT-TYPE
    SYNTAX          Counter
    ACCESS          read-only
    STATUS          mandatory
    DESCRIPTION     
            "A count of how many LCR calls are identified as intra lata local call type."
    ::= { sonusSoftSwitchPesLcrCounters 5 }

sonusSoftSwitchPesLcrCallTypeInterLataLocal OBJECT-TYPE
    SYNTAX          Counter
    ACCESS          read-only
    STATUS          mandatory
    DESCRIPTION     
            "A count of how many LCR calls are identified as inter lata local call type."
    ::= { sonusSoftSwitchPesLcrCounters 6 }

sonusSoftSwitchCPSLicenseCounters OBJECT IDENTIFIER
    ::= { sonusSoftSwitchPolicyExecutionServerStatistics 16 }

sonusSoftSwitchCPSLicenseDplus OBJECT-TYPE
    SYNTAX          Counter
    ACCESS          read-only
    STATUS          mandatory
    DESCRIPTION     
            "CPS License capacity for D+ Interface"
    ::= { sonusSoftSwitchCPSLicenseCounters 1 }

-- sonusSoftSwitchAcceptedCPSDplus OBJECT-TYPE
--     SYNTAX          Counter64
--     ACCESS          read-only
--     STATUS          mandatory
--     DESCRIPTION     
--             "Calls Accepted for D+ Interface with CPS Based Licensing enforced"
--     ::= { sonusSoftSwitchCPSLicenseCounters 2 }

-- sonusSoftSwitchRejectedCPSDplus OBJECT-TYPE
--     SYNTAX          Counter64
--     ACCESS          read-only
--     STATUS          mandatory
--     DESCRIPTION     
--             "Calls Rejected for D+ Interface with CPS Based Licensing enforced"
--     ::= { sonusSoftSwitchCPSLicenseCounters 3 }

sonusSoftSwitchCPSLicenseSipe OBJECT-TYPE
    SYNTAX          Counter
    ACCESS          read-only
    STATUS          mandatory
    DESCRIPTION     
            "CPS License capacity for Sipe Interface"
    ::= { sonusSoftSwitchCPSLicenseCounters 4 }

-- sonusSoftSwitchAcceptedCPSSipe OBJECT-TYPE
--     SYNTAX          Counter64
--     ACCESS          read-only
--     STATUS          mandatory
--     DESCRIPTION     
--             "Calls Accepted for Sipe Interface with CPS Based Licensing enforced"
--     ::= { sonusSoftSwitchCPSLicenseCounters 5 }

-- sonusSoftSwitchRejectedCPSSipe OBJECT-TYPE
--     SYNTAX          Counter64
--     ACCESS          read-only
--     STATUS          mandatory
--     DESCRIPTION     
--             "Calls Rejected for Sipe Interface with CPS Based Licensing enforced"
--     ::= { sonusSoftSwitchCPSLicenseCounters 6 }

sonusSoftSwitchCPSLicenseEnume OBJECT-TYPE
    SYNTAX          Counter
    ACCESS          read-only
    STATUS          mandatory
    DESCRIPTION     
            "CPS License capacity for Enume Interface"
    ::= { sonusSoftSwitchCPSLicenseCounters 7 }

-- sonusSoftSwitchAcceptedCPSEnume OBJECT-TYPE
--     SYNTAX          Counter64
--     ACCESS          read-only
--     STATUS          mandatory
--     DESCRIPTION     
--             "Calls Accepted for Enume Interface with CPS Based Licensing enforced"
--     ::= { sonusSoftSwitchCPSLicenseCounters 8 }

-- sonusSoftSwitchRejectedCPSEnume OBJECT-TYPE
--     SYNTAX          Counter64
--     ACCESS          read-only
--     STATUS          mandatory
--     DESCRIPTION     
--             "Calls Rejected for Enume Interface with CPS Based Licensing enforced"
--     ::= { sonusSoftSwitchCPSLicenseCounters 9 }

sonusSoftSwitchPeakCPSDplus OBJECT-TYPE
    SYNTAX          Gauge
    ACCESS          read-only
    STATUS          mandatory
    DESCRIPTION     
            "Peak CPS usage for DPLUS Interface when CPS Based Licensing is enforced."
    ::= { sonusSoftSwitchCPSLicenseCounters 10 }

sonusSoftSwitchPeakCPSSipe OBJECT-TYPE
    SYNTAX          Gauge
    ACCESS          read-only
    STATUS          mandatory
    DESCRIPTION     
            "Peak CPS usage for SIPE Interface when CPS Based Licensing is enforced."
    ::= { sonusSoftSwitchCPSLicenseCounters 11 }

sonusSoftSwitchPeakCPSEnume OBJECT-TYPE
    SYNTAX          Gauge
    ACCESS          read-only
    STATUS          mandatory
    DESCRIPTION     
            "Peak CPS usage for ENUME Interface when CPS Based Licensing is enforced."
    ::= { sonusSoftSwitchCPSLicenseCounters 12 }

-- sonusSoftSwitchAcceptedCPSInvite OBJECT-TYPE
--     SYNTAX          Counter64
--     ACCESS          read-only
--     STATUS          mandatory
--     DESCRIPTION     
--             "Invite Calls Accepted for Sipe Interface with CPS Based Licensing enforced"
--     ::= { sonusSoftSwitchCPSLicenseCounters 13 }

-- sonusSoftSwitchAcceptedCPSSubscribe OBJECT-TYPE
--     SYNTAX          Counter64
--     ACCESS          read-only
--     STATUS          mandatory
--     DESCRIPTION     
--             "Subscribe Calls Accepted for Sipe Interface with CPS Based Licensing enforced"
--     ::= { sonusSoftSwitchCPSLicenseCounters 14 }

-- sonusSoftSwitchAcceptedCPSNotify OBJECT-TYPE
--     SYNTAX          Counter64
--     ACCESS          read-only
--     STATUS          mandatory
--     DESCRIPTION     
--             "Notify Calls Accepted for Sipe Interface with CPS Based Licensing enforced"
--     ::= { sonusSoftSwitchCPSLicenseCounters 15 }

-- sonusSoftSwitchAcceptedCPSRegister OBJECT-TYPE
--     SYNTAX          Counter64
--     ACCESS          read-only
--     STATUS          mandatory
--     DESCRIPTION     
--             "Register Calls Accepted for Sipe Interface with CPS Based Licensing enforced"
--     ::= { sonusSoftSwitchCPSLicenseCounters 16 }

-- sonusSoftSwitchAcceptedCPSOptions OBJECT-TYPE
--     SYNTAX          Counter64
--     ACCESS          read-only
--     STATUS          mandatory
--     DESCRIPTION     
--             "Options Calls Accepted for Sipe Interface with CPS Based Licensing enforced"
--     ::= { sonusSoftSwitchCPSLicenseCounters 17 }

-- sonusSoftSwitchAcceptedCPSMessage OBJECT-TYPE
--     SYNTAX          Counter64
--     ACCESS          read-only
--     STATUS          mandatory
--     DESCRIPTION     
--             "Message Calls Accepted for Sipe Interface with CPS Based Licensing enforced"
--     ::= { sonusSoftSwitchCPSLicenseCounters 18 }

-- sonusSoftSwitchAcceptedCPSRefer OBJECT-TYPE
--     SYNTAX          Counter64
--     ACCESS          read-only
--     STATUS          mandatory
--     DESCRIPTION     
--             "Refer Calls Accepted for Sipe Interface with CPS Based Licensing enforced"
--     ::= { sonusSoftSwitchCPSLicenseCounters 19 }

-- sonusSoftSwitchAcceptedCPSOthers OBJECT-TYPE
--     SYNTAX          Counter64
--     ACCESS          read-only
--     STATUS          mandatory
--     DESCRIPTION     
--             "Others Calls Accepted for Sipe Interface with CPS Based Licensing enforced"
--     ::= { sonusSoftSwitchCPSLicenseCounters 20 }

sonusSoftSwitchPeakCPSInvite OBJECT-TYPE
    SYNTAX          Gauge
    ACCESS          read-only
    STATUS          mandatory
    DESCRIPTION     
            "Invite Peak CPS usage for SIPE Interface when CPS Based Licensing is enforced."
    ::= { sonusSoftSwitchCPSLicenseCounters 21 }

sonusSoftSwitchPeakCPSSubscribe OBJECT-TYPE
    SYNTAX          Gauge
    ACCESS          read-only
    STATUS          mandatory
    DESCRIPTION     
            "Subscribe Peak CPS usage for SIPE Interface when CPS Based Licensing is enforced."
    ::= { sonusSoftSwitchCPSLicenseCounters 22 }

sonusSoftSwitchPeakCPSNotify OBJECT-TYPE
    SYNTAX          Gauge
    ACCESS          read-only
    STATUS          mandatory
    DESCRIPTION     
            "Notify Peak CPS usage for SIPE Interface when CPS Based Licensing is enforced."
    ::= { sonusSoftSwitchCPSLicenseCounters 23 }

sonusSoftSwitchPeakCPSRegister OBJECT-TYPE
    SYNTAX          Gauge
    ACCESS          read-only
    STATUS          mandatory
    DESCRIPTION     
            "Register Peak CPS usage for SIPE Interface when CPS Based Licensing is enforced."
    ::= { sonusSoftSwitchCPSLicenseCounters 24 }

sonusSoftSwitchPeakCPSOptions OBJECT-TYPE
    SYNTAX          Gauge
    ACCESS          read-only
    STATUS          mandatory
    DESCRIPTION     
            "Options Peak CPS usage for SIPE Interface when CPS Based Licensing is enforced."
    ::= { sonusSoftSwitchCPSLicenseCounters 25 }

sonusSoftSwitchPeakCPSMessage OBJECT-TYPE
    SYNTAX          Gauge
    ACCESS          read-only
    STATUS          mandatory
    DESCRIPTION     
            "Message Peak CPS usage for SIPE Interface when CPS Based Licensing is enforced."
    ::= { sonusSoftSwitchCPSLicenseCounters 26 }

sonusSoftSwitchPeakCPSRefer OBJECT-TYPE
    SYNTAX          Gauge
    ACCESS          read-only
    STATUS          mandatory
    DESCRIPTION     
            "Refer Peak CPS usage for SIPE Interface when CPS Based Licensing is enforced."
    ::= { sonusSoftSwitchCPSLicenseCounters 27 }

sonusSoftSwitchPeakCPSOthers OBJECT-TYPE
    SYNTAX          Gauge
    ACCESS          read-only
    STATUS          mandatory
    DESCRIPTION     
            "Others Peak CPS usage for SIPE Interface when CPS Based Licensing is enforced."
    ::= { sonusSoftSwitchCPSLicenseCounters 28 }

sonusSoftSwitchLicenseMode OBJECT-TYPE
    SYNTAX          Gauge
    ACCESS          read-only
    STATUS          mandatory
    DESCRIPTION     
            "License Mode of the node: 0 = Node Locked. 1 = Domain Locked, 2 = SLS based. "
    ::= { sonusSoftSwitchCPSLicenseCounters 29 }

sonusSoftSwitchPesDscNpCounters OBJECT IDENTIFIER
    ::= { sonusSoftSwitchPolicyExecutionServerStatistics 17 }

sonusSoftSwitchPesDscNpRequest OBJECT-TYPE
    SYNTAX          Counter
    ACCESS          read-only
    STATUS          mandatory
    DESCRIPTION     
            "The total number of DSC originated NP requests received."
    ::= { sonusSoftSwitchPesDscNpCounters 1 }

sonusSoftSwitchPesDscNpSuccess OBJECT-TYPE
    SYNTAX          Counter
    ACCESS          read-only
    STATUS          mandatory
    DESCRIPTION     
            "The total number of DSC NP responses where the status was set to Success."
    ::= { sonusSoftSwitchPesDscNpCounters 2 }

sonusSoftSwitchPesDscNpPorted OBJECT-TYPE
    SYNTAX          Counter
    ACCESS          read-only
    STATUS          mandatory
    DESCRIPTION     
            "The total number of DSC NP requests that resulted in a ported number with an LRN/RN"
    ::= { sonusSoftSwitchPesDscNpCounters 3 }

sonusSoftSwitchPesDscNpNotPorted OBJECT-TYPE
    SYNTAX          Counter
    ACCESS          read-only
    STATUS          mandatory
    DESCRIPTION     
            "The total number of DSC NP requests that resulted in a number that was not ported."
    ::= { sonusSoftSwitchPesDscNpCounters 4 }

sonusSoftSwitchPesDscNpPredipped OBJECT-TYPE
    SYNTAX          Counter
    ACCESS          read-only
    STATUS          mandatory
    DESCRIPTION     
            "The total number of DSC NP requests that were received where the number portability check had already been performed."
    ::= { sonusSoftSwitchPesDscNpCounters 5 }

sonusSoftSwitchPesDscNpFailure OBJECT-TYPE
    SYNTAX          Counter
    ACCESS          read-only
    STATUS          mandatory
    DESCRIPTION     
            "The total number of DSC NP responses where the status was set to Failure."
    ::= { sonusSoftSwitchPesDscNpCounters 6 }

sonusSoftSwitchPesHttpcCounters OBJECT IDENTIFIER
    ::= { sonusSoftSwitchPolicyExecutionServerStatistics 18 }

sonusSoftSwitchPesHttpcSignReqCounter OBJECT-TYPE
    SYNTAX          Counter
    ACCESS          read-only
    STATUS          mandatory
    DESCRIPTION     
            "Count of Signing Service Requests"
    ::= { sonusSoftSwitchPesHttpcCounters 1 }

sonusSoftSwitchPesHttpcSignRespCounter OBJECT-TYPE
    SYNTAX          Counter
    ACCESS          read-only
    STATUS          mandatory
    DESCRIPTION     
            "Count of Signing Service Response."
    ::= { sonusSoftSwitchPesHttpcCounters 2 }

sonusSoftSwitchPesHttpcSignTimeOutCounter OBJECT-TYPE
    SYNTAX          Counter
    ACCESS          read-only
    STATUS          mandatory
    DESCRIPTION     
            "Count of Signing Service TimeOut"
    ::= { sonusSoftSwitchPesHttpcCounters 3 }

sonusSoftSwitchPesHttpcSignMissingParamCounter OBJECT-TYPE
    SYNTAX          Counter
    ACCESS          read-only
    STATUS          mandatory
    DESCRIPTION     
            "Count of Signing Service failure due to Missing Mandatory Paramaters."
    ::= { sonusSoftSwitchPesHttpcCounters 4 }

sonusSoftSwitchPesHttpcVerReqCounter OBJECT-TYPE
    SYNTAX          Counter
    ACCESS          read-only
    STATUS          mandatory
    DESCRIPTION     
            "Count of Verification Service Requests"
    ::= { sonusSoftSwitchPesHttpcCounters 5 }

sonusSoftSwitchPesHttpcVerRespCounter OBJECT-TYPE
    SYNTAX          Counter
    ACCESS          read-only
    STATUS          mandatory
    DESCRIPTION     
            "Count of Verification Service Response."
    ::= { sonusSoftSwitchPesHttpcCounters 6 }

sonusSoftSwitchPesHttpcVerTimeOutCounter OBJECT-TYPE
    SYNTAX          Counter
    ACCESS          read-only
    STATUS          mandatory
    DESCRIPTION     
            "Count of Verification Service TimeOut"
    ::= { sonusSoftSwitchPesHttpcCounters 7 }

sonusSoftSwitchPesHttpcVerMissingParamCounter OBJECT-TYPE
    SYNTAX          Counter
    ACCESS          read-only
    STATUS          mandatory
    DESCRIPTION     
            "Count of Verification Service failure due to Missing Mandatory Paramaters."
    ::= { sonusSoftSwitchPesHttpcCounters 8 }

sonusSoftSwitchPesHttpcTagMissingParamCounter OBJECT-TYPE
    SYNTAX          Counter
    ACCESS          read-only
    STATUS          mandatory
    DESCRIPTION     
            "Count of Tagging Service failure due to Missing Mandatory Paramaters."
    ::= { sonusSoftSwitchPesHttpcCounters 9 }

sonusSoftSwitchPesHttpcRESTReqCounter OBJECT-TYPE
    SYNTAX          Counter
    ACCESS          read-only
    STATUS          mandatory
    DESCRIPTION     
            "Count of REST Service Requests"
    ::= { sonusSoftSwitchPesHttpcCounters 10 }

sonusSoftSwitchPesHttpcRESTRespCounter OBJECT-TYPE
    SYNTAX          Counter
    ACCESS          read-only
    STATUS          mandatory
    DESCRIPTION     
            "Count of REST Service Response."
    ::= { sonusSoftSwitchPesHttpcCounters 11 }

sonusSoftSwitchPesHttpcRESTTimeOutCounter OBJECT-TYPE
    SYNTAX          Counter
    ACCESS          read-only
    STATUS          mandatory
    DESCRIPTION     
            "Count of REST Service TimeOut"
    ::= { sonusSoftSwitchPesHttpcCounters 12 }

sonusSoftSwitchPesHttpcRESTMissingParamCounter OBJECT-TYPE
    SYNTAX          Counter
    ACCESS          read-only
    STATUS          mandatory
    DESCRIPTION     
            "Count of REST Service failure due to Missing Mandatory Paramaters."
    ::= { sonusSoftSwitchPesHttpcCounters 13 }

sonusSoftSwitchPesHttpcRESTMissingRespParamCounter OBJECT-TYPE
    SYNTAX          Counter
    ACCESS          read-only
    STATUS          mandatory
    DESCRIPTION     
            "Count of REST Service failure due to Missing Mandatory Response Paramaters."
    ::= { sonusSoftSwitchPesHttpcCounters 14 }

sonusSoftSwitchPesHpcGetsCounters OBJECT IDENTIFIER
    ::= { sonusSoftSwitchPolicyExecutionServerStatistics 19 }

sonusSoftSwitchPesHPCTotalRequestsCounter OBJECT-TYPE
    SYNTAX          Counter
    ACCESS          read-only
    STATUS          mandatory
    DESCRIPTION     
            "Count of Total HPC calls "
    ::= { sonusSoftSwitchPesHpcGetsCounters 1 }

sonusSoftSwitchPesNonHPCTotalRequestsCounter OBJECT-TYPE
    SYNTAX          Counter
    ACCESS          read-only
    STATUS          mandatory
    DESCRIPTION     
            "Count of Total non-HPC calls "
    ::= { sonusSoftSwitchPesHpcGetsCounters 2 }

sonusSoftSwitchPesHPCTotalRequestsFailedCounter OBJECT-TYPE
    SYNTAX          Counter
    ACCESS          read-only
    STATUS          mandatory
    DESCRIPTION     
            "Count of Total HPC calls Failed"
    ::= { sonusSoftSwitchPesHpcGetsCounters 3 }

sonusSoftSwitchPesNonHPCTotalRequestsFailedCounter OBJECT-TYPE
    SYNTAX          Counter
    ACCESS          read-only
    STATUS          mandatory
    DESCRIPTION     
            "Count of Total Non-HPC calls failed"
    ::= { sonusSoftSwitchPesHpcGetsCounters 4 }

sonusSoftSwitchPesEscapedServiceCounters OBJECT IDENTIFIER
    ::= { sonusSoftSwitchPolicyExecutionServerStatistics 20 }

sonusSoftSwitchPesEscapedServiceCounterTable OBJECT-TYPE
    SYNTAX          SEQUENCE OF SonusSoftSwitchPesEscapedServiceCountersEntry
    ACCESS          not-accessible
    STATUS          mandatory
    DESCRIPTION     
            "The Escaped Service Counters due to license unavailability table."
    ::= { sonusSoftSwitchPesEscapedServiceCounters 1 }

sonusSoftSwitchPesEscapedServiceCountersEntry OBJECT-TYPE
    SYNTAX          SonusSoftSwitchPesEscapedServiceCountersEntry
    ACCESS          not-accessible
    STATUS          mandatory
    DESCRIPTION     
            "An entry in the Escaped Service Counters due to license unavailability table."
    INDEX           { sonusSoftSwitchPesEscapedServiceCountersName }
    ::= { sonusSoftSwitchPesEscapedServiceCounterTable 1 }

SonusSoftSwitchPesEscapedServiceCountersEntry ::=
    SEQUENCE {
        sonusSoftSwitchPesEscapedServiceCountersName            SonusName
--         sonusSoftSwitchPesEscapedServiceCountersCount             Counter64
    }

sonusSoftSwitchPesEscapedServiceCountersName OBJECT-TYPE
    SYNTAX          SonusName
    ACCESS          read-only
    STATUS          mandatory
    DESCRIPTION     
            "The Service Name that the Escaped counters due to license unavailability apply to"
    ::= { sonusSoftSwitchPesEscapedServiceCountersEntry 1 }

-- sonusSoftSwitchPesEscapedServiceCountersCount OBJECT-TYPE
--     SYNTAX          Counter64
--     ACCESS          read-only
--     STATUS          mandatory
--     DESCRIPTION     
--             "The number of times service escaped"
--     ::= { sonusSoftSwitchPesEscapedServiceCountersEntry 2 }

sonusSoftSwitchPesTriggeredServiceCounters OBJECT IDENTIFIER
    ::= { sonusSoftSwitchPolicyExecutionServerStatistics 21 }

sonusSoftSwitchPesTriggeredServiceCounterTable OBJECT-TYPE
    SYNTAX          SEQUENCE OF SonusSoftSwitchPesTriggeredServiceCountersEntry
    ACCESS          not-accessible
    STATUS          mandatory
    DESCRIPTION     
            "The Triggered Service Counters due to license availability table."
    ::= { sonusSoftSwitchPesTriggeredServiceCounters 1 }

sonusSoftSwitchPesTriggeredServiceCountersEntry OBJECT-TYPE
    SYNTAX          SonusSoftSwitchPesTriggeredServiceCountersEntry
    ACCESS          not-accessible
    STATUS          mandatory
    DESCRIPTION     
            "An entry in the Triggered Service Counters due to license availability table."
    INDEX           { sonusSoftSwitchPesTriggeredServiceCountersName }
    ::= { sonusSoftSwitchPesTriggeredServiceCounterTable 1 }

SonusSoftSwitchPesTriggeredServiceCountersEntry ::=
    SEQUENCE {
        sonusSoftSwitchPesTriggeredServiceCountersName              SonusName
--         sonusSoftSwitchPesTriggeredServiceCountersCount               Counter64
    }

sonusSoftSwitchPesTriggeredServiceCountersName OBJECT-TYPE
    SYNTAX          SonusName
    ACCESS          read-only
    STATUS          mandatory
    DESCRIPTION     
            "The Service Name that the Triggered counters due to license availability apply to"
    ::= { sonusSoftSwitchPesTriggeredServiceCountersEntry 1 }

-- sonusSoftSwitchPesTriggeredServiceCountersCount OBJECT-TYPE
--     SYNTAX          Counter64
--     ACCESS          read-only
--     STATUS          mandatory
--     DESCRIPTION     
--             "The number of times service triggered"
--     ::= { sonusSoftSwitchPesTriggeredServiceCountersEntry 2 }

sonusSoftSwitchLnpPerSipServerCounters OBJECT IDENTIFIER
    ::= { sonusSoftSwitchPolicyExecutionServerStatistics 22 }

sonusSoftSwitchLnpPerSipServerCountersTable OBJECT-TYPE
    SYNTAX          SEQUENCE OF SonusSoftSwitchLnpCountersEntry
    ACCESS          not-accessible
    STATUS          mandatory
    DESCRIPTION     
            "LNP Counters Per Sip Server"
    ::= { sonusSoftSwitchLnpPerSipServerCounters 1 }

sonusSoftSwitchLnpCountersEntry OBJECT-TYPE
    SYNTAX          SonusSoftSwitchLnpCountersEntry
    ACCESS          not-accessible
    STATUS          mandatory
    DESCRIPTION     
            "An entry of Traffic counters related to LNP "
    INDEX           { 
                      sonusSoftSwitchLnpPerSipServerCountersSipServerName }
    ::= { sonusSoftSwitchLnpPerSipServerCountersTable 1 }

SonusSoftSwitchLnpCountersEntry ::=
    SEQUENCE {
        sonusSoftSwitchLnpPerSipServerCountersSipServerName                   DisplayString,
        sonusSoftSwitchLnpPerSipServerCountersLnpReqRcvd                Counter,
        sonusSoftSwitchLnpPerSipServerCountersLnpReqWithLrnRsp                      Counter,
        sonusSoftSwitchLnpPerSipServerCountersLnpReqWithoutLrnRsp                         Counter,
        sonusSoftSwitchLnpPerSipServerCountersClassTypeRecvd                    Counter,
        sonusSoftSwitchLnpPerSipServerCountersClassTypeSuccess                      Counter,
        sonusSoftSwitchLnpPerSipServerCountersClassTypeFailed                     Counter,
        sonusSoftSwitchLnpPerSipServerCountersLidbTypeRecvd                   Counter,
        sonusSoftSwitchLnpPerSipServerCountersLidbTypeSuccess                     Counter,
        sonusSoftSwitchLnpPerSipServerCountersLidbTypeFailed                    Counter,
        sonusSoftSwitchLnpPerSipServerCountersCnamTypeRecvd                   Counter,
        sonusSoftSwitchLnpPerSipServerCountersCnamTypeSuccess                     Counter,
        sonusSoftSwitchLnpPerSipServerCountersCnamTypeFailed                    Counter,
        sonusSoftSwitchLnpPerSipServerCountersIsvmTypeRecvd                   Counter,
        sonusSoftSwitchLnpPerSipServerCountersIsvmTypeSuccess                     Counter,
        sonusSoftSwitchLnpPerSipServerCountersIsvmTypeFailed                    Counter
    }

sonusSoftSwitchLnpPerSipServerCountersSipServerName OBJECT-TYPE
    SYNTAX          DisplayString
    ACCESS          read-only
    STATUS          mandatory
    DESCRIPTION     
            "Sip Server Name."
    ::= { sonusSoftSwitchLnpCountersEntry 1 }

sonusSoftSwitchLnpPerSipServerCountersLnpReqRcvd OBJECT-TYPE
    SYNTAX          Counter
    ACCESS          read-only
    STATUS          mandatory
    DESCRIPTION     
            "This counter keeps track of the number of LNP requests"
    ::= { sonusSoftSwitchLnpCountersEntry 2 }

sonusSoftSwitchLnpPerSipServerCountersLnpReqWithLrnRsp OBJECT-TYPE
    SYNTAX          Counter
    ACCESS          read-only
    STATUS          mandatory
    DESCRIPTION     
            "This counter keeps track of the number of responses having LRN "
    ::= { sonusSoftSwitchLnpCountersEntry 3 }

sonusSoftSwitchLnpPerSipServerCountersLnpReqWithoutLrnRsp OBJECT-TYPE
    SYNTAX          Counter
    ACCESS          read-only
    STATUS          mandatory
    DESCRIPTION     
            "This counter keeps track of the number of responses not having LRN "
    ::= { sonusSoftSwitchLnpCountersEntry 4 }

sonusSoftSwitchLnpPerSipServerCountersClassTypeRecvd OBJECT-TYPE
    SYNTAX          Counter
    ACCESS          read-only
    STATUS          mandatory
    DESCRIPTION     
            "This counter keeps track of the number of requests having qtype as class"
    ::= { sonusSoftSwitchLnpCountersEntry 5 }

sonusSoftSwitchLnpPerSipServerCountersClassTypeSuccess OBJECT-TYPE
    SYNTAX          Counter
    ACCESS          read-only
    STATUS          mandatory
    DESCRIPTION     
            "This counter keeps track of the number of successful queries for qtype class "
    ::= { sonusSoftSwitchLnpCountersEntry 6 }

sonusSoftSwitchLnpPerSipServerCountersClassTypeFailed OBJECT-TYPE
    SYNTAX          Counter
    ACCESS          read-only
    STATUS          mandatory
    DESCRIPTION     
            "This counter keeps track of the number of failed queries for qtype class "
    ::= { sonusSoftSwitchLnpCountersEntry 7 }

sonusSoftSwitchLnpPerSipServerCountersLidbTypeRecvd OBJECT-TYPE
    SYNTAX          Counter
    ACCESS          read-only
    STATUS          mandatory
    DESCRIPTION     
            "This counter keeps track of the number of requests having qtype as lidb "
    ::= { sonusSoftSwitchLnpCountersEntry 8 }

sonusSoftSwitchLnpPerSipServerCountersLidbTypeSuccess OBJECT-TYPE
    SYNTAX          Counter
    ACCESS          read-only
    STATUS          mandatory
    DESCRIPTION     
            "This counter keeps track of the number of successful queries for qtype lidb "
    ::= { sonusSoftSwitchLnpCountersEntry 9 }

sonusSoftSwitchLnpPerSipServerCountersLidbTypeFailed OBJECT-TYPE
    SYNTAX          Counter
    ACCESS          read-only
    STATUS          mandatory
    DESCRIPTION     
            "This counter keeps track of the number of failed queries for qtype lidb "
    ::= { sonusSoftSwitchLnpCountersEntry 10 }

sonusSoftSwitchLnpPerSipServerCountersCnamTypeRecvd OBJECT-TYPE
    SYNTAX          Counter
    ACCESS          read-only
    STATUS          mandatory
    DESCRIPTION     
            "This counter keeps track of the number of requests having qtype as cnam "
    ::= { sonusSoftSwitchLnpCountersEntry 11 }

sonusSoftSwitchLnpPerSipServerCountersCnamTypeSuccess OBJECT-TYPE
    SYNTAX          Counter
    ACCESS          read-only
    STATUS          mandatory
    DESCRIPTION     
            "This counter keeps track of the number of successful queries for qtype cnam"
    ::= { sonusSoftSwitchLnpCountersEntry 12 }

sonusSoftSwitchLnpPerSipServerCountersCnamTypeFailed OBJECT-TYPE
    SYNTAX          Counter
    ACCESS          read-only
    STATUS          mandatory
    DESCRIPTION     
            "This counter keeps track of the number of failed queries for qtype cnam"
    ::= { sonusSoftSwitchLnpCountersEntry 13 }

sonusSoftSwitchLnpPerSipServerCountersIsvmTypeRecvd OBJECT-TYPE
    SYNTAX          Counter
    ACCESS          read-only
    STATUS          mandatory
    DESCRIPTION     
            "This counter keeps track of the number of requests having qtype as isvm"
    ::= { sonusSoftSwitchLnpCountersEntry 14 }

sonusSoftSwitchLnpPerSipServerCountersIsvmTypeSuccess OBJECT-TYPE
    SYNTAX          Counter
    ACCESS          read-only
    STATUS          mandatory
    DESCRIPTION     
            "This counter keeps track of the number of successful queries for qtype isvm"
    ::= { sonusSoftSwitchLnpCountersEntry 15 }

sonusSoftSwitchLnpPerSipServerCountersIsvmTypeFailed OBJECT-TYPE
    SYNTAX          Counter
    ACCESS          read-only
    STATUS          mandatory
    DESCRIPTION     
            "This counter keeps track of the number of failed queries for qtype isvm"
    ::= { sonusSoftSwitchLnpCountersEntry 16 }

sonusSoftSwitchPesTranslationLookupCounters OBJECT IDENTIFIER
    ::= { sonusSoftSwitchPolicyExecutionServerStatistics 23 }

sonusSoftSwitchPesTranslationLookupCountersTable OBJECT-TYPE
    SYNTAX          SEQUENCE OF SonusSoftSwitchPesTranslationLookupCountersEntry
    ACCESS          not-accessible
    STATUS          mandatory
    DESCRIPTION     
            "Translation lookup counters per service table."
    ::= { sonusSoftSwitchPesTranslationLookupCounters 1 }

sonusSoftSwitchPesTranslationLookupCountersEntry OBJECT-TYPE
    SYNTAX          SonusSoftSwitchPesTranslationLookupCountersEntry
    ACCESS          not-accessible
    STATUS          mandatory
    DESCRIPTION     
            "An entry in the Translation Lookup counters per service table."
    INDEX           { 
                      sonusSoftSwitchPesTranslationLookupCountersServiceType, 
                      sonusSoftSwitchPesTranslationLookupCountersServiceName }
    ::= { sonusSoftSwitchPesTranslationLookupCountersTable 1 }

SonusSoftSwitchPesTranslationLookupCountersEntry ::=
    SEQUENCE {
        sonusSoftSwitchPesTranslationLookupCountersServiceType                      SonusName,
        sonusSoftSwitchPesTranslationLookupCountersServiceName                      SonusName,
        sonusSoftSwitchPesTranslationLookupCountersTotal                Counter,
        sonusSoftSwitchPesTranslationLookupCountersSuccess                  Counter,
        sonusSoftSwitchPesTranslationLookupCountersFailed                 Counter
    }

sonusSoftSwitchPesTranslationLookupCountersServiceType OBJECT-TYPE
    SYNTAX          SonusName
    ACCESS          read-only
    STATUS          mandatory
    DESCRIPTION     
            "Key1: Translation lookup service type."
    ::= { sonusSoftSwitchPesTranslationLookupCountersEntry 1 }

sonusSoftSwitchPesTranslationLookupCountersServiceName OBJECT-TYPE
    SYNTAX          SonusName
    ACCESS          read-only
    STATUS          mandatory
    DESCRIPTION     
            "Key2: Translation lookup service Name."
    ::= { sonusSoftSwitchPesTranslationLookupCountersEntry 2 }

sonusSoftSwitchPesTranslationLookupCountersTotal OBJECT-TYPE
    SYNTAX          Counter
    ACCESS          read-only
    STATUS          mandatory
    DESCRIPTION     
            "Total Translation lookup triggered per service "
    ::= { sonusSoftSwitchPesTranslationLookupCountersEntry 3 }

sonusSoftSwitchPesTranslationLookupCountersSuccess OBJECT-TYPE
    SYNTAX          Counter
    ACCESS          read-only
    STATUS          mandatory
    DESCRIPTION     
            "Total number of Translation lookup per service that were successful"
    ::= { sonusSoftSwitchPesTranslationLookupCountersEntry 4 }

sonusSoftSwitchPesTranslationLookupCountersFailed OBJECT-TYPE
    SYNTAX          Counter
    ACCESS          read-only
    STATUS          mandatory
    DESCRIPTION     
            "Total number of Translation lookup per service that failed"
    ::= { sonusSoftSwitchPesTranslationLookupCountersEntry 5 }

sonusSoftSwitchPesPerServiceCounters OBJECT IDENTIFIER
    ::= { sonusSoftSwitchPolicyExecutionServerStatistics 24 }

sonusSoftSwitchPesPerServiceCountersTable OBJECT-TYPE
    SYNTAX          SEQUENCE OF SonusSoftSwitchPesPerSvcCountersEntry
    ACCESS          not-accessible
    STATUS          mandatory
    DESCRIPTION     
            "Counters PER PES Service"
    ::= { sonusSoftSwitchPesPerServiceCounters 1 }

sonusSoftSwitchPesPerSvcCountersEntry OBJECT-TYPE
    SYNTAX          SonusSoftSwitchPesPerSvcCountersEntry
    ACCESS          not-accessible
    STATUS          mandatory
    DESCRIPTION     
            "An entry of Traffic counters related to PES Service Name"
    INDEX           { sonusSoftSwitchPesPerServiceCountersType, 
                      sonusSoftSwitchPesPerServiceCountersName }
    ::= { sonusSoftSwitchPesPerServiceCountersTable 1 }

SonusSoftSwitchPesPerSvcCountersEntry ::=
    SEQUENCE {
        sonusSoftSwitchPesPerServiceCountersType        DisplayString,
        sonusSoftSwitchPesPerServiceCountersName        DisplayString,
        sonusSoftSwitchPesPerServiceCountersRequestsSent                Counter,
        sonusSoftSwitchPesPerServiceCountersResponsesRcvd                 Counter,
        sonusSoftSwitchPesPerServiceCountersTimeouts            Counter,
        sonusSoftSwitchPesPerServiceCountersMissingParam                Counter,
        sonusSoftSwitchPesPerServiceCountersCvt       Counter,
        sonusSoftSwitchPesPerServiceCountersCvtEscaped              Counter,
        sonusSoftSwitchPesPerServiceCountersMissingRespParam                    Counter
    }

sonusSoftSwitchPesPerServiceCountersType OBJECT-TYPE
    SYNTAX          DisplayString
    ACCESS          read-only
    STATUS          mandatory
    DESCRIPTION     
            "Service Type"
    ::= { sonusSoftSwitchPesPerSvcCountersEntry 1 }

sonusSoftSwitchPesPerServiceCountersName OBJECT-TYPE
    SYNTAX          DisplayString
    ACCESS          read-only
    STATUS          mandatory
    DESCRIPTION     
            "Service Name"
    ::= { sonusSoftSwitchPesPerSvcCountersEntry 2 }

sonusSoftSwitchPesPerServiceCountersRequestsSent OBJECT-TYPE
    SYNTAX          Counter
    ACCESS          read-only
    STATUS          mandatory
    DESCRIPTION     
            "This counter keeps track of the number of requests
             which have been sent by the pes process counted for each Service"
    ::= { sonusSoftSwitchPesPerSvcCountersEntry 3 }

sonusSoftSwitchPesPerServiceCountersResponsesRcvd OBJECT-TYPE
    SYNTAX          Counter
    ACCESS          read-only
    STATUS          mandatory
    DESCRIPTION     
            "This counter keeps track of the number of responses
             which have been received by the pes process counted for each Service "
    ::= { sonusSoftSwitchPesPerSvcCountersEntry 4 }

sonusSoftSwitchPesPerServiceCountersTimeouts OBJECT-TYPE
    SYNTAX          Counter
    ACCESS          read-only
    STATUS          mandatory
    DESCRIPTION     
            "This counter keeps track of the number of timeouts reached by the pes process counted for each Service "
    ::= { sonusSoftSwitchPesPerSvcCountersEntry 5 }

sonusSoftSwitchPesPerServiceCountersMissingParam OBJECT-TYPE
    SYNTAX          Counter
    ACCESS          read-only
    STATUS          mandatory
    DESCRIPTION     
            "This counter keeps track of the number of Missing Request parameters by the pes process counted for each Service "
    ::= { sonusSoftSwitchPesPerSvcCountersEntry 6 }

sonusSoftSwitchPesPerServiceCountersCvt OBJECT-TYPE
    SYNTAX          Counter
    ACCESS          read-only
    STATUS          mandatory
    DESCRIPTION     
            "This counter keeps track of number of times Call Validation and treatment executed "
    ::= { sonusSoftSwitchPesPerSvcCountersEntry 7 }

sonusSoftSwitchPesPerServiceCountersCvtEscaped OBJECT-TYPE
    SYNTAX          Counter
    ACCESS          read-only
    STATUS          mandatory
    DESCRIPTION     
            "This counter keeps track of number of times Call Validation and treatment escaped "
    ::= { sonusSoftSwitchPesPerSvcCountersEntry 8 }

sonusSoftSwitchPesPerServiceCountersMissingRespParam OBJECT-TYPE
    SYNTAX          Counter
    ACCESS          read-only
    STATUS          mandatory
    DESCRIPTION     
            "This counter keeps track of the number of Missing mandatory response parameters
             which have been received by the pes process counted for each Service "
    ::= { sonusSoftSwitchPesPerSvcCountersEntry 9 }

sonusSoftSwitchPolicyExecutionServerMIBNotifications OBJECT IDENTIFIER
    ::= { sonusSoftSwitchPolicyExecutionServerMIB 2 }

sonusSoftSwitchPolicyExecutionServerMIBNotificationsPrefix OBJECT IDENTIFIER
    ::= { sonusSoftSwitchPolicyExecutionServerMIBNotifications 0 }

sonusSoftSwitchPolicyExecutionServerMIBNotificationsObjects OBJECT IDENTIFIER
    ::= { sonusSoftSwitchPolicyExecutionServerMIBNotifications 1 }

sonusSoftSwitchPesRegisterReason OBJECT-TYPE
    SYNTAX          INTEGER { new(1) }
    ACCESS          read-only
    STATUS          mandatory
    DESCRIPTION     
            "Register operation reason."
    ::= { sonusSoftSwitchPolicyExecutionServerMIBNotificationsObjects 1 }

sonusSoftSwitchPesUnregisterReason OBJECT-TYPE
    SYNTAX          INTEGER { threshold(1), unknown(2), duplicate(3), 
                        lostConnection(4), clientUnregistered(5), 
                        unknownGateway(6), maxClientsExceeded(7) }
    ACCESS          read-only
    STATUS          mandatory
    DESCRIPTION     
            "Unregister operation reason."
    ::= { sonusSoftSwitchPolicyExecutionServerMIBNotificationsObjects 2 }

sonusPgkInterfaceIdentifier OBJECT-TYPE
    SYNTAX          INTEGER { primary(1), secondary(2) }
    ACCESS          read-only
    STATUS          mandatory
    DESCRIPTION     
            "PGK redundant interface identifier"
    ::= { sonusSoftSwitchPolicyExecutionServerMIBNotificationsObjects 3 }

sonusH323AccountingLevelIdentifier OBJECT-TYPE
    SYNTAX          INTEGER { percent50(1), percent75(2), percent90(3) }
    ACCESS          read-only
    STATUS          mandatory
    DESCRIPTION     
            "H323 Directory Capacity Used"
    ::= { sonusSoftSwitchPolicyExecutionServerMIBNotificationsObjects 4 }

sonusSoftSwitchPesCongestionLevel OBJECT-TYPE
    SYNTAX          INTEGER
    ACCESS          read-only
    STATUS          mandatory
    DESCRIPTION     
            "Congestion level to which the PSX is transitioning."
    ::= { sonusSoftSwitchPolicyExecutionServerMIBNotificationsObjects 5 }

sonusSoftSwitchPesPipeErrorCode OBJECT-TYPE
    SYNTAX          INTEGER
    ACCESS          read-only
    STATUS          mandatory
    DESCRIPTION     
            "The unix error code, if any, will be available in this field."
    ::= { sonusSoftSwitchPolicyExecutionServerMIBNotificationsObjects 6 }

sonusSoftSwitchPesPipeMwiQueueLevel OBJECT-TYPE
    SYNTAX          INTEGER { mwiQueueSafe(0), mwiQueueLevelMinor(1), 
                        mwiQueueLevelMajor(2), mwiQueueLevelCritical(3) }
    ACCESS          read-only
    STATUS          mandatory
    DESCRIPTION     
            "This field contains the MWI queue level information."
    ::= { sonusSoftSwitchPolicyExecutionServerMIBNotificationsObjects 7 }

sonusSoftSwitchPesUpNotification TRAP-TYPE
    ENTERPRISE      sonusSoftSwitchPolicyExecutionServerMIBNotifications
    VARIABLES       { sonusEventDescription, sonusEventClass, 
                      sonusEventLevel, sonusEventTime }
--     STATUS          mandatory
    DESCRIPTION     
            "SoftSwitch Policy Execution Server is up."
    ::= 1

sonusSoftSwitchPesDownNotification TRAP-TYPE
    ENTERPRISE      sonusSoftSwitchPolicyExecutionServerMIBNotifications
    VARIABLES       { sonusEventDescription, sonusEventClass, 
                      sonusEventLevel, sonusEventTime }
--     STATUS          mandatory
    DESCRIPTION     
            "SoftSwitch Policy Execution Server is down."
    ::= 2

sonusSoftSwitchPesDbOperationFailureNotification TRAP-TYPE
    ENTERPRISE      sonusSoftSwitchPolicyExecutionServerMIBNotifications
    VARIABLES       { sonusSoftSwitchDbOperationFailureReason, 
                      sonusEventDescription, sonusEventClass, 
                      sonusEventLevel, sonusEventTime }
--     STATUS          mandatory
    DESCRIPTION     
            "DB operation failed. Look at the failure reason."
    ::= 3

sonusSoftSwitchPesRegisterNotification TRAP-TYPE
    ENTERPRISE      sonusSoftSwitchPolicyExecutionServerMIBNotifications
    VARIABLES       { sonusSoftSwitchClientName, 
                      sonusSoftSwitchPesRegisterReason, 
                      sonusEventDescription, sonusEventClass, 
                      sonusEventLevel, sonusEventTime }
--     STATUS          mandatory
    DESCRIPTION     
            "Register operation. Look at register reason."
    ::= 4

sonusSoftSwitchPesUnregisterNotification TRAP-TYPE
    ENTERPRISE      sonusSoftSwitchPolicyExecutionServerMIBNotifications
    VARIABLES       { sonusSoftSwitchClientName, 
                      sonusSoftSwitchPesUnregisterReason, 
                      sonusEventDescription, sonusEventClass, 
                      sonusEventLevel, sonusEventTime }
--     STATUS          mandatory
    DESCRIPTION     
            "Unregister operation. Look at unregister reason."
    ::= 5

sonusSoftSwitchPesLnpServiceUpNotification TRAP-TYPE
    ENTERPRISE      sonusSoftSwitchPolicyExecutionServerMIBNotifications
    VARIABLES       { sonusEventDescription, sonusEventClass, 
                      sonusEventLevel, sonusEventTime }
--     STATUS          mandatory
    DESCRIPTION     
            "LNP Service is up."
    ::= 6

sonusSoftSwitchPesLnpServiceDownNotification TRAP-TYPE
    ENTERPRISE      sonusSoftSwitchPolicyExecutionServerMIBNotifications
    VARIABLES       { sonusEventDescription, sonusEventClass, 
                      sonusEventLevel, sonusEventTime }
--     STATUS          mandatory
    DESCRIPTION     
            "LNP Service is down."
    ::= 7

sonusSoftSwitchPesTollFreeServiceUpNotification TRAP-TYPE
    ENTERPRISE      sonusSoftSwitchPolicyExecutionServerMIBNotifications
    VARIABLES       { sonusEventDescription, sonusEventClass, 
                      sonusEventLevel, sonusEventTime }
--     STATUS          mandatory
    DESCRIPTION     
            "Toll Free Service is up."
    ::= 8

sonusSoftSwitchPesTollFreeServiceDownNotification TRAP-TYPE
    ENTERPRISE      sonusSoftSwitchPolicyExecutionServerMIBNotifications
    VARIABLES       { sonusEventDescription, sonusEventClass, 
                      sonusEventLevel, sonusEventTime }
--     STATUS          mandatory
    DESCRIPTION     
            "Toll Free Service is down."
    ::= 9

sonusSoftSwitchPesPgkServiceUpNotification TRAP-TYPE
    ENTERPRISE      sonusSoftSwitchPolicyExecutionServerMIBNotifications
    VARIABLES       { sonusEventDescription, sonusEventClass, 
                      sonusEventLevel, sonusEventTime }
--     STATUS          mandatory
    DESCRIPTION     
            "PGK Service is up."
    ::= 10

sonusSoftSwitchPesPgkServiceDownNotification TRAP-TYPE
    ENTERPRISE      sonusSoftSwitchPolicyExecutionServerMIBNotifications
    VARIABLES       { sonusEventDescription, sonusEventClass, 
                      sonusEventLevel, sonusEventTime }
--     STATUS          mandatory
    DESCRIPTION     
            "PGK Service is down."
    ::= 11

sonusSoftSwitchPesPgkInterfaceUpNotification TRAP-TYPE
    ENTERPRISE      sonusSoftSwitchPolicyExecutionServerMIBNotifications
    VARIABLES       { sonusPgkInterfaceIdentifier, sonusEventDescription, 
                      sonusEventClass, sonusEventLevel, sonusEventTime }
--     STATUS          mandatory
    DESCRIPTION     
            "PGK Interface is up."
    ::= 12

sonusSoftSwitchPesPgkInterfaceDownNotification TRAP-TYPE
    ENTERPRISE      sonusSoftSwitchPolicyExecutionServerMIBNotifications
    VARIABLES       { sonusPgkInterfaceIdentifier, sonusEventDescription, 
                      sonusEventClass, sonusEventLevel, sonusEventTime }
--     STATUS          mandatory
    DESCRIPTION     
            "PGK Interface is down."
    ::= 13

sonusSoftSwitchPesPgkChangeoverNotification TRAP-TYPE
    ENTERPRISE      sonusSoftSwitchPolicyExecutionServerMIBNotifications
    VARIABLES       { sonusPgkInterfaceIdentifier, sonusEventDescription, 
                      sonusEventClass, sonusEventLevel, sonusEventTime }
--     STATUS          mandatory
    DESCRIPTION     
            "Changing Active PGK."
    ::= 14

sonusSoftSwitchPesH323AccountingNotification TRAP-TYPE
    ENTERPRISE      sonusSoftSwitchPolicyExecutionServerMIBNotifications
    VARIABLES       { sonusH323AccountingLevelIdentifier, 
                      sonusEventDescription, sonusEventClass, 
                      sonusEventLevel, sonusEventTime }
--     STATUS          mandatory
    DESCRIPTION     
            "H323 Accounting Directory Level "
    ::= 15

sonusSoftSwitchPesH323AccountingShutdownNotification TRAP-TYPE
    ENTERPRISE      sonusSoftSwitchPolicyExecutionServerMIBNotifications
    VARIABLES       { sonusEventDescription, sonusEventClass, 
                      sonusEventLevel, sonusEventTime }
--     STATUS          mandatory
    DESCRIPTION     
            "H323 Accounting Directory FULL."
    ::= 16

sonusSoftSwitchPesScpaInterfaceUpNotification TRAP-TYPE
    ENTERPRISE      sonusSoftSwitchPolicyExecutionServerMIBNotifications
    VARIABLES       { sonusEventDescription, sonusEventClass, 
                      sonusEventLevel, sonusEventTime }
--     STATUS          mandatory
    DESCRIPTION     
            "SCPA interface is UP."
    ::= 17

sonusSoftSwitchPesScpaInterfaceDownNotification TRAP-TYPE
    ENTERPRISE      sonusSoftSwitchPolicyExecutionServerMIBNotifications
    VARIABLES       { sonusEventDescription, sonusEventClass, 
                      sonusEventLevel, sonusEventTime }
--     STATUS          mandatory
    DESCRIPTION     
            "SCPA interface is DOWN."
    ::= 18

sonusSoftSwitchPesNumberTranslationServiceUpNotification TRAP-TYPE
    ENTERPRISE      sonusSoftSwitchPolicyExecutionServerMIBNotifications
    VARIABLES       { sonusEventDescription, sonusEventClass, 
                      sonusEventLevel, sonusEventTime }
--     STATUS          mandatory
    DESCRIPTION     
            "Number Translation Service is UP."
    ::= 19

sonusSoftSwitchPesNumberTranslationServiceDownNotification TRAP-TYPE
    ENTERPRISE      sonusSoftSwitchPolicyExecutionServerMIBNotifications
    VARIABLES       { sonusEventDescription, sonusEventClass, 
                      sonusEventLevel, sonusEventTime }
--     STATUS          mandatory
    DESCRIPTION     
            "Number Translation Service is DOWN."
    ::= 20

sonusSoftSwitchPesScpCommunicationUpNotification TRAP-TYPE
    ENTERPRISE      sonusSoftSwitchPolicyExecutionServerMIBNotifications
    VARIABLES       { sonusEventDescription, sonusEventClass, 
                      sonusEventLevel, sonusEventTime }
--     STATUS          mandatory
    DESCRIPTION     
            "Communication to SCP is UP."
    ::= 21

sonusSoftSwitchPesScpCommunicationDownNotification TRAP-TYPE
    ENTERPRISE      sonusSoftSwitchPolicyExecutionServerMIBNotifications
    VARIABLES       { sonusEventDescription, sonusEventClass, 
                      sonusEventLevel, sonusEventTime }
--     STATUS          mandatory
    DESCRIPTION     
            "Communication to SCP is DOWN."
    ::= 22

sonusSoftSwitchPesCallProcessTimeHighThresholdNotification TRAP-TYPE
    ENTERPRISE      sonusSoftSwitchPolicyExecutionServerMIBNotifications
    VARIABLES       { sonusEventDescription, sonusEventClass, 
                      sonusEventLevel, sonusEventTime }
--     STATUS          mandatory
    DESCRIPTION     
            "PSX overload condition set."
    ::= 23

sonusSoftSwitchPesCallProcessTimeLowThresholdNotification TRAP-TYPE
    ENTERPRISE      sonusSoftSwitchPolicyExecutionServerMIBNotifications
    VARIABLES       { sonusEventDescription, sonusEventClass, 
                      sonusEventLevel, sonusEventTime }
--     STATUS          mandatory
    DESCRIPTION     
            "PSX overload condition cleared."
    ::= 24

sonusSoftSwitchPesScpTimeoutNotification TRAP-TYPE
    ENTERPRISE      sonusSoftSwitchPolicyExecutionServerMIBNotifications
    VARIABLES       { sonusEventDescription, sonusEventClass, 
                      sonusEventLevel, sonusEventTime }
--     STATUS          mandatory
    DESCRIPTION     
            "SCP queries timing out."
    ::= 25

sonusSoftSwitchPesNoRouteFoundNotification TRAP-TYPE
    ENTERPRISE      sonusSoftSwitchPolicyExecutionServerMIBNotifications
    VARIABLES       { sonusEventDescription, sonusEventClass, 
                      sonusEventLevel, sonusEventTime }
--     STATUS          mandatory
    DESCRIPTION     
            "No route found for Pes request"
    ::= 26

sonusSoftSwitchPesTMControlAppliedNotification TRAP-TYPE
    ENTERPRISE      sonusSoftSwitchPolicyExecutionServerMIBNotifications
    VARIABLES       { sonusSoftSwitchTMElementType, 
                      sonusSoftSwitchTMIdentifier1, 
                      sonusSoftSwitchTMIdentifier2, 
                      sonusSoftSwitchTMAppliedControlType, 
                      sonusSoftSwitchTMAddressNature, 
                      sonusEventDescription, sonusEventClass, 
                      sonusEventLevel, sonusEventTime }
--     STATUS          mandatory
    DESCRIPTION     
            "A traffic control has been applied."
    ::= 27

sonusSoftSwitchPesScpIs41LocReqErrorThresholdExceeded TRAP-TYPE
    ENTERPRISE      sonusSoftSwitchPolicyExecutionServerMIBNotifications
    VARIABLES       { sonusEventDescription, sonusEventClass, 
                      sonusEventLevel, sonusEventTime }
--     STATUS          mandatory
    DESCRIPTION     
            "ANSI-41 LOC REQ error count exceedes threshold"
    ::= 28

sonusSoftSwitchPesScpIs41RedReqErrorThresholdExceeded TRAP-TYPE
    ENTERPRISE      sonusSoftSwitchPolicyExecutionServerMIBNotifications
    VARIABLES       { sonusEventDescription, sonusEventClass, 
                      sonusEventLevel, sonusEventTime }
--     STATUS          mandatory
    DESCRIPTION     
            "ANSI-41 RED REQ error count exceedes threshold"
    ::= 29

sonusSoftSwitchPesScpIs41TranNumReqErrorThresholdExceeded TRAP-TYPE
    ENTERPRISE      sonusSoftSwitchPolicyExecutionServerMIBNotifications
    VARIABLES       { sonusEventDescription, sonusEventClass, 
                      sonusEventLevel, sonusEventTime }
--     STATUS          mandatory
    DESCRIPTION     
            "ANSI-41 TRAN NUM REQ error count exceedes threshold"
    ::= 30

sonusSoftSwitchPesScpGsmSriErrorThresholdExceeded TRAP-TYPE
    ENTERPRISE      sonusSoftSwitchPolicyExecutionServerMIBNotifications
    VARIABLES       { sonusEventDescription, sonusEventClass, 
                      sonusEventLevel, sonusEventTime }
--     STATUS          mandatory
    DESCRIPTION     
            "GSM-MAP SRI error count exceedes threshold"
    ::= 31

sonusSoftSwitchPesScpGsmRchErrorThresholdExceeded TRAP-TYPE
    ENTERPRISE      sonusSoftSwitchPolicyExecutionServerMIBNotifications
    VARIABLES       { sonusEventDescription, sonusEventClass, 
                      sonusEventLevel, sonusEventTime }
--     STATUS          mandatory
    DESCRIPTION     
            "GSM-MAP RCH error count exceedes threshold"
    ::= 32

sonusSoftSwitchPesCongestionNotification TRAP-TYPE
    ENTERPRISE      sonusSoftSwitchPolicyExecutionServerMIBNotifications
    VARIABLES       { sonusEventDescription, sonusEventClass, 
                      sonusEventLevel, sonusEventTime, 
                      sonusSoftSwitchPesCongestionLevel }
--     STATUS          mandatory
    DESCRIPTION     
            "The PSX congestion control level is changed"
    ::= 33

sonusSoftSwitchPesDbConnSuccessNotification TRAP-TYPE
    ENTERPRISE      sonusSoftSwitchPolicyExecutionServerMIBNotifications
    VARIABLES       { sonusEventDescription, sonusEventClass, 
                      sonusEventLevel, sonusEventTime }
--     STATUS          mandatory
    DESCRIPTION     
            "The 'pes' process establishes connection to the PSX DB."
    ::= 34

sonusSoftSwitchPesPipeCommunicationDownNotification TRAP-TYPE
    ENTERPRISE      sonusSoftSwitchPolicyExecutionServerMIBNotifications
    VARIABLES       { sonusSoftSwitchPesPipeErrorCode, 
                      sonusEventDescription, sonusEventClass, 
                      sonusEventLevel, sonusEventTime }
--     STATUS          mandatory
    DESCRIPTION     
            "'pes' process was unable to establish connection with master 'pipe' process."
    ::= 35

sonusSoftSwitchPesPipeRegistrationFailureNotification TRAP-TYPE
    ENTERPRISE      sonusSoftSwitchPolicyExecutionServerMIBNotifications
    VARIABLES       { sonusSoftSwitchPesPipeErrorCode, 
                      sonusEventDescription, sonusEventClass, 
                      sonusEventLevel, sonusEventTime }
--     STATUS          mandatory
    DESCRIPTION     
            "'pes' process was unable to register with master 'pipe' process."
    ::= 36

sonusSoftSwitchPesPipeIOErrorNotification TRAP-TYPE
    ENTERPRISE      sonusSoftSwitchPolicyExecutionServerMIBNotifications
    VARIABLES       { sonusSoftSwitchPesPipeErrorCode, 
                      sonusEventDescription, sonusEventClass, 
                      sonusEventLevel, sonusEventTime }
--     STATUS          mandatory
    DESCRIPTION     
            "'pes' process was unable to send/receive an update to 'pipe' process."
    ::= 37

sonusSoftSwitchPesPipeMWIQueueLevelChanged TRAP-TYPE
    ENTERPRISE      sonusSoftSwitchPolicyExecutionServerMIBNotifications
    VARIABLES       { sonusSoftSwitchPesPipeMwiQueueLevel, 
                      sonusEventDescription, sonusEventClass, 
                      sonusEventLevel, sonusEventTime }
--     STATUS          mandatory
    DESCRIPTION     
            "The MWI queue level changed. There is a safe level, followed by yellow, 
             orange and red levels. If the incoming message rate is far higher than 
             the consumption rate (updating the database), then the queue builds up 
             and crosses levels. Once the red level is reached, incoming messages 
             will be floored (not put in the queue)."
    ::= 38

sonusSoftSwitchPesPipeCommunicationUpNotification TRAP-TYPE
    ENTERPRISE      sonusSoftSwitchPolicyExecutionServerMIBNotifications
    VARIABLES       { sonusEventDescription, sonusEventClass, 
                      sonusEventLevel, sonusEventTime }
--     STATUS          mandatory
    DESCRIPTION     
            "'pes' process establishes connection with master 'pipe' process."
    ::= 39

sonusSoftSwitchPesPipeRegistrationSuccessNotification TRAP-TYPE
    ENTERPRISE      sonusSoftSwitchPolicyExecutionServerMIBNotifications
    VARIABLES       { sonusEventDescription, sonusEventClass, 
                      sonusEventLevel, sonusEventTime }
--     STATUS          mandatory
    DESCRIPTION     
            "'pes' process registers with master 'pipe' process."
    ::= 40

sonusSoftSwitchPesLwresdCommunicationUpNotification TRAP-TYPE
    ENTERPRISE      sonusSoftSwitchPolicyExecutionServerMIBNotifications
    VARIABLES       { sonusEventDescription, sonusEventClass, 
                      sonusEventLevel, sonusEventTime }
--     STATUS          mandatory
    DESCRIPTION     
            "Communication to LWRESD is UP."
    ::= 41

sonusSoftSwitchPesLwresdCommunicationDownNotification TRAP-TYPE
    ENTERPRISE      sonusSoftSwitchPolicyExecutionServerMIBNotifications
    VARIABLES       { sonusEventDescription, sonusEventClass, 
                      sonusEventLevel, sonusEventTime }
--     STATUS          mandatory
    DESCRIPTION     
            "Communication to LWRESD is DOWN."
    ::= 42

sonusSoftSwitchPesSqlErrorHighThresholdNotification TRAP-TYPE
    ENTERPRISE      sonusSoftSwitchPolicyExecutionServerMIBNotifications
    VARIABLES       { sonusEventDescription, sonusEventClass, 
                      sonusEventLevel, sonusEventTime }
--     STATUS          mandatory
    DESCRIPTION     
            "PES communication ports closed due to excessive failures."
    ::= 43

sonusSoftSwitchPesInternalErrorHighThresholdNotification TRAP-TYPE
    ENTERPRISE      sonusSoftSwitchPolicyExecutionServerMIBNotifications
    VARIABLES       { sonusEventDescription, sonusEventClass, 
                      sonusEventLevel, sonusEventTime }
--     STATUS          mandatory
    DESCRIPTION     
            "PSX excessive Internal communication failure crossed configured threshold."
    ::= 44

sonusSoftSwitchPesExternalErrorHighThresholdNotification TRAP-TYPE
    ENTERPRISE      sonusSoftSwitchPolicyExecutionServerMIBNotifications
    VARIABLES       { sonusEventDescription, sonusEventClass, 
                      sonusEventLevel, sonusEventTime }
--     STATUS          mandatory
    DESCRIPTION     
            "PSX excessive External communication failure crossed configured threshold."
    ::= 45

sonusSoftSwitchPesInternalErrorLowThresholdNotification TRAP-TYPE
    ENTERPRISE      sonusSoftSwitchPolicyExecutionServerMIBNotifications
    VARIABLES       { sonusEventDescription, sonusEventClass, 
                      sonusEventLevel, sonusEventTime }
--     STATUS          mandatory
    DESCRIPTION     
            "PSX excessive Internal communication failure cleared."
    ::= 46

sonusSoftSwitchPesExternalErrorLowThresholdNotification TRAP-TYPE
    ENTERPRISE      sonusSoftSwitchPolicyExecutionServerMIBNotifications
    VARIABLES       { sonusEventDescription, sonusEventClass, 
                      sonusEventLevel, sonusEventTime }
--     STATUS          mandatory
    DESCRIPTION     
            "PSX excessive External communication failure cleared."
    ::= 47

sonusSoftSwitchPesCongestionCCUsageNotification TRAP-TYPE
    ENTERPRISE      sonusSoftSwitchPolicyExecutionServerMIBNotifications
    VARIABLES       { sonusEventDescription, sonusEventClass, 
                      sonusEventLevel, sonusEventTime, 
                      sonusSoftSwitchPesCongestionLevel }
--     STATUS          mandatory
    DESCRIPTION     
            "The PSX call context usage level is changed"
    ::= 48

sonusSoftSwitchPesCallTracingDisabledNotification TRAP-TYPE
    ENTERPRISE      sonusSoftSwitchPolicyExecutionServerMIBNotifications
    VARIABLES       { sonusEventDescription, sonusEventClass, 
                      sonusEventLevel, sonusEventTime }
--     STATUS          mandatory
    DESCRIPTION     
            "Call Tracing is DISABLED."
    ::= 49

sonusSoftSwitchPesAdaCommunicationUpNotification TRAP-TYPE
    ENTERPRISE      sonusSoftSwitchPolicyExecutionServerMIBNotifications
    VARIABLES       { sonusEventDescription, sonusEventClass, 
                      sonusEventLevel, sonusEventTime }
--     STATUS          mandatory
    DESCRIPTION     
            "Communication to ADA is UP."
    ::= 50

sonusSoftSwitchPesAdaCommunicationDownNotification TRAP-TYPE
    ENTERPRISE      sonusSoftSwitchPolicyExecutionServerMIBNotifications
    VARIABLES       { sonusEventDescription, sonusEventClass, 
                      sonusEventLevel, sonusEventTime }
--     STATUS          mandatory
    DESCRIPTION     
            "Communication to ADA is DOWN."
    ::= 51

sonusSoftSwitchPesPlmCommunicationUpNotification TRAP-TYPE
    ENTERPRISE      sonusSoftSwitchPolicyExecutionServerMIBNotifications
    VARIABLES       { sonusEventDescription, sonusEventClass, 
                      sonusEventLevel, sonusEventTime }
--     STATUS          deprecated
    DESCRIPTION     
            "Softswitch PES-PLM communication is UP."
    ::= 52

sonusSoftSwitchPesPlmCommunicationDownNotification TRAP-TYPE
    ENTERPRISE      sonusSoftSwitchPolicyExecutionServerMIBNotifications
    VARIABLES       { sonusEventDescription, sonusEventClass, 
                      sonusEventLevel, sonusEventTime }
--     STATUS          deprecated
    DESCRIPTION     
            "Softswitch PES-PLM communication is DOWN"
    ::= 53

sonusSoftSwitchPesHTTPCCommunicationUpNotification TRAP-TYPE
    ENTERPRISE      sonusSoftSwitchPolicyExecutionServerMIBNotifications
    VARIABLES       { sonusEventDescription, sonusEventClass, 
                      sonusEventLevel, sonusEventTime }
--     STATUS          mandatory
    DESCRIPTION     
            "Softswitch PES-HTTPC communication is UP."
    ::= 54

sonusSoftSwitchPesHTTPCCommunicationDownNotification TRAP-TYPE
    ENTERPRISE      sonusSoftSwitchPolicyExecutionServerMIBNotifications
    VARIABLES       { sonusEventDescription, sonusEventClass, 
                      sonusEventLevel, sonusEventTime }
--     STATUS          mandatory
    DESCRIPTION     
            "Softswitch PES-HTTPC communication is DOWN."
    ::= 55

sonusSoftSwitchPesThreadKeepAliveFailedNotification TRAP-TYPE
    ENTERPRISE      sonusSoftSwitchPolicyExecutionServerMIBNotifications
    VARIABLES       { sonusEventDescription, sonusEventClass, 
                      sonusEventLevel, sonusEventTime }
--     STATUS          mandatory
    DESCRIPTION     
            "Indicates that one of the threads of PES process failed to send keepalive message."
    ::= 56

END -- end of module SONUS-SOFTSWITCH-POLICY-EXECUTION-SERVER-MIB.
