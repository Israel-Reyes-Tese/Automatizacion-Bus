--
-- This SMIv1 module has been generated by smidump 0.2-cvs. Do not edit.
--

SONUS-SMI DEFINITIONS ::= BEGIN

IMPORTS
    enterprises
        FROM SNMPv2-SMI;

sonus OBJECT IDENTIFIER
    ::= { enterprises 2879 }

-- sonus MODULE-IDENTITY
--     LAST-UPDATED    "201310070000Z"
--     ORGANIZATION    
--             "Sonus Networks, Inc."
--     CONTACT-INFO    
--             "   Customer Support    
--              Sonus Networks, Inc.
--              4 Technology Park Drive
--              Westford, MA 01886
--              USA
--              
--              Tel: 978-614-8100
--              Fax: 978-614-8609"
--     DESCRIPTION     
--             "Initial version of this MIB module."
--     ::= { enterprises 2879 }


sonusProducts OBJECT IDENTIFIER
    ::= { sonus 1 }

sonusGSXProducts OBJECT IDENTIFIER
    ::= { sonusProducts 1 }

sonusGSX9000 OBJECT IDENTIFIER
    ::= { sonusGSXProducts 1 }

sonusGSX9000HD OBJECT IDENTIFIER
    ::= { sonusGSXProducts 2 }

sonusGSX4000 OBJECT IDENTIFIER
    ::= { sonusGSXProducts 3 }

sonusPSXProducts OBJECT IDENTIFIER
    ::= { sonusProducts 2 }

sonusPSX6000 OBJECT IDENTIFIER
    ::= { sonusPSXProducts 1 }

sonusSGXProducts OBJECT IDENTIFIER
    ::= { sonusProducts 3 }

sonusSGX2000 OBJECT IDENTIFIER
    ::= { sonusSGXProducts 1 }

sonusSGX4000 OBJECT IDENTIFIER
    ::= { sonusSGXProducts 2 }

sonusASXProducts OBJECT IDENTIFIER
    ::= { sonusProducts 4 }

sonusASX OBJECT IDENTIFIER
    ::= { sonusASXProducts 1 }

sonusADS OBJECT IDENTIFIER
    ::= { sonusASXProducts 2 }

sonusInsightProducts OBJECT IDENTIFIER
    ::= { sonusProducts 5 }

sonusEMS OBJECT IDENTIFIER
    ::= { sonusInsightProducts 1 }

sonusDSI OBJECT IDENTIFIER
    ::= { sonusInsightProducts 2 }

sonusCommunicator OBJECT IDENTIFIER
    ::= { sonusInsightProducts 3 }

sonusIAS OBJECT IDENTIFIER
    ::= { sonusInsightProducts 4 }

sonusNFSProducts OBJECT IDENTIFIER
    ::= { sonusProducts 6 }

sonusSolNFS OBJECT IDENTIFIER
    ::= { sonusNFSProducts 1 }

sonusIMXProducts OBJECT IDENTIFIER
    ::= { sonusProducts 7 }

sonusIMX OBJECT IDENTIFIER
    ::= { sonusIMXProducts 1 }

sonusSRX OBJECT IDENTIFIER
    ::= { sonusIMXProducts 2 }

sonusFMCAS OBJECT IDENTIFIER
    ::= { sonusIMXProducts 3 }

sonusSBXProducts OBJECT IDENTIFIER
    ::= { sonusProducts 9 }

sonusSBX5000 OBJECT IDENTIFIER
    ::= { sonusSBXProducts 1 }

sonusSBC5200 OBJECT IDENTIFIER
    ::= { sonusSBXProducts 2 }

sonusSBC5100 OBJECT IDENTIFIER
    ::= { sonusSBXProducts 3 }

slb OBJECT IDENTIFIER
    ::= { sonusSBXProducts 7 }

sonusWSX OBJECT IDENTIFIER
    ::= { sonusProducts 10 }

sonusDatanode OBJECT IDENTIFIER
    ::= { sonusProducts 11 }

ribbonVnfm OBJECT IDENTIFIER
    ::= { sonusProducts 12 }

ribbonSTIProducts OBJECT IDENTIFIER
    ::= { sonusProducts 13 }

ribbonSTI OBJECT IDENTIFIER
    ::= { ribbonSTIProducts 1 }

ribbonIDHProducts OBJECT IDENTIFIER
    ::= { sonusProducts 14 }

ribbonIDH OBJECT IDENTIFIER
    ::= { ribbonIDHProducts 1 }

sonusMgmt OBJECT IDENTIFIER
    ::= { sonus 2 }

sonusSystemMIBs OBJECT IDENTIFIER
    ::= { sonusMgmt 1 }

sonusResourcesMIBs OBJECT IDENTIFIER
    ::= { sonusMgmt 2 }

sonusPacketMIBs OBJECT IDENTIFIER
    ::= { sonusMgmt 3 }

sonusCircuitMIBs OBJECT IDENTIFIER
    ::= { sonusMgmt 4 }

sonusServicesMIBs OBJECT IDENTIFIER
    ::= { sonusMgmt 5 }

sonusSignallingMIBs OBJECT IDENTIFIER
    ::= { sonusMgmt 6 }

sonusToolsMIBs OBJECT IDENTIFIER
    ::= { sonusMgmt 7 }

sonusCommonSoftwarePlatformServicesMIBs OBJECT IDENTIFIER
    ::= { sonusMgmt 8 }

sonusCspsNotificationMIBs OBJECT IDENTIFIER
    ::= { sonusCommonSoftwarePlatformServicesMIBs 1 }

sonusSGX4000MIBs OBJECT IDENTIFIER
    ::= { sonusMgmt 9 }

sonusSGX4000NotificationMIBs OBJECT IDENTIFIER
    ::= { sonusSGX4000MIBs 1 }

sonusSBX5000MIBs OBJECT IDENTIFIER
    ::= { sonusMgmt 10 }

sonusSBX5000NotificationMIBs OBJECT IDENTIFIER
    ::= { sonusSBX5000MIBs 1 }

sonusWSXMIBs OBJECT IDENTIFIER
    ::= { sonusMgmt 11 }

sonusWSXNotificationMIBs OBJECT IDENTIFIER
    ::= { sonusWSXMIBs 1 }

sonusDatanodeMIBs OBJECT IDENTIFIER
    ::= { sonusMgmt 12 }

sonusDatanodeNotificationMIBs OBJECT IDENTIFIER
    ::= { sonusDatanodeMIBs 1 }

ribbonVnfmMIBs OBJECT IDENTIFIER
    ::= { sonusMgmt 13 }

ribbonVnfmNotificationMIBs OBJECT IDENTIFIER
    ::= { ribbonVnfmMIBs 1 }

sonusModules OBJECT IDENTIFIER
    ::= { sonus 3 }

END -- end of module SONUS-SMI.
