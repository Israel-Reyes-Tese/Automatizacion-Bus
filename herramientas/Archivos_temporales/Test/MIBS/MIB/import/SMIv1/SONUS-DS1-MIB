--
-- This SMIv1 module has been generated by smidump 0.2-cvs. Do not edit.
--

SONUS-DS1-MIB DEFINITIONS ::= BEGIN

IMPORTS
    PerfCurrentCount
        FROM PerfHist-TC-MIB
    OBJECT-TYPE
        FROM RFC-1212
    TRAP-TYPE
        FROM RFC-1215
    DisplayString, RowStatus, TruthValue
        FROM SNMPv2-TC
    sonusDs1Index, sonusDs3Index, sonusEventClass, sonusEventDescription, 
    sonusEventLevel, sonusEventTime, sonusPortIndex, sonusSequenceId, 
    sonusShelfIndex, sonusSlotIndex
        FROM SONUS-COMMON-MIB
    sonusCircuitMIBs
        FROM SONUS-SMI
    SonusAdminAction, SonusAdminState, SonusName, SonusServiceState, 
    SonusShelfIndex, SonusSlotIndex
        FROM SONUS-TC;

sonusDsx1MIB OBJECT IDENTIFIER
    ::= { sonusCircuitMIBs 1 }

-- sonusDsx1MIB MODULE-IDENTITY
--     LAST-UPDATED    "201402050000Z"
--     ORGANIZATION    
--             "Sonus Networks, Inc."
--     CONTACT-INFO    
--             "   Customer Support    
--              Sonus Networks, Inc.
--              7 Technology Park Drive
--              Westford, MA 01886
--              USA
--              
--              Tel: 978-614-8100
--              Fax: 978-614-8609"
--     DESCRIPTION     
--             "The MIB Module for DS1 Management."
--     ::= { sonusCircuitMIBs 1 }


sonusDsx1MIBObjects OBJECT IDENTIFIER
    ::= { sonusDsx1MIB 1 }

sonusDsx1Admn OBJECT IDENTIFIER
    ::= { sonusDsx1MIBObjects 1 }

sonusDsx1AdmnNextIndex OBJECT IDENTIFIER
    ::= { sonusDsx1Admn 1 }

sonusDsx1AdmnTable OBJECT-TYPE
    SYNTAX          SEQUENCE OF SonusDsx1AdmnEntry
    ACCESS          not-accessible
    STATUS          mandatory
    DESCRIPTION     
            "Table of Sonus Enterprise Configurations for all DS1s"
    ::= { sonusDsx1Admn 2 }

sonusDsx1AdmnEntry OBJECT-TYPE
    SYNTAX          SonusDsx1AdmnEntry
    ACCESS          not-accessible
    STATUS          mandatory
    DESCRIPTION     
            "Entry in Table consisting of the all the Sonus Enterprise DS1 Configurations"
    INDEX           { sonusDsx1AdmnShelfIndex, sonusDsx1AdmnSlotIndex, 
                      sonusDsx1AdmnPortIndex, sonusDsx1AdmnDs3Index, 
                      sonusDsx1AdmnDs1Index }
    ::= { sonusDsx1AdmnTable 1 }

SonusDsx1AdmnEntry ::=
    SEQUENCE {
        sonusDsx1AdmnRowStatus          RowStatus,
        sonusDsx1AdmnName               SonusName,
        sonusDsx1AdmnProfileName        DisplayString,
        sonusDsx1AdmnShelfIndex         SonusShelfIndex,
        sonusDsx1AdmnSlotIndex          SonusSlotIndex,
        sonusDsx1AdmnPortIndex          INTEGER,
        sonusDsx1AdmnDs3Index           INTEGER,
        sonusDsx1AdmnDs1Index           INTEGER,
        sonusDsx1AdmnIfIndex            INTEGER,
        sonusDsx1AdmnState              SonusAdminState,
        sonusDsx1AdmnLineBuildOut       INTEGER,
        sonusDsx1AdmnTimeout            INTEGER,
        sonusDsx1AdmnMode               SonusServiceState,
        sonusDsx1AdmnAction             SonusAdminAction,
        sonusDsx1AdmnIdleCode           INTEGER,
        sonusDsx1AdmnAvailChannels      OCTET STRING,
        sonusDsx1AdmnType               INTEGER,
        sonusDsx1AdmnESThreshold        INTEGER,
        sonusDsx1AdmnSESThreshold       INTEGER,
        sonusDsx1AdmnCSSThreshold       INTEGER,
        sonusDsx1AdmnDayESThreshold     INTEGER,
        sonusDsx1AdmnDaySESThreshold    INTEGER,
        sonusDsx1AdmnDayCSSThreshold    INTEGER,
        sonusDsx1AdmnFarESThreshold     INTEGER,
        sonusDsx1AdmnFarSESThreshold    INTEGER,
        sonusDsx1AdmnFarDayESThreshold  INTEGER,
        sonusDsx1AdmnFarDaySESThreshold INTEGER,
        sonusDsx1AdmnPCVThreshold       INTEGER,
        sonusDsx1AdmnLCVThreshold       INTEGER,
        sonusDsx1AdmnUASThreshold       INTEGER,
        sonusDsx1AdmnFarPCVThreshold    INTEGER,
        sonusDsx1AdmnFarLCVThreshold    INTEGER,
        sonusDsx1AdmnFarUASThreshold    INTEGER,
        sonusDsx1AdmnDayPCVThreshold    INTEGER,
        sonusDsx1AdmnDayLCVThreshold    INTEGER,
        sonusDsx1AdmnDayUASThreshold    INTEGER,
        sonusDsx1AdmnFarDayPCVThreshold INTEGER,
        sonusDsx1AdmnFarDayLCVThreshold INTEGER,
        sonusDsx1AdmnFarDayUASThreshold INTEGER,
        sonusDsx1AdmnInitCounters       SonusAdminState,
        sonusDsx1AdmnEchoProfileName    DisplayString,
        sonusDsx1AdmnEchoCancellorMaxTail INTEGER,
        sonusDsx1AdmnEchoCancellorAudioType   INTEGER,
        sonusDsx1AdmnEchoCancellorSignallingTone        INTEGER,
        sonusDsx1AdmnEchoCancellorNlpDisable    INTEGER,
        sonusDsx1AdmnEchoCancellorNlpEnable   INTEGER,
        sonusDsx1AdmnEchoCancellorReturnLoss    INTEGER,
        sonusDsx1AdmnEchoCancellorResidualEcho      INTEGER,
        sonusDsx1AdmnEchoCancellorHiLevelComp     INTEGER,
        sonusDsx1AdmnEchoCancellorModemDisable      INTEGER,
        sonusDsx1AdmnZeroSuppression    INTEGER,
        sonusDsx1AdmnCircuitId          DisplayString,
        sonusDsx1AdmnEchoCancellorNarrowbandDetection             INTEGER,
        sonusDsx1AdmnLESThreshold       INTEGER,
        sonusDsx1AdmnLSESThreshold      INTEGER,
        sonusDsx1AdmnDayLESThreshold    INTEGER,
        sonusDsx1AdmnDayLSESThreshold   INTEGER,
        sonusDsx1AdmnSASThreshold       INTEGER,
        sonusDsx1AdmnDaySASThreshold    INTEGER,
        sonusDsx1AdmnSEFSThreshold      INTEGER,
        sonusDsx1AdmnDaySEFSThreshold   INTEGER,
        sonusDsx1AdmnStatAction         INTEGER,
        sonusDsx1AdmnSTS1Index          INTEGER,
        sonusDsx1AdmnVTGroupIndex       INTEGER,
        sonusDsx1AdmnVTIndex            INTEGER,
        sonusDsx1AdmnLCVTcaFilter       SonusAdminState,
        sonusDsx1AdmnLESTcaFilter       SonusAdminState,
        sonusDsx1AdmnLSESTcaFilter      SonusAdminState,
        sonusDsx1AdmnPCVTcaFilter       SonusAdminState,
        sonusDsx1AdmnPESTcaFilter       SonusAdminState,
        sonusDsx1AdmnPSESTcaFilter      SonusAdminState,
        sonusDsx1AdmnSASTcaFilter       SonusAdminState,
        sonusDsx1AdmnCSSTcaFilter       SonusAdminState,
        sonusDsx1AdmnSEFSTcaFilter      SonusAdminState,
        sonusDsx1AdmnUASTcaFilter       SonusAdminState,
        sonusDsx1AdmnLegacyTrapEnable   SonusAdminState,
        sonusDsx1AdmnInbandCode         INTEGER,
        sonusDsx1AdmnQ50BssSignalBits   INTEGER,
        sonusDsx1AdmnQ50MaintReqResp    INTEGER,
        sonusDsx1AdmnQ50DcmeAckTimeout  INTEGER,
        sonusDsx1AdmnQ50InitStatistics  SonusAdminState,
        sonusDsx1AdmnAisTimer           INTEGER,
        sonusDsx1AdmnRaiTimer           INTEGER
    }

sonusDsx1AdmnRowStatus OBJECT-TYPE
    SYNTAX          RowStatus
    ACCESS          read-write
    STATUS          mandatory
    DESCRIPTION     
            "DS1, Needed for SNMP"
    ::= { sonusDsx1AdmnEntry 1 }

sonusDsx1AdmnName OBJECT-TYPE
    SYNTAX          SonusName
    ACCESS          read-write
    STATUS          mandatory
    DESCRIPTION     
            "Name of this T1/E1 Span"
    ::= { sonusDsx1AdmnEntry 2 }

sonusDsx1AdmnProfileName OBJECT-TYPE
    SYNTAX          DisplayString (SIZE(0..23))
    ACCESS          read-write
    STATUS          mandatory
    DESCRIPTION     
            "The name of the profile applied to this T1/E1 Table"
    ::= { sonusDsx1AdmnEntry 3 }

sonusDsx1AdmnShelfIndex OBJECT-TYPE
    SYNTAX          SonusShelfIndex
    ACCESS          read-only
    STATUS          mandatory
    DESCRIPTION     
            "Shelf index for this table"
    ::= { sonusDsx1AdmnEntry 4 }

sonusDsx1AdmnSlotIndex OBJECT-TYPE
    SYNTAX          SonusSlotIndex
    ACCESS          read-only
    STATUS          mandatory
    DESCRIPTION     
            "Slot index for this table"
    ::= { sonusDsx1AdmnEntry 5 }

sonusDsx1AdmnPortIndex OBJECT-TYPE
    SYNTAX          INTEGER
    ACCESS          read-only
    STATUS          mandatory
    DESCRIPTION     
            "Port Index into this table"
    ::= { sonusDsx1AdmnEntry 6 }

sonusDsx1AdmnDs3Index OBJECT-TYPE
    SYNTAX          INTEGER
    ACCESS          read-only
    STATUS          mandatory
    DESCRIPTION     
            "Ds3 Index into this table"
    ::= { sonusDsx1AdmnEntry 7 }

sonusDsx1AdmnDs1Index OBJECT-TYPE
    SYNTAX          INTEGER
    ACCESS          read-only
    STATUS          mandatory
    DESCRIPTION     
            "Ds1 Index into this table"
    ::= { sonusDsx1AdmnEntry 8 }

sonusDsx1AdmnIfIndex OBJECT-TYPE
    SYNTAX          INTEGER
    ACCESS          read-only
    STATUS          mandatory
    DESCRIPTION     
            "If Index for the corresponding standard MIB table"
    ::= { sonusDsx1AdmnEntry 9 }

sonusDsx1AdmnState OBJECT-TYPE
    SYNTAX          SonusAdminState
    ACCESS          read-write
    STATUS          mandatory
    DESCRIPTION     
            "State of T1/E1, Enabled/Disabled"
    DEFVAL          { disabled }
    ::= { sonusDsx1AdmnEntry 10 }

sonusDsx1AdmnLineBuildOut OBJECT-TYPE
    SYNTAX          INTEGER { buildOut0to110(1), buildOut110to220(2), 
                        buildOut220to330(3), buildOut330to440(4), 
                        buildOut440to550(5), buildOut550to660(6), 
                        buildOut120Ohms(7), buildOut75Ohms(8), 
                        notConfigured(9) }
    ACCESS          read-write
    STATUS          mandatory
    DESCRIPTION     
            "Line build out of T1/E1"
    DEFVAL          { notConfigured }
    ::= { sonusDsx1AdmnEntry 11 }

sonusDsx1AdmnTimeout OBJECT-TYPE
    SYNTAX          INTEGER (0..1440)
    ACCESS          read-write
    STATUS          mandatory
    DESCRIPTION     
            "Max time in minutes before dryup takes place"
    DEFVAL          { 5 }
    ::= { sonusDsx1AdmnEntry 12 }

sonusDsx1AdmnMode OBJECT-TYPE
    SYNTAX          SonusServiceState
    ACCESS          read-write
    STATUS          mandatory
    DESCRIPTION     
            "T1/E1 span is in service or out of service."
    DEFVAL          { outOfService }
    ::= { sonusDsx1AdmnEntry 13 }

sonusDsx1AdmnAction OBJECT-TYPE
    SYNTAX          SonusAdminAction
    ACCESS          read-write
    STATUS          mandatory
    DESCRIPTION     
            "Force out of service or wait for dryup"
    DEFVAL          { dryUp }
    ::= { sonusDsx1AdmnEntry 14 }

sonusDsx1AdmnIdleCode OBJECT-TYPE
    SYNTAX          INTEGER (0..255)
    ACCESS          read-write
    STATUS          mandatory
    DESCRIPTION     
            "Idle code to be applied to the channels"
    DEFVAL          { 127 }
    ::= { sonusDsx1AdmnEntry 15 }

sonusDsx1AdmnAvailChannels OBJECT-TYPE
    SYNTAX          OCTET STRING
--                       { channel1(0), channel2(1), channel3(2), 
--                         channel4(3), channel5(4), channel6(5), 
--                         channel7(6), channel8(7), channel9(8), 
--                         channel10(9), channel11(10), channel12(11), 
--                         channel13(12), channel14(13), channel15(14), 
--                         channel16(15), channel17(16), channel18(17), 
--                         channel19(18), channel20(19), channel21(20), 
--                         channel22(21), channel23(22), channel24(23), 
--                         channel25(24), channel26(25), channel27(26), 
--                         channel28(27), channel29(28), channel30(29), 
--                         channel31(30), channel32(31) }
    ACCESS          read-write
    STATUS          mandatory
    DESCRIPTION     
            "Bitstring map of channels that are available on this T1/E1 span."
    ::= { sonusDsx1AdmnEntry 16 }

sonusDsx1AdmnType OBJECT-TYPE
    SYNTAX          INTEGER { t1(1), e1(2), notConfigured(3) }
    ACCESS          read-write
    STATUS          mandatory
    DESCRIPTION     
            "Type of DSx1. Indicates whether this span is a T1 span or E1 span."
    DEFVAL          { notConfigured }
    ::= { sonusDsx1AdmnEntry 17 }

sonusDsx1AdmnESThreshold OBJECT-TYPE
    SYNTAX          INTEGER (1..900)
    ACCESS          read-write
    STATUS          obsolete
    DESCRIPTION     
            "Errored Seconds threshold value for 15 minute interval. This is for near end.
             This object was obsoleted in release 6.1"
    DEFVAL          { 65 }
    ::= { sonusDsx1AdmnEntry 18 }

sonusDsx1AdmnSESThreshold OBJECT-TYPE
    SYNTAX          INTEGER (1..900)
    ACCESS          read-write
    STATUS          obsolete
    DESCRIPTION     
            "Severely Errored Seconds threshold value for 15 minute interval. 
             This is for near end. This object was obsoleted in release 6.1."
    DEFVAL          { 10 }
    ::= { sonusDsx1AdmnEntry 19 }

sonusDsx1AdmnCSSThreshold OBJECT-TYPE
    SYNTAX          INTEGER (1..900)
    ACCESS          read-write
    STATUS          obsolete
    DESCRIPTION     
            "Controlled Slip Seconds threshold value for 15 minute interval. 
             This is for near end. This object was obsoleted in release 6.1."
    DEFVAL          { 1 }
    ::= { sonusDsx1AdmnEntry 20 }

sonusDsx1AdmnDayESThreshold OBJECT-TYPE
    SYNTAX          INTEGER (1..65535)
    ACCESS          read-write
    STATUS          obsolete
    DESCRIPTION     
            "Errored Seconds threshold value for a day. This is for near end.
             This object was obsoleted in release 6.1."
    DEFVAL          { 648 }
    ::= { sonusDsx1AdmnEntry 21 }

sonusDsx1AdmnDaySESThreshold OBJECT-TYPE
    SYNTAX          INTEGER (1..65535)
    ACCESS          read-write
    STATUS          obsolete
    DESCRIPTION     
            "Severely Errored Seconds threshold value for a day. This is for near end.
             This object was obsoleted in release 6.1."
    DEFVAL          { 100 }
    ::= { sonusDsx1AdmnEntry 22 }

sonusDsx1AdmnDayCSSThreshold OBJECT-TYPE
    SYNTAX          INTEGER (1..65535)
    ACCESS          read-write
    STATUS          obsolete
    DESCRIPTION     
            "Controlled Slip Seconds threshold value for a day. This is for near end.
             This object was obsoleted in release 6.1."
    DEFVAL          { 4 }
    ::= { sonusDsx1AdmnEntry 23 }

sonusDsx1AdmnFarESThreshold OBJECT-TYPE
    SYNTAX          INTEGER (1..900)
    ACCESS          read-write
    STATUS          obsolete
    DESCRIPTION     
            "Errored Seconds threshold value for 15 minute interval. This is for far end.
             This object was obsoleted in release 5.1"
    DEFVAL          { 65 }
    ::= { sonusDsx1AdmnEntry 24 }

sonusDsx1AdmnFarSESThreshold OBJECT-TYPE
    SYNTAX          INTEGER (1..900)
    ACCESS          read-write
    STATUS          obsolete
    DESCRIPTION     
            "Severely Errored Seconds threshold value for 15 minute interval. 
             This is for far end. This object was obsoleted in release 5.1"
    DEFVAL          { 10 }
    ::= { sonusDsx1AdmnEntry 25 }

sonusDsx1AdmnFarDayESThreshold OBJECT-TYPE
    SYNTAX          INTEGER (1..65535)
    ACCESS          read-write
    STATUS          obsolete
    DESCRIPTION     
            "Errored Seconds threshold value for a day. This is for far end.
             This object was obsoleted in release 5.1"
    DEFVAL          { 648 }
    ::= { sonusDsx1AdmnEntry 26 }

sonusDsx1AdmnFarDaySESThreshold OBJECT-TYPE
    SYNTAX          INTEGER (1..65535)
    ACCESS          read-write
    STATUS          obsolete
    DESCRIPTION     
            "Severely Errored Seconds threshold value for a day. This is for far end.
             This object was obsoleted in release 5.1."
    DEFVAL          { 100 }
    ::= { sonusDsx1AdmnEntry 27 }

sonusDsx1AdmnPCVThreshold OBJECT-TYPE
    SYNTAX          INTEGER (1..16383)
    ACCESS          read-write
    STATUS          obsolete
    DESCRIPTION     
            "Path Code Violations threshold value for 15 minute interval. This is for near end.
             This object was obsoleted in release 6.1."
    DEFVAL          { 13296 }
    ::= { sonusDsx1AdmnEntry 28 }

sonusDsx1AdmnLCVThreshold OBJECT-TYPE
    SYNTAX          INTEGER (1..16383)
    ACCESS          read-write
    STATUS          obsolete
    DESCRIPTION     
            "Line Code Violations threshold value for 15 minute interval. This is for near end.
             This object was obsoleted in release 6.1."
    DEFVAL          { 13340 }
    ::= { sonusDsx1AdmnEntry 29 }

sonusDsx1AdmnUASThreshold OBJECT-TYPE
    SYNTAX          INTEGER (1..900)
    ACCESS          read-write
    STATUS          obsolete
    DESCRIPTION     
            "Unavailable Seconds threshold value for 15 minute interval. This is for near end.
             This object was obsoleted in release 6.1."
    DEFVAL          { 10 }
    ::= { sonusDsx1AdmnEntry 30 }

sonusDsx1AdmnFarPCVThreshold OBJECT-TYPE
    SYNTAX          INTEGER (1..16383)
    ACCESS          read-write
    STATUS          obsolete
    DESCRIPTION     
            "Path Code Violations threshold value for 15 minute interval. This is for far end.
             This object was obsoleted in release 5.1."
    DEFVAL          { 72 }
    ::= { sonusDsx1AdmnEntry 31 }

sonusDsx1AdmnFarLCVThreshold OBJECT-TYPE
    SYNTAX          INTEGER (1..16383)
    ACCESS          read-write
    STATUS          obsolete
    DESCRIPTION     
            "Line Code Violations threshold value for 15 minute interval. This is for far end.
             This object was obsoleted in release 5.1."
    DEFVAL          { 72 }
    ::= { sonusDsx1AdmnEntry 32 }

sonusDsx1AdmnFarUASThreshold OBJECT-TYPE
    SYNTAX          INTEGER (1..900)
    ACCESS          read-write
    STATUS          obsolete
    DESCRIPTION     
            "Unavailable Seconds threshold value for 15 minute interval. This is for far end.
             This object was obsoleted in release 5.1."
    DEFVAL          { 10 }
    ::= { sonusDsx1AdmnEntry 33 }

sonusDsx1AdmnDayPCVThreshold OBJECT-TYPE
    SYNTAX          INTEGER (1..1048575)
    ACCESS          read-write
    STATUS          obsolete
    DESCRIPTION     
            "Path Code Violations threshold value for a day. This is for near end.
             This object was obsoleted in release 6.1."
    DEFVAL          { 132960 }
    ::= { sonusDsx1AdmnEntry 34 }

sonusDsx1AdmnDayLCVThreshold OBJECT-TYPE
    SYNTAX          INTEGER (1..1048575)
    ACCESS          read-write
    STATUS          obsolete
    DESCRIPTION     
            "Line Code Violations threshold value for a day. This is for near end.
             This object was obsoleted in release 6.1."
    DEFVAL          { 133400 }
    ::= { sonusDsx1AdmnEntry 35 }

sonusDsx1AdmnDayUASThreshold OBJECT-TYPE
    SYNTAX          INTEGER (1..65535)
    ACCESS          read-write
    STATUS          obsolete
    DESCRIPTION     
            "Unavailable Seconds threshold value for a day. This is for near end.
             This object was obsoleted in release 6.1."
    DEFVAL          { 10 }
    ::= { sonusDsx1AdmnEntry 36 }

sonusDsx1AdmnFarDayPCVThreshold OBJECT-TYPE
    SYNTAX          INTEGER (1..1048575)
    ACCESS          read-write
    STATUS          obsolete
    DESCRIPTION     
            "Path Code Violations threshold value for a day. This is for far end.
             This object was obsoleted in release 5.1."
    DEFVAL          { 691 }
    ::= { sonusDsx1AdmnEntry 37 }

sonusDsx1AdmnFarDayLCVThreshold OBJECT-TYPE
    SYNTAX          INTEGER (1..1048575)
    ACCESS          read-write
    STATUS          obsolete
    DESCRIPTION     
            "Line Code Violations threshold value for a day. This is for far end.
             This object was obsoleted in release 5.1."
    DEFVAL          { 691 }
    ::= { sonusDsx1AdmnEntry 38 }

sonusDsx1AdmnFarDayUASThreshold OBJECT-TYPE
    SYNTAX          INTEGER (1..65535)
    ACCESS          read-write
    STATUS          obsolete
    DESCRIPTION     
            "Unavailable Seconds threshold value for a day. This is for far end.
             This object was obsoleted in release 5.1."
    DEFVAL          { 100 }
    ::= { sonusDsx1AdmnEntry 39 }

sonusDsx1AdmnInitCounters OBJECT-TYPE
    SYNTAX          SonusAdminState
    ACCESS          read-write
    STATUS          mandatory
    DESCRIPTION     
            "Used to initialize all counters. Once enabled clears all T1/E1 counters."
    DEFVAL          { disabled }
    ::= { sonusDsx1AdmnEntry 40 }

sonusDsx1AdmnEchoProfileName OBJECT-TYPE
    SYNTAX          DisplayString (SIZE(1..23))
    ACCESS          read-write
    STATUS          mandatory
    DESCRIPTION     
            "The name of the Echo Canceller profile applied to this T1/E1 Table"
    ::= { sonusDsx1AdmnEntry 41 }

sonusDsx1AdmnEchoCancellorMaxTail OBJECT-TYPE
    SYNTAX          INTEGER { millisec24(1), millisec32(2), 
                        millisec48(3), millisec64(4) }
    ACCESS          read-only
    STATUS          mandatory
    DESCRIPTION     
            "Maximum Echo canceller tail length"
    DEFVAL          { millisec64 }
    ::= { sonusDsx1AdmnEntry 42 }

sonusDsx1AdmnEchoCancellorAudioType OBJECT-TYPE
    SYNTAX          INTEGER { uLaw(1), aLaw(2) }
    ACCESS          read-only
    STATUS          mandatory
    DESCRIPTION     
            "Echo Canceller Audio encoding type A-law or U-law"
    DEFVAL          { uLaw }
    ::= { sonusDsx1AdmnEntry 43 }

sonusDsx1AdmnEchoCancellorSignallingTone OBJECT-TYPE
    SYNTAX          INTEGER { none(1), c5(2) }
    ACCESS          read-only
    STATUS          deprecated
    DESCRIPTION     
            "Has been deprecated and is a shelf wide configuration. 
             Echo Cancellation: None, 2400, 2600 or 2101 Hz"
    DEFVAL          { none }
    ::= { sonusDsx1AdmnEntry 44 }

sonusDsx1AdmnEchoCancellorNlpDisable OBJECT-TYPE
    SYNTAX          INTEGER (0..16)
    ACCESS          read-only
    STATUS          deprecated
    DESCRIPTION     
            "Has been deprecated and is a shelf wide configuration. 
             Echo Canceller Non-linear processing control, Disable"
    DEFVAL          { 6 }
    ::= { sonusDsx1AdmnEntry 45 }

sonusDsx1AdmnEchoCancellorNlpEnable OBJECT-TYPE
    SYNTAX          INTEGER (0..80)
    ACCESS          read-only
    STATUS          deprecated
    DESCRIPTION     
            "Has been deprecated and is a shelf wide configuration. 
             Echo canceller Non-linear processing control, Enable"
    DEFVAL          { 75 }
    ::= { sonusDsx1AdmnEntry 46 }

sonusDsx1AdmnEchoCancellorReturnLoss OBJECT-TYPE
    SYNTAX          INTEGER { dB6(1), dB3(2), dB0(3) }
    ACCESS          read-only
    STATUS          mandatory
    DESCRIPTION     
            "For Network Echo Cancellation, specifies the echo
             return loss in dB's. Default value is 6dB."
    DEFVAL          { dB6 }
    ::= { sonusDsx1AdmnEntry 47 }

sonusDsx1AdmnEchoCancellorResidualEcho OBJECT-TYPE
    SYNTAX          INTEGER { cancelOnly(1), suppressResidual(2), 
                        comfortNoise(4) }
    ACCESS          read-only
    STATUS          mandatory
    DESCRIPTION     
            "For Network Echo Cancellation, specifies the residual echo
             cancellation."
    DEFVAL          { comfortNoise }
    ::= { sonusDsx1AdmnEntry 48 }

sonusDsx1AdmnEchoCancellorHiLevelComp OBJECT-TYPE
    SYNTAX          INTEGER { none(1), dB6(2) }
    ACCESS          read-only
    STATUS          deprecated
    DESCRIPTION     
            "For Network Echo Cancellation, the high level compensation
             value. Default value is to attenuate by 6dB."
    DEFVAL          { dB6 }
    ::= { sonusDsx1AdmnEntry 49 }

sonusDsx1AdmnEchoCancellorModemDisable OBJECT-TYPE
    SYNTAX          INTEGER { ignore2100Hz(1), g164(2), g165(4), 
                        sonusCustom(5) }
    ACCESS          read-only
    STATUS          mandatory
    DESCRIPTION     
            "For Network Echo Cancellation, specifies whether to disable
             echo cancellation when a modem tone is detected."
    DEFVAL          { g165 }
    ::= { sonusDsx1AdmnEntry 50 }

sonusDsx1AdmnZeroSuppression OBJECT-TYPE
    SYNTAX          INTEGER { none(1), jamBit8(2), 
                        signalFrameOnlyJamBit8(3), gteZeroSuppression(4), 
                        bellZeroSuppression(5) }
    ACCESS          read-write
    STATUS          mandatory
    DESCRIPTION     
            "T1 span zero suppression control."
    DEFVAL          { none }
    ::= { sonusDsx1AdmnEntry 51 }

sonusDsx1AdmnCircuitId OBJECT-TYPE
    SYNTAX          DisplayString (SIZE(1..23))
    ACCESS          read-write
    STATUS          mandatory
    DESCRIPTION     
            "The Circuit Id."
    ::= { sonusDsx1AdmnEntry 52 }

sonusDsx1AdmnEchoCancellorNarrowbandDetection OBJECT-TYPE
    SYNTAX          INTEGER { off(1), on(2) }
    ACCESS          read-only
    STATUS          mandatory
    DESCRIPTION     
            "For Network Echo Cancellation, narrow band detection is OFF or ON. If set ON
             it narrows the G.164 detection bandwidth in G.165 mode to the G.165 band."
    DEFVAL          { off }
    ::= { sonusDsx1AdmnEntry 53 }

sonusDsx1AdmnLESThreshold OBJECT-TYPE
    SYNTAX          INTEGER (1..900)
    ACCESS          read-write
    STATUS          obsolete
    DESCRIPTION     
            "Errored Seconds threshold value for 15 minute interval. This is for near end.
             This object was obsoleted in release 6.1."
    DEFVAL          { 65 }
    ::= { sonusDsx1AdmnEntry 54 }

sonusDsx1AdmnLSESThreshold OBJECT-TYPE
    SYNTAX          INTEGER (1..900)
    ACCESS          read-write
    STATUS          obsolete
    DESCRIPTION     
            "Severely Errored Seconds threshold value for 15 minute interval. 
             This is for near end. This object was obsoleted in release 6.1."
    DEFVAL          { 10 }
    ::= { sonusDsx1AdmnEntry 55 }

sonusDsx1AdmnDayLESThreshold OBJECT-TYPE
    SYNTAX          INTEGER (1..65535)
    ACCESS          read-write
    STATUS          obsolete
    DESCRIPTION     
            "Errored Seconds threshold value for a day. This is for near end.
             This object was obsoleted in release 6.1."
    DEFVAL          { 648 }
    ::= { sonusDsx1AdmnEntry 56 }

sonusDsx1AdmnDayLSESThreshold OBJECT-TYPE
    SYNTAX          INTEGER (1..65535)
    ACCESS          read-write
    STATUS          obsolete
    DESCRIPTION     
            "Severely Errored Seconds threshold value for a day. This is for near end.
             This object was obsoleted in release 6.1."
    DEFVAL          { 100 }
    ::= { sonusDsx1AdmnEntry 57 }

sonusDsx1AdmnSASThreshold OBJECT-TYPE
    SYNTAX          INTEGER (1..900)
    ACCESS          read-write
    STATUS          obsolete
    DESCRIPTION     
            "SEF/AIS Seconds threshold value for 15 minute interval. 
             This is for near end. This object was obsoleted in release 6.1."
    DEFVAL          { 2 }
    ::= { sonusDsx1AdmnEntry 58 }

sonusDsx1AdmnDaySASThreshold OBJECT-TYPE
    SYNTAX          INTEGER (1..65535)
    ACCESS          read-write
    STATUS          obsolete
    DESCRIPTION     
            "SES/AIS Seconds threshold value for a day. This is for near end.
             This object was obsoleted in release 6.1."
    DEFVAL          { 17 }
    ::= { sonusDsx1AdmnEntry 59 }

sonusDsx1AdmnSEFSThreshold OBJECT-TYPE
    SYNTAX          INTEGER (1..900)
    ACCESS          read-write
    STATUS          obsolete
    DESCRIPTION     
            "Severely Errored Frame Seconds threshold value for 15 minute interval. 
             This is for near end. This object was obsoleted in release 6.1."
    DEFVAL          { 2 }
    ::= { sonusDsx1AdmnEntry 60 }

sonusDsx1AdmnDaySEFSThreshold OBJECT-TYPE
    SYNTAX          INTEGER (1..65535)
    ACCESS          read-write
    STATUS          obsolete
    DESCRIPTION     
            "Severely Errored Frame Seconds threshold value for a day. This is for near end.
             This object was obsoleted in release 6.1."
    DEFVAL          { 17 }
    ::= { sonusDsx1AdmnEntry 61 }

sonusDsx1AdmnStatAction OBJECT-TYPE
    SYNTAX          INTEGER { initLine15MinNearEnd(1), 
                        initPath15MinNearEnd(2), initLine15MinFarEnd(3), 
                        initPath15MinFarEnd(4), initLine24HourNearEnd(5), 
                        initPath24HourNearEnd(6), 
                        initLine24HourFarEnd(7), initPath24HourFarEnd(8) }
    ACCESS          read-write
    STATUS          mandatory
    DESCRIPTION     
            "Initialize Performance Monitoring Statistics."
    ::= { sonusDsx1AdmnEntry 62 }

sonusDsx1AdmnSTS1Index OBJECT-TYPE
    SYNTAX          INTEGER (1..3)
    ACCESS          read-only
    STATUS          mandatory
    DESCRIPTION     
            "Only valid if DS1 is carried in SONET/SDH signal.
             STS1 Index in which the DS1 is carried."
    ::= { sonusDsx1AdmnEntry 63 }

sonusDsx1AdmnVTGroupIndex OBJECT-TYPE
    SYNTAX          INTEGER (1..7)
    ACCESS          read-only
    STATUS          mandatory
    DESCRIPTION     
            "Only valid if DS1 is carried in SONET/SDH signal which
             has been configured for Virtual Tributary mapping.
             VT Group Index in which the DS1 is carried."
    ::= { sonusDsx1AdmnEntry 64 }

sonusDsx1AdmnVTIndex OBJECT-TYPE
    SYNTAX          INTEGER (1..4)
    ACCESS          read-only
    STATUS          mandatory
    DESCRIPTION     
            "Only valid if DS1 is carried in SONET/SDH signal which
             has been configured for Virtual Tributary mapping.
             VT Index in which the DS1 is carried."
    ::= { sonusDsx1AdmnEntry 65 }

sonusDsx1AdmnLCVTcaFilter OBJECT-TYPE
    SYNTAX          SonusAdminState
    ACCESS          read-write
    STATUS          obsolete
    DESCRIPTION     
            "Controls whether a threshold Crossing Alert (TCA) is reported (via
             an event log and trap). Setting this object to Enabled will prevent
             the TCA from being reported (i.e will Filter the TCA report).
             This object was obsoleted in release 6.1."
    DEFVAL          { disabled }
    ::= { sonusDsx1AdmnEntry 66 }

sonusDsx1AdmnLESTcaFilter OBJECT-TYPE
    SYNTAX          SonusAdminState
    ACCESS          read-write
    STATUS          obsolete
    DESCRIPTION     
            "Controls whether a threshold Crossing Alert (TCA) is reported (via
             an event log and trap). Setting this object to Enabled will prevent
             the TCA from being reported (i.e will Filter the TCA report).
             This object was obsoleted in release 6.1."
    DEFVAL          { disabled }
    ::= { sonusDsx1AdmnEntry 67 }

sonusDsx1AdmnLSESTcaFilter OBJECT-TYPE
    SYNTAX          SonusAdminState
    ACCESS          read-write
    STATUS          obsolete
    DESCRIPTION     
            "Controls whether a threshold Crossing Alert (TCA) is reported (via
             an event log and trap). Setting this object to Enabled will prevent
             the TCA from being reported (i.e will Filter the TCA report).
             This object was obsoleted in release 6.1."
    DEFVAL          { disabled }
    ::= { sonusDsx1AdmnEntry 68 }

sonusDsx1AdmnPCVTcaFilter OBJECT-TYPE
    SYNTAX          SonusAdminState
    ACCESS          read-write
    STATUS          obsolete
    DESCRIPTION     
            "Controls whether a threshold Crossing Alert (TCA) is reported (via
             an event log and trap). Setting this object to Enabled will prevent
             the TCA from being reported (i.e will Filter the TCA report).
             This object was obsoleted in release 6.1."
    DEFVAL          { disabled }
    ::= { sonusDsx1AdmnEntry 69 }

sonusDsx1AdmnPESTcaFilter OBJECT-TYPE
    SYNTAX          SonusAdminState
    ACCESS          read-write
    STATUS          obsolete
    DESCRIPTION     
            "Controls whether a threshold Crossing Alert (TCA) is reported (via
             an event log and trap). Setting this object to Enabled will prevent
             the TCA from being reported (i.e will Filter the TCA report).
             This object was obsoleted in release 6.1."
    DEFVAL          { disabled }
    ::= { sonusDsx1AdmnEntry 70 }

sonusDsx1AdmnPSESTcaFilter OBJECT-TYPE
    SYNTAX          SonusAdminState
    ACCESS          read-write
    STATUS          obsolete
    DESCRIPTION     
            "Controls whether a threshold Crossing Alert (TCA) is reported (via
             an event log and trap). Setting this object to Enabled will prevent
             the TCA from being reported (i.e will Filter the TCA report).
             This object was obsoleted in release 6.1."
    DEFVAL          { disabled }
    ::= { sonusDsx1AdmnEntry 71 }

sonusDsx1AdmnSASTcaFilter OBJECT-TYPE
    SYNTAX          SonusAdminState
    ACCESS          read-write
    STATUS          obsolete
    DESCRIPTION     
            "Controls whether a threshold Crossing Alert (TCA) is reported (via
             an event log and trap). Setting this object to Enabled will prevent
             the TCA from being reported (i.e will Filter the TCA report).
             This object was obsoleted in release 6.1."
    DEFVAL          { disabled }
    ::= { sonusDsx1AdmnEntry 72 }

sonusDsx1AdmnCSSTcaFilter OBJECT-TYPE
    SYNTAX          SonusAdminState
    ACCESS          read-write
    STATUS          obsolete
    DESCRIPTION     
            "Controls whether a threshold Crossing Alert (TCA) is reported (via
             an event log and trap). Setting this object to Enabled will prevent
             the TCA from being reported (i.e will Filter the TCA report).
             This object was obsoleted in release 6.1."
    DEFVAL          { disabled }
    ::= { sonusDsx1AdmnEntry 73 }

sonusDsx1AdmnSEFSTcaFilter OBJECT-TYPE
    SYNTAX          SonusAdminState
    ACCESS          read-write
    STATUS          obsolete
    DESCRIPTION     
            "Controls whether a threshold Crossing Alert (TCA) is reported (via
             an event log and trap). Setting this object to Enabled will prevent
             the TCA from being reported (i.e will Filter the TCA report).
             This object was obsoleted in release 6.1."
    DEFVAL          { disabled }
    ::= { sonusDsx1AdmnEntry 74 }

sonusDsx1AdmnUASTcaFilter OBJECT-TYPE
    SYNTAX          SonusAdminState
    ACCESS          read-write
    STATUS          obsolete
    DESCRIPTION     
            "Controls whether a threshold Crossing Alert (TCA) is reported (via
             an event log and trap). Setting this object to Enabled will prevent
             the TCA from being reported (i.e will Filter the TCA report).
             This object was obsoleted in release 6.1."
    DEFVAL          { disabled }
    ::= { sonusDsx1AdmnEntry 75 }

sonusDsx1AdmnLegacyTrapEnable OBJECT-TYPE
    SYNTAX          SonusAdminState
    ACCESS          read-write
    STATUS          mandatory
    DESCRIPTION     
            "Controls whether the old traps sonusDsx1AdminChangeNotification,
             sonusDsx1OutOfServiceNotification, sonusDsx1ThresholdCrossingNotification,
             sonusDsx1LineStatusChangeNotification are generated, or whether
             the new traps sonusDsx1AdminStateChangeNotification,
             sonusDsx1AdminModeChangeNotification, sonusDsx1AdminDryupNotification,
             sonusDsx1PerfmonThresholdCrossingNotification,
             sonusDsx1AlarmStateChangeNotification are generated. If ENABLED,
             old traps are generated. This is to support	third-party management
             systems which expected the old traps; normally	this object value
             should be set to DISABLED to allow the new traps to be generated."
    DEFVAL          { disabled }
    ::= { sonusDsx1AdmnEntry 76 }

sonusDsx1AdmnInbandCode OBJECT-TYPE
    SYNTAX          INTEGER { ibcNone(1), ibcLpbkActFramed(2), 
                        ibcLpbkDeactFramed(3), ibcLpbkActUnframed(4), 
                        ibcLpbkDeactUnframed(5) }
    ACCESS          read-write
    STATUS          mandatory
    DESCRIPTION     
            "Configures inband code to send to far-end."
    DEFVAL          { ibcNone }
    ::= { sonusDsx1AdmnEntry 77 }

sonusDsx1AdmnQ50BssSignalBits OBJECT-TYPE
    SYNTAX          INTEGER { bitsAB(1), bitsCD(2) }
    ACCESS          read-write
    STATUS          mandatory
    DESCRIPTION     
            " "
    DEFVAL          { bitsAB }
    ::= { sonusDsx1AdmnEntry 78 }

sonusDsx1AdmnQ50MaintReqResp OBJECT-TYPE
    SYNTAX          INTEGER { accept(1), refuse(2) }
    ACCESS          read-write
    STATUS          mandatory
    DESCRIPTION     
            " "
    DEFVAL          { accept }
    ::= { sonusDsx1AdmnEntry 79 }

sonusDsx1AdmnQ50DcmeAckTimeout OBJECT-TYPE
    SYNTAX          INTEGER (100..2000)
    ACCESS          read-write
    STATUS          mandatory
    DESCRIPTION     
            " "
    DEFVAL          { 2000 }
    ::= { sonusDsx1AdmnEntry 80 }

sonusDsx1AdmnQ50InitStatistics OBJECT-TYPE
    SYNTAX          SonusAdminState
    ACCESS          read-write
    STATUS          mandatory
    DESCRIPTION     
            " "
    DEFVAL          { disabled }
    ::= { sonusDsx1AdmnEntry 81 }

sonusDsx1AdmnAisTimer OBJECT-TYPE
    SYNTAX          INTEGER { millisec100(1), millisec2500(2) }
    ACCESS          read-write
    STATUS          mandatory
    DESCRIPTION     
            " "
    DEFVAL          { millisec100 }
    ::= { sonusDsx1AdmnEntry 82 }

sonusDsx1AdmnRaiTimer OBJECT-TYPE
    SYNTAX          INTEGER { millisec450(1), millisec2500(2) }
    ACCESS          read-write
    STATUS          mandatory
    DESCRIPTION     
            " "
    DEFVAL          { millisec450 }
    ::= { sonusDsx1AdmnEntry 83 }

sonusDsx1StatTable OBJECT-TYPE
    SYNTAX          SEQUENCE OF SonusDsx1StatEntry
    ACCESS          not-accessible
    STATUS          mandatory
    DESCRIPTION     
            "Table of Sonus Enterprise Status for all DS1s"
    ::= { sonusDsx1MIBObjects 2 }

sonusDsx1StatEntry OBJECT-TYPE
    SYNTAX          SonusDsx1StatEntry
    ACCESS          not-accessible
    STATUS          mandatory
    DESCRIPTION     
            "Entry in Table consisting of the all the Sonus Enterprise DS1 Status"
    INDEX           { sonusDsx1StatShelfIndex, sonusDsx1StatSlotIndex, 
                      sonusDsx1StatPortIndex, sonusDsx1StatDs3Index, 
                      sonusDsx1StatDs1Index }
    ::= { sonusDsx1StatTable 1 }

SonusDsx1StatEntry ::=
    SEQUENCE {
        sonusDsx1StatShelfIndex         SonusShelfIndex,
        sonusDsx1StatSlotIndex          SonusSlotIndex,
        sonusDsx1StatPortIndex          INTEGER,
        sonusDsx1StatDs3Index           INTEGER,
        sonusDsx1StatDs1Index           INTEGER,
        sonusDsx1StatValidInt           INTEGER,
        sonusDsx1StatRxSlips            INTEGER,
        sonusDsx1StatTxSlips            INTEGER,
        sonusDsx1StatLOF                INTEGER,
        sonusDsx1StatAIS                INTEGER,
        sonusDsx1StatRAI                INTEGER,
        sonusDsx1StatRED                INTEGER,
        sonusDsx1StatCRC                INTEGER,
        sonusDsx1StatCOFA               INTEGER,
        sonusDsx1StatFBE                INTEGER,
        sonusDsx1StatStatus             DisplayString,
        sonusDsx1StatAllocChannels      DisplayString,
        sonusDsx1StatEnabChannels       DisplayString,
        sonusE1StatLOMF                 INTEGER,
        sonusE1StatMFError              INTEGER,
        sonusE1StatFEBE                 INTEGER,
        sonusE1StatOOOF                 INTEGER,
        sonusE1StatC2NCIWCK             INTEGER,
        sonusE1StatRAIContCRC           INTEGER,
        sonusE1StatContFEBE             INTEGER,
        sonusE1StatExcessCRC            INTEGER,
        sonusE1StatFASErr               INTEGER,
        sonusDsx1StatSendPattern        INTEGER,
        sonusDsx1StatStatusCode         INTEGER,
        sonusDsx1StatLoopbackStatus     INTEGER,
        sonusDsx1StatOperStatus         INTEGER,
        sonusDsx1StatValidDayInt        INTEGER,
        sonusDsx1StatDefectAIS          INTEGER,
        sonusDsx1StatDefectRAI          INTEGER,
        sonusDsx1StatE1CasAlarmStatus   INTEGER,
        sonusDsx1StatQ50TrunkState      INTEGER,
        sonusDsx1StatQ50RcvTrmSignal    INTEGER,
        sonusDsx1StatQ50XmtTrmSignal    INTEGER,
        sonusDsx1StatQ50Good3kHzCalls   INTEGER,
        sonusDsx1StatQ50Failed3kHzCalls INTEGER,
        sonusDsx1StatQ50Good64kbpsCalls INTEGER,
        sonusDsx1StatQ50Failed64kbpsCalls INTEGER,
        sonusDsx1StatQ50Alloc3khzChannels DisplayString,
        sonusDsx1StatQ50Alloc64kbpsChannels   DisplayString
    }

sonusDsx1StatShelfIndex OBJECT-TYPE
    SYNTAX          SonusShelfIndex
    ACCESS          read-only
    STATUS          mandatory
    DESCRIPTION     
            "Shelf index into this table"
    ::= { sonusDsx1StatEntry 1 }

sonusDsx1StatSlotIndex OBJECT-TYPE
    SYNTAX          SonusSlotIndex
    ACCESS          read-only
    STATUS          mandatory
    DESCRIPTION     
            "Slot index into this table"
    ::= { sonusDsx1StatEntry 2 }

sonusDsx1StatPortIndex OBJECT-TYPE
    SYNTAX          INTEGER
    ACCESS          read-only
    STATUS          mandatory
    DESCRIPTION     
            "Port Index into this table"
    ::= { sonusDsx1StatEntry 3 }

sonusDsx1StatDs3Index OBJECT-TYPE
    SYNTAX          INTEGER
    ACCESS          read-only
    STATUS          mandatory
    DESCRIPTION     
            "Ds3 Index into this table"
    ::= { sonusDsx1StatEntry 4 }

sonusDsx1StatDs1Index OBJECT-TYPE
    SYNTAX          INTEGER
    ACCESS          read-only
    STATUS          mandatory
    DESCRIPTION     
            "Ds1 Index into this table"
    ::= { sonusDsx1StatEntry 5 }

sonusDsx1StatValidInt OBJECT-TYPE
    SYNTAX          INTEGER
    ACCESS          read-only
    STATUS          mandatory
    DESCRIPTION     
            "Number of valid intervals of Performance Monitoring"
    ::= { sonusDsx1StatEntry 6 }

sonusDsx1StatRxSlips OBJECT-TYPE
    SYNTAX          INTEGER
    ACCESS          read-only
    STATUS          mandatory
    DESCRIPTION     
            "Number of frame slips in the receive direction."
    ::= { sonusDsx1StatEntry 7 }

sonusDsx1StatTxSlips OBJECT-TYPE
    SYNTAX          INTEGER
    ACCESS          read-only
    STATUS          mandatory
    DESCRIPTION     
            "Number of frame slips in the transmit direction."
    ::= { sonusDsx1StatEntry 8 }

sonusDsx1StatLOF OBJECT-TYPE
    SYNTAX          INTEGER
    ACCESS          read-only
    STATUS          mandatory
    DESCRIPTION     
            "Number of Loss of Frame defects that have occured."
    ::= { sonusDsx1StatEntry 9 }

sonusDsx1StatAIS OBJECT-TYPE
    SYNTAX          INTEGER
    ACCESS          read-only
    STATUS          mandatory
    DESCRIPTION     
            "Number of AIS alarms that have occured."
    ::= { sonusDsx1StatEntry 10 }

sonusDsx1StatRAI OBJECT-TYPE
    SYNTAX          INTEGER
    ACCESS          read-only
    STATUS          mandatory
    DESCRIPTION     
            "Number of RAI alarms that have occured."
    ::= { sonusDsx1StatEntry 11 }

sonusDsx1StatRED OBJECT-TYPE
    SYNTAX          INTEGER
    ACCESS          read-only
    STATUS          mandatory
    DESCRIPTION     
            "Number of RED alarms that have occured."
    ::= { sonusDsx1StatEntry 12 }

sonusDsx1StatCRC OBJECT-TYPE
    SYNTAX          INTEGER
    ACCESS          read-only
    STATUS          mandatory
    DESCRIPTION     
            "Number T1 CRC framing errors that have occured."
    ::= { sonusDsx1StatEntry 13 }

sonusDsx1StatCOFA OBJECT-TYPE
    SYNTAX          INTEGER
    ACCESS          read-only
    STATUS          obsolete
    DESCRIPTION     
            "Number of Change of Frame Alignments that have occured.
             This object was obsoleted in release 5.1."
    ::= { sonusDsx1StatEntry 14 }

sonusDsx1StatFBE OBJECT-TYPE
    SYNTAX          INTEGER
    ACCESS          read-only
    STATUS          mandatory
    DESCRIPTION     
            "Number framing bit errors that have occured."
    ::= { sonusDsx1StatEntry 15 }

sonusDsx1StatStatus OBJECT-TYPE
    SYNTAX          DisplayString
    ACCESS          read-only
    STATUS          deprecated
    DESCRIPTION     
            "T1/E1 span status. Indicates if port in alarm state, loopback state etc."
    ::= { sonusDsx1StatEntry 16 }

sonusDsx1StatAllocChannels OBJECT-TYPE
    SYNTAX          DisplayString
    ACCESS          read-only
    STATUS          mandatory
    DESCRIPTION     
            "String display showing bitmap of channels that are currently allocated.
             A 1 indicates that the channel is allocated."
    ::= { sonusDsx1StatEntry 17 }

sonusDsx1StatEnabChannels OBJECT-TYPE
    SYNTAX          DisplayString
    ACCESS          read-only
    STATUS          mandatory
    DESCRIPTION     
            "String display showing bitmap of channels that are currently enabled
             A 1 indicates that the channel is allocated."
    ::= { sonusDsx1StatEntry 18 }

sonusE1StatLOMF OBJECT-TYPE
    SYNTAX          INTEGER
    ACCESS          read-only
    STATUS          mandatory
    DESCRIPTION     
            "Number of Loss of Multiframe alignments that have occured."
    ::= { sonusDsx1StatEntry 19 }

sonusE1StatMFError OBJECT-TYPE
    SYNTAX          INTEGER
    ACCESS          read-only
    STATUS          mandatory
    DESCRIPTION     
            "Number of Multiframe CRC errors that have occured."
    ::= { sonusDsx1StatEntry 20 }

sonusE1StatFEBE OBJECT-TYPE
    SYNTAX          INTEGER
    ACCESS          read-only
    STATUS          mandatory
    DESCRIPTION     
            "Number of Far End Block errors that have occured."
    ::= { sonusDsx1StatEntry 21 }

sonusE1StatOOOF OBJECT-TYPE
    SYNTAX          INTEGER
    ACCESS          read-only
    STATUS          mandatory
    DESCRIPTION     
            "Number of Out of ofline framer errors that have occured."
    ::= { sonusDsx1StatEntry 22 }

sonusE1StatC2NCIWCK OBJECT-TYPE
    SYNTAX          INTEGER
    ACCESS          read-only
    STATUS          mandatory
    DESCRIPTION     
            "Number of CRC 2 Non CRC framing events that have occured."
    ::= { sonusDsx1StatEntry 23 }

sonusE1StatRAIContCRC OBJECT-TYPE
    SYNTAX          INTEGER
    ACCESS          read-only
    STATUS          mandatory
    DESCRIPTION     
            "Number of RAI and Continuous CRC errors that have occured."
    ::= { sonusDsx1StatEntry 24 }

sonusE1StatContFEBE OBJECT-TYPE
    SYNTAX          INTEGER
    ACCESS          read-only
    STATUS          mandatory
    DESCRIPTION     
            "Number of Continuous FEBE errors that have occured."
    ::= { sonusDsx1StatEntry 25 }

sonusE1StatExcessCRC OBJECT-TYPE
    SYNTAX          INTEGER
    ACCESS          read-only
    STATUS          mandatory
    DESCRIPTION     
            "Number of Excessive CRC errors that have occured."
    ::= { sonusDsx1StatEntry 26 }

sonusE1StatFASErr OBJECT-TYPE
    SYNTAX          INTEGER
    ACCESS          read-only
    STATUS          mandatory
    DESCRIPTION     
            "Number of Frame Alignment Sequence Errors."
    ::= { sonusDsx1StatEntry 27 }

sonusDsx1StatSendPattern OBJECT-TYPE
    SYNTAX          INTEGER { dsx1SendNoCode(1), dsx1SendLineCode(2), 
                        dsx1SendPayloadCode(3), dsx1SendResetCode(4), 
                        dsx1SendQRS(5), dsx1Send511Pattern(6), 
                        dsx1Send3in24Pattern(7), 
                        dsx1SendOtherTestPattern(8) }
    ACCESS          read-only
    STATUS          mandatory
    DESCRIPTION     
            "Indicates status of SendCode variable for PATTERNS ONLY
             - does not include SendCodes that require loopback."
    DEFVAL          { dsx1SendNoCode }
    ::= { sonusDsx1StatEntry 28 }

sonusDsx1StatStatusCode OBJECT-TYPE
    SYNTAX          INTEGER { dsx1StatStatusCodeNoAlarm(1), 
                        dsx1StatStatusCodeRedAlarm(2), 
                        dsx1StatStatusCodeYellowAlarm(3), 
                        dsx1StatStatusCodeAisAlarm(4), 
                        dsx1StatStatusCodeDspFailure(5), 
                        dsx1StatStatusCodeLoopback(6), notApplicable(7) }
    ACCESS          read-only
    STATUS          mandatory
    DESCRIPTION     
            "T1/E1 span status. Indicates if port in alarm state, loopback state etc. Integer version of 
             sonusDsx1StatStatus variable."
    DEFVAL          { dsx1StatStatusCodeNoAlarm }
    ::= { sonusDsx1StatEntry 29 }

sonusDsx1StatLoopbackStatus OBJECT-TYPE
    SYNTAX          INTEGER { dsx1StatLoopbackStatusNoLoopback(1), 
                        dsx1StatLoopbackStatusNeLineLoopback(2), 
                        dsx1StatLoopbackStatusNePayloadLoopback(3), 
                        dsx1StatLoopbackStatusNeInwardLoopback(4), 
                        dsx1StatLoopbackStatusNeDualLoopback(5), 
                        dsx1StatLoopbackStatusFeLineLoopback(6), 
                        dsx1StatLoopbackStatusFePayloadLoopback(7) }
    ACCESS          read-only
    STATUS          mandatory
    DESCRIPTION     
            "T1 loopback status display. Indicates loopback STATUS of T1 port."
    DEFVAL          { dsx1StatLoopbackStatusNoLoopback }
    ::= { sonusDsx1StatEntry 30 }

sonusDsx1StatOperStatus OBJECT-TYPE
    SYNTAX          INTEGER { up(1), down(2), dryingUp(3), remoteDown(4), 
                        downOos(5), downDs1Alarm(6), downQ50Maint(7), 
                        downQ50Ts16Alarm(8) }
    ACCESS          read-only
    STATUS          mandatory
    DESCRIPTION     
            "The actual status of the DS1 interface. Interface is 
             Up if it is administratively in service and there are no
             line failures or hardware failures. Interface is Down if
             it is administratively in service and there are line
             failures or hardware failures, or if it is administratively
             out of service. Interface is DryingUp if it is administratively
             out of service and is drying up (no new	calls, still carrying
             in-progress calls)."
    ::= { sonusDsx1StatEntry 31 }

sonusDsx1StatValidDayInt OBJECT-TYPE
    SYNTAX          INTEGER
    ACCESS          read-only
    STATUS          mandatory
    DESCRIPTION     
            "Number of valid day intervals of Performance Monitoring"
    ::= { sonusDsx1StatEntry 32 }

sonusDsx1StatDefectAIS OBJECT-TYPE
    SYNTAX          INTEGER
    ACCESS          read-only
    STATUS          mandatory
    DESCRIPTION     
            "Number of AIS defects that have occured."
    ::= { sonusDsx1StatEntry 33 }

sonusDsx1StatDefectRAI OBJECT-TYPE
    SYNTAX          INTEGER
    ACCESS          read-only
    STATUS          mandatory
    DESCRIPTION     
            "Number of RAI defects that have occured."
    ::= { sonusDsx1StatEntry 34 }

sonusDsx1StatE1CasAlarmStatus OBJECT-TYPE
    SYNTAX          INTEGER { notApplicable(1), noAlarm(2), ais16(3), 
                        lomfa(4), yellow(5) }
    ACCESS          read-only
    STATUS          mandatory
    DESCRIPTION     
            "E1 CAS Channel 16 alarm status."
    ::= { sonusDsx1StatEntry 35 }

sonusDsx1StatQ50TrunkState OBJECT-TYPE
    SYNTAX          INTEGER { fullCapacity(1), no3khzCapacity(2), 
                        no64kbpsCapacity(3), maintRelease(4), 
                        maintReleaseReq(5), alarm(6) }
    ACCESS          read-only
    STATUS          mandatory
    DESCRIPTION     
            " "
    ::= { sonusDsx1StatEntry 36 }

sonusDsx1StatQ50RcvTrmSignal OBJECT-TYPE
    SYNTAX          INTEGER { dcmeNormal(1), noTrunkAvail3khzAudio(2), 
                        noChanAvail3khzAudio(3), 
                        no64kbpsCapacityAvail(4), maintReleaseReq(5), 
                        unknown(6), invalid(7) }
    ACCESS          read-only
    STATUS          mandatory
    DESCRIPTION     
            " "
    ::= { sonusDsx1StatEntry 37 }

sonusDsx1StatQ50XmtTrmSignal OBJECT-TYPE
    SYNTAX          INTEGER { iscNormal(1), maintReleaseAck(2), 
                        dcmeClearOfTraffic(3), invalid(4) }
    ACCESS          read-only
    STATUS          mandatory
    DESCRIPTION     
            " "
    ::= { sonusDsx1StatEntry 38 }

sonusDsx1StatQ50Good3kHzCalls OBJECT-TYPE
    SYNTAX          INTEGER
    ACCESS          read-only
    STATUS          mandatory
    DESCRIPTION     
            " "
    ::= { sonusDsx1StatEntry 39 }

sonusDsx1StatQ50Failed3kHzCalls OBJECT-TYPE
    SYNTAX          INTEGER
    ACCESS          read-only
    STATUS          mandatory
    DESCRIPTION     
            " "
    ::= { sonusDsx1StatEntry 40 }

sonusDsx1StatQ50Good64kbpsCalls OBJECT-TYPE
    SYNTAX          INTEGER
    ACCESS          read-only
    STATUS          mandatory
    DESCRIPTION     
            " "
    ::= { sonusDsx1StatEntry 41 }

sonusDsx1StatQ50Failed64kbpsCalls OBJECT-TYPE
    SYNTAX          INTEGER
    ACCESS          read-only
    STATUS          mandatory
    DESCRIPTION     
            " "
    ::= { sonusDsx1StatEntry 42 }

sonusDsx1StatQ50Alloc3khzChannels OBJECT-TYPE
    SYNTAX          DisplayString
    ACCESS          read-only
    STATUS          mandatory
    DESCRIPTION     
            " "
    ::= { sonusDsx1StatEntry 43 }

sonusDsx1StatQ50Alloc64kbpsChannels OBJECT-TYPE
    SYNTAX          DisplayString
    ACCESS          read-only
    STATUS          mandatory
    DESCRIPTION     
            " "
    ::= { sonusDsx1StatEntry 44 }

sonusDs0AdmnTable OBJECT-TYPE
    SYNTAX          SEQUENCE OF SonusDs0AdmnEntry
    ACCESS          not-accessible
    STATUS          mandatory
    DESCRIPTION     
            "Table of Sonus Enterprise Configuration for DS0s"
    ::= { sonusDsx1MIBObjects 3 }

sonusDs0AdmnEntry OBJECT-TYPE
    SYNTAX          SonusDs0AdmnEntry
    ACCESS          not-accessible
    STATUS          mandatory
    DESCRIPTION     
            "Entry in Table consisting of the all the Sonus Enterprise Ds0 Configuration"
    INDEX           { sonusDs0AdmnShelfIndex, sonusDs0AdmnSlotIndex, 
                      sonusDs0AdmnPortIndex, sonusDs0AdmnDs3Index, 
                      sonusDs0AdmnDs1Index, sonusDs0AdmnDs0Index }
    ::= { sonusDs0AdmnTable 1 }

SonusDs0AdmnEntry ::=
    SEQUENCE {
        sonusDs0AdmnShelfIndex          SonusShelfIndex,
        sonusDs0AdmnSlotIndex           SonusSlotIndex,
        sonusDs0AdmnPortIndex           INTEGER,
        sonusDs0AdmnDs3Index            INTEGER,
        sonusDs0AdmnDs1Index            INTEGER,
        sonusDs0AdmnDs0Index            INTEGER,
        sonusDs0AdmnTimeout             INTEGER,
        sonusDs0AdmnMode                SonusServiceState,
        sonusDs0AdmnAction              SonusAdminAction,
        sonusDs0AdmnState               INTEGER,
        sonusDs0AdmnIdleCode            INTEGER,
        sonusDs0AdmnTone                INTEGER,
        sonusDs0AdmnLoopback            INTEGER,
        sonusDs0AdmnQ50ChannelState     INTEGER,
        sonusDs0AdmnQ50RcvBssSignal     INTEGER,
        sonusDs0AdmnQ50XmtBssSignal     INTEGER
    }

sonusDs0AdmnShelfIndex OBJECT-TYPE
    SYNTAX          SonusShelfIndex
    ACCESS          read-only
    STATUS          mandatory
    DESCRIPTION     
            "Shelf Index for this table"
    ::= { sonusDs0AdmnEntry 1 }

sonusDs0AdmnSlotIndex OBJECT-TYPE
    SYNTAX          SonusSlotIndex
    ACCESS          read-only
    STATUS          mandatory
    DESCRIPTION     
            "Slot index for this table"
    ::= { sonusDs0AdmnEntry 2 }

sonusDs0AdmnPortIndex OBJECT-TYPE
    SYNTAX          INTEGER
    ACCESS          read-only
    STATUS          mandatory
    DESCRIPTION     
            "Port Index into this table"
    ::= { sonusDs0AdmnEntry 3 }

sonusDs0AdmnDs3Index OBJECT-TYPE
    SYNTAX          INTEGER
    ACCESS          read-only
    STATUS          mandatory
    DESCRIPTION     
            "Ds3 Index into this table"
    ::= { sonusDs0AdmnEntry 4 }

sonusDs0AdmnDs1Index OBJECT-TYPE
    SYNTAX          INTEGER
    ACCESS          read-only
    STATUS          mandatory
    DESCRIPTION     
            "DS1 index for this table"
    ::= { sonusDs0AdmnEntry 5 }

sonusDs0AdmnDs0Index OBJECT-TYPE
    SYNTAX          INTEGER
    ACCESS          read-only
    STATUS          mandatory
    DESCRIPTION     
            "DS0 index for this table"
    ::= { sonusDs0AdmnEntry 6 }

sonusDs0AdmnTimeout OBJECT-TYPE
    SYNTAX          INTEGER (0..1440)
    ACCESS          read-write
    STATUS          mandatory
    DESCRIPTION     
            "Max time in minutes before channel dryup takes place"
    DEFVAL          { 5 }
    ::= { sonusDs0AdmnEntry 7 }

sonusDs0AdmnMode OBJECT-TYPE
    SYNTAX          SonusServiceState
    ACCESS          read-write
    STATUS          mandatory
    DESCRIPTION     
            "Channel is in service or out of service."
    DEFVAL          { outOfService }
    ::= { sonusDs0AdmnEntry 8 }

sonusDs0AdmnAction OBJECT-TYPE
    SYNTAX          SonusAdminAction
    ACCESS          read-write
    STATUS          mandatory
    DESCRIPTION     
            "Force out of service or wait for dryup"
    DEFVAL          { dryUp }
    ::= { sonusDs0AdmnEntry 9 }

sonusDs0AdmnState OBJECT-TYPE
    SYNTAX          INTEGER { unavailable(1), available(2) }
    ACCESS          read-write
    STATUS          mandatory
    DESCRIPTION     
            "Channel state, available/unavailable"
    DEFVAL          { available }
    ::= { sonusDs0AdmnEntry 10 }

sonusDs0AdmnIdleCode OBJECT-TYPE
    SYNTAX          INTEGER (0..255)
    ACCESS          read-write
    STATUS          mandatory
    DESCRIPTION     
            "Channel Idle Code pattern"
    DEFVAL          { 127 }
    ::= { sonusDs0AdmnEntry 11 }

sonusDs0AdmnTone OBJECT-TYPE
    SYNTAX          INTEGER { none(1), dmw(2) }
    ACCESS          read-write
    STATUS          mandatory
    DESCRIPTION     
            "Insert different tones into channel. Digital milliwatt"
    DEFVAL          { none }
    ::= { sonusDs0AdmnEntry 12 }

sonusDs0AdmnLoopback OBJECT-TYPE
    SYNTAX          INTEGER { disabled(1), enabled(2) }
    ACCESS          read-write
    STATUS          mandatory
    DESCRIPTION     
            "Put channel in loopback"
    DEFVAL          { disabled }
    ::= { sonusDs0AdmnEntry 13 }

sonusDs0AdmnQ50ChannelState OBJECT-TYPE
    SYNTAX          INTEGER { idle(1), seized3khzAudio(2), 
                        seized64kbpsUnres(3), oosUnavail(4) }
    ACCESS          read-only
    STATUS          mandatory
    DESCRIPTION     
            " "
    ::= { sonusDs0AdmnEntry 14 }

sonusDs0AdmnQ50RcvBssSignal OBJECT-TYPE
    SYNTAX          INTEGER { normalService(1), specialServiceAck(2), 
                        oosUnavailable(3), unknown(4), invalid(5) }
    ACCESS          read-only
    STATUS          mandatory
    DESCRIPTION     
            " "
    ::= { sonusDs0AdmnEntry 15 }

sonusDs0AdmnQ50XmtBssSignal OBJECT-TYPE
    SYNTAX          INTEGER { normalService(1), request64kbps(2), 
                        invalid(3) }
    ACCESS          read-only
    STATUS          mandatory
    DESCRIPTION     
            " "
    ::= { sonusDs0AdmnEntry 16 }

sonusDs1Profile OBJECT IDENTIFIER
    ::= { sonusDsx1MIBObjects 4 }

sonusDs1ProfileNextIndex OBJECT-TYPE
    SYNTAX          INTEGER
    ACCESS          read-only
    STATUS          mandatory
    DESCRIPTION     
            "The next valid index to use when creating an entry in
             the sonusDs1ProfileTable."
    ::= { sonusDs1Profile 1 }

sonusDs1ProfileTable OBJECT-TYPE
    SYNTAX          SEQUENCE OF SonusDs1ProfileEntry
    ACCESS          not-accessible
    STATUS          mandatory
    DESCRIPTION     
            "Table for T1/E1 profile"
    ::= { sonusDs1Profile 2 }

sonusDs1ProfileEntry OBJECT-TYPE
    SYNTAX          SonusDs1ProfileEntry
    ACCESS          not-accessible
    STATUS          mandatory
    DESCRIPTION     
            "Entry in Table consisting of T1/E1 profile. The T1/E1 profiles
             have to be created by users and then configured. These profiles
             can then be applied onto any T1/E1 span."
    INDEX           { sonusDs1ProfileIndex }
    ::= { sonusDs1ProfileTable 1 }

SonusDs1ProfileEntry ::=
    SEQUENCE {
        sonusDs1ProfileRowStatus        RowStatus,
        sonusDs1ProfileName             SonusName,
        sonusDs1ProfileIndex            INTEGER,
        sonusDs1ProfileState            SonusAdminState,
        sonusDs1ProfileDs1LineBO        INTEGER,
        sonusDs1ProfileDs1LineType      INTEGER,
        sonusDs1ProfileDs1LineCoding    INTEGER,
        sonusDs1ProfileDs1SignalMode    INTEGER,
        sonusDs1ProfileDs1Fdl           INTEGER,
        sonusDs1ProfileDs0IdleCode      INTEGER,
        sonusDs1ProfileAvailChannels    OCTET STRING,
        sonusDs1ProfileDs1LineBOState   SonusAdminState,
        sonusDs1ProfileDs1LineTypeState SonusAdminState,
        sonusDs1ProfileDs1LineCodingState SonusAdminState,
        sonusDs1ProfileDs1SignalModeState SonusAdminState,
        sonusDs1ProfileDs1FdlState      SonusAdminState,
        sonusDs1ProfileDs0IdleCodeState SonusAdminState,
        sonusDs1ProfileAvailChannelsState SonusAdminState,
        sonusDs1ProfileType             INTEGER,
        sonusDs1ProfileESThreshold      INTEGER,
        sonusDs1ProfileSESThreshold     INTEGER,
        sonusDs1ProfileCSSThreshold     INTEGER,
        sonusDs1ProfileDayESThreshold   INTEGER,
        sonusDs1ProfileDaySESThreshold  INTEGER,
        sonusDs1ProfileDayCSSThreshold  INTEGER,
        sonusDs1ProfileFarESThreshold   INTEGER,
        sonusDs1ProfileFarSESThreshold  INTEGER,
        sonusDs1ProfileFarDayESThreshold INTEGER,
        sonusDs1ProfileFarDaySESThreshold INTEGER,
        sonusDs1ProfilePCVThreshold     INTEGER,
        sonusDs1ProfileLCVThreshold     INTEGER,
        sonusDs1ProfileUASThreshold     INTEGER,
        sonusDs1ProfileFarPCVThreshold  INTEGER,
        sonusDs1ProfileFarLCVThreshold  INTEGER,
        sonusDs1ProfileFarUASThreshold  INTEGER,
        sonusDs1ProfileDayPCVThreshold  INTEGER,
        sonusDs1ProfileDayLCVThreshold  INTEGER,
        sonusDs1ProfileDayUASThreshold  INTEGER,
        sonusDs1ProfileFarDayPCVThreshold INTEGER,
        sonusDs1ProfileFarDayLCVThreshold INTEGER,
        sonusDs1ProfileFarDayUASThreshold INTEGER,
        sonusDs1ProfileESThresholdState SonusAdminState,
        sonusDs1ProfileSESThresholdState SonusAdminState,
        sonusDs1ProfileCSSThresholdState SonusAdminState,
        sonusDs1ProfileDayESThresholdState  SonusAdminState,
        sonusDs1ProfileDaySESThresholdState   SonusAdminState,
        sonusDs1ProfileDayCSSThresholdState   SonusAdminState,
        sonusDs1ProfileFarESThresholdState  SonusAdminState,
        sonusDs1ProfileFarSESThresholdState   SonusAdminState,
        sonusDs1ProfileFarDayESThresholdState     SonusAdminState,
        sonusDs1ProfileFarDaySESThresholdState      SonusAdminState,
        sonusDs1ProfilePCVThresholdState SonusAdminState,
        sonusDs1ProfileLCVThresholdState SonusAdminState,
        sonusDs1ProfileUASThresholdState SonusAdminState,
        sonusDs1ProfileFarPCVThresholdState   SonusAdminState,
        sonusDs1ProfileFarLCVThresholdState   SonusAdminState,
        sonusDs1ProfileFarUASThresholdState   SonusAdminState,
        sonusDs1ProfileDayPCVThresholdState   SonusAdminState,
        sonusDs1ProfileDayLCVThresholdState   SonusAdminState,
        sonusDs1ProfileDayUASThresholdState   SonusAdminState,
        sonusDs1ProfileFarDayPCVThresholdState      SonusAdminState,
        sonusDs1ProfileFarDayLCVThresholdState      SonusAdminState,
        sonusDs1ProfileFarDayUASThresholdState      SonusAdminState,
        sonusDs1ProfileLESThreshold     INTEGER,
        sonusDs1ProfileLSESThreshold    INTEGER,
        sonusDs1ProfileDayLESThreshold  INTEGER,
        sonusDs1ProfileDayLSESThreshold INTEGER,
        sonusDs1ProfileSASThreshold     INTEGER,
        sonusDs1ProfileDaySASThreshold  INTEGER,
        sonusDs1ProfileSEFSThreshold    INTEGER,
        sonusDs1ProfileDaySEFSThreshold INTEGER,
        sonusDs1ProfileLESThresholdState SonusAdminState,
        sonusDs1ProfileLSESThresholdState SonusAdminState,
        sonusDs1ProfileDayLESThresholdState   SonusAdminState,
        sonusDs1ProfileDayLSESThresholdState    SonusAdminState,
        sonusDs1ProfileSASThresholdState SonusAdminState,
        sonusDs1ProfileDaySASThresholdState   SonusAdminState,
        sonusDs1ProfileSEFSThresholdState SonusAdminState,
        sonusDs1ProfileDaySEFSThresholdState    SonusAdminState,
        sonusDs1ProfileLCVTcaFilter     SonusAdminState,
        sonusDs1ProfileLESTcaFilter     SonusAdminState,
        sonusDs1ProfileLSESTcaFilter    SonusAdminState,
        sonusDs1ProfilePCVTcaFilter     SonusAdminState,
        sonusDs1ProfilePESTcaFilter     SonusAdminState,
        sonusDs1ProfilePSESTcaFilter    SonusAdminState,
        sonusDs1ProfileSASTcaFilter     SonusAdminState,
        sonusDs1ProfileCSSTcaFilter     SonusAdminState,
        sonusDs1ProfileSEFSTcaFilter    SonusAdminState,
        sonusDs1ProfileUASTcaFilter     SonusAdminState,
        sonusDs1ProfileLCVTcaFilterState SonusAdminState,
        sonusDs1ProfileLESTcaFilterState SonusAdminState,
        sonusDs1ProfileLSESTcaFilterState SonusAdminState,
        sonusDs1ProfilePCVTcaFilterState SonusAdminState,
        sonusDs1ProfilePESTcaFilterState SonusAdminState,
        sonusDs1ProfilePSESTcaFilterState SonusAdminState,
        sonusDs1ProfileSASTcaFilterState SonusAdminState,
        sonusDs1ProfileCSSTcaFilterState SonusAdminState,
        sonusDs1ProfileSEFSTcaFilterState SonusAdminState,
        sonusDs1ProfileUASTcaFilterState SonusAdminState,
        sonusDs1ProfileQ50BssSignalBits INTEGER,
        sonusDs1ProfileQ50MaintReqResp  INTEGER,
        sonusDs1ProfileQ50DcmeAckTimeout INTEGER,
        sonusDs1ProfileQ50BssSignalBitsState    SonusAdminState,
        sonusDs1ProfileQ50MaintReqRespState   SonusAdminState,
        sonusDs1ProfileQ50DcmeAckTimeoutState     SonusAdminState
    }

sonusDs1ProfileRowStatus OBJECT-TYPE
    SYNTAX          RowStatus
    ACCESS          read-write
    STATUS          mandatory
    DESCRIPTION     
            "Profile: Row Status Needed for SNMP"
    ::= { sonusDs1ProfileEntry 1 }

sonusDs1ProfileName OBJECT-TYPE
    SYNTAX          SonusName
    ACCESS          read-write
    STATUS          mandatory
    DESCRIPTION     
            "Name of this Profile"
    ::= { sonusDs1ProfileEntry 2 }

sonusDs1ProfileIndex OBJECT-TYPE
    SYNTAX          INTEGER
    ACCESS          read-only
    STATUS          mandatory
    DESCRIPTION     
            "Index into the profile table"
    ::= { sonusDs1ProfileEntry 3 }

sonusDs1ProfileState OBJECT-TYPE
    SYNTAX          SonusAdminState
    ACCESS          read-write
    STATUS          mandatory
    DESCRIPTION     
            "Profile: State"
    DEFVAL          { disabled }
    ::= { sonusDs1ProfileEntry 4 }

sonusDs1ProfileDs1LineBO OBJECT-TYPE
    SYNTAX          INTEGER { buildOut0to110(1), buildOut110to220(2), 
                        buildOut220to330(3), buildOut330to440(4), 
                        buildOut440to550(5), buildOut550to660(6), 
                        buildOut120Ohms(7), buildOut75Ohms(8), 
                        notConfigured(9) }
    ACCESS          read-write
    STATUS          mandatory
    DESCRIPTION     
            "Profile: DS1 Line build out"
    DEFVAL          { buildOut110to220 }
    ::= { sonusDs1ProfileEntry 5 }

sonusDs1ProfileDs1LineType OBJECT-TYPE
    SYNTAX          INTEGER { esf(2), d4(3), e1(4), e1crc(5) }
    ACCESS          read-write
    STATUS          mandatory
    DESCRIPTION     
            "Profile: T1/E1 Line type"
    DEFVAL          { esf }
    ::= { sonusDs1ProfileEntry 6 }

sonusDs1ProfileDs1LineCoding OBJECT-TYPE
    SYNTAX          INTEGER { b8zs(2), hdb3(3), ami(5) }
    ACCESS          read-write
    STATUS          mandatory
    DESCRIPTION     
            "Profile: T1/E1 Line Coding, B8ZS, AMI, HDB3"
    DEFVAL          { b8zs }
    ::= { sonusDs1ProfileEntry 7 }

sonusDs1ProfileDs1SignalMode OBJECT-TYPE
    SYNTAX          INTEGER { none(1), robbedBit(2), bitOriented(3), 
                        other(5) }
    ACCESS          read-write
    STATUS          mandatory
    DESCRIPTION     
            "Profile: T1/E1 Signalling, Bit Oriented, Robbed Bit, other (Q.50) or None"
    DEFVAL          { none }
    ::= { sonusDs1ProfileEntry 8 }

sonusDs1ProfileDs1Fdl OBJECT-TYPE
    SYNTAX          INTEGER { ansi(2), none(8) }
    ACCESS          read-write
    STATUS          obsolete
    DESCRIPTION     
            "Profile: T1 Facilities Data Link type. This object was obsoleted in release 5.1."
    DEFVAL          { ansi }
    ::= { sonusDs1ProfileEntry 9 }

sonusDs1ProfileDs0IdleCode OBJECT-TYPE
    SYNTAX          INTEGER (0..255)
    ACCESS          read-write
    STATUS          mandatory
    DESCRIPTION     
            "Profile: Idle code to be used on all channels in this T1/E1 span"
    DEFVAL          { 127 }
    ::= { sonusDs1ProfileEntry 10 }

sonusDs1ProfileAvailChannels OBJECT-TYPE
    SYNTAX          OCTET STRING
--                       { channel1(0), channel2(1), channel3(2), 
--                         channel4(3), channel5(4), channel6(5), 
--                         channel7(6), channel8(7), channel9(8), 
--                         channel10(9), channel11(10), channel12(11), 
--                         channel13(12), channel14(13), channel15(14), 
--                         channel16(15), channel17(16), channel18(17), 
--                         channel19(18), channel20(19), channel21(20), 
--                         channel22(21), channel23(22), channel24(23), 
--                         channel25(24), channel26(25), channel27(26), 
--                         channel28(27), channel29(28), channel30(29), 
--                         channel31(30) }
    ACCESS          read-write
    STATUS          mandatory
    DESCRIPTION     
            "Bitstring map of channels that are available on this T1/E1."
    ::= { sonusDs1ProfileEntry 11 }

sonusDs1ProfileDs1LineBOState OBJECT-TYPE
    SYNTAX          SonusAdminState
    ACCESS          read-write
    STATUS          mandatory
    DESCRIPTION     
            "Profile: Line Build Out State, used by profile code"
    DEFVAL          { enabled }
    ::= { sonusDs1ProfileEntry 12 }

sonusDs1ProfileDs1LineTypeState OBJECT-TYPE
    SYNTAX          SonusAdminState
    ACCESS          read-write
    STATUS          mandatory
    DESCRIPTION     
            "Profile: T1/E1 Line type State, used by profile code"
    DEFVAL          { enabled }
    ::= { sonusDs1ProfileEntry 13 }

sonusDs1ProfileDs1LineCodingState OBJECT-TYPE
    SYNTAX          SonusAdminState
    ACCESS          read-write
    STATUS          mandatory
    DESCRIPTION     
            "Profile: T1/E1 Line coding State, used by profile code"
    DEFVAL          { enabled }
    ::= { sonusDs1ProfileEntry 14 }

sonusDs1ProfileDs1SignalModeState OBJECT-TYPE
    SYNTAX          SonusAdminState
    ACCESS          read-write
    STATUS          mandatory
    DESCRIPTION     
            "Profile: T1/E1 Signal Mode state, used by profile code"
    DEFVAL          { enabled }
    ::= { sonusDs1ProfileEntry 15 }

sonusDs1ProfileDs1FdlState OBJECT-TYPE
    SYNTAX          SonusAdminState
    ACCESS          read-write
    STATUS          obsolete
    DESCRIPTION     
            "Profile: T1/E1 FDL State, used by profile code.
             This object was obsoleted in release 5.1."
    DEFVAL          { enabled }
    ::= { sonusDs1ProfileEntry 16 }

sonusDs1ProfileDs0IdleCodeState OBJECT-TYPE
    SYNTAX          SonusAdminState
    ACCESS          read-write
    STATUS          mandatory
    DESCRIPTION     
            "Profile: Channel Idle Code State, used by profile"
    DEFVAL          { enabled }
    ::= { sonusDs1ProfileEntry 17 }

sonusDs1ProfileAvailChannelsState OBJECT-TYPE
    SYNTAX          SonusAdminState
    ACCESS          read-write
    STATUS          mandatory
    DESCRIPTION     
            "Profile: Available channel state, disabled/enabled"
    DEFVAL          { enabled }
    ::= { sonusDs1ProfileEntry 18 }

sonusDs1ProfileType OBJECT-TYPE
    SYNTAX          INTEGER { t1(1), e1(2) }
    ACCESS          read-write
    STATUS          mandatory
    DESCRIPTION     
            "Type of DSx1. Indicates whether this span is a T1 span or E1 span."
    DEFVAL          { t1 }
    ::= { sonusDs1ProfileEntry 19 }

sonusDs1ProfileESThreshold OBJECT-TYPE
    SYNTAX          INTEGER (1..900)
    ACCESS          read-write
    STATUS          obsolete
    DESCRIPTION     
            "Errored Seconds threshold value for 15 minute interval. This is for near end.
             This object was obsoleted in release 6.1."
    DEFVAL          { 65 }
    ::= { sonusDs1ProfileEntry 20 }

sonusDs1ProfileSESThreshold OBJECT-TYPE
    SYNTAX          INTEGER (1..900)
    ACCESS          read-write
    STATUS          obsolete
    DESCRIPTION     
            "Severely Errored Seconds threshold value for 15 minute interval. 
             This is for near end.
             This object was obsoleted in release 6.1."
    DEFVAL          { 10 }
    ::= { sonusDs1ProfileEntry 21 }

sonusDs1ProfileCSSThreshold OBJECT-TYPE
    SYNTAX          INTEGER (1..900)
    ACCESS          read-write
    STATUS          obsolete
    DESCRIPTION     
            "Controlled Slip Seconds threshold value for 15 minute interval. 
             This is for near end.
             This object was obsoleted in release 6.1."
    DEFVAL          { 1 }
    ::= { sonusDs1ProfileEntry 22 }

sonusDs1ProfileDayESThreshold OBJECT-TYPE
    SYNTAX          INTEGER (1..65535)
    ACCESS          read-write
    STATUS          obsolete
    DESCRIPTION     
            "Errored Seconds threshold value for a day. This is for near end.
             This object was obsoleted in release 6.1."
    DEFVAL          { 648 }
    ::= { sonusDs1ProfileEntry 23 }

sonusDs1ProfileDaySESThreshold OBJECT-TYPE
    SYNTAX          INTEGER (1..65535)
    ACCESS          read-write
    STATUS          obsolete
    DESCRIPTION     
            "Severely Errored Seconds threshold value for a day. This is for near end.
             This object was obsoleted in release 6.1."
    DEFVAL          { 100 }
    ::= { sonusDs1ProfileEntry 24 }

sonusDs1ProfileDayCSSThreshold OBJECT-TYPE
    SYNTAX          INTEGER (1..65535)
    ACCESS          read-write
    STATUS          obsolete
    DESCRIPTION     
            "Controlled Slip Seconds threshold value for a day. This is for near end.
             This object was obsoleted in release 6.1."
    DEFVAL          { 4 }
    ::= { sonusDs1ProfileEntry 25 }

sonusDs1ProfileFarESThreshold OBJECT-TYPE
    SYNTAX          INTEGER (1..900)
    ACCESS          read-write
    STATUS          obsolete
    DESCRIPTION     
            "Errored Seconds threshold value for 15 minute interval. This is for far end.
             This object was obsoleted in release 5.1."
    DEFVAL          { 65 }
    ::= { sonusDs1ProfileEntry 26 }

sonusDs1ProfileFarSESThreshold OBJECT-TYPE
    SYNTAX          INTEGER (1..900)
    ACCESS          read-write
    STATUS          obsolete
    DESCRIPTION     
            "Severely Errored Seconds threshold value for 15 minute interval. 
             This is for far end. This object was obsoleted in release 5.1."
    DEFVAL          { 10 }
    ::= { sonusDs1ProfileEntry 27 }

sonusDs1ProfileFarDayESThreshold OBJECT-TYPE
    SYNTAX          INTEGER (1..65535)
    ACCESS          read-write
    STATUS          obsolete
    DESCRIPTION     
            "Errored Seconds threshold value for a day. This is for far end.
             This object was obsoleted in release 5.1."
    DEFVAL          { 648 }
    ::= { sonusDs1ProfileEntry 28 }

sonusDs1ProfileFarDaySESThreshold OBJECT-TYPE
    SYNTAX          INTEGER (1..65535)
    ACCESS          read-write
    STATUS          obsolete
    DESCRIPTION     
            "Severely Errored Seconds threshold value for a day. This is for far end.
             This object was obsoleted in release 5.1."
    DEFVAL          { 100 }
    ::= { sonusDs1ProfileEntry 29 }

sonusDs1ProfilePCVThreshold OBJECT-TYPE
    SYNTAX          INTEGER (1..16383)
    ACCESS          read-write
    STATUS          obsolete
    DESCRIPTION     
            "Path Code Violations threshold value for 15 minute interval. This is for near end.
             This object was obsoleted in release 6.1."
    DEFVAL          { 13296 }
    ::= { sonusDs1ProfileEntry 30 }

sonusDs1ProfileLCVThreshold OBJECT-TYPE
    SYNTAX          INTEGER (1..16383)
    ACCESS          read-write
    STATUS          obsolete
    DESCRIPTION     
            "Line Code Violations threshold value for 15 minute interval. This is for near end.
             This object was obsoleted in release 6.1."
    DEFVAL          { 13340 }
    ::= { sonusDs1ProfileEntry 31 }

sonusDs1ProfileUASThreshold OBJECT-TYPE
    SYNTAX          INTEGER (1..900)
    ACCESS          read-write
    STATUS          obsolete
    DESCRIPTION     
            "Unavailable Seconds threshold value for 15 minute interval. This is for near end.
             This object was obsoleted in release 6.1."
    DEFVAL          { 10 }
    ::= { sonusDs1ProfileEntry 32 }

sonusDs1ProfileFarPCVThreshold OBJECT-TYPE
    SYNTAX          INTEGER (1..16383)
    ACCESS          read-write
    STATUS          obsolete
    DESCRIPTION     
            "Path Code Violations threshold value for 15 minute interval. This is for far end.
             This object was obsoleted in release 5.1."
    DEFVAL          { 72 }
    ::= { sonusDs1ProfileEntry 33 }

sonusDs1ProfileFarLCVThreshold OBJECT-TYPE
    SYNTAX          INTEGER (1..16383)
    ACCESS          read-write
    STATUS          obsolete
    DESCRIPTION     
            "Line Code Violations threshold value for 15 minute interval. This is for far end.
             This object was obsoleted in release 5.1."
    DEFVAL          { 72 }
    ::= { sonusDs1ProfileEntry 34 }

sonusDs1ProfileFarUASThreshold OBJECT-TYPE
    SYNTAX          INTEGER (1..900)
    ACCESS          read-write
    STATUS          obsolete
    DESCRIPTION     
            "Unavailable Seconds threshold value for 15 minute interval. This is for far end.
             This object was obsoleted in release 5.1."
    DEFVAL          { 10 }
    ::= { sonusDs1ProfileEntry 35 }

sonusDs1ProfileDayPCVThreshold OBJECT-TYPE
    SYNTAX          INTEGER (1..1048575)
    ACCESS          read-write
    STATUS          obsolete
    DESCRIPTION     
            "Path Code Violations threshold value for a day. This is for near end.
             This object was obsoleted in release 6.1."
    DEFVAL          { 132960 }
    ::= { sonusDs1ProfileEntry 36 }

sonusDs1ProfileDayLCVThreshold OBJECT-TYPE
    SYNTAX          INTEGER (1..1048575)
    ACCESS          read-write
    STATUS          obsolete
    DESCRIPTION     
            "Line Code Violations threshold value for a day. This is for near end.
             This object was obsoleted in release 6.1."
    DEFVAL          { 133400 }
    ::= { sonusDs1ProfileEntry 37 }

sonusDs1ProfileDayUASThreshold OBJECT-TYPE
    SYNTAX          INTEGER (1..65535)
    ACCESS          read-write
    STATUS          obsolete
    DESCRIPTION     
            "Unavailable Seconds threshold value for a day. This is for near end.
             This object was obsoleted in release 6.1."
    DEFVAL          { 100 }
    ::= { sonusDs1ProfileEntry 38 }

sonusDs1ProfileFarDayPCVThreshold OBJECT-TYPE
    SYNTAX          INTEGER (1..1048575)
    ACCESS          read-write
    STATUS          obsolete
    DESCRIPTION     
            "Path Code Violations threshold value for a day. This is for far end.
             This object was obsoleted in release 5.1."
    DEFVAL          { 691 }
    ::= { sonusDs1ProfileEntry 39 }

sonusDs1ProfileFarDayLCVThreshold OBJECT-TYPE
    SYNTAX          INTEGER (1..1048575)
    ACCESS          read-write
    STATUS          obsolete
    DESCRIPTION     
            "Line Code Violations threshold value for a day. This is for far end.
             This object was obsoleted in release 5.1."
    DEFVAL          { 691 }
    ::= { sonusDs1ProfileEntry 40 }

sonusDs1ProfileFarDayUASThreshold OBJECT-TYPE
    SYNTAX          INTEGER (1..65535)
    ACCESS          read-write
    STATUS          obsolete
    DESCRIPTION     
            "Unavailable Seconds threshold value for a day. This is for far end.
             This object was obsoleted in release 5.1."
    DEFVAL          { 100 }
    ::= { sonusDs1ProfileEntry 41 }

sonusDs1ProfileESThresholdState OBJECT-TYPE
    SYNTAX          SonusAdminState
    ACCESS          read-write
    STATUS          obsolete
    DESCRIPTION     
            "Errored Seconds threshold profile state.
             This object was obsoleted in release 6.1."
    DEFVAL          { enabled }
    ::= { sonusDs1ProfileEntry 42 }

sonusDs1ProfileSESThresholdState OBJECT-TYPE
    SYNTAX          SonusAdminState
    ACCESS          read-write
    STATUS          obsolete
    DESCRIPTION     
            "Severely Errored Seconds profile state.
             This object was obsoleted in release 6.1."
    DEFVAL          { enabled }
    ::= { sonusDs1ProfileEntry 43 }

sonusDs1ProfileCSSThresholdState OBJECT-TYPE
    SYNTAX          SonusAdminState
    ACCESS          read-write
    STATUS          obsolete
    DESCRIPTION     
            "Controlled Slip Seconds profile state.
             This object was obsoleted in release 6.1."
    DEFVAL          { enabled }
    ::= { sonusDs1ProfileEntry 44 }

sonusDs1ProfileDayESThresholdState OBJECT-TYPE
    SYNTAX          SonusAdminState
    ACCESS          read-write
    STATUS          obsolete
    DESCRIPTION     
            "Errored Seconds threshold profile state.
             This object was obsoleted in release 6.1."
    DEFVAL          { enabled }
    ::= { sonusDs1ProfileEntry 45 }

sonusDs1ProfileDaySESThresholdState OBJECT-TYPE
    SYNTAX          SonusAdminState
    ACCESS          read-write
    STATUS          obsolete
    DESCRIPTION     
            "Severely Errored Seconds threshold profile state.
             This object was obsoleted in release 6.1."
    DEFVAL          { enabled }
    ::= { sonusDs1ProfileEntry 46 }

sonusDs1ProfileDayCSSThresholdState OBJECT-TYPE
    SYNTAX          SonusAdminState
    ACCESS          read-write
    STATUS          obsolete
    DESCRIPTION     
            "Controlled Slip Seconds threshold profile state.
             This object was obsoleted in release 6.1."
    DEFVAL          { enabled }
    ::= { sonusDs1ProfileEntry 47 }

sonusDs1ProfileFarESThresholdState OBJECT-TYPE
    SYNTAX          SonusAdminState
    ACCESS          read-write
    STATUS          obsolete
    DESCRIPTION     
            "Errored Seconds threshold profile state.
             This object was obsoleted in release 5.1."
    DEFVAL          { enabled }
    ::= { sonusDs1ProfileEntry 48 }

sonusDs1ProfileFarSESThresholdState OBJECT-TYPE
    SYNTAX          SonusAdminState
    ACCESS          read-write
    STATUS          obsolete
    DESCRIPTION     
            "Severely Errored Seconds threshold profile state.
             This object was obsoleted in release 5.1."
    DEFVAL          { enabled }
    ::= { sonusDs1ProfileEntry 49 }

sonusDs1ProfileFarDayESThresholdState OBJECT-TYPE
    SYNTAX          SonusAdminState
    ACCESS          read-write
    STATUS          obsolete
    DESCRIPTION     
            "Errored Seconds threshold profile state.
             This object was obsoleted in release 5.1."
    DEFVAL          { enabled }
    ::= { sonusDs1ProfileEntry 50 }

sonusDs1ProfileFarDaySESThresholdState OBJECT-TYPE
    SYNTAX          SonusAdminState
    ACCESS          read-write
    STATUS          obsolete
    DESCRIPTION     
            "Severely Errored Seconds threshold profile state.
             This object was obsoleted in release 5.1."
    DEFVAL          { enabled }
    ::= { sonusDs1ProfileEntry 51 }

sonusDs1ProfilePCVThresholdState OBJECT-TYPE
    SYNTAX          SonusAdminState
    ACCESS          read-write
    STATUS          obsolete
    DESCRIPTION     
            "Path Code Violations threshold profile state.
             This object was obsoleted in release 6.1."
    DEFVAL          { enabled }
    ::= { sonusDs1ProfileEntry 52 }

sonusDs1ProfileLCVThresholdState OBJECT-TYPE
    SYNTAX          SonusAdminState
    ACCESS          read-write
    STATUS          obsolete
    DESCRIPTION     
            "Line Code Violations threshold profile state.
             This object was obsoleted in release 6.1."
    DEFVAL          { enabled }
    ::= { sonusDs1ProfileEntry 53 }

sonusDs1ProfileUASThresholdState OBJECT-TYPE
    SYNTAX          SonusAdminState
    ACCESS          read-write
    STATUS          obsolete
    DESCRIPTION     
            "Unavailable Seconds threshold profile state.
             This object was obsoleted in release 6.1."
    DEFVAL          { enabled }
    ::= { sonusDs1ProfileEntry 54 }

sonusDs1ProfileFarPCVThresholdState OBJECT-TYPE
    SYNTAX          SonusAdminState
    ACCESS          read-write
    STATUS          obsolete
    DESCRIPTION     
            "Path Code Violations threshold profile state.
             This object was obsoleted in release 5.1."
    DEFVAL          { enabled }
    ::= { sonusDs1ProfileEntry 55 }

sonusDs1ProfileFarLCVThresholdState OBJECT-TYPE
    SYNTAX          SonusAdminState
    ACCESS          read-write
    STATUS          obsolete
    DESCRIPTION     
            "Line Code Violations threshold profile state.
             This object was obsoleted in release 5.1."
    DEFVAL          { enabled }
    ::= { sonusDs1ProfileEntry 56 }

sonusDs1ProfileFarUASThresholdState OBJECT-TYPE
    SYNTAX          SonusAdminState
    ACCESS          read-write
    STATUS          obsolete
    DESCRIPTION     
            "Unavailable Seconds threshold profile state.
             This object was obsoleted in release 5.1."
    DEFVAL          { enabled }
    ::= { sonusDs1ProfileEntry 57 }

sonusDs1ProfileDayPCVThresholdState OBJECT-TYPE
    SYNTAX          SonusAdminState
    ACCESS          read-write
    STATUS          obsolete
    DESCRIPTION     
            "Path Code Violations threshold profile state.
             This object was obsoleted in release 6.1."
    DEFVAL          { enabled }
    ::= { sonusDs1ProfileEntry 58 }

sonusDs1ProfileDayLCVThresholdState OBJECT-TYPE
    SYNTAX          SonusAdminState
    ACCESS          read-write
    STATUS          obsolete
    DESCRIPTION     
            "Line Code Violations threshold profile state.
             This object was obsoleted in release 6.1."
    DEFVAL          { enabled }
    ::= { sonusDs1ProfileEntry 59 }

sonusDs1ProfileDayUASThresholdState OBJECT-TYPE
    SYNTAX          SonusAdminState
    ACCESS          read-write
    STATUS          obsolete
    DESCRIPTION     
            "Unavailable Seconds threshold profile state.
             This object was obsoleted in release 6.1."
    DEFVAL          { enabled }
    ::= { sonusDs1ProfileEntry 60 }

sonusDs1ProfileFarDayPCVThresholdState OBJECT-TYPE
    SYNTAX          SonusAdminState
    ACCESS          read-write
    STATUS          obsolete
    DESCRIPTION     
            "Path Code Violations threshold profile state.
             This object was obsoleted in release 5.1."
    DEFVAL          { enabled }
    ::= { sonusDs1ProfileEntry 61 }

sonusDs1ProfileFarDayLCVThresholdState OBJECT-TYPE
    SYNTAX          SonusAdminState
    ACCESS          read-write
    STATUS          obsolete
    DESCRIPTION     
            "Line Code Violations threshold state.
             This object was obsoleted in release 5.1."
    DEFVAL          { enabled }
    ::= { sonusDs1ProfileEntry 62 }

sonusDs1ProfileFarDayUASThresholdState OBJECT-TYPE
    SYNTAX          SonusAdminState
    ACCESS          read-write
    STATUS          obsolete
    DESCRIPTION     
            "Unavailable Seconds threshold profile state.
             This object was obsoleted in release 5.1."
    DEFVAL          { enabled }
    ::= { sonusDs1ProfileEntry 63 }

sonusDs1ProfileLESThreshold OBJECT-TYPE
    SYNTAX          INTEGER (1..900)
    ACCESS          read-write
    STATUS          obsolete
    DESCRIPTION     
            "Line Errored Seconds threshold value. This is for near end.
             This object was obsoleted in release 6.1."
    DEFVAL          { 65 }
    ::= { sonusDs1ProfileEntry 64 }

sonusDs1ProfileLSESThreshold OBJECT-TYPE
    SYNTAX          INTEGER (1..900)
    ACCESS          read-write
    STATUS          obsolete
    DESCRIPTION     
            "Line Severely Errored Seconds threshold value. This is for near end.
             This object was obsoleted in release 6.1."
    DEFVAL          { 10 }
    ::= { sonusDs1ProfileEntry 65 }

sonusDs1ProfileDayLESThreshold OBJECT-TYPE
    SYNTAX          INTEGER (1..65535)
    ACCESS          read-write
    STATUS          obsolete
    DESCRIPTION     
            "Line Errored Seconds threshold value for a day. This is for near end.
             This object was obsoleted in release 6.1."
    DEFVAL          { 648 }
    ::= { sonusDs1ProfileEntry 66 }

sonusDs1ProfileDayLSESThreshold OBJECT-TYPE
    SYNTAX          INTEGER (1..65535)
    ACCESS          read-write
    STATUS          obsolete
    DESCRIPTION     
            "Line Severely Errored Seconds threshold value for a day. This is for near end.
             This object was obsoleted in release 6.1."
    DEFVAL          { 100 }
    ::= { sonusDs1ProfileEntry 67 }

sonusDs1ProfileSASThreshold OBJECT-TYPE
    SYNTAX          INTEGER (1..900)
    ACCESS          read-write
    STATUS          obsolete
    DESCRIPTION     
            "SEF/AIS Seconds threshold value. This is for near end.
             This object was obsoleted in release 6.1."
    DEFVAL          { 2 }
    ::= { sonusDs1ProfileEntry 68 }

sonusDs1ProfileDaySASThreshold OBJECT-TYPE
    SYNTAX          INTEGER (1..65535)
    ACCESS          read-write
    STATUS          obsolete
    DESCRIPTION     
            "SEF/AIS Seconds threshold value for a day. This is for near end.
             This object was obsoleted in release 6.1."
    DEFVAL          { 17 }
    ::= { sonusDs1ProfileEntry 69 }

sonusDs1ProfileSEFSThreshold OBJECT-TYPE
    SYNTAX          INTEGER (1..900)
    ACCESS          read-write
    STATUS          obsolete
    DESCRIPTION     
            "Severely Errored Frame Seconds threshold value. This is for near end.
             This object was obsoleted in release 6.1."
    DEFVAL          { 2 }
    ::= { sonusDs1ProfileEntry 70 }

sonusDs1ProfileDaySEFSThreshold OBJECT-TYPE
    SYNTAX          INTEGER (1..65535)
    ACCESS          read-write
    STATUS          obsolete
    DESCRIPTION     
            "Severely Errored Frame Seconds threshold value for a day. This is for near end.
             This object was obsoleted in release 6.1."
    DEFVAL          { 17 }
    ::= { sonusDs1ProfileEntry 71 }

sonusDs1ProfileLESThresholdState OBJECT-TYPE
    SYNTAX          SonusAdminState
    ACCESS          read-write
    STATUS          obsolete
    DESCRIPTION     
            "Line Errored Seconds threshold profile state.
             This object was obsoleted in release 6.1."
    DEFVAL          { enabled }
    ::= { sonusDs1ProfileEntry 72 }

sonusDs1ProfileLSESThresholdState OBJECT-TYPE
    SYNTAX          SonusAdminState
    ACCESS          read-write
    STATUS          obsolete
    DESCRIPTION     
            "Line Severely Errored Seconds threshold profile state.
             This object was obsoleted in release 6.1."
    DEFVAL          { enabled }
    ::= { sonusDs1ProfileEntry 73 }

sonusDs1ProfileDayLESThresholdState OBJECT-TYPE
    SYNTAX          SonusAdminState
    ACCESS          read-write
    STATUS          obsolete
    DESCRIPTION     
            "Line Errored Seconds threshold profile state.
             This object was obsoleted in release 6.1."
    DEFVAL          { enabled }
    ::= { sonusDs1ProfileEntry 74 }

sonusDs1ProfileDayLSESThresholdState OBJECT-TYPE
    SYNTAX          SonusAdminState
    ACCESS          read-write
    STATUS          obsolete
    DESCRIPTION     
            "Line Severely Errored Seconds threshold profile state.
             This object was obsoleted in release 6.1."
    DEFVAL          { enabled }
    ::= { sonusDs1ProfileEntry 75 }

sonusDs1ProfileSASThresholdState OBJECT-TYPE
    SYNTAX          SonusAdminState
    ACCESS          read-write
    STATUS          obsolete
    DESCRIPTION     
            "SEF/AIS Seconds threshold profile state.
             This object was obsoleted in release 6.1."
    DEFVAL          { enabled }
    ::= { sonusDs1ProfileEntry 76 }

sonusDs1ProfileDaySASThresholdState OBJECT-TYPE
    SYNTAX          SonusAdminState
    ACCESS          read-write
    STATUS          obsolete
    DESCRIPTION     
            "SEF/AIS Seconds threshold profile state.
             This object was obsoleted in release 6.1."
    DEFVAL          { enabled }
    ::= { sonusDs1ProfileEntry 77 }

sonusDs1ProfileSEFSThresholdState OBJECT-TYPE
    SYNTAX          SonusAdminState
    ACCESS          read-write
    STATUS          obsolete
    DESCRIPTION     
            "Severely Errored Frame Seconds threshold profile state.
             This object was obsoleted in release 6.1."
    DEFVAL          { enabled }
    ::= { sonusDs1ProfileEntry 78 }

sonusDs1ProfileDaySEFSThresholdState OBJECT-TYPE
    SYNTAX          SonusAdminState
    ACCESS          read-write
    STATUS          obsolete
    DESCRIPTION     
            "Severely Errored Frame Seconds threshold profile state.
             This object was obsoleted in release 6.1."
    DEFVAL          { enabled }
    ::= { sonusDs1ProfileEntry 79 }

sonusDs1ProfileLCVTcaFilter OBJECT-TYPE
    SYNTAX          SonusAdminState
    ACCESS          read-write
    STATUS          obsolete
    DESCRIPTION     
            "Controls whether a threshold Crossing Alert (TCA) is reported (via
             an event log and trap). Setting this object to Enabled will prevent
             the TCA from being reported (i.e will Filter the TCA report).
             This object was obsoleted in release 6.1."
    DEFVAL          { disabled }
    ::= { sonusDs1ProfileEntry 80 }

sonusDs1ProfileLESTcaFilter OBJECT-TYPE
    SYNTAX          SonusAdminState
    ACCESS          read-write
    STATUS          obsolete
    DESCRIPTION     
            "Controls whether a threshold Crossing Alert (TCA) is reported (via
             an event log and trap). Setting this object to Enabled will prevent
             the TCA from being reported (i.e will Filter the TCA report).
             This object was obsoleted in release 6.1."
    DEFVAL          { disabled }
    ::= { sonusDs1ProfileEntry 81 }

sonusDs1ProfileLSESTcaFilter OBJECT-TYPE
    SYNTAX          SonusAdminState
    ACCESS          read-write
    STATUS          obsolete
    DESCRIPTION     
            "Controls whether a threshold Crossing Alert (TCA) is reported (via
             an event log and trap). Setting this object to Enabled will prevent
             the TCA from being reported (i.e will Filter the TCA report).
             This object was obsoleted in release 6.1."
    DEFVAL          { disabled }
    ::= { sonusDs1ProfileEntry 82 }

sonusDs1ProfilePCVTcaFilter OBJECT-TYPE
    SYNTAX          SonusAdminState
    ACCESS          read-write
    STATUS          obsolete
    DESCRIPTION     
            "Controls whether a threshold Crossing Alert (TCA) is reported (via
             an event log and trap). Setting this object to Enabled will prevent
             the TCA from being reported (i.e will Filter the TCA report).
             This object was obsoleted in release 6.1."
    DEFVAL          { disabled }
    ::= { sonusDs1ProfileEntry 83 }

sonusDs1ProfilePESTcaFilter OBJECT-TYPE
    SYNTAX          SonusAdminState
    ACCESS          read-write
    STATUS          obsolete
    DESCRIPTION     
            "Controls whether a threshold Crossing Alert (TCA) is reported (via
             an event log and trap). Setting this object to Enabled will prevent
             the TCA from being reported (i.e will Filter the TCA report).
             This object was obsoleted in release 6.1."
    DEFVAL          { disabled }
    ::= { sonusDs1ProfileEntry 84 }

sonusDs1ProfilePSESTcaFilter OBJECT-TYPE
    SYNTAX          SonusAdminState
    ACCESS          read-write
    STATUS          obsolete
    DESCRIPTION     
            "Controls whether a threshold Crossing Alert (TCA) is reported (via
             an event log and trap). Setting this object to Enabled will prevent
             the TCA from being reported (i.e will Filter the TCA report).
             This object was obsoleted in release 6.1."
    DEFVAL          { disabled }
    ::= { sonusDs1ProfileEntry 85 }

sonusDs1ProfileSASTcaFilter OBJECT-TYPE
    SYNTAX          SonusAdminState
    ACCESS          read-write
    STATUS          obsolete
    DESCRIPTION     
            "Controls whether a threshold Crossing Alert (TCA) is reported (via
             an event log and trap). Setting this object to Enabled will prevent
             the TCA from being reported (i.e will Filter the TCA report).
             This object was obsoleted in release 6.1."
    DEFVAL          { disabled }
    ::= { sonusDs1ProfileEntry 86 }

sonusDs1ProfileCSSTcaFilter OBJECT-TYPE
    SYNTAX          SonusAdminState
    ACCESS          read-write
    STATUS          obsolete
    DESCRIPTION     
            "Controls whether a threshold Crossing Alert (TCA) is reported (via
             an event log and trap). Setting this object to Enabled will prevent
             the TCA from being reported (i.e will Filter the TCA report).
             This object was obsoleted in release 6.1."
    DEFVAL          { disabled }
    ::= { sonusDs1ProfileEntry 87 }

sonusDs1ProfileSEFSTcaFilter OBJECT-TYPE
    SYNTAX          SonusAdminState
    ACCESS          read-write
    STATUS          obsolete
    DESCRIPTION     
            "Controls whether a threshold Crossing Alert (TCA) is reported (via
             an event log and trap). Setting this object to Enabled will prevent
             the TCA from being reported (i.e will Filter the TCA report).
             This object was obsoleted in release 6.1."
    DEFVAL          { disabled }
    ::= { sonusDs1ProfileEntry 88 }

sonusDs1ProfileUASTcaFilter OBJECT-TYPE
    SYNTAX          SonusAdminState
    ACCESS          read-write
    STATUS          obsolete
    DESCRIPTION     
            "Controls whether a threshold Crossing Alert (TCA) is reported (via
             an event log and trap). Setting this object to Enabled will prevent
             the TCA from being reported (i.e will Filter the TCA report).
             This object was obsoleted in release 6.1."
    DEFVAL          { disabled }
    ::= { sonusDs1ProfileEntry 89 }

sonusDs1ProfileLCVTcaFilterState OBJECT-TYPE
    SYNTAX          SonusAdminState
    ACCESS          read-write
    STATUS          obsolete
    DESCRIPTION     
            "Profile state.
             This object was obsoleted in release 6.1."
    DEFVAL          { enabled }
    ::= { sonusDs1ProfileEntry 90 }

sonusDs1ProfileLESTcaFilterState OBJECT-TYPE
    SYNTAX          SonusAdminState
    ACCESS          read-write
    STATUS          obsolete
    DESCRIPTION     
            "Profile state.
             This object was obsoleted in release 6.1."
    DEFVAL          { enabled }
    ::= { sonusDs1ProfileEntry 91 }

sonusDs1ProfileLSESTcaFilterState OBJECT-TYPE
    SYNTAX          SonusAdminState
    ACCESS          read-write
    STATUS          obsolete
    DESCRIPTION     
            "Profile state.
             This object was obsoleted in release 6.1."
    DEFVAL          { enabled }
    ::= { sonusDs1ProfileEntry 92 }

sonusDs1ProfilePCVTcaFilterState OBJECT-TYPE
    SYNTAX          SonusAdminState
    ACCESS          read-write
    STATUS          obsolete
    DESCRIPTION     
            "Profile state.
             This object was obsoleted in release 6.1."
    DEFVAL          { enabled }
    ::= { sonusDs1ProfileEntry 93 }

sonusDs1ProfilePESTcaFilterState OBJECT-TYPE
    SYNTAX          SonusAdminState
    ACCESS          read-write
    STATUS          obsolete
    DESCRIPTION     
            "Profile state.
             This object was obsoleted in release 6.1."
    DEFVAL          { enabled }
    ::= { sonusDs1ProfileEntry 94 }

sonusDs1ProfilePSESTcaFilterState OBJECT-TYPE
    SYNTAX          SonusAdminState
    ACCESS          read-write
    STATUS          obsolete
    DESCRIPTION     
            "Profile state.
             This object was obsoleted in release 6.1."
    DEFVAL          { enabled }
    ::= { sonusDs1ProfileEntry 95 }

sonusDs1ProfileSASTcaFilterState OBJECT-TYPE
    SYNTAX          SonusAdminState
    ACCESS          read-write
    STATUS          obsolete
    DESCRIPTION     
            "Profile state.
             This object was obsoleted in release 6.1."
    DEFVAL          { enabled }
    ::= { sonusDs1ProfileEntry 96 }

sonusDs1ProfileCSSTcaFilterState OBJECT-TYPE
    SYNTAX          SonusAdminState
    ACCESS          read-write
    STATUS          obsolete
    DESCRIPTION     
            "Profile state.
             This object was obsoleted in release 6.1."
    DEFVAL          { enabled }
    ::= { sonusDs1ProfileEntry 97 }

sonusDs1ProfileSEFSTcaFilterState OBJECT-TYPE
    SYNTAX          SonusAdminState
    ACCESS          read-write
    STATUS          obsolete
    DESCRIPTION     
            "Profile state.
             This object was obsoleted in release 6.1."
    DEFVAL          { enabled }
    ::= { sonusDs1ProfileEntry 98 }

sonusDs1ProfileUASTcaFilterState OBJECT-TYPE
    SYNTAX          SonusAdminState
    ACCESS          read-write
    STATUS          obsolete
    DESCRIPTION     
            "Profile state.
             This object was obsoleted in release 6.1."
    DEFVAL          { enabled }
    ::= { sonusDs1ProfileEntry 99 }

sonusDs1ProfileQ50BssSignalBits OBJECT-TYPE
    SYNTAX          INTEGER { bitsAB(1), bitsCD(2) }
    ACCESS          read-write
    STATUS          mandatory
    DESCRIPTION     
            " "
    DEFVAL          { bitsAB }
    ::= { sonusDs1ProfileEntry 100 }

sonusDs1ProfileQ50MaintReqResp OBJECT-TYPE
    SYNTAX          INTEGER { accept(1), refuse(2) }
    ACCESS          read-write
    STATUS          mandatory
    DESCRIPTION     
            " "
    DEFVAL          { accept }
    ::= { sonusDs1ProfileEntry 101 }

sonusDs1ProfileQ50DcmeAckTimeout OBJECT-TYPE
    SYNTAX          INTEGER (100..2000)
    ACCESS          read-write
    STATUS          mandatory
    DESCRIPTION     
            " "
    DEFVAL          { 1000 }
    ::= { sonusDs1ProfileEntry 102 }

sonusDs1ProfileQ50BssSignalBitsState OBJECT-TYPE
    SYNTAX          SonusAdminState
    ACCESS          read-write
    STATUS          mandatory
    DESCRIPTION     
            " "
    DEFVAL          { enabled }
    ::= { sonusDs1ProfileEntry 103 }

sonusDs1ProfileQ50MaintReqRespState OBJECT-TYPE
    SYNTAX          SonusAdminState
    ACCESS          read-write
    STATUS          mandatory
    DESCRIPTION     
            " "
    DEFVAL          { enabled }
    ::= { sonusDs1ProfileEntry 104 }

sonusDs1ProfileQ50DcmeAckTimeoutState OBJECT-TYPE
    SYNTAX          SonusAdminState
    ACCESS          read-write
    STATUS          mandatory
    DESCRIPTION     
            " "
    DEFVAL          { enabled }
    ::= { sonusDs1ProfileEntry 105 }

sonusDsx1CurrentTable OBJECT-TYPE
    SYNTAX          SEQUENCE OF SonusDsx1CurrentEntry
    ACCESS          not-accessible
    STATUS          mandatory
    DESCRIPTION     
            "The DS1 current table contains various statistics
             being collected for the near end current 15 minute
             interval."
    ::= { sonusDsx1MIBObjects 5 }

sonusDsx1CurrentEntry OBJECT-TYPE
    SYNTAX          SonusDsx1CurrentEntry
    ACCESS          not-accessible
    STATUS          mandatory
    DESCRIPTION     
            "An entry in the DS1 Current table."
    INDEX           { sonusDsx1CurrentShelfIndex, 
                      sonusDsx1CurrentSlotIndex, 
                      sonusDsx1CurrentPortIndex, 
                      sonusDsx1CurrentDs1Index }
    ::= { sonusDsx1CurrentTable 1 }

SonusDsx1CurrentEntry ::=
    SEQUENCE {
        sonusDsx1CurrentShelfIndex      SonusShelfIndex,
        sonusDsx1CurrentSlotIndex       SonusSlotIndex,
        sonusDsx1CurrentPortIndex       INTEGER,
        sonusDsx1CurrentDs1Index        INTEGER,
        sonusDsx1CurrentElapsedTime     INTEGER,
        sonusDsx1CurrentLCVs            PerfCurrentCount,
        sonusDsx1CurrentLESs            PerfCurrentCount,
        sonusDsx1CurrentLSESs           PerfCurrentCount,
        sonusDsx1CurrentPCVs            PerfCurrentCount,
        sonusDsx1CurrentPESs            PerfCurrentCount,
        sonusDsx1CurrentPSESs           PerfCurrentCount,
        sonusDsx1CurrentSASs            PerfCurrentCount,
        sonusDsx1CurrentCSSs            PerfCurrentCount,
        sonusDsx1CurrentUASs            PerfCurrentCount,
        sonusDsx1CurrentFC              INTEGER,
        sonusDsx1CurrentTcaLCV          TruthValue,
        sonusDsx1CurrentTcaLES          TruthValue,
        sonusDsx1CurrentTcaLSES         TruthValue,
        sonusDsx1CurrentTcaPCV          TruthValue,
        sonusDsx1CurrentTcaPES          TruthValue,
        sonusDsx1CurrentTcaPSES         TruthValue,
        sonusDsx1CurrentTcaSAS          TruthValue,
        sonusDsx1CurrentTcaCSS          TruthValue,
        sonusDsx1CurrentTcaUAS          TruthValue,
        sonusDsx1CurrentMinorTcaLCV     TruthValue,
        sonusDsx1CurrentMinorTcaLES     TruthValue,
        sonusDsx1CurrentMinorTcaLSES    TruthValue,
        sonusDsx1CurrentMinorTcaPCV     TruthValue,
        sonusDsx1CurrentMinorTcaPES     TruthValue,
        sonusDsx1CurrentMinorTcaPSES    TruthValue,
        sonusDsx1CurrentMinorTcaSAS     TruthValue,
        sonusDsx1CurrentMinorTcaCSS     TruthValue,
        sonusDsx1CurrentMinorTcaUAS     TruthValue,
        sonusDsx1CurrentMajorTcaLCV     TruthValue,
        sonusDsx1CurrentMajorTcaLES     TruthValue,
        sonusDsx1CurrentMajorTcaLSES    TruthValue,
        sonusDsx1CurrentMajorTcaPCV     TruthValue,
        sonusDsx1CurrentMajorTcaPES     TruthValue,
        sonusDsx1CurrentMajorTcaPSES    TruthValue,
        sonusDsx1CurrentMajorTcaSAS     TruthValue,
        sonusDsx1CurrentMajorTcaCSS     TruthValue,
        sonusDsx1CurrentMajorTcaUAS     TruthValue,
        sonusDsx1CurrentCriticalTcaLCV  TruthValue,
        sonusDsx1CurrentCriticalTcaLES  TruthValue,
        sonusDsx1CurrentCriticalTcaLSES TruthValue,
        sonusDsx1CurrentCriticalTcaPCV  TruthValue,
        sonusDsx1CurrentCriticalTcaPES  TruthValue,
        sonusDsx1CurrentCriticalTcaPSES TruthValue,
        sonusDsx1CurrentCriticalTcaSAS  TruthValue,
        sonusDsx1CurrentCriticalTcaCSS  TruthValue,
        sonusDsx1CurrentCriticalTcaUAS  TruthValue
    }

sonusDsx1CurrentShelfIndex OBJECT-TYPE
    SYNTAX          SonusShelfIndex
    ACCESS          read-only
    STATUS          mandatory
    DESCRIPTION     
            "Shelf index into this table"
    ::= { sonusDsx1CurrentEntry 1 }

sonusDsx1CurrentSlotIndex OBJECT-TYPE
    SYNTAX          SonusSlotIndex
    ACCESS          read-only
    STATUS          mandatory
    DESCRIPTION     
            "Slot index into this table"
    ::= { sonusDsx1CurrentEntry 2 }

sonusDsx1CurrentPortIndex OBJECT-TYPE
    SYNTAX          INTEGER
    ACCESS          read-only
    STATUS          mandatory
    DESCRIPTION     
            "Port Index into this table"
    ::= { sonusDsx1CurrentEntry 3 }

sonusDsx1CurrentDs1Index OBJECT-TYPE
    SYNTAX          INTEGER
    ACCESS          read-only
    STATUS          mandatory
    DESCRIPTION     
            "Ds1 Index into this table"
    ::= { sonusDsx1CurrentEntry 4 }

sonusDsx1CurrentElapsedTime OBJECT-TYPE
    SYNTAX          INTEGER
    ACCESS          read-only
    STATUS          mandatory
    DESCRIPTION     
            "Elapsed time in the current period"
    ::= { sonusDsx1CurrentEntry 5 }

sonusDsx1CurrentLCVs OBJECT-TYPE
    SYNTAX          PerfCurrentCount
    ACCESS          read-only
    STATUS          mandatory
    DESCRIPTION     
            "The number of Line Code Violations (LCVs)."
    ::= { sonusDsx1CurrentEntry 6 }

sonusDsx1CurrentLESs OBJECT-TYPE
    SYNTAX          PerfCurrentCount
    ACCESS          read-only
    STATUS          mandatory
    DESCRIPTION     
            "The number of Line Errored Seconds."
    ::= { sonusDsx1CurrentEntry 7 }

sonusDsx1CurrentLSESs OBJECT-TYPE
    SYNTAX          PerfCurrentCount
    ACCESS          read-only
    STATUS          mandatory
    DESCRIPTION     
            "The number of Line Severely Errored Seconds."
    ::= { sonusDsx1CurrentEntry 8 }

sonusDsx1CurrentPCVs OBJECT-TYPE
    SYNTAX          PerfCurrentCount
    ACCESS          read-only
    STATUS          mandatory
    DESCRIPTION     
            "The number of Path Coding Violations."
    ::= { sonusDsx1CurrentEntry 9 }

sonusDsx1CurrentPESs OBJECT-TYPE
    SYNTAX          PerfCurrentCount
    ACCESS          read-only
    STATUS          mandatory
    DESCRIPTION     
            "The number of Path Errored Seconds."
    ::= { sonusDsx1CurrentEntry 10 }

sonusDsx1CurrentPSESs OBJECT-TYPE
    SYNTAX          PerfCurrentCount
    ACCESS          read-only
    STATUS          mandatory
    DESCRIPTION     
            "The number of Path Severely Errored Seconds."
    ::= { sonusDsx1CurrentEntry 11 }

sonusDsx1CurrentSASs OBJECT-TYPE
    SYNTAX          PerfCurrentCount
    ACCESS          read-only
    STATUS          mandatory
    DESCRIPTION     
            "The number of SEF/AIS Errored Seconds."
    ::= { sonusDsx1CurrentEntry 12 }

sonusDsx1CurrentCSSs OBJECT-TYPE
    SYNTAX          PerfCurrentCount
    ACCESS          read-only
    STATUS          mandatory
    DESCRIPTION     
            "The number of Controlled Slip Seconds."
    ::= { sonusDsx1CurrentEntry 13 }

sonusDsx1CurrentUASs OBJECT-TYPE
    SYNTAX          PerfCurrentCount
    ACCESS          read-only
    STATUS          mandatory
    DESCRIPTION     
            "The number of Unavailable Seconds."
    ::= { sonusDsx1CurrentEntry 14 }

sonusDsx1CurrentFC OBJECT-TYPE
    SYNTAX          INTEGER
    ACCESS          read-only
    STATUS          mandatory
    DESCRIPTION     
            "The number of LOF or AIS failures detected."
    ::= { sonusDsx1CurrentEntry 15 }

sonusDsx1CurrentTcaLCV OBJECT-TYPE
    SYNTAX          TruthValue
    ACCESS          read-only
    STATUS          obsolete
    DESCRIPTION     
            "Indicates status of threshold crossing for Line Code Violations."
    ::= { sonusDsx1CurrentEntry 16 }

sonusDsx1CurrentTcaLES OBJECT-TYPE
    SYNTAX          TruthValue
    ACCESS          read-only
    STATUS          obsolete
    DESCRIPTION     
            "Indicates status of threshold crossing for Line Errored Seconds."
    ::= { sonusDsx1CurrentEntry 17 }

sonusDsx1CurrentTcaLSES OBJECT-TYPE
    SYNTAX          TruthValue
    ACCESS          read-only
    STATUS          obsolete
    DESCRIPTION     
            "Indicates status of threshold crossing for Line Severely
             Errored Seconds."
    ::= { sonusDsx1CurrentEntry 18 }

sonusDsx1CurrentTcaPCV OBJECT-TYPE
    SYNTAX          TruthValue
    ACCESS          read-only
    STATUS          obsolete
    DESCRIPTION     
            "Indicates status of threshold crossing for Path Code Violations."
    ::= { sonusDsx1CurrentEntry 19 }

sonusDsx1CurrentTcaPES OBJECT-TYPE
    SYNTAX          TruthValue
    ACCESS          read-only
    STATUS          obsolete
    DESCRIPTION     
            "Indicates status of threshold crossing for Path Errored Seconds."
    ::= { sonusDsx1CurrentEntry 20 }

sonusDsx1CurrentTcaPSES OBJECT-TYPE
    SYNTAX          TruthValue
    ACCESS          read-only
    STATUS          obsolete
    DESCRIPTION     
            "Indicates status of threshold crossing for Path Severely
             Errored Seconds."
    ::= { sonusDsx1CurrentEntry 21 }

sonusDsx1CurrentTcaSAS OBJECT-TYPE
    SYNTAX          TruthValue
    ACCESS          read-only
    STATUS          obsolete
    DESCRIPTION     
            "Indicates status of threshold crossing for SEF/AIS Seconds."
    ::= { sonusDsx1CurrentEntry 22 }

sonusDsx1CurrentTcaCSS OBJECT-TYPE
    SYNTAX          TruthValue
    ACCESS          read-only
    STATUS          obsolete
    DESCRIPTION     
            "Indicates status of threshold crossing for Controlled Slip
             Seconds."
    ::= { sonusDsx1CurrentEntry 23 }

sonusDsx1CurrentTcaUAS OBJECT-TYPE
    SYNTAX          TruthValue
    ACCESS          read-only
    STATUS          obsolete
    DESCRIPTION     
            "Indicates status of threshold crossing for Unavailable Seconds."
    ::= { sonusDsx1CurrentEntry 24 }

sonusDsx1CurrentMinorTcaLCV OBJECT-TYPE
    SYNTAX          TruthValue
    ACCESS          read-only
    STATUS          mandatory
    DESCRIPTION     
            "Indicates status of Minor threshold crossing for Line Code Violations."
    ::= { sonusDsx1CurrentEntry 25 }

sonusDsx1CurrentMinorTcaLES OBJECT-TYPE
    SYNTAX          TruthValue
    ACCESS          read-only
    STATUS          mandatory
    DESCRIPTION     
            "Indicates status of Minor threshold crossing for Line Errored Seconds."
    ::= { sonusDsx1CurrentEntry 26 }

sonusDsx1CurrentMinorTcaLSES OBJECT-TYPE
    SYNTAX          TruthValue
    ACCESS          read-only
    STATUS          mandatory
    DESCRIPTION     
            "Indicates status of Minor threshold crossing for Line Severely
             Errored Seconds."
    ::= { sonusDsx1CurrentEntry 27 }

sonusDsx1CurrentMinorTcaPCV OBJECT-TYPE
    SYNTAX          TruthValue
    ACCESS          read-only
    STATUS          mandatory
    DESCRIPTION     
            "Indicates status of Minor threshold crossing for Path Code Violations."
    ::= { sonusDsx1CurrentEntry 28 }

sonusDsx1CurrentMinorTcaPES OBJECT-TYPE
    SYNTAX          TruthValue
    ACCESS          read-only
    STATUS          mandatory
    DESCRIPTION     
            "Indicates status of Minor threshold crossing for Path Errored Seconds."
    ::= { sonusDsx1CurrentEntry 29 }

sonusDsx1CurrentMinorTcaPSES OBJECT-TYPE
    SYNTAX          TruthValue
    ACCESS          read-only
    STATUS          mandatory
    DESCRIPTION     
            "Indicates status of Minor threshold crossing for Path Severely
             Errored Seconds."
    ::= { sonusDsx1CurrentEntry 30 }

sonusDsx1CurrentMinorTcaSAS OBJECT-TYPE
    SYNTAX          TruthValue
    ACCESS          read-only
    STATUS          mandatory
    DESCRIPTION     
            "Indicates status of Minor threshold crossing for SEF/AIS Seconds."
    ::= { sonusDsx1CurrentEntry 31 }

sonusDsx1CurrentMinorTcaCSS OBJECT-TYPE
    SYNTAX          TruthValue
    ACCESS          read-only
    STATUS          mandatory
    DESCRIPTION     
            "Indicates status of Minor threshold crossing for Controlled Slip
             Seconds."
    ::= { sonusDsx1CurrentEntry 32 }

sonusDsx1CurrentMinorTcaUAS OBJECT-TYPE
    SYNTAX          TruthValue
    ACCESS          read-only
    STATUS          mandatory
    DESCRIPTION     
            "Indicates status of Minor threshold crossing for Unavailable Seconds."
    ::= { sonusDsx1CurrentEntry 33 }

sonusDsx1CurrentMajorTcaLCV OBJECT-TYPE
    SYNTAX          TruthValue
    ACCESS          read-only
    STATUS          mandatory
    DESCRIPTION     
            "Indicates status of Major threshold crossing for Line Code Violations."
    ::= { sonusDsx1CurrentEntry 34 }

sonusDsx1CurrentMajorTcaLES OBJECT-TYPE
    SYNTAX          TruthValue
    ACCESS          read-only
    STATUS          mandatory
    DESCRIPTION     
            "Indicates status of Major threshold crossing for Line Errored Seconds."
    ::= { sonusDsx1CurrentEntry 35 }

sonusDsx1CurrentMajorTcaLSES OBJECT-TYPE
    SYNTAX          TruthValue
    ACCESS          read-only
    STATUS          mandatory
    DESCRIPTION     
            "Indicates status of Major threshold crossing for Line Severely
             Errored Seconds."
    ::= { sonusDsx1CurrentEntry 36 }

sonusDsx1CurrentMajorTcaPCV OBJECT-TYPE
    SYNTAX          TruthValue
    ACCESS          read-only
    STATUS          mandatory
    DESCRIPTION     
            "Indicates status of Major threshold crossing for Path Code Violations."
    ::= { sonusDsx1CurrentEntry 37 }

sonusDsx1CurrentMajorTcaPES OBJECT-TYPE
    SYNTAX          TruthValue
    ACCESS          read-only
    STATUS          mandatory
    DESCRIPTION     
            "Indicates status of Major threshold crossing for Path Errored Seconds."
    ::= { sonusDsx1CurrentEntry 38 }

sonusDsx1CurrentMajorTcaPSES OBJECT-TYPE
    SYNTAX          TruthValue
    ACCESS          read-only
    STATUS          mandatory
    DESCRIPTION     
            "Indicates status of Major threshold crossing for Path Severely
             Errored Seconds."
    ::= { sonusDsx1CurrentEntry 39 }

sonusDsx1CurrentMajorTcaSAS OBJECT-TYPE
    SYNTAX          TruthValue
    ACCESS          read-only
    STATUS          mandatory
    DESCRIPTION     
            "Indicates status of Major threshold crossing for SEF/AIS Seconds."
    ::= { sonusDsx1CurrentEntry 40 }

sonusDsx1CurrentMajorTcaCSS OBJECT-TYPE
    SYNTAX          TruthValue
    ACCESS          read-only
    STATUS          mandatory
    DESCRIPTION     
            "Indicates status of Major threshold crossing for Controlled Slip
             Seconds."
    ::= { sonusDsx1CurrentEntry 41 }

sonusDsx1CurrentMajorTcaUAS OBJECT-TYPE
    SYNTAX          TruthValue
    ACCESS          read-only
    STATUS          mandatory
    DESCRIPTION     
            "Indicates status of Major threshold crossing for Unavailable Seconds."
    ::= { sonusDsx1CurrentEntry 42 }

sonusDsx1CurrentCriticalTcaLCV OBJECT-TYPE
    SYNTAX          TruthValue
    ACCESS          read-only
    STATUS          mandatory
    DESCRIPTION     
            "Indicates status of Critical threshold crossing for Line Code Violations."
    ::= { sonusDsx1CurrentEntry 43 }

sonusDsx1CurrentCriticalTcaLES OBJECT-TYPE
    SYNTAX          TruthValue
    ACCESS          read-only
    STATUS          mandatory
    DESCRIPTION     
            "Indicates status of Critical threshold crossing for Line Errored Seconds."
    ::= { sonusDsx1CurrentEntry 44 }

sonusDsx1CurrentCriticalTcaLSES OBJECT-TYPE
    SYNTAX          TruthValue
    ACCESS          read-only
    STATUS          mandatory
    DESCRIPTION     
            "Indicates status of Critical threshold crossing for Line Severely
             Errored Seconds."
    ::= { sonusDsx1CurrentEntry 45 }

sonusDsx1CurrentCriticalTcaPCV OBJECT-TYPE
    SYNTAX          TruthValue
    ACCESS          read-only
    STATUS          mandatory
    DESCRIPTION     
            "Indicates status of Critical threshold crossing for Path Code Violations."
    ::= { sonusDsx1CurrentEntry 46 }

sonusDsx1CurrentCriticalTcaPES OBJECT-TYPE
    SYNTAX          TruthValue
    ACCESS          read-only
    STATUS          mandatory
    DESCRIPTION     
            "Indicates status of Critical threshold crossing for Path Errored Seconds."
    ::= { sonusDsx1CurrentEntry 47 }

sonusDsx1CurrentCriticalTcaPSES OBJECT-TYPE
    SYNTAX          TruthValue
    ACCESS          read-only
    STATUS          mandatory
    DESCRIPTION     
            "Indicates status of Critical threshold crossing for Path Severely
             Errored Seconds."
    ::= { sonusDsx1CurrentEntry 48 }

sonusDsx1CurrentCriticalTcaSAS OBJECT-TYPE
    SYNTAX          TruthValue
    ACCESS          read-only
    STATUS          mandatory
    DESCRIPTION     
            "Indicates status of Critical threshold crossing for SEF/AIS Seconds."
    ::= { sonusDsx1CurrentEntry 49 }

sonusDsx1CurrentCriticalTcaCSS OBJECT-TYPE
    SYNTAX          TruthValue
    ACCESS          read-only
    STATUS          mandatory
    DESCRIPTION     
            "Indicates status of Critical threshold crossing for Controlled Slip
             Seconds."
    ::= { sonusDsx1CurrentEntry 50 }

sonusDsx1CurrentCriticalTcaUAS OBJECT-TYPE
    SYNTAX          TruthValue
    ACCESS          read-only
    STATUS          mandatory
    DESCRIPTION     
            "Indicates status of Critical threshold crossing for Unavailable Seconds."
    ::= { sonusDsx1CurrentEntry 51 }

sonusDsx1FarEndCurrentTable OBJECT-TYPE
    SYNTAX          SEQUENCE OF SonusDsx1FarEndCurrentEntry
    ACCESS          not-accessible
    STATUS          mandatory
    DESCRIPTION     
            "The DS1 current table contains various statistics
             being collected for the far end current 15 minute
             interval."
    ::= { sonusDsx1MIBObjects 6 }

sonusDsx1FarEndCurrentEntry OBJECT-TYPE
    SYNTAX          SonusDsx1FarEndCurrentEntry
    ACCESS          not-accessible
    STATUS          mandatory
    DESCRIPTION     
            "An entry in the DS1 Current table."
    INDEX           { sonusDsx1FarEndCurrentShelfIndex, 
                      sonusDsx1FarEndCurrentSlotIndex, 
                      sonusDsx1FarEndCurrentPortIndex, 
                      sonusDsx1FarEndCurrentDs1Index }
    ::= { sonusDsx1FarEndCurrentTable 1 }

SonusDsx1FarEndCurrentEntry ::=
    SEQUENCE {
        sonusDsx1FarEndCurrentShelfIndex SonusShelfIndex,
        sonusDsx1FarEndCurrentSlotIndex SonusSlotIndex,
        sonusDsx1FarEndCurrentPortIndex INTEGER,
        sonusDsx1FarEndCurrentDs1Index  INTEGER,
        sonusDsx1FarEndCurrentElapsedTime INTEGER,
        sonusDsx1FarEndCurrentLESs      PerfCurrentCount,
        sonusDsx1FarEndCurrentPCVs      PerfCurrentCount,
        sonusDsx1FarEndCurrentPESs      PerfCurrentCount,
        sonusDsx1FarEndCurrentPSESs     PerfCurrentCount,
        sonusDsx1FarEndCurrentSEFSs     PerfCurrentCount,
        sonusDsx1FarEndCurrentCSSs      PerfCurrentCount,
        sonusDsx1FarEndCurrentUASs      PerfCurrentCount,
        sonusDsx1FarEndCurrentFC        INTEGER,
        sonusDsx1FarEndCurrentTcaLES    TruthValue,
        sonusDsx1FarEndCurrentTcaPCV    TruthValue,
        sonusDsx1FarEndCurrentTcaPES    TruthValue,
        sonusDsx1FarEndCurrentTcaPSES   TruthValue,
        sonusDsx1FarEndCurrentTcaSEFS   TruthValue,
        sonusDsx1FarEndCurrentTcaCSS    TruthValue,
        sonusDsx1FarEndCurrentTcaUAS    TruthValue,
        sonusDsx1FarEndCurrentMinorTcaLES TruthValue,
        sonusDsx1FarEndCurrentMinorTcaPCV TruthValue,
        sonusDsx1FarEndCurrentMinorTcaPES TruthValue,
        sonusDsx1FarEndCurrentMinorTcaPSES  TruthValue,
        sonusDsx1FarEndCurrentMinorTcaSEFS  TruthValue,
        sonusDsx1FarEndCurrentMinorTcaCSS TruthValue,
        sonusDsx1FarEndCurrentMinorTcaUAS TruthValue,
        sonusDsx1FarEndCurrentMajorTcaLES TruthValue,
        sonusDsx1FarEndCurrentMajorTcaPCV TruthValue,
        sonusDsx1FarEndCurrentMajorTcaPES TruthValue,
        sonusDsx1FarEndCurrentMajorTcaPSES  TruthValue,
        sonusDsx1FarEndCurrentMajorTcaSEFS  TruthValue,
        sonusDsx1FarEndCurrentMajorTcaCSS TruthValue,
        sonusDsx1FarEndCurrentMajorTcaUAS TruthValue,
        sonusDsx1FarEndCurrentCriticalTcaLES    TruthValue,
        sonusDsx1FarEndCurrentCriticalTcaPCV    TruthValue,
        sonusDsx1FarEndCurrentCriticalTcaPES    TruthValue,
        sonusDsx1FarEndCurrentCriticalTcaPSES     TruthValue,
        sonusDsx1FarEndCurrentCriticalTcaSEFS     TruthValue,
        sonusDsx1FarEndCurrentCriticalTcaCSS    TruthValue,
        sonusDsx1FarEndCurrentCriticalTcaUAS    TruthValue
    }

sonusDsx1FarEndCurrentShelfIndex OBJECT-TYPE
    SYNTAX          SonusShelfIndex
    ACCESS          read-only
    STATUS          mandatory
    DESCRIPTION     
            "Shelf index into this table"
    ::= { sonusDsx1FarEndCurrentEntry 1 }

sonusDsx1FarEndCurrentSlotIndex OBJECT-TYPE
    SYNTAX          SonusSlotIndex
    ACCESS          read-only
    STATUS          mandatory
    DESCRIPTION     
            "Slot index into this table"
    ::= { sonusDsx1FarEndCurrentEntry 2 }

sonusDsx1FarEndCurrentPortIndex OBJECT-TYPE
    SYNTAX          INTEGER
    ACCESS          read-only
    STATUS          mandatory
    DESCRIPTION     
            "Port Index into this table"
    ::= { sonusDsx1FarEndCurrentEntry 3 }

sonusDsx1FarEndCurrentDs1Index OBJECT-TYPE
    SYNTAX          INTEGER
    ACCESS          read-only
    STATUS          mandatory
    DESCRIPTION     
            "Ds1 Index into this table"
    ::= { sonusDsx1FarEndCurrentEntry 4 }

sonusDsx1FarEndCurrentElapsedTime OBJECT-TYPE
    SYNTAX          INTEGER
    ACCESS          read-only
    STATUS          mandatory
    DESCRIPTION     
            "Elapsed time in the current period"
    ::= { sonusDsx1FarEndCurrentEntry 5 }

sonusDsx1FarEndCurrentLESs OBJECT-TYPE
    SYNTAX          PerfCurrentCount
    ACCESS          read-only
    STATUS          mandatory
    DESCRIPTION     
            "The number of Line Errored Seconds."
    ::= { sonusDsx1FarEndCurrentEntry 6 }

sonusDsx1FarEndCurrentPCVs OBJECT-TYPE
    SYNTAX          PerfCurrentCount
    ACCESS          read-only
    STATUS          mandatory
    DESCRIPTION     
            "The number of Path Coding Violations."
    ::= { sonusDsx1FarEndCurrentEntry 7 }

sonusDsx1FarEndCurrentPESs OBJECT-TYPE
    SYNTAX          PerfCurrentCount
    ACCESS          read-only
    STATUS          mandatory
    DESCRIPTION     
            "The number of Path Errored Seconds."
    ::= { sonusDsx1FarEndCurrentEntry 8 }

sonusDsx1FarEndCurrentPSESs OBJECT-TYPE
    SYNTAX          PerfCurrentCount
    ACCESS          read-only
    STATUS          mandatory
    DESCRIPTION     
            "The number of Path Severely Errored Seconds."
    ::= { sonusDsx1FarEndCurrentEntry 9 }

sonusDsx1FarEndCurrentSEFSs OBJECT-TYPE
    SYNTAX          PerfCurrentCount
    ACCESS          read-only
    STATUS          mandatory
    DESCRIPTION     
            "The number of Severely Errored Frame Seconds."
    ::= { sonusDsx1FarEndCurrentEntry 10 }

sonusDsx1FarEndCurrentCSSs OBJECT-TYPE
    SYNTAX          PerfCurrentCount
    ACCESS          read-only
    STATUS          mandatory
    DESCRIPTION     
            "The number of Controlled Slip Seconds."
    ::= { sonusDsx1FarEndCurrentEntry 11 }

sonusDsx1FarEndCurrentUASs OBJECT-TYPE
    SYNTAX          PerfCurrentCount
    ACCESS          read-only
    STATUS          mandatory
    DESCRIPTION     
            "The number of Unavailable Seconds."
    ::= { sonusDsx1FarEndCurrentEntry 12 }

sonusDsx1FarEndCurrentFC OBJECT-TYPE
    SYNTAX          INTEGER
    ACCESS          read-only
    STATUS          mandatory
    DESCRIPTION     
            "The number of RAI failures detected."
    ::= { sonusDsx1FarEndCurrentEntry 13 }

sonusDsx1FarEndCurrentTcaLES OBJECT-TYPE
    SYNTAX          TruthValue
    ACCESS          read-only
    STATUS          obsolete
    DESCRIPTION     
            "Indicates status of threshold crossing for far-end Line
             Errored Seconds."
    ::= { sonusDsx1FarEndCurrentEntry 14 }

sonusDsx1FarEndCurrentTcaPCV OBJECT-TYPE
    SYNTAX          TruthValue
    ACCESS          read-only
    STATUS          obsolete
    DESCRIPTION     
            "Indicates status of threshold crossing for far-end Path
             Code Violations."
    ::= { sonusDsx1FarEndCurrentEntry 15 }

sonusDsx1FarEndCurrentTcaPES OBJECT-TYPE
    SYNTAX          TruthValue
    ACCESS          read-only
    STATUS          obsolete
    DESCRIPTION     
            "Indicates status of threshold crossing for far-end Path
             Errored Seconds."
    ::= { sonusDsx1FarEndCurrentEntry 16 }

sonusDsx1FarEndCurrentTcaPSES OBJECT-TYPE
    SYNTAX          TruthValue
    ACCESS          read-only
    STATUS          obsolete
    DESCRIPTION     
            "Indicates status of threshold crossing for far-end Path
             Severely Errored Seconds."
    ::= { sonusDsx1FarEndCurrentEntry 17 }

sonusDsx1FarEndCurrentTcaSEFS OBJECT-TYPE
    SYNTAX          TruthValue
    ACCESS          read-only
    STATUS          obsolete
    DESCRIPTION     
            "Indicates status of threshold crossing for far-end Path
             Severely Errored Frame Seconds."
    ::= { sonusDsx1FarEndCurrentEntry 18 }

sonusDsx1FarEndCurrentTcaCSS OBJECT-TYPE
    SYNTAX          TruthValue
    ACCESS          read-only
    STATUS          obsolete
    DESCRIPTION     
            "Indicates status of threshold crossing for far-end
             Controlled Slip Seconds."
    ::= { sonusDsx1FarEndCurrentEntry 19 }

sonusDsx1FarEndCurrentTcaUAS OBJECT-TYPE
    SYNTAX          TruthValue
    ACCESS          read-only
    STATUS          obsolete
    DESCRIPTION     
            "Indicates status of threshold crossing for far-end
             Unavailable Seconds."
    ::= { sonusDsx1FarEndCurrentEntry 20 }

sonusDsx1FarEndCurrentMinorTcaLES OBJECT-TYPE
    SYNTAX          TruthValue
    ACCESS          read-only
    STATUS          mandatory
    DESCRIPTION     
            "Indicates status of Minor threshold crossing for far-end Line
             Errored Seconds."
    ::= { sonusDsx1FarEndCurrentEntry 21 }

sonusDsx1FarEndCurrentMinorTcaPCV OBJECT-TYPE
    SYNTAX          TruthValue
    ACCESS          read-only
    STATUS          mandatory
    DESCRIPTION     
            "Indicates status of Minor threshold crossing for far-end Path
             Code Violations."
    ::= { sonusDsx1FarEndCurrentEntry 22 }

sonusDsx1FarEndCurrentMinorTcaPES OBJECT-TYPE
    SYNTAX          TruthValue
    ACCESS          read-only
    STATUS          mandatory
    DESCRIPTION     
            "Indicates status of Minor threshold crossing for far-end Path
             Errored Seconds."
    ::= { sonusDsx1FarEndCurrentEntry 23 }

sonusDsx1FarEndCurrentMinorTcaPSES OBJECT-TYPE
    SYNTAX          TruthValue
    ACCESS          read-only
    STATUS          mandatory
    DESCRIPTION     
            "Indicates status of Minor threshold crossing for far-end Path
             Severely Errored Seconds."
    ::= { sonusDsx1FarEndCurrentEntry 24 }

sonusDsx1FarEndCurrentMinorTcaSEFS OBJECT-TYPE
    SYNTAX          TruthValue
    ACCESS          read-only
    STATUS          mandatory
    DESCRIPTION     
            "Indicates status of Minor threshold crossing for far-end Path
             Severely Errored Frame Seconds."
    ::= { sonusDsx1FarEndCurrentEntry 25 }

sonusDsx1FarEndCurrentMinorTcaCSS OBJECT-TYPE
    SYNTAX          TruthValue
    ACCESS          read-only
    STATUS          mandatory
    DESCRIPTION     
            "Indicates status of Minor threshold crossing for far-end
             Controlled Slip Seconds."
    ::= { sonusDsx1FarEndCurrentEntry 26 }

sonusDsx1FarEndCurrentMinorTcaUAS OBJECT-TYPE
    SYNTAX          TruthValue
    ACCESS          read-only
    STATUS          mandatory
    DESCRIPTION     
            "Indicates status of Minor threshold crossing for far-end
             Unavailable Seconds."
    ::= { sonusDsx1FarEndCurrentEntry 27 }

sonusDsx1FarEndCurrentMajorTcaLES OBJECT-TYPE
    SYNTAX          TruthValue
    ACCESS          read-only
    STATUS          mandatory
    DESCRIPTION     
            "Indicates status of Major threshold crossing for far-end Line
             Errored Seconds."
    ::= { sonusDsx1FarEndCurrentEntry 28 }

sonusDsx1FarEndCurrentMajorTcaPCV OBJECT-TYPE
    SYNTAX          TruthValue
    ACCESS          read-only
    STATUS          mandatory
    DESCRIPTION     
            "Indicates status of Major threshold crossing for far-end Path
             Code Violations."
    ::= { sonusDsx1FarEndCurrentEntry 29 }

sonusDsx1FarEndCurrentMajorTcaPES OBJECT-TYPE
    SYNTAX          TruthValue
    ACCESS          read-only
    STATUS          mandatory
    DESCRIPTION     
            "Indicates status of Major threshold crossing for far-end Path
             Errored Seconds."
    ::= { sonusDsx1FarEndCurrentEntry 30 }

sonusDsx1FarEndCurrentMajorTcaPSES OBJECT-TYPE
    SYNTAX          TruthValue
    ACCESS          read-only
    STATUS          mandatory
    DESCRIPTION     
            "Indicates status of Major threshold crossing for far-end Path
             Severely Errored Seconds."
    ::= { sonusDsx1FarEndCurrentEntry 31 }

sonusDsx1FarEndCurrentMajorTcaSEFS OBJECT-TYPE
    SYNTAX          TruthValue
    ACCESS          read-only
    STATUS          mandatory
    DESCRIPTION     
            "Indicates status of Major threshold crossing for far-end Path
             Severely Errored Frame Seconds."
    ::= { sonusDsx1FarEndCurrentEntry 32 }

sonusDsx1FarEndCurrentMajorTcaCSS OBJECT-TYPE
    SYNTAX          TruthValue
    ACCESS          read-only
    STATUS          mandatory
    DESCRIPTION     
            "Indicates status of Major threshold crossing for far-end
             Controlled Slip Seconds."
    ::= { sonusDsx1FarEndCurrentEntry 33 }

sonusDsx1FarEndCurrentMajorTcaUAS OBJECT-TYPE
    SYNTAX          TruthValue
    ACCESS          read-only
    STATUS          mandatory
    DESCRIPTION     
            "Indicates status of Major threshold crossing for far-end
             Unavailable Seconds."
    ::= { sonusDsx1FarEndCurrentEntry 34 }

sonusDsx1FarEndCurrentCriticalTcaLES OBJECT-TYPE
    SYNTAX          TruthValue
    ACCESS          read-only
    STATUS          mandatory
    DESCRIPTION     
            "Indicates status of Critical threshold crossing for far-end Line
             Errored Seconds."
    ::= { sonusDsx1FarEndCurrentEntry 35 }

sonusDsx1FarEndCurrentCriticalTcaPCV OBJECT-TYPE
    SYNTAX          TruthValue
    ACCESS          read-only
    STATUS          mandatory
    DESCRIPTION     
            "Indicates status of Critical threshold crossing for far-end Path
             Code Violations."
    ::= { sonusDsx1FarEndCurrentEntry 36 }

sonusDsx1FarEndCurrentCriticalTcaPES OBJECT-TYPE
    SYNTAX          TruthValue
    ACCESS          read-only
    STATUS          mandatory
    DESCRIPTION     
            "Indicates status of Critical threshold crossing for far-end Path
             Errored Seconds."
    ::= { sonusDsx1FarEndCurrentEntry 37 }

sonusDsx1FarEndCurrentCriticalTcaPSES OBJECT-TYPE
    SYNTAX          TruthValue
    ACCESS          read-only
    STATUS          mandatory
    DESCRIPTION     
            "Indicates status of Critical threshold crossing for far-end Path
             Severely Errored Seconds."
    ::= { sonusDsx1FarEndCurrentEntry 38 }

sonusDsx1FarEndCurrentCriticalTcaSEFS OBJECT-TYPE
    SYNTAX          TruthValue
    ACCESS          read-only
    STATUS          mandatory
    DESCRIPTION     
            "Indicates status of Critical threshold crossing for far-end Path
             Severely Errored Frame Seconds."
    ::= { sonusDsx1FarEndCurrentEntry 39 }

sonusDsx1FarEndCurrentCriticalTcaCSS OBJECT-TYPE
    SYNTAX          TruthValue
    ACCESS          read-only
    STATUS          mandatory
    DESCRIPTION     
            "Indicates status of Critical threshold crossing for far-end
             Controlled Slip Seconds."
    ::= { sonusDsx1FarEndCurrentEntry 40 }

sonusDsx1FarEndCurrentCriticalTcaUAS OBJECT-TYPE
    SYNTAX          TruthValue
    ACCESS          read-only
    STATUS          mandatory
    DESCRIPTION     
            "Indicates status of Critical threshold crossing for far-end
             Unavailable Seconds."
    ::= { sonusDsx1FarEndCurrentEntry 41 }

sonusDsx1IntervalTable OBJECT-TYPE
    SYNTAX          SEQUENCE OF SonusDsx1IntervalEntry
    ACCESS          not-accessible
    STATUS          mandatory
    DESCRIPTION     
            "The DS1 Near End Interval Table contains various
             near end statistics collected by each DS1 interface
             over the previous 24 hours of operation.  The past
             		 24 hours are broken into 96 completed 15 minute
             intervals. Each row in this table represents one
             such interval for one specific instance."
    ::= { sonusDsx1MIBObjects 7 }

sonusDsx1IntervalEntry OBJECT-TYPE
    SYNTAX          SonusDsx1IntervalEntry
    ACCESS          not-accessible
    STATUS          mandatory
    DESCRIPTION     
            "An entry in the DS1 Current table."
    INDEX           { sonusDsx1IntervalShelfIndex, 
                      sonusDsx1IntervalSlotIndex, 
                      sonusDsx1IntervalPortIndex, 
                      sonusDsx1IntervalDs1Index, sonusDsx1IntervalNumber }
    ::= { sonusDsx1IntervalTable 1 }

SonusDsx1IntervalEntry ::=
    SEQUENCE {
        sonusDsx1IntervalShelfIndex     SonusShelfIndex,
        sonusDsx1IntervalSlotIndex      SonusSlotIndex,
        sonusDsx1IntervalPortIndex      INTEGER,
        sonusDsx1IntervalDs1Index       INTEGER,
        sonusDsx1IntervalNumber         INTEGER,
        sonusDsx1IntervalLCVs           PerfCurrentCount,
        sonusDsx1IntervalLESs           PerfCurrentCount,
        sonusDsx1IntervalLSESs          PerfCurrentCount,
        sonusDsx1IntervalPCVs           PerfCurrentCount,
        sonusDsx1IntervalPESs           PerfCurrentCount,
        sonusDsx1IntervalPSESs          PerfCurrentCount,
        sonusDsx1IntervalSASs           PerfCurrentCount,
        sonusDsx1IntervalCSSs           PerfCurrentCount,
        sonusDsx1IntervalUASs           PerfCurrentCount,
        sonusDsx1IntervalLineIDF        TruthValue,
        sonusDsx1IntervalPathIDF        TruthValue,
        sonusDsx1IntervalFC             INTEGER
    }

sonusDsx1IntervalShelfIndex OBJECT-TYPE
    SYNTAX          SonusShelfIndex
    ACCESS          read-only
    STATUS          mandatory
    DESCRIPTION     
            "Shelf index into this table"
    ::= { sonusDsx1IntervalEntry 1 }

sonusDsx1IntervalSlotIndex OBJECT-TYPE
    SYNTAX          SonusSlotIndex
    ACCESS          read-only
    STATUS          mandatory
    DESCRIPTION     
            "Slot index into this table"
    ::= { sonusDsx1IntervalEntry 2 }

sonusDsx1IntervalPortIndex OBJECT-TYPE
    SYNTAX          INTEGER
    ACCESS          read-only
    STATUS          mandatory
    DESCRIPTION     
            "Port Index into this table"
    ::= { sonusDsx1IntervalEntry 3 }

sonusDsx1IntervalDs1Index OBJECT-TYPE
    SYNTAX          INTEGER
    ACCESS          read-only
    STATUS          mandatory
    DESCRIPTION     
            "Ds1 Index into this table"
    ::= { sonusDsx1IntervalEntry 4 }

sonusDsx1IntervalNumber OBJECT-TYPE
    SYNTAX          INTEGER (1..32)
    ACCESS          read-only
    STATUS          mandatory
    DESCRIPTION     
            "A number between 1 and 32, where 1 is the most
             recently completed 15 minute interval."
    ::= { sonusDsx1IntervalEntry 5 }

sonusDsx1IntervalLCVs OBJECT-TYPE
    SYNTAX          PerfCurrentCount
    ACCESS          read-only
    STATUS          mandatory
    DESCRIPTION     
            "The number of Line Code Violations (LCVs)."
    ::= { sonusDsx1IntervalEntry 6 }

sonusDsx1IntervalLESs OBJECT-TYPE
    SYNTAX          PerfCurrentCount
    ACCESS          read-only
    STATUS          mandatory
    DESCRIPTION     
            "The number of Line Errored Seconds."
    ::= { sonusDsx1IntervalEntry 7 }

sonusDsx1IntervalLSESs OBJECT-TYPE
    SYNTAX          PerfCurrentCount
    ACCESS          read-only
    STATUS          mandatory
    DESCRIPTION     
            "The number of Line Severely Errored Seconds."
    ::= { sonusDsx1IntervalEntry 8 }

sonusDsx1IntervalPCVs OBJECT-TYPE
    SYNTAX          PerfCurrentCount
    ACCESS          read-only
    STATUS          mandatory
    DESCRIPTION     
            "The number of Path Coding Violations."
    ::= { sonusDsx1IntervalEntry 9 }

sonusDsx1IntervalPESs OBJECT-TYPE
    SYNTAX          PerfCurrentCount
    ACCESS          read-only
    STATUS          mandatory
    DESCRIPTION     
            "The number of Path Errored Seconds."
    ::= { sonusDsx1IntervalEntry 10 }

sonusDsx1IntervalPSESs OBJECT-TYPE
    SYNTAX          PerfCurrentCount
    ACCESS          read-only
    STATUS          mandatory
    DESCRIPTION     
            "The number of Path Severely Errored Seconds."
    ::= { sonusDsx1IntervalEntry 11 }

sonusDsx1IntervalSASs OBJECT-TYPE
    SYNTAX          PerfCurrentCount
    ACCESS          read-only
    STATUS          mandatory
    DESCRIPTION     
            "The number of SEF/AIS Errored Seconds."
    ::= { sonusDsx1IntervalEntry 12 }

sonusDsx1IntervalCSSs OBJECT-TYPE
    SYNTAX          PerfCurrentCount
    ACCESS          read-only
    STATUS          mandatory
    DESCRIPTION     
            "The number of Controlled Slip Seconds."
    ::= { sonusDsx1IntervalEntry 13 }

sonusDsx1IntervalUASs OBJECT-TYPE
    SYNTAX          PerfCurrentCount
    ACCESS          read-only
    STATUS          mandatory
    DESCRIPTION     
            "The number of Unavailable Seconds."
    ::= { sonusDsx1IntervalEntry 14 }

sonusDsx1IntervalLineIDF OBJECT-TYPE
    SYNTAX          TruthValue
    ACCESS          read-only
    STATUS          mandatory
    DESCRIPTION     
            "This variable indicates if the Line data for this
             interval is valid."
    ::= { sonusDsx1IntervalEntry 15 }

sonusDsx1IntervalPathIDF OBJECT-TYPE
    SYNTAX          TruthValue
    ACCESS          read-only
    STATUS          mandatory
    DESCRIPTION     
            "This variable indicates if the Path data for this
             interval is valid."
    ::= { sonusDsx1IntervalEntry 16 }

sonusDsx1IntervalFC OBJECT-TYPE
    SYNTAX          INTEGER
    ACCESS          read-only
    STATUS          mandatory
    DESCRIPTION     
            "The number of LOF or AIS failures detected."
    ::= { sonusDsx1IntervalEntry 17 }

sonusDsx1FarEndIntervalTable OBJECT-TYPE
    SYNTAX          SEQUENCE OF SonusDsx1FarEndIntervalEntry
    ACCESS          not-accessible
    STATUS          mandatory
    DESCRIPTION     
            "The DS1 Far End Interval Table contains various
             near end statistics collected by each DS1 interface
             over the previous 24 hours of operation.  The past
             		 24 hours are broken into 96 completed 15 minute
             intervals. Each row in this table represents one
             such interval for one specific instance."
    ::= { sonusDsx1MIBObjects 8 }

sonusDsx1FarEndIntervalEntry OBJECT-TYPE
    SYNTAX          SonusDsx1FarEndIntervalEntry
    ACCESS          not-accessible
    STATUS          mandatory
    DESCRIPTION     
            "An entry in the DS1 Current table."
    INDEX           { sonusDsx1FarEndIntervalShelfIndex, 
                      sonusDsx1FarEndIntervalSlotIndex, 
                      sonusDsx1FarEndIntervalPortIndex, 
                      sonusDsx1FarEndIntervalDs1Index, 
                      sonusDsx1FarEndIntervalNumber }
    ::= { sonusDsx1FarEndIntervalTable 1 }

SonusDsx1FarEndIntervalEntry ::=
    SEQUENCE {
        sonusDsx1FarEndIntervalShelfIndex SonusShelfIndex,
        sonusDsx1FarEndIntervalSlotIndex SonusSlotIndex,
        sonusDsx1FarEndIntervalPortIndex INTEGER,
        sonusDsx1FarEndIntervalDs1Index INTEGER,
        sonusDsx1FarEndIntervalNumber   INTEGER,
        sonusDsx1FarEndIntervalLESs     PerfCurrentCount,
        sonusDsx1FarEndIntervalPCVs     PerfCurrentCount,
        sonusDsx1FarEndIntervalPESs     PerfCurrentCount,
        sonusDsx1FarEndIntervalPSESs    PerfCurrentCount,
        sonusDsx1FarEndIntervalSEFSs    PerfCurrentCount,
        sonusDsx1FarEndIntervalCSSs     PerfCurrentCount,
        sonusDsx1FarEndIntervalUASs     PerfCurrentCount,
        sonusDsx1FarEndIntervalLineIDF  TruthValue,
        sonusDsx1FarEndIntervalPathIDF  TruthValue,
        sonusDsx1FarEndIntervalFC       INTEGER
    }

sonusDsx1FarEndIntervalShelfIndex OBJECT-TYPE
    SYNTAX          SonusShelfIndex
    ACCESS          read-only
    STATUS          mandatory
    DESCRIPTION     
            "Shelf index into this table"
    ::= { sonusDsx1FarEndIntervalEntry 1 }

sonusDsx1FarEndIntervalSlotIndex OBJECT-TYPE
    SYNTAX          SonusSlotIndex
    ACCESS          read-only
    STATUS          mandatory
    DESCRIPTION     
            "Slot index into this table"
    ::= { sonusDsx1FarEndIntervalEntry 2 }

sonusDsx1FarEndIntervalPortIndex OBJECT-TYPE
    SYNTAX          INTEGER
    ACCESS          read-only
    STATUS          mandatory
    DESCRIPTION     
            "Port Index into this table"
    ::= { sonusDsx1FarEndIntervalEntry 3 }

sonusDsx1FarEndIntervalDs1Index OBJECT-TYPE
    SYNTAX          INTEGER
    ACCESS          read-only
    STATUS          mandatory
    DESCRIPTION     
            "Ds1 Index into this table"
    ::= { sonusDsx1FarEndIntervalEntry 4 }

sonusDsx1FarEndIntervalNumber OBJECT-TYPE
    SYNTAX          INTEGER (1..32)
    ACCESS          read-only
    STATUS          mandatory
    DESCRIPTION     
            "A number between 1 and 32, where 1 is the most
             recently completed 15 minute interval."
    ::= { sonusDsx1FarEndIntervalEntry 5 }

sonusDsx1FarEndIntervalLESs OBJECT-TYPE
    SYNTAX          PerfCurrentCount
    ACCESS          read-only
    STATUS          mandatory
    DESCRIPTION     
            "The number of Line Errored Seconds."
    ::= { sonusDsx1FarEndIntervalEntry 6 }

sonusDsx1FarEndIntervalPCVs OBJECT-TYPE
    SYNTAX          PerfCurrentCount
    ACCESS          read-only
    STATUS          mandatory
    DESCRIPTION     
            "The number of Path Coding Violations."
    ::= { sonusDsx1FarEndIntervalEntry 7 }

sonusDsx1FarEndIntervalPESs OBJECT-TYPE
    SYNTAX          PerfCurrentCount
    ACCESS          read-only
    STATUS          mandatory
    DESCRIPTION     
            "The number of Path Errored Seconds."
    ::= { sonusDsx1FarEndIntervalEntry 8 }

sonusDsx1FarEndIntervalPSESs OBJECT-TYPE
    SYNTAX          PerfCurrentCount
    ACCESS          read-only
    STATUS          mandatory
    DESCRIPTION     
            "The number of Path Severely Errored Seconds."
    ::= { sonusDsx1FarEndIntervalEntry 9 }

sonusDsx1FarEndIntervalSEFSs OBJECT-TYPE
    SYNTAX          PerfCurrentCount
    ACCESS          read-only
    STATUS          mandatory
    DESCRIPTION     
            "The number of Severely Errored Frame Seconds."
    ::= { sonusDsx1FarEndIntervalEntry 10 }

sonusDsx1FarEndIntervalCSSs OBJECT-TYPE
    SYNTAX          PerfCurrentCount
    ACCESS          read-only
    STATUS          mandatory
    DESCRIPTION     
            "The number of Controlled Slip Seconds."
    ::= { sonusDsx1FarEndIntervalEntry 11 }

sonusDsx1FarEndIntervalUASs OBJECT-TYPE
    SYNTAX          PerfCurrentCount
    ACCESS          read-only
    STATUS          mandatory
    DESCRIPTION     
            "The number of Unavailable Seconds."
    ::= { sonusDsx1FarEndIntervalEntry 12 }

sonusDsx1FarEndIntervalLineIDF OBJECT-TYPE
    SYNTAX          TruthValue
    ACCESS          read-only
    STATUS          mandatory
    DESCRIPTION     
            "This variable indicates if the Line data for this
             interval is valid."
    ::= { sonusDsx1FarEndIntervalEntry 13 }

sonusDsx1FarEndIntervalPathIDF OBJECT-TYPE
    SYNTAX          TruthValue
    ACCESS          read-only
    STATUS          mandatory
    DESCRIPTION     
            "This variable indicates if the Path data for this
             interval is valid."
    ::= { sonusDsx1FarEndIntervalEntry 14 }

sonusDsx1FarEndIntervalFC OBJECT-TYPE
    SYNTAX          INTEGER
    ACCESS          read-only
    STATUS          mandatory
    DESCRIPTION     
            "The number of RAI failures detected."
    ::= { sonusDsx1FarEndIntervalEntry 15 }

sonusDsx1CurrentDayTable OBJECT-TYPE
    SYNTAX          SEQUENCE OF SonusDsx1CurrentDayEntry
    ACCESS          not-accessible
    STATUS          mandatory
    DESCRIPTION     
            "The DS1 current table contains various statistics
             being collected for the near end current 24 hour
             interval."
    ::= { sonusDsx1MIBObjects 9 }

sonusDsx1CurrentDayEntry OBJECT-TYPE
    SYNTAX          SonusDsx1CurrentDayEntry
    ACCESS          not-accessible
    STATUS          mandatory
    DESCRIPTION     
            "An entry in the DS1 Current table."
    INDEX           { sonusDsx1CurrentDayShelfIndex, 
                      sonusDsx1CurrentDaySlotIndex, 
                      sonusDsx1CurrentDayPortIndex, 
                      sonusDsx1CurrentDayDs1Index }
    ::= { sonusDsx1CurrentDayTable 1 }

SonusDsx1CurrentDayEntry ::=
    SEQUENCE {
        sonusDsx1CurrentDayShelfIndex   SonusShelfIndex,
        sonusDsx1CurrentDaySlotIndex    SonusSlotIndex,
        sonusDsx1CurrentDayPortIndex    INTEGER,
        sonusDsx1CurrentDayDs1Index     INTEGER,
        sonusDsx1CurrentDayElapsedTime  INTEGER,
        sonusDsx1CurrentDayLCVs         PerfCurrentCount,
        sonusDsx1CurrentDayLESs         PerfCurrentCount,
        sonusDsx1CurrentDayLSESs        PerfCurrentCount,
        sonusDsx1CurrentDayPCVs         PerfCurrentCount,
        sonusDsx1CurrentDayPESs         PerfCurrentCount,
        sonusDsx1CurrentDayPSESs        PerfCurrentCount,
        sonusDsx1CurrentDaySASs         PerfCurrentCount,
        sonusDsx1CurrentDayCSSs         PerfCurrentCount,
        sonusDsx1CurrentDayUASs         PerfCurrentCount,
        sonusDsx1CurrentDayFC           INTEGER,
        sonusDsx1CurrentDayTcaLCV       TruthValue,
        sonusDsx1CurrentDayTcaLES       TruthValue,
        sonusDsx1CurrentDayTcaLSES      TruthValue,
        sonusDsx1CurrentDayTcaPCV       TruthValue,
        sonusDsx1CurrentDayTcaPES       TruthValue,
        sonusDsx1CurrentDayTcaPSES      TruthValue,
        sonusDsx1CurrentDayTcaSAS       TruthValue,
        sonusDsx1CurrentDayTcaCSS       TruthValue,
        sonusDsx1CurrentDayTcaUAS       TruthValue,
        sonusDsx1CurrentDayMinorTcaLCV  TruthValue,
        sonusDsx1CurrentDayMinorTcaLES  TruthValue,
        sonusDsx1CurrentDayMinorTcaLSES TruthValue,
        sonusDsx1CurrentDayMinorTcaPCV  TruthValue,
        sonusDsx1CurrentDayMinorTcaPES  TruthValue,
        sonusDsx1CurrentDayMinorTcaPSES TruthValue,
        sonusDsx1CurrentDayMinorTcaSAS  TruthValue,
        sonusDsx1CurrentDayMinorTcaCSS  TruthValue,
        sonusDsx1CurrentDayMinorTcaUAS  TruthValue,
        sonusDsx1CurrentDayMajorTcaLCV  TruthValue,
        sonusDsx1CurrentDayMajorTcaLES  TruthValue,
        sonusDsx1CurrentDayMajorTcaLSES TruthValue,
        sonusDsx1CurrentDayMajorTcaPCV  TruthValue,
        sonusDsx1CurrentDayMajorTcaPES  TruthValue,
        sonusDsx1CurrentDayMajorTcaPSES TruthValue,
        sonusDsx1CurrentDayMajorTcaSAS  TruthValue,
        sonusDsx1CurrentDayMajorTcaCSS  TruthValue,
        sonusDsx1CurrentDayMajorTcaUAS  TruthValue,
        sonusDsx1CurrentDayCriticalTcaLCV TruthValue,
        sonusDsx1CurrentDayCriticalTcaLES TruthValue,
        sonusDsx1CurrentDayCriticalTcaLSES  TruthValue,
        sonusDsx1CurrentDayCriticalTcaPCV TruthValue,
        sonusDsx1CurrentDayCriticalTcaPES TruthValue,
        sonusDsx1CurrentDayCriticalTcaPSES  TruthValue,
        sonusDsx1CurrentDayCriticalTcaSAS TruthValue,
        sonusDsx1CurrentDayCriticalTcaCSS TruthValue,
        sonusDsx1CurrentDayCriticalTcaUAS TruthValue
    }

sonusDsx1CurrentDayShelfIndex OBJECT-TYPE
    SYNTAX          SonusShelfIndex
    ACCESS          read-only
    STATUS          mandatory
    DESCRIPTION     
            "Shelf index into this table"
    ::= { sonusDsx1CurrentDayEntry 1 }

sonusDsx1CurrentDaySlotIndex OBJECT-TYPE
    SYNTAX          SonusSlotIndex
    ACCESS          read-only
    STATUS          mandatory
    DESCRIPTION     
            "Slot index into this table"
    ::= { sonusDsx1CurrentDayEntry 2 }

sonusDsx1CurrentDayPortIndex OBJECT-TYPE
    SYNTAX          INTEGER
    ACCESS          read-only
    STATUS          mandatory
    DESCRIPTION     
            "Port Index into this table"
    ::= { sonusDsx1CurrentDayEntry 3 }

sonusDsx1CurrentDayDs1Index OBJECT-TYPE
    SYNTAX          INTEGER
    ACCESS          read-only
    STATUS          mandatory
    DESCRIPTION     
            "Ds1 Index into this table"
    ::= { sonusDsx1CurrentDayEntry 4 }

sonusDsx1CurrentDayElapsedTime OBJECT-TYPE
    SYNTAX          INTEGER
    ACCESS          read-only
    STATUS          mandatory
    DESCRIPTION     
            "Elapsed time in the current period"
    ::= { sonusDsx1CurrentDayEntry 5 }

sonusDsx1CurrentDayLCVs OBJECT-TYPE
    SYNTAX          PerfCurrentCount
    ACCESS          read-only
    STATUS          mandatory
    DESCRIPTION     
            "The number of Line Code Violations (LCVs)."
    ::= { sonusDsx1CurrentDayEntry 6 }

sonusDsx1CurrentDayLESs OBJECT-TYPE
    SYNTAX          PerfCurrentCount
    ACCESS          read-only
    STATUS          mandatory
    DESCRIPTION     
            "The number of Line Errored Seconds."
    ::= { sonusDsx1CurrentDayEntry 7 }

sonusDsx1CurrentDayLSESs OBJECT-TYPE
    SYNTAX          PerfCurrentCount
    ACCESS          read-only
    STATUS          mandatory
    DESCRIPTION     
            "The number of Line Severely Errored Seconds."
    ::= { sonusDsx1CurrentDayEntry 8 }

sonusDsx1CurrentDayPCVs OBJECT-TYPE
    SYNTAX          PerfCurrentCount
    ACCESS          read-only
    STATUS          mandatory
    DESCRIPTION     
            "The number of Path Coding Violations."
    ::= { sonusDsx1CurrentDayEntry 9 }

sonusDsx1CurrentDayPESs OBJECT-TYPE
    SYNTAX          PerfCurrentCount
    ACCESS          read-only
    STATUS          mandatory
    DESCRIPTION     
            "The number of Path Errored Seconds."
    ::= { sonusDsx1CurrentDayEntry 10 }

sonusDsx1CurrentDayPSESs OBJECT-TYPE
    SYNTAX          PerfCurrentCount
    ACCESS          read-only
    STATUS          mandatory
    DESCRIPTION     
            "The number of Path Severely Errored Seconds."
    ::= { sonusDsx1CurrentDayEntry 11 }

sonusDsx1CurrentDaySASs OBJECT-TYPE
    SYNTAX          PerfCurrentCount
    ACCESS          read-only
    STATUS          mandatory
    DESCRIPTION     
            "The number of SEF/AIS Errored Seconds."
    ::= { sonusDsx1CurrentDayEntry 12 }

sonusDsx1CurrentDayCSSs OBJECT-TYPE
    SYNTAX          PerfCurrentCount
    ACCESS          read-only
    STATUS          mandatory
    DESCRIPTION     
            "The number of Controlled Slip Seconds."
    ::= { sonusDsx1CurrentDayEntry 13 }

sonusDsx1CurrentDayUASs OBJECT-TYPE
    SYNTAX          PerfCurrentCount
    ACCESS          read-only
    STATUS          mandatory
    DESCRIPTION     
            "The number of Unavailable Seconds."
    ::= { sonusDsx1CurrentDayEntry 14 }

sonusDsx1CurrentDayFC OBJECT-TYPE
    SYNTAX          INTEGER
    ACCESS          read-only
    STATUS          mandatory
    DESCRIPTION     
            "The number of LOF or AIS failures detected."
    ::= { sonusDsx1CurrentDayEntry 16 }

sonusDsx1CurrentDayTcaLCV OBJECT-TYPE
    SYNTAX          TruthValue
    ACCESS          read-only
    STATUS          obsolete
    DESCRIPTION     
            "Indicates status of threshold crossing for Line Code Violations."
    ::= { sonusDsx1CurrentDayEntry 17 }

sonusDsx1CurrentDayTcaLES OBJECT-TYPE
    SYNTAX          TruthValue
    ACCESS          read-only
    STATUS          obsolete
    DESCRIPTION     
            "Indicates status of threshold crossing for Line Errored Seconds."
    ::= { sonusDsx1CurrentDayEntry 18 }

sonusDsx1CurrentDayTcaLSES OBJECT-TYPE
    SYNTAX          TruthValue
    ACCESS          read-only
    STATUS          obsolete
    DESCRIPTION     
            "Indicates status of threshold crossing for Line Severely
             Errored Seconds."
    ::= { sonusDsx1CurrentDayEntry 19 }

sonusDsx1CurrentDayTcaPCV OBJECT-TYPE
    SYNTAX          TruthValue
    ACCESS          read-only
    STATUS          obsolete
    DESCRIPTION     
            "Indicates status of threshold crossing for Path Code Violations."
    ::= { sonusDsx1CurrentDayEntry 20 }

sonusDsx1CurrentDayTcaPES OBJECT-TYPE
    SYNTAX          TruthValue
    ACCESS          read-only
    STATUS          obsolete
    DESCRIPTION     
            "Indicates status of threshold crossing for Path Errored Seconds."
    ::= { sonusDsx1CurrentDayEntry 21 }

sonusDsx1CurrentDayTcaPSES OBJECT-TYPE
    SYNTAX          TruthValue
    ACCESS          read-only
    STATUS          obsolete
    DESCRIPTION     
            "Indicates status of threshold crossing for Path Severely
             Errored Seconds."
    ::= { sonusDsx1CurrentDayEntry 22 }

sonusDsx1CurrentDayTcaSAS OBJECT-TYPE
    SYNTAX          TruthValue
    ACCESS          read-only
    STATUS          obsolete
    DESCRIPTION     
            "Indicates status of threshold crossing for SEF/AIS Seconds."
    ::= { sonusDsx1CurrentDayEntry 23 }

sonusDsx1CurrentDayTcaCSS OBJECT-TYPE
    SYNTAX          TruthValue
    ACCESS          read-only
    STATUS          obsolete
    DESCRIPTION     
            "Indicates status of threshold crossing for Controlled Slip
             Seconds."
    ::= { sonusDsx1CurrentDayEntry 24 }

sonusDsx1CurrentDayTcaUAS OBJECT-TYPE
    SYNTAX          TruthValue
    ACCESS          read-only
    STATUS          obsolete
    DESCRIPTION     
            "Indicates status of threshold crossing for Unavailable Seconds."
    ::= { sonusDsx1CurrentDayEntry 25 }

sonusDsx1CurrentDayMinorTcaLCV OBJECT-TYPE
    SYNTAX          TruthValue
    ACCESS          read-only
    STATUS          mandatory
    DESCRIPTION     
            "Indicates status of Minor threshold crossing for Line Code Violations."
    ::= { sonusDsx1CurrentDayEntry 26 }

sonusDsx1CurrentDayMinorTcaLES OBJECT-TYPE
    SYNTAX          TruthValue
    ACCESS          read-only
    STATUS          mandatory
    DESCRIPTION     
            "Indicates status of Minor threshold crossing for Line Errored Seconds."
    ::= { sonusDsx1CurrentDayEntry 27 }

sonusDsx1CurrentDayMinorTcaLSES OBJECT-TYPE
    SYNTAX          TruthValue
    ACCESS          read-only
    STATUS          mandatory
    DESCRIPTION     
            "Indicates status of Minor threshold crossing for Line Severely
             Errored Seconds."
    ::= { sonusDsx1CurrentDayEntry 28 }

sonusDsx1CurrentDayMinorTcaPCV OBJECT-TYPE
    SYNTAX          TruthValue
    ACCESS          read-only
    STATUS          mandatory
    DESCRIPTION     
            "Indicates status of Minor threshold crossing for Path Code Violations."
    ::= { sonusDsx1CurrentDayEntry 29 }

sonusDsx1CurrentDayMinorTcaPES OBJECT-TYPE
    SYNTAX          TruthValue
    ACCESS          read-only
    STATUS          mandatory
    DESCRIPTION     
            "Indicates status of Minor threshold crossing for Path Errored Seconds."
    ::= { sonusDsx1CurrentDayEntry 30 }

sonusDsx1CurrentDayMinorTcaPSES OBJECT-TYPE
    SYNTAX          TruthValue
    ACCESS          read-only
    STATUS          mandatory
    DESCRIPTION     
            "Indicates status of Minor threshold crossing for Path Severely
             Errored Seconds."
    ::= { sonusDsx1CurrentDayEntry 31 }

sonusDsx1CurrentDayMinorTcaSAS OBJECT-TYPE
    SYNTAX          TruthValue
    ACCESS          read-only
    STATUS          mandatory
    DESCRIPTION     
            "Indicates status of Minor threshold crossing for SEF/AIS Seconds."
    ::= { sonusDsx1CurrentDayEntry 32 }

sonusDsx1CurrentDayMinorTcaCSS OBJECT-TYPE
    SYNTAX          TruthValue
    ACCESS          read-only
    STATUS          mandatory
    DESCRIPTION     
            "Indicates status of Minor threshold crossing for Controlled Slip
             Seconds."
    ::= { sonusDsx1CurrentDayEntry 33 }

sonusDsx1CurrentDayMinorTcaUAS OBJECT-TYPE
    SYNTAX          TruthValue
    ACCESS          read-only
    STATUS          mandatory
    DESCRIPTION     
            "Indicates status of Minor threshold crossing for Unavailable Seconds."
    ::= { sonusDsx1CurrentDayEntry 34 }

sonusDsx1CurrentDayMajorTcaLCV OBJECT-TYPE
    SYNTAX          TruthValue
    ACCESS          read-only
    STATUS          mandatory
    DESCRIPTION     
            "Indicates status of Major threshold crossing for Line Code Violations."
    ::= { sonusDsx1CurrentDayEntry 35 }

sonusDsx1CurrentDayMajorTcaLES OBJECT-TYPE
    SYNTAX          TruthValue
    ACCESS          read-only
    STATUS          mandatory
    DESCRIPTION     
            "Indicates status of Major threshold crossing for Line Errored Seconds."
    ::= { sonusDsx1CurrentDayEntry 36 }

sonusDsx1CurrentDayMajorTcaLSES OBJECT-TYPE
    SYNTAX          TruthValue
    ACCESS          read-only
    STATUS          mandatory
    DESCRIPTION     
            "Indicates status of Major threshold crossing for Line Severely
             Errored Seconds."
    ::= { sonusDsx1CurrentDayEntry 37 }

sonusDsx1CurrentDayMajorTcaPCV OBJECT-TYPE
    SYNTAX          TruthValue
    ACCESS          read-only
    STATUS          mandatory
    DESCRIPTION     
            "Indicates status of Major threshold crossing for Path Code Violations."
    ::= { sonusDsx1CurrentDayEntry 38 }

sonusDsx1CurrentDayMajorTcaPES OBJECT-TYPE
    SYNTAX          TruthValue
    ACCESS          read-only
    STATUS          mandatory
    DESCRIPTION     
            "Indicates status of Major threshold crossing for Path Errored Seconds."
    ::= { sonusDsx1CurrentDayEntry 39 }

sonusDsx1CurrentDayMajorTcaPSES OBJECT-TYPE
    SYNTAX          TruthValue
    ACCESS          read-only
    STATUS          mandatory
    DESCRIPTION     
            "Indicates status of Major threshold crossing for Path Severely
             Errored Seconds."
    ::= { sonusDsx1CurrentDayEntry 40 }

sonusDsx1CurrentDayMajorTcaSAS OBJECT-TYPE
    SYNTAX          TruthValue
    ACCESS          read-only
    STATUS          mandatory
    DESCRIPTION     
            "Indicates status of Major threshold crossing for SEF/AIS Seconds."
    ::= { sonusDsx1CurrentDayEntry 41 }

sonusDsx1CurrentDayMajorTcaCSS OBJECT-TYPE
    SYNTAX          TruthValue
    ACCESS          read-only
    STATUS          mandatory
    DESCRIPTION     
            "Indicates status of Major threshold crossing for Controlled Slip
             Seconds."
    ::= { sonusDsx1CurrentDayEntry 42 }

sonusDsx1CurrentDayMajorTcaUAS OBJECT-TYPE
    SYNTAX          TruthValue
    ACCESS          read-only
    STATUS          mandatory
    DESCRIPTION     
            "Indicates status of Major threshold crossing for Unavailable Seconds."
    ::= { sonusDsx1CurrentDayEntry 43 }

sonusDsx1CurrentDayCriticalTcaLCV OBJECT-TYPE
    SYNTAX          TruthValue
    ACCESS          read-only
    STATUS          mandatory
    DESCRIPTION     
            "Indicates status of Critical threshold crossing for Line Code Violations."
    ::= { sonusDsx1CurrentDayEntry 44 }

sonusDsx1CurrentDayCriticalTcaLES OBJECT-TYPE
    SYNTAX          TruthValue
    ACCESS          read-only
    STATUS          mandatory
    DESCRIPTION     
            "Indicates status of Critical threshold crossing for Line Errored Seconds."
    ::= { sonusDsx1CurrentDayEntry 45 }

sonusDsx1CurrentDayCriticalTcaLSES OBJECT-TYPE
    SYNTAX          TruthValue
    ACCESS          read-only
    STATUS          mandatory
    DESCRIPTION     
            "Indicates status of Critical threshold crossing for Line Severely
             Errored Seconds."
    ::= { sonusDsx1CurrentDayEntry 46 }

sonusDsx1CurrentDayCriticalTcaPCV OBJECT-TYPE
    SYNTAX          TruthValue
    ACCESS          read-only
    STATUS          mandatory
    DESCRIPTION     
            "Indicates status of Critical threshold crossing for Path Code Violations."
    ::= { sonusDsx1CurrentDayEntry 47 }

sonusDsx1CurrentDayCriticalTcaPES OBJECT-TYPE
    SYNTAX          TruthValue
    ACCESS          read-only
    STATUS          mandatory
    DESCRIPTION     
            "Indicates status of Critical threshold crossing for Path Errored Seconds."
    ::= { sonusDsx1CurrentDayEntry 48 }

sonusDsx1CurrentDayCriticalTcaPSES OBJECT-TYPE
    SYNTAX          TruthValue
    ACCESS          read-only
    STATUS          mandatory
    DESCRIPTION     
            "Indicates status of Critical threshold crossing for Path Severely
             Errored Seconds."
    ::= { sonusDsx1CurrentDayEntry 49 }

sonusDsx1CurrentDayCriticalTcaSAS OBJECT-TYPE
    SYNTAX          TruthValue
    ACCESS          read-only
    STATUS          mandatory
    DESCRIPTION     
            "Indicates status of Critical threshold crossing for SEF/AIS Seconds."
    ::= { sonusDsx1CurrentDayEntry 50 }

sonusDsx1CurrentDayCriticalTcaCSS OBJECT-TYPE
    SYNTAX          TruthValue
    ACCESS          read-only
    STATUS          mandatory
    DESCRIPTION     
            "Indicates status of Critical threshold crossing for Controlled Slip
             Seconds."
    ::= { sonusDsx1CurrentDayEntry 51 }

sonusDsx1CurrentDayCriticalTcaUAS OBJECT-TYPE
    SYNTAX          TruthValue
    ACCESS          read-only
    STATUS          mandatory
    DESCRIPTION     
            "Indicates status of Critical threshold crossing for Unavailable Seconds."
    ::= { sonusDsx1CurrentDayEntry 52 }

sonusDsx1FarEndCurrentDayTable OBJECT-TYPE
    SYNTAX          SEQUENCE OF SonusDsx1FarEndCurrentDayEntry
    ACCESS          not-accessible
    STATUS          mandatory
    DESCRIPTION     
            "The DS1 current table contains various statistics
             being collected for the far end current 24 hour
             interval."
    ::= { sonusDsx1MIBObjects 10 }

sonusDsx1FarEndCurrentDayEntry OBJECT-TYPE
    SYNTAX          SonusDsx1FarEndCurrentDayEntry
    ACCESS          not-accessible
    STATUS          mandatory
    DESCRIPTION     
            "An entry in the DS1 Current table."
    INDEX           { sonusDsx1FarEndCurrentDayShelfIndex, 
                      sonusDsx1FarEndCurrentDaySlotIndex, 
                      sonusDsx1FarEndCurrentDayPortIndex, 
                      sonusDsx1FarEndCurrentDayDs1Index }
    ::= { sonusDsx1FarEndCurrentDayTable 1 }

SonusDsx1FarEndCurrentDayEntry ::=
    SEQUENCE {
        sonusDsx1FarEndCurrentDayShelfIndex   SonusShelfIndex,
        sonusDsx1FarEndCurrentDaySlotIndex  SonusSlotIndex,
        sonusDsx1FarEndCurrentDayPortIndex  INTEGER,
        sonusDsx1FarEndCurrentDayDs1Index INTEGER,
        sonusDsx1FarEndCurrentDayElapsedTime    INTEGER,
        sonusDsx1FarEndCurrentDayLESs   PerfCurrentCount,
        sonusDsx1FarEndCurrentDayPCVs   PerfCurrentCount,
        sonusDsx1FarEndCurrentDayPESs   PerfCurrentCount,
        sonusDsx1FarEndCurrentDayPSESs  PerfCurrentCount,
        sonusDsx1FarEndCurrentDaySEFSs  PerfCurrentCount,
        sonusDsx1FarEndCurrentDayCSSs   PerfCurrentCount,
        sonusDsx1FarEndCurrentDayUASs   PerfCurrentCount,
        sonusDsx1FarEndCurrentDayFC     INTEGER,
        sonusDsx1FarEndCurrentDayTcaLES TruthValue,
        sonusDsx1FarEndCurrentDayTcaPCV TruthValue,
        sonusDsx1FarEndCurrentDayTcaPES TruthValue,
        sonusDsx1FarEndCurrentDayTcaPSES TruthValue,
        sonusDsx1FarEndCurrentDayTcaSEFS TruthValue,
        sonusDsx1FarEndCurrentDayTcaCSS TruthValue,
        sonusDsx1FarEndCurrentDayTcaUAS TruthValue,
        sonusDsx1FarEndCurrentDayMinorTcaLES    TruthValue,
        sonusDsx1FarEndCurrentDayMinorTcaPCV    TruthValue,
        sonusDsx1FarEndCurrentDayMinorTcaPES    TruthValue,
        sonusDsx1FarEndCurrentDayMinorTcaPSES     TruthValue,
        sonusDsx1FarEndCurrentDayMinorTcaSEFS     TruthValue,
        sonusDsx1FarEndCurrentDayMinorTcaCSS    TruthValue,
        sonusDsx1FarEndCurrentDayMinorTcaUAS    TruthValue,
        sonusDsx1FarEndCurrentDayMajorTcaLES    TruthValue,
        sonusDsx1FarEndCurrentDayMajorTcaPCV    TruthValue,
        sonusDsx1FarEndCurrentDayMajorTcaPES    TruthValue,
        sonusDsx1FarEndCurrentDayMajorTcaPSES     TruthValue,
        sonusDsx1FarEndCurrentDayMajorTcaSEFS     TruthValue,
        sonusDsx1FarEndCurrentDayMajorTcaCSS    TruthValue,
        sonusDsx1FarEndCurrentDayMajorTcaUAS    TruthValue,
        sonusDsx1FarEndCurrentDayCriticalTcaLES       TruthValue,
        sonusDsx1FarEndCurrentDayCriticalTcaPCV       TruthValue,
        sonusDsx1FarEndCurrentDayCriticalTcaPES       TruthValue,
        sonusDsx1FarEndCurrentDayCriticalTcaPSES        TruthValue,
        sonusDsx1FarEndCurrentDayCriticalTcaSEFS        TruthValue,
        sonusDsx1FarEndCurrentDayCriticalTcaCSS       TruthValue,
        sonusDsx1FarEndCurrentDayCriticalTcaUAS       TruthValue
    }

sonusDsx1FarEndCurrentDayShelfIndex OBJECT-TYPE
    SYNTAX          SonusShelfIndex
    ACCESS          read-only
    STATUS          mandatory
    DESCRIPTION     
            "Shelf index into this table"
    ::= { sonusDsx1FarEndCurrentDayEntry 1 }

sonusDsx1FarEndCurrentDaySlotIndex OBJECT-TYPE
    SYNTAX          SonusSlotIndex
    ACCESS          read-only
    STATUS          mandatory
    DESCRIPTION     
            "Slot index into this table"
    ::= { sonusDsx1FarEndCurrentDayEntry 2 }

sonusDsx1FarEndCurrentDayPortIndex OBJECT-TYPE
    SYNTAX          INTEGER
    ACCESS          read-only
    STATUS          mandatory
    DESCRIPTION     
            "Port Index into this table"
    ::= { sonusDsx1FarEndCurrentDayEntry 3 }

sonusDsx1FarEndCurrentDayDs1Index OBJECT-TYPE
    SYNTAX          INTEGER
    ACCESS          read-only
    STATUS          mandatory
    DESCRIPTION     
            "Ds1 Index into this table"
    ::= { sonusDsx1FarEndCurrentDayEntry 4 }

sonusDsx1FarEndCurrentDayElapsedTime OBJECT-TYPE
    SYNTAX          INTEGER
    ACCESS          read-only
    STATUS          mandatory
    DESCRIPTION     
            "Elapsed time in the current period"
    ::= { sonusDsx1FarEndCurrentDayEntry 5 }

sonusDsx1FarEndCurrentDayLESs OBJECT-TYPE
    SYNTAX          PerfCurrentCount
    ACCESS          read-only
    STATUS          mandatory
    DESCRIPTION     
            "The number of Line Errored Seconds."
    ::= { sonusDsx1FarEndCurrentDayEntry 6 }

sonusDsx1FarEndCurrentDayPCVs OBJECT-TYPE
    SYNTAX          PerfCurrentCount
    ACCESS          read-only
    STATUS          mandatory
    DESCRIPTION     
            "The number of Path Coding Violations."
    ::= { sonusDsx1FarEndCurrentDayEntry 7 }

sonusDsx1FarEndCurrentDayPESs OBJECT-TYPE
    SYNTAX          PerfCurrentCount
    ACCESS          read-only
    STATUS          mandatory
    DESCRIPTION     
            "The number of Path Errored Seconds."
    ::= { sonusDsx1FarEndCurrentDayEntry 8 }

sonusDsx1FarEndCurrentDayPSESs OBJECT-TYPE
    SYNTAX          PerfCurrentCount
    ACCESS          read-only
    STATUS          mandatory
    DESCRIPTION     
            "The number of Path Severely Errored Seconds."
    ::= { sonusDsx1FarEndCurrentDayEntry 9 }

sonusDsx1FarEndCurrentDaySEFSs OBJECT-TYPE
    SYNTAX          PerfCurrentCount
    ACCESS          read-only
    STATUS          mandatory
    DESCRIPTION     
            "The number of Severely Errored Frame Seconds."
    ::= { sonusDsx1FarEndCurrentDayEntry 10 }

sonusDsx1FarEndCurrentDayCSSs OBJECT-TYPE
    SYNTAX          PerfCurrentCount
    ACCESS          read-only
    STATUS          mandatory
    DESCRIPTION     
            "The number of Controlled Slip Seconds."
    ::= { sonusDsx1FarEndCurrentDayEntry 11 }

sonusDsx1FarEndCurrentDayUASs OBJECT-TYPE
    SYNTAX          PerfCurrentCount
    ACCESS          read-only
    STATUS          mandatory
    DESCRIPTION     
            "The number of Unavailable Seconds."
    ::= { sonusDsx1FarEndCurrentDayEntry 12 }

sonusDsx1FarEndCurrentDayFC OBJECT-TYPE
    SYNTAX          INTEGER
    ACCESS          read-only
    STATUS          mandatory
    DESCRIPTION     
            "The number of RAI failures detected."
    ::= { sonusDsx1FarEndCurrentDayEntry 13 }

sonusDsx1FarEndCurrentDayTcaLES OBJECT-TYPE
    SYNTAX          TruthValue
    ACCESS          read-only
    STATUS          obsolete
    DESCRIPTION     
            "Indicates status of threshold crossing for far-end Line
             Errored Seconds."
    ::= { sonusDsx1FarEndCurrentDayEntry 14 }

sonusDsx1FarEndCurrentDayTcaPCV OBJECT-TYPE
    SYNTAX          TruthValue
    ACCESS          read-only
    STATUS          obsolete
    DESCRIPTION     
            "Indicates status of threshold crossing for far-end Path
             Code Violations."
    ::= { sonusDsx1FarEndCurrentDayEntry 15 }

sonusDsx1FarEndCurrentDayTcaPES OBJECT-TYPE
    SYNTAX          TruthValue
    ACCESS          read-only
    STATUS          obsolete
    DESCRIPTION     
            "Indicates status of threshold crossing for far-end Path
             Errored Seconds."
    ::= { sonusDsx1FarEndCurrentDayEntry 16 }

sonusDsx1FarEndCurrentDayTcaPSES OBJECT-TYPE
    SYNTAX          TruthValue
    ACCESS          read-only
    STATUS          obsolete
    DESCRIPTION     
            "Indicates status of threshold crossing for far-end Path
             Severely Errored Seconds."
    ::= { sonusDsx1FarEndCurrentDayEntry 17 }

sonusDsx1FarEndCurrentDayTcaSEFS OBJECT-TYPE
    SYNTAX          TruthValue
    ACCESS          read-only
    STATUS          obsolete
    DESCRIPTION     
            "Indicates status of threshold crossing for far-end Path
             Severely Errored Frame Seconds."
    ::= { sonusDsx1FarEndCurrentDayEntry 18 }

sonusDsx1FarEndCurrentDayTcaCSS OBJECT-TYPE
    SYNTAX          TruthValue
    ACCESS          read-only
    STATUS          obsolete
    DESCRIPTION     
            "Indicates status of threshold crossing for far-end
             Controlled Slip Seconds."
    ::= { sonusDsx1FarEndCurrentDayEntry 19 }

sonusDsx1FarEndCurrentDayTcaUAS OBJECT-TYPE
    SYNTAX          TruthValue
    ACCESS          read-only
    STATUS          obsolete
    DESCRIPTION     
            "Indicates status of threshold crossing for far-end
             Unavailable Seconds."
    ::= { sonusDsx1FarEndCurrentDayEntry 20 }

sonusDsx1FarEndCurrentDayMinorTcaLES OBJECT-TYPE
    SYNTAX          TruthValue
    ACCESS          read-only
    STATUS          mandatory
    DESCRIPTION     
            "Indicates status of Minor threshold crossing for far-end Line
             Errored Seconds."
    ::= { sonusDsx1FarEndCurrentDayEntry 21 }

sonusDsx1FarEndCurrentDayMinorTcaPCV OBJECT-TYPE
    SYNTAX          TruthValue
    ACCESS          read-only
    STATUS          mandatory
    DESCRIPTION     
            "Indicates status of Minor threshold crossing for far-end Path
             Code Violations."
    ::= { sonusDsx1FarEndCurrentDayEntry 22 }

sonusDsx1FarEndCurrentDayMinorTcaPES OBJECT-TYPE
    SYNTAX          TruthValue
    ACCESS          read-only
    STATUS          mandatory
    DESCRIPTION     
            "Indicates status of Minor threshold crossing for far-end Path
             Errored Seconds."
    ::= { sonusDsx1FarEndCurrentDayEntry 23 }

sonusDsx1FarEndCurrentDayMinorTcaPSES OBJECT-TYPE
    SYNTAX          TruthValue
    ACCESS          read-only
    STATUS          mandatory
    DESCRIPTION     
            "Indicates status of Minor threshold crossing for far-end Path
             Severely Errored Seconds."
    ::= { sonusDsx1FarEndCurrentDayEntry 24 }

sonusDsx1FarEndCurrentDayMinorTcaSEFS OBJECT-TYPE
    SYNTAX          TruthValue
    ACCESS          read-only
    STATUS          mandatory
    DESCRIPTION     
            "Indicates status of Minor threshold crossing for far-end Path
             Severely Errored Frame Seconds."
    ::= { sonusDsx1FarEndCurrentDayEntry 25 }

sonusDsx1FarEndCurrentDayMinorTcaCSS OBJECT-TYPE
    SYNTAX          TruthValue
    ACCESS          read-only
    STATUS          mandatory
    DESCRIPTION     
            "Indicates status of Minor threshold crossing for far-end
             Controlled Slip Seconds."
    ::= { sonusDsx1FarEndCurrentDayEntry 26 }

sonusDsx1FarEndCurrentDayMinorTcaUAS OBJECT-TYPE
    SYNTAX          TruthValue
    ACCESS          read-only
    STATUS          mandatory
    DESCRIPTION     
            "Indicates status of Minor threshold crossing for far-end
             Unavailable Seconds."
    ::= { sonusDsx1FarEndCurrentDayEntry 27 }

sonusDsx1FarEndCurrentDayMajorTcaLES OBJECT-TYPE
    SYNTAX          TruthValue
    ACCESS          read-only
    STATUS          mandatory
    DESCRIPTION     
            "Indicates status of Major threshold crossing for far-end Line
             Errored Seconds."
    ::= { sonusDsx1FarEndCurrentDayEntry 28 }

sonusDsx1FarEndCurrentDayMajorTcaPCV OBJECT-TYPE
    SYNTAX          TruthValue
    ACCESS          read-only
    STATUS          mandatory
    DESCRIPTION     
            "Indicates status of Major threshold crossing for far-end Path
             Code Violations."
    ::= { sonusDsx1FarEndCurrentDayEntry 29 }

sonusDsx1FarEndCurrentDayMajorTcaPES OBJECT-TYPE
    SYNTAX          TruthValue
    ACCESS          read-only
    STATUS          mandatory
    DESCRIPTION     
            "Indicates status of Major threshold crossing for far-end Path
             Errored Seconds."
    ::= { sonusDsx1FarEndCurrentDayEntry 30 }

sonusDsx1FarEndCurrentDayMajorTcaPSES OBJECT-TYPE
    SYNTAX          TruthValue
    ACCESS          read-only
    STATUS          mandatory
    DESCRIPTION     
            "Indicates status of Major threshold crossing for far-end Path
             Severely Errored Seconds."
    ::= { sonusDsx1FarEndCurrentDayEntry 31 }

sonusDsx1FarEndCurrentDayMajorTcaSEFS OBJECT-TYPE
    SYNTAX          TruthValue
    ACCESS          read-only
    STATUS          mandatory
    DESCRIPTION     
            "Indicates status of Major threshold crossing for far-end Path
             Severely Errored Frame Seconds."
    ::= { sonusDsx1FarEndCurrentDayEntry 32 }

sonusDsx1FarEndCurrentDayMajorTcaCSS OBJECT-TYPE
    SYNTAX          TruthValue
    ACCESS          read-only
    STATUS          mandatory
    DESCRIPTION     
            "Indicates status of Major threshold crossing for far-end
             Controlled Slip Seconds."
    ::= { sonusDsx1FarEndCurrentDayEntry 33 }

sonusDsx1FarEndCurrentDayMajorTcaUAS OBJECT-TYPE
    SYNTAX          TruthValue
    ACCESS          read-only
    STATUS          mandatory
    DESCRIPTION     
            "Indicates status of Major threshold crossing for far-end
             Unavailable Seconds."
    ::= { sonusDsx1FarEndCurrentDayEntry 34 }

sonusDsx1FarEndCurrentDayCriticalTcaLES OBJECT-TYPE
    SYNTAX          TruthValue
    ACCESS          read-only
    STATUS          mandatory
    DESCRIPTION     
            "Indicates status of Critical threshold crossing for far-end Line
             Errored Seconds."
    ::= { sonusDsx1FarEndCurrentDayEntry 35 }

sonusDsx1FarEndCurrentDayCriticalTcaPCV OBJECT-TYPE
    SYNTAX          TruthValue
    ACCESS          read-only
    STATUS          mandatory
    DESCRIPTION     
            "Indicates status of Critical threshold crossing for far-end Path
             Code Violations."
    ::= { sonusDsx1FarEndCurrentDayEntry 36 }

sonusDsx1FarEndCurrentDayCriticalTcaPES OBJECT-TYPE
    SYNTAX          TruthValue
    ACCESS          read-only
    STATUS          mandatory
    DESCRIPTION     
            "Indicates status of Critical threshold crossing for far-end Path
             Errored Seconds."
    ::= { sonusDsx1FarEndCurrentDayEntry 37 }

sonusDsx1FarEndCurrentDayCriticalTcaPSES OBJECT-TYPE
    SYNTAX          TruthValue
    ACCESS          read-only
    STATUS          mandatory
    DESCRIPTION     
            "Indicates status of Critical threshold crossing for far-end Path
             Severely Errored Seconds."
    ::= { sonusDsx1FarEndCurrentDayEntry 38 }

sonusDsx1FarEndCurrentDayCriticalTcaSEFS OBJECT-TYPE
    SYNTAX          TruthValue
    ACCESS          read-only
    STATUS          mandatory
    DESCRIPTION     
            "Indicates status of Critical threshold crossing for far-end Path
             Severely Errored Frame Seconds."
    ::= { sonusDsx1FarEndCurrentDayEntry 39 }

sonusDsx1FarEndCurrentDayCriticalTcaCSS OBJECT-TYPE
    SYNTAX          TruthValue
    ACCESS          read-only
    STATUS          mandatory
    DESCRIPTION     
            "Indicates status of Critical threshold crossing for far-end
             Controlled Slip Seconds."
    ::= { sonusDsx1FarEndCurrentDayEntry 40 }

sonusDsx1FarEndCurrentDayCriticalTcaUAS OBJECT-TYPE
    SYNTAX          TruthValue
    ACCESS          read-only
    STATUS          mandatory
    DESCRIPTION     
            "Indicates status of Critical threshold crossing for far-end
             Unavailable Seconds."
    ::= { sonusDsx1FarEndCurrentDayEntry 41 }

sonusDsx1IntervalDayTable OBJECT-TYPE
    SYNTAX          SEQUENCE OF SonusDsx1IntervalDayEntry
    ACCESS          not-accessible
    STATUS          mandatory
    DESCRIPTION     
            "The DS1 Near End Interval Table contains various
             near end statistics collected by each DS1 interface
             over the previous 24 hours of operation."
    ::= { sonusDsx1MIBObjects 11 }

sonusDsx1IntervalDayEntry OBJECT-TYPE
    SYNTAX          SonusDsx1IntervalDayEntry
    ACCESS          not-accessible
    STATUS          mandatory
    DESCRIPTION     
            "An entry in the DS1 Current table."
    INDEX           { sonusDsx1IntervalDayShelfIndex, 
                      sonusDsx1IntervalDaySlotIndex, 
                      sonusDsx1IntervalDayPortIndex, 
                      sonusDsx1IntervalDayDs1Index }
    ::= { sonusDsx1IntervalDayTable 1 }

SonusDsx1IntervalDayEntry ::=
    SEQUENCE {
        sonusDsx1IntervalDayShelfIndex  SonusShelfIndex,
        sonusDsx1IntervalDaySlotIndex   SonusSlotIndex,
        sonusDsx1IntervalDayPortIndex   INTEGER,
        sonusDsx1IntervalDayDs1Index    INTEGER,
        sonusDsx1IntervalDayLCVs        PerfCurrentCount,
        sonusDsx1IntervalDayLESs        PerfCurrentCount,
        sonusDsx1IntervalDayLSESs       PerfCurrentCount,
        sonusDsx1IntervalDayPCVs        PerfCurrentCount,
        sonusDsx1IntervalDayPESs        PerfCurrentCount,
        sonusDsx1IntervalDayPSESs       PerfCurrentCount,
        sonusDsx1IntervalDaySASs        PerfCurrentCount,
        sonusDsx1IntervalDayCSSs        PerfCurrentCount,
        sonusDsx1IntervalDayUASs        PerfCurrentCount,
        sonusDsx1IntervalDayLineIDF     TruthValue,
        sonusDsx1IntervalDayPathIDF     TruthValue,
        sonusDsx1IntervalDayFC          INTEGER
    }

sonusDsx1IntervalDayShelfIndex OBJECT-TYPE
    SYNTAX          SonusShelfIndex
    ACCESS          read-only
    STATUS          mandatory
    DESCRIPTION     
            "Shelf index into this table"
    ::= { sonusDsx1IntervalDayEntry 1 }

sonusDsx1IntervalDaySlotIndex OBJECT-TYPE
    SYNTAX          SonusSlotIndex
    ACCESS          read-only
    STATUS          mandatory
    DESCRIPTION     
            "Slot index into this table"
    ::= { sonusDsx1IntervalDayEntry 2 }

sonusDsx1IntervalDayPortIndex OBJECT-TYPE
    SYNTAX          INTEGER
    ACCESS          read-only
    STATUS          mandatory
    DESCRIPTION     
            "Port Index into this table"
    ::= { sonusDsx1IntervalDayEntry 3 }

sonusDsx1IntervalDayDs1Index OBJECT-TYPE
    SYNTAX          INTEGER
    ACCESS          read-only
    STATUS          mandatory
    DESCRIPTION     
            "Ds1 Index into this table"
    ::= { sonusDsx1IntervalDayEntry 4 }

sonusDsx1IntervalDayLCVs OBJECT-TYPE
    SYNTAX          PerfCurrentCount
    ACCESS          read-only
    STATUS          mandatory
    DESCRIPTION     
            "The number of Line Code Violations (LCVs)."
    ::= { sonusDsx1IntervalDayEntry 5 }

sonusDsx1IntervalDayLESs OBJECT-TYPE
    SYNTAX          PerfCurrentCount
    ACCESS          read-only
    STATUS          mandatory
    DESCRIPTION     
            "The number of Line Errored Seconds."
    ::= { sonusDsx1IntervalDayEntry 6 }

sonusDsx1IntervalDayLSESs OBJECT-TYPE
    SYNTAX          PerfCurrentCount
    ACCESS          read-only
    STATUS          mandatory
    DESCRIPTION     
            "The number of Line Severely Errored Seconds."
    ::= { sonusDsx1IntervalDayEntry 7 }

sonusDsx1IntervalDayPCVs OBJECT-TYPE
    SYNTAX          PerfCurrentCount
    ACCESS          read-only
    STATUS          mandatory
    DESCRIPTION     
            "The number of Path Coding Violations."
    ::= { sonusDsx1IntervalDayEntry 8 }

sonusDsx1IntervalDayPESs OBJECT-TYPE
    SYNTAX          PerfCurrentCount
    ACCESS          read-only
    STATUS          mandatory
    DESCRIPTION     
            "The number of Path Errored Seconds."
    ::= { sonusDsx1IntervalDayEntry 9 }

sonusDsx1IntervalDayPSESs OBJECT-TYPE
    SYNTAX          PerfCurrentCount
    ACCESS          read-only
    STATUS          mandatory
    DESCRIPTION     
            "The number of Path Severely Errored Seconds."
    ::= { sonusDsx1IntervalDayEntry 10 }

sonusDsx1IntervalDaySASs OBJECT-TYPE
    SYNTAX          PerfCurrentCount
    ACCESS          read-only
    STATUS          mandatory
    DESCRIPTION     
            "The number of SEF/AIS Errored Seconds."
    ::= { sonusDsx1IntervalDayEntry 11 }

sonusDsx1IntervalDayCSSs OBJECT-TYPE
    SYNTAX          PerfCurrentCount
    ACCESS          read-only
    STATUS          mandatory
    DESCRIPTION     
            "The number of Controlled Slip Seconds."
    ::= { sonusDsx1IntervalDayEntry 12 }

sonusDsx1IntervalDayUASs OBJECT-TYPE
    SYNTAX          PerfCurrentCount
    ACCESS          read-only
    STATUS          mandatory
    DESCRIPTION     
            "The number of Unavailable Seconds."
    ::= { sonusDsx1IntervalDayEntry 13 }

sonusDsx1IntervalDayLineIDF OBJECT-TYPE
    SYNTAX          TruthValue
    ACCESS          read-only
    STATUS          mandatory
    DESCRIPTION     
            "This variable indicates if the Line data for this
             interval is valid."
    ::= { sonusDsx1IntervalDayEntry 14 }

sonusDsx1IntervalDayPathIDF OBJECT-TYPE
    SYNTAX          TruthValue
    ACCESS          read-only
    STATUS          mandatory
    DESCRIPTION     
            "This variable indicates if the Path data for this
             interval is valid."
    ::= { sonusDsx1IntervalDayEntry 15 }

sonusDsx1IntervalDayFC OBJECT-TYPE
    SYNTAX          INTEGER
    ACCESS          read-only
    STATUS          mandatory
    DESCRIPTION     
            "The number of LOF or AIS failures detected."
    ::= { sonusDsx1IntervalDayEntry 16 }

sonusDsx1FarEndIntervalDayTable OBJECT-TYPE
    SYNTAX          SEQUENCE OF SonusDsx1FarEndIntervalDayEntry
    ACCESS          not-accessible
    STATUS          mandatory
    DESCRIPTION     
            "The DS1 Near End Interval Table contains various
             far end statistics collected by each DS1 interface
             over the previous 24 hours of operation."
    ::= { sonusDsx1MIBObjects 12 }

sonusDsx1FarEndIntervalDayEntry OBJECT-TYPE
    SYNTAX          SonusDsx1FarEndIntervalDayEntry
    ACCESS          not-accessible
    STATUS          mandatory
    DESCRIPTION     
            "An entry in the DS1 Current table."
    INDEX           { sonusDsx1FarEndIntervalDayShelfIndex, 
                      sonusDsx1FarEndIntervalDaySlotIndex, 
                      sonusDsx1FarEndIntervalDayPortIndex, 
                      sonusDsx1FarEndIntervalDayDs1Index }
    ::= { sonusDsx1FarEndIntervalDayTable 1 }

SonusDsx1FarEndIntervalDayEntry ::=
    SEQUENCE {
        sonusDsx1FarEndIntervalDayShelfIndex    SonusShelfIndex,
        sonusDsx1FarEndIntervalDaySlotIndex   SonusSlotIndex,
        sonusDsx1FarEndIntervalDayPortIndex   INTEGER,
        sonusDsx1FarEndIntervalDayDs1Index  INTEGER,
        sonusDsx1FarEndIntervalDayLESs  PerfCurrentCount,
        sonusDsx1FarEndIntervalDayPCVs  PerfCurrentCount,
        sonusDsx1FarEndIntervalDayPESs  PerfCurrentCount,
        sonusDsx1FarEndIntervalDayPSESs PerfCurrentCount,
        sonusDsx1FarEndIntervalDaySEFSs PerfCurrentCount,
        sonusDsx1FarEndIntervalDayCSSs  PerfCurrentCount,
        sonusDsx1FarEndIntervalDayUASs  PerfCurrentCount,
        sonusDsx1FarEndIntervalDayLineIDF TruthValue,
        sonusDsx1FarEndIntervalDayPathIDF TruthValue,
        sonusDsx1FarEndIntervalDayFC    INTEGER
    }

sonusDsx1FarEndIntervalDayShelfIndex OBJECT-TYPE
    SYNTAX          SonusShelfIndex
    ACCESS          read-only
    STATUS          mandatory
    DESCRIPTION     
            "Shelf index into this table"
    ::= { sonusDsx1FarEndIntervalDayEntry 1 }

sonusDsx1FarEndIntervalDaySlotIndex OBJECT-TYPE
    SYNTAX          SonusSlotIndex
    ACCESS          read-only
    STATUS          mandatory
    DESCRIPTION     
            "Slot index into this table"
    ::= { sonusDsx1FarEndIntervalDayEntry 2 }

sonusDsx1FarEndIntervalDayPortIndex OBJECT-TYPE
    SYNTAX          INTEGER
    ACCESS          read-only
    STATUS          mandatory
    DESCRIPTION     
            "Port Index into this table"
    ::= { sonusDsx1FarEndIntervalDayEntry 3 }

sonusDsx1FarEndIntervalDayDs1Index OBJECT-TYPE
    SYNTAX          INTEGER
    ACCESS          read-only
    STATUS          mandatory
    DESCRIPTION     
            "Ds1 Index into this table"
    ::= { sonusDsx1FarEndIntervalDayEntry 4 }

sonusDsx1FarEndIntervalDayLESs OBJECT-TYPE
    SYNTAX          PerfCurrentCount
    ACCESS          read-only
    STATUS          mandatory
    DESCRIPTION     
            "The number of Line Errored Seconds."
    ::= { sonusDsx1FarEndIntervalDayEntry 5 }

sonusDsx1FarEndIntervalDayPCVs OBJECT-TYPE
    SYNTAX          PerfCurrentCount
    ACCESS          read-only
    STATUS          mandatory
    DESCRIPTION     
            "The number of Path Coding Violations."
    ::= { sonusDsx1FarEndIntervalDayEntry 6 }

sonusDsx1FarEndIntervalDayPESs OBJECT-TYPE
    SYNTAX          PerfCurrentCount
    ACCESS          read-only
    STATUS          mandatory
    DESCRIPTION     
            "The number of Path Errored Seconds."
    ::= { sonusDsx1FarEndIntervalDayEntry 7 }

sonusDsx1FarEndIntervalDayPSESs OBJECT-TYPE
    SYNTAX          PerfCurrentCount
    ACCESS          read-only
    STATUS          mandatory
    DESCRIPTION     
            "The number of Path Severely Errored Seconds."
    ::= { sonusDsx1FarEndIntervalDayEntry 8 }

sonusDsx1FarEndIntervalDaySEFSs OBJECT-TYPE
    SYNTAX          PerfCurrentCount
    ACCESS          read-only
    STATUS          mandatory
    DESCRIPTION     
            "The number of Severely Errored Frame Seconds."
    ::= { sonusDsx1FarEndIntervalDayEntry 9 }

sonusDsx1FarEndIntervalDayCSSs OBJECT-TYPE
    SYNTAX          PerfCurrentCount
    ACCESS          read-only
    STATUS          mandatory
    DESCRIPTION     
            "The number of Controlled Slip Seconds."
    ::= { sonusDsx1FarEndIntervalDayEntry 10 }

sonusDsx1FarEndIntervalDayUASs OBJECT-TYPE
    SYNTAX          PerfCurrentCount
    ACCESS          read-only
    STATUS          mandatory
    DESCRIPTION     
            "The number of Unavailable Seconds."
    ::= { sonusDsx1FarEndIntervalDayEntry 11 }

sonusDsx1FarEndIntervalDayLineIDF OBJECT-TYPE
    SYNTAX          TruthValue
    ACCESS          read-only
    STATUS          mandatory
    DESCRIPTION     
            "This variable indicates if the Line data for this
             interval is valid."
    ::= { sonusDsx1FarEndIntervalDayEntry 12 }

sonusDsx1FarEndIntervalDayPathIDF OBJECT-TYPE
    SYNTAX          TruthValue
    ACCESS          read-only
    STATUS          mandatory
    DESCRIPTION     
            "This variable indicates if the Path data for this
             interval is valid."
    ::= { sonusDsx1FarEndIntervalDayEntry 13 }

sonusDsx1FarEndIntervalDayFC OBJECT-TYPE
    SYNTAX          INTEGER
    ACCESS          read-only
    STATUS          mandatory
    DESCRIPTION     
            "The number of RAI failures detected."
    ::= { sonusDsx1FarEndIntervalDayEntry 14 }

sonusDsx1MIBNotifications OBJECT IDENTIFIER
    ::= { sonusDsx1MIB 2 }

sonusDsx1MIBNotificationsPrefix OBJECT IDENTIFIER
    ::= { sonusDsx1MIBNotifications 0 }

sonusDsx1MIBNotificationsObjects OBJECT IDENTIFIER
    ::= { sonusDsx1MIBNotifications 1 }

sonusDs1OutOfServiceReason OBJECT-TYPE
    SYNTAX          INTEGER { maintenance(1) }
    ACCESS          read-only
    STATUS          mandatory
    DESCRIPTION     
            "The reason for T1/E1 span going out of service"
    ::= { sonusDsx1MIBNotificationsObjects 1 }

sonusDs1OutOfServiceType OBJECT-TYPE
    SYNTAX          INTEGER { admin(1), hwFailure(2) }
    ACCESS          read-only
    STATUS          mandatory
    DESCRIPTION     
            "The type of operation which caused T1/E1 span to go out of service"
    ::= { sonusDsx1MIBNotificationsObjects 2 }

sonusDs1ThresholdType OBJECT-TYPE
    SYNTAX          INTEGER { currentLineCodeViolation(1), 
                        currentPathCodeViolation(2), 
                        currentPathCodeViolationFarEnd(3), 
                        currentControlledSlips(4), 
                        currentErroredSeconds(5), 
                        currentSeverelyErrSeconds(6), 
                        currentUnavailableSeconds(7), 
                        totalLineCodeViolation(8), 
                        totalPathCodeViolation(9), 
                        totalPathCodeViolationFarEnd(10), 
                        totalControlledSlips(11), 
                        totalErroredSeconds(12), 
                        totalSeverelyErrSeconds(13), 
                        totalUnavailableSeconds(14), 
                        currentFarEndErroredSeconds(15), 
                        currentFarEndSeverelyErrSeconds(16), 
                        totalFarEndErroredSeconds(17), 
                        totalFarEndCurrentSeverelyErrSeconds(18), 
                        currentFarEndUnavailableSeconds(19), 
                        totalFarEndUnavailableSeconds(20), 
                        currentLineErroredSeconds(21), 
                        currentLineSeverelyErrSeconds(22), 
                        currentSEForAISSeconds(23), 
                        totalLineErroredSeconds(24), 
                        totalLineSeverelyErrSeconds(25), 
                        totalSEForAISSeconds(26), 
                        currentLineErroredSecondsFarEnd(27), 
                        currentSeverelyErrFrameSecondsFarEnd(28), 
                        currentControlledSlipsFarEnd(29), 
                        totalLineErroredSecondsFarEnd(30), 
                        totalSeverelyErrFrameSecondsFarEnd(31), 
                        totalControlledSlipsFarEnd(32) }
    ACCESS          read-only
    STATUS          mandatory
    DESCRIPTION     
            "Type of threshold that was crossed which caused a threshold crossing trap"
    ::= { sonusDsx1MIBNotificationsObjects 3 }

sonusDs1LineState OBJECT-TYPE
    SYNTAX          INTEGER { green(1), red(2), yellow(3), ais(4), 
                        hwfailure(5) }
    ACCESS          read-only
    STATUS          mandatory
    DESCRIPTION     
            "The type of Alarm or failure which caused T1/E1 span to go out of service"
    ::= { sonusDsx1MIBNotificationsObjects 4 }

sonusDs1AdmnState OBJECT-TYPE
    SYNTAX          INTEGER { disabled(1), enabled(2), deleted(3), 
                        inservice(4), dryingUp(5) }
    ACCESS          read-only
    STATUS          mandatory
    DESCRIPTION     
            "The administrative state of the T1/E1 span."
    ::= { sonusDsx1MIBNotificationsObjects 5 }

sonusDs1Mask OBJECT-TYPE
    SYNTAX          OCTET STRING
--                       { ds11(0), ds12(1), ds13(2), ds14(3), ds15(4), 
--                         ds16(5), ds17(6), ds18(7), ds19(8), ds110(9), 
--                         ds111(10), ds112(11), ds113(12), ds114(13), 
--                         ds115(14), ds116(15), ds117(16), ds118(17), 
--                         ds119(18), ds120(19), ds121(20), ds122(21), 
--                         ds123(22), ds124(23), ds125(24), ds126(25), 
--                         ds127(26), ds128(27), ds129(28), ds130(29), 
--                         ds131(30), ds132(31), ds133(32), ds134(33), 
--                         ds135(34), ds136(35), ds137(36), ds138(37), 
--                         ds139(38), ds140(39), ds141(40), ds142(41), 
--                         ds143(42), ds144(43), ds145(44), ds146(45), 
--                         ds147(46), ds148(47), ds149(48), ds150(49), 
--                         ds151(50), ds152(51), ds153(52), ds154(53), 
--                         ds155(54), ds156(55), ds157(56), ds158(57), 
--                         ds159(58), ds160(59), ds161(60), ds162(61), 
--                         ds163(62), ds164(63), ds165(64), ds166(65), 
--                         ds167(66), ds168(67), ds169(68), ds170(69), 
--                         ds171(70), ds172(71), ds173(72), ds174(73), 
--                         ds175(74), ds176(75), ds177(76), ds178(77), 
--                         ds179(78), ds180(79), ds181(80), ds182(81), 
--                         ds183(82), ds184(83) }
    ACCESS          read-only
    STATUS          mandatory
    DESCRIPTION     
            "A bitmask of 84 DS1s."
    ::= { sonusDsx1MIBNotificationsObjects 6 }

sonusDs1ThresholdLevel OBJECT-TYPE
    SYNTAX          INTEGER { minor(1), major(2), critical(3) }
    ACCESS          read-only
    STATUS          mandatory
    DESCRIPTION     
            "Threshold level."
    ::= { sonusDsx1MIBNotificationsObjects 7 }

sonusDs1Q50TrmState OBJECT-TYPE
    SYNTAX          INTEGER { dcmeNormal(1), noTrunkAvail3khzAudio(2), 
                        no64kbpsCapacityAvail(3), maintenanceRelease(4) }
    ACCESS          read-only
    STATUS          mandatory
    DESCRIPTION     
            " "
    ::= { sonusDsx1MIBNotificationsObjects 9 }

sonusDs1ModeChangeReason OBJECT-TYPE
    SYNTAX          INTEGER { administrative(1), q50Maintenance(2) }
    ACCESS          read-only
    STATUS          mandatory
    DESCRIPTION     
            " "
    ::= { sonusDsx1MIBNotificationsObjects 10 }

sonusDsx1AdminChangeNotification TRAP-TYPE
    ENTERPRISE      sonusDsx1MIBNotifications
    VARIABLES       { sonusShelfIndex, sonusSlotIndex, sonusPortIndex, 
                      sonusDs3Index, sonusDs1Index, sonusDs1AdmnState, 
                      sonusEventDescription, sonusEventClass, 
                      sonusEventLevel, sonusSequenceId, sonusEventTime }
--     STATUS          mandatory
    DESCRIPTION     
            "A sonusDsx1AdminChangeNotification trap indicates the DS1 admin changes. 
             It is used to notify out-of-service, in-service, enabled and
             	 disabled."
    ::= 1

sonusDsx1OutOfServiceNotification TRAP-TYPE
    ENTERPRISE      sonusDsx1MIBNotifications
    VARIABLES       { sonusShelfIndex, sonusSlotIndex, sonusPortIndex, 
                      sonusDs3Index, sonusDs1Index, 
                      sonusDs1OutOfServiceReason, 
                      sonusDs1OutOfServiceType, sonusEventDescription, 
                      sonusEventClass, sonusEventLevel, sonusSequenceId, 
                      sonusEventTime }
--     STATUS          mandatory
    DESCRIPTION     
            "A sonusDsx1OutOfServiceNotification trap indicates that a T1/E1 span
             went out of service. The reason indicates the reason why and
             type indicates the type of failure or alarm."
    ::= 2

sonusDsx1ThresholdCrossingNotification TRAP-TYPE
    ENTERPRISE      sonusDsx1MIBNotifications
    VARIABLES       { sonusShelfIndex, sonusSlotIndex, sonusPortIndex, 
                      sonusDs3Index, sonusDs1Index, 
                      sonusDs1ThresholdType, sonusEventDescription, 
                      sonusEventClass, sonusEventLevel, sonusSequenceId, 
                      sonusEventTime }
--     STATUS          mandatory
    DESCRIPTION     
            "A sonusDsx1ThresholdCrossingNotification trap indicates that a T1/E1 span
             threshold has been crossed. The type indicates the type of threshold."
    ::= 3

sonusDsx1LineStatusChangeNotification TRAP-TYPE
    ENTERPRISE      sonusDsx1MIBNotifications
    VARIABLES       { sonusShelfIndex, sonusSlotIndex, sonusPortIndex, 
                      sonusDs3Index, sonusDs1Index, sonusDs1LineState, 
                      sonusEventDescription, sonusEventClass, 
                      sonusEventLevel, sonusSequenceId, sonusEventTime }
--     STATUS          mandatory
    DESCRIPTION     
            "A sonusDsx1LineStatusChangeNotification trap indicates the T1/E1 span state
             changes. It is used to notify T1/E1 span Alarms states."
    ::= 4

sonusDsx1AdminStateChangeNotification TRAP-TYPE
    ENTERPRISE      sonusDsx1MIBNotifications
    VARIABLES       { sonusShelfIndex, sonusSlotIndex, sonusPortIndex, 
                      sonusDs1Mask, sonusEventDescription, 
                      sonusEventClass, sonusEventLevel, sonusSequenceId, 
                      sonusEventTime }
--     STATUS          mandatory
    DESCRIPTION     
            "A sonusDsx1AdminStateChangeNotification trap indicates one or more
             DS1s in the specified Port have changed admin State. sonusDs1Mask
             is a bitmask indicating which DS1s are Enabled; a '1' in a bit
             position indicates the corresponding DS1 is Enabled, a '0' in a bit
             position indicates the corresponding DS1 is Disabled."
    ::= 5

sonusDsx1AdminModeChangeNotification TRAP-TYPE
    ENTERPRISE      sonusDsx1MIBNotifications
    VARIABLES       { sonusShelfIndex, sonusSlotIndex, sonusPortIndex, 
                      sonusDs1Mask, sonusEventDescription, 
                      sonusEventClass, sonusEventLevel, sonusSequenceId, 
                      sonusEventTime, sonusDs1ModeChangeReason }
--     STATUS          mandatory
    DESCRIPTION     
            "A sonusDsx1AdminModeChangeNotification trap indicates one or more
             DS1s in the specified Port have changed admin Mode. sonusDs1Mask
             is a bitmask indicating which DS1s are In Service; a '1' in a bit
             position indicates the corresponding DS1 is In Service, a '0' in a bit
             position indicates the corresponding DS1 is Out of Service."
    ::= 6

sonusDsx1AdminDryupNotification TRAP-TYPE
    ENTERPRISE      sonusDsx1MIBNotifications
    VARIABLES       { sonusShelfIndex, sonusSlotIndex, sonusPortIndex, 
                      sonusDs1Mask, sonusEventDescription, 
                      sonusEventClass, sonusEventLevel, sonusSequenceId, 
                      sonusEventTime, sonusDs1ModeChangeReason }
--     STATUS          mandatory
    DESCRIPTION     
            "A sonusDsx1AdminDryupNotification trap indicates one or more
             DS1s in the specified Port are Drying Up. sonusDs1Mask
             is a bitmask indicating which DS1s are Drying; a '1' in a bit
             position indicates the corresponding DS1 is Drying Up."
    ::= 7

sonusDsx1AlarmStateChangeNotification TRAP-TYPE
    ENTERPRISE      sonusDsx1MIBNotifications
    VARIABLES       { sonusShelfIndex, sonusSlotIndex, sonusPortIndex, 
                      sonusDs1Index, sonusDs1LineState, 
                      sonusEventDescription, sonusEventClass, 
                      sonusEventLevel, sonusSequenceId, sonusEventTime }
--     STATUS          mandatory
    DESCRIPTION     
            "A sonusDsx1AlarmStateChangeNotification trap indicates the alarm state of
             a T1/E1 span has changed."
    ::= 9

sonusDsx1Q50DcmeTrmStateChangeNotification TRAP-TYPE
    ENTERPRISE      sonusDsx1MIBNotifications
    VARIABLES       { sonusShelfIndex, sonusSlotIndex, sonusPortIndex, 
                      sonusDs1Index, sonusDs1Q50TrmState, 
                      sonusEventDescription, sonusEventClass, 
                      sonusEventLevel, sonusSequenceId, sonusEventTime }
--     STATUS          mandatory
    DESCRIPTION     
            " "
    ::= 11

END -- end of module SONUS-DS1-MIB.
