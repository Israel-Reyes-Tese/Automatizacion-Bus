--
-- This SMIv2 module has been generated by smidump 0.2-cvs. Do not edit.
--

RIVERSTONE-RS93X-AGENTCAP-MIB DEFINITIONS ::= BEGIN

IMPORTS
    aal5VccGroup, atmInterfaceConfGroup2, atmInterfaceIlmiVci, 
    atmInterfaceIlmiVpi, atmInterfaceMaxActiveVciBits, 
    atmInterfaceMaxActiveVpiBits, atmInterfaceMaxVccs, 
    atmInterfaceMaxVpcs, atmInterfaceMyNeighborIfName, 
    atmInterfaceMyNeighborIpAddress, atmTrafficDescrGroup2, 
    atmTrafficDescrParam1, atmTrafficDescrParam2, atmTrafficDescrParam3, 
    atmTrafficDescrParam4, atmTrafficDescrParam5, 
    atmTrafficDescrRowStatus, atmTrafficQoSClass, 
    atmVcPvcCrossConnectGroup, atmVccAalType, atmVclAdminStatus, 
    atmVclCrossConnectGroup, atmVclReceiveTrafficDescrIndex, 
    atmVclRowStatus, atmVclTransmitTrafficDescrIndex, 
    atmVpcTerminationGroup2
        FROM ATM-MIB
    atmAal5VclInPkts, atmAddrVclAddrType, atmHostGroup, 
    atmSigDescrParamAalSscsType, atmSigDescrParamAalType, 
    atmSigDescrParamBbcConnConf, atmSigDescrParamBhliInfo, 
    atmSigDescrParamBhliType, atmSigDescrParamBlliLayer2, 
    atmSigDescrParamBlliLayer3, atmSigDescrParamBlliOuiPid, 
    atmSigDescrParamBlliPktSize, atmSigDescrParamBlliSnapId, 
    atmSigDescrParamRowStatus, atmVclAddrRowStatus, atmVclAddrType, 
    atmVclGenSigDescrIndex
        FROM ATM2-MIB
    cbpAcctTableGroup
        FROM CISCO-BGP-POLICY-ACCOUNTING-MIB
    srpErrCntCurrGroup, srpErrCntIntGroup, srpErrorsCountersCurrentGroup, 
    srpErrorsCountersIntervalGroup, srpHostCountersCurrentGroup, 
    srpHostCountersIntervalGroup, srpIfGroup, srpIpsLockedOut, 
    srpIpsWaitToRestoreTimer, srpMACClockSourceMode, 
    srpMACCountPktsByDestAddress, srpMACCountPktsByDestinationFlag, 
    srpMACCountPktsBySourceAddress, srpMACCountPktsBySourceFlag, 
    srpMACCountersGroup, srpMACIpsMgmtRequestedMode, 
    srpMACRejectPktsByDestAddress, srpMACRejectPktsByDestFlag, 
    srpMACRejectPktsBySourceAddress, srpMACRejectPktsBySourceFlag, 
    srpMACSideGroup, srpMACTopologyTimer, srpNotificationsGroup, 
    srpPriorityThreshold, srpRingCountersCurrentGroup, 
    srpRingCountersIntervalGroup, srpRingTopologyMapGroup
        FROM CISCO-SRP-MIB
    lfapConfGroupV40
        FROM CTRON-LFAP-MIB
    capConfGroupV10
        FROM CTRON-SSR-CAPACITY-MIB
    configGroup20
        FROM CTRON-SSR-CONFIG-MIB
    hwConfGroupV30
        FROM CTRON-SSR-HARDWARE-MIB
    polGroupV11
        FROM CTRON-SSR-POLICY-MIB
    ssConfGroupV11
        FROM CTRON-SSR-SERVICE-STATUS-MIB
    pingCtlIfIndex, pingCtlMaxRows, pingCtlSourceAddress, 
    pingCtlSourceAddressType, pingCtlStorageType, pingCtlTargetAddress, 
    pingCtlTargetAddressType, pingGroup, pingNotificationsGroup, 
    pingTimeStampGroup
        FROM DISMAN-PING-MIB
    schedCalendarGroup, schedGroup, schedNotificationsGroup
        FROM DISMAN-SCHEDULE-MIB
    traceRouteCtlIfIndex, traceRouteCtlSourceAddress, 
    traceRouteCtlSourceAddressType, traceRouteCtlStorageType, 
    traceRouteCtlTargetAddress, traceRouteCtlTargetAddressType, 
    traceRouteGroup, traceRouteHopsTableGroup, 
    traceRouteNotificationsGroup, traceRouteTimeStampGroup
        FROM DISMAN-TRACEROUTE-MIB
    docsDevEventGroup
        FROM DOCS-CABLE-DEVICE-MIB
    docsIfBasicGroup, docsIfCmtsGroup, docsIfQosProfMaxTxBurst
        FROM DOCS-IF-MIB
    ds0ConfigGroup
        FROM DS0-MIB
    ds0BundleConfigGroup
        FROM DS0BUNDLE-MIB
    ds1ChanMappingGroup, ds1NearEndConfigGroup, 
    ds1NearEndOptionalConfigGroup, ds1NearEndStatisticsGroup, 
    dsx1Channelization, dsx1CircuitIdentifier, dsx1Fdl, dsx1LineCoding, 
    dsx1LineLength, dsx1LineStatusChangeTrapEnable, dsx1LineType, 
    dsx1LoopbackConfig, dsx1SendCode, dsx1SignalMode, 
    dsx1TransmitClockSource
        FROM DS1-MIB
    ds3NearEndConfigGroup, ds3NearEndOptionalConfigGroup, 
    ds3NearEndStatisticsGroup, dsx3Channelization, dsx3CircuitIdentifier, 
    dsx3Ds1ForRemoteLoop, dsx3LineCoding, dsx3LineLength, 
    dsx3LineStatusChangeTrapEnable, dsx3LineType, dsx3LoopbackConfig, 
    dsx3SendCode, dsx3TransmitClockSource
        FROM DS3-MIB
    entAliasLogicalIndexOrZero, entLPPhysicalIndex, entLastChangeTime, 
    entLogicalTAddress, entLogicalTDomain, entPhysicalAlias, 
    entPhysicalAssetID, entPhysicalSerialNum, entityGeneralGroup, 
    entityLogical2Group, entityMappingGroup, entityNotificationsGroup, 
    entityPhysical2Group, entityPhysicalGroup
        FROM ENTITY-MIB
    etherStats100MbsGroup
        FROM EtherLike-MIB
    frCircuitCommittedBurst, frCircuitExcessBurst, frCircuitGroup, 
    frCircuitLogicalIfIndex, frCircuitMulticast, frCircuitRowStatus, 
    frCircuitState, frCircuitThroughput, frDlcmiAddress, 
    frDlcmiAddressLen, frDlcmiErrorThreshold, frDlcmiFullEnquiryInterval, 
    frDlcmiMaxSupportedVCs, frDlcmiMonitoredEvents, frDlcmiMulticast, 
    frDlcmiPollingInterval, frDlcmiRowStatus, frDlcmiState, frErrGroup, 
    frPortGroup, frTrapGroup
        FROM FRAME-RELAY-DTE-MIB
    ifAdminStatus, ifAlias, ifCounterDiscontinuityGroup, 
    ifFixedLengthGroup, ifGeneralInformationGroup, ifHCFixedLengthGroup, 
    ifHCPacketGroup, ifLinkUpDownTrapEnable, ifOldObjectsGroup, 
    ifPacketGroup, ifRcvAddressGroup, ifStackGroup2, ifStackStatus, 
    ifVHCPacketGroup
        FROM IF-MIB
    igmpBaseMIBGroup, igmpRouterMIBGroup, igmpV2RouterMIBGroup
        FROM IGMP-STD-MIB
    ipCidrRouteIfIndex, ipCidrRouteInfo, ipCidrRouteMetric1, 
    ipCidrRouteMetric2, ipCidrRouteMetric3, ipCidrRouteMetric4, 
    ipCidrRouteMetric5, ipCidrRouteNextHopAS, ipCidrRouteStatus, 
    ipCidrRouteType, ipForwardCidrRouteGroup
        FROM IP-FORWARD-MIB
    icmpGroup, ipDefaultTTL, ipGroup
        FROM IP-MIB
    dot3adAggCollectorMaxDelay, dot3adAggGroup, 
    dot3adAggPartnerSystemPriority, dot3adAggPortDebugActorChangeCount, 
    dot3adAggPortDebugActorChurnCount, dot3adAggPortDebugActorChurnState, 
    dot3adAggPortDebugActorSyncTransitionCount, dot3adAggPortDebugGroup, 
    dot3adAggPortDebugLastRxTime, dot3adAggPortDebugMuxReason, 
    dot3adAggPortDebugMuxState, dot3adAggPortDebugPartnerChangeCount, 
    dot3adAggPortDebugPartnerChurnCount, 
    dot3adAggPortDebugPartnerChurnState, 
    dot3adAggPortDebugPartnerSyncTransitionCount, 
    dot3adAggPortDebugRxState, dot3adAggPortGroup, 
    dot3adAggPortListGroup, dot3adAggPortPartnerAdminKey, 
    dot3adAggPortPartnerAdminPort, dot3adAggPortPartnerAdminPortPriority, 
    dot3adAggPortPartnerAdminSystemID, 
    dot3adAggPortPartnerAdminSystemPriority, dot3adAggPortStatsGroup, 
    dot3adTablesLastChanged, dot3adTablesLastChangedGroup
        FROM LAG-MIB
    mplsHCInSegmentPerfGroup, mplsHCOutSegmentPerfGroup, 
    mplsInSegmentErrors, mplsInSegmentGroup, mplsInSegmentOwner, 
    mplsInSegmentRowStatus, mplsInSegmentStorageType, 
    mplsInSegmentTrafficParamPtr, mplsInterfaceFailedLabelLookup, 
    mplsInterfaceGroup, mplsInterfaceOutFragments, mplsLabelStackGroup, 
    mplsLabelStackLabel, mplsLabelStackRowStatus, 
    mplsLabelStackStorageType, mplsLsrNotificationGroup, 
    mplsOutSegmentErrors, mplsOutSegmentGroup, mplsOutSegmentOwner, 
    mplsOutSegmentTrafficParamPtr, mplsPerfGroup, mplsTrafficParamGroup, 
    mplsTrafficParamMaxBurstSize, mplsTrafficParamMaxRate, 
    mplsTrafficParamRowStatus, mplsTrafficParamStorageType, mplsXCGroup, 
    mplsXCLspId, mplsXCOwner
        FROM MPLS-LSR-MIB
    notificationLogConfigGroup, notificationLogLogGroup, 
    notificationLogStatsGroup
        FROM NOTIFICATION-LOG-MIB
    ospfAdminStat, ospfAreaAggregateEffect, ospfAreaAggregateGroup, 
    ospfAreaAggregateStatus, ospfAreaGroup, ospfAreaRangeEffect, 
    ospfAreaRangeMask, ospfAreaRangeStatus, ospfAreaStatus, 
    ospfAreaSummary, ospfAuthType, ospfBasicGroup, ospfDemandExtensions, 
    ospfExitOverflowInterval, ospfExtLsdbLimit, ospfHostMetric, 
    ospfHostStatus, ospfIfAdminStat, ospfIfAreaId, ospfIfAuthKey, 
    ospfIfAuthType, ospfIfDemand, ospfIfGroup, ospfIfHelloInterval, 
    ospfIfMetricGroup, ospfIfMetricValue, ospfIfMulticastForwarding, 
    ospfIfPollInterval, ospfIfRetransInterval, ospfIfRtrDeadInterval, 
    ospfIfRtrPriority, ospfIfStatus, ospfIfTransitDelay, ospfIfType, 
    ospfImportAsExtern, ospfMulticastExtensions, ospfNbmaNbrStatus, 
    ospfNbrGroup, ospfNbrPriority, ospfRouterId, ospfStubAreaGroup, 
    ospfStubMetric, ospfStubMetricType, ospfStubStatus, ospfTOSSupport, 
    ospfVirtIfAuthKey, ospfVirtIfAuthType, ospfVirtIfGroup, 
    ospfVirtIfHelloInterval, ospfVirtIfRetransInterval, 
    ospfVirtIfRtrDeadInterval, ospfVirtIfStatus, ospfVirtIfTransitDelay, 
    ospfVirtNbrGroup
        FROM OSPF-MIB
    ospfTrapControlGroup
        FROM OSPF-TRAP-MIB
    dot1dGmrpStatus, dot1dPortGarpJoinTime, dot1dPortGarpLeaveAllTime, 
    dot1dPortGarpLeaveTime, dot1dPortNumTrafficClasses, 
    dot1dTrafficClassesEnabled, pBridgeDefaultPriorityGroup, 
    pBridgeDevicePriorityGroup, pBridgeExtCapGroup, pBridgePortGarpGroup, 
    pBridgePriorityGroup
        FROM P-BRIDGE-MIB
    dot1qConstraintSetDefault, dot1qConstraintTypeDefault, 
    dot1qPortGvrpStatus, dot1qPvid, dot1qTpVlanPortHCInDiscards, 
    dot1qTpVlanPortHCInFrames, dot1qTpVlanPortHCOutFrames, 
    dot1qTpVlanPortInDiscards, dot1qTpVlanPortInFrames, 
    dot1qTpVlanPortInOverflowDiscards, dot1qTpVlanPortInOverflowFrames, 
    dot1qTpVlanPortOutFrames, dot1qTpVlanPortOutOverflowFrames, 
    dot1qVlanStaticEgressPorts, dot1qVlanStaticUntaggedPorts, 
    qBridgeBaseGroup, qBridgeFdbMulticastGroup, qBridgeFdbUnicastGroup, 
    qBridgePortGroup, qBridgeVlanGroup, qBridgeVlanStaticGroup
        FROM Q-BRIDGE-MIB
    radiusAccClientMIBGroup
        FROM RADIUS-ACC-CLIENT-MIB
    radiusAuthClientMIBGroup
        FROM RADIUS-AUTH-CLIENT-MIB
    rip2GlobalGroup, rip2IfConfAuthKey, rip2IfConfAuthType, 
    rip2IfConfDefaultMetric, rip2IfConfDomain, rip2IfConfGroup, 
    rip2IfConfReceive, rip2IfConfSend, rip2IfConfSrcAddress, 
    rip2IfConfStatus, rip2IfStatGroup, rip2IfStatStatus, rip2PeerGroup
        FROM RIPv2-MIB
    rsAtmFdbBaseGroup
        FROM RIVERSTONE-ATM-MIB
    rsBootInfoGroup, rsCfgFileName, rsCfgFileTransferProtocol, 
    rsCfgHostAddress, rsCfgHostAddressType, rsCfgMaxActiveChangeLines, 
    rsCfgMaxActiveChangeLinesPerSession, rsCfgMaxActiveChangeSessions, 
    rsChangeLogGroup, rsConfigGroup, rsConfigNotificationControlGroup, 
    rsConfigNotificationGroup
        FROM RIVERSTONE-CONFIG-MIB
    rsDhcpGroup1
        FROM RIVERSTONE-DHCP-MIB
    rsImageMibAddDeleteChooseGroup, rsImageMibListGroup, 
    rsImageMibStatusAndErrorGroup
        FROM RIVERSTONE-IMAGE-MIB
    rsChassisGroup, rsEnvGroup, rsModuleGroup
        FROM RIVERSTONE-INVENTORY-MIB
    rsLfapAgentCfgGroup, rsLfapAgentStateGroup, rsLfapBatchInterval, 
    rsLfapBatchSize, rsLfapLostContactInterval, rsLfapMaxTxQueueSize, 
    rsLfapPollInterval, rsLfapServerRetryInterval, 
    rsLfapServerStaticGroup, rsLfapStatsGroup, rsLfapTaskPriority, 
    rsRunLfapSelfTest
        FROM RIVERSTONE-LFAP-MIB
    rsMPLSLSRExtensionGroup, rsMPLSNotificationControlGroup, 
    rsMPLSNotificationGroup
        FROM RIVERSTONE-MPLS-MIB
    rsQueuePropertiesGroup, rsQueueStatsGroup
        FROM RIVERSTONE-QUEUE-MIB
    riverstoneAgentCapabilities
        FROM RIVERSTONE-SMI-MIB
    rsSnmpBaseGroup
        FROM RIVERSTONE-SNMP-MIB
    rsStpBaseGroup, rsStpStatus
        FROM RIVERSTONE-STP-MIB
    rsPortVlanHCStatsGroup, rsPortVlanStatsGroup, 
    rsPortVlanStatsOverflowGroup
        FROM RIVERSTONE-VLAN-EXTENSIONS-MIB
    rmonAlarmGroup, rmonEtherStatsGroup, rmonEthernetHistoryGroup, 
    rmonEventGroup, rmonFilterGroup, rmonHistoryControlGroup, 
    rmonHostGroup, rmonHostTopNGroup, rmonMatrixGroup, 
    rmonNotificationGroup, rmonPacketCaptureGroup
        FROM RMON-MIB
    addressMapGroup, alHostGroup, alMatrixGroup, 
    filterProtocolDirDataLocalIndex, filterProtocolDirLocalIndex, 
    nlHostGroup, nlMatrixGroup, probeConfigurationGroup, 
    probeInformationGroup, protocolDirectoryGroup, 
    protocolDistributionGroup, rmon1EthernetEnhancementGroup, 
    usrHistoryGroup
        FROM RMON2-MIB
    snmpBasicNotificationsGroup, snmpCommunityGroup, snmpGroup, 
    snmpObsoleteGroup, systemGroup
        FROM SNMPv2-MIB
    Integer32, MODULE-IDENTITY, Unsigned32
        FROM SNMPv2-SMI
    DisplayString
        FROM SNMPv2-TC
    sonetFarEndLineStuff2, sonetFarEndPathStuff2, sonetLineStuff2, 
    sonetMediumCircuitIdentifier, sonetMediumInvalidIntervals, 
    sonetMediumLineCoding, sonetMediumLineType, 
    sonetMediumLoopbackConfig, sonetMediumStuff2, sonetMediumType, 
    sonetPathCurrentWidth, sonetPathStuff2, sonetSESthresholdSet, 
    sonetSectionStuff2
        FROM SONET-MIB
    tcpConnState, tcpGroup
        FROM TCP-MIB
    udpGroup
        FROM UDP-MIB
    vrrpAssoIpAddrRowStatus, vrrpNotificationGroup, vrrpOperAdminState, 
    vrrpOperAdvertisementInterval, vrrpOperAuthKey, vrrpOperAuthType, 
    vrrpOperGroup, vrrpOperPreemptMode, vrrpOperPrimaryIpAddr, 
    vrrpOperPriority, vrrpOperProtocol, vrrpOperRowStatus, 
    vrrpStatsGroup, vrrpStatsPacketLengthErrors, vrrpTrapGroup
        FROM VRRP-MIB;

rstoneRs93xAgentCapabilityMIB MODULE-IDENTITY
    LAST-UPDATED    "200211250000Z"
    ORGANIZATION    
            "Riverstone Networks, Inc"
    CONTACT-INFO    
            "Riverstone Networks, Inc
             5200 Great America Parkway
             Santa Clara CA USA 95054
             PHONE:+1 408.878.6500
             EMAIL: nms-eng@riverstonenet.com
             WEB: http://www.riverstonenet.com"
    DESCRIPTION     
            "This module defines agent capabilities for Riverstone RS RapidOS 
             Software Product version 9.3.x."
    REVISION        "200211150000Z"
    DESCRIPTION     
            "Created agent capabilities mib for version 9.3.x of 
             Riverstone RS RapidOS software product. For agent capabilities of 
             	  older versions of RapidOS, refer to rstone-rs-agent-cap-mib.txt and
             ssr-agent-capabilities mib"
    ::= { riverstoneAgentCapabilities 93 }


rsCapability OBJECT IDENTIFIER
    ::= { rstoneRs93xAgentCapabilityMIB 1 }

-- This has been an SMIv2 AGENT-CAPABILITIES node:
rs93x OBJECT-IDENTITY
    STATUS          current
    DESCRIPTION     
            "Firmware Release 9.3.x for Riverstone  RS RapidOS product line.
             This firmware version supports the following new features - 
             Layer 2 VPLS based on Lasserre-Compella draft, 
             RFC 2549 MPLS-BGP VPN support, ATM VC support for Martini VLL, and 
             HRT enhancements. New hardware includes ES 10170 with Gen5 GE and 
             Gen 4 FE blades, CM5 for RS 8000,
             OC3 and OC48 PoS/MPLS blades for RS 38000, PoS/MPLS blade for RS 3000,
             and FE Gen5 blades for RS 38000, RS 8000 and RS 3000.
             
             Changes in Existing MIB Modules include:
                 DISMAN-PING-MIB
             New MIB modules include:
                 RIVERSTONE-MPLS-MIB
                 RIVERSTONE-QUEUE-MIB
                 RIVERSTONE-VLAN-EXTENSIONS-MIB (introduced in release 9.1.0.1)
             
             "
    REFERENCE       
            "http://www.riverstonenet.com/products"
    ::= { rsCapability 9 }

END -- end of module RIVERSTONE-RS93X-AGENTCAP-MIB.
