--
-- This SMIv2 module has been generated by smidump 0.2-cvs. Do not edit.
--

SONUS-HA-RAC-MIB DEFINITIONS ::= BEGIN

IMPORTS
    InetAddress
        FROM INET-ADDRESS-MIB
    sysName
        FROM SNMPv2-MIB
    MODULE-IDENTITY, NOTIFICATION-TYPE, OBJECT-TYPE
        FROM SNMPv2-SMI
    TEXTUAL-CONVENTION
        FROM SNMPv2-TC
    sonusEventClass, sonusEventDescription, sonusEventLevel, 
    sonusEventTime
        FROM SONUS-COMMON-MIB
    sonusHostID
        FROM SONUS-HOST-MIB
    sonusServicesMIBs
        FROM SONUS-SMI;

sonusHARACMIB MODULE-IDENTITY
    LAST-UPDATED    "201308040000Z"
    ORGANIZATION    
            "Sonus Networks, Inc."
    CONTACT-INFO    
            "   Customer Support
             Sonus Networks, Inc.
             250 Apollo Drive
             Chelmsford, MA 01824
             USA
             
             Tel: 978-614-8100
             Fax: 978-614-8609"
    DESCRIPTION     
            "The MIB Module for Sonus High Availability RAC Management."
    ::= { sonusServicesMIBs 3339 }


SonusHARACState ::= TEXTUAL-CONVENTION
    STATUS          current
    DESCRIPTION     
            "The high availability designation of the host.  This is an operational state."
    SYNTAX          INTEGER { offline(0), active(1), standby(2), 
                        standby-intent(3) }

sonusHARACMIBObjects OBJECT IDENTIFIER
    ::= { sonusHARACMIB 1 }

sonusHARACMIBNotifications OBJECT IDENTIFIER
    ::= { sonusHARACMIB 2 }

sonusHARACMIBNotificationsPrefix OBJECT IDENTIFIER
    ::= { sonusHARACMIBNotifications 0 }

sonusHARACMIBNotificationsObjects OBJECT IDENTIFIER
    ::= { sonusHARACMIBNotifications 1 }

sonusRACProcess OBJECT IDENTIFIER
    ::= { sonusHARACMIBNotificationsObjects 11 }

sonusHARACPrevState OBJECT-TYPE
    SYNTAX          SonusHARACState
    MAX-ACCESS      read-only
    STATUS          current
    DESCRIPTION     
            "The previous high availability state of this host."
    ::= { sonusHARACMIBNotificationsObjects 12 }

sonusHARACNewState OBJECT-TYPE
    SYNTAX          SonusHARACState
    MAX-ACCESS      read-only
    STATUS          current
    DESCRIPTION     
            "The new high availability state of this host."
    ::= { sonusHARACMIBNotificationsObjects 13 }

sonusHARACClusterName OBJECT IDENTIFIER
    ::= { sonusHARACMIBNotificationsObjects 14 }

sonusHARACNodeName OBJECT IDENTIFIER
    ::= { sonusHARACMIBNotificationsObjects 15 }

sonusHARACFailoverReason OBJECT IDENTIFIER
    ::= { sonusHARACMIBNotificationsObjects 16 }

sonusHARACEvicted OBJECT IDENTIFIER
    ::= { sonusHARACMIBNotificationsObjects 26 }

sonusRACHostID OBJECT IDENTIFIER
    ::= { sonusHARACMIBNotificationsObjects 27 }

sonusRACResource OBJECT IDENTIFIER
    ::= { sonusHARACMIBNotificationsObjects 28 }

sonusHARACArbitratorIp OBJECT-TYPE
    SYNTAX          InetAddress
    MAX-ACCESS      read-only
    STATUS          current
    DESCRIPTION     
            "The IP address of the Arbitrator instance for whom the trap is raised."
    ::= { sonusHARACMIBNotificationsObjects 29 }

sonusHARACProcessDownNotification NOTIFICATION-TYPE
    OBJECTS         { sonusHostID, sonusEventDescription, 
                      sonusEventClass, sonusEventLevel, sonusEventTime, 
                      sonusRACProcess, sonusRACHostID }
    STATUS          current
    DESCRIPTION     
            "Could not start clusterware process"
    ::= { sonusHARACMIBNotificationsPrefix 1 }

sonusHARACProcessUpNotification NOTIFICATION-TYPE
    OBJECTS         { sonusHostID, sonusEventDescription, 
                      sonusEventClass, sonusEventLevel, sonusEventTime, 
                      sonusRACProcess, sonusRACHostID }
    STATUS          current
    DESCRIPTION     
            "Successfully started clusterware process"
    ::= { sonusHARACMIBNotificationsPrefix 2 }

sonusHARACStateChangeNotification NOTIFICATION-TYPE
    OBJECTS         { sonusHARACPrevState, sonusHARACNewState, 
                      sonusHARACClusterName, sonusHARACNodeName }
    STATUS          current
    DESCRIPTION     
            "Insight State Change notification"
    ::= { sonusHARACMIBNotificationsPrefix 3 }

sonusHARACFailoverInitiatedNotification NOTIFICATION-TYPE
    OBJECTS         { sonusHARACFailoverReason, sonusHARACClusterName }
    STATUS          current
    DESCRIPTION     
            "RAC relocate initiated notification"
    ::= { sonusHARACMIBNotificationsPrefix 4 }

sonusHARACFailoverStandbyTimeoutNotification NOTIFICATION-TYPE
    OBJECTS         { sonusHARACClusterName, sonusHARACNodeName }
    STATUS          current
    DESCRIPTION     
            "RAC relocate timedout notification"
    ::= { sonusHARACMIBNotificationsPrefix 5 }

sonusHARACResourceDownNotification NOTIFICATION-TYPE
    OBJECTS         { sonusHostID, sonusEventDescription, 
                      sonusEventClass, sonusEventLevel, sonusEventTime, 
                      sonusRACResource, sonusRACHostID }
    STATUS          current
    DESCRIPTION     
            "HA RAC Resource down"
    ::= { sonusHARACMIBNotificationsPrefix 6 }

sonusHARACResourceUpNotification NOTIFICATION-TYPE
    OBJECTS         { sonusHostID, sonusEventDescription, 
                      sonusEventClass, sonusEventLevel, sonusEventTime, 
                      sonusRACResource, sonusRACHostID }
    STATUS          current
    DESCRIPTION     
            "HA RAC Resource up"
    ::= { sonusHARACMIBNotificationsPrefix 7 }

sonusHARACNodeShutdownInitiated NOTIFICATION-TYPE
    OBJECTS         { sonusHostID, sonusEventDescription, 
                      sonusEventClass, sonusEventLevel, sonusEventTime, 
                      sonusRACHostID }
    STATUS          current
    DESCRIPTION     
            "HA RAC Shutdown initiated"
    ::= { sonusHARACMIBNotificationsPrefix 8 }

sonusHARACNodeShutdownSucceeded NOTIFICATION-TYPE
    OBJECTS         { sonusHostID, sonusEventDescription, 
                      sonusEventClass, sonusEventLevel, sonusEventTime, 
                      sonusRACHostID }
    STATUS          current
    DESCRIPTION     
            "HA RAC Shutdown succeeded"
    ::= { sonusHARACMIBNotificationsPrefix 9 }

sonusHARACNodeShutdownFailed NOTIFICATION-TYPE
    OBJECTS         { sonusHostID, sonusEventDescription, 
                      sonusEventClass, sonusEventLevel, sonusEventTime, 
                      sonusRACHostID }
    STATUS          current
    DESCRIPTION     
            "HA RAC Shutdown Failed"
    ::= { sonusHARACMIBNotificationsPrefix 10 }

sonusHARACNodeStartupInitiated NOTIFICATION-TYPE
    OBJECTS         { sonusHostID, sonusEventDescription, 
                      sonusEventClass, sonusEventLevel, sonusEventTime, 
                      sonusRACHostID }
    STATUS          current
    DESCRIPTION     
            "HA RAC StartUp initiated"
    ::= { sonusHARACMIBNotificationsPrefix 11 }

sonusHARACNodeStartupSucceeded NOTIFICATION-TYPE
    OBJECTS         { sonusHostID, sonusEventDescription, 
                      sonusEventClass, sonusEventLevel, sonusEventTime, 
                      sonusRACHostID }
    STATUS          current
    DESCRIPTION     
            "HA RAC StartUp succeeded"
    ::= { sonusHARACMIBNotificationsPrefix 12 }

sonusHARACNodeStartupFailed NOTIFICATION-TYPE
    OBJECTS         { sonusHostID, sonusEventDescription, 
                      sonusEventClass, sonusEventLevel, sonusEventTime, 
                      sonusRACHostID }
    STATUS          current
    DESCRIPTION     
            "HA RAC StartUp failed"
    ::= { sonusHARACMIBNotificationsPrefix 13 }

sonusHARACFailoverSuccessful NOTIFICATION-TYPE
    OBJECTS         { sonusHostID, sonusEventDescription, 
                      sonusEventClass, sonusEventLevel, sonusEventTime, 
                      sonusRACHostID }
    STATUS          current
    DESCRIPTION     
            "HA RAC failover successful"
    ::= { sonusHARACMIBNotificationsPrefix 14 }

sonusHARACFailoverFailed NOTIFICATION-TYPE
    OBJECTS         { sonusHostID, sonusEventDescription, 
                      sonusEventClass, sonusEventLevel, sonusEventTime, 
                      sonusRACHostID }
    STATUS          current
    DESCRIPTION     
            "HA RAC failover failed"
    ::= { sonusHARACMIBNotificationsPrefix 15 }

sonusHARACArbitratorDownNotification NOTIFICATION-TYPE
    OBJECTS         { sysName, sonusEventTime, sonusEventDescription, 
                      sonusEventLevel, sonusHARACArbitratorIp }
    STATUS          current
    DESCRIPTION     
            "Arbitrator instance down"
    ::= { sonusHARACMIBNotificationsPrefix 16 }

sonusHARACArbitratorUpNotification NOTIFICATION-TYPE
    OBJECTS         { sysName, sonusEventTime, sonusEventDescription, 
                      sonusEventLevel, sonusHARACArbitratorIp }
    STATUS          current
    DESCRIPTION     
            "Arbitrator instance up"
    ::= { sonusHARACMIBNotificationsPrefix 17 }

END -- end of module SONUS-HA-RAC-MIB.
