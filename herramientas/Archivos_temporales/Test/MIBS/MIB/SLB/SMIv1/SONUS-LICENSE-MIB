--
-- This SMIv1 module has been generated by smidump 0.2-cvs. Do not edit.
--

SONUS-LICENSE-MIB DEFINITIONS ::= BEGIN

IMPORTS
    OBJECT-TYPE
        FROM RFC-1212
    Counter, Gauge, IpAddress
        FROM RFC1155-SMI
    DateAndTime, RowStatus
        FROM SNMPv2-TC
    sonusCommonSoftwarePlatformServicesMIBs
        FROM SONUS-SMI;

sonusLicenseMIB OBJECT IDENTIFIER
    ::= { sonusCommonSoftwarePlatformServicesMIBs 16 }

-- sonusLicenseMIB MODULE-IDENTITY
--     LAST-UPDATED    "201212310000Z"
--     ORGANIZATION    
--             "Ribbon Communications, Inc."
--     CONTACT-INFO    
--             "Customer Support        
--              Ribbon Communications, Inc. 
--              4 Technology Park Drive 
--              Westford, MA 01886      
--              USA                     
--                                      
--              Tel: 978-614-8100       
--              Fax: 978-614-8609"
--     DESCRIPTION     
--             "The MIB module for Sonus License."
--     REVISION        "201212310000Z"
--     DESCRIPTION     
--             "Auto generated MIB."
--     ::= { sonusCommonSoftwarePlatformServicesMIBs 16 }


String ::=
    OCTET STRING

-- String ::= TEXTUAL-CONVENTION
--     DISPLAY-HINT    "1t"
--     STATUS          mandatory
--     DESCRIPTION     
--             "xs:string"
--     SYNTAX          OCTET STRING

AuthSignatureType ::=
    OCTET STRING (SIZE(0..500))

-- AuthSignatureType ::= TEXTUAL-CONVENTION
--     DISPLAY-HINT    "1t"
--     STATUS          mandatory
--     DESCRIPTION     
--             ""
--     SYNTAX          OCTET STRING (SIZE(0..500))

HashType ::=
    OCTET STRING (SIZE(0..40))

-- HashType ::= TEXTUAL-CONVENTION
--     DISPLAY-HINT    "1t"
--     STATUS          mandatory
--     DESCRIPTION     
--             ""
--     SYNTAX          OCTET STRING (SIZE(0..40))

SonusFeatureType ::=
    INTEGER { onoff(1), counted(2) }

-- SonusFeatureType ::= TEXTUAL-CONVENTION
--     STATUS          mandatory
--     DESCRIPTION     
--             ""
--     SYNTAX          INTEGER
--                       { onoff(1), counted(2) }

LicenseBundleString ::=
    OCTET STRING (SIZE(0..20000))

-- LicenseBundleString ::= TEXTUAL-CONVENTION
--     DISPLAY-HINT    "1t"
--     STATUS          mandatory
--     DESCRIPTION     
--             ""
--     SYNTAX          OCTET STRING (SIZE(0..20000))

SonusLicenseBundleType ::=
    INTEGER { nodeLocked(0), legacy(1), local(2), domain(3) }

-- SonusLicenseBundleType ::= TEXTUAL-CONVENTION
--     STATUS          mandatory
--     DESCRIPTION     
--             ""
--     SYNTAX          INTEGER
--                       { nodeLocked(0), legacy(1), local(2), domain(3) }

sonusLicense OBJECT IDENTIFIER
    ::= { sonusLicenseMIB 1 }

sonusLicenseBundleTable OBJECT-TYPE
    SYNTAX          SEQUENCE OF SonusLicenseBundleEntry
    ACCESS          not-accessible
    STATUS          mandatory
    DESCRIPTION     
            "
             The license bundle.
             "
    ::= { sonusLicense 1 }

sonusLicenseBundleEntry OBJECT-TYPE
    SYNTAX          SonusLicenseBundleEntry
    ACCESS          not-accessible
    STATUS          mandatory
    DESCRIPTION     
            ""
    INDEX           { IMPLIED sonusLicenseBundleBundleName }
    ::= { sonusLicenseBundleTable 1 }

SonusLicenseBundleEntry ::=
    SEQUENCE {
        sonusLicenseBundleBundleName    String,
        sonusLicenseBundleBundleString  LicenseBundleString,
        sonusLicenseBundleRowstatus     RowStatus,
        sonusLicenseBundleBundleType    SonusLicenseBundleType,
        sonusLicenseBundleInstallDate   DateAndTime
    }

sonusLicenseBundleBundleName OBJECT-TYPE
    SYNTAX          String (SIZE(0..23))
    ACCESS          not-accessible
    STATUS          mandatory
    DESCRIPTION     
            "
             This indicates the license identifier for license bundle.
             "
    ::= { sonusLicenseBundleEntry 1 }

sonusLicenseBundleBundleString OBJECT-TYPE
    SYNTAX          LicenseBundleString
    ACCESS          read-write
    STATUS          mandatory
    DESCRIPTION     
            "
             This object indicates the license bundle XML string.
             "
    ::= { sonusLicenseBundleEntry 2 }

sonusLicenseBundleRowstatus OBJECT-TYPE
    SYNTAX          RowStatus
    ACCESS          read-write
    STATUS          mandatory
    DESCRIPTION     
            ""
    ::= { sonusLicenseBundleEntry 3 }

sonusLicenseBundleBundleType OBJECT-TYPE
    SYNTAX          SonusLicenseBundleType
    ACCESS          read-write
    STATUS          mandatory
    DESCRIPTION     
            "
             This indicates the license type of the bundle string
             "
    DEFVAL          { nodeLocked }
    ::= { sonusLicenseBundleEntry 4 }

sonusLicenseBundleInstallDate OBJECT-TYPE
    SYNTAX          DateAndTime
    ACCESS          read-write
    STATUS          mandatory
    DESCRIPTION     
            "
             This date the license was installed
             "
    ::= { sonusLicenseBundleEntry 5 }

sonusLicenseLicenseFeaturesInfoTable OBJECT-TYPE
    SYNTAX          SEQUENCE OF SonusLicenseLicenseFeaturesInfoEntry
    ACCESS          not-accessible
    STATUS          mandatory
    DESCRIPTION     
            "
             The features allowed  by this application
             "
    ::= { sonusLicense 2 }

sonusLicenseLicenseFeaturesInfoEntry OBJECT-TYPE
    SYNTAX          SonusLicenseLicenseFeaturesInfoEntry
    ACCESS          not-accessible
    STATUS          mandatory
    DESCRIPTION     
            ""
    INDEX           { sonusLicenseLicenseFeaturesInfoFeatureName }
    ::= { sonusLicenseLicenseFeaturesInfoTable 1 }

SonusLicenseLicenseFeaturesInfoEntry ::=
    SEQUENCE {
        sonusLicenseLicenseFeaturesInfoFeatureName          String,
        sonusLicenseLicenseFeaturesInfoFeatureType          SonusFeatureType
    }

sonusLicenseLicenseFeaturesInfoFeatureName OBJECT-TYPE
    SYNTAX          String (SIZE(0..23))
    ACCESS          not-accessible
    STATUS          mandatory
    DESCRIPTION     
            "
             This indicates feature name
             "
    ::= { sonusLicenseLicenseFeaturesInfoEntry 1 }

sonusLicenseLicenseFeaturesInfoFeatureType OBJECT-TYPE
    SYNTAX          SonusFeatureType
    ACCESS          read-write
    STATUS          mandatory
    DESCRIPTION     
            "
             The type of license
             "
    ::= { sonusLicenseLicenseFeaturesInfoEntry 2 }

END -- end of module SONUS-LICENSE-MIB.
