--
-- This SMIv1 module has been generated by smidump 0.2-cvs. Do not edit.
--

SONUS-NODE-RESOURCES-MIB DEFINITIONS ::= BEGIN

IMPORTS
    AtmAddr
        FROM ATM-TC-MIB
    Ipv6Address
        FROM IPV6-TC
    OBJECT-TYPE
        FROM RFC-1212
    TRAP-TYPE
        FROM RFC-1215
    Counter, Gauge, IpAddress
        FROM RFC1155-SMI
    PhysAddress, RowStatus, TruthValue
        FROM SNMPv2-TC
    sonusEventClass, sonusEventDescription, sonusEventLevel, 
    sonusEventTime, sonusSequenceId
        FROM SONUS-COMMON-MIB
    sonusResourcesMIBs
        FROM SONUS-SMI
    SonusAdminState, SonusBoolean, SonusName, SonusNameReference, 
    SonusShelfIndex, SonusSlotIndex, SonusSupportFlag
        FROM SONUS-TC;

sonusNodeResourcesMIB OBJECT IDENTIFIER
    ::= { sonusResourcesMIBs 2 }

-- sonusNodeResourcesMIB MODULE-IDENTITY
--     LAST-UPDATED    "201510210000Z"
--     ORGANIZATION    
--             "Sonus Networks, Inc."
--     CONTACT-INFO    
--             "   Customer Support    
--              Sonus Networks, Inc.
--              7 Technology Park Drive
--              Westford, MA 01886
--              USA
--              
--              Tel: 978-614-8100
--              Fax: 978-614-8609"
--     DESCRIPTION     
--             "The MIB Module for Node Resources Management."
--     ::= { sonusResourcesMIBs 2 }


sonusNodeResourcesMIBObjects OBJECT IDENTIFIER
    ::= { sonusNodeResourcesMIB 1 }

sonusServProfile OBJECT IDENTIFIER
    ::= { sonusNodeResourcesMIBObjects 1 }

sonusServProfileNextIndex OBJECT-TYPE
    SYNTAX          INTEGER
    ACCESS          read-only
    STATUS          deprecated
    DESCRIPTION     
            "This field is deprecated. The next valid index to use when creating an entry in
             the sonusServProfileTable."
    ::= { sonusServProfile 1 }

sonusServProfileTable OBJECT-TYPE
    SYNTAX          SEQUENCE OF SonusServProfileEntry
    ACCESS          not-accessible
    STATUS          deprecated
    DESCRIPTION     
            "This field is deprecated. This table specifies the service profile list for the node."
    ::= { sonusServProfile 2 }

sonusServProfileEntry OBJECT-TYPE
    SYNTAX          SonusServProfileEntry
    ACCESS          not-accessible
    STATUS          deprecated
    DESCRIPTION     
            "This field is deprecated. "
    INDEX           { sonusServProfileIndex }
    ::= { sonusServProfileTable 1 }

SonusServProfileEntry ::=
    SEQUENCE {
        sonusServProfileIndex           INTEGER,
        sonusServProfileState           INTEGER,
        sonusServProfileName            SonusName,
        sonusServProfileType            INTEGER,
        sonusServProfileVCktEncoding    INTEGER,
        sonusServProfileVCktBandwidth   INTEGER,
        sonusServProfileVCktNecEnable   INTEGER,
        sonusServProfileVPktEncoding    INTEGER,
        sonusServProfileVPktFrameSize   INTEGER,
        sonusServProfileVPktFramesPerPacket   INTEGER,
        sonusServProfileVPktMaxNetworkJitter    INTEGER,
        sonusServProfileVPktTosValue    INTEGER,
        sonusServProfileCttTestType     INTEGER,
        sonusServProfileCttTimeout      INTEGER,
        sonusServProfileCttMinDetectTime INTEGER,
        sonusServProfileCttMinReleaseTime INTEGER,
        sonusServProfileCapability      INTEGER,
        sonusServProfileDPktRestrictedCfg INTEGER,
        sonusServProfileDPktRtpPayloadType  INTEGER,
        sonusServProfileDPktMaxNetworkJitter    INTEGER,
        sonusServProfileRowStatus       RowStatus
    }

sonusServProfileIndex OBJECT-TYPE
    SYNTAX          INTEGER
    ACCESS          read-only
    STATUS          deprecated
    DESCRIPTION     
            "This field is deprecated. Identifies the target service profile entry."
    ::= { sonusServProfileEntry 1 }

sonusServProfileState OBJECT-TYPE
    SYNTAX          INTEGER { disabled(1), enabled(2) }
    ACCESS          read-write
    STATUS          deprecated
    DESCRIPTION     
            "This field is deprecated. The administrative state of this service profile entry."
    DEFVAL          { disabled }
    ::= { sonusServProfileEntry 2 }

sonusServProfileName OBJECT-TYPE
    SYNTAX          SonusName
    ACCESS          read-write
    STATUS          deprecated
    DESCRIPTION     
            "This field is deprecated. The user name of this service profile."
    ::= { sonusServProfileEntry 3 }

sonusServProfileType OBJECT-TYPE
    SYNTAX          INTEGER { circuit(1), packet(2) }
    ACCESS          read-write
    STATUS          deprecated
    DESCRIPTION     
            "This field is deprecated. The type of endpoint (circuit or packet) supported by this service profile.
             Circuit endpoints support all the VCkt and VPkt profile parameters for echo
             cancellation and packetization. Packet endpoints support only the VPkt
             parameters for packetization."
    DEFVAL          { circuit }
    ::= { sonusServProfileEntry 4 }

sonusServProfileVCktEncoding OBJECT-TYPE
    SYNTAX          INTEGER { g711ulaw(1), g711alaw(2), none(5) }
    ACCESS          read-write
    STATUS          deprecated
    DESCRIPTION     
            "This field is deprecated. The audio encoding method to be performed on the voice data
             received from, and destined to the PSTN. The default encoding
             method is G.711 Ulaw."
    DEFVAL          { g711ulaw }
    ::= { sonusServProfileEntry 5 }

sonusServProfileVCktBandwidth OBJECT-TYPE
    SYNTAX          INTEGER (1..24)
    ACCESS          read-write
    STATUS          deprecated
    DESCRIPTION     
            "This field is deprecated. The number of DS0 channels to group for Nx64 connections. 
             Valid entries are 1 to 24 channels, allowing up to a 
             complete set of T1 channels to be grouped at a single
             connection. The default bandwidth is 1 channel."
    DEFVAL          { 1 }
    ::= { sonusServProfileEntry 6 }

sonusServProfileVCktNecEnable OBJECT-TYPE
    SYNTAX          INTEGER { disabled(1), enabled(2) }
    ACCESS          read-write
    STATUS          deprecated
    DESCRIPTION     
            "This field is deprecated. Specifies whether Network Echo Cancellation (NEC) is 
             enabled for the channel. When enabled, NEC is enabled
             acording to the appropriate NEC configuration parameters.
             When disabled, the Voice Packet Assembler/Disassember (VPAD)
             operates in a circuit emulation mode."
    DEFVAL          { enabled }
    ::= { sonusServProfileEntry 7 }

sonusServProfileVPktEncoding OBJECT-TYPE
    SYNTAX          INTEGER { g711ulaw(1), g711alaw(2), g7231(3), 
                        g729a(4), none(5) }
    ACCESS          read-write
    STATUS          deprecated
    DESCRIPTION     
            "This field is deprecated. The audio encoding method to be performed on the packet data
             received from, and destined to the IP network. The default 
             encoding method is G.711 Ulaw."
    DEFVAL          { g711ulaw }
    ::= { sonusServProfileEntry 8 }

sonusServProfileVPktFrameSize OBJECT-TYPE
    SYNTAX          INTEGER
    ACCESS          read-write
    STATUS          deprecated
    DESCRIPTION     
            "This field is deprecated. Specifies the number of samples per frame. For G.711
             encoding mode, value must be a multiple of 8 samples.
             For G.723 encoding mode, value must be a multiple of
             240 samples. For G.729A, value must be a multiple of
             80 samples. Note that 8 samples represent one millisecond
             of voice data. 
             
             A value of 0 specifies a frame size equal to the minimum 
             for the encoding method (e.g 8 samples for G.711)"
    DEFVAL          { 8 }
    ::= { sonusServProfileEntry 9 }

sonusServProfileVPktFramesPerPacket OBJECT-TYPE
    SYNTAX          INTEGER
    ACCESS          read-write
    STATUS          deprecated
    DESCRIPTION     
            "This field is deprecated. Specifies the number of frames to transmit per packet.
             For G.711 encoding mode, valid values range from 5 to
             40 frames, in increments of 5 frames. The default value
             for G.711 is 10 frames per packet. For G.723 encoding
             mode, valid values are 1 or 2, with a default value of
             1 frame per packet.
             
             A value of 0 specifies the number of frames per packet
             equal to the default value for the encoding mode
             (e.g. 10 frames per packet for G.711)."
    DEFVAL          { 10 }
    ::= { sonusServProfileEntry 10 }

sonusServProfileVPktMaxNetworkJitter OBJECT-TYPE
    SYNTAX          INTEGER (40..400)
    ACCESS          read-write
    STATUS          deprecated
    DESCRIPTION     
            "This field is deprecated. Specifies the maximum expected network jitter across the
             IP network in increments of 125usec. This value defines
             the size of the initial playout buffer required to 
             absorb the maximum expected packet delay across the 
             network. The minimum value is 40 (5msec) and the maximum
             value is 400 (50msec), with a default value of 80 (10msec)."
    DEFVAL          { 80 }
    ::= { sonusServProfileEntry 11 }

sonusServProfileVPktTosValue OBJECT-TYPE
    SYNTAX          INTEGER (0..255)
    ACCESS          read-write
    STATUS          deprecated
    DESCRIPTION     
            "This field is deprecated. Specifies the Type Of Service (TOS) parameters to be provided in the 
             IP header for voice packets. The TOS value is specified as an 8-bit hex 
             value 0x00-0xFF allowing complete flexibility with respect to the contents
             of the TOS byte."
    DEFVAL          { 0 }
    ::= { sonusServProfileEntry 12 }

sonusServProfileCttTestType OBJECT-TYPE
    SYNTAX          INTEGER { remoteLoopback(1), remote2Wire(2), 
                        remote4Wire(3) }
    ACCESS          read-write
    STATUS          deprecated
    DESCRIPTION     
            "This field is deprecated. For ISUP service profiles, specifies the type of continuity
             test to perform, based on the configuration of the remote
             switch or trunk connection. The remoteLoopback test is used
             when the remote switch will loop back channel being tested.
             The remote2Wire test is used when the remote switch supports
             the 2 wire continuity test procedure. And the remote4Wire 
             test mode is used when the remote switch supports the 4 wire
             continuity test procedure. The default value is remoteLoopback."
    DEFVAL          { remoteLoopback }
    ::= { sonusServProfileEntry 13 }

sonusServProfileCttTimeout OBJECT-TYPE
    SYNTAX          INTEGER (1..10)
    ACCESS          read-write
    STATUS          deprecated
    DESCRIPTION     
            "This field is deprecated. For ISUP service profiles, specifies the overall test timeout
             value. The continuity test will be declared failed if the
             continuity tone is not detected within this timeout period. 
             The timeout is specified in seconds, with a default value of
             2 seconds."
    DEFVAL          { 2 }
    ::= { sonusServProfileEntry 14 }

sonusServProfileCttMinDetectTime OBJECT-TYPE
    SYNTAX          INTEGER (10..60)
    ACCESS          read-write
    STATUS          deprecated
    DESCRIPTION     
            "This field is deprecated. For ISUP service profiles, specifies the minimum time
             to detect the presence of the continuity test tone. The 
             minimum detect time is specified in milliseconds, with
             a default time of 45 ms."
    DEFVAL          { 45 }
    ::= { sonusServProfileEntry 15 }

sonusServProfileCttMinReleaseTime OBJECT-TYPE
    SYNTAX          INTEGER (10..40)
    ACCESS          read-write
    STATUS          deprecated
    DESCRIPTION     
            "This field is deprecated. For ISUP service profiles, specifies the minimum time
             to detect that the continuity test tone has been removed
             and is no longer present. The minimum release time
             is specified in milliseconds, with a default time of 25 ms."
    DEFVAL          { 25 }
    ::= { sonusServProfileEntry 16 }

sonusServProfileCapability OBJECT-TYPE
    SYNTAX          INTEGER { voiceOnly(1), circuitModeData(2), 
                        voiceOrCircuitModeData(3) }
    ACCESS          read-write
    STATUS          deprecated
    DESCRIPTION     
            "This field is deprecated. Specifies the data capabilities for the circuit. This parameter
             specifies whether voice only, circuit mode data only, or both voice
             and circuit mode data can be supported by the circuit."
    DEFVAL          { voiceOrCircuitModeData }
    ::= { sonusServProfileEntry 17 }

sonusServProfileDPktRestrictedCfg OBJECT-TYPE
    SYNTAX          INTEGER { unrestricted(1), restricted(2) }
    ACCESS          read-write
    STATUS          deprecated
    DESCRIPTION     
            "This field is deprecated. Specifies whether the circuit may support 64 Kbit/s unrestricted data, or
             if the circuit supports 56 Kbit/s restricted data."
    DEFVAL          { unrestricted }
    ::= { sonusServProfileEntry 18 }

sonusServProfileDPktRtpPayloadType OBJECT-TYPE
    SYNTAX          INTEGER (0..127)
    ACCESS          read-write
    STATUS          deprecated
    DESCRIPTION     
            "This field is deprecated. Specifies the RTP payload type to be included in the RTP header of the voice data
             packet"
    DEFVAL          { 56 }
    ::= { sonusServProfileEntry 19 }

sonusServProfileDPktMaxNetworkJitter OBJECT-TYPE
    SYNTAX          INTEGER (40..400)
    ACCESS          read-write
    STATUS          deprecated
    DESCRIPTION     
            "This field is deprecated. Specifies the maximum expected network jitter across the
             network for data calls in increments of 125usec. This value 
             defines the size of the initial playout buffer required to 
             absorb the maximum expected packet delay across the 
             network. A separate value for data calls is provided to 
             allow a single service profile to specify the jitter buffer
             size for both voice calls and data calls.
             The minimum value is 40 (5msec) and the maximum value is 400 (50msec), 
             with a default value of 400 (50msec)."
    DEFVAL          { 400 }
    ::= { sonusServProfileEntry 20 }

sonusServProfileRowStatus OBJECT-TYPE
    SYNTAX          RowStatus
    ACCESS          read-write
    STATUS          deprecated
    DESCRIPTION     
            "This field is deprecated. "
    ::= { sonusServProfileEntry 21 }

sonusSonicBusStatTable OBJECT-TYPE
    SYNTAX          SEQUENCE OF SonusSonicBusStatEntry
    ACCESS          not-accessible
    STATUS          mandatory
    DESCRIPTION     
            "This table presents Sonic Bus statistics for the node."
    ::= { sonusNodeResourcesMIBObjects 2 }

sonusSonicBusStatEntry OBJECT-TYPE
    SYNTAX          SonusSonicBusStatEntry
    ACCESS          not-accessible
    STATUS          mandatory
    DESCRIPTION     
            ""
    INDEX           { sonusSonicBusStatShelfIndex }
    ::= { sonusSonicBusStatTable 1 }

SonusSonicBusStatEntry ::=
    SEQUENCE {
        sonusSonicBusStatShelfIndex     SonusShelfIndex,
        sonusSonicBusStatNumCalls       INTEGER,
        sonusSonicBusStatBwAllocated    INTEGER,
        sonusSonicBusStatSduCount       INTEGER
    }

sonusSonicBusStatShelfIndex OBJECT-TYPE
    SYNTAX          SonusShelfIndex
    ACCESS          read-only
    STATUS          mandatory
    DESCRIPTION     
            "Identifies the target shelf."
    ::= { sonusSonicBusStatEntry 1 }

sonusSonicBusStatNumCalls OBJECT-TYPE
    SYNTAX          INTEGER
    ACCESS          read-only
    STATUS          mandatory
    DESCRIPTION     
            "Indicates the number of active calls on the shelf."
    ::= { sonusSonicBusStatEntry 2 }

sonusSonicBusStatBwAllocated OBJECT-TYPE
    SYNTAX          INTEGER
    ACCESS          read-only
    STATUS          mandatory
    DESCRIPTION     
            "Indicates the percentage of Sonic Bus bandwidth allocated to
             the active calls on the shelf."
    ::= { sonusSonicBusStatEntry 3 }

sonusSonicBusStatSduCount OBJECT-TYPE
    SYNTAX          INTEGER
    ACCESS          read-only
    STATUS          mandatory
    DESCRIPTION     
            "Indicates the number of Sonic Bus data units allocated to
             the active calls on the shelf."
    ::= { sonusSonicBusStatEntry 4 }

sonusActiveCallTable OBJECT-TYPE
    SYNTAX          SEQUENCE OF SonusActiveCallEntry
    ACCESS          not-accessible
    STATUS          mandatory
    DESCRIPTION     
            "This table presents the active call data for the node."
    ::= { sonusNodeResourcesMIBObjects 3 }

sonusActiveCallEntry OBJECT-TYPE
    SYNTAX          SonusActiveCallEntry
    ACCESS          not-accessible
    STATUS          mandatory
    DESCRIPTION     
            ""
    INDEX           { sonusActiveCallShelfIndex, 
                      sonusActiveCallSlotIndex, sonusActiveCallIndex }
    ::= { sonusActiveCallTable 1 }

SonusActiveCallEntry ::=
    SEQUENCE {
        sonusActiveCallShelfIndex       SonusShelfIndex,
        sonusActiveCallSlotIndex        SonusSlotIndex,
        sonusActiveCallIndex            INTEGER,
        sonusActiveCallId               INTEGER,
        sonusActiveCallSonicBusUnitsAllocated     INTEGER,
        sonusActiveCallNumResources     INTEGER,
        sonusActiveCallState            DisplayString,
        sonusActiveCallIngressServProfile DisplayString,
        sonusActiveCallEgressServProfile DisplayString,
        sonusActiveCallCallingNum       DisplayString,
        sonusActiveCallCalledNum        DisplayString,
        sonusActiveCallAddressTransPerformed    INTEGER,
        sonusActiveCallOrigCalledNum    DisplayString,
        sonusActiveCallScenarioType     DisplayString,
        sonusActiveCallIngressPstnSlotNum SonusSlotIndex,
        sonusActiveCallIngressPstnPortNum INTEGER,
        sonusActiveCallIngressPstnChannelNum    INTEGER,
        sonusActiveCallIngressPstnChannelCount      INTEGER,
        sonusActiveCallIngressPstnChannelBitMap       INTEGER,
        sonusActiveCallEgressPstnSlotNum SonusSlotIndex,
        sonusActiveCallEgressPstnPortNum INTEGER,
        sonusActiveCallEgressPstnChannelNum   INTEGER,
        sonusActiveCallEgressPstnChannelCount     INTEGER,
        sonusActiveCallEgressPstnChannelBitMap      INTEGER,
        sonusActiveCallIngressLocalIpSockAddr     IpAddress,
        sonusActiveCallIngressRemoteIpSockAddr      IpAddress,
        sonusActiveCallEgressLocalIpSockAddr    IpAddress,
        sonusActiveCallEgressRemoteIpSockAddr     IpAddress,
        sonusActiveCallIngressPstnTrunk DisplayString,
        sonusActiveCallEgressPstnTrunk  DisplayString,
        sonusActiveCallIngressIpDestGwName  DisplayString,
        sonusActiveCallEgressIpDestGwName DisplayString,
        sonusActiveCallDuration         INTEGER,
        sonusActiveCallIngressEpType    INTEGER,
        sonusActiveCallEgressEpType     INTEGER,
        sonusActiveCallIngressSgType    INTEGER,
        sonusActiveCallEgressSgType     INTEGER,
        sonusActiveCallPacketsSent      INTEGER,
        sonusActiveCallPacketsReceived  INTEGER,
        sonusActiveCallOctetsSent       INTEGER,
        sonusActiveCallOctetsReceived   INTEGER,
        sonusActiveCallPacketsLost      INTEGER,
        sonusActiveCallPacketsDiscarded INTEGER,
        sonusActiveCallInterarrivalJitter INTEGER,
        sonusActiveCallPacketLatency    INTEGER,
        sonusActiveCallIngressLocalAtmAddr  AtmAddr,
        sonusActiveCallIngressRemoteAtmAddr   AtmAddr,
        sonusActiveCallEgressLocalAtmAddr AtmAddr,
        sonusActiveCallEgressRemoteAtmAddr  AtmAddr,
        sonusActiveCallCellsSent        INTEGER,
        sonusActiveCallCellsReceived    INTEGER,
        sonusActiveCallCellsLost        INTEGER,
        sonusActiveCallCellsDiscarded   INTEGER,
        sonusActiveCallCellsOutOfSeq    INTEGER,
        sonusActiveCallCellBufferOverFlow INTEGER,
        sonusActiveCallCellBufferUnderFlow  INTEGER,
        sonusActiveCallCellCrcViolations INTEGER,
        sonusActiveCallCellParityCheckFail  INTEGER,
        sonusActiveCallCellDelayVariation INTEGER,
        sonusActiveCallIngressMacHeader PhysAddress,
        sonusActiveCallEgressMacHeader  PhysAddress,
        sonusActiveCallIngressBearerType INTEGER,
        sonusActiveCallEgressBearerType INTEGER,
        sonusActiveCallIngressCfgECStatus INTEGER,
        sonusActiveCallIngressActECStatus INTEGER,
        sonusActiveCallIngressElSend    INTEGER,
        sonusActiveCallIngressElReceive INTEGER,
        sonusActiveCallIngressMainECReflector     INTEGER,
        sonusActiveCallIngressErl       INTEGER,
        sonusActiveCallIngressErle      INTEGER,
        sonusActiveCallIngressFaxModemDetected      INTEGER,
        sonusActiveCallEgressCfgECStatus INTEGER,
        sonusActiveCallEgressActECStatus INTEGER,
        sonusActiveCallEgressElSend     INTEGER,
        sonusActiveCallEgressElReceive  INTEGER,
        sonusActiveCallEgressMainECReflector    INTEGER,
        sonusActiveCallEgressErl        INTEGER,
        sonusActiveCallEgressErle       INTEGER,
        sonusActiveCallEgressFaxModemDetected     INTEGER,
        sonusActiveCallIngressTxLevel   INTEGER,
        sonusActiveCallIngressRxLevel   INTEGER,
        sonusActiveCallEgressTxLevel    INTEGER,
        sonusActiveCallEgressRxLevel    INTEGER,
        sonusActiveCallIngressTxGain    INTEGER,
        sonusActiveCallIngressRxGain    INTEGER,
        sonusActiveCallEgressTxGain     INTEGER,
        sonusActiveCallEgressRxGain     INTEGER,
        sonusActiveCallIngressCfgAudioType  INTEGER,
        sonusActiveCallEgressCfgAudioType INTEGER,
        sonusActiveCallIngressActAudioType  INTEGER,
        sonusActiveCallEgressActAudioType INTEGER,
        sonusActiveCallType             INTEGER,
        sonusActiveCallAssociatedGcid1  INTEGER,
        sonusActiveCallAssociatedGcid2  INTEGER,
        sonusActiveCallAssociatedGcid3  INTEGER,
        sonusActiveCallAssociatedGcid4  INTEGER,
        sonusActiveCallAssociatedGcid5  INTEGER,
        sonusActiveCallIngressECMaxTail INTEGER,
        sonusActiveCallEgressECMaxTail  INTEGER,
        sonusActiveCallAssociatedGcid6  INTEGER,
        sonusActiveCallAssociatedGcidLegId1   INTEGER,
        sonusActiveCallAssociatedGcidLegId2   INTEGER,
        sonusActiveCallAssociatedGcidLegId3   INTEGER,
        sonusActiveCallAssociatedGcidLegId4   INTEGER,
        sonusActiveCallAssociatedGcidLegId5   INTEGER,
        sonusActiveCallAssociatedGcidLegId6   INTEGER,
        sonusActiveCallP2PStatsValid    INTEGER,
        sonusActiveCallP2PPacketsSent   INTEGER,
        sonusActiveCallP2PPacketsReceived INTEGER,
        sonusActiveCallP2POctetsSent    INTEGER,
        sonusActiveCallP2POctetsReceived INTEGER,
        sonusActiveCallP2PPacketsLost   INTEGER,
        sonusActiveCallP2PPacketsDiscarded  INTEGER,
        sonusActiveCallP2PInterarrivalJitter    INTEGER,
        sonusActiveCallP2PPacketLatency INTEGER,
        sonusActiveCallIpLoopIngressAssocGcid     INTEGER,
        sonusActiveCallIpLoopEgressAssocGcid    INTEGER,
        sonusActiveCallIpLoopIngressAssocLegId      INTEGER,
        sonusActiveCallIpLoopEgressAssocLegId     INTEGER,
        sonusActiveCallIngressSrtpCrypto INTEGER,
        sonusActiveCallIngressSrtpAuth  INTEGER,
        sonusActiveCallEgressSrtpCrypto INTEGER,
        sonusActiveCallEgressSrtpAuth   INTEGER,
        sonusActiveCallIngressSrtcpCrypto INTEGER,
        sonusActiveCallIngressSrtcpAuth INTEGER,
        sonusActiveCallEgressSrtcpCrypto INTEGER,
        sonusActiveCallEgressSrtcpAuth  INTEGER,
        sonusActiveCallVideoDuration    INTEGER,
        sonusActiveCallVideoBandwidth   INTEGER,
        sonusActiveCallIngressVideoLocalIpSockAddr          IpAddress,
        sonusActiveCallIngressVideoRemoteIpSockAddr           IpAddress,
        sonusActiveCallEgressVideoLocalIpSockAddr         IpAddress,
        sonusActiveCallEgressVideoRemoteIpSockAddr          IpAddress,
        sonusActiveCallIngressVideoStatsValid     INTEGER,
        sonusActiveCallIngressVideoPacketsSent      INTEGER,
        sonusActiveCallIngressVideoPacketsReceived          INTEGER,
        sonusActiveCallIngressVideoOctetsSent     INTEGER,
        sonusActiveCallIngressVideoOctetsReceived         INTEGER,
        sonusActiveCallIngressVideoPacketsLost      INTEGER,
        sonusActiveCallIngressVideoPacketsDiscarded           INTEGER,
        sonusActiveCallIngressVideoPacketLatency        INTEGER,
        sonusActiveCallIngressVideoInterarrivalJitter             INTEGER,
        sonusActiveCallEgressVideoStatsValid    INTEGER,
        sonusActiveCallEgressVideoPacketsSent     INTEGER,
        sonusActiveCallEgressVideoPacketsReceived         INTEGER,
        sonusActiveCallEgressVideoOctetsSent    INTEGER,
        sonusActiveCallEgressVideoOctetsReceived        INTEGER,
        sonusActiveCallEgressVideoPacketsLost     INTEGER,
        sonusActiveCallEgressVideoPacketsDiscarded          INTEGER,
        sonusActiveCallEgressVideoPacketLatency       INTEGER,
        sonusActiveCallEgressVideoInterarrivalJitter            INTEGER,
        sonusActiveCallMediaType        INTEGER,
        sonusActiveCallBiccIngressCktInfoValid      INTEGER,
        sonusActiveCallIngressBiccCICNum INTEGER,
        sonusActiveCallIngressBiccSlotNum SonusSlotIndex,
        sonusActiveCallBiccEgressCktInfoValid     INTEGER,
        sonusActiveCallEgressBiccSlotNum SonusSlotIndex,
        sonusActiveCallEgressBiccCICNum INTEGER,
        sonusActiveCallIngressLocalIp6SockAddr      Ipv6Address,
        sonusActiveCallIngressLocalIpVersion    INTEGER,
        sonusActiveCallIngressRemoteIp6SockAddr       Ipv6Address,
        sonusActiveCallIngressRemoteIpVersion     INTEGER,
        sonusActiveCallEgressLocalIp6SockAddr     Ipv6Address,
        sonusActiveCallEgressLocalIpVersion   INTEGER,
        sonusActiveCallEgressRemoteIp6SockAddr      Ipv6Address,
        sonusActiveCallEgressRemoteIpVersion    INTEGER,
        sonusActiveCallIngressVideoLocalIp6SockAddr           Ipv6Address,
        sonusActiveCallIngressVideoLocalIpVersion         INTEGER,
        sonusActiveCallIngressVideoRemoteIp6SockAddr            Ipv6Address,
        sonusActiveCallIngressVideoRemoteIpVersion          INTEGER,
        sonusActiveCallEgressVideoLocalIp6SockAddr          Ipv6Address,
        sonusActiveCallEgressVideoLocalIpVersion        INTEGER,
        sonusActiveCallEgressVideoRemoteIp6SockAddr           Ipv6Address,
        sonusActiveCallEgressVideoRemoteIpVersion         INTEGER
    }

sonusActiveCallShelfIndex OBJECT-TYPE
    SYNTAX          SonusShelfIndex
    ACCESS          read-only
    STATUS          mandatory
    DESCRIPTION     
            "Identifies the target shelf."
    ::= { sonusActiveCallEntry 1 }

sonusActiveCallSlotIndex OBJECT-TYPE
    SYNTAX          SonusSlotIndex
    ACCESS          read-only
    STATUS          mandatory
    DESCRIPTION     
            "Identifies the target slot."
    ::= { sonusActiveCallEntry 2 }

sonusActiveCallIndex OBJECT-TYPE
    SYNTAX          INTEGER
    ACCESS          read-only
    STATUS          mandatory
    DESCRIPTION     
            "Identifies the target call index."
    ::= { sonusActiveCallEntry 3 }

sonusActiveCallId OBJECT-TYPE
    SYNTAX          INTEGER
    ACCESS          read-only
    STATUS          mandatory
    DESCRIPTION     
            "Represents the global call identifier (GCID) for the call. GCID is unique
             across the entire node."
    ::= { sonusActiveCallEntry 4 }

sonusActiveCallSonicBusUnitsAllocated OBJECT-TYPE
    SYNTAX          INTEGER
    ACCESS          read-only
    STATUS          mandatory
    DESCRIPTION     
            "Represents the SonicBus bandwidth allocated for the call expressed as
             SonicData Units per second."
    ::= { sonusActiveCallEntry 5 }

sonusActiveCallNumResources OBJECT-TYPE
    SYNTAX          INTEGER
    ACCESS          read-only
    STATUS          mandatory
    DESCRIPTION     
            "Represents the number of resources currently allocated to the call."
    ::= { sonusActiveCallEntry 6 }

sonusActiveCallState OBJECT-TYPE
    SYNTAX          DisplayString (SIZE(0..23))
    ACCESS          read-only
    STATUS          mandatory
    DESCRIPTION     
            "Represents the current call state."
    ::= { sonusActiveCallEntry 7 }

sonusActiveCallIngressServProfile OBJECT-TYPE
    SYNTAX          DisplayString (SIZE(0..23))
    ACCESS          read-only
    STATUS          mandatory
    DESCRIPTION     
            "The name of the ingress service profile associated with this call."
    ::= { sonusActiveCallEntry 8 }

sonusActiveCallEgressServProfile OBJECT-TYPE
    SYNTAX          DisplayString (SIZE(0..23))
    ACCESS          read-only
    STATUS          mandatory
    DESCRIPTION     
            "The name of the egress service profile associated with this call."
    ::= { sonusActiveCallEntry 9 }

sonusActiveCallCallingNum OBJECT-TYPE
    SYNTAX          DisplayString (SIZE(0..30))
    ACCESS          read-only
    STATUS          mandatory
    DESCRIPTION     
            "The E.164 number representing the Calling Party's telephone number."
    ::= { sonusActiveCallEntry 10 }

sonusActiveCallCalledNum OBJECT-TYPE
    SYNTAX          DisplayString (SIZE(0..30))
    ACCESS          read-only
    STATUS          mandatory
    DESCRIPTION     
            "The E.164 number representing the Called Party's telephone number."
    ::= { sonusActiveCallEntry 11 }

sonusActiveCallAddressTransPerformed OBJECT-TYPE
    SYNTAX          INTEGER { none(1), lnp(2), tollfree(3) }
    ACCESS          read-only
    STATUS          mandatory
    DESCRIPTION     
            "Indicates whether any address translation has been performed on the 
             called party number. Valid translations are Local Number Portability (LPN), 
             and 800 number translation (Tollfree)."
    ::= { sonusActiveCallEntry 12 }

sonusActiveCallOrigCalledNum OBJECT-TYPE
    SYNTAX          DisplayString (SIZE(0..30))
    ACCESS          read-only
    STATUS          mandatory
    DESCRIPTION     
            "If an address translation has been performed on the called party number, 
             this entry contains the original, untranslated number."
    ::= { sonusActiveCallEntry 13 }

sonusActiveCallScenarioType OBJECT-TYPE
    SYNTAX          DisplayString (SIZE(0..23))
    ACCESS          read-only
    STATUS          mandatory
    DESCRIPTION     
            "Specifies the call scenario type for this call."
    ::= { sonusActiveCallEntry 14 }

sonusActiveCallIngressPstnSlotNum OBJECT-TYPE
    SYNTAX          SonusSlotIndex
    ACCESS          read-only
    STATUS          mandatory
    DESCRIPTION     
            "For calls originating from the PSTN (circuit) side, indicates the slot
             of the circuit card on which the call was delivered."
    ::= { sonusActiveCallEntry 15 }

sonusActiveCallIngressPstnPortNum OBJECT-TYPE
    SYNTAX          INTEGER (1..28)
    ACCESS          read-only
    STATUS          mandatory
    DESCRIPTION     
            "For calls originating from the PSTN (circuit) side, indicates the T1 port
             on the circuit card on which the call was delivered. For CNS10 cards, the
             port number will be in the range 1-12; for CNS30 cards, the port number will
             be in the range 1-28."
    ::= { sonusActiveCallEntry 16 }

sonusActiveCallIngressPstnChannelNum OBJECT-TYPE
    SYNTAX          INTEGER (1..24)
    ACCESS          read-only
    STATUS          mandatory
    DESCRIPTION     
            "For calls originating from the PSTN (circuit) side, indicates the DS0 channel
             on which the call is being carried."
    ::= { sonusActiveCallEntry 17 }

sonusActiveCallIngressPstnChannelCount OBJECT-TYPE
    SYNTAX          INTEGER (1..24)
    ACCESS          read-only
    STATUS          mandatory
    DESCRIPTION     
            "For calls originating from the PSTN (circuit) side, indicates the number of
             DS0 channels on which the call is being carried. This value is meaningful for
             Nx64 service calls."
    ::= { sonusActiveCallEntry 18 }

sonusActiveCallIngressPstnChannelBitMap OBJECT-TYPE
    SYNTAX          INTEGER
    ACCESS          read-only
    STATUS          mandatory
    DESCRIPTION     
            "For calls originating from the PSTN (circuit) side, provides a bit map of DS0
             channels on which the call is being carried. For Nx64 service calls where N is
             greater than 1, multiple bits will be marked in the bit map."
    ::= { sonusActiveCallEntry 19 }

sonusActiveCallEgressPstnSlotNum OBJECT-TYPE
    SYNTAX          SonusSlotIndex
    ACCESS          read-only
    STATUS          mandatory
    DESCRIPTION     
            "For calls delivered to the PSTN (circuit) side, indicates the slot
             of the circuit card on which the call was delivered."
    ::= { sonusActiveCallEntry 20 }

sonusActiveCallEgressPstnPortNum OBJECT-TYPE
    SYNTAX          INTEGER (1..28)
    ACCESS          read-only
    STATUS          mandatory
    DESCRIPTION     
            "For calls delivered to the PSTN (circuit) side, indicates the T1 port
             on the circuit card on which the call was delivered. For CNS10 cards, the
             port number will be in the range 1-12; for CNS30 cards, the port number will
             be in the range 1-28."
    ::= { sonusActiveCallEntry 21 }

sonusActiveCallEgressPstnChannelNum OBJECT-TYPE
    SYNTAX          INTEGER (1..24)
    ACCESS          read-only
    STATUS          mandatory
    DESCRIPTION     
            "For calls delivered to the PSTN (circuit) side, indicates the DS0 channel
             on which the call is being carried."
    ::= { sonusActiveCallEntry 22 }

sonusActiveCallEgressPstnChannelCount OBJECT-TYPE
    SYNTAX          INTEGER (1..24)
    ACCESS          read-only
    STATUS          mandatory
    DESCRIPTION     
            "For calls delivered to the PSTN (circuit) side, indicates the number of
             DS0 channels on which the call is being carried. This value is meaningful for
             Nx64 service calls."
    ::= { sonusActiveCallEntry 23 }

sonusActiveCallEgressPstnChannelBitMap OBJECT-TYPE
    SYNTAX          INTEGER
    ACCESS          read-only
    STATUS          mandatory
    DESCRIPTION     
            "For calls delivered to the PSTN (circuit) side, provides a bit map of DS0
             channels on which the call is being carried. For Nx64 service calls where N is
             greater than 1, multiple bits will be marked in the bit map."
    ::= { sonusActiveCallEntry 24 }

sonusActiveCallIngressLocalIpSockAddr OBJECT-TYPE
    SYNTAX          IpAddress
    ACCESS          read-only
    STATUS          mandatory
    DESCRIPTION     
            "For calls originated on the IP (packet) side, indicates the IP address
             of the incoming (ingress) local socket connection."
    ::= { sonusActiveCallEntry 25 }

sonusActiveCallIngressRemoteIpSockAddr OBJECT-TYPE
    SYNTAX          IpAddress
    ACCESS          read-only
    STATUS          mandatory
    DESCRIPTION     
            "For calls originated on the IP (packet) side, indicates the IP address
             of the incoming (ingress) remote socket connection."
    ::= { sonusActiveCallEntry 26 }

sonusActiveCallEgressLocalIpSockAddr OBJECT-TYPE
    SYNTAX          IpAddress
    ACCESS          read-only
    STATUS          mandatory
    DESCRIPTION     
            "For calls delivered to the IP (packet) side, indicates the IP address
             of the outgoing (egress) local socket connection."
    ::= { sonusActiveCallEntry 27 }

sonusActiveCallEgressRemoteIpSockAddr OBJECT-TYPE
    SYNTAX          IpAddress
    ACCESS          read-only
    STATUS          mandatory
    DESCRIPTION     
            "For calls delivered to the IP (packet) side, indicates the IP address
             of the outgoing (egress) remote socket connection."
    ::= { sonusActiveCallEntry 28 }

sonusActiveCallIngressPstnTrunk OBJECT-TYPE
    SYNTAX          DisplayString (SIZE(0..23))
    ACCESS          read-only
    STATUS          mandatory
    DESCRIPTION     
            "For calls originating from the PSTN (circuit) side, specifies the trunk
             group name to which the Ingress Pstn Channel belongs."
    ::= { sonusActiveCallEntry 29 }

sonusActiveCallEgressPstnTrunk OBJECT-TYPE
    SYNTAX          DisplayString (SIZE(0..23))
    ACCESS          read-only
    STATUS          mandatory
    DESCRIPTION     
            "For calls delivered to the PSTN (circuit) side, specifies the trunk
             group name to which the Egress Pstn Channel belongs."
    ::= { sonusActiveCallEntry 30 }

sonusActiveCallIngressIpDestGwName OBJECT-TYPE
    SYNTAX          DisplayString (SIZE(0..23))
    ACCESS          read-only
    STATUS          mandatory
    DESCRIPTION     
            "For calls originating from the IP (packet) side, specifies the name of the
             remote gateway on which the call originated."
    ::= { sonusActiveCallEntry 31 }

sonusActiveCallEgressIpDestGwName OBJECT-TYPE
    SYNTAX          DisplayString (SIZE(0..23))
    ACCESS          read-only
    STATUS          mandatory
    DESCRIPTION     
            "For calls delivered to the IP (packet) side, specifies the name of the 
             remote gateway to which the call was delivered."
    ::= { sonusActiveCallEntry 32 }

sonusActiveCallDuration OBJECT-TYPE
    SYNTAX          INTEGER
    ACCESS          read-only
    STATUS          mandatory
    DESCRIPTION     
            "Indicates the duration in seconds for this call following answer."
    ::= { sonusActiveCallEntry 33 }

sonusActiveCallIngressEpType OBJECT-TYPE
    SYNTAX          INTEGER { unknown(0), circuit(1), packet(2), vtoa(3) }
    ACCESS          read-only
    STATUS          mandatory
    DESCRIPTION     
            "Indicates the end point type for the ingress end point."
    ::= { sonusActiveCallEntry 34 }

sonusActiveCallEgressEpType OBJECT-TYPE
    SYNTAX          INTEGER { unknown(0), circuit(1), packet(2), vtoa(3) }
    ACCESS          read-only
    STATUS          mandatory
    DESCRIPTION     
            "Indicates the end point type for the egress end point."
    ::= { sonusActiveCallEntry 35 }

sonusActiveCallIngressSgType OBJECT-TYPE
    SYNTAX          INTEGER { unknown(0), isup(1), cas(2), isdn(3), 
                        h323(4), gwip(5), internal1(6), internal2(7), 
                        mg(8), asg(9), static(10) }
    ACCESS          read-only
    STATUS          mandatory
    DESCRIPTION     
            "Indicates the signaling type for the ingress end point."
    ::= { sonusActiveCallEntry 36 }

sonusActiveCallEgressSgType OBJECT-TYPE
    SYNTAX          INTEGER { unknown(0), isup(1), cas(2), isdn(3), 
                        h323(4), gwip(5), internal1(6), internal2(7), 
                        mg(8), asg(9), static(10) }
    ACCESS          read-only
    STATUS          mandatory
    DESCRIPTION     
            "Indicates the signaling type for the egress end point."
    ::= { sonusActiveCallEntry 37 }

sonusActiveCallPacketsSent OBJECT-TYPE
    SYNTAX          INTEGER
    ACCESS          read-only
    STATUS          mandatory
    DESCRIPTION     
            "Indicates the number of RTP packets sent on this call."
    ::= { sonusActiveCallEntry 38 }

sonusActiveCallPacketsReceived OBJECT-TYPE
    SYNTAX          INTEGER
    ACCESS          read-only
    STATUS          mandatory
    DESCRIPTION     
            "Indicates the number of RTP packets received on this call."
    ::= { sonusActiveCallEntry 39 }

sonusActiveCallOctetsSent OBJECT-TYPE
    SYNTAX          INTEGER
    ACCESS          read-only
    STATUS          mandatory
    DESCRIPTION     
            "Indicates the number of RTP octets sent on this call."
    ::= { sonusActiveCallEntry 40 }

sonusActiveCallOctetsReceived OBJECT-TYPE
    SYNTAX          INTEGER
    ACCESS          read-only
    STATUS          mandatory
    DESCRIPTION     
            "Indicates the number of RTP octets received on this call."
    ::= { sonusActiveCallEntry 41 }

sonusActiveCallPacketsLost OBJECT-TYPE
    SYNTAX          INTEGER
    ACCESS          read-only
    STATUS          mandatory
    DESCRIPTION     
            "Indicates the number of RTP packets lost on this call."
    ::= { sonusActiveCallEntry 42 }

sonusActiveCallPacketsDiscarded OBJECT-TYPE
    SYNTAX          INTEGER
    ACCESS          read-only
    STATUS          mandatory
    DESCRIPTION     
            "Indicates the number of RTP packets discarded by the jitter buffer."
    ::= { sonusActiveCallEntry 43 }

sonusActiveCallInterarrivalJitter OBJECT-TYPE
    SYNTAX          INTEGER
    ACCESS          read-only
    STATUS          mandatory
    DESCRIPTION     
            "Indicates the interarrival packet jitter on this call."
    ::= { sonusActiveCallEntry 44 }

sonusActiveCallPacketLatency OBJECT-TYPE
    SYNTAX          INTEGER
    ACCESS          read-only
    STATUS          mandatory
    DESCRIPTION     
            "Indicates the latency experienced on this call."
    ::= { sonusActiveCallEntry 45 }

sonusActiveCallIngressLocalAtmAddr OBJECT-TYPE
    SYNTAX          AtmAddr
    ACCESS          read-only
    STATUS          mandatory
    DESCRIPTION     
            "For calls originated on the ATM (cell) side, indicates the ATM address
             of the incoming (ingress) local media connection."
    ::= { sonusActiveCallEntry 46 }

sonusActiveCallIngressRemoteAtmAddr OBJECT-TYPE
    SYNTAX          AtmAddr
    ACCESS          read-only
    STATUS          mandatory
    DESCRIPTION     
            "For calls originated on the ATM (cell) side, indicates the ATM address
             of the incoming (ingress) remote media connection."
    ::= { sonusActiveCallEntry 47 }

sonusActiveCallEgressLocalAtmAddr OBJECT-TYPE
    SYNTAX          AtmAddr
    ACCESS          read-only
    STATUS          mandatory
    DESCRIPTION     
            "For calls delivered to the ATM (cell) side, indicates the ATM address
             of the outgoing (egress) local media connection."
    ::= { sonusActiveCallEntry 48 }

sonusActiveCallEgressRemoteAtmAddr OBJECT-TYPE
    SYNTAX          AtmAddr
    ACCESS          read-only
    STATUS          mandatory
    DESCRIPTION     
            "For calls delivered to the ATM (cell) side, indicates the ATM address
             of the outgoing (egress) remote media connection."
    ::= { sonusActiveCallEntry 49 }

sonusActiveCallCellsSent OBJECT-TYPE
    SYNTAX          INTEGER
    ACCESS          read-only
    STATUS          mandatory
    DESCRIPTION     
            "Indicates the number of ATM cells sent on this call."
    ::= { sonusActiveCallEntry 50 }

sonusActiveCallCellsReceived OBJECT-TYPE
    SYNTAX          INTEGER
    ACCESS          read-only
    STATUS          mandatory
    DESCRIPTION     
            "Indicates the number of ATM cells received on this call."
    ::= { sonusActiveCallEntry 51 }

sonusActiveCallCellsLost OBJECT-TYPE
    SYNTAX          INTEGER
    ACCESS          read-only
    STATUS          mandatory
    DESCRIPTION     
            "Indicates the number of ATM cells lost on this call."
    ::= { sonusActiveCallEntry 52 }

sonusActiveCallCellsDiscarded OBJECT-TYPE
    SYNTAX          INTEGER
    ACCESS          read-only
    STATUS          mandatory
    DESCRIPTION     
            "Indicates the number of ATM cells discarded by the jitter buffer."
    ::= { sonusActiveCallEntry 53 }

sonusActiveCallCellsOutOfSeq OBJECT-TYPE
    SYNTAX          INTEGER
    ACCESS          read-only
    STATUS          mandatory
    DESCRIPTION     
            "Indicates the number of ATM cells received out of sequence."
    ::= { sonusActiveCallEntry 54 }

sonusActiveCallCellBufferOverFlow OBJECT-TYPE
    SYNTAX          INTEGER
    ACCESS          read-only
    STATUS          mandatory
    DESCRIPTION     
            "Indicates the number of ATM cell buffer overflows."
    ::= { sonusActiveCallEntry 55 }

sonusActiveCallCellBufferUnderFlow OBJECT-TYPE
    SYNTAX          INTEGER
    ACCESS          read-only
    STATUS          mandatory
    DESCRIPTION     
            "Indicates the number of ATM cell buffer underflows."
    ::= { sonusActiveCallEntry 56 }

sonusActiveCallCellCrcViolations OBJECT-TYPE
    SYNTAX          INTEGER
    ACCESS          read-only
    STATUS          mandatory
    DESCRIPTION     
            "Indicates the number of ATM cell CRC violations."
    ::= { sonusActiveCallEntry 57 }

sonusActiveCallCellParityCheckFail OBJECT-TYPE
    SYNTAX          INTEGER
    ACCESS          read-only
    STATUS          mandatory
    DESCRIPTION     
            "Indicates the number of ATM cell parity check failures."
    ::= { sonusActiveCallEntry 58 }

sonusActiveCallCellDelayVariation OBJECT-TYPE
    SYNTAX          INTEGER
    ACCESS          read-only
    STATUS          mandatory
    DESCRIPTION     
            "Indicates the ATM cell dealy variation in %."
    ::= { sonusActiveCallEntry 59 }

sonusActiveCallIngressMacHeader OBJECT-TYPE
    SYNTAX          PhysAddress
    ACCESS          read-only
    STATUS          mandatory
    DESCRIPTION     
            "Ingress MAC header for IP calls over Ethernet"
    ::= { sonusActiveCallEntry 60 }

sonusActiveCallEgressMacHeader OBJECT-TYPE
    SYNTAX          PhysAddress
    ACCESS          read-only
    STATUS          mandatory
    DESCRIPTION     
            "Egress MAC header for IP calls over Ethernet"
    ::= { sonusActiveCallEntry 61 }

sonusActiveCallIngressBearerType OBJECT-TYPE
    SYNTAX          INTEGER { unknown(0), voice(1), ctt(2), dchannel(3), 
                        data56k(4), data64k(5), nocompression(6), 
                        ss7mtpchannel(7), notapplicable(8) }
    ACCESS          read-only
    STATUS          mandatory
    DESCRIPTION     
            "Bearer Type - voice, 3.1Khz, 64K Data, 56K data, ss7 mtp"
    ::= { sonusActiveCallEntry 62 }

sonusActiveCallEgressBearerType OBJECT-TYPE
    SYNTAX          INTEGER { unknown(0), voice(1), ctt(2), dchannel(3), 
                        data56k(4), data64k(5), nocompression(6), 
                        ss7mtpchannel(7), notapplicable(8) }
    ACCESS          read-only
    STATUS          mandatory
    DESCRIPTION     
            "Bearer Type - voice, 3.1Khz, 64K Data, 56K data, ss7 mtp"
    ::= { sonusActiveCallEntry 63 }

sonusActiveCallIngressCfgECStatus OBJECT-TYPE
    SYNTAX          INTEGER { none(0), disabled(1), enabled(2) }
    ACCESS          read-only
    STATUS          mandatory
    DESCRIPTION     
            "provisioned echo canceller status"
    ::= { sonusActiveCallEntry 64 }

sonusActiveCallIngressActECStatus OBJECT-TYPE
    SYNTAX          INTEGER
    ACCESS          read-only
    STATUS          mandatory
    DESCRIPTION     
            "actual echo canceller status"
    ::= { sonusActiveCallEntry 65 }

sonusActiveCallIngressElSend OBJECT-TYPE
    SYNTAX          INTEGER
    ACCESS          read-only
    STATUS          mandatory
    DESCRIPTION     
            "energy level send"
    ::= { sonusActiveCallEntry 66 }

sonusActiveCallIngressElReceive OBJECT-TYPE
    SYNTAX          INTEGER
    ACCESS          read-only
    STATUS          mandatory
    DESCRIPTION     
            "energy level received"
    ::= { sonusActiveCallEntry 67 }

sonusActiveCallIngressMainECReflector OBJECT-TYPE
    SYNTAX          INTEGER
    ACCESS          read-only
    STATUS          mandatory
    DESCRIPTION     
            "main echo canceller reflector location"
    ::= { sonusActiveCallEntry 68 }

sonusActiveCallIngressErl OBJECT-TYPE
    SYNTAX          INTEGER
    ACCESS          read-only
    STATUS          mandatory
    DESCRIPTION     
            "echo return loss"
    ::= { sonusActiveCallEntry 69 }

sonusActiveCallIngressErle OBJECT-TYPE
    SYNTAX          INTEGER
    ACCESS          read-only
    STATUS          mandatory
    DESCRIPTION     
            "echo return loss enhancement"
    ::= { sonusActiveCallEntry 70 }

sonusActiveCallIngressFaxModemDetected OBJECT-TYPE
    SYNTAX          INTEGER { none(0), fax(1), modem(2) }
    ACCESS          read-only
    STATUS          mandatory
    DESCRIPTION     
            "indicating if FAX or Modem are detected"
    ::= { sonusActiveCallEntry 71 }

sonusActiveCallEgressCfgECStatus OBJECT-TYPE
    SYNTAX          INTEGER { none(0), disabled(1), enabled(2) }
    ACCESS          read-only
    STATUS          mandatory
    DESCRIPTION     
            "provisioned echo canceller status"
    ::= { sonusActiveCallEntry 72 }

sonusActiveCallEgressActECStatus OBJECT-TYPE
    SYNTAX          INTEGER
    ACCESS          read-only
    STATUS          mandatory
    DESCRIPTION     
            "actual echo canceller status"
    ::= { sonusActiveCallEntry 73 }

sonusActiveCallEgressElSend OBJECT-TYPE
    SYNTAX          INTEGER
    ACCESS          read-only
    STATUS          mandatory
    DESCRIPTION     
            "energy level send"
    ::= { sonusActiveCallEntry 74 }

sonusActiveCallEgressElReceive OBJECT-TYPE
    SYNTAX          INTEGER
    ACCESS          read-only
    STATUS          mandatory
    DESCRIPTION     
            "energy level received"
    ::= { sonusActiveCallEntry 75 }

sonusActiveCallEgressMainECReflector OBJECT-TYPE
    SYNTAX          INTEGER
    ACCESS          read-only
    STATUS          mandatory
    DESCRIPTION     
            "main echo canceller reflector location"
    ::= { sonusActiveCallEntry 76 }

sonusActiveCallEgressErl OBJECT-TYPE
    SYNTAX          INTEGER
    ACCESS          read-only
    STATUS          mandatory
    DESCRIPTION     
            "echo return loss"
    ::= { sonusActiveCallEntry 77 }

sonusActiveCallEgressErle OBJECT-TYPE
    SYNTAX          INTEGER
    ACCESS          read-only
    STATUS          mandatory
    DESCRIPTION     
            "echo return loss enhancement"
    ::= { sonusActiveCallEntry 78 }

sonusActiveCallEgressFaxModemDetected OBJECT-TYPE
    SYNTAX          INTEGER { none(0), fax(1), modem(2) }
    ACCESS          read-only
    STATUS          mandatory
    DESCRIPTION     
            "indicating if FAX or Modem are detected"
    ::= { sonusActiveCallEntry 79 }

sonusActiveCallIngressTxLevel OBJECT-TYPE
    SYNTAX          INTEGER { none(1), highLevelCompensation(2), 
                        fixedGain(3) }
    ACCESS          read-only
    STATUS          mandatory
    DESCRIPTION     
            "indicate tx level on call"
    ::= { sonusActiveCallEntry 80 }

sonusActiveCallIngressRxLevel OBJECT-TYPE
    SYNTAX          INTEGER { none(1), fixedGain(3) }
    ACCESS          read-only
    STATUS          mandatory
    DESCRIPTION     
            "indicate rx level on call"
    ::= { sonusActiveCallEntry 81 }

sonusActiveCallEgressTxLevel OBJECT-TYPE
    SYNTAX          INTEGER { none(1), highLevelCompensation(2), 
                        fixedGain(3) }
    ACCESS          read-only
    STATUS          mandatory
    DESCRIPTION     
            "indicate tx level on call"
    ::= { sonusActiveCallEntry 82 }

sonusActiveCallEgressRxLevel OBJECT-TYPE
    SYNTAX          INTEGER { none(1), fixedGain(3) }
    ACCESS          read-only
    STATUS          mandatory
    DESCRIPTION     
            "indicate rx level on call"
    ::= { sonusActiveCallEntry 83 }

sonusActiveCallIngressTxGain OBJECT-TYPE
    SYNTAX          INTEGER (-12..12)
    ACCESS          read-only
    STATUS          mandatory
    DESCRIPTION     
            "indicate tx gain used on call"
    ::= { sonusActiveCallEntry 84 }

sonusActiveCallIngressRxGain OBJECT-TYPE
    SYNTAX          INTEGER (-12..12)
    ACCESS          read-only
    STATUS          mandatory
    DESCRIPTION     
            "indicate rx gain used on call"
    ::= { sonusActiveCallEntry 85 }

sonusActiveCallEgressTxGain OBJECT-TYPE
    SYNTAX          INTEGER (-12..12)
    ACCESS          read-only
    STATUS          mandatory
    DESCRIPTION     
            "indicate tx gain used on call"
    ::= { sonusActiveCallEntry 86 }

sonusActiveCallEgressRxGain OBJECT-TYPE
    SYNTAX          INTEGER (-12..12)
    ACCESS          read-only
    STATUS          mandatory
    DESCRIPTION     
            "indicate rx gain used on call"
    ::= { sonusActiveCallEntry 87 }

sonusActiveCallIngressCfgAudioType OBJECT-TYPE
    SYNTAX          INTEGER
    ACCESS          read-only
    STATUS          mandatory
    DESCRIPTION     
            "indicate configured audio type"
    ::= { sonusActiveCallEntry 88 }

sonusActiveCallEgressCfgAudioType OBJECT-TYPE
    SYNTAX          INTEGER
    ACCESS          read-only
    STATUS          mandatory
    DESCRIPTION     
            "indicate configured audio type"
    ::= { sonusActiveCallEntry 89 }

sonusActiveCallIngressActAudioType OBJECT-TYPE
    SYNTAX          INTEGER
    ACCESS          read-only
    STATUS          mandatory
    DESCRIPTION     
            "indicate actual audio type"
    ::= { sonusActiveCallEntry 90 }

sonusActiveCallEgressActAudioType OBJECT-TYPE
    SYNTAX          INTEGER
    ACCESS          read-only
    STATUS          mandatory
    DESCRIPTION     
            "indicate actual audio type"
    ::= { sonusActiveCallEntry 91 }

sonusActiveCallType OBJECT-TYPE
    SYNTAX          INTEGER { simple(0), parent(1), child(2), master(3), 
                        slave(4) }
    ACCESS          read-only
    STATUS          mandatory
    DESCRIPTION     
            "indicates the call type"
    ::= { sonusActiveCallEntry 92 }

sonusActiveCallAssociatedGcid1 OBJECT-TYPE
    SYNTAX          INTEGER
    ACCESS          read-only
    STATUS          mandatory
    DESCRIPTION     
            "GCID of another call which is associated with this call"
    ::= { sonusActiveCallEntry 93 }

sonusActiveCallAssociatedGcid2 OBJECT-TYPE
    SYNTAX          INTEGER
    ACCESS          read-only
    STATUS          mandatory
    DESCRIPTION     
            "GCID of another call which is associated with this call"
    ::= { sonusActiveCallEntry 94 }

sonusActiveCallAssociatedGcid3 OBJECT-TYPE
    SYNTAX          INTEGER
    ACCESS          read-only
    STATUS          mandatory
    DESCRIPTION     
            "GCID of another call which is associated with this call"
    ::= { sonusActiveCallEntry 95 }

sonusActiveCallAssociatedGcid4 OBJECT-TYPE
    SYNTAX          INTEGER
    ACCESS          read-only
    STATUS          mandatory
    DESCRIPTION     
            "GCID of another call which is associated with this call"
    ::= { sonusActiveCallEntry 96 }

sonusActiveCallAssociatedGcid5 OBJECT-TYPE
    SYNTAX          INTEGER
    ACCESS          read-only
    STATUS          mandatory
    DESCRIPTION     
            "GCID of another call which is associated with this call"
    ::= { sonusActiveCallEntry 97 }

sonusActiveCallIngressECMaxTail OBJECT-TYPE
    SYNTAX          INTEGER (0..6)
    ACCESS          read-only
    STATUS          mandatory
    DESCRIPTION     
            "indicate ingress echo cancellor max tail configuration "
    ::= { sonusActiveCallEntry 98 }

sonusActiveCallEgressECMaxTail OBJECT-TYPE
    SYNTAX          INTEGER (0..6)
    ACCESS          read-only
    STATUS          mandatory
    DESCRIPTION     
            "indicate egress echo cancellor max tail configuration "
    ::= { sonusActiveCallEntry 99 }

sonusActiveCallAssociatedGcid6 OBJECT-TYPE
    SYNTAX          INTEGER
    ACCESS          read-only
    STATUS          mandatory
    DESCRIPTION     
            "GCID of another call which is associated with this call"
    ::= { sonusActiveCallEntry 100 }

sonusActiveCallAssociatedGcidLegId1 OBJECT-TYPE
    SYNTAX          INTEGER
    ACCESS          read-only
    STATUS          mandatory
    DESCRIPTION     
            "call leg ID corresponding to sonusActiveCallAssociatedGcid1"
    ::= { sonusActiveCallEntry 101 }

sonusActiveCallAssociatedGcidLegId2 OBJECT-TYPE
    SYNTAX          INTEGER
    ACCESS          read-only
    STATUS          mandatory
    DESCRIPTION     
            "call leg ID corresponding to sonusActiveCallAssociatedGcid2"
    ::= { sonusActiveCallEntry 102 }

sonusActiveCallAssociatedGcidLegId3 OBJECT-TYPE
    SYNTAX          INTEGER
    ACCESS          read-only
    STATUS          mandatory
    DESCRIPTION     
            "call leg ID corresponding to sonusActiveCallAssociatedGcid3"
    ::= { sonusActiveCallEntry 103 }

sonusActiveCallAssociatedGcidLegId4 OBJECT-TYPE
    SYNTAX          INTEGER
    ACCESS          read-only
    STATUS          mandatory
    DESCRIPTION     
            "call leg ID corresponding to sonusActiveCallAssociatedGcid4"
    ::= { sonusActiveCallEntry 104 }

sonusActiveCallAssociatedGcidLegId5 OBJECT-TYPE
    SYNTAX          INTEGER
    ACCESS          read-only
    STATUS          mandatory
    DESCRIPTION     
            "call leg ID corresponding to sonusActiveCallAssociatedGcid5"
    ::= { sonusActiveCallEntry 105 }

sonusActiveCallAssociatedGcidLegId6 OBJECT-TYPE
    SYNTAX          INTEGER
    ACCESS          read-only
    STATUS          mandatory
    DESCRIPTION     
            "call leg ID corresponding to sonusActiveCallAssociatedGcid6"
    ::= { sonusActiveCallEntry 106 }

sonusActiveCallP2PStatsValid OBJECT-TYPE
    SYNTAX          INTEGER { unknown(0), invalid(1), valid(2) }
    ACCESS          read-only
    STATUS          mandatory
    DESCRIPTION     
            "For P2P calls only, indicates the validity of the P2P RTP statistics for egress side of call."
    ::= { sonusActiveCallEntry 107 }

sonusActiveCallP2PPacketsSent OBJECT-TYPE
    SYNTAX          INTEGER
    ACCESS          read-only
    STATUS          mandatory
    DESCRIPTION     
            "Indicates the number of RTP packets sent on egress side of a P2P call."
    ::= { sonusActiveCallEntry 108 }

sonusActiveCallP2PPacketsReceived OBJECT-TYPE
    SYNTAX          INTEGER
    ACCESS          read-only
    STATUS          mandatory
    DESCRIPTION     
            "Indicates the number of RTP packets received on egress side of a P2P call."
    ::= { sonusActiveCallEntry 109 }

sonusActiveCallP2POctetsSent OBJECT-TYPE
    SYNTAX          INTEGER
    ACCESS          read-only
    STATUS          mandatory
    DESCRIPTION     
            "Indicates the number of RTP octets sent on egress side of a P2P call."
    ::= { sonusActiveCallEntry 110 }

sonusActiveCallP2POctetsReceived OBJECT-TYPE
    SYNTAX          INTEGER
    ACCESS          read-only
    STATUS          mandatory
    DESCRIPTION     
            "Indicates the number of RTP octets received on egress side of a P2P call."
    ::= { sonusActiveCallEntry 111 }

sonusActiveCallP2PPacketsLost OBJECT-TYPE
    SYNTAX          INTEGER
    ACCESS          read-only
    STATUS          mandatory
    DESCRIPTION     
            "Indicates the number of RTP packets lost on egress side of a P2P call."
    ::= { sonusActiveCallEntry 112 }

sonusActiveCallP2PPacketsDiscarded OBJECT-TYPE
    SYNTAX          INTEGER
    ACCESS          read-only
    STATUS          mandatory
    DESCRIPTION     
            "Indicates the number of RTP packets discarded by the jitter buffer on egress side of a P2P call."
    ::= { sonusActiveCallEntry 113 }

sonusActiveCallP2PInterarrivalJitter OBJECT-TYPE
    SYNTAX          INTEGER
    ACCESS          read-only
    STATUS          mandatory
    DESCRIPTION     
            "Indicates the interarrival packet jitter on egress side of a P2P call."
    ::= { sonusActiveCallEntry 114 }

sonusActiveCallP2PPacketLatency OBJECT-TYPE
    SYNTAX          INTEGER
    ACCESS          read-only
    STATUS          mandatory
    DESCRIPTION     
            "Indicates the latency experienced on egress side of a P2P call."
    ::= { sonusActiveCallEntry 115 }

sonusActiveCallIpLoopIngressAssocGcid OBJECT-TYPE
    SYNTAX          INTEGER
    ACCESS          read-only
    STATUS          mandatory
    DESCRIPTION     
            "GCID of another call leg which is IP looped with the Ingress leg "
    ::= { sonusActiveCallEntry 116 }

sonusActiveCallIpLoopEgressAssocGcid OBJECT-TYPE
    SYNTAX          INTEGER
    ACCESS          read-only
    STATUS          mandatory
    DESCRIPTION     
            "GCID of another call leg which is IP looped with the Egress leg"
    ::= { sonusActiveCallEntry 117 }

sonusActiveCallIpLoopIngressAssocLegId OBJECT-TYPE
    SYNTAX          INTEGER
    ACCESS          read-only
    STATUS          mandatory
    DESCRIPTION     
            "Leg Id of another call Leg which is IP looped with the Ingress leg "
    ::= { sonusActiveCallEntry 118 }

sonusActiveCallIpLoopEgressAssocLegId OBJECT-TYPE
    SYNTAX          INTEGER
    ACCESS          read-only
    STATUS          mandatory
    DESCRIPTION     
            "Leg Id of another call leg which is IP looped with the Egress leg "
    ::= { sonusActiveCallEntry 119 }

sonusActiveCallIngressSrtpCrypto OBJECT-TYPE
    SYNTAX          INTEGER { null(0), aescm(1), f8(2) }
    ACCESS          read-only
    STATUS          mandatory
    DESCRIPTION     
            "Ingress sRTP crypto type for IP call legs"
    ::= { sonusActiveCallEntry 120 }

sonusActiveCallIngressSrtpAuth OBJECT-TYPE
    SYNTAX          INTEGER { none(0), hmacsha132(1), hmacsha180(2) }
    ACCESS          read-only
    STATUS          mandatory
    DESCRIPTION     
            "Ingress sRTP authentication type for IP call legs"
    ::= { sonusActiveCallEntry 121 }

sonusActiveCallEgressSrtpCrypto OBJECT-TYPE
    SYNTAX          INTEGER { null(0), aescm(1), f8(2) }
    ACCESS          read-only
    STATUS          mandatory
    DESCRIPTION     
            "Egress sRTP crypto type for IP call legs"
    ::= { sonusActiveCallEntry 122 }

sonusActiveCallEgressSrtpAuth OBJECT-TYPE
    SYNTAX          INTEGER { none(0), hmacsha132(1), hmacsha180(2) }
    ACCESS          read-only
    STATUS          mandatory
    DESCRIPTION     
            "Egress sRTP authentication type for IP call legs"
    ::= { sonusActiveCallEntry 123 }

sonusActiveCallIngressSrtcpCrypto OBJECT-TYPE
    SYNTAX          INTEGER { null(0), aescm(1), f8(2) }
    ACCESS          read-only
    STATUS          mandatory
    DESCRIPTION     
            "Ingress sRTCP crypto type for IP call legs"
    ::= { sonusActiveCallEntry 124 }

sonusActiveCallIngressSrtcpAuth OBJECT-TYPE
    SYNTAX          INTEGER { none(0), hmacsha132(1), hmacsha180(2) }
    ACCESS          read-only
    STATUS          mandatory
    DESCRIPTION     
            "Ingress sRTCP authentication type for IP call legs"
    ::= { sonusActiveCallEntry 125 }

sonusActiveCallEgressSrtcpCrypto OBJECT-TYPE
    SYNTAX          INTEGER { null(0), aescm(1), f8(2) }
    ACCESS          read-only
    STATUS          mandatory
    DESCRIPTION     
            "Egress sRTCP crypto type for IP call legs"
    ::= { sonusActiveCallEntry 126 }

sonusActiveCallEgressSrtcpAuth OBJECT-TYPE
    SYNTAX          INTEGER { none(0), hmacsha132(1), hmacsha180(2) }
    ACCESS          read-only
    STATUS          mandatory
    DESCRIPTION     
            "Egress sRTCP authentication type for IP call legs"
    ::= { sonusActiveCallEntry 127 }

sonusActiveCallVideoDuration OBJECT-TYPE
    SYNTAX          INTEGER
    ACCESS          read-only
    STATUS          mandatory
    DESCRIPTION     
            "Number of seconds that video resources were allocated to 
             the call."
    ::= { sonusActiveCallEntry 128 }

sonusActiveCallVideoBandwidth OBJECT-TYPE
    SYNTAX          INTEGER
    ACCESS          read-only
    STATUS          mandatory
    DESCRIPTION     
            "Maximim bandwidth in Kbps for the video stream."
    ::= { sonusActiveCallEntry 129 }

sonusActiveCallIngressVideoLocalIpSockAddr OBJECT-TYPE
    SYNTAX          IpAddress
    ACCESS          read-only
    STATUS          mandatory
    DESCRIPTION     
            "For IP Video calls, indicates the IP address of the
             video stream for the ingress local socket connection."
    ::= { sonusActiveCallEntry 130 }

sonusActiveCallIngressVideoRemoteIpSockAddr OBJECT-TYPE
    SYNTAX          IpAddress
    ACCESS          read-only
    STATUS          mandatory
    DESCRIPTION     
            "For IP Video calls, indicates the IP address of the
             video stream for the ingress remote socket connection."
    ::= { sonusActiveCallEntry 131 }

sonusActiveCallEgressVideoLocalIpSockAddr OBJECT-TYPE
    SYNTAX          IpAddress
    ACCESS          read-only
    STATUS          mandatory
    DESCRIPTION     
            "For IP Video calls, indicates the IP address of the
             video stream for the egress local socket connection."
    ::= { sonusActiveCallEntry 132 }

sonusActiveCallEgressVideoRemoteIpSockAddr OBJECT-TYPE
    SYNTAX          IpAddress
    ACCESS          read-only
    STATUS          mandatory
    DESCRIPTION     
            "For IP Video calls, indicates the IP address of the
             video stream for the egress remote socket connection."
    ::= { sonusActiveCallEntry 133 }

sonusActiveCallIngressVideoStatsValid OBJECT-TYPE
    SYNTAX          INTEGER { unknown(0), invalid(1), valid(2) }
    ACCESS          read-only
    STATUS          mandatory
    DESCRIPTION     
            "For video IP calls, indicates the validity of the RTP 
             statistics for the ingress side of the video stream."
    ::= { sonusActiveCallEntry 134 }

sonusActiveCallIngressVideoPacketsSent OBJECT-TYPE
    SYNTAX          INTEGER
    ACCESS          read-only
    STATUS          mandatory
    DESCRIPTION     
            "For video IP calls, indicates the number of RTP packets 
             sent on the ingress side of the video stream."
    ::= { sonusActiveCallEntry 135 }

sonusActiveCallIngressVideoPacketsReceived OBJECT-TYPE
    SYNTAX          INTEGER
    ACCESS          read-only
    STATUS          mandatory
    DESCRIPTION     
            "For video IP calls, indicates the number of RTP packets 
             received on the ingress side of the video stream."
    ::= { sonusActiveCallEntry 136 }

sonusActiveCallIngressVideoOctetsSent OBJECT-TYPE
    SYNTAX          INTEGER
    ACCESS          read-only
    STATUS          mandatory
    DESCRIPTION     
            "For video IP calls, indicates the number of RTP bytes 
             sent on the ingress side of the video stream."
    ::= { sonusActiveCallEntry 137 }

sonusActiveCallIngressVideoOctetsReceived OBJECT-TYPE
    SYNTAX          INTEGER
    ACCESS          read-only
    STATUS          mandatory
    DESCRIPTION     
            "For video IP calls, indicates the number of RTP bytes 
             received on the ingress side of the video stream."
    ::= { sonusActiveCallEntry 138 }

sonusActiveCallIngressVideoPacketsLost OBJECT-TYPE
    SYNTAX          INTEGER
    ACCESS          read-only
    STATUS          mandatory
    DESCRIPTION     
            "For video IP calls, indicates the number of RTP packets 
             lost on the ingress side of the video stream."
    ::= { sonusActiveCallEntry 139 }

sonusActiveCallIngressVideoPacketsDiscarded OBJECT-TYPE
    SYNTAX          INTEGER
    ACCESS          read-only
    STATUS          mandatory
    DESCRIPTION     
            "For video IP calls, indicates the number of RTP packets 
             discarded by the jitter buffer on the ingress side of the 
             video stream."
    ::= { sonusActiveCallEntry 140 }

sonusActiveCallIngressVideoPacketLatency OBJECT-TYPE
    SYNTAX          INTEGER
    ACCESS          read-only
    STATUS          mandatory
    DESCRIPTION     
            "For video IP calls, indicates the latency experienced on 
             the ingress side of the video stream."
    ::= { sonusActiveCallEntry 141 }

sonusActiveCallIngressVideoInterarrivalJitter OBJECT-TYPE
    SYNTAX          INTEGER
    ACCESS          read-only
    STATUS          mandatory
    DESCRIPTION     
            "For video IP calls, indicates the interarrival packet 
             jitter on the ingress side of the video stream."
    ::= { sonusActiveCallEntry 142 }

sonusActiveCallEgressVideoStatsValid OBJECT-TYPE
    SYNTAX          INTEGER { unknown(0), invalid(1), valid(2) }
    ACCESS          read-only
    STATUS          mandatory
    DESCRIPTION     
            "For video IP calls, indicates the validity of the RTP 
             statistics for the egress side of the video stream."
    ::= { sonusActiveCallEntry 143 }

sonusActiveCallEgressVideoPacketsSent OBJECT-TYPE
    SYNTAX          INTEGER
    ACCESS          read-only
    STATUS          mandatory
    DESCRIPTION     
            "For video IP calls, indicates the number of RTP packets 
             sent on the egress side of the video stream."
    ::= { sonusActiveCallEntry 144 }

sonusActiveCallEgressVideoPacketsReceived OBJECT-TYPE
    SYNTAX          INTEGER
    ACCESS          read-only
    STATUS          mandatory
    DESCRIPTION     
            "For video IP calls, indicates the number of RTP packets 
             received on the egress side of the video stream."
    ::= { sonusActiveCallEntry 145 }

sonusActiveCallEgressVideoOctetsSent OBJECT-TYPE
    SYNTAX          INTEGER
    ACCESS          read-only
    STATUS          mandatory
    DESCRIPTION     
            "For video IP calls, indicates the number of RTP bytes 
             sent on the egress side of the video stream."
    ::= { sonusActiveCallEntry 146 }

sonusActiveCallEgressVideoOctetsReceived OBJECT-TYPE
    SYNTAX          INTEGER
    ACCESS          read-only
    STATUS          mandatory
    DESCRIPTION     
            "For video IP calls, indicates the number of RTP bytes 
             received on the egress side of the video stream."
    ::= { sonusActiveCallEntry 147 }

sonusActiveCallEgressVideoPacketsLost OBJECT-TYPE
    SYNTAX          INTEGER
    ACCESS          read-only
    STATUS          mandatory
    DESCRIPTION     
            "For video IP calls, indicates the number of RTP packets 
             lost on the egress side of the video stream."
    ::= { sonusActiveCallEntry 148 }

sonusActiveCallEgressVideoPacketsDiscarded OBJECT-TYPE
    SYNTAX          INTEGER
    ACCESS          read-only
    STATUS          mandatory
    DESCRIPTION     
            "For video IP calls, indicates the number of RTP packets 
             discarded by the jitter buffer on the egress side of the 
             video stream."
    ::= { sonusActiveCallEntry 149 }

sonusActiveCallEgressVideoPacketLatency OBJECT-TYPE
    SYNTAX          INTEGER
    ACCESS          read-only
    STATUS          mandatory
    DESCRIPTION     
            "For video IP calls, indicates the latency experienced on 
             the egress side of the video stream."
    ::= { sonusActiveCallEntry 150 }

sonusActiveCallEgressVideoInterarrivalJitter OBJECT-TYPE
    SYNTAX          INTEGER
    ACCESS          read-only
    STATUS          mandatory
    DESCRIPTION     
            "For video IP calls, indicates the interarrival packet 
             jitter on the egress side of the video stream."
    ::= { sonusActiveCallEntry 151 }

sonusActiveCallMediaType OBJECT-TYPE
    SYNTAX          INTEGER { notapplicable(0), passthru(1), 
                        directmedia(2), transcode(3) }
    ACCESS          read-only
    STATUS          mandatory
    DESCRIPTION     
            "Indicates the media type for this Active call"
    ::= { sonusActiveCallEntry 152 }

sonusActiveCallBiccIngressCktInfoValid OBJECT-TYPE
    SYNTAX          INTEGER { unknown(0), invalid(1), valid(2) }
    ACCESS          read-only
    STATUS          mandatory
    DESCRIPTION     
            "For Indicates if the current call is BICC call 
             and BICC CIC info is available or not for ingress Side."
    ::= { sonusActiveCallEntry 153 }

sonusActiveCallIngressBiccCICNum OBJECT-TYPE
    SYNTAX          INTEGER (1..24)
    ACCESS          read-only
    STATUS          mandatory
    DESCRIPTION     
            "For calls originating from the BICC side, 
             indicates the CIC on which the call is being carried."
    ::= { sonusActiveCallEntry 154 }

sonusActiveCallIngressBiccSlotNum OBJECT-TYPE
    SYNTAX          SonusSlotIndex
    ACCESS          read-only
    STATUS          mandatory
    DESCRIPTION     
            "For calls originating from the BICC side, indicates the slot
             of the circuit card on which the call was delivered."
    ::= { sonusActiveCallEntry 155 }

sonusActiveCallBiccEgressCktInfoValid OBJECT-TYPE
    SYNTAX          INTEGER { unknown(0), invalid(1), valid(2) }
    ACCESS          read-only
    STATUS          mandatory
    DESCRIPTION     
            "For Indicates if the current call is BICC call and BICC CIC 
             info is available or not for egress Side."
    ::= { sonusActiveCallEntry 156 }

sonusActiveCallEgressBiccSlotNum OBJECT-TYPE
    SYNTAX          SonusSlotIndex
    ACCESS          read-only
    STATUS          mandatory
    DESCRIPTION     
            "For calls delivered to the BICC side, indicates the slot
             of the circuit card on which the call was delivered."
    ::= { sonusActiveCallEntry 157 }

sonusActiveCallEgressBiccCICNum OBJECT-TYPE
    SYNTAX          INTEGER (1..24)
    ACCESS          read-only
    STATUS          mandatory
    DESCRIPTION     
            "For calls delivered to the BICC side, indicates the CIC channel
             on which the call is being carried."
    ::= { sonusActiveCallEntry 158 }

sonusActiveCallIngressLocalIp6SockAddr OBJECT-TYPE
    SYNTAX          Ipv6Address
    ACCESS          read-only
    STATUS          mandatory
    DESCRIPTION     
            "IPv6 Address"
    ::= { sonusActiveCallEntry 159 }

sonusActiveCallIngressLocalIpVersion OBJECT-TYPE
    SYNTAX          INTEGER { afInet(2), afInet6(24) }
    ACCESS          read-only
    STATUS          mandatory
    DESCRIPTION     
            "IP Address Type"
    ::= { sonusActiveCallEntry 160 }

sonusActiveCallIngressRemoteIp6SockAddr OBJECT-TYPE
    SYNTAX          Ipv6Address
    ACCESS          read-only
    STATUS          mandatory
    DESCRIPTION     
            "IPv6 Address"
    ::= { sonusActiveCallEntry 161 }

sonusActiveCallIngressRemoteIpVersion OBJECT-TYPE
    SYNTAX          INTEGER { afInet(2), afInet6(24) }
    ACCESS          read-only
    STATUS          mandatory
    DESCRIPTION     
            "IP Address Type"
    ::= { sonusActiveCallEntry 162 }

sonusActiveCallEgressLocalIp6SockAddr OBJECT-TYPE
    SYNTAX          Ipv6Address
    ACCESS          read-only
    STATUS          mandatory
    DESCRIPTION     
            "IPv6 Address"
    ::= { sonusActiveCallEntry 163 }

sonusActiveCallEgressLocalIpVersion OBJECT-TYPE
    SYNTAX          INTEGER { afInet(2), afInet6(24) }
    ACCESS          read-only
    STATUS          mandatory
    DESCRIPTION     
            "IP Address Type"
    ::= { sonusActiveCallEntry 164 }

sonusActiveCallEgressRemoteIp6SockAddr OBJECT-TYPE
    SYNTAX          Ipv6Address
    ACCESS          read-only
    STATUS          mandatory
    DESCRIPTION     
            "IPv6 Address"
    ::= { sonusActiveCallEntry 165 }

sonusActiveCallEgressRemoteIpVersion OBJECT-TYPE
    SYNTAX          INTEGER { afInet(2), afInet6(24) }
    ACCESS          read-only
    STATUS          mandatory
    DESCRIPTION     
            "IP Address Type"
    ::= { sonusActiveCallEntry 166 }

sonusActiveCallIngressVideoLocalIp6SockAddr OBJECT-TYPE
    SYNTAX          Ipv6Address
    ACCESS          read-only
    STATUS          mandatory
    DESCRIPTION     
            "IPv6 Address"
    ::= { sonusActiveCallEntry 167 }

sonusActiveCallIngressVideoLocalIpVersion OBJECT-TYPE
    SYNTAX          INTEGER { afInet(2), afInet6(24) }
    ACCESS          read-only
    STATUS          mandatory
    DESCRIPTION     
            "IP Address Type"
    ::= { sonusActiveCallEntry 168 }

sonusActiveCallIngressVideoRemoteIp6SockAddr OBJECT-TYPE
    SYNTAX          Ipv6Address
    ACCESS          read-only
    STATUS          mandatory
    DESCRIPTION     
            "IPv6 Address"
    ::= { sonusActiveCallEntry 169 }

sonusActiveCallIngressVideoRemoteIpVersion OBJECT-TYPE
    SYNTAX          INTEGER { afInet(2), afInet6(24) }
    ACCESS          read-only
    STATUS          mandatory
    DESCRIPTION     
            "IP Address Type"
    ::= { sonusActiveCallEntry 170 }

sonusActiveCallEgressVideoLocalIp6SockAddr OBJECT-TYPE
    SYNTAX          Ipv6Address
    ACCESS          read-only
    STATUS          mandatory
    DESCRIPTION     
            "IPv6 Address"
    ::= { sonusActiveCallEntry 171 }

sonusActiveCallEgressVideoLocalIpVersion OBJECT-TYPE
    SYNTAX          INTEGER { afInet(2), afInet6(24) }
    ACCESS          read-only
    STATUS          mandatory
    DESCRIPTION     
            "IP Address Type"
    ::= { sonusActiveCallEntry 172 }

sonusActiveCallEgressVideoRemoteIp6SockAddr OBJECT-TYPE
    SYNTAX          Ipv6Address
    ACCESS          read-only
    STATUS          mandatory
    DESCRIPTION     
            "IPv6 Address"
    ::= { sonusActiveCallEntry 173 }

sonusActiveCallEgressVideoRemoteIpVersion OBJECT-TYPE
    SYNTAX          INTEGER { afInet(2), afInet6(24) }
    ACCESS          read-only
    STATUS          mandatory
    DESCRIPTION     
            "IP Address Type"
    ::= { sonusActiveCallEntry 174 }

sonusCallResTable OBJECT-TYPE
    SYNTAX          SEQUENCE OF SonusCallResEntry
    ACCESS          not-accessible
    STATUS          mandatory
    DESCRIPTION     
            "This table presents the call resource data for the node. Each active
             call contains a set of allocated resources. This table provides a brief
             description and the information required to access detailed information
             about each allocated resource."
    ::= { sonusNodeResourcesMIBObjects 4 }

sonusCallResEntry OBJECT-TYPE
    SYNTAX          SonusCallResEntry
    ACCESS          not-accessible
    STATUS          mandatory
    DESCRIPTION     
            ""
    INDEX           { sonusCallResShelfIndex, sonusCallResSlotIndex, 
                      sonusCallResCallIndex, sonusCallResIndex }
    ::= { sonusCallResTable 1 }

SonusCallResEntry ::=
    SEQUENCE {
        sonusCallResShelfIndex          SonusShelfIndex,
        sonusCallResSlotIndex           SonusSlotIndex,
        sonusCallResCallIndex           INTEGER,
        sonusCallResIndex               INTEGER,
        sonusCallResId                  INTEGER,
        sonusCallResCallId              INTEGER,
        sonusCallResType                INTEGER,
        sonusCallResMgrHandle           INTEGER,
        sonusCallResMgrShelfIndex       SonusShelfIndex,
        sonusCallResMgrSlotIndex        SonusSlotIndex,
        sonusCallResCallLegId           INTEGER
    }

sonusCallResShelfIndex OBJECT-TYPE
    SYNTAX          SonusShelfIndex
    ACCESS          read-only
    STATUS          mandatory
    DESCRIPTION     
            "Identifies the target shelf containing the call to be accessed."
    ::= { sonusCallResEntry 1 }

sonusCallResSlotIndex OBJECT-TYPE
    SYNTAX          SonusSlotIndex
    ACCESS          read-only
    STATUS          mandatory
    DESCRIPTION     
            "Identifies the target slot containing the call to be accessed."
    ::= { sonusCallResEntry 2 }

sonusCallResCallIndex OBJECT-TYPE
    SYNTAX          INTEGER
    ACCESS          read-only
    STATUS          mandatory
    DESCRIPTION     
            "Identifies the target call to be accessed."
    ::= { sonusCallResEntry 3 }

sonusCallResIndex OBJECT-TYPE
    SYNTAX          INTEGER
    ACCESS          read-only
    STATUS          mandatory
    DESCRIPTION     
            "Identifies the target resource index to access within the call."
    ::= { sonusCallResEntry 4 }

sonusCallResId OBJECT-TYPE
    SYNTAX          INTEGER
    ACCESS          read-only
    STATUS          mandatory
    DESCRIPTION     
            "Represents the internal resource identifier that uniquely represents
             the resource to the resource manager entity responsible for the
             resource."
    ::= { sonusCallResEntry 5 }

sonusCallResCallId OBJECT-TYPE
    SYNTAX          INTEGER
    ACCESS          read-only
    STATUS          mandatory
    DESCRIPTION     
            "Represents the global call identifier (GCID) for the call to which this
             resource is allocated. This information is provided to ensure that the 
             resource is truly allocated to the call."
    ::= { sonusCallResEntry 6 }

sonusCallResType OBJECT-TYPE
    SYNTAX          INTEGER { bresIcm(0), bresSw2Nif(1), 
                        bresSw2DspCtrl(2), bresSw2DspLocal(3), 
                        bresSw2DspSonic(4), bresDsp2Dsp(5), 
                        bresDsp2Sonic(6), bresLe2Sonic(7), bresAtm2Sw(8), 
                        bresSw2Atm(9), dresPstn(10), dresService(11), 
                        pres(12), xresCntrl(13), xresUser(14), 
                        aresAmq2Dsp(15), atmres(16), bresSw2DspApps(17), 
                        atmresVtoa(18), bresAtm2Sonic(19), fresIcm(20), 
                        fresSal2Sal2(21), fresSal2Dsp(22), 
                        fresSal2Ssb(23), fresDspDsp(24), fresDspSsb(25), 
                        fresLeSsb(26), fresSwDspctl(27), 
                        fresSwDspapp(28), fresSwNif(29), 
                        fresSwDsphdlcLocal(30), fresSwDsphdlcSsb(31), 
                        fresSal2dspSsb(32), xresFe(33), bresLe2Le(34), 
                        dresBrpad(35), bresMcast(36), bresDsp2Le(37), 
                        xresUserVid(38), bresLe2LeVid(39), 
                        bresDsp2Mcast(40), bresLe2Mcast(41), 
                        bresLe2SonicRtcprelay(42), 
                        bresLe2LeRtcprelay(43), 
                        bresLe2LeVidRtcprelay(44), bresLe2TxSplitter(45), 
                        bresLe2RxSplitter(46), bresTxSplitter2Sonic(47), 
                        bresRxSplitter2Sonic(48), bresLeTxOnly2Sonic(49), 
                        xresVirtual(50), bresDsp2LeRtcpDsp(51), 
                        bresDsp2SonicRtcpDsp(52), 
                        bresLe2SonicRtcpDsp(53) }
    ACCESS          read-only
    STATUS          mandatory
    DESCRIPTION     
            "Specifies the resource type for this resource."
    ::= { sonusCallResEntry 7 }

sonusCallResMgrHandle OBJECT-TYPE
    SYNTAX          INTEGER
    ACCESS          read-only
    STATUS          mandatory
    DESCRIPTION     
            "Specifies the internal handle for the resource manager entity responsible
             for this resource. This element is provided for information only."
    ::= { sonusCallResEntry 8 }

sonusCallResMgrShelfIndex OBJECT-TYPE
    SYNTAX          SonusShelfIndex
    ACCESS          read-only
    STATUS          mandatory
    DESCRIPTION     
            "Specifies the shelf on which this resource resides."
    ::= { sonusCallResEntry 9 }

sonusCallResMgrSlotIndex OBJECT-TYPE
    SYNTAX          SonusSlotIndex
    ACCESS          read-only
    STATUS          mandatory
    DESCRIPTION     
            "Specifies the card slot on which this resource resides."
    ::= { sonusCallResEntry 10 }

sonusCallResCallLegId OBJECT-TYPE
    SYNTAX          INTEGER
    ACCESS          read-only
    STATUS          mandatory
    DESCRIPTION     
            "The call leg ID which this resource resides."
    ::= { sonusCallResEntry 11 }

sonusCallPegCountsTable OBJECT-TYPE
    SYNTAX          SEQUENCE OF SonusCallPegCountsEntry
    ACCESS          not-accessible
    STATUS          mandatory
    DESCRIPTION     
            "This table presents call peg count statistics for the node."
    ::= { sonusNodeResourcesMIBObjects 5 }

sonusCallPegCountsEntry OBJECT-TYPE
    SYNTAX          SonusCallPegCountsEntry
    ACCESS          not-accessible
    STATUS          mandatory
    DESCRIPTION     
            ""
    INDEX           { sonusCallPegCountsShelfIndex, 
                      sonusCallPegCountsSlotIndex }
    ::= { sonusCallPegCountsTable 1 }

SonusCallPegCountsEntry ::=
    SEQUENCE {
        sonusCallPegCountsShelfIndex    SonusShelfIndex,
        sonusCallPegCountsSlotIndex     SonusSlotIndex,
        sonusCallPegCountsReset         INTEGER,
        sonusCallPegCountsAttempts      Counter,
        sonusCallPegCountsCompletions   Counter,
        sonusCallPegCountsActiveCalls   Gauge,
        sonusCallPegCountsStableCalls   Gauge,
        sonusCallPegCountsUpdates       Counter,
        sonusCallPegCountsActiveCallsNonUser    Gauge,
        sonusCallPegCountsStableCallsNonUser    Gauge,
        sonusCallPegCountsTotalCalls    Counter,
        sonusCallPegCountsTotalCallsNonUser   Counter,
        sonusCallPegCountsTotalCallsEmergEstablishing             Counter,
        sonusCallPegCountsTotalCallsEmergStable       Counter
    }

sonusCallPegCountsShelfIndex OBJECT-TYPE
    SYNTAX          SonusShelfIndex
    ACCESS          read-only
    STATUS          mandatory
    DESCRIPTION     
            "Identifies the target shelf to obtain the call counters."
    ::= { sonusCallPegCountsEntry 1 }

sonusCallPegCountsSlotIndex OBJECT-TYPE
    SYNTAX          SonusSlotIndex
    ACCESS          read-only
    STATUS          mandatory
    DESCRIPTION     
            "Identifies the target slot."
    ::= { sonusCallPegCountsEntry 2 }

sonusCallPegCountsReset OBJECT-TYPE
    SYNTAX          INTEGER { unknown(1), reset(2) }
    ACCESS          read-write
    STATUS          mandatory
    DESCRIPTION     
            "Provides a means to reset the active call attempt and
             completion counters. Any set operation on this object will
             result in the attempt and completion counters being cleared."
    ::= { sonusCallPegCountsEntry 3 }

sonusCallPegCountsAttempts OBJECT-TYPE
    SYNTAX          Counter
    ACCESS          read-only
    STATUS          mandatory
    DESCRIPTION     
            "Indicates the number of call attempts on this card."
    ::= { sonusCallPegCountsEntry 4 }

sonusCallPegCountsCompletions OBJECT-TYPE
    SYNTAX          Counter
    ACCESS          read-only
    STATUS          mandatory
    DESCRIPTION     
            "Indicates the total number of completed call attempts on this card."
    ::= { sonusCallPegCountsEntry 5 }

sonusCallPegCountsActiveCalls OBJECT-TYPE
    SYNTAX          Gauge
    ACCESS          read-only
    STATUS          mandatory
    DESCRIPTION     
            "Indicates the current number of active managed calls on this card. A managed
             call is one that a card is maintaining all resources for the call, including
             the assignment of the GCID (global call identifer). A card may also be simply
             providing resources for other calls, too. These non-managed calls are not
             reflected in this count."
    ::= { sonusCallPegCountsEntry 6 }

sonusCallPegCountsStableCalls OBJECT-TYPE
    SYNTAX          Gauge
    ACCESS          read-only
    STATUS          mandatory
    DESCRIPTION     
            "Indicates the current number of stable managed calls on this card. A managed
             call is one that a card is maintaining all resources for the call, including
             the assignment of the GCID (global call identifer). A card may also be simply
             providing resources for other calls, too. These non-managed calls are not
             reflected in this count."
    ::= { sonusCallPegCountsEntry 7 }

sonusCallPegCountsUpdates OBJECT-TYPE
    SYNTAX          Counter
    ACCESS          read-only
    STATUS          mandatory
    DESCRIPTION     
            "Indicates the number of call updates (modifications) on this card."
    ::= { sonusCallPegCountsEntry 8 }

sonusCallPegCountsActiveCallsNonUser OBJECT-TYPE
    SYNTAX          Gauge
    ACCESS          read-only
    STATUS          mandatory
    DESCRIPTION     
            "Indicates the current number of active non-call associated signalling channels in 
             the shelf. (ie ISDN D channel)"
    ::= { sonusCallPegCountsEntry 9 }

sonusCallPegCountsStableCallsNonUser OBJECT-TYPE
    SYNTAX          Gauge
    ACCESS          read-only
    STATUS          mandatory
    DESCRIPTION     
            "Indicates the current number of stable non-call associated signalling channels 
             in the shelf. (ie ISDN D channel)"
    ::= { sonusCallPegCountsEntry 10 }

sonusCallPegCountsTotalCalls OBJECT-TYPE
    SYNTAX          Counter
    ACCESS          read-only
    STATUS          mandatory
    DESCRIPTION     
            "Indicates the total number of calls that this card is participating in. The card
             may be actively managing the resources for the call or it may be simply providing 
             resources for the call."
    ::= { sonusCallPegCountsEntry 11 }

sonusCallPegCountsTotalCallsNonUser OBJECT-TYPE
    SYNTAX          Counter
    ACCESS          read-only
    STATUS          mandatory
    DESCRIPTION     
            "Indicates the total number of non-user calls that this card is participating in. 
             The card may be actively managing the resources for the call or it may be simply 
             providing resources for these non-user calls."
    ::= { sonusCallPegCountsEntry 12 }

sonusCallPegCountsTotalCallsEmergEstablishing OBJECT-TYPE
    SYNTAX          Counter
    ACCESS          read-only
    STATUS          mandatory
    DESCRIPTION     
            "Indicates the number of emergency calls which have GSX resources but are not
             stable."
    ::= { sonusCallPegCountsEntry 13 }

sonusCallPegCountsTotalCallsEmergStable OBJECT-TYPE
    SYNTAX          Counter
    ACCESS          read-only
    STATUS          mandatory
    DESCRIPTION     
            "Indicates the number of emergency calls which are stable."
    ::= { sonusCallPegCountsEntry 14 }

sonusToneObjects OBJECT IDENTIFIER
    ::= { sonusNodeResourcesMIBObjects 6 }

sonusToneProfile OBJECT IDENTIFIER
    ::= { sonusToneObjects 1 }

sonusToneProfileNextIndex OBJECT-TYPE
    SYNTAX          INTEGER
    ACCESS          read-only
    STATUS          mandatory
    DESCRIPTION     
            "The next valid index to use when creating an entry in
             the sonusToneProfileTable."
    ::= { sonusToneProfile 1 }

sonusToneProfileTable OBJECT-TYPE
    SYNTAX          SEQUENCE OF SonusToneProfileEntry
    ACCESS          not-accessible
    STATUS          mandatory
    DESCRIPTION     
            "This table contains tone profiles for the node."
    ::= { sonusToneProfile 2 }

sonusToneProfileEntry OBJECT-TYPE
    SYNTAX          SonusToneProfileEntry
    ACCESS          not-accessible
    STATUS          mandatory
    DESCRIPTION     
            ""
    INDEX           { sonusToneProfileIndex }
    ::= { sonusToneProfileTable 1 }

SonusToneProfileEntry ::=
    SEQUENCE {
        sonusToneProfileIndex           INTEGER,
        sonusToneProfileName            SonusName,
        sonusToneProfileGenerationMethod INTEGER,
        sonusToneProfileTone1Freq       INTEGER,
        sonusToneProfileTone1Power      INTEGER,
        sonusToneProfileTone2Freq       INTEGER,
        sonusToneProfileTone2Power      INTEGER,
        sonusToneProfileCarrierFreq     INTEGER,
        sonusToneProfileSignalFreq      INTEGER,
        sonusToneProfileModPower        INTEGER,
        sonusToneProfileModIndex        INTEGER,
        sonusToneProfileMake1           INTEGER,
        sonusToneProfileBreak1          INTEGER,
        sonusToneProfileMake2           INTEGER,
        sonusToneProfileBreak2          INTEGER,
        sonusToneProfileMake3           INTEGER,
        sonusToneProfileBreak3          INTEGER,
        sonusToneProfileRepeat          INTEGER,
        sonusToneProfileRowStatus       RowStatus,
        sonusToneProfileTone3Freq       INTEGER,
        sonusToneProfileTone3Power      INTEGER,
        sonusToneProfileTone4Freq       INTEGER,
        sonusToneProfileTone4Power      INTEGER,
        sonusToneProfileRepeatCadence1  INTEGER,
        sonusToneProfileRepeatCadence2  INTEGER,
        sonusToneProfileRepeatCadence3  INTEGER,
        sonusToneProfileDecayTimeConstant INTEGER,
        sonusToneProfileFrequencyChangeRate   INTEGER,
        sonusToneProfileDecayApplyToToneBitMap      INTEGER,
        sonusToneProfileTone1ApplyToCadenceNumber         INTEGER,
        sonusToneProfileTone2ApplyToCadenceNumber         INTEGER,
        sonusToneProfileTone3ApplyToCadenceNumber         INTEGER,
        sonusToneProfileTone4ApplyToCadenceNumber         INTEGER
    }

sonusToneProfileIndex OBJECT-TYPE
    SYNTAX          INTEGER
    ACCESS          read-only
    STATUS          mandatory
    DESCRIPTION     
            "Identifies the tone profile entry."
    ::= { sonusToneProfileEntry 1 }

sonusToneProfileName OBJECT-TYPE
    SYNTAX          SonusName
    ACCESS          read-write
    STATUS          mandatory
    DESCRIPTION     
            "The user name of this tone profile."
    ::= { sonusToneProfileEntry 2 }

sonusToneProfileGenerationMethod OBJECT-TYPE
    SYNTAX          INTEGER { singleTone(1), dualTone(2), 
                        modulatedTone(3), compositeTone(4) }
    ACCESS          read-write
    STATUS          mandatory
    DESCRIPTION     
            "Determines the generation method for the tone.  This value
             is specified at object creation time and cannot be modified."
    ::= { sonusToneProfileEntry 3 }

sonusToneProfileTone1Freq OBJECT-TYPE
    SYNTAX          INTEGER (0..3999)
    ACCESS          read-write
    STATUS          mandatory
    DESCRIPTION     
            "Specifies Tone 1 Frequency in Hertz.
             If 0, then silence is generated.
             Only valid if generation method is singleTone, dualTone, or compositeTone."
    DEFVAL          { 0 }
    ::= { sonusToneProfileEntry 4 }

sonusToneProfileTone1Power OBJECT-TYPE
    SYNTAX          INTEGER (-50..3)
    ACCESS          read-write
    STATUS          mandatory
    DESCRIPTION     
            "Specifies Tone 1 Power in dBm.  Power levels range from
             -50 dBm (minimum power) to +3 dBm (maximum power).
             Only valid if generation method is singleTone, dualTone, or compositeTone."
    DEFVAL          { 0 }
    ::= { sonusToneProfileEntry 5 }

sonusToneProfileTone2Freq OBJECT-TYPE
    SYNTAX          INTEGER (0..3999)
    ACCESS          read-write
    STATUS          mandatory
    DESCRIPTION     
            "Specifies Tone 2 Frequency in Hertz.
             If 0, then a single frequency tone is generated.
             Only valid if generation method is dualTone or compositeTone."
    DEFVAL          { 0 }
    ::= { sonusToneProfileEntry 6 }

sonusToneProfileTone2Power OBJECT-TYPE
    SYNTAX          INTEGER (-50..3)
    ACCESS          read-write
    STATUS          mandatory
    DESCRIPTION     
            "Specifies Tone 2 Power in dBm.  Power levels range from
             -50 dBm (minimum power) to +3 dBm (maximum power).
             Only valid if generation method is dualTone or compositeTone."
    DEFVAL          { 0 }
    ::= { sonusToneProfileEntry 7 }

sonusToneProfileCarrierFreq OBJECT-TYPE
    SYNTAX          INTEGER (0..3999)
    ACCESS          read-write
    STATUS          mandatory
    DESCRIPTION     
            "Specifies the frequency in Hertz of the carrier for the
             modulated signal.  Value must be less than 4000.
             If set to 0, then silence is generated.
             Only valid if generation method is modulatedTone."
    DEFVAL          { 0 }
    ::= { sonusToneProfileEntry 8 }

sonusToneProfileSignalFreq OBJECT-TYPE
    SYNTAX          INTEGER (0..3999)
    ACCESS          read-write
    STATUS          mandatory
    DESCRIPTION     
            "Specifies the frequency in Hertz of the sinusoid modulating
             the carrier sinusoid.  Value must be less than 4000.
             Only valid if generation method is modulatedTone."
    DEFVAL          { 0 }
    ::= { sonusToneProfileEntry 9 }

sonusToneProfileModPower OBJECT-TYPE
    SYNTAX          INTEGER (-50..3)
    ACCESS          read-write
    STATUS          mandatory
    DESCRIPTION     
            "Specifies Carrier Power in dBm.  Power levels range from
             -50 dBm (minimum power) to +3 dBm (maximum power).
             Only valid if generation method is modulatedTone."
    DEFVAL          { 0 }
    ::= { sonusToneProfileEntry 10 }

sonusToneProfileModIndex OBJECT-TYPE
    SYNTAX          INTEGER (0..300)
    ACCESS          read-write
    STATUS          mandatory
    DESCRIPTION     
            "Specifies the modulation index of the signal.
             Value must be in the range of 0 to 300 in 1% units.
             Only valid if generation method is modulatedTone."
    DEFVAL          { 0 }
    ::= { sonusToneProfileEntry 11 }

sonusToneProfileMake1 OBJECT-TYPE
    SYNTAX          INTEGER (-1..8000)
    ACCESS          read-write
    STATUS          mandatory
    DESCRIPTION     
            "Duration of the first on cadence in milliseconds.
             If 0, then the duration of the first on cadence is 0 msec.
             If -1, then the tone is played continuously."
    DEFVAL          { 0 }
    ::= { sonusToneProfileEntry 12 }

sonusToneProfileBreak1 OBJECT-TYPE
    SYNTAX          INTEGER (-1..8000)
    ACCESS          read-write
    STATUS          mandatory
    DESCRIPTION     
            "Duration of the first off cadence in milliseconds.
             If 0, then silence is not generated between the on cadences.
             If -1, then silence is generated continuously."
    DEFVAL          { 0 }
    ::= { sonusToneProfileEntry 13 }

sonusToneProfileMake2 OBJECT-TYPE
    SYNTAX          INTEGER (-1..8000)
    ACCESS          read-write
    STATUS          mandatory
    DESCRIPTION     
            "Duration of the second on cadence in milliseconds.
             If 0, then the duration of the second on cadence is 0 msec.
             If -1, then the tone is played continuously."
    DEFVAL          { 0 }
    ::= { sonusToneProfileEntry 14 }

sonusToneProfileBreak2 OBJECT-TYPE
    SYNTAX          INTEGER (-1..8000)
    ACCESS          read-write
    STATUS          mandatory
    DESCRIPTION     
            "Duration of the second off cadence in milliseconds.
             If 0, then silence is not generated between the on cadences.
             If -1, then silence is generated continuously."
    DEFVAL          { 0 }
    ::= { sonusToneProfileEntry 15 }

sonusToneProfileMake3 OBJECT-TYPE
    SYNTAX          INTEGER (-1..8000)
    ACCESS          read-write
    STATUS          mandatory
    DESCRIPTION     
            "Duration of the thrid on cadence in milliseconds.
             If 0, then the duration of the third on cadence is 0 msec.
             If -1, then the tone is played continuously."
    DEFVAL          { 0 }
    ::= { sonusToneProfileEntry 16 }

sonusToneProfileBreak3 OBJECT-TYPE
    SYNTAX          INTEGER (-1..8000)
    ACCESS          read-write
    STATUS          mandatory
    DESCRIPTION     
            "Duration of the third off cadence in milliseconds.
             If 0, then silence is not generated after the third on cadence.
             If -1, then silence is generated continuously."
    DEFVAL          { 0 }
    ::= { sonusToneProfileEntry 17 }

sonusToneProfileRepeat OBJECT-TYPE
    SYNTAX          INTEGER
    ACCESS          read-write
    STATUS          mandatory
    DESCRIPTION     
            "Number of overall cadence (1, 2, and 3 in sequence) cycles to generate.
             If 0, then the tone pattern is repeated indefinitely."
    DEFVAL          { 1 }
    ::= { sonusToneProfileEntry 18 }

sonusToneProfileRowStatus OBJECT-TYPE
    SYNTAX          RowStatus
    ACCESS          read-write
    STATUS          mandatory
    DESCRIPTION     
            ""
    ::= { sonusToneProfileEntry 19 }

sonusToneProfileTone3Freq OBJECT-TYPE
    SYNTAX          INTEGER (0..3999)
    ACCESS          read-write
    STATUS          mandatory
    DESCRIPTION     
            "Specifies Tone 3 Frequency in Hertz.
             If 0, then a single or dual frequency tone is generated.
             Only valid if generation method is compositeTone."
    DEFVAL          { 0 }
    ::= { sonusToneProfileEntry 20 }

sonusToneProfileTone3Power OBJECT-TYPE
    SYNTAX          INTEGER (-50..3)
    ACCESS          read-write
    STATUS          mandatory
    DESCRIPTION     
            "Specifies Tone 3 Power in dBm.  Power levels range from
             -50 dBm (minimum power) to +3 dBm (maximum power).
             Only valid if generation method is compositeTone."
    DEFVAL          { 0 }
    ::= { sonusToneProfileEntry 21 }

sonusToneProfileTone4Freq OBJECT-TYPE
    SYNTAX          INTEGER (0..3999)
    ACCESS          read-write
    STATUS          mandatory
    DESCRIPTION     
            "Specifies Tone 4 Frequency in Hertz.
             If 0, then a single or dual frequency tone is generated.
             Only valid if generation method is compositeTone."
    DEFVAL          { 0 }
    ::= { sonusToneProfileEntry 22 }

sonusToneProfileTone4Power OBJECT-TYPE
    SYNTAX          INTEGER (-50..3)
    ACCESS          read-write
    STATUS          mandatory
    DESCRIPTION     
            "Specifies Tone 4 Power in dBm.  Power levels range from
             -50 dBm (minimum power) to +3 dBm (maximum power).
             Only valid if generation method is compositeTone."
    DEFVAL          { 0 }
    ::= { sonusToneProfileEntry 23 }

sonusToneProfileRepeatCadence1 OBJECT-TYPE
    SYNTAX          INTEGER
    ACCESS          read-write
    STATUS          mandatory
    DESCRIPTION     
            "Number of cadence 1 cycles to generate.
             If 0, then the tone pattern is repeated indefinitely."
    DEFVAL          { 1 }
    ::= { sonusToneProfileEntry 24 }

sonusToneProfileRepeatCadence2 OBJECT-TYPE
    SYNTAX          INTEGER
    ACCESS          read-write
    STATUS          mandatory
    DESCRIPTION     
            "Number of cadence 2 cycles to generate.
             If 0, then the tone pattern is repeated indefinitely."
    DEFVAL          { 1 }
    ::= { sonusToneProfileEntry 25 }

sonusToneProfileRepeatCadence3 OBJECT-TYPE
    SYNTAX          INTEGER
    ACCESS          read-write
    STATUS          mandatory
    DESCRIPTION     
            "Number of cadence 3 cycles to generate.
             If 0, then the tone pattern is repeated indefinitely."
    DEFVAL          { 1 }
    ::= { sonusToneProfileEntry 26 }

sonusToneProfileDecayTimeConstant OBJECT-TYPE
    SYNTAX          INTEGER (0..2000)
    ACCESS          read-write
    STATUS          mandatory
    DESCRIPTION     
            "Specifies exponential decay time constant in milliseconds.
             If 0, then no decay is applied.  Maximum value is 2000 msec.
             Only valid if generation method is compositeTone."
    DEFVAL          { 0 }
    ::= { sonusToneProfileEntry 27 }

sonusToneProfileFrequencyChangeRate OBJECT-TYPE
    SYNTAX          INTEGER (0..1000)
    ACCESS          read-write
    STATUS          mandatory
    DESCRIPTION     
            "Specifies rate of change (Hz/s) of the tone frequency.
             If 0, then no frequency change rate is applied.
             Only valid if generation method is compositeTone."
    DEFVAL          { 0 }
    ::= { sonusToneProfileEntry 28 }

sonusToneProfileDecayApplyToToneBitMap OBJECT-TYPE
    SYNTAX          INTEGER (0..15)
    ACCESS          read-write
    STATUS          mandatory
    DESCRIPTION     
            "Specifies the tones to which decay and frequency rate change are applied.
             Application is by bitmap:
             If 0,  then decay/frequency rate change is not applied to any tone.
             If 1,  then decay/frequency rate change is applied to tone  1.
             If 2,  then decay/frequency rate change is applied to tone  2.
             If 3,  then decay/frequency rate change is applied to tones 1 and 2.
             If 4,  then decay/frequency rate change is applied to tones 3.
             ...etc...
             If 15, then decay/frequency rate change is applied to tones 1, 2, and 3.
             Only valid if generation method is compositeTone."
    DEFVAL          { 0 }
    ::= { sonusToneProfileEntry 29 }

sonusToneProfileTone1ApplyToCadenceNumber OBJECT-TYPE
    SYNTAX          INTEGER { allCadence(0), cadence1(1), cadence2(2), 
                        cadence3(3) }
    ACCESS          read-write
    STATUS          mandatory
    DESCRIPTION     
            "Specifies the cadences to which Tone 1 is applied.
             Application is as follows:
             If 0, then Tone 1 is applied to Cadences 1, 2, and 3.
             If 1, then Tone 1 is applied to Cadence  1.
             If 2, then Tone 1 is applied to Cadence  2.
             If 3, then Tone 1 is applied to Cadence  3.
             Only valid if generation method is compositeTone."
    DEFVAL          { allCadence }
    ::= { sonusToneProfileEntry 30 }

sonusToneProfileTone2ApplyToCadenceNumber OBJECT-TYPE
    SYNTAX          INTEGER { allCadence(0), cadence1(1), cadence2(2), 
                        cadence3(3) }
    ACCESS          read-write
    STATUS          mandatory
    DESCRIPTION     
            "Specifies the cadences to which Tone 2 is applied.
             Application is as follows:
             If 0, then Tone 2 is applied to Cadences 1, 2, and 3.
             If 1, then Tone 2 is applied to Cadence  1.
             If 2, then Tone 2 is applied to Cadence  2.
             If 3, then Tone 2 is applied to Cadence  3.
             Only valid if generation method is compositeTone."
    DEFVAL          { allCadence }
    ::= { sonusToneProfileEntry 31 }

sonusToneProfileTone3ApplyToCadenceNumber OBJECT-TYPE
    SYNTAX          INTEGER { allCadence(0), cadence1(1), cadence2(2), 
                        cadence3(3) }
    ACCESS          read-write
    STATUS          mandatory
    DESCRIPTION     
            "Specifies the cadences to which Tone 3 is applied.
             Application is as follows:
             If 0, then Tone 3 is applied to Cadences 1, 2, and 3.
             If 1, then Tone 3 is applied to Cadence  1.
             If 2, then Tone 3 is applied to Cadence  2.
             If 3, then Tone 3 is applied to Cadence  3.
             Only valid if generation method is compositeTone."
    DEFVAL          { allCadence }
    ::= { sonusToneProfileEntry 32 }

sonusToneProfileTone4ApplyToCadenceNumber OBJECT-TYPE
    SYNTAX          INTEGER { allCadence(0), cadence1(1), cadence2(2), 
                        cadence3(3) }
    ACCESS          read-write
    STATUS          mandatory
    DESCRIPTION     
            "Specifies the cadences to which Tone 1 is applied.
             Application is as follows:
             If 0, then Tone 4 is applied to Cadences 1, 2, and 3.
             If 1, then Tone 4 is applied to Cadence  1.
             If 2, then Tone 4 is applied to Cadence  2.
             If 3, then Tone 4 is applied to Cadence  3.
             Only valid if generation method is compositeTone."
    DEFVAL          { allCadence }
    ::= { sonusToneProfileEntry 33 }

sonusToneType OBJECT IDENTIFIER
    ::= { sonusToneObjects 2 }

sonusToneTypeNextIndex OBJECT-TYPE
    SYNTAX          INTEGER
    ACCESS          read-only
    STATUS          mandatory
    DESCRIPTION     
            "The next valid index to use when creating an entry in
             the sonusToneTypeTable."
    ::= { sonusToneType 1 }

sonusToneTypeTable OBJECT-TYPE
    SYNTAX          SEQUENCE OF SonusToneTypeEntry
    ACCESS          not-accessible
    STATUS          mandatory
    DESCRIPTION     
            "This table contains tone types for the node."
    ::= { sonusToneType 2 }

sonusToneTypeEntry OBJECT-TYPE
    SYNTAX          SonusToneTypeEntry
    ACCESS          not-accessible
    STATUS          mandatory
    DESCRIPTION     
            ""
    INDEX           { sonusToneTypeIndex }
    ::= { sonusToneTypeTable 1 }

SonusToneTypeEntry ::=
    SEQUENCE {
        sonusToneTypeIndex              INTEGER,
        sonusToneTypeName               SonusName,
        sonusToneTypeRowStatus          RowStatus
    }

sonusToneTypeIndex OBJECT-TYPE
    SYNTAX          INTEGER
    ACCESS          read-only
    STATUS          mandatory
    DESCRIPTION     
            "Identifies the tone type entry."
    ::= { sonusToneTypeEntry 1 }

sonusToneTypeName OBJECT-TYPE
    SYNTAX          SonusName
    ACCESS          read-write
    STATUS          mandatory
    DESCRIPTION     
            "The user name of this tone type.  Possible types include
             'dial', 'busy', 'reorder', etc."
    ::= { sonusToneTypeEntry 2 }

sonusToneTypeRowStatus OBJECT-TYPE
    SYNTAX          RowStatus
    ACCESS          read-write
    STATUS          mandatory
    DESCRIPTION     
            ""
    ::= { sonusToneTypeEntry 3 }

sonusTonePackage OBJECT IDENTIFIER
    ::= { sonusToneObjects 3 }

sonusTonePackageNextIndex OBJECT-TYPE
    SYNTAX          INTEGER
    ACCESS          read-only
    STATUS          mandatory
    DESCRIPTION     
            "The next valid index to use when creating an entry in
             the sonusTonePackageTable."
    ::= { sonusTonePackage 1 }

sonusTonePackageTable OBJECT-TYPE
    SYNTAX          SEQUENCE OF SonusTonePackageEntry
    ACCESS          not-accessible
    STATUS          mandatory
    DESCRIPTION     
            "This table contains tone packages for the node."
    ::= { sonusTonePackage 2 }

sonusTonePackageEntry OBJECT-TYPE
    SYNTAX          SonusTonePackageEntry
    ACCESS          not-accessible
    STATUS          mandatory
    DESCRIPTION     
            ""
    INDEX           { sonusTonePackageIndex }
    ::= { sonusTonePackageTable 1 }

SonusTonePackageEntry ::=
    SEQUENCE {
        sonusTonePackageIndex           INTEGER,
        sonusTonePackageName            SonusName,
        sonusTonePackageRowStatus       RowStatus,
        sonusTonePackageId              INTEGER
    }

sonusTonePackageIndex OBJECT-TYPE
    SYNTAX          INTEGER
    ACCESS          read-only
    STATUS          mandatory
    DESCRIPTION     
            "Identifies the tone package."
    ::= { sonusTonePackageEntry 1 }

sonusTonePackageName OBJECT-TYPE
    SYNTAX          SonusName
    ACCESS          read-write
    STATUS          mandatory
    DESCRIPTION     
            "The name of this tone package.  This name should reflect
             the country or carrier which will be using this package."
    ::= { sonusTonePackageEntry 2 }

sonusTonePackageRowStatus OBJECT-TYPE
    SYNTAX          RowStatus
    ACCESS          read-write
    STATUS          mandatory
    DESCRIPTION     
            ""
    ::= { sonusTonePackageEntry 3 }

sonusTonePackageId OBJECT-TYPE
    SYNTAX          INTEGER (1..65535)
    ACCESS          read-write
    STATUS          mandatory
    DESCRIPTION     
            "The tone package identifier defined by the 
             Sonus Softswitch for this package."
    ::= { sonusTonePackageEntry 4 }

sonusTonePkgElem OBJECT IDENTIFIER
    ::= { sonusToneObjects 4 }

sonusTonePkgElemTable OBJECT-TYPE
    SYNTAX          SEQUENCE OF SonusTonePkgElemEntry
    ACCESS          not-accessible
    STATUS          mandatory
    DESCRIPTION     
            "This table contains elements which bind tone types to
             tone profiles for a given tone package."
    ::= { sonusTonePkgElem 1 }

sonusTonePkgElemEntry OBJECT-TYPE
    SYNTAX          SonusTonePkgElemEntry
    ACCESS          not-accessible
    STATUS          mandatory
    DESCRIPTION     
            ""
    INDEX           { sonusTonePkgElemIndex }
    ::= { sonusTonePkgElemTable 1 }

SonusTonePkgElemEntry ::=
    SEQUENCE {
        sonusTonePkgElemIndex           INTEGER,
        sonusTonePkgElemTonePackageRef  SonusNameReference,
        sonusTonePkgElemToneTypeRef     SonusNameReference,
        sonusTonePkgElemToneProfileRef  SonusNameReference,
        sonusTonePkgElemRowStatus       RowStatus
    }

sonusTonePkgElemIndex OBJECT-TYPE
    SYNTAX          INTEGER
    ACCESS          read-only
    STATUS          mandatory
    DESCRIPTION     
            "Identifies the target tone package element."
    ::= { sonusTonePkgElemEntry 1 }

sonusTonePkgElemTonePackageRef OBJECT-TYPE
    SYNTAX          SonusNameReference
    ACCESS          read-write
    STATUS          mandatory
    DESCRIPTION     
            "Identifies the tone packge for this element."
    ::= { sonusTonePkgElemEntry 2 }

sonusTonePkgElemToneTypeRef OBJECT-TYPE
    SYNTAX          SonusNameReference
    ACCESS          read-write
    STATUS          mandatory
    DESCRIPTION     
            "Identifies the tone type for this element."
    ::= { sonusTonePkgElemEntry 3 }

sonusTonePkgElemToneProfileRef OBJECT-TYPE
    SYNTAX          SonusNameReference
    ACCESS          read-write
    STATUS          mandatory
    DESCRIPTION     
            "The name of the tone profile that this tone type maps
             to for this tone package."
    DEFVAL          { "default" }
    ::= { sonusTonePkgElemEntry 4 }

sonusTonePkgElemRowStatus OBJECT-TYPE
    SYNTAX          RowStatus
    ACCESS          read-write
    STATUS          mandatory
    DESCRIPTION     
            ""
    ::= { sonusTonePkgElemEntry 5 }

sonusDigitProfile OBJECT IDENTIFIER
    ::= { sonusNodeResourcesMIBObjects 7 }

sonusDigitProfileNextIndex OBJECT-TYPE
    SYNTAX          INTEGER
    ACCESS          read-only
    STATUS          mandatory
    DESCRIPTION     
            "The next valid index to use when creating an entry in
             the sonusDigitProfileTable."
    ::= { sonusDigitProfile 1 }

sonusDigitProfileTable OBJECT-TYPE
    SYNTAX          SEQUENCE OF SonusDigitProfileEntry
    ACCESS          not-accessible
    STATUS          mandatory
    DESCRIPTION     
            "This table contains digit profiles for the node.  Digit Profiles
             contain both digit generation (sonusDigitProfileGen...) and
             digit detection (sonusDigitProfileDet...) parameters."
    ::= { sonusDigitProfile 2 }

sonusDigitProfileEntry OBJECT-TYPE
    SYNTAX          SonusDigitProfileEntry
    ACCESS          not-accessible
    STATUS          mandatory
    DESCRIPTION     
            ""
    INDEX           { sonusDigitProfileIndex }
    ::= { sonusDigitProfileTable 1 }

SonusDigitProfileEntry ::=
    SEQUENCE {
        sonusDigitProfileIndex          INTEGER,
        sonusDigitProfileName           SonusName,
        sonusDigitProfileType           INTEGER,
        sonusDigitProfileGenPower       INTEGER,
        sonusDigitProfileGenMake        INTEGER,
        sonusDigitProfileGenBreak       INTEGER,
        sonusDigitProfileDetMinPower    INTEGER,
        sonusDigitProfileDetMinOnDuration INTEGER,
        sonusDigitProfileDetMinOffDuration  INTEGER,
        sonusDigitProfileDetFreqAcceptRange   INTEGER,
        sonusDigitProfileDtmfDetTwistCutoff   INTEGER,
        sonusDigitProfileMfr1GenMakeKp  INTEGER,
        sonusDigitProfileRowStatus      RowStatus,
        sonusDigitProfileMfr2DetMaxPulseDuration        INTEGER,
        sonusDigitProfileMfr2DetPostPulseDelay      INTEGER,
        sonusDigitProfileMfr2GenPrePulseDelay     INTEGER,
        sonusDigitProfileMfr2GenMaxFwdOnDuration        INTEGER,
        sonusDigitProfileMfr2GenMaxFwdOffDuration         INTEGER,
        sonusDigitProfileMfr2GenFinalDigitDelay       INTEGER
    }

sonusDigitProfileIndex OBJECT-TYPE
    SYNTAX          INTEGER
    ACCESS          read-only
    STATUS          mandatory
    DESCRIPTION     
            "Identifies the digit profile entry."
    ::= { sonusDigitProfileEntry 1 }

sonusDigitProfileName OBJECT-TYPE
    SYNTAX          SonusName
    ACCESS          read-write
    STATUS          mandatory
    DESCRIPTION     
            "The user name of this digit profile."
    ::= { sonusDigitProfileEntry 2 }

sonusDigitProfileType OBJECT-TYPE
    SYNTAX          INTEGER { dtmf(1), mfr1(2), mfr2(3), mfr2b(4) }
    ACCESS          read-write
    STATUS          mandatory
    DESCRIPTION     
            "Specifies the digit's format.  This value is set at object
             creation time and cannot be modified."
    ::= { sonusDigitProfileEntry 3 }

sonusDigitProfileGenPower OBJECT-TYPE
    SYNTAX          INTEGER (-50..3)
    ACCESS          read-write
    STATUS          mandatory
    DESCRIPTION     
            "Specifies digit generation power level in dBm.  Power level
             ranges from -50 dBm (minimum power) to +3 dBm (maximum power)."
    DEFVAL          { -10 }
    ::= { sonusDigitProfileEntry 4 }

sonusDigitProfileGenMake OBJECT-TYPE
    SYNTAX          INTEGER (0..8000)
    ACCESS          read-write
    STATUS          mandatory
    DESCRIPTION     
            "Specifies duration of generated digits in milliseconds."
    DEFVAL          { 100 }
    ::= { sonusDigitProfileEntry 5 }

sonusDigitProfileGenBreak OBJECT-TYPE
    SYNTAX          INTEGER (0..8000)
    ACCESS          read-write
    STATUS          mandatory
    DESCRIPTION     
            "Specifies silence between generated digits in milliseconds."
    DEFVAL          { 100 }
    ::= { sonusDigitProfileEntry 6 }

sonusDigitProfileDetMinPower OBJECT-TYPE
    SYNTAX          INTEGER (-45..-25)
    ACCESS          read-write
    STATUS          mandatory
    DESCRIPTION     
            "Specifies minimum power level in dBm required for digit
             detection.  Valid levels range from -45dBm to -25dBm."
    DEFVAL          { -45 }
    ::= { sonusDigitProfileEntry 7 }

sonusDigitProfileDetMinOnDuration OBJECT-TYPE
    SYNTAX          INTEGER (25..100)
    ACCESS          read-write
    STATUS          mandatory
    DESCRIPTION     
            "Specifies minimum tone duration in milliseconds required
             for digit detection.  The value must in increments of 5ms.
             For DTMF digits, the value must be between 25ms and 80ms.
             For MF digits, the value must be between 25ms and 100ms."
    DEFVAL          { 40 }
    ::= { sonusDigitProfileEntry 8 }

sonusDigitProfileDetMinOffDuration OBJECT-TYPE
    SYNTAX          INTEGER (10..100)
    ACCESS          read-write
    STATUS          mandatory
    DESCRIPTION     
            "Specifies minimum interdigit duration in milliseconds for
             digit detection.  The value must be in increments of 5ms.
             For DTMF digits, the value must be between 25ms and 80ms.
             For MF digits, the value must be between 10ms and 100ms.
             "
    DEFVAL          { 40 }
    ::= { sonusDigitProfileEntry 9 }

sonusDigitProfileDetFreqAcceptRange OBJECT-TYPE
    SYNTAX          INTEGER { narrow(1), medium(2), wide(3), wider(4) }
    ACCESS          read-write
    STATUS          mandatory
    DESCRIPTION     
            "Specifies frequency tolerances for digit detection.  For DTMF
             digits the value represents accept and reject ranges.  For MF
             digits the value represents only the accept range.	 Frequencies
             detected within the accept range will result in digit detection.
             Frequencies detected outside the reject range will not result
             in digit detection.
             .                   DTMF     DTMF       MFR1                  MFR2
             VALUE  ENUMERATION  ACCEPT   REJECT     ACCEPT                ACCEPT
             -----  -----------  ----------------    ------------------    --------------
             1      narrow       +/-2.0%  +/-3.0%    +/-(1.5% + 5Hz)       +/-(1.5% + 10Hz)
             2      medium       +/-2.5%  +/-3.5%    +/-(1.5% + 10Hz)      +/-(1.5% + 20Hz)
             3      wide         +/-3.0%  +/-4.0%    +/-(1.5% + 15Hz)      +/-(1.5% + 30Hz)
             4      wider        +/-3.5%  +/-4.5%    N/A                   N/A"
    DEFVAL          { 2 }
    ::= { sonusDigitProfileEntry 10 }

sonusDigitProfileDtmfDetTwistCutoff OBJECT-TYPE
    SYNTAX          INTEGER (4..12)
    ACCESS          read-write
    STATUS          mandatory
    DESCRIPTION     
            "For DTMF digit detection only.  Twist is the ratio of high
             group power to low.  Twist ratios below the twist cutoff will
             result in digit detection.  Twist ratios above the twist
             cutoff will result in digit rejection.
             Value must be between 4dB and 12dB in increments of 2dB."
    DEFVAL          { 8 }
    ::= { sonusDigitProfileEntry 11 }

sonusDigitProfileMfr1GenMakeKp OBJECT-TYPE
    SYNTAX          INTEGER (0..8000)
    ACCESS          read-write
    STATUS          mandatory
    DESCRIPTION     
            "Specifies duration of generated KP digit in milliseconds.
             Only applicable if digit type is MFR1."
    DEFVAL          { 105 }
    ::= { sonusDigitProfileEntry 12 }

sonusDigitProfileRowStatus OBJECT-TYPE
    SYNTAX          RowStatus
    ACCESS          read-write
    STATUS          mandatory
    DESCRIPTION     
            ""
    ::= { sonusDigitProfileEntry 13 }

sonusDigitProfileMfr2DetMaxPulseDuration OBJECT-TYPE
    SYNTAX          INTEGER (0..8000)
    ACCESS          read-write
    STATUS          mandatory
    DESCRIPTION     
            "For MFCR2 digit detection only. Maximum allowed duration of a received pulsed MF tone"
    DEFVAL          { 1000 }
    ::= { sonusDigitProfileEntry 14 }

sonusDigitProfileMfr2DetPostPulseDelay OBJECT-TYPE
    SYNTAX          INTEGER (0..8000)
    ACCESS          read-write
    STATUS          mandatory
    DESCRIPTION     
            "For MFCR2 digit detection only. Duration after a pulse signal is transmitted
             in which no forward signals will be recognized."
    DEFVAL          { 250 }
    ::= { sonusDigitProfileEntry 15 }

sonusDigitProfileMfr2GenPrePulseDelay OBJECT-TYPE
    SYNTAX          INTEGER (0..8000)
    ACCESS          read-write
    STATUS          mandatory
    DESCRIPTION     
            "For MFCR2 digit generation only. Delay between the end of the last compelled signal and
             the start of a backward pulsed signal."
    DEFVAL          { 100 }
    ::= { sonusDigitProfileEntry 16 }

sonusDigitProfileMfr2GenMaxFwdOnDuration OBJECT-TYPE
    SYNTAX          INTEGER (100..60000)
    ACCESS          read-write
    STATUS          mandatory
    DESCRIPTION     
            "For MFCR2 digit generation only. Maximum amount of time a forward signal is sent."
    DEFVAL          { 15000 }
    ::= { sonusDigitProfileEntry 17 }

sonusDigitProfileMfr2GenMaxFwdOffDuration OBJECT-TYPE
    SYNTAX          INTEGER (100..60000)
    ACCESS          read-write
    STATUS          mandatory
    DESCRIPTION     
            "For MFCR2 digit generation only. Maximum amount of time between the removal of a forward signal and
             the sending of the next forward signal."
    DEFVAL          { 27000 }
    ::= { sonusDigitProfileEntry 18 }

sonusDigitProfileMfr2GenFinalDigitDelay OBJECT-TYPE
    SYNTAX          INTEGER (0..8000)
    ACCESS          read-write
    STATUS          mandatory
    DESCRIPTION     
            "For MFCR2 digit generation only. Minimum interval after the sending of the last backward 
             compelled signal is complete that an answer line signal can be applied in the backward direction."
    DEFVAL          { 50 }
    ::= { sonusDigitProfileEntry 19 }

sonusStaticCall OBJECT IDENTIFIER
    ::= { sonusNodeResourcesMIBObjects 8 }

sonusStaticCallNextIndex OBJECT-TYPE
    SYNTAX          INTEGER
    ACCESS          read-only
    STATUS          mandatory
    DESCRIPTION     
            "The next valid index to use when creating an entry in
             the sonusStaticCallAdmnTable"
    ::= { sonusStaticCall 1 }

sonusStaticCallAdmnTable OBJECT-TYPE
    SYNTAX          SEQUENCE OF SonusStaticCallAdmnEntry
    ACCESS          not-accessible
    STATUS          mandatory
    DESCRIPTION     
            "This table specifies the static call list for the node."
    ::= { sonusStaticCall 2 }

sonusStaticCallAdmnEntry OBJECT-TYPE
    SYNTAX          SonusStaticCallAdmnEntry
    ACCESS          not-accessible
    STATUS          mandatory
    DESCRIPTION     
            ""
    INDEX           { sonusStaticCallAdmnIndex }
    ::= { sonusStaticCallAdmnTable 1 }

SonusStaticCallAdmnEntry ::=
    SEQUENCE {
        sonusStaticCallAdmnIndex        INTEGER,
        sonusStaticCallAdmnState        INTEGER,
        sonusStaticCallAdmnName         SonusName,
        sonusStaticCallAdmnEndPointAShelf SonusShelfIndex,
        sonusStaticCallAdmnEndPointASlot SonusSlotIndex,
        sonusStaticCallAdmnEndPointAPort INTEGER,
        sonusStaticCallAdmnEndPointAChannel   INTEGER,
        sonusStaticCallAdmnEndPointAServProfile       SonusName,
        sonusStaticCallAdmnEndPointBType INTEGER,
        sonusStaticCallAdmnEndPointBShelf SonusShelfIndex,
        sonusStaticCallAdmnEndPointBSlot SonusSlotIndex,
        sonusStaticCallAdmnEndPointBPort INTEGER,
        sonusStaticCallAdmnEndPointBChannel   INTEGER,
        sonusStaticCallAdmnEndPointBLocalRTPPort        INTEGER,
        sonusStaticCallAdmnEndPointBLocalIpAddress          IpAddress,
        sonusStaticCallAdmnEndPointBRemoteRTPPort         INTEGER,
        sonusStaticCallAdmnEndPointBRemoteIpAddress           IpAddress,
        sonusStaticCallAdmnEndPointBServProfile       SonusName,
        sonusStaticCallAdmnCircuitMode  INTEGER,
        sonusStaticCallAdmnRowStatus    RowStatus
    }

sonusStaticCallAdmnIndex OBJECT-TYPE
    SYNTAX          INTEGER
    ACCESS          read-only
    STATUS          mandatory
    DESCRIPTION     
            "Identifies the target static call entry."
    ::= { sonusStaticCallAdmnEntry 1 }

sonusStaticCallAdmnState OBJECT-TYPE
    SYNTAX          INTEGER { disabled(1), enabled(2) }
    ACCESS          read-write
    STATUS          mandatory
    DESCRIPTION     
            "The administrative state of this static call entry."
    DEFVAL          { disabled }
    ::= { sonusStaticCallAdmnEntry 2 }

sonusStaticCallAdmnName OBJECT-TYPE
    SYNTAX          SonusName
    ACCESS          read-write
    STATUS          mandatory
    DESCRIPTION     
            "The user name of this static call."
    ::= { sonusStaticCallAdmnEntry 3 }

sonusStaticCallAdmnEndPointAShelf OBJECT-TYPE
    SYNTAX          SonusShelfIndex
    ACCESS          read-write
    STATUS          mandatory
    DESCRIPTION     
            "A 32-bit integer identifying the shelf of the end point A"
    ::= { sonusStaticCallAdmnEntry 4 }

sonusStaticCallAdmnEndPointASlot OBJECT-TYPE
    SYNTAX          SonusSlotIndex
    ACCESS          read-write
    STATUS          mandatory
    DESCRIPTION     
            "A 32-bit integer identifying the slot of the end point A"
    ::= { sonusStaticCallAdmnEntry 5 }

sonusStaticCallAdmnEndPointAPort OBJECT-TYPE
    SYNTAX          INTEGER (1..65535)
    ACCESS          read-write
    STATUS          mandatory
    DESCRIPTION     
            "Port index of end point A."
    ::= { sonusStaticCallAdmnEntry 6 }

sonusStaticCallAdmnEndPointAChannel OBJECT-TYPE
    SYNTAX          INTEGER (1..32)
    ACCESS          read-write
    STATUS          mandatory
    DESCRIPTION     
            "Indicates the DS0 channel of the end point A"
    ::= { sonusStaticCallAdmnEntry 7 }

sonusStaticCallAdmnEndPointAServProfile OBJECT-TYPE
    SYNTAX          SonusName
    ACCESS          read-write
    STATUS          mandatory
    DESCRIPTION     
            "The service profile used for end point A"
    ::= { sonusStaticCallAdmnEntry 8 }

sonusStaticCallAdmnEndPointBType OBJECT-TYPE
    SYNTAX          INTEGER { circuit(1), packet(2) }
    ACCESS          read-write
    STATUS          mandatory
    DESCRIPTION     
            "The type of end point B (circuit or packet)."
    DEFVAL          { circuit }
    ::= { sonusStaticCallAdmnEntry 9 }

sonusStaticCallAdmnEndPointBShelf OBJECT-TYPE
    SYNTAX          SonusShelfIndex
    ACCESS          read-write
    STATUS          mandatory
    DESCRIPTION     
            "A 32-bit integer identifying the shelf of the end point B"
    ::= { sonusStaticCallAdmnEntry 10 }

sonusStaticCallAdmnEndPointBSlot OBJECT-TYPE
    SYNTAX          SonusSlotIndex
    ACCESS          read-write
    STATUS          mandatory
    DESCRIPTION     
            "A 32-bit integer identifying the slot of the end point B"
    ::= { sonusStaticCallAdmnEntry 11 }

sonusStaticCallAdmnEndPointBPort OBJECT-TYPE
    SYNTAX          INTEGER (1..65535)
    ACCESS          read-write
    STATUS          mandatory
    DESCRIPTION     
            "Port index of end point B."
    ::= { sonusStaticCallAdmnEntry 12 }

sonusStaticCallAdmnEndPointBChannel OBJECT-TYPE
    SYNTAX          INTEGER (1..32)
    ACCESS          read-write
    STATUS          mandatory
    DESCRIPTION     
            "Indicates the DS0 channel of the end point B"
    ::= { sonusStaticCallAdmnEntry 13 }

sonusStaticCallAdmnEndPointBLocalRTPPort OBJECT-TYPE
    SYNTAX          INTEGER
    ACCESS          read-write
    STATUS          mandatory
    DESCRIPTION     
            "Indicates the local RTP port."
    ::= { sonusStaticCallAdmnEntry 14 }

sonusStaticCallAdmnEndPointBLocalIpAddress OBJECT-TYPE
    SYNTAX          IpAddress
    ACCESS          read-write
    STATUS          mandatory
    DESCRIPTION     
            "The IP Address of the end point B if it is packet"
    ::= { sonusStaticCallAdmnEntry 15 }

sonusStaticCallAdmnEndPointBRemoteRTPPort OBJECT-TYPE
    SYNTAX          INTEGER
    ACCESS          read-write
    STATUS          mandatory
    DESCRIPTION     
            "Indicates the remote RTP port."
    ::= { sonusStaticCallAdmnEntry 16 }

sonusStaticCallAdmnEndPointBRemoteIpAddress OBJECT-TYPE
    SYNTAX          IpAddress
    ACCESS          read-write
    STATUS          mandatory
    DESCRIPTION     
            "The IP Address of the end point B if it is packet"
    ::= { sonusStaticCallAdmnEntry 17 }

sonusStaticCallAdmnEndPointBServProfile OBJECT-TYPE
    SYNTAX          SonusName
    ACCESS          read-write
    STATUS          mandatory
    DESCRIPTION     
            "The service profile used for end point B"
    ::= { sonusStaticCallAdmnEntry 18 }

sonusStaticCallAdmnCircuitMode OBJECT-TYPE
    SYNTAX          INTEGER { voice(1), data(2) }
    ACCESS          read-write
    STATUS          mandatory
    DESCRIPTION     
            "The circuit mode for this static call"
    DEFVAL          { voice }
    ::= { sonusStaticCallAdmnEntry 19 }

sonusStaticCallAdmnRowStatus OBJECT-TYPE
    SYNTAX          RowStatus
    ACCESS          read-write
    STATUS          mandatory
    DESCRIPTION     
            ""
    ::= { sonusStaticCallAdmnEntry 20 }

sonusStaticCallStatTable OBJECT-TYPE
    SYNTAX          SEQUENCE OF SonusStaticCallStatEntry
    ACCESS          not-accessible
    STATUS          mandatory
    DESCRIPTION     
            "The Manual Call Stat Table"
    ::= { sonusNodeResourcesMIBObjects 9 }

sonusStaticCallStatEntry OBJECT-TYPE
    SYNTAX          SonusStaticCallStatEntry
    ACCESS          not-accessible
    STATUS          mandatory
    DESCRIPTION     
            "An entry in the Manual Call Stat Table"
    INDEX           { sonusStaticCallStatIndex }
    ::= { sonusStaticCallStatTable 1 }

SonusStaticCallStatEntry ::=
    SEQUENCE {
        sonusStaticCallStatIndex        INTEGER,
        sonusStaticCallStatCallId       INTEGER,
        sonusStaticCallStatState        DisplayString,
        sonusStaticCallStatTime         DisplayString
    }

sonusStaticCallStatIndex OBJECT-TYPE
    SYNTAX          INTEGER
    ACCESS          read-only
    STATUS          mandatory
    DESCRIPTION     
            "The index for target static call."
    ::= { sonusStaticCallStatEntry 1 }

sonusStaticCallStatCallId OBJECT-TYPE
    SYNTAX          INTEGER
    ACCESS          read-only
    STATUS          mandatory
    DESCRIPTION     
            "The call identifier(GCID) assigned to this static call"
    ::= { sonusStaticCallStatEntry 2 }

sonusStaticCallStatState OBJECT-TYPE
    SYNTAX          DisplayString (SIZE(0..23))
    ACCESS          read-only
    STATUS          mandatory
    DESCRIPTION     
            "The status of the static call"
    ::= { sonusStaticCallStatEntry 3 }

sonusStaticCallStatTime OBJECT-TYPE
    SYNTAX          DisplayString (SIZE(0..23))
    ACCESS          read-only
    STATUS          mandatory
    DESCRIPTION     
            "Displays the Date/time the connection was created"
    ::= { sonusStaticCallStatEntry 4 }

sonusStaticCallActionObjects OBJECT IDENTIFIER
    ::= { sonusNodeResourcesMIBObjects 10 }

sonusStaticCallGcid OBJECT-TYPE
    SYNTAX          INTEGER
    ACCESS          read-write
    STATUS          mandatory
    DESCRIPTION     
            "The call identifier for a call to be deleted"
    ::= { sonusStaticCallActionObjects 1 }

sonusStaticCallAction OBJECT-TYPE
    SYNTAX          INTEGER { none(1), delete(2) }
    ACCESS          read-write
    STATUS          mandatory
    DESCRIPTION     
            "The action that should be taken on the call"
    DEFVAL          { none }
    ::= { sonusStaticCallActionObjects 2 }

sonusCallTrace OBJECT IDENTIFIER
    ::= { sonusNodeResourcesMIBObjects 11 }

sonusCallTraceNextIndex OBJECT-TYPE
    SYNTAX          INTEGER
    ACCESS          read-only
    STATUS          mandatory
    DESCRIPTION     
            "The next valid index to use when creating an entry in
             the sonusCallTraceTable."
    ::= { sonusCallTrace 1 }

sonusCallTraceTable OBJECT-TYPE
    SYNTAX          SEQUENCE OF SonusCallTraceEntry
    ACCESS          not-accessible
    STATUS          mandatory
    DESCRIPTION     
            "This table specifies the Call Trace Table"
    ::= { sonusCallTrace 2 }

sonusCallTraceEntry OBJECT-TYPE
    SYNTAX          SonusCallTraceEntry
    ACCESS          not-accessible
    STATUS          mandatory
    DESCRIPTION     
            ""
    INDEX           { sonusCallTraceIndex }
    ::= { sonusCallTraceTable 1 }

SonusCallTraceEntry ::=
    SEQUENCE {
        sonusCallTraceIndex             INTEGER,
        sonusCallTraceState             INTEGER,
        sonusCallTraceName              SonusName,
        sonusCallTraceType              INTEGER,
        sonusCallTraceCalledNumber      DisplayString,
        sonusCallTraceCallingNumber     DisplayString,
        sonusCallTraceLevel             INTEGER,
        sonusCallTraceRowStatus         RowStatus,
        sonusCallTraceKey               OCTET STRING,
        sonusCallTraceContractorNumber  DisplayString,
        sonusCallTraceRedirectingNumber DisplayString,
        sonusCallTraceTransferCapability INTEGER,
        sonusCallTraceSlot              SonusSlotIndex,
        sonusCallTracePort              INTEGER,
        sonusCallTraceChannel           INTEGER,
        sonusCallTraceServiceGroup      SonusNameReference,
        sonusCallTraceTrunkGroup        SonusNameReference,
        sonusCallTracePeerIpAddress     IpAddress,
        sonusCallTraceCalledDirectoryNumber   DisplayString,
        sonusCallTraceStopMatch         SonusSupportFlag,
        sonusCallTraceGR303IGIndex      Gauge,
        sonusCallTraceGR303CRV          INTEGER,
        sonusCallTracePeerIp6Address    Ipv6Address,
        sonusCallTracePeerIpVersion     INTEGER
    }

sonusCallTraceIndex OBJECT-TYPE
    SYNTAX          INTEGER
    ACCESS          read-only
    STATUS          mandatory
    DESCRIPTION     
            "The index of this Call Trace entry."
    ::= { sonusCallTraceEntry 1 }

sonusCallTraceState OBJECT-TYPE
    SYNTAX          INTEGER { disabled(1), enabled(2) }
    ACCESS          read-write
    STATUS          mandatory
    DESCRIPTION     
            "The administrative state of this Call Trace entry."
    DEFVAL          { disabled }
    ::= { sonusCallTraceEntry 2 }

sonusCallTraceName OBJECT-TYPE
    SYNTAX          SonusName
    ACCESS          read-write
    STATUS          mandatory
    DESCRIPTION     
            "The name of this Call Trace entry."
    ::= { sonusCallTraceEntry 3 }

sonusCallTraceType OBJECT-TYPE
    SYNTAX          INTEGER { calledcalling(1), calledonly(2), 
                        callingonly(3) }
    ACCESS          read-write
    STATUS          mandatory
    DESCRIPTION     
            "The trace type of this Call Trace entry."
    DEFVAL          { calledcalling }
    ::= { sonusCallTraceEntry 4 }

sonusCallTraceCalledNumber OBJECT-TYPE
    SYNTAX          DisplayString (SIZE(0..30))
    ACCESS          read-write
    STATUS          mandatory
    DESCRIPTION     
            "The called number being traced."
    ::= { sonusCallTraceEntry 5 }

sonusCallTraceCallingNumber OBJECT-TYPE
    SYNTAX          DisplayString (SIZE(0..30))
    ACCESS          read-write
    STATUS          mandatory
    DESCRIPTION     
            "The calling number being traced."
    ::= { sonusCallTraceEntry 6 }

sonusCallTraceLevel OBJECT-TYPE
    SYNTAX          INTEGER { level1(1), level2(2), level3(3) }
    ACCESS          read-write
    STATUS          mandatory
    DESCRIPTION     
            "The trace level of this call trace entry, currently only one level is supported."
    DEFVAL          { level2 }
    ::= { sonusCallTraceEntry 7 }

sonusCallTraceRowStatus OBJECT-TYPE
    SYNTAX          RowStatus
    ACCESS          read-write
    STATUS          mandatory
    DESCRIPTION     
            ""
    ::= { sonusCallTraceEntry 8 }

sonusCallTraceKey OBJECT-TYPE
    SYNTAX          OCTET STRING
--                       { called(0), calling(1), contractor(2), 
--                         redirecting(3), transferCapability(4), 
--                         slotPortChannel(5), serviceGroup(6), 
--                         trunkGroup(7), peerIpAddress(8), cddn(9), 
--                         gr303igcrv(10) }
    ACCESS          read-write
    STATUS          mandatory
    DESCRIPTION     
            "Indicates which key components are active on this filter.
             BIT 0 - Called Number is part of key
             BIT 1 - Calling Number is part of key
             BIT 2 - Contractor Number is part of key
             BIT 3 - Redirecting Number is part of key
             BIT 4 - Transfer Capability is part of key
             BIT 5 - Slot/Port/Channel is part of key
             BIT 6 - Service Group is part of key
             BIT 7 - Trunk Group is part of key
             BIT 8 - Peer IP Address is part of key
             BIT 9 - Called Directory Number
             BIT 10 - GR303 IG and CRV is part of key"
    ::= { sonusCallTraceEntry 9 }

sonusCallTraceContractorNumber OBJECT-TYPE
    SYNTAX          DisplayString (SIZE(0..30))
    ACCESS          read-write
    STATUS          mandatory
    DESCRIPTION     
            "The Contractor Number being traced."
    ::= { sonusCallTraceEntry 10 }

sonusCallTraceRedirectingNumber OBJECT-TYPE
    SYNTAX          DisplayString (SIZE(0..30))
    ACCESS          read-write
    STATUS          mandatory
    DESCRIPTION     
            "The Redirecting Number being traced."
    ::= { sonusCallTraceEntry 11 }

sonusCallTraceTransferCapability OBJECT-TYPE
    SYNTAX          INTEGER { speech(1), unrestricted(2), audio31Khz(3), 
                        unrestrictedWithTones(4), video(5), message(6) }
    ACCESS          read-write
    STATUS          mandatory
    DESCRIPTION     
            "The Transfer Capability of the call trace filter."
    ::= { sonusCallTraceEntry 12 }

sonusCallTraceSlot OBJECT-TYPE
    SYNTAX          SonusSlotIndex
    ACCESS          read-write
    STATUS          mandatory
    DESCRIPTION     
            "The Slot entry for a Call Trace Filter."
    ::= { sonusCallTraceEntry 13 }

sonusCallTracePort OBJECT-TYPE
    SYNTAX          INTEGER (1..65535)
    ACCESS          read-write
    STATUS          mandatory
    DESCRIPTION     
            "The Port entry for a Call Trace Filter."
    ::= { sonusCallTraceEntry 14 }

sonusCallTraceChannel OBJECT-TYPE
    SYNTAX          INTEGER (1..32)
    ACCESS          read-write
    STATUS          mandatory
    DESCRIPTION     
            "The Channel entry for a Call Trace Filter."
    ::= { sonusCallTraceEntry 15 }

sonusCallTraceServiceGroup OBJECT-TYPE
    SYNTAX          SonusNameReference
    ACCESS          read-write
    STATUS          mandatory
    DESCRIPTION     
            "The Service Group entry for a Call Trace Filter."
    ::= { sonusCallTraceEntry 16 }

sonusCallTraceTrunkGroup OBJECT-TYPE
    SYNTAX          SonusNameReference
    ACCESS          read-write
    STATUS          mandatory
    DESCRIPTION     
            "The Trunk Group entry for a Call Trace Filter."
    ::= { sonusCallTraceEntry 17 }

sonusCallTracePeerIpAddress OBJECT-TYPE
    SYNTAX          IpAddress
    ACCESS          read-write
    STATUS          mandatory
    DESCRIPTION     
            "The Peer IP Address for call tracing"
    DEFVAL          { '00000000'H }
    ::= { sonusCallTraceEntry 18 }

sonusCallTraceCalledDirectoryNumber OBJECT-TYPE
    SYNTAX          DisplayString (SIZE(0..30))
    ACCESS          read-write
    STATUS          mandatory
    DESCRIPTION     
            "The called directory number being traced."
    ::= { sonusCallTraceEntry 19 }

sonusCallTraceStopMatch OBJECT-TYPE
    SYNTAX          SonusSupportFlag
    ACCESS          read-write
    STATUS          mandatory
    DESCRIPTION     
            "Stop trying to match filter profiles after a match is found with this flag set to supported."
    DEFVAL          { unsupported }
    ::= { sonusCallTraceEntry 20 }

sonusCallTraceGR303IGIndex OBJECT-TYPE
    SYNTAX          Gauge (1..500)
    ACCESS          read-write
    STATUS          mandatory
    DESCRIPTION     
            "The Index of the GR303 Interface group being traced."
    ::= { sonusCallTraceEntry 23 }

sonusCallTraceGR303CRV OBJECT-TYPE
    SYNTAX          INTEGER (0..2048)
    ACCESS          read-write
    STATUS          mandatory
    DESCRIPTION     
            "The GR303 CRV being traced. The value of zero indicates all CRVs in an interface group
             and is set internally when CRV ALL is selected through the CLI."
    ::= { sonusCallTraceEntry 24 }

sonusCallTracePeerIp6Address OBJECT-TYPE
    SYNTAX          Ipv6Address
    ACCESS          read-write
    STATUS          mandatory
    DESCRIPTION     
            "The Peer IPV6 Address for call tracing"
    ::= { sonusCallTraceEntry 25 }

sonusCallTracePeerIpVersion OBJECT-TYPE
    SYNTAX          INTEGER { afInet(2), afInet6(24) }
    ACCESS          read-only
    STATUS          mandatory
    DESCRIPTION     
            "The Peer Address type for call tracing"
    ::= { sonusCallTraceEntry 26 }

sonusCktServProfile OBJECT IDENTIFIER
    ::= { sonusNodeResourcesMIBObjects 12 }

sonusCktServProfileNextIndex OBJECT-TYPE
    SYNTAX          INTEGER
    ACCESS          read-only
    STATUS          mandatory
    DESCRIPTION     
            "The next valid index to use when creating an entry in
             the sonusCktServProfileTable."
    ::= { sonusCktServProfile 1 }

sonusCktServProfileTable OBJECT-TYPE
    SYNTAX          SEQUENCE OF SonusCktServProfileEntry
    ACCESS          not-accessible
    STATUS          mandatory
    DESCRIPTION     
            "This table specifies the Circuit service profile list for the node."
    ::= { sonusCktServProfile 2 }

sonusCktServProfileEntry OBJECT-TYPE
    SYNTAX          SonusCktServProfileEntry
    ACCESS          not-accessible
    STATUS          mandatory
    DESCRIPTION     
            ""
    INDEX           { sonusCktServProfileIndex }
    ::= { sonusCktServProfileTable 1 }

SonusCktServProfileEntry ::=
    SEQUENCE {
        sonusCktServProfileIndex        INTEGER,
        sonusCktServProfileState        INTEGER,
        sonusCktServProfileName         SonusName,
        sonusCktServProfileAudioEncoding INTEGER,
        sonusCktServProfileBandwidth    INTEGER,
        sonusCktServProfileNecEnable    INTEGER,
        sonusCktServProfileCttTestType  INTEGER,
        sonusCktServProfileCttTimeout   INTEGER,
        sonusCktServProfileCttMinDetectTime   INTEGER,
        sonusCktServProfileCttMinReleaseTime    INTEGER,
        sonusCktServProfileCapability   INTEGER,
        sonusCktServProfileDataRestrictedCfg    INTEGER,
        sonusCktServProfileDtmfProfileName  SonusNameReference,
        sonusCktServProfileRowStatus    RowStatus,
        sonusCktServProfileInterworkingXfrCap     INTEGER,
        sonusCktServProfileTxLevelControl INTEGER,
        sonusCktServProfileRxLevelControl INTEGER,
        sonusCktServProfileTxGain       INTEGER,
        sonusCktServProfileRxGain       INTEGER
    }

sonusCktServProfileIndex OBJECT-TYPE
    SYNTAX          INTEGER
    ACCESS          read-only
    STATUS          mandatory
    DESCRIPTION     
            "Identifies the target circuit service profile entry."
    ::= { sonusCktServProfileEntry 1 }

sonusCktServProfileState OBJECT-TYPE
    SYNTAX          INTEGER { disabled(1), enabled(2) }
    ACCESS          read-write
    STATUS          mandatory
    DESCRIPTION     
            "The administrative state of this circuit service profile entry."
    DEFVAL          { disabled }
    ::= { sonusCktServProfileEntry 2 }

sonusCktServProfileName OBJECT-TYPE
    SYNTAX          SonusName
    ACCESS          read-write
    STATUS          mandatory
    DESCRIPTION     
            "The name of this circuit service profile."
    ::= { sonusCktServProfileEntry 3 }

sonusCktServProfileAudioEncoding OBJECT-TYPE
    SYNTAX          INTEGER { g711ulaw(1), g711alaw(2) }
    ACCESS          read-write
    STATUS          mandatory
    DESCRIPTION     
            "The audio encoding method to be performed on the voice data
             received from, and destined to the PSTN. The default encoding
             method is G.711 Ulaw."
    DEFVAL          { g711ulaw }
    ::= { sonusCktServProfileEntry 4 }

sonusCktServProfileBandwidth OBJECT-TYPE
    SYNTAX          INTEGER (1..24)
    ACCESS          read-write
    STATUS          mandatory
    DESCRIPTION     
            "The number of DS0 channels to group for Nx64 connections. 
             Valid entries are 1 to 24 channels, allowing up to a 
             complete set of T1 channels to be grouped at a single
             connection. The default bandwidth is 1 channel."
    DEFVAL          { 1 }
    ::= { sonusCktServProfileEntry 5 }

sonusCktServProfileNecEnable OBJECT-TYPE
    SYNTAX          INTEGER { disabled(1), enabled(2) }
    ACCESS          read-write
    STATUS          mandatory
    DESCRIPTION     
            "Specifies whether Network Echo Cancellation (NEC) is 
             enabled for the channel. When enabled, NEC is enabled
             acording to the appropriate NEC configuration parameters.
             When disabled, the echo chaceller is bypassed."
    DEFVAL          { enabled }
    ::= { sonusCktServProfileEntry 6 }

sonusCktServProfileCttTestType OBJECT-TYPE
    SYNTAX          INTEGER { remoteLoopback(1), remote2Wire(2), 
                        remote4Wire(3) }
    ACCESS          read-write
    STATUS          mandatory
    DESCRIPTION     
            "For ISUP service profiles, specifies the type of continuity
             test to perform, based on the configuration of the remote
             switch or trunk connection. The remoteLoopback test is used
             when the remote switch will loop back channel being tested.
             The remote2Wire test is used when the remote switch supports
             the 2 wire continuity test procedure. And the remote4Wire 
             test mode is used when the remote switch supports the 4 wire
             continuity test procedure. The default value is remoteLoopback."
    DEFVAL          { remoteLoopback }
    ::= { sonusCktServProfileEntry 7 }

sonusCktServProfileCttTimeout OBJECT-TYPE
    SYNTAX          INTEGER (1..8)
    ACCESS          read-write
    STATUS          mandatory
    DESCRIPTION     
            "For ISUP service profiles, specifies the overall test timeout
             value. The continuity test will be declared failed if the
             continuity tone is not detected within this timeout period. 
             The timeout is specified in seconds, with a default value of
             2 seconds."
    DEFVAL          { 2 }
    ::= { sonusCktServProfileEntry 8 }

sonusCktServProfileCttMinDetectTime OBJECT-TYPE
    SYNTAX          INTEGER (10..60)
    ACCESS          read-write
    STATUS          mandatory
    DESCRIPTION     
            "For ISUP service profiles, specifies the minimum time
             to detect the presence of the continuity test tone. The 
             minimum detect time is specified in milliseconds, with
             a default time of 45 ms."
    DEFVAL          { 45 }
    ::= { sonusCktServProfileEntry 9 }

sonusCktServProfileCttMinReleaseTime OBJECT-TYPE
    SYNTAX          INTEGER (10..40)
    ACCESS          read-write
    STATUS          mandatory
    DESCRIPTION     
            "For ISUP service profiles, specifies the minimum time
             to detect that the continuity test tone has been removed
             and is no longer present. The minimum release time
             is specified in milliseconds, with a default time of 25 ms."
    DEFVAL          { 25 }
    ::= { sonusCktServProfileEntry 10 }

sonusCktServProfileCapability OBJECT-TYPE
    SYNTAX          INTEGER { voiceOnly(1), circuitModeData(2), 
                        voiceOrCircuitModeData(3) }
    ACCESS          read-write
    STATUS          mandatory
    DESCRIPTION     
            "Specifies the data capabilities for the circuit. This parameter
             specifies whether voice only, circuit mode data only, or both voice
             and circuit mode data can be supported by the circuit."
    DEFVAL          { voiceOrCircuitModeData }
    ::= { sonusCktServProfileEntry 11 }

sonusCktServProfileDataRestrictedCfg OBJECT-TYPE
    SYNTAX          INTEGER { unrestricted(1), restricted(2) }
    ACCESS          read-write
    STATUS          mandatory
    DESCRIPTION     
            "Specifies whether the circuit may support 64 Kbit/s unrestricted data, 
             or if the circuit supports 56 Kbit/s restricted data."
    DEFVAL          { unrestricted }
    ::= { sonusCktServProfileEntry 12 }

sonusCktServProfileDtmfProfileName OBJECT-TYPE
    SYNTAX          SonusNameReference
    ACCESS          read-write
    STATUS          mandatory
    DESCRIPTION     
            "The name of DTMF profile associated with this circuit service profile."
    ::= { sonusCktServProfileEntry 13 }

sonusCktServProfileRowStatus OBJECT-TYPE
    SYNTAX          RowStatus
    ACCESS          read-write
    STATUS          mandatory
    DESCRIPTION     
            ""
    ::= { sonusCktServProfileEntry 14 }

sonusCktServProfileInterworkingXfrCap OBJECT-TYPE
    SYNTAX          INTEGER { speech(1), audio31Khz(2) }
    ACCESS          read-write
    STATUS          mandatory
    DESCRIPTION     
            "The transfer capability for audio calls when interworking
             with CAS. The default transfer capability is speech."
    DEFVAL          { speech }
    ::= { sonusCktServProfileEntry 15 }

sonusCktServProfileTxLevelControl OBJECT-TYPE
    SYNTAX          INTEGER { none(1), highLevelCompensation(2), 
                        fixedGain(3) }
    ACCESS          read-write
    STATUS          mandatory
    DESCRIPTION     
            " Specifies the type of level control transmit to PSTN to be applies to the circuit.
             
             When None is selected, 0 dB is applied to TX gain.
             
             When High Level Compensation is selected, this adds 6dB of attenuation to TX signals 
             if the proprietary Echo Canceller logic has determined that the signal level may 
             saturate the analog hybrid.  This attenuation is added or removed only during silence 
             gaps so it is less noticeable.  It is disabled if a modem or a FAX is detected. 
             This is done to prevent non-linear echoes from occurring. 
             This only applies if there is an enabled echo canceller in the call. 
             
             Fixed Gain Control applies the gain or loss in TX direction according 
             to sonusCktServProfileTxGain settings. 
             A constant gain is applied to all signals on the circuit. 
             0dB means no gain and will preserve PCM transparency with G.711. 
             This is applied to all non-data bearer channel calls regardless of whether 
             an echo canceller is either present or enabled.
             
             It's recommended that:
             	HLC is not selected in Japan
             	HLC is not selected in North America
             	HLC is selected in Europe
             	HLC is not selected during G.168 testing.
             "
    DEFVAL          { none }
    ::= { sonusCktServProfileEntry 16 }

sonusCktServProfileRxLevelControl OBJECT-TYPE
    SYNTAX          INTEGER { none(1), fixedGain(3) }
    ACCESS          read-write
    STATUS          mandatory
    DESCRIPTION     
            " Specifies the type of level control receive from PSTN to be applies to the circuit.
             
             When None is selected, 0 dB is applied to RX gain.
             
             When High Level Compensation is selected, this adds 6dB of attenuation to RX signals 
             if the proprietary Echo Canceller logic has determined that the signal level may 
             saturate the analog hybrid.  This attenuation is added or removed only during silence 
             gaps so it is less noticeable.  It is disabled if a modem or a FAX is detected. 
             This is done to prevent non-linear echoes from occurring. 
             This only applies if there is an enabled echo canceller in the call. 
             
             Fixed Gain Control applies the gain or loss in RX direction according 
             to sonusCktServProfileRxGain settings. 
             A constant gain is applied to all signals on the circuit. 
             0dB means no gain and will preserve PCM transparency with G.711. 
             This is applied to all non-data bearer channel calls regardless of whether 
             an echo canceller is either present or enabled.
             "
    DEFVAL          { none }
    ::= { sonusCktServProfileEntry 17 }

sonusCktServProfileTxGain OBJECT-TYPE
    SYNTAX          INTEGER (-12..12)
    ACCESS          read-write
    STATUS          mandatory
    DESCRIPTION     
            "When sonusCktServProfileLevelControl is set to fixedGain, this setting specifies 
             the amount of gain or loss to be applies to the circuit in the transmit direction 
             (signals sent out to the PSTN).
             
             The gain is applied at RIN of the echo canceller for calls that have echo cancellation enabled.
             
             The gain/loss range from -12 dB to +12 dB in increments of 1dB.
             When sonusCktServProfileTxLevelControl is set to a value other than fixedGain, 
             this setting is ignored."
    DEFVAL          { 0 }
    ::= { sonusCktServProfileEntry 18 }

sonusCktServProfileRxGain OBJECT-TYPE
    SYNTAX          INTEGER (-12..12)
    ACCESS          read-write
    STATUS          mandatory
    DESCRIPTION     
            "When sonusCktServProfileLevelControl is set to fixedGain, this setting 
             specifies the amount of gain or loss to be applies to the circuit in the 
             receive direction (received from PSTN).
             
             The gain is applied at SOUT of the echo canceller for calls that have echo cancellers enabled.
             
             The gain/loss range from -12 dB to +12 dB in increments of 1dB.
             0dB means no gain and will preserve PCM transparency with G.711.	
             When sonusCktServProfileRxLevelControl is set to a value other than fixedGain, 
             this setting is ignored."
    DEFVAL          { 0 }
    ::= { sonusCktServProfileEntry 19 }

sonusPktServProfile OBJECT IDENTIFIER
    ::= { sonusNodeResourcesMIBObjects 13 }

sonusPktServProfileNextIndex OBJECT-TYPE
    SYNTAX          INTEGER
    ACCESS          read-only
    STATUS          mandatory
    DESCRIPTION     
            "The next valid index to use when creating an entry in
             the sonusPktServProfileTable."
    ::= { sonusPktServProfile 1 }

sonusPktServProfileTable OBJECT-TYPE
    SYNTAX          SEQUENCE OF SonusPktServProfileEntry
    ACCESS          not-accessible
    STATUS          mandatory
    DESCRIPTION     
            "This table specifies the packet service profile list for the node."
    ::= { sonusPktServProfile 2 }

sonusPktServProfileEntry OBJECT-TYPE
    SYNTAX          SonusPktServProfileEntry
    ACCESS          not-accessible
    STATUS          mandatory
    DESCRIPTION     
            ""
    INDEX           { sonusPktServProfileIndex }
    ::= { sonusPktServProfileTable 1 }

SonusPktServProfileEntry ::=
    SEQUENCE {
        sonusPktServProfileIndex        INTEGER,
        sonusPktServProfileState        INTEGER,
        sonusPktServProfileName         SonusName,
        sonusPktServProfileDestProtocol INTEGER,
        sonusPktServProfilePrfdAudioEncoding    INTEGER,
        sonusPktServProfilePrfdFramesPerPacket      INTEGER,
        sonusPktServProfileDefFramesPerPacket     INTEGER,
        sonusPktServProfileDefAudioEnable INTEGER,
        sonusPktServProfileSilenceFactor INTEGER,
        sonusPktServProfileVInitPlayoutBufDelay       INTEGER,
        sonusPktServProfileFaxRelay     INTEGER,
        sonusPktServProfileDtmfRelay    INTEGER,
        sonusPktServProfileFallbackHandling   INTEGER,
        sonusPktServProfileTosValue     INTEGER,
        sonusPktServProfileDInitPlayoutBufDelay       INTEGER,
        sonusPktServProfileDataRtpPayloadType     INTEGER,
        sonusPktServProfileRowStatus    RowStatus,
        sonusPktServProfileG711SendSidPackets     INTEGER,
        sonusPktServProfileG711SidRtpPayloadType        INTEGER,
        sonusPktServProfileSidHeartbeat INTEGER,
        sonusPktServProfileRtcp         INTEGER,
        sonusPktServProfilePacketLossThreshold      INTEGER,
        sonusPktServProfilePacketLossAction   INTEGER,
        sonusPktServProfileRtpPeerAbsenceAction       INTEGER,
        sonusPktServProfileDtmfRelayOutOfBand     INTEGER,
        sonusPktServProfileDtmfRelayRemoveDigits        INTEGER,
        sonusPktServProfileAAL1PayloadSize  INTEGER,
        sonusPktServProfileT38ErrorControlType      INTEGER,
        sonusPktServProfileT38HighSpeedNumberOfRedundantPacket                      INTEGER,
        sonusPktServProfileT38MaximumBitRate    INTEGER,
        sonusPktServProfileT38DataRateManagementType            INTEGER,
        sonusPktServProfileHonorRemotePrecedence        INTEGER,
        sonusPktServProfileT38LowSpeedNumberOfRedundantPacket                     INTEGER,
        sonusPktServProfileDataCallPacketSize     INTEGER,
        sonusPktServProfileDigitDetectSend  INTEGER,
        sonusPktServProfileDisallowDataCalls    INTEGER,
        sonusPktServProfileDtmfRelayRtpPayloadType          INTEGER,
        sonusPktServProfileP2pControlTranscode      INTEGER,
        sonusPktServProfileP2pControlConditionDifferentPacketSize                         INTEGER,
        sonusPktServProfileP2pControlConditionDifferentSilenceSuppression                                 INTEGER,
        sonusPktServProfileP2pControlConditionDifferentDtmfRelay                        INTEGER,
        sonusPktServProfileP2pControlCodecAllowedTranscodingThisLegG711a                                INTEGER,
        sonusPktServProfileP2pControlCodecAllowedTranscodingThisLegG711u                                INTEGER,
        sonusPktServProfileP2pControlCodecAllowedTranscodingThisLegG7231                                INTEGER,
        sonusPktServProfileP2pControlCodecAllowedTranscodingThisLegG726                               INTEGER,
        sonusPktServProfileP2pControlCodecAllowedTranscodingThisLegG729                               INTEGER,
        sonusPktServProfileP2pControlCodecAllowedTranscodingThisLegIlbc                               INTEGER,
        sonusPktServProfileP2pControlCodecAllowedTranscodingThisLegT38                              INTEGER,
        sonusPktServProfileP2pControlCodecAllowedTranscodingOtherLegG711a                                 INTEGER,
        sonusPktServProfileP2pControlCodecAllowedTranscodingOtherLegG711u                                 INTEGER,
        sonusPktServProfileP2pControlCodecAllowedTranscodingOtherLegG7231                                 INTEGER,
        sonusPktServProfileP2pControlCodecAllowedTranscodingOtherLegG726                                INTEGER,
        sonusPktServProfileP2pControlCodecAllowedTranscodingOtherLegG729                                INTEGER,
        sonusPktServProfileP2pControlCodecAllowedTranscodingOtherLegIlbc                                INTEGER,
        sonusPktServProfileP2pControlCodecAllowedTranscodingOtherLegT38                               INTEGER,
        sonusPktServProfileSecureRtpAdminState      SonusAdminState,
        sonusPktServProfileSecureRtpFallBackToRtp         SonusBoolean,
        sonusPktServProfileSecureRtpCryptoSuite1        INTEGER,
        sonusPktServProfileSecureRtpSessionParameter            OCTET STRING,
        sonusPktServProfileVideoMaxBandwidth    INTEGER,
        sonusPktServProfileVideoBandwidthReductionFactor                INTEGER,
        sonusPktServProfileVideoFailAudioOnly     SonusAdminState,
        sonusPktServProfileCosValue     INTEGER,
        sonusPktServProfileP2pControlCodecAllowedTranscodingThisLegAmr                              INTEGER,
        sonusPktServProfileP2pControlCodecAllowedTranscodingThisLegEfr                              INTEGER,
        sonusPktServProfileP2pControlCodecAllowedTranscodingOtherLegAmr                               INTEGER,
        sonusPktServProfileP2pControlCodecAllowedTranscodingOtherLegEfr                               INTEGER,
        sonusPktServProfileP2pControlConditionHonorOfferPreference                          INTEGER,
        sonusPktServProfileP2pControlCodecAllowedTranscodingThisLegEvrc                               INTEGER,
        sonusPktServProfileP2pControlCodecAllowedTranscodingOtherLegEvrc                                INTEGER,
        sonusPktServProfileSendPspPrecedence    INTEGER,
        sonusPktServProfileT38EcmPreferred  INTEGER,
        sonusPktServProfileUseDirectMedia INTEGER,
        sonusPktServProfileValPeerSuppDtmfEvnts       INTEGER,
        sonusPktServProfileT38UseMaxBitRatesOnly        INTEGER,
        sonusPktServProfileInterworkDtmfWithoutTranscoding                  INTEGER,
        sonusPktServProfileMediaAddrType INTEGER,
        sonusPktServProfileP2pControlConditionDifferentApplyFaxToneTreatment                                    INTEGER,
        sonusPktServProfileSsrcRandomization    INTEGER,
        sonusPktServProfileP2pControlCodecAllowedTranscodingThisLegG722                               INTEGER,
        sonusPktServProfileP2pControlCodecAllowedTranscodingThisLegAmrwb                                INTEGER,
        sonusPktServProfileP2pControlCodecAllowedTranscodingOtherLegG722                                INTEGER,
        sonusPktServProfileP2pControlCodecAllowedTranscodingOtherLegAmrwb                                 INTEGER,
        sonusPktServProfileP2pControlConditionDifferent2833PayloadType                              INTEGER,
        sonusPktServProfileHdCodecPreferred   INTEGER,
        sonusPktServProfilepreferNBPassthruOverHDTranscode                  INTEGER,
        sonusPktServProfilematchOfferedCodecGroupIfNbOnly                 INTEGER,
        sonusPktServProfileforceRoutePSPOrder     INTEGER
    }

sonusPktServProfileIndex OBJECT-TYPE
    SYNTAX          INTEGER
    ACCESS          read-only
    STATUS          mandatory
    DESCRIPTION     
            "Identifies the target packet service profile entry."
    ::= { sonusPktServProfileEntry 1 }

sonusPktServProfileState OBJECT-TYPE
    SYNTAX          INTEGER { disabled(1), enabled(2) }
    ACCESS          read-write
    STATUS          mandatory
    DESCRIPTION     
            "The administrative state of this packet service profile entry."
    DEFVAL          { disabled }
    ::= { sonusPktServProfileEntry 2 }

sonusPktServProfileName OBJECT-TYPE
    SYNTAX          SonusName
    ACCESS          read-write
    STATUS          mandatory
    DESCRIPTION     
            "The user name of this packet service profile."
    ::= { sonusPktServProfileEntry 3 }

sonusPktServProfileDestProtocol OBJECT-TYPE
    SYNTAX          INTEGER { gsx(1), h323(2) }
    ACCESS          read-write
    STATUS          obsolete
    DESCRIPTION     
            "Specifies the Packet Destination Protocal used. 
             GSX - uses Sonus GSX-GSX MCS protocol.
             h323 - uses H.323 protocol.
             
             Obsoleted by the sonusAudioEncodingTable."
    DEFVAL          { gsx }
    ::= { sonusPktServProfileEntry 4 }

sonusPktServProfilePrfdAudioEncoding OBJECT-TYPE
    SYNTAX          INTEGER { g711(1), g711ss(2), g729a(4), g729ab(5) }
    ACCESS          read-write
    STATUS          deprecated
    DESCRIPTION     
            "The preferred audio encoding method to be performed on the packet data received from, 
             and destined to the IP network. 
             The possible options are: G.711, G.711 with Silence Suppression, G.729A and G.729A+B. 
             The default encoding method is G.711. For G.711, the law is determined by Circuit Service Profile.
             
             Deprecated by sonusAudioEncodingCodec."
    DEFVAL          { g711 }
    ::= { sonusPktServProfileEntry 5 }

sonusPktServProfilePrfdFramesPerPacket OBJECT-TYPE
    SYNTAX          INTEGER
    ACCESS          read-write
    STATUS          deprecated
    DESCRIPTION     
            "Specifies the Preferred Audio Encoding Packet Size in milliseconds.
             For G.711 encoding mode, valid values range from 10 ms to
             40 ms, in increments of 5 ms. The default value for G.711 is 10 ms. 
             For G.729 encoding mode, valid values from 10 ms to 40 ms, in increments of 10 ms. The default value for G.729 is 20 ms.
             
             Deprecated by sonusAudioEncodingPacketSize."
    DEFVAL          { 10 }
    ::= { sonusPktServProfileEntry 6 }

sonusPktServProfileDefFramesPerPacket OBJECT-TYPE
    SYNTAX          INTEGER
    ACCESS          read-write
    STATUS          obsolete
    DESCRIPTION     
            "Specifies the default Audio Encoding Packet Size in milliseconds.
             For G.711 encoding mode, valid values range from 10 ms to
             40 ms, in increments of 5 ms. The default value for G.711 is 10 ms. 
             For G.729 encoding mode, valid values from 10 ms to 40 ms, in increments of 10 ms. The default value for G.729 is 20 ms.
             
              Obsoleted by the sonusAudioEncodingTable."
    DEFVAL          { 10 }
    ::= { sonusPktServProfileEntry 7 }

sonusPktServProfileDefAudioEnable OBJECT-TYPE
    SYNTAX          INTEGER { disabled(1), enabled(2) }
    ACCESS          read-write
    STATUS          obsolete
    DESCRIPTION     
            "Specifies whether or not to allow default Audio (G.711).
             If enabled, allow use of G.711 if preferred audio resource is not available. 
             If disabled, Do not use of G.711 if preferred audio resource is not available and the call is disconnected.
             
              Obsoleted by the sonusAudioEncodingTable."
    DEFVAL          { enabled }
    ::= { sonusPktServProfileEntry 8 }

sonusPktServProfileSilenceFactor OBJECT-TYPE
    SYNTAX          INTEGER (0..50)
    ACCESS          read-write
    STATUS          mandatory
    DESCRIPTION     
            "Specifies percentage of call time that silence is expected."
    DEFVAL          { 0 }
    ::= { sonusPktServProfileEntry 9 }

sonusPktServProfileVInitPlayoutBufDelay OBJECT-TYPE
    SYNTAX          INTEGER
    ACCESS          read-write
    STATUS          mandatory
    DESCRIPTION     
            "This value defines the size of the initial playout bufferrequired to absorb 
             the maximum expected voice packet delay across the network.
             Range from 1 ms to 50 ms, in increments of 1 ms."
    DEFVAL          { 10 }
    ::= { sonusPktServProfileEntry 10 }

sonusPktServProfileFaxRelay OBJECT-TYPE
    SYNTAX          INTEGER { never(0), useIfCompressedAudio(1), 
                        always(2) }
    ACCESS          read-write
    STATUS          obsolete
    DESCRIPTION     
            "If never is specified, Fax Relay is not used regardless of the audio encoding method.
             If useIfCompressedAudio is specified, Fax Relay is used if the compressed resource is available.
             If always is specified, Fax Relay is used regardless of the audio encoding method.
             
             Obsoleted by sonusAudioEncodingTable."
    DEFVAL          { never }
    ::= { sonusPktServProfileEntry 11 }

sonusPktServProfileDtmfRelay OBJECT-TYPE
    SYNTAX          INTEGER { never(0), useIfCompressedAudio(1), 
                        always(2) }
    ACCESS          read-write
    STATUS          obsolete
    DESCRIPTION     
            "If never is specified, DTMF Relay is not used regardless of the audio encoding method.
             If useIfCompressedAudio is specified, DTMF Relay is used if the compressed resource is available.
             If always is specified, DTMF Relay is used regardless of the audio encoding method.
             
             Obsoleted by sonusAudioEncodingTable."
    DEFVAL          { never }
    ::= { sonusPktServProfileEntry 12 }

sonusPktServProfileFallbackHandling OBJECT-TYPE
    SYNTAX          INTEGER { disconnet(1), continue(2) }
    ACCESS          read-write
    STATUS          obsolete
    DESCRIPTION     
            "This specifies the behavior when a compressed codec call needs to revert to G.711 (e.g., to pass modem data) 
             and there is no bandwidth available.
             
             Obsoleted by sonusAudioEncodingTable"
    DEFVAL          { continue }
    ::= { sonusPktServProfileEntry 13 }

sonusPktServProfileTosValue OBJECT-TYPE
    SYNTAX          INTEGER (0..255)
    ACCESS          read-write
    STATUS          mandatory
    DESCRIPTION     
            "Specifies the Type Of Service (TOS) parameters to be provided in the IP header for voice packets.
             The TOS value is specified as an 8-bit hex value 0x00-0xFF allowing complete flexibility with 
             respect to the contents of the TOS byte."
    DEFVAL          { 0 }
    ::= { sonusPktServProfileEntry 14 }

sonusPktServProfileDInitPlayoutBufDelay OBJECT-TYPE
    SYNTAX          INTEGER
    ACCESS          read-write
    STATUS          mandatory
    DESCRIPTION     
            "This value defines the size of the initial playout buffer required to absorb the 
             maximum expected data packet delay across the network.
             Range from 5 ms to 50 ms, in increments of 1 ms. The default value is 50 ms."
    DEFVAL          { 50 }
    ::= { sonusPktServProfileEntry 15 }

sonusPktServProfileDataRtpPayloadType OBJECT-TYPE
    SYNTAX          INTEGER (0..127)
    ACCESS          read-write
    STATUS          mandatory
    DESCRIPTION     
            "Specifies the preferred RTP payload type to be set in the RTP header for data calls."
    DEFVAL          { 56 }
    ::= { sonusPktServProfileEntry 16 }

sonusPktServProfileRowStatus OBJECT-TYPE
    SYNTAX          RowStatus
    ACCESS          read-write
    STATUS          mandatory
    DESCRIPTION     
            ""
    ::= { sonusPktServProfileEntry 17 }

sonusPktServProfileG711SendSidPackets OBJECT-TYPE
    SYNTAX          INTEGER { disabled(1), enabled(2) }
    ACCESS          read-write
    STATUS          deprecated
    DESCRIPTION     
            " Specifies whether sending SID packets is enabled.
             This applies only if preferred audio encoding is G.711 with silence suppression.
             
             Deprecated by sonusAudioEncodingG711SendSID."
    DEFVAL          { enabled }
    ::= { sonusPktServProfileEntry 18 }

sonusPktServProfileG711SidRtpPayloadType OBJECT-TYPE
    SYNTAX          INTEGER (0..127)
    ACCESS          read-write
    STATUS          mandatory
    DESCRIPTION     
            "Specifies the preferred RTP payload type to be set in the RTP header of G.711 SID packets.
             This applies if the selected audio encoding is G.711 or iLBC with silence suppression."
    DEFVAL          { 13 }
    ::= { sonusPktServProfileEntry 19 }

sonusPktServProfileSidHeartbeat OBJECT-TYPE
    SYNTAX          INTEGER { disabled(1), enabled(2) }
    ACCESS          read-write
    STATUS          mandatory
    DESCRIPTION     
            " Specifies whether sending SID heartbeat packets is enabled.
             This applies if preferred audio encoding is either G.711 with silence suppression or G.729A+B."
    DEFVAL          { enabled }
    ::= { sonusPktServProfileEntry 20 }

sonusPktServProfileRtcp OBJECT-TYPE
    SYNTAX          INTEGER { disabled(1), enabled(2) }
    ACCESS          read-write
    STATUS          mandatory
    DESCRIPTION     
            "Specifies whether RTCP is enabled for the call."
    DEFVAL          { disabled }
    ::= { sonusPktServProfileEntry 21 }

sonusPktServProfilePacketLossThreshold OBJECT-TYPE
    SYNTAX          INTEGER
    ACCESS          read-write
    STATUS          mandatory
    DESCRIPTION     
            " Specifies the RTCP packet loss threshold in packets/100,000.
             0 means no detection.
             Requires RTCP to be enabled."
    DEFVAL          { 0 }
    ::= { sonusPktServProfileEntry 22 }

sonusPktServProfilePacketLossAction OBJECT-TYPE
    SYNTAX          INTEGER { none(0), trap(1), trapAndDisconnect(3) }
    ACCESS          read-write
    STATUS          mandatory
    DESCRIPTION     
            " Specifies the action taken when the packet loss threshold is
             exceeded. Requires RTCP to be enabled."
    DEFVAL          { none }
    ::= { sonusPktServProfileEntry 23 }

sonusPktServProfileRtpPeerAbsenceAction OBJECT-TYPE
    SYNTAX          INTEGER { none(0), trap(1), trapAndDisconnect(3) }
    ACCESS          read-write
    STATUS          mandatory
    DESCRIPTION     
            " Specifies the action taken when the RTP peer is detected to be absent (due to lack of RTP and RTCP packets).
             Requires RTCP to be enabled."
    DEFVAL          { none }
    ::= { sonusPktServProfileEntry 24 }

sonusPktServProfileDtmfRelayOutOfBand OBJECT-TYPE
    SYNTAX          INTEGER { disabled(1), enabled(2) }
    ACCESS          read-write
    STATUS          deprecated
    DESCRIPTION     
            " Specifies whether out of band DTMF relay is enabled.
             This applies if DTMF relay is configured as useIfCompressedAudio or always .
             
             Deprecated by sonusAudioEncodingDtmfRelay."
    DEFVAL          { disabled }
    ::= { sonusPktServProfileEntry 25 }

sonusPktServProfileDtmfRelayRemoveDigits OBJECT-TYPE
    SYNTAX          INTEGER { disabled(1), enabled(2) }
    ACCESS          read-write
    STATUS          deprecated
    DESCRIPTION     
            " Specifies whether removing DTMF digits from the media stream is enabled.
             This applies if DTMF relay is configured as useIfCompressedAudio or always .
             
             Deprecated by sonusAudioEncodingDtmfRemoveDigits."
    DEFVAL          { enabled }
    ::= { sonusPktServProfileEntry 26 }

sonusPktServProfileAAL1PayloadSize OBJECT-TYPE
    SYNTAX          INTEGER
    ACCESS          read-write
    STATUS          mandatory
    DESCRIPTION     
            " This value defines VTOA AAL1 Payload Size.
             For G.711, Valid values are 40, 44 and 47 bytes."
    DEFVAL          { 47 }
    ::= { sonusPktServProfileEntry 27 }

sonusPktServProfileT38ErrorControlType OBJECT-TYPE
    SYNTAX          INTEGER { redundancy(2) }
    ACCESS          read-write
    STATUS          mandatory
    DESCRIPTION     
            "This field specifies the T.38 error control type.  Error
             correction using redundancy is achieved by the repeating
             of previous secondary IFP (Internet Facsimile Protocol)
             messages along with a primary message."
    DEFVAL          { redundancy }
    ::= { sonusPktServProfileEntry 28 }

sonusPktServProfileT38HighSpeedNumberOfRedundantPacket OBJECT-TYPE
    SYNTAX          INTEGER (0..2)
    ACCESS          read-write
    STATUS          mandatory
    DESCRIPTION     
            "This field specifies the number of redundant IFP messages
             sent in a UDP packet for high speed fax transmission.
             This field applies only if the Redundancy of T.38 Error
             Control Type is selected."
    DEFVAL          { 1 }
    ::= { sonusPktServProfileEntry 29 }

sonusPktServProfileT38MaximumBitRate OBJECT-TYPE
    SYNTAX          INTEGER { r2400bps(1), r4800bps(2), r9600bps(3), 
                        r14400bps(4) }
    ACCESS          read-write
    STATUS          mandatory
    DESCRIPTION     
            "The T.38 maximum bit rates."
    DEFVAL          { r14400bps }
    ::= { sonusPktServProfileEntry 30 }

sonusPktServProfileT38DataRateManagementType OBJECT-TYPE
    SYNTAX          INTEGER { type1(1), type2(2) }
    ACCESS          read-write
    STATUS          mandatory
    DESCRIPTION     
            "Type 1 data rate management requires that the TCF training
             signal be generated locally by the receiving gateway. Data
             rate management is performed by the emitting gateway based
             on training results from both PSTN connections. Type 1 is
             used for TCP implementations and is optional for use with
             UDP implementations.
             
             Type 2 data rate management requires that the TCF be
             transferred from the sending G3FE to the receiving G3FE
             rather than having the receiving gateway generate it
             locally.  Speed selection is done by the G3FEs in the same
             way as they would on a regular PSTN connection.  Data rate
             management type 2 requires the use of UDP and is not
             recommended for use with TCP. "
    DEFVAL          { type2 }
    ::= { sonusPktServProfileEntry 31 }

sonusPktServProfileHonorRemotePrecedence OBJECT-TYPE
    SYNTAX          INTEGER { disabled(1), enabled(2) }
    ACCESS          read-write
    STATUS          mandatory
    DESCRIPTION     
            "This applies to IP SG to decide whether the audio encoding
             list of the local packet service profile take precedence
             against the remote peer's audio encoding list when creating
             the priority order of audio encodings that are common to
             both.  When enabled, the remote audio encoding order takes
             precedence.  When disabled, the local audio encoding order
             takes precedence."
    DEFVAL          { disabled }
    ::= { sonusPktServProfileEntry 32 }

sonusPktServProfileT38LowSpeedNumberOfRedundantPacket OBJECT-TYPE
    SYNTAX          INTEGER (0..2)
    ACCESS          read-write
    STATUS          mandatory
    DESCRIPTION     
            "This field specifies the number of redundant IFP messages
             sent in a UDP packet for low speed fax transmission.
             This field applies only if the Redundancy of T.38 Error
             Control Type is selected."
    DEFVAL          { 1 }
    ::= { sonusPktServProfileEntry 33 }

sonusPktServProfileDataCallPacketSize OBJECT-TYPE
    SYNTAX          INTEGER (10..40)
    ACCESS          read-write
    STATUS          mandatory
    DESCRIPTION     
            "The data call packet size in milliseconds.  The valid range
             is 10ms to 40ms."
    DEFVAL          { 20 }
    ::= { sonusPktServProfileEntry 34 }

sonusPktServProfileDigitDetectSend OBJECT-TYPE
    SYNTAX          INTEGER { disabled(1), enabled(2) }
    ACCESS          read-write
    STATUS          mandatory
    DESCRIPTION     
            "Specifies whether digit detection is enabled on digits
             send to the network."
    DEFVAL          { disabled }
    ::= { sonusPktServProfileEntry 35 }

sonusPktServProfileDisallowDataCalls OBJECT-TYPE
    SYNTAX          INTEGER { disabled(1), enabled(2) }
    ACCESS          read-write
    STATUS          mandatory
    DESCRIPTION     
            "Specifies whether data calls are allowed.  If enabled,
             digit data calls are rejected."
    DEFVAL          { disabled }
    ::= { sonusPktServProfileEntry 36 }

sonusPktServProfileDtmfRelayRtpPayloadType OBJECT-TYPE
    SYNTAX          INTEGER (0..128)
    ACCESS          read-write
    STATUS          mandatory
    DESCRIPTION     
            "Specifies the prferred RTP payload type to be set
             in the RTP header of RFC 2833 packets.  If set to 128,
             the value of sonusPadAdmnRtpDtmfRelay is used instead."
    DEFVAL          { 128 }
    ::= { sonusPktServProfileEntry 37 }

sonusPktServProfileP2pControlTranscode OBJECT-TYPE
    SYNTAX          INTEGER { only(1), conditional(2), 
                        determinedByOtherLeg(3), 
                        transcoderFreeTransparency(4) }
    ACCESS          read-write
    STATUS          mandatory
    DESCRIPTION     
            "This controls whether media is transcoded between the ingress
             and egress leg audio encoding formats.  Permitted values are:
             
               only - apply transcoding unconditionally
               conditional - evaluate the P2pControlConditions of both legs
               determinedByOtherLeg - defer to other Packet Service Profile
             transcoderFreeTransparency - no transcoding and do not apply any local policy
             
             If either leg says only, transcoding is applied unconditionally.
             Otherwise if either leg says conditional, the conditions set by
             both legs are evaluated; so is the fixed condition of No Common
             Codec; if any of these conditions is true, transcoding is applied.
             Otherwise if both legs say determinedByOtherLeg, transcoding is
             not applied.  If not transcoded, media is passed thru unchanged.
             If either leg selects transcoderFreeTransparency, no transcoding and no local 
             policy will be applied to media"
    DEFVAL          { conditional }
    ::= { sonusPktServProfileEntry 38 }

sonusPktServProfileP2pControlConditionDifferentPacketSize OBJECT-TYPE
    SYNTAX          INTEGER { disabled(1), enabled(2) }
    ACCESS          read-write
    STATUS          mandatory
    DESCRIPTION     
            "This controls whether media is transcoded when the ingress
             and egress legs use different packet sizes."
    DEFVAL          { disabled }
    ::= { sonusPktServProfileEntry 39 }

sonusPktServProfileP2pControlConditionDifferentSilenceSuppression OBJECT-TYPE
    SYNTAX          INTEGER { disabled(1), enabled(2) }
    ACCESS          read-write
    STATUS          mandatory
    DESCRIPTION     
            "This controls whether media is transcoded when the ingress
             and egress legs differ about using silence suppression."
    DEFVAL          { disabled }
    ::= { sonusPktServProfileEntry 40 }

sonusPktServProfileP2pControlConditionDifferentDtmfRelay OBJECT-TYPE
    SYNTAX          INTEGER { disabled(1), enabled(2) }
    ACCESS          read-write
    STATUS          mandatory
    DESCRIPTION     
            "This controls whether media is transcoded when the ingress
             and egress legs use different DTMF relay methods."
    DEFVAL          { disabled }
    ::= { sonusPktServProfileEntry 41 }

sonusPktServProfileP2pControlCodecAllowedTranscodingThisLegG711a OBJECT-TYPE
    SYNTAX          INTEGER { disabled(1), enabled(2) }
    ACCESS          read-write
    STATUS          mandatory
    DESCRIPTION     
            "This controls whether audio encoding G.711 A-Law
             on this call leg is allowed to be transcoded."
    DEFVAL          { disabled }
    ::= { sonusPktServProfileEntry 42 }

sonusPktServProfileP2pControlCodecAllowedTranscodingThisLegG711u OBJECT-TYPE
    SYNTAX          INTEGER { disabled(1), enabled(2) }
    ACCESS          read-write
    STATUS          mandatory
    DESCRIPTION     
            "This controls whether audio encoding G.711 U-Law
             on this call leg is allowed to be transcoded."
    DEFVAL          { disabled }
    ::= { sonusPktServProfileEntry 43 }

sonusPktServProfileP2pControlCodecAllowedTranscodingThisLegG7231 OBJECT-TYPE
    SYNTAX          INTEGER { disabled(1), enabled(2) }
    ACCESS          read-write
    STATUS          mandatory
    DESCRIPTION     
            "This controls whether audio encoding G.723.1
             on this call leg is allowed to be transcoded."
    DEFVAL          { disabled }
    ::= { sonusPktServProfileEntry 44 }

sonusPktServProfileP2pControlCodecAllowedTranscodingThisLegG726 OBJECT-TYPE
    SYNTAX          INTEGER { disabled(1), enabled(2) }
    ACCESS          read-write
    STATUS          mandatory
    DESCRIPTION     
            "This controls whether audio encoding G.726
             on this call leg is allowed to be transcoded."
    DEFVAL          { disabled }
    ::= { sonusPktServProfileEntry 45 }

sonusPktServProfileP2pControlCodecAllowedTranscodingThisLegG729 OBJECT-TYPE
    SYNTAX          INTEGER { disabled(1), enabled(2) }
    ACCESS          read-write
    STATUS          mandatory
    DESCRIPTION     
            "This controls whether audio encoding G.729
             on this call leg is allowed to be transcoded."
    DEFVAL          { disabled }
    ::= { sonusPktServProfileEntry 46 }

sonusPktServProfileP2pControlCodecAllowedTranscodingThisLegIlbc OBJECT-TYPE
    SYNTAX          INTEGER { disabled(1), enabled(2) }
    ACCESS          read-write
    STATUS          mandatory
    DESCRIPTION     
            "This controls whether audio encoding iLBC
             on this call leg is allowed to be transcoded."
    DEFVAL          { disabled }
    ::= { sonusPktServProfileEntry 47 }

sonusPktServProfileP2pControlCodecAllowedTranscodingThisLegT38 OBJECT-TYPE
    SYNTAX          INTEGER { disabled(1), enabled(2) }
    ACCESS          read-write
    STATUS          mandatory
    DESCRIPTION     
            "This controls whether fax media encoding T.38
             on this call leg is allowed to be transcoded."
    DEFVAL          { disabled }
    ::= { sonusPktServProfileEntry 48 }

sonusPktServProfileP2pControlCodecAllowedTranscodingOtherLegG711a OBJECT-TYPE
    SYNTAX          INTEGER { disabled(1), enabled(2) }
    ACCESS          read-write
    STATUS          mandatory
    DESCRIPTION     
            "This controls whether audio encoding G.711 A-Law
             on the other call leg is allowed to be transcoded."
    DEFVAL          { disabled }
    ::= { sonusPktServProfileEntry 49 }

sonusPktServProfileP2pControlCodecAllowedTranscodingOtherLegG711u OBJECT-TYPE
    SYNTAX          INTEGER { disabled(1), enabled(2) }
    ACCESS          read-write
    STATUS          mandatory
    DESCRIPTION     
            "This controls whether audio encoding G.711 U-Law
             on the other call leg is allowed to be transcoded."
    DEFVAL          { disabled }
    ::= { sonusPktServProfileEntry 50 }

sonusPktServProfileP2pControlCodecAllowedTranscodingOtherLegG7231 OBJECT-TYPE
    SYNTAX          INTEGER { disabled(1), enabled(2) }
    ACCESS          read-write
    STATUS          mandatory
    DESCRIPTION     
            "This controls whether audio encoding G.723.1
             on the other call leg is allowed to be transcoded."
    DEFVAL          { disabled }
    ::= { sonusPktServProfileEntry 51 }

sonusPktServProfileP2pControlCodecAllowedTranscodingOtherLegG726 OBJECT-TYPE
    SYNTAX          INTEGER { disabled(1), enabled(2) }
    ACCESS          read-write
    STATUS          mandatory
    DESCRIPTION     
            "This controls whether audio encoding G.726
             on the other call leg is allowed to be transcoded."
    DEFVAL          { disabled }
    ::= { sonusPktServProfileEntry 52 }

sonusPktServProfileP2pControlCodecAllowedTranscodingOtherLegG729 OBJECT-TYPE
    SYNTAX          INTEGER { disabled(1), enabled(2) }
    ACCESS          read-write
    STATUS          mandatory
    DESCRIPTION     
            "This controls whether audio encoding G.729
             on the other call leg is allowed to be transcoded."
    DEFVAL          { disabled }
    ::= { sonusPktServProfileEntry 53 }

sonusPktServProfileP2pControlCodecAllowedTranscodingOtherLegIlbc OBJECT-TYPE
    SYNTAX          INTEGER { disabled(1), enabled(2) }
    ACCESS          read-write
    STATUS          mandatory
    DESCRIPTION     
            "This controls whether audio encoding iLBC
             on the other call leg is allowed to be transcoded."
    DEFVAL          { disabled }
    ::= { sonusPktServProfileEntry 54 }

sonusPktServProfileP2pControlCodecAllowedTranscodingOtherLegT38 OBJECT-TYPE
    SYNTAX          INTEGER { disabled(1), enabled(2) }
    ACCESS          read-write
    STATUS          mandatory
    DESCRIPTION     
            "This controls whether fax media encoding T.38
             on the other call leg is allowed to be transcoded."
    DEFVAL          { disabled }
    ::= { sonusPktServProfileEntry 55 }

sonusPktServProfileSecureRtpAdminState OBJECT-TYPE
    SYNTAX          SonusAdminState
    ACCESS          read-write
    STATUS          mandatory
    DESCRIPTION     
            "The admin state of the Secure RTP."
    DEFVAL          { disabled }
    ::= { sonusPktServProfileEntry 56 }

sonusPktServProfileSecureRtpFallBackToRtp OBJECT-TYPE
    SYNTAX          SonusBoolean
    ACCESS          read-write
    STATUS          mandatory
    DESCRIPTION     
            "This field indicates whether or not to allow fallback to
             regular RTP when the crypto attribute fails answer."
    DEFVAL          { false }
    ::= { sonusPktServProfileEntry 57 }

sonusPktServProfileSecureRtpCryptoSuite1 OBJECT-TYPE
    SYNTAX          INTEGER { nosuite(0), aes-cm-128-hmac-sha1-80(2) }
    ACCESS          read-write
    STATUS          mandatory
    DESCRIPTION     
            "This field indicates the media encryption of Secure RTP."
    DEFVAL          { aes-cm-128-hmac-sha1-80 }
    ::= { sonusPktServProfileEntry 58 }

sonusPktServProfileSecureRtpSessionParameter OBJECT-TYPE
    SYNTAX          OCTET STRING
--                       { unencrypted-srtp(0), unencrypted-srtcp(1), 
--                         unauthenticated-srtp(2) }
    ACCESS          read-write
    STATUS          mandatory
    DESCRIPTION     
            "This field indicates the session parameter of secure RTP's
             media crypto attibutes."
    DEFVAL          { {} }
    ::= { sonusPktServProfileEntry 59 }

sonusPktServProfileVideoMaxBandwidth OBJECT-TYPE
    SYNTAX          INTEGER (0..2048)
    ACCESS          read-write
    STATUS          mandatory
    DESCRIPTION     
            "Maximum bandwidth in Kbps for the video stream.
             Value should include all codec specific header and
             payload data as well as any non-codec header data
             including RTP, UDP, IP, Ethernet or MAC."
    DEFVAL          { 0 }
    ::= { sonusPktServProfileEntry 60 }

sonusPktServProfileVideoBandwidthReductionFactor OBJECT-TYPE
    SYNTAX          INTEGER (0..100)
    ACCESS          read-write
    STATUS          mandatory
    DESCRIPTION     
            "Specifies the percentage that the video bandwidth
             should be reduced when the IP resources are allocated
             from the IP trunk group and NIF. The average video
             bandwidth is derived by subtracting this percentage
             from the maximum video bandwidth."
    DEFVAL          { 0 }
    ::= { sonusPktServProfileEntry 61 }

sonusPktServProfileVideoFailAudioOnly OBJECT-TYPE
    SYNTAX          SonusAdminState
    ACCESS          read-write
    STATUS          mandatory
    DESCRIPTION     
            "Determines if a video call will continue as audio only
             when video is prevented by a lack of resources or by
             			 zero maximum bandwidth on the other call leg."
    DEFVAL          { enabled }
    ::= { sonusPktServProfileEntry 62 }

sonusPktServProfileCosValue OBJECT-TYPE
    SYNTAX          INTEGER (0..7)
    ACCESS          read-write
    STATUS          mandatory
    DESCRIPTION     
            "Specifies the Class of Service (COS) value to be set in the IEEE 802.1D 
             User Priority field of media packets transmitted on a call leg that uses 
             this Packet Service  Profile.  Only has an effect if the network interface 
             supports 802.1Q tagged Ethernet frames.  The default value zero corresponds to 
             best effort."
    DEFVAL          { 0 }
    ::= { sonusPktServProfileEntry 63 }

sonusPktServProfileP2pControlCodecAllowedTranscodingThisLegAmr OBJECT-TYPE
    SYNTAX          INTEGER { disabled(1), enabled(2) }
    ACCESS          read-write
    STATUS          mandatory
    DESCRIPTION     
            "This controls whether audio encoding AMR (octet-align mode)
             on this call leg is allowed to be transcoded."
    DEFVAL          { disabled }
    ::= { sonusPktServProfileEntry 64 }

sonusPktServProfileP2pControlCodecAllowedTranscodingThisLegEfr OBJECT-TYPE
    SYNTAX          INTEGER { disabled(1), enabled(2) }
    ACCESS          read-write
    STATUS          mandatory
    DESCRIPTION     
            "This controls whether audio encoding EFR
             on this call leg is allowed to be transcoded."
    DEFVAL          { disabled }
    ::= { sonusPktServProfileEntry 65 }

sonusPktServProfileP2pControlCodecAllowedTranscodingOtherLegAmr OBJECT-TYPE
    SYNTAX          INTEGER { disabled(1), enabled(2) }
    ACCESS          read-write
    STATUS          mandatory
    DESCRIPTION     
            "This controls whether audio encoding iLBC
             on the other call leg is allowed to be transcoded."
    DEFVAL          { disabled }
    ::= { sonusPktServProfileEntry 66 }

sonusPktServProfileP2pControlCodecAllowedTranscodingOtherLegEfr OBJECT-TYPE
    SYNTAX          INTEGER { disabled(1), enabled(2) }
    ACCESS          read-write
    STATUS          mandatory
    DESCRIPTION     
            "This controls whether audio encoding iLBC
             on the other call leg is allowed to be transcoded."
    DEFVAL          { disabled }
    ::= { sonusPktServProfileEntry 67 }

sonusPktServProfileP2pControlConditionHonorOfferPreference OBJECT-TYPE
    SYNTAX          INTEGER { disabled(1), enabled(2) }
    ACCESS          read-write
    STATUS          mandatory
    DESCRIPTION     
            "This controls whether media is transcoded in order
             to match a more preferred codec of the received offer."
    DEFVAL          { disabled }
    ::= { sonusPktServProfileEntry 68 }

sonusPktServProfileP2pControlCodecAllowedTranscodingThisLegEvrc OBJECT-TYPE
    SYNTAX          INTEGER { disabled(1), enabled(2) }
    ACCESS          read-write
    STATUS          mandatory
    DESCRIPTION     
            "This controls whether audio encoding EVRC
             on this call leg is allowed to be transcoded."
    DEFVAL          { disabled }
    ::= { sonusPktServProfileEntry 69 }

sonusPktServProfileP2pControlCodecAllowedTranscodingOtherLegEvrc OBJECT-TYPE
    SYNTAX          INTEGER { disabled(1), enabled(2) }
    ACCESS          read-write
    STATUS          mandatory
    DESCRIPTION     
            "This controls whether audio encoding EVRC
             on the other call leg is allowed to be transcoded."
    DEFVAL          { disabled }
    ::= { sonusPktServProfileEntry 70 }

sonusPktServProfileSendPspPrecedence OBJECT-TYPE
    SYNTAX          INTEGER { disabled(1), enabled(2) }
    ACCESS          read-write
    STATUS          mandatory
    DESCRIPTION     
            "This controls the order in which codecs are listed
             whenever a choice of multiple codecs is sent.
             If enabled, the order of the route packet service profile applies.
             If disabled, codecs may be passed through in an order
             that results from processing on the opposite call leg."
    DEFVAL          { enabled }
    ::= { sonusPktServProfileEntry 71 }

sonusPktServProfileT38EcmPreferred OBJECT-TYPE
    SYNTAX          INTEGER { disabled(1), enabled(2) }
    ACCESS          read-write
    STATUS          mandatory
    DESCRIPTION     
            "This field specifies whether Error Correction
             Mode has to be turned on for a fax call, 
             when fax is detected. When enabled, preferance shall be
             given to DSPs capable of ECM. Default value -
             Disabled."
    DEFVAL          { disabled }
    ::= { sonusPktServProfileEntry 72 }

sonusPktServProfileUseDirectMedia OBJECT-TYPE
    SYNTAX          INTEGER { disabled(1), enabled(2) }
    ACCESS          read-write
    STATUS          mandatory
    DESCRIPTION     
            "This controls whether Direct Media is enabled or not."
    DEFVAL          { disabled }
    ::= { sonusPktServProfileEntry 73 }

sonusPktServProfileValPeerSuppDtmfEvnts OBJECT-TYPE
    SYNTAX          INTEGER { disabled(1), enabled(2) }
    ACCESS          read-write
    STATUS          mandatory
    DESCRIPTION     
            "Support for 4733 DTMF events."
    DEFVAL          { disabled }
    ::= { sonusPktServProfileEntry 74 }

sonusPktServProfileT38UseMaxBitRatesOnly OBJECT-TYPE
    SYNTAX          INTEGER { disabled(0), enabled(1) }
    ACCESS          read-write
    STATUS          mandatory
    DESCRIPTION     
            "This controls how to set T.38 max bit rate on DSP. 
             If enabled, the configured max bit rate in Packet Service Profile will be used. 
              If disabled, the max bit rate is calculated based on max datagram and max packet buffer sizes."
    DEFVAL          { disabled }
    ::= { sonusPktServProfileEntry 75 }

sonusPktServProfileInterworkDtmfWithoutTranscoding OBJECT-TYPE
    SYNTAX          INTEGER { disabled(0), enabled(1) }
    ACCESS          read-write
    STATUS          mandatory
    DESCRIPTION     
            "If enabled for both legs of a packet-to-packet call and supported
             by the network interface hardware, DTMF events will be relayed
             - without requiring PAD resources to transcode the audio stream -
             between call legs that use Out-Of-Band and RFC 2833, respectively,
             subject to the DTMF Relay settings of Codec entries in their PSPs.
             If audio is transcoded for other reasons, this feature does not apply.
             To benefit from the feature, if Transcode is set to CONDITIONAL,
             Different DTMF Relay should be disabled."
    DEFVAL          { disabled }
    ::= { sonusPktServProfileEntry 76 }

sonusPktServProfileMediaAddrType OBJECT-TYPE
    SYNTAX          INTEGER { sipSigAddrIpType(1), ipv4(2), ipv6(24), 
                        ipv4andipv6(3) }
    ACCESS          read-write
    STATUS          mandatory
    DESCRIPTION     
            "Type of IP address used in offer for media address"
    DEFVAL          { 1 }
    ::= { sonusPktServProfileEntry 77 }

sonusPktServProfileP2pControlConditionDifferentApplyFaxToneTreatment OBJECT-TYPE
    SYNTAX          INTEGER { disabled(1), enabled(2) }
    ACCESS          read-write
    STATUS          mandatory
    DESCRIPTION     
            "This controls whether whether T38 should be bumped up the codec list."
    DEFVAL          { disabled }
    ::= { sonusPktServProfileEntry 78 }

sonusPktServProfileSsrcRandomization OBJECT-TYPE
    SYNTAX          INTEGER { disabled(1), enabled(2) }
    ACCESS          read-write
    STATUS          mandatory
    DESCRIPTION     
            "This controls whether SSRC randomization should be enabled or not
             when a resource chain is rebuilt."
    DEFVAL          { disabled }
    ::= { sonusPktServProfileEntry 79 }

sonusPktServProfileP2pControlCodecAllowedTranscodingThisLegG722 OBJECT-TYPE
    SYNTAX          INTEGER { disabled(1), enabled(2) }
    ACCESS          read-write
    STATUS          mandatory
    DESCRIPTION     
            "This controls whether audio encoding G722
             on this call leg is allowed to be transcoded."
    DEFVAL          { disabled }
    ::= { sonusPktServProfileEntry 80 }

sonusPktServProfileP2pControlCodecAllowedTranscodingThisLegAmrwb OBJECT-TYPE
    SYNTAX          INTEGER { disabled(1), enabled(2) }
    ACCESS          read-write
    STATUS          mandatory
    DESCRIPTION     
            "This controls whether audio encoding AMRWB 
             on this call leg is allowed to be transcoded."
    DEFVAL          { disabled }
    ::= { sonusPktServProfileEntry 81 }

sonusPktServProfileP2pControlCodecAllowedTranscodingOtherLegG722 OBJECT-TYPE
    SYNTAX          INTEGER { disabled(1), enabled(2) }
    ACCESS          read-write
    STATUS          mandatory
    DESCRIPTION     
            "This controls whether audio encoding G722
             on the other call leg is allowed to be transcoded."
    DEFVAL          { disabled }
    ::= { sonusPktServProfileEntry 82 }

sonusPktServProfileP2pControlCodecAllowedTranscodingOtherLegAmrwb OBJECT-TYPE
    SYNTAX          INTEGER { disabled(1), enabled(2) }
    ACCESS          read-write
    STATUS          mandatory
    DESCRIPTION     
            "This controls whether audio encoding AMRWB 
             on the other call leg is allowed to be transcoded."
    DEFVAL          { disabled }
    ::= { sonusPktServProfileEntry 83 }

sonusPktServProfileP2pControlConditionDifferent2833PayloadType OBJECT-TYPE
    SYNTAX          INTEGER { disabled(1), enabled(2) }
    ACCESS          read-write
    STATUS          mandatory
    DESCRIPTION     
            "This controls whether media is transcoded when the ingress
             and egress legs use different 2833 payload types."
    DEFVAL          { disabled }
    ::= { sonusPktServProfileEntry 86 }

sonusPktServProfileHdCodecPreferred OBJECT-TYPE
    SYNTAX          INTEGER { disabled(1), enabled(2) }
    ACCESS          read-write
    STATUS          mandatory
    DESCRIPTION     
            "This controls whether HD Codec Preferred is enabled or not."
    DEFVAL          { disabled }
    ::= { sonusPktServProfileEntry 87 }

sonusPktServProfilepreferNBPassthruOverHDTranscode OBJECT-TYPE
    SYNTAX          INTEGER { disabled(1), enabled(2) }
    ACCESS          read-write
    STATUS          mandatory
    DESCRIPTION     
            "This controls whether NB Passthru over HD Transcode is enabled or not."
    DEFVAL          { disabled }
    ::= { sonusPktServProfileEntry 88 }

sonusPktServProfilematchOfferedCodecGroupIfNbOnly OBJECT-TYPE
    SYNTAX          INTEGER { disabled(1), enabled(2) }
    ACCESS          read-write
    STATUS          mandatory
    DESCRIPTION     
            "This controls whether Match Offered Codec Group If Nb only is enabled or not."
    DEFVAL          { disabled }
    ::= { sonusPktServProfileEntry 89 }

sonusPktServProfileforceRoutePSPOrder OBJECT-TYPE
    SYNTAX          INTEGER { disabled(1), enabled(2) }
    ACCESS          read-write
    STATUS          mandatory
    DESCRIPTION     
            "This controls whether Force route PSP Order is enabled or not."
    DEFVAL          { disabled }
    ::= { sonusPktServProfileEntry 90 }

sonusDisconnectTreatmentObjects OBJECT IDENTIFIER
    ::= { sonusNodeResourcesMIBObjects 14 }

sonusDiscTreatProfile OBJECT IDENTIFIER
    ::= { sonusDisconnectTreatmentObjects 1 }

sonusDiscTreatProfileNextIndex OBJECT-TYPE
    SYNTAX          INTEGER
    ACCESS          read-only
    STATUS          mandatory
    DESCRIPTION     
            "The next valid index to use when creating an entry in
             the sonusDiscTreatProfileTable."
    ::= { sonusDiscTreatProfile 1 }

sonusDiscTreatProfileTable OBJECT-TYPE
    SYNTAX          SEQUENCE OF SonusDiscTreatProfileEntry
    ACCESS          not-accessible
    STATUS          mandatory
    DESCRIPTION     
            "This table contains Disconnect Treatment Profiles for the node."
    ::= { sonusDiscTreatProfile 2 }

sonusDiscTreatProfileEntry OBJECT-TYPE
    SYNTAX          SonusDiscTreatProfileEntry
    ACCESS          not-accessible
    STATUS          mandatory
    DESCRIPTION     
            ""
    INDEX           { sonusDiscTreatProfileIndex }
    ::= { sonusDiscTreatProfileTable 1 }

SonusDiscTreatProfileEntry ::=
    SEQUENCE {
        sonusDiscTreatProfileIndex      INTEGER,
        sonusDiscTreatProfileName       SonusName,
        sonusDiscTreatProfileRowStatus  RowStatus
    }

sonusDiscTreatProfileIndex OBJECT-TYPE
    SYNTAX          INTEGER
    ACCESS          not-accessible
    STATUS          mandatory
    DESCRIPTION     
            "Identifies the Disconnect Treatment Profile."
    ::= { sonusDiscTreatProfileEntry 1 }

sonusDiscTreatProfileName OBJECT-TYPE
    SYNTAX          SonusName
    ACCESS          read-write
    STATUS          mandatory
    DESCRIPTION     
            "The user name of this Disconnect Treatment Profile."
    ::= { sonusDiscTreatProfileEntry 2 }

sonusDiscTreatProfileRowStatus OBJECT-TYPE
    SYNTAX          RowStatus
    ACCESS          read-write
    STATUS          mandatory
    DESCRIPTION     
            ""
    ::= { sonusDiscTreatProfileEntry 3 }

sonusDiscTreatmentAdmnTable OBJECT-TYPE
    SYNTAX          SEQUENCE OF SonusDiscTreatmentAdmnEntry
    ACCESS          not-accessible
    STATUS          mandatory
    DESCRIPTION     
            ""
    ::= { sonusDisconnectTreatmentObjects 2 }

sonusDiscTreatmentAdmnEntry OBJECT-TYPE
    SYNTAX          SonusDiscTreatmentAdmnEntry
    ACCESS          not-accessible
    STATUS          mandatory
    DESCRIPTION     
            ""
    INDEX           { sonusDiscTreatmentProfileIndex, 
                      sonusDiscTreatmentIndex }
    ::= { sonusDiscTreatmentAdmnTable 1 }

SonusDiscTreatmentAdmnEntry ::=
    SEQUENCE {
        sonusDiscTreatmentProfileIndex  INTEGER,
        sonusDiscTreatmentIndex         INTEGER,
        sonusDiscTreatmentReason        INTEGER,
        sonusDiscTreatmentSigSeqProfileName   SonusNameReference,
        sonusDiscTreatmentRowStatus     RowStatus
    }

sonusDiscTreatmentProfileIndex OBJECT-TYPE
    SYNTAX          INTEGER
    ACCESS          not-accessible
    STATUS          mandatory
    DESCRIPTION     
            "Identifies the Disconnect Treatment Profile to which this entry belongs."
    ::= { sonusDiscTreatmentAdmnEntry 1 }

sonusDiscTreatmentIndex OBJECT-TYPE
    SYNTAX          INTEGER
    ACCESS          not-accessible
    STATUS          mandatory
    DESCRIPTION     
            "Identifies the target Disconnect Treatment entry."
    ::= { sonusDiscTreatmentAdmnEntry 2 }

sonusDiscTreatmentReason OBJECT-TYPE
    SYNTAX          INTEGER (0..255)
    ACCESS          read-only
    STATUS          mandatory
    DESCRIPTION     
            "Disconnect Reason Code."
    ::= { sonusDiscTreatmentAdmnEntry 3 }

sonusDiscTreatmentSigSeqProfileName OBJECT-TYPE
    SYNTAX          SonusNameReference
    ACCESS          read-write
    STATUS          mandatory
    DESCRIPTION     
            "For given Disconnect Treatment Profile and Disconnect
             Reason Code, execute this Disconnect SSP."
    ::= { sonusDiscTreatmentAdmnEntry 4 }

sonusDiscTreatmentRowStatus OBJECT-TYPE
    SYNTAX          RowStatus
    ACCESS          read-write
    STATUS          mandatory
    DESCRIPTION     
            ""
    ::= { sonusDiscTreatmentAdmnEntry 5 }

sonusDiscSspGroupAdmn OBJECT IDENTIFIER
    ::= { sonusDisconnectTreatmentObjects 3 }

sonusDiscSspNextIndex OBJECT-TYPE
    SYNTAX          INTEGER
    ACCESS          read-only
    STATUS          mandatory
    DESCRIPTION     
            "The next valid index to use when creating a new sonusDiscSspGroupAdmnEntry"
    ::= { sonusDiscSspGroupAdmn 1 }

sonusDiscSspAdmnTable OBJECT-TYPE
    SYNTAX          SEQUENCE OF SonusDiscSspAdmnEntry
    ACCESS          not-accessible
    STATUS          mandatory
    DESCRIPTION     
            ""
    ::= { sonusDiscSspGroupAdmn 2 }

sonusDiscSspAdmnEntry OBJECT-TYPE
    SYNTAX          SonusDiscSspAdmnEntry
    ACCESS          not-accessible
    STATUS          mandatory
    DESCRIPTION     
            ""
    INDEX           { sonusDiscSigSeqProfileIndex }
    ::= { sonusDiscSspAdmnTable 1 }

SonusDiscSspAdmnEntry ::=
    SEQUENCE {
        sonusDiscSigSeqProfileIndex     INTEGER,
        sonusDiscSigSeqProfileName      SonusName,
        sonusDiscSigSeqProfileRowStatus RowStatus
    }

sonusDiscSigSeqProfileIndex OBJECT-TYPE
    SYNTAX          INTEGER
    ACCESS          not-accessible
    STATUS          mandatory
    DESCRIPTION     
            "Identifies the target Disconnect Signal Sequence Profile."
    ::= { sonusDiscSspAdmnEntry 1 }

sonusDiscSigSeqProfileName OBJECT-TYPE
    SYNTAX          SonusName
    ACCESS          read-write
    STATUS          mandatory
    DESCRIPTION     
            "The user name of this Disconnect Signal Sequence Profile."
    ::= { sonusDiscSspAdmnEntry 2 }

sonusDiscSigSeqProfileRowStatus OBJECT-TYPE
    SYNTAX          RowStatus
    ACCESS          read-write
    STATUS          mandatory
    DESCRIPTION     
            ""
    ::= { sonusDiscSspAdmnEntry 3 }

sonusDiscSigSeqAdmnTable OBJECT-TYPE
    SYNTAX          SEQUENCE OF SonusDiscSigSeqAdmnEntry
    ACCESS          not-accessible
    STATUS          mandatory
    DESCRIPTION     
            ""
    ::= { sonusDisconnectTreatmentObjects 4 }

sonusDiscSigSeqAdmnEntry OBJECT-TYPE
    SYNTAX          SonusDiscSigSeqAdmnEntry
    ACCESS          not-accessible
    STATUS          mandatory
    DESCRIPTION     
            ""
    INDEX           { sonusDiscSigSequenceProfileIndex, 
                      sonusDiscSigSequenceIndex }
    ::= { sonusDiscSigSeqAdmnTable 1 }

SonusDiscSigSeqAdmnEntry ::=
    SEQUENCE {
        sonusDiscSigSequenceProfileIndex INTEGER,
        sonusDiscSigSequenceIndex       INTEGER,
        sonusDiscSigSequencePosition    INTEGER,
        sonusDiscSigSequenceToken       INTEGER,
        sonusDiscSigSequenceParam1      DisplayString,
        sonusDiscSigSequenceParam2      DisplayString,
        sonusDiscSigSequenceAdminState  SonusAdminState,
        sonusDiscSigSequenceRowStatus   RowStatus
    }

sonusDiscSigSequenceProfileIndex OBJECT-TYPE
    SYNTAX          INTEGER
    ACCESS          not-accessible
    STATUS          mandatory
    DESCRIPTION     
            ""
    ::= { sonusDiscSigSeqAdmnEntry 1 }

sonusDiscSigSequenceIndex OBJECT-TYPE
    SYNTAX          INTEGER
    ACCESS          not-accessible
    STATUS          mandatory
    DESCRIPTION     
            ""
    ::= { sonusDiscSigSeqAdmnEntry 2 }

sonusDiscSigSequencePosition OBJECT-TYPE
    SYNTAX          INTEGER (0..31)
    ACCESS          read-write
    STATUS          mandatory
    DESCRIPTION     
            ""
    DEFVAL          { 0 }
    ::= { sonusDiscSigSeqAdmnEntry 3 }

sonusDiscSigSequenceToken OBJECT-TYPE
    SYNTAX          INTEGER { playTone(7), playAnn(8), delay(9), 
                        clear(16), exec(17) }
    ACCESS          read-write
    STATUS          mandatory
    DESCRIPTION     
            ""
    DEFVAL          { clear }
    ::= { sonusDiscSigSeqAdmnEntry 4 }

sonusDiscSigSequenceParam1 OBJECT-TYPE
    SYNTAX          DisplayString (SIZE(0..31))
    ACCESS          read-write
    STATUS          mandatory
    DESCRIPTION     
            ""
    ::= { sonusDiscSigSeqAdmnEntry 5 }

sonusDiscSigSequenceParam2 OBJECT-TYPE
    SYNTAX          DisplayString (SIZE(0..31))
    ACCESS          read-write
    STATUS          mandatory
    DESCRIPTION     
            ""
    ::= { sonusDiscSigSeqAdmnEntry 6 }

sonusDiscSigSequenceAdminState OBJECT-TYPE
    SYNTAX          SonusAdminState
    ACCESS          read-write
    STATUS          mandatory
    DESCRIPTION     
            ""
    DEFVAL          { disabled }
    ::= { sonusDiscSigSeqAdmnEntry 7 }

sonusDiscSigSequenceRowStatus OBJECT-TYPE
    SYNTAX          RowStatus
    ACCESS          read-write
    STATUS          mandatory
    DESCRIPTION     
            ""
    ::= { sonusDiscSigSeqAdmnEntry 8 }

sonusTestCall OBJECT IDENTIFIER
    ::= { sonusNodeResourcesMIBObjects 15 }

sonusTestCallNextIndex OBJECT-TYPE
    SYNTAX          INTEGER
    ACCESS          read-only
    STATUS          mandatory
    DESCRIPTION     
            "The next valid index to use when creating an entry in
             the sonusTestCallAdmnTable"
    ::= { sonusTestCall 1 }

sonusTestCallAdmnTable OBJECT-TYPE
    SYNTAX          SEQUENCE OF SonusTestCallAdmnEntry
    ACCESS          not-accessible
    STATUS          mandatory
    DESCRIPTION     
            "This table specifies the test call list for the node."
    ::= { sonusTestCall 2 }

sonusTestCallAdmnEntry OBJECT-TYPE
    SYNTAX          SonusTestCallAdmnEntry
    ACCESS          not-accessible
    STATUS          mandatory
    DESCRIPTION     
            ""
    INDEX           { sonusTestCallAdmnIndex }
    ::= { sonusTestCallAdmnTable 1 }

SonusTestCallAdmnEntry ::=
    SEQUENCE {
        sonusTestCallAdmnIndex          INTEGER,
        sonusTestCallAdmnState          INTEGER,
        sonusTestCallAdmnName           SonusName,
        sonusTestCallAdmnEndPointShelf  INTEGER,
        sonusTestCallAdmnEndPointSlot   INTEGER,
        sonusTestCallAdmnEndPointPort   INTEGER,
        sonusTestCallAdmnEndPointChannel INTEGER,
        sonusTestCallAdmnRowStatus      RowStatus,
        sonusTestCallAdmnType           INTEGER,
        sonusTestCallAdmnPower          INTEGER,
        sonusTestCallAdmnFrequency      INTEGER,
        sonusTestCallAdmnStatPower      INTEGER,
        sonusTestCallAdmnStatPowerTenths INTEGER
    }

sonusTestCallAdmnIndex OBJECT-TYPE
    SYNTAX          INTEGER
    ACCESS          read-only
    STATUS          mandatory
    DESCRIPTION     
            "Identifies the target test call entry."
    ::= { sonusTestCallAdmnEntry 1 }

sonusTestCallAdmnState OBJECT-TYPE
    SYNTAX          INTEGER { disabled(0), enabled(1) }
    ACCESS          read-write
    STATUS          mandatory
    DESCRIPTION     
            "The administrative state of this test call entry."
    DEFVAL          { disabled }
    ::= { sonusTestCallAdmnEntry 2 }

sonusTestCallAdmnName OBJECT-TYPE
    SYNTAX          SonusName
    ACCESS          read-write
    STATUS          mandatory
    DESCRIPTION     
            "The user name of this test call."
    ::= { sonusTestCallAdmnEntry 3 }

sonusTestCallAdmnEndPointShelf OBJECT-TYPE
    SYNTAX          INTEGER (1..6)
    ACCESS          read-write
    STATUS          mandatory
    DESCRIPTION     
            "A 32-bit integer identifying the shelf of the end point"
    ::= { sonusTestCallAdmnEntry 4 }

sonusTestCallAdmnEndPointSlot OBJECT-TYPE
    SYNTAX          INTEGER (1..16)
    ACCESS          read-write
    STATUS          mandatory
    DESCRIPTION     
            "A 32-bit integer identifying the slot of the end point"
    ::= { sonusTestCallAdmnEntry 5 }

sonusTestCallAdmnEndPointPort OBJECT-TYPE
    SYNTAX          INTEGER (1..65535)
    ACCESS          read-write
    STATUS          mandatory
    DESCRIPTION     
            "Port index of end point."
    ::= { sonusTestCallAdmnEntry 6 }

sonusTestCallAdmnEndPointChannel OBJECT-TYPE
    SYNTAX          INTEGER (1..32)
    ACCESS          read-write
    STATUS          mandatory
    DESCRIPTION     
            "Indicates the DS0 channel of the end point."
    ::= { sonusTestCallAdmnEntry 7 }

sonusTestCallAdmnRowStatus OBJECT-TYPE
    SYNTAX          RowStatus
    ACCESS          read-write
    STATUS          mandatory
    DESCRIPTION     
            ""
    ::= { sonusTestCallAdmnEntry 8 }

sonusTestCallAdmnType OBJECT-TYPE
    SYNTAX          INTEGER { listen(0), play(1) }
    ACCESS          read-write
    STATUS          mandatory
    DESCRIPTION     
            "The circuit type for this test call."
    DEFVAL          { listen }
    ::= { sonusTestCallAdmnEntry 9 }

sonusTestCallAdmnPower OBJECT-TYPE
    SYNTAX          INTEGER (-50..3)
    ACCESS          read-write
    STATUS          mandatory
    DESCRIPTION     
            "The power in dBm of the tone to play."
    DEFVAL          { -6 }
    ::= { sonusTestCallAdmnEntry 10 }

sonusTestCallAdmnFrequency OBJECT-TYPE
    SYNTAX          INTEGER (0..3999)
    ACCESS          read-write
    STATUS          mandatory
    DESCRIPTION     
            "The frequency in Hz of the tone to play or listen for."
    DEFVAL          { 1004 }
    ::= { sonusTestCallAdmnEntry 11 }

sonusTestCallAdmnStatPower OBJECT-TYPE
    SYNTAX          INTEGER (-1000..3)
    ACCESS          read-write
    STATUS          mandatory
    DESCRIPTION     
            "The dBm of the tone received in LISTEN mode."
    DEFVAL          { -1000 }
    ::= { sonusTestCallAdmnEntry 12 }

sonusTestCallAdmnStatPowerTenths OBJECT-TYPE
    SYNTAX          INTEGER (0..9)
    ACCESS          read-write
    STATUS          mandatory
    DESCRIPTION     
            "The tenths of dBm of the tone received in LISTEN mode."
    DEFVAL          { 0 }
    ::= { sonusTestCallAdmnEntry 13 }

sonusTestCallStatTable OBJECT-TYPE
    SYNTAX          SEQUENCE OF SonusTestCallStatEntry
    ACCESS          not-accessible
    STATUS          mandatory
    DESCRIPTION     
            "The Manual Call Stat Table"
    ::= { sonusNodeResourcesMIBObjects 16 }

sonusTestCallStatEntry OBJECT-TYPE
    SYNTAX          SonusTestCallStatEntry
    ACCESS          not-accessible
    STATUS          mandatory
    DESCRIPTION     
            "An entry in the Manual Call Stat Table"
    INDEX           { sonusTestCallStatIndex }
    ::= { sonusTestCallStatTable 1 }

SonusTestCallStatEntry ::=
    SEQUENCE {
        sonusTestCallStatIndex          INTEGER,
        sonusTestCallStatCallId         INTEGER,
        sonusTestCallStatState          DisplayString,
        sonusTestCallStatTime           DisplayString,
        sonusTestCallStatEnableStatus   INTEGER
    }

sonusTestCallStatIndex OBJECT-TYPE
    SYNTAX          INTEGER
    ACCESS          read-only
    STATUS          mandatory
    DESCRIPTION     
            "The index for target test call."
    ::= { sonusTestCallStatEntry 1 }

sonusTestCallStatCallId OBJECT-TYPE
    SYNTAX          INTEGER
    ACCESS          read-only
    STATUS          mandatory
    DESCRIPTION     
            "The call identifier(GCID) assigned to this test call"
    ::= { sonusTestCallStatEntry 2 }

sonusTestCallStatState OBJECT-TYPE
    SYNTAX          DisplayString (SIZE(0..23))
    ACCESS          read-only
    STATUS          mandatory
    DESCRIPTION     
            "The status of the test call"
    ::= { sonusTestCallStatEntry 3 }

sonusTestCallStatTime OBJECT-TYPE
    SYNTAX          DisplayString (SIZE(0..23))
    ACCESS          read-only
    STATUS          mandatory
    DESCRIPTION     
            "Displays the Date/time the connection was created"
    ::= { sonusTestCallStatEntry 4 }

sonusTestCallStatEnableStatus OBJECT-TYPE
    SYNTAX          INTEGER { success(1), calladmissionsuspended(2), 
                        resourceallocationfailure(3) }
    ACCESS          read-only
    STATUS          mandatory
    DESCRIPTION     
            "Indicates why the test call could not be properly set up."
    ::= { sonusTestCallStatEntry 5 }

sonusTestCallActionObjects OBJECT IDENTIFIER
    ::= { sonusNodeResourcesMIBObjects 17 }

sonusTestCallGcid OBJECT-TYPE
    SYNTAX          INTEGER
    ACCESS          read-write
    STATUS          mandatory
    DESCRIPTION     
            "The call identifier for a call to be deleted"
    ::= { sonusTestCallActionObjects 1 }

sonusTestCallAction OBJECT-TYPE
    SYNTAX          INTEGER { none(1), delete(2) }
    ACCESS          read-write
    STATUS          mandatory
    DESCRIPTION     
            "The action that should be taken on the call"
    DEFVAL          { none }
    ::= { sonusTestCallActionObjects 2 }

sonusAudioEncodingTable OBJECT-TYPE
    SYNTAX          SEQUENCE OF SonusAudioEncodingEntry
    ACCESS          not-accessible
    STATUS          mandatory
    DESCRIPTION     
            "This table specifies the Audio Encoding entries for the
             Packet Service Profiles.  There are always four Audio
             Encoding entries per Packet Service Profile, which
             are created and deleted automatically with their Packet
             Service Profile entry.  Refer to the sonusPktServProfileTable."
    ::= { sonusNodeResourcesMIBObjects 18 }

sonusAudioEncodingEntry OBJECT-TYPE
    SYNTAX          SonusAudioEncodingEntry
    ACCESS          not-accessible
    STATUS          mandatory
    DESCRIPTION     
            ""
    INDEX           { sonusAudioEncodingPktServProfileIndex, 
                      sonusAudioEncodingPriority }
    ::= { sonusAudioEncodingTable 1 }

SonusAudioEncodingEntry ::=
    SEQUENCE {
        sonusAudioEncodingPktServProfileIndex     INTEGER,
        sonusAudioEncodingPriority      INTEGER,
        sonusAudioEncodingCodec         INTEGER,
        sonusAudioEncodingG711Law       INTEGER,
        sonusAudioEncodingModemToneTreatment    INTEGER,
        sonusAudioEncodingFaxToneTreatment  INTEGER,
        sonusAudioEncodingModemToneFailureHandling          INTEGER,
        sonusAudioEncodingFaxToneFailureHandling        INTEGER,
        sonusAudioEncodingDtmfRelay     INTEGER,
        sonusAudioEncodingDtmfRemoveDigits  INTEGER,
        sonusAudioEncodingPacketSize    INTEGER,
        sonusAudioEncodingCodingRate    INTEGER,
        sonusAudioEncodingG711SendSID   INTEGER,
        sonusAudioEncodingRtpPayloadType INTEGER,
        sonusAudioEncodingAmrGancMode   SonusAdminState,
        sonusAudioEncodingAmrModeSet    OCTET STRING,
        sonusAudioEncodingAmrwbModeSet  OCTET STRING,
        sonusAudioEncodingCodecRedundancy INTEGER,
        sonusAudioEncodingAmrwbIuUPMode SonusAdminState,
        sonusAudioEncodingEvrcMaxInterLeaveDepth        INTEGER
    }

sonusAudioEncodingPktServProfileIndex OBJECT-TYPE
    SYNTAX          INTEGER
    ACCESS          read-only
    STATUS          mandatory
    DESCRIPTION     
            "The index of the Packet Service Profile for this
             Audio Encoding entry."
    ::= { sonusAudioEncodingEntry 1 }

sonusAudioEncodingPriority OBJECT-TYPE
    SYNTAX          INTEGER (1..12)
    ACCESS          read-only
    STATUS          mandatory
    DESCRIPTION     
            "The priority of this Audio Encoding entry relative to its
             Packet Service Profile."
    ::= { sonusAudioEncodingEntry 2 }

sonusAudioEncodingCodec OBJECT-TYPE
    SYNTAX          INTEGER { none(0), g711(1), g711ss(2), g7231(3), 
                        g729a(4), g729ab(5), g7231a(7), g726(8), ilbc(9), 
                        ilbcss(10), g722(11), g722ss(12), g7221(13), 
                        g7221ss(14), g728(15), g728ss(16), 
                        amrBandwidthEfficient(17), amrOctetAligned(18), 
                        amrCrc(19), amrCrcInterleaving(20), 
                        amrCrcRobustSorting(21), 
                        amrCrcInterleavingRobustSorting(22), 
                        amrInterleaving(23), 
                        amrInterleavingRobustSorting(24), 
                        amrRobustSorting(25), 
                        amrwbBandwidthEfficient(26), 
                        amrwbOctetAligned(27), amrwbCrc(28), 
                        amrwbCrcInterleaving(29), 
                        amrwbCrcRobustSorting(30), 
                        amrwbCrcInterleavingRobustSorting(31), 
                        amrwbInterleaving(32), 
                        amrwbInterleavingRobustSorting(33), 
                        amrwbRobustSorting(34), evrc(35), evrc0(36), 
                        evrc1(37), evrc1Fr(38), evrcb(39), evrcb0(40), 
                        evrcb1(41), evrcb1Fr(42), efr(43), g726ss(46), 
                        amr(47) }
    ACCESS          read-write
    STATUS          mandatory
    DESCRIPTION     
            "The codec of this Audio Encoding entry."
    DEFVAL          { g711 }
    ::= { sonusAudioEncodingEntry 3 }

sonusAudioEncodingG711Law OBJECT-TYPE
    SYNTAX          INTEGER { lawFromOtherLeg(1), aLaw(2), uLaw(3) }
    ACCESS          read-write
    STATUS          mandatory
    DESCRIPTION     
            "The G.711 Law value.  Applicable only when
             sonusAudioEncodingCodec is set to g711 or g711ss."
    DEFVAL          { lawFromOtherLeg }
    ::= { sonusAudioEncodingEntry 4 }

sonusAudioEncodingModemToneTreatment OBJECT-TYPE
    SYNTAX          INTEGER { none(1), notifyPeer(2), disconnect(3), 
                        g711Fallback(4), applyFaxTreatment(5) }
    ACCESS          read-write
    STATUS          mandatory
    DESCRIPTION     
            "Specifies the treatment taken when the modem tone is detected:
             
             none          Do nothing when modem tone detected.
             notifyPeer    Notify peer when modem tone detected.
             disconnect    Disconnect the call when modem tone detected.
             g711Fallback      Fallback to G.711 when modem tone detected.
             applyFaxTreatment Treat it as a fax tone and apply fax treatment."
    DEFVAL          { none }
    ::= { sonusAudioEncodingEntry 5 }

sonusAudioEncodingFaxToneTreatment OBJECT-TYPE
    SYNTAX          INTEGER { none(1), notifyPeer(2), disconnect(3), 
                        g711Fallback(4), faxRelay(5), 
                        faxRelayOrG711Fallback(6) }
    ACCESS          read-write
    STATUS          mandatory
    DESCRIPTION     
            "Specifies the treatment taken when the fax tone is detected:
             
             none          Do nothing when fax tone detected.
             notifyPeer    Notify peer when fax tone detected.
             disconnect    Disconnect the call when fax tone detected.
             g711fallback  Fallback to G.711 when fax tone detected.
             faxRelay      Fax relay when fax tone detected;
                           requires XPAD resource.
             faxRelayG711Fallback
                           Fax relay / Fallback to G.711 when fax tone detected;
                           requires XPAD resource."
    DEFVAL          { none }
    ::= { sonusAudioEncodingEntry 6 }

sonusAudioEncodingModemToneFailureHandling OBJECT-TYPE
    SYNTAX          INTEGER { disconnect(1), continue(2) }
    ACCESS          read-write
    STATUS          mandatory
    DESCRIPTION     
            "This specifies the behavior when a modem tone is detected but
             modem tone treatment fails for any reason."
    DEFVAL          { continue }
    ::= { sonusAudioEncodingEntry 7 }

sonusAudioEncodingFaxToneFailureHandling OBJECT-TYPE
    SYNTAX          INTEGER { disconnect(1), continue(2) }
    ACCESS          read-write
    STATUS          mandatory
    DESCRIPTION     
            "This specifies the behavior when a fax tone is detected but
             modem tone treatment fails for any reason."
    DEFVAL          { continue }
    ::= { sonusAudioEncodingEntry 8 }

sonusAudioEncodingDtmfRelay OBJECT-TYPE
    SYNTAX          INTEGER { none(1), longDigit(2), outOfBand(3), 
                        rfc2833(4), eitherOobOr2833(129), 
                        bothOobAnd2833(130) }
    ACCESS          read-write
    STATUS          mandatory
    DESCRIPTION     
            "none               No delay
             longDigit          # (or ##), applicable to SIP only.
             outOfBand          Applicable to SIP INFO or H245; requires XPAD resource.
             rfc2833            Use RFC2833 inband payload type - Requires XPAD resource.
             eitherOobOr2833    Signals either out-of-band or in-band - Requires XPAD resource.
             bothOobAnd2833     Signals both out-of-band and in-band - Requires XPAD resource."
    DEFVAL          { none }
    ::= { sonusAudioEncodingEntry 9 }

sonusAudioEncodingDtmfRemoveDigits OBJECT-TYPE
    SYNTAX          INTEGER { disabled(1), enabled(2) }
    ACCESS          read-write
    STATUS          mandatory
    DESCRIPTION     
            "Specifies whether removing DTMF digits from the media
             stream is enabled.  This applies if sonusAudioEncodingDtmfRelay
             	 is configured as outOfBand or rfc2833."
    DEFVAL          { enabled }
    ::= { sonusAudioEncodingEntry 10 }

sonusAudioEncodingPacketSize OBJECT-TYPE
    SYNTAX          INTEGER
    ACCESS          read-write
    STATUS          mandatory
    DESCRIPTION     
            "The packet size in milliseconds.  The valid ranges for 
             the various ranges are:
             
             G.711     10ms to 40ms, in increments of 5ms
             G.711SS   10ms to 40ms, in increments of 5ms
             G.723.1   30ms to 150ms, in increments of 30ms
             G.723.1A  30ms to 150ms, in increments of 30ms
             G.726     10ms to 40ms, in increments of 10ms
             G.726SS   10ms to 40ms, in increments of 10ms
             G.729A    10ms to 40ms, in increments of 10ms
             G.729A+B  10ms to 40ms, in increments of 10ms
             iLBC      20ms to 60ms, a multiple of the mode
             iLBCSS    20ms to 60ms, a multiple of the mode
             
             G.722     10ms to 40ms, in increments of 10ms
             G.722SS   10ms to 40ms, in increments of 10ms
             G.7221    20ms to 80ms, in increments of 20ms
             G.7221SS  20ms to 80ms, in increments of 20ms
             G.728     10ms to 150ms, in increments of 10ms
             G.728SS   10ms to 150ms, in increments of 10ms
             AMR (all) 20ms to 60ms, in increments of 20ms
             AMRWB (all) 20ms to 100ms, in increments of 20ms
             EFR       20ms to 60ms, in increments of 20ms
             EVRC0     20ms 	
             EVRC  (all) 20ms to 60ms, in increments of 20ms
             
             If a compression resource is allocated for G.711,
             the packet size is rounded to a multiple of 10ms.
             For iLBC/iLBCSS, the packet size is a multiple, based on
             the coding rate, of 30ms for 13.3kbps, 20ms for 15.2kbps."
    DEFVAL          { 10 }
    ::= { sonusAudioEncodingEntry 11 }

sonusAudioEncodingCodingRate OBJECT-TYPE
    SYNTAX          INTEGER { r0bps(1), r5300bps(2), r6300bps(3), 
                        r16kbps(4), r24kbps(5), r32kbps(6), r48kbps(7), 
                        r13333bps(8), r15200bps(9), r4kbps(10), 
                        r8550bps(11), r56kbps(12), r64kbps(13) }
    ACCESS          read-write
    STATUS          mandatory
    DESCRIPTION     
            "The coding rate in bits per second; applicable only to the
             G.723.1, G.723.1A, G.726, iLBC, EVRC, G722 and G722.1 audio encoding codecs.
             The valid values are as follows:
             
             G.723.1, G.723.1A   5300bps, 6300bps (default)
             G.726, G.726SS      16kbps, 24kbps, 32kbps (default), 48kbps
             iLBC, iLBCSS        13333bps (default), 15200bps
             EVRC1, EVRCB1       4kbps (default), 8550bps
             G.722               48kbps, 56kbps, 64kbps (default)
             G.722.1             24kbps (default), 32kbps"
    DEFVAL          { r0bps }
    ::= { sonusAudioEncodingEntry 12 }

sonusAudioEncodingG711SendSID OBJECT-TYPE
    SYNTAX          INTEGER { disabled(1), enabled(2) }
    ACCESS          read-write
    STATUS          mandatory
    DESCRIPTION     
            "Specifies whether SID (Silence Insertion Descriptor) packets
             are sent (enabled) on a call enabled for G.711SS.  If disabled
             the G.711SS call does not send SID packets so placing the burden
             		 entirely on the remote side to determine the way it will generate
             		 comfort noise.  Applicable only for G.711 audio encoding codec."
    DEFVAL          { disabled }
    ::= { sonusAudioEncodingEntry 13 }

sonusAudioEncodingRtpPayloadType OBJECT-TYPE
    SYNTAX          INTEGER (0..128)
    ACCESS          read-write
    STATUS          mandatory
    DESCRIPTION     
            "Specifies the preferred RTP payload type to be set
             in the RTP header of audio packets for this encoding.
             For most codecs, use the value 128 to select the static
             RTP payload type assigned to the codec by RFC 3551.
             This field was introduced for iLBC and is not supported
             for all compressed encodings.  The preference may not
             be honored if the signaling peer offers a different
             value first."
    DEFVAL          { 128 }
    ::= { sonusAudioEncodingEntry 14 }

sonusAudioEncodingAmrGancMode OBJECT-TYPE
    SYNTAX          SonusAdminState
    ACCESS          read-write
    STATUS          mandatory
    DESCRIPTION     
            "For AMR only, determines default mode (disabled) or GANC mode (enabled)"
    DEFVAL          { disabled }
    ::= { sonusAudioEncodingEntry 15 }

sonusAudioEncodingAmrModeSet OBJECT-TYPE
    SYNTAX          OCTET STRING
--                       { r4750bps(0), r5150bps(1), r5900bps(2), 
--                         r6700bps(3), r7400bps(4), r7950bps(5), 
--                         r10200bps(6), r12200bps(7) }
    ACCESS          read-write
    STATUS          mandatory
    DESCRIPTION     
            "Bitstring representing the AMR active codec mode set."
    DEFVAL          { 0 }
    ::= { sonusAudioEncodingEntry 16 }

sonusAudioEncodingAmrwbModeSet OBJECT-TYPE
    SYNTAX          OCTET STRING
--                       { r6600bps(0), r8850bps(1), r12650bps(2), 
--                         r14250bps(3), r15850bps(4), r18250bps(5), 
--                         r19850bps(6), r23050bps(7), r23850bps(8) }
    ACCESS          read-write
    STATUS          mandatory
    DESCRIPTION     
            "Bitstring representing the AMRWB active codec mode set."
    DEFVAL          { 0 }
    ::= { sonusAudioEncodingEntry 17 }

sonusAudioEncodingCodecRedundancy OBJECT-TYPE
    SYNTAX          INTEGER { none(0), one(1), two(2) }
    ACCESS          read-write
    STATUS          mandatory
    DESCRIPTION     
            "For AMR and AMRWB, determines the packet redundancy level."
    DEFVAL          { none }
    ::= { sonusAudioEncodingEntry 20 }

sonusAudioEncodingAmrwbIuUPMode OBJECT-TYPE
    SYNTAX          SonusAdminState
    ACCESS          read-write
    STATUS          mandatory
    DESCRIPTION     
            "For AMRWB only, determines default mode (disabled) or IuUP mode (enabled)"
    DEFVAL          { disabled }
    ::= { sonusAudioEncodingEntry 22 }

sonusAudioEncodingEvrcMaxInterLeaveDepth OBJECT-TYPE
    SYNTAX          INTEGER (0..7)
    ACCESS          read-write
    STATUS          mandatory
    DESCRIPTION     
            "This parameter indicates the amount of interleaving an endpoint can deal with. Peer is expected to not exceed
             the interleave value in packet it sends. For EVRC & EVRCB the default value is 5 and for evrc0, evrcb0, evrc1
              & evrcb1 the default value is 0 i.e., 0 indicates no interleaving"
    DEFVAL          { 5 }
    ::= { sonusAudioEncodingEntry 23 }

sonusCrankBackObjects OBJECT IDENTIFIER
    ::= { sonusNodeResourcesMIBObjects 19 }

sonusCrankBackProfile OBJECT IDENTIFIER
    ::= { sonusCrankBackObjects 1 }

sonusCrankBackProfileNextIndex OBJECT-TYPE
    SYNTAX          INTEGER
    ACCESS          read-only
    STATUS          mandatory
    DESCRIPTION     
            "The next valid index to use when creating an entry in
             the sonusCrankBackProfileTable."
    ::= { sonusCrankBackProfile 1 }

sonusCrankBackProfileTable OBJECT-TYPE
    SYNTAX          SEQUENCE OF SonusCrankBackProfileEntry
    ACCESS          not-accessible
    STATUS          mandatory
    DESCRIPTION     
            "This table contains Crank Back Profiles for the node."
    ::= { sonusCrankBackProfile 2 }

sonusCrankBackProfileEntry OBJECT-TYPE
    SYNTAX          SonusCrankBackProfileEntry
    ACCESS          not-accessible
    STATUS          mandatory
    DESCRIPTION     
            ""
    INDEX           { sonusCrankBackProfileIndex }
    ::= { sonusCrankBackProfileTable 1 }

SonusCrankBackProfileEntry ::=
    SEQUENCE {
        sonusCrankBackProfileIndex      INTEGER,
        sonusCrankBackProfileName       SonusName,
        sonusCrankBackProfileRowStatus  RowStatus,
        sonusCrankBackProfileLateCrankBack  INTEGER,
        sonusCrankBackProfileAttemptRecordGeneration            INTEGER,
        sonusCrankBackProfileType       INTEGER
    }

sonusCrankBackProfileIndex OBJECT-TYPE
    SYNTAX          INTEGER
    ACCESS          not-accessible
    STATUS          mandatory
    DESCRIPTION     
            "Identifies the Crank Back Profile."
    DEFVAL          { 1 }
    ::= { sonusCrankBackProfileEntry 1 }

sonusCrankBackProfileName OBJECT-TYPE
    SYNTAX          SonusName
    ACCESS          read-write
    STATUS          mandatory
    DESCRIPTION     
            "The user name of this Crank Back Profile."
    ::= { sonusCrankBackProfileEntry 2 }

sonusCrankBackProfileRowStatus OBJECT-TYPE
    SYNTAX          RowStatus
    ACCESS          read-write
    STATUS          mandatory
    DESCRIPTION     
            ""
    ::= { sonusCrankBackProfileEntry 3 }

sonusCrankBackProfileLateCrankBack OBJECT-TYPE
    SYNTAX          INTEGER { disabled(1), enabled(2) }
    ACCESS          read-write
    STATUS          mandatory
    DESCRIPTION     
            "When enabled, a late crankback may be performed.  That is,
             after an ALERT, PROGRESS or equivalent message has been
             received from the egress network.
                  When disabled, late crankbacks will never be performed.
             The default state is 'disabled'."
    DEFVAL          { disabled }
    ::= { sonusCrankBackProfileEntry 4 }

sonusCrankBackProfileAttemptRecordGeneration OBJECT-TYPE
    SYNTAX          INTEGER { disabled(1), enabled(2) }
    ACCESS          read-write
    STATUS          mandatory
    DESCRIPTION     
            "When enabled, an ATTEMPT record will be logged to the
             accounting file after each crankback.  When disabled,
             ATTEMPT records will not be logged for crankbacks.
             The default state is 'disabled'."
    DEFVAL          { disabled }
    ::= { sonusCrankBackProfileEntry 5 }

sonusCrankBackProfileType OBJECT-TYPE
    SYNTAX          INTEGER { crankback(0), skip(1) }
    ACCESS          read-write
    STATUS          mandatory
    DESCRIPTION     
            "Identifies the Crank Back Profile Type - CrankBack or Skip."
    DEFVAL          { crankback }
    ::= { sonusCrankBackProfileEntry 7 }

sonusCrankBackAdmnTable OBJECT-TYPE
    SYNTAX          SEQUENCE OF SonusCrankBackAdmnEntry
    ACCESS          not-accessible
    STATUS          mandatory
    DESCRIPTION     
            ""
    ::= { sonusCrankBackObjects 2 }

sonusCrankBackAdmnEntry OBJECT-TYPE
    SYNTAX          SonusCrankBackAdmnEntry
    ACCESS          not-accessible
    STATUS          mandatory
    DESCRIPTION     
            ""
    INDEX           { sonusCrankBackwardProfileIndex, 
                      sonusCrankBackIndex }
    ::= { sonusCrankBackAdmnTable 1 }

SonusCrankBackAdmnEntry ::=
    SEQUENCE {
        sonusCrankBackwardProfileIndex  INTEGER,
        sonusCrankBackIndex             INTEGER,
        sonusCrankBackReason            INTEGER,
        sonusCrankBackRowStatus         RowStatus,
        sonusCrankBackCompareLocationValueBeforeCrankingBack                    INTEGER
    }

sonusCrankBackwardProfileIndex OBJECT-TYPE
    SYNTAX          INTEGER
    ACCESS          not-accessible
    STATUS          mandatory
    DESCRIPTION     
            "Identifies the Crank Back Profile to which this entry belongs."
    ::= { sonusCrankBackAdmnEntry 1 }

sonusCrankBackIndex OBJECT-TYPE
    SYNTAX          INTEGER
    ACCESS          not-accessible
    STATUS          mandatory
    DESCRIPTION     
            "Identifies the target Crank Back entry."
    ::= { sonusCrankBackAdmnEntry 2 }

sonusCrankBackReason OBJECT-TYPE
    SYNTAX          INTEGER (0..255)
    ACCESS          read-only
    STATUS          mandatory
    DESCRIPTION     
            "Disconnect Reason Code."
    ::= { sonusCrankBackAdmnEntry 3 }

sonusCrankBackRowStatus OBJECT-TYPE
    SYNTAX          RowStatus
    ACCESS          read-write
    STATUS          mandatory
    DESCRIPTION     
            ""
    ::= { sonusCrankBackAdmnEntry 4 }

sonusCrankBackCompareLocationValueBeforeCrankingBack OBJECT-TYPE
    SYNTAX          INTEGER { disabled(1), enabled(2) }
    ACCESS          read-write
    STATUS          mandatory
    DESCRIPTION     
            "Use Location Table values for this reason code while cranking back on the next route. "
    DEFVAL          { disabled }
    ::= { sonusCrankBackAdmnEntry 5 }

sonusCrankBackLocationCodeAdmnTable OBJECT-TYPE
    SYNTAX          SEQUENCE OF SonusCrankBackLocationCodeAdmnEntry
    ACCESS          not-accessible
    STATUS          mandatory
    DESCRIPTION     
            ""
    ::= { sonusCrankBackObjects 3 }

sonusCrankBackLocationCodeAdmnEntry OBJECT-TYPE
    SYNTAX          SonusCrankBackLocationCodeAdmnEntry
    ACCESS          not-accessible
    STATUS          mandatory
    DESCRIPTION     
            ""
    INDEX           { sonusCrankBackLocationProfileIndex, 
                      sonusCrankBackLocationReasonIndex, 
                      sonusCrankBackLocationIndex }
    ::= { sonusCrankBackLocationCodeAdmnTable 1 }

SonusCrankBackLocationCodeAdmnEntry ::=
    SEQUENCE {
        sonusCrankBackLocationProfileIndex  INTEGER,
        sonusCrankBackLocationReasonIndex INTEGER,
        sonusCrankBackLocationIndex     INTEGER,
        sonusCrankBackLocationValue     INTEGER,
        sonusCrankBackLocationRowStatus RowStatus
    }

sonusCrankBackLocationProfileIndex OBJECT-TYPE
    SYNTAX          INTEGER
    ACCESS          not-accessible
    STATUS          mandatory
    DESCRIPTION     
            "Identifies the Crank Back Profile to which this entry belongs."
    ::= { sonusCrankBackLocationCodeAdmnEntry 1 }

sonusCrankBackLocationReasonIndex OBJECT-TYPE
    SYNTAX          INTEGER
    ACCESS          not-accessible
    STATUS          mandatory
    DESCRIPTION     
            "Identifies the Crank Back Reason to which this entry belongs."
    ::= { sonusCrankBackLocationCodeAdmnEntry 2 }

sonusCrankBackLocationIndex OBJECT-TYPE
    SYNTAX          INTEGER { user(2), privateLocal(3), publicLocal(4), 
                        transitNet(5), publicRemote(6), privateRemote(7), 
                        natReserved6(8), internationalNet(9), 
                        natReserved8(10), natReserved9(11), 
                        netBeyondInterPoint(12), natReserved11(13), 
                        natReserved12(14), natReserved13(15), 
                        natReserved14(16), natReserved15(17), 
                        gwLinkFailure(18) }
    ACCESS          not-accessible
    STATUS          mandatory
    DESCRIPTION     
            "Identifies the target Crank Back Location Code entry."
    ::= { sonusCrankBackLocationCodeAdmnEntry 3 }

sonusCrankBackLocationValue OBJECT-TYPE
    SYNTAX          INTEGER { user(1), privateLocal(2), publicLocal(3), 
                        transitNet(4), publicRemote(5), privateRemote(6), 
                        natReserved6(7), internationalNet(8), 
                        natReserved8(9), natReserved9(10), 
                        netBeyondInterPoint(11), natReserved11(12), 
                        natReserved12(13), natReserved13(14), 
                        natReserved14(15), natReserved15(16), 
                        gwLinkFailure(17) }
    ACCESS          read-only
    STATUS          mandatory
    DESCRIPTION     
            "This represents the Release Cause Location value"
    ::= { sonusCrankBackLocationCodeAdmnEntry 4 }

sonusCrankBackLocationRowStatus OBJECT-TYPE
    SYNTAX          RowStatus
    ACCESS          read-write
    STATUS          mandatory
    DESCRIPTION     
            ""
    ::= { sonusCrankBackLocationCodeAdmnEntry 5 }

sonusOverloadObjects OBJECT IDENTIFIER
    ::= { sonusNodeResourcesMIBObjects 20 }

sonusOverloadProfile OBJECT IDENTIFIER
    ::= { sonusOverloadObjects 1 }

sonusOverloadProfileNextIndex OBJECT-TYPE
    SYNTAX          INTEGER
    ACCESS          read-only
    STATUS          mandatory
    DESCRIPTION     
            "The next valid index to use when creating an entry in
             the sonusOverloadProfileTable."
    ::= { sonusOverloadProfile 1 }

sonusOverloadProfileTable OBJECT-TYPE
    SYNTAX          SEQUENCE OF SonusOverloadProfileEntry
    ACCESS          not-accessible
    STATUS          mandatory
    DESCRIPTION     
            "This table contains Overload profile for the node."
    ::= { sonusOverloadProfile 2 }

sonusOverloadProfileEntry OBJECT-TYPE
    SYNTAX          SonusOverloadProfileEntry
    ACCESS          not-accessible
    STATUS          mandatory
    DESCRIPTION     
            ""
    INDEX           { sonusOverloadProfileIndex }
    ::= { sonusOverloadProfileTable 1 }

SonusOverloadProfileEntry ::=
    SEQUENCE {
        sonusOverloadProfileIndex       INTEGER,
        sonusOverloadProfileName        SonusName,
        sonusOverloadProfileRowStatus   RowStatus,
        sonusOverloadProfileAdminState  INTEGER,
        sonusOverloadProfileCPUSetThreshold   INTEGER,
        sonusOverloadProfileCPUClearThreshold     INTEGER,
        sonusOverloadProfileMemSetThreshold   INTEGER,
        sonusOverloadProfileMemClearThreshold     INTEGER,
        sonusOverloadProfilePsxSetThreshold   INTEGER,
        sonusOverloadProfilePsxClearThreshold     INTEGER,
        sonusOverloadProfileCallAcceptRate  INTEGER,
        sonusOverloadProfileCallRateSetThreshold        INTEGER,
        sonusOverloadProfileCallRateClearThreshold          INTEGER,
        sonusOverloadProfileCPUSetDuration  INTEGER,
        sonusOverloadProfileCPUClearDuration    INTEGER,
        sonusOverloadProfileMemSetDuration  INTEGER,
        sonusOverloadProfileMemClearDuration    INTEGER,
        sonusOverloadProfilePsxSetDuration  INTEGER,
        sonusOverloadProfilePsxClearDuration    INTEGER,
        sonusOverloadProfileCallRateSetDuration       INTEGER,
        sonusOverloadProfileCallRateClearDuration         INTEGER,
        sonusOverloadProfileLogSetThreshold   INTEGER,
        sonusOverloadProfileLogClearThreshold     INTEGER,
        sonusOverloadProfileLogSetDuration  INTEGER,
        sonusOverloadProfileLogClearDuration    INTEGER,
        sonusOverloadProfileICMSetThreshold   INTEGER,
        sonusOverloadProfileICMClearThreshold     INTEGER,
        sonusOverloadProfileICMSetDuration  INTEGER,
        sonusOverloadProfileICMClearDuration    INTEGER,
        sonusOverloadProfileCDRSetThreshold   INTEGER,
        sonusOverloadProfileCDRClearThreshold     INTEGER,
        sonusOverloadProfileCDRSetDuration  INTEGER,
        sonusOverloadProfileCDRClearDuration    INTEGER,
        sonusOverloadProfileAcceptNoCallsOnCDRCongestion                SonusAdminState
    }

sonusOverloadProfileIndex OBJECT-TYPE
    SYNTAX          INTEGER
    ACCESS          read-only
    STATUS          mandatory
    DESCRIPTION     
            "Identifies the Overload profile."
    ::= { sonusOverloadProfileEntry 1 }

sonusOverloadProfileName OBJECT-TYPE
    SYNTAX          SonusName
    ACCESS          read-write
    STATUS          mandatory
    DESCRIPTION     
            "The profile name."
    ::= { sonusOverloadProfileEntry 2 }

sonusOverloadProfileRowStatus OBJECT-TYPE
    SYNTAX          RowStatus
    ACCESS          read-write
    STATUS          mandatory
    DESCRIPTION     
            ""
    ::= { sonusOverloadProfileEntry 3 }

sonusOverloadProfileAdminState OBJECT-TYPE
    SYNTAX          INTEGER { disabled(1), enabled(2) }
    ACCESS          read-write
    STATUS          mandatory
    DESCRIPTION     
            "The administrative state of the overload profile."
    DEFVAL          { disabled }
    ::= { sonusOverloadProfileEntry 4 }

sonusOverloadProfileCPUSetThreshold OBJECT-TYPE
    SYNTAX          INTEGER (0..100)
    ACCESS          read-write
    STATUS          mandatory
    DESCRIPTION     
            "the CPU utilization percentage threshold at which a congestion level may be set."
    DEFVAL          { 85 }
    ::= { sonusOverloadProfileEntry 5 }

sonusOverloadProfileCPUClearThreshold OBJECT-TYPE
    SYNTAX          INTEGER (0..100)
    ACCESS          read-write
    STATUS          mandatory
    DESCRIPTION     
            "the CPU utilization percentage threshold at which a congestion level may be cleared."
    DEFVAL          { 80 }
    ::= { sonusOverloadProfileEntry 6 }

sonusOverloadProfileMemSetThreshold OBJECT-TYPE
    SYNTAX          INTEGER (0..100)
    ACCESS          read-write
    STATUS          mandatory
    DESCRIPTION     
            "the memory(or ICM) utilization percentage threshold at which a congestion level may be set."
    DEFVAL          { 90 }
    ::= { sonusOverloadProfileEntry 7 }

sonusOverloadProfileMemClearThreshold OBJECT-TYPE
    SYNTAX          INTEGER (0..100)
    ACCESS          read-write
    STATUS          mandatory
    DESCRIPTION     
            "the memory(or ICM) utilization percentage threshold at which a congestion level may be cleared."
    DEFVAL          { 85 }
    ::= { sonusOverloadProfileEntry 8 }

sonusOverloadProfilePsxSetThreshold OBJECT-TYPE
    SYNTAX          INTEGER (0..3)
    ACCESS          read-write
    STATUS          mandatory
    DESCRIPTION     
            "The PSX congestion level which sets the GSX congestion level"
    DEFVAL          { 1 }
    ::= { sonusOverloadProfileEntry 9 }

sonusOverloadProfilePsxClearThreshold OBJECT-TYPE
    SYNTAX          INTEGER (0..3)
    ACCESS          read-write
    STATUS          mandatory
    DESCRIPTION     
            "The PSX congestion level which clears the GSX congestion level"
    DEFVAL          { 0 }
    ::= { sonusOverloadProfileEntry 10 }

sonusOverloadProfileCallAcceptRate OBJECT-TYPE
    SYNTAX          INTEGER (0..100)
    ACCESS          read-write
    STATUS          mandatory
    DESCRIPTION     
            "the rate at which calls will be accepted in this congestion level."
    DEFVAL          { 85 }
    ::= { sonusOverloadProfileEntry 11 }

sonusOverloadProfileCallRateSetThreshold OBJECT-TYPE
    SYNTAX          INTEGER (0..65535)
    ACCESS          read-write
    STATUS          mandatory
    DESCRIPTION     
            "the rate of calls(in calls per second) at which a congestion level may be set."
    DEFVAL          { 100 }
    ::= { sonusOverloadProfileEntry 12 }

sonusOverloadProfileCallRateClearThreshold OBJECT-TYPE
    SYNTAX          INTEGER (0..65535)
    ACCESS          read-write
    STATUS          mandatory
    DESCRIPTION     
            "the rate of calls(in calls per second) at which a congestion level may be cleared."
    DEFVAL          { 90 }
    ::= { sonusOverloadProfileEntry 13 }

sonusOverloadProfileCPUSetDuration OBJECT-TYPE
    SYNTAX          INTEGER (0..65535)
    ACCESS          read-write
    STATUS          mandatory
    DESCRIPTION     
            "the length of time(in seconds) that the CPU utilization must be above its set threshold
             before the congestion level is set. 0 sets it immediately."
    DEFVAL          { 10 }
    ::= { sonusOverloadProfileEntry 14 }

sonusOverloadProfileCPUClearDuration OBJECT-TYPE
    SYNTAX          INTEGER (0..65535)
    ACCESS          read-write
    STATUS          mandatory
    DESCRIPTION     
            "the length of time(in seconds) that the CPU utilization must be below its clear threshold
             before the congestion level is cleared. 0 clears it immediately."
    DEFVAL          { 10 }
    ::= { sonusOverloadProfileEntry 15 }

sonusOverloadProfileMemSetDuration OBJECT-TYPE
    SYNTAX          INTEGER (0..65535)
    ACCESS          read-write
    STATUS          mandatory
    DESCRIPTION     
            "the length of time(in seconds) that the memory(or ICM) utilization must be above its set threshold
             before the congestion level is set. 0 sets it immediately."
    DEFVAL          { 10 }
    ::= { sonusOverloadProfileEntry 16 }

sonusOverloadProfileMemClearDuration OBJECT-TYPE
    SYNTAX          INTEGER (0..65535)
    ACCESS          read-write
    STATUS          mandatory
    DESCRIPTION     
            "the length of time(in seconds) that the memory(or ICM) utilization must be below its clear threshold
             before the congestion level is cleared. 0 clears it immediately."
    DEFVAL          { 10 }
    ::= { sonusOverloadProfileEntry 17 }

sonusOverloadProfilePsxSetDuration OBJECT-TYPE
    SYNTAX          INTEGER (0..65535)
    ACCESS          read-write
    STATUS          mandatory
    DESCRIPTION     
            "the length of time(in seconds) that the PSX congestion level must be above its set threshold
             before the congestion level is set. 0 sets it immediately."
    DEFVAL          { 10 }
    ::= { sonusOverloadProfileEntry 18 }

sonusOverloadProfilePsxClearDuration OBJECT-TYPE
    SYNTAX          INTEGER (0..65535)
    ACCESS          read-write
    STATUS          mandatory
    DESCRIPTION     
            "the length of time(in seconds) that the PSX congestion level must be  below its clear threshold
             before the congestion level is cleared. 0 clears it immediately."
    DEFVAL          { 10 }
    ::= { sonusOverloadProfileEntry 19 }

sonusOverloadProfileCallRateSetDuration OBJECT-TYPE
    SYNTAX          INTEGER (0..65535)
    ACCESS          read-write
    STATUS          mandatory
    DESCRIPTION     
            "the length of time(in seconds) that the call rate must be above its set threshold
             before the congestion level is set. 0 sets it immediately."
    DEFVAL          { 10 }
    ::= { sonusOverloadProfileEntry 20 }

sonusOverloadProfileCallRateClearDuration OBJECT-TYPE
    SYNTAX          INTEGER (0..65535)
    ACCESS          read-write
    STATUS          mandatory
    DESCRIPTION     
            "the length of time(in seconds) that the call rate must be below its clear threshold
             before the congestion level is cleared. 0 clears it immediately."
    DEFVAL          { 10 }
    ::= { sonusOverloadProfileEntry 21 }

sonusOverloadProfileLogSetThreshold OBJECT-TYPE
    SYNTAX          INTEGER (0..100)
    ACCESS          read-write
    STATUS          mandatory
    DESCRIPTION     
            "Identifies the Log spooler utilization percentage threshold at which a congestion level may be set."
    DEFVAL          { 90 }
    ::= { sonusOverloadProfileEntry 22 }

sonusOverloadProfileLogClearThreshold OBJECT-TYPE
    SYNTAX          INTEGER (0..100)
    ACCESS          read-write
    STATUS          mandatory
    DESCRIPTION     
            "Identifies the Log spooler utilization percentage threshold at which a congestion level may be cleared."
    DEFVAL          { 85 }
    ::= { sonusOverloadProfileEntry 23 }

sonusOverloadProfileLogSetDuration OBJECT-TYPE
    SYNTAX          INTEGER (0..65535)
    ACCESS          read-write
    STATUS          mandatory
    DESCRIPTION     
            "the length of time(in seconds) that the Log spooler utilization must be above its set threshold
             before the congestion level is set. 0 sets it immediately."
    DEFVAL          { 10 }
    ::= { sonusOverloadProfileEntry 24 }

sonusOverloadProfileLogClearDuration OBJECT-TYPE
    SYNTAX          INTEGER (0..65535)
    ACCESS          read-write
    STATUS          mandatory
    DESCRIPTION     
            "the length of time(in seconds) that the Log spooler utilization must be below its clear threshold
             before the congestion level is cleared. 0 clears it immediately."
    DEFVAL          { 10 }
    ::= { sonusOverloadProfileEntry 25 }

sonusOverloadProfileICMSetThreshold OBJECT-TYPE
    SYNTAX          INTEGER (0..254)
    ACCESS          read-write
    STATUS          mandatory
    DESCRIPTION     
            "the ICM congestion occurance threshold at which a congestion level may be set."
    DEFVAL          { 32 }
    ::= { sonusOverloadProfileEntry 26 }

sonusOverloadProfileICMClearThreshold OBJECT-TYPE
    SYNTAX          INTEGER (0..254)
    ACCESS          read-write
    STATUS          mandatory
    DESCRIPTION     
            "the ICM congestion occurance threshold at which a congestion level may be cleared."
    DEFVAL          { 8 }
    ::= { sonusOverloadProfileEntry 27 }

sonusOverloadProfileICMSetDuration OBJECT-TYPE
    SYNTAX          INTEGER (0..65535)
    ACCESS          read-write
    STATUS          mandatory
    DESCRIPTION     
            "the length of time(in seconds) that the ICM congestion occurances must be above its set threshold
             before the congestion level is set. 0 sets it immediately."
    DEFVAL          { 2 }
    ::= { sonusOverloadProfileEntry 28 }

sonusOverloadProfileICMClearDuration OBJECT-TYPE
    SYNTAX          INTEGER (0..65535)
    ACCESS          read-write
    STATUS          mandatory
    DESCRIPTION     
            "the length of time(in seconds) that the ICM congestion occurances must be below its clear threshold
             before the congestion level is cleared. 0 clears it immediately."
    DEFVAL          { 3 }
    ::= { sonusOverloadProfileEntry 29 }

sonusOverloadProfileCDRSetThreshold OBJECT-TYPE
    SYNTAX          INTEGER (0..100)
    ACCESS          read-write
    STATUS          mandatory
    DESCRIPTION     
            "Identifies the CDR spooler utilization percentage threshold at which a congestion level may be set."
    DEFVAL          { 90 }
    ::= { sonusOverloadProfileEntry 30 }

sonusOverloadProfileCDRClearThreshold OBJECT-TYPE
    SYNTAX          INTEGER (0..100)
    ACCESS          read-write
    STATUS          mandatory
    DESCRIPTION     
            "Identifies the CDR spooler utilization percentage threshold at which a congestion level may be cleared."
    DEFVAL          { 85 }
    ::= { sonusOverloadProfileEntry 31 }

sonusOverloadProfileCDRSetDuration OBJECT-TYPE
    SYNTAX          INTEGER (0..65535)
    ACCESS          read-write
    STATUS          mandatory
    DESCRIPTION     
            "the length of time(in seconds) that the CDR spooler utilization must be above its set threshold
             before the congestion level is set. 0 sets it immediately."
    DEFVAL          { 10 }
    ::= { sonusOverloadProfileEntry 32 }

sonusOverloadProfileCDRClearDuration OBJECT-TYPE
    SYNTAX          INTEGER (0..65535)
    ACCESS          read-write
    STATUS          mandatory
    DESCRIPTION     
            "the length of time(in seconds) that the CDR spooler utilization must be below its clear threshold
             before the congestion level is cleared. 0 clears it immediately."
    DEFVAL          { 10 }
    ::= { sonusOverloadProfileEntry 33 }

sonusOverloadProfileAcceptNoCallsOnCDRCongestion OBJECT-TYPE
    SYNTAX          SonusAdminState
    ACCESS          read-write
    STATUS          mandatory
    DESCRIPTION     
            "enables or disables acceptance of calls in this congestion level if CDR generation is congested."
    DEFVAL          { disabled }
    ::= { sonusOverloadProfileEntry 34 }

sonusSysCongestionAdmnTable OBJECT-TYPE
    SYNTAX          SEQUENCE OF SonusSysCongestionAdmnEntry
    ACCESS          not-accessible
    STATUS          mandatory
    DESCRIPTION     
            ""
    ::= { sonusOverloadObjects 2 }

sonusSysCongestionAdmnEntry OBJECT-TYPE
    SYNTAX          SonusSysCongestionAdmnEntry
    ACCESS          not-accessible
    STATUS          mandatory
    DESCRIPTION     
            ""
    INDEX           { sonusSysCongestionShelfIndex }
    ::= { sonusSysCongestionAdmnTable 1 }

SonusSysCongestionAdmnEntry ::=
    SEQUENCE {
        sonusSysCongestionShelfIndex    SonusShelfIndex,
        sonusSysCongestionMC1Mode       INTEGER,
        sonusSysCongestionMC2Mode       INTEGER,
        sonusSysCongestionMC3Mode       INTEGER,
        sonusSysCongestionMC1OverloadProfileName        SonusNameReference,
        sonusSysCongestionMC2OverloadProfileName        SonusNameReference,
        sonusSysCongestionMC3OverloadProfileName        SonusNameReference,
        sonusSysCongestionRowStatus     RowStatus,
        sonusSysCongestionAdaptiveMCLevel INTEGER,
        sonusSysCongestionAdaptiveOGF   INTEGER,
        sonusSysCongestionRSI           INTEGER,
        sonusSysCongestionResAF         INTEGER,
        sonusSysCongestionPolicerState  INTEGER,
        sonusSysCongestionPolicerBucketSize   INTEGER,
        sonusSysCongestionPolicerNonpriorityCallThreshold                 INTEGER,
        sonusSysCongestionServerAdaptiveState     INTEGER,
        sonusSysCongestionPolicerRegistrationThreshold              INTEGER,
        sonusSysCongestionIcmOverloadAccptPercnt        INTEGER,
        sonusSysCongestionIcmOverloadState  INTEGER
    }

sonusSysCongestionShelfIndex OBJECT-TYPE
    SYNTAX          SonusShelfIndex
    ACCESS          read-write
    STATUS          mandatory
    DESCRIPTION     
            "Identifies the target system congestion admin entry."
    ::= { sonusSysCongestionAdmnEntry 1 }

sonusSysCongestionMC1Mode OBJECT-TYPE
    SYNTAX          INTEGER { outOfService(1), inService(2) }
    ACCESS          read-write
    STATUS          mandatory
    DESCRIPTION     
            "maintenance mode for MC1."
    DEFVAL          { outOfService }
    ::= { sonusSysCongestionAdmnEntry 2 }

sonusSysCongestionMC2Mode OBJECT-TYPE
    SYNTAX          INTEGER { outOfService(1), inService(2) }
    ACCESS          read-write
    STATUS          mandatory
    DESCRIPTION     
            "maintenance mode for MC2."
    DEFVAL          { outOfService }
    ::= { sonusSysCongestionAdmnEntry 3 }

sonusSysCongestionMC3Mode OBJECT-TYPE
    SYNTAX          INTEGER { outOfService(1), inService(2) }
    ACCESS          read-write
    STATUS          mandatory
    DESCRIPTION     
            "maintenance mode for MC3."
    DEFVAL          { outOfService }
    ::= { sonusSysCongestionAdmnEntry 4 }

sonusSysCongestionMC1OverloadProfileName OBJECT-TYPE
    SYNTAX          SonusNameReference
    ACCESS          read-write
    STATUS          mandatory
    DESCRIPTION     
            "the overload profile for MC1."
    ::= { sonusSysCongestionAdmnEntry 5 }

sonusSysCongestionMC2OverloadProfileName OBJECT-TYPE
    SYNTAX          SonusNameReference
    ACCESS          read-write
    STATUS          mandatory
    DESCRIPTION     
            "the overload profile for MC2."
    ::= { sonusSysCongestionAdmnEntry 6 }

sonusSysCongestionMC3OverloadProfileName OBJECT-TYPE
    SYNTAX          SonusNameReference
    ACCESS          read-write
    STATUS          mandatory
    DESCRIPTION     
            "the overload profile for MC3."
    ::= { sonusSysCongestionAdmnEntry 7 }

sonusSysCongestionRowStatus OBJECT-TYPE
    SYNTAX          RowStatus
    ACCESS          read-write
    STATUS          mandatory
    DESCRIPTION     
            ""
    ::= { sonusSysCongestionAdmnEntry 8 }

sonusSysCongestionAdaptiveMCLevel OBJECT-TYPE
    SYNTAX          INTEGER { mc0(0), mc1(1), mc2(2), mc3(3) }
    ACCESS          read-write
    STATUS          mandatory
    DESCRIPTION     
            "Machine congestion level to activate adaptive overload algorithm"
    DEFVAL          { mc2 }
    ::= { sonusSysCongestionAdmnEntry 9 }

sonusSysCongestionAdaptiveOGF OBJECT-TYPE
    SYNTAX          INTEGER (1..10)
    ACCESS          read-write
    STATUS          mandatory
    DESCRIPTION     
            "Adaptive overload algorithm gain factor"
    DEFVAL          { 3 }
    ::= { sonusSysCongestionAdmnEntry 10 }

sonusSysCongestionRSI OBJECT-TYPE
    SYNTAX          INTEGER (1..30)
    ACCESS          read-write
    STATUS          mandatory
    DESCRIPTION     
            "Re-sample interval"
    DEFVAL          { 3 }
    ::= { sonusSysCongestionAdmnEntry 11 }

sonusSysCongestionResAF OBJECT-TYPE
    SYNTAX          INTEGER (0..100)
    ACCESS          read-write
    STATUS          mandatory
    DESCRIPTION     
            "Resource average factor"
    DEFVAL          { 30 }
    ::= { sonusSysCongestionAdmnEntry 12 }

sonusSysCongestionPolicerState OBJECT-TYPE
    SYNTAX          INTEGER { disabled(1), enabled(2) }
    ACCESS          read-write
    STATUS          mandatory
    DESCRIPTION     
            "Administrative state of the system congestion call rate policer."
    DEFVAL          { disabled }
    ::= { sonusSysCongestionAdmnEntry 13 }

sonusSysCongestionPolicerBucketSize OBJECT-TYPE
    SYNTAX          INTEGER (5..100)
    ACCESS          read-write
    STATUS          mandatory
    DESCRIPTION     
            "Maximum number of credits in the system congestion policer bucket.
             This controls call burst handling capability during system congestion."
    DEFVAL          { 50 }
    ::= { sonusSysCongestionAdmnEntry 14 }

sonusSysCongestionPolicerNonpriorityCallThreshold OBJECT-TYPE
    SYNTAX          INTEGER (0..20)
    ACCESS          read-write
    STATUS          mandatory
    DESCRIPTION     
            "Number of credits in the system congestion policer bucket above which
             non-priority (i.e. not Emergency or HPC) calls are allowed."
    DEFVAL          { 0 }
    ::= { sonusSysCongestionAdmnEntry 15 }

sonusSysCongestionServerAdaptiveState OBJECT-TYPE
    SYNTAX          INTEGER { disabled(1), enabled(2) }
    ACCESS          read-write
    STATUS          mandatory
    DESCRIPTION     
            "Administrative state of the server adaptive congestion controls for
             all non-management server modules."
    DEFVAL          { disabled }
    ::= { sonusSysCongestionAdmnEntry 16 }

sonusSysCongestionPolicerRegistrationThreshold OBJECT-TYPE
    SYNTAX          INTEGER (0..20)
    ACCESS          read-write
    STATUS          mandatory
    DESCRIPTION     
            "Number of credits in the system congestion policer bucket above
             which SIP registrations are allowed."
    DEFVAL          { 0 }
    ::= { sonusSysCongestionAdmnEntry 17 }

sonusSysCongestionIcmOverloadAccptPercnt OBJECT-TYPE
    SYNTAX          INTEGER (0..100)
    ACCESS          read-write
    STATUS          mandatory
    DESCRIPTION     
            "Percentage of calls to be allowed during PNS congestion."
    DEFVAL          { 90 }
    ::= { sonusSysCongestionAdmnEntry 18 }

sonusSysCongestionIcmOverloadState OBJECT-TYPE
    SYNTAX          INTEGER { disabled(1), enabled(2) }
    ACCESS          read-write
    STATUS          mandatory
    DESCRIPTION     
            "Icm overload state controls the PNS 40 overload control for GSX deployed as PSTN-GW."
    DEFVAL          { disabled }
    ::= { sonusSysCongestionAdmnEntry 19 }

sonusServerCongestionAdmnTable OBJECT-TYPE
    SYNTAX          SEQUENCE OF SonusServerCongestionAdmnEntry
    ACCESS          not-accessible
    STATUS          mandatory
    DESCRIPTION     
            ""
    ::= { sonusOverloadObjects 3 }

sonusServerCongestionAdmnEntry OBJECT-TYPE
    SYNTAX          SonusServerCongestionAdmnEntry
    ACCESS          not-accessible
    STATUS          mandatory
    DESCRIPTION     
            ""
    INDEX           { sonusServerCongestionShelfId, 
                      sonusServerCongestionSlotId }
    ::= { sonusServerCongestionAdmnTable 1 }

SonusServerCongestionAdmnEntry ::=
    SEQUENCE {
        sonusServerCongestionShelfId    SonusShelfIndex,
        sonusServerCongestionSlotId     SonusSlotIndex,
        sonusServerCongestionMode       INTEGER,
        sonusServerCongestionOverloadProfileName        SonusNameReference,
        sonusServerCongestionRowStatus  RowStatus,
        sonusServerCongestionRSI        INTEGER,
        sonusServerCongestionResAF      INTEGER,
        sonusServerCongestionAdaptiveSDF INTEGER,
        sonusServerCongestionAdaptiveSUF INTEGER,
        sonusServerCongestionPolicerBucketSize      INTEGER,
        sonusServerCongestionPolicerNonpriorityCallThreshold                    INTEGER,
        sonusServerCongestionPolicerRegistrationThreshold                 INTEGER
    }

sonusServerCongestionShelfId OBJECT-TYPE
    SYNTAX          SonusShelfIndex
    ACCESS          read-write
    STATUS          mandatory
    DESCRIPTION     
            "shelf index of the server."
    ::= { sonusServerCongestionAdmnEntry 1 }

sonusServerCongestionSlotId OBJECT-TYPE
    SYNTAX          SonusSlotIndex
    ACCESS          read-write
    STATUS          mandatory
    DESCRIPTION     
            "logical slot ID of the server."
    ::= { sonusServerCongestionAdmnEntry 2 }

sonusServerCongestionMode OBJECT-TYPE
    SYNTAX          INTEGER { outOfService(1), inService(2) }
    ACCESS          read-write
    STATUS          mandatory
    DESCRIPTION     
            "maintenance mode for the server."
    DEFVAL          { outOfService }
    ::= { sonusServerCongestionAdmnEntry 3 }

sonusServerCongestionOverloadProfileName OBJECT-TYPE
    SYNTAX          SonusNameReference
    ACCESS          read-write
    STATUS          mandatory
    DESCRIPTION     
            "the overload profile for the server."
    ::= { sonusServerCongestionAdmnEntry 4 }

sonusServerCongestionRowStatus OBJECT-TYPE
    SYNTAX          RowStatus
    ACCESS          read-write
    STATUS          mandatory
    DESCRIPTION     
            ""
    ::= { sonusServerCongestionAdmnEntry 5 }

sonusServerCongestionRSI OBJECT-TYPE
    SYNTAX          INTEGER (1..30)
    ACCESS          read-write
    STATUS          mandatory
    DESCRIPTION     
            "Re-sample interval"
    DEFVAL          { 1 }
    ::= { sonusServerCongestionAdmnEntry 6 }

sonusServerCongestionResAF OBJECT-TYPE
    SYNTAX          INTEGER (0..100)
    ACCESS          read-write
    STATUS          mandatory
    DESCRIPTION     
            "Resource average factor"
    DEFVAL          { 30 }
    ::= { sonusServerCongestionAdmnEntry 7 }

sonusServerCongestionAdaptiveSDF OBJECT-TYPE
    SYNTAX          INTEGER (1..99)
    ACCESS          read-write
    STATUS          mandatory
    DESCRIPTION     
            "Adaptive server congestion step-down factor - percentage of call
             rate for each step down when server is in congestion."
    DEFVAL          { 10 }
    ::= { sonusServerCongestionAdmnEntry 8 }

sonusServerCongestionAdaptiveSUF OBJECT-TYPE
    SYNTAX          INTEGER (1..99)
    ACCESS          read-write
    STATUS          mandatory
    DESCRIPTION     
            "Adaptive server congestion step-up factor - percentage of call
             rate for each step up when server comes out of congestion."
    DEFVAL          { 10 }
    ::= { sonusServerCongestionAdmnEntry 9 }

sonusServerCongestionPolicerBucketSize OBJECT-TYPE
    SYNTAX          INTEGER (5..100)
    ACCESS          read-write
    STATUS          mandatory
    DESCRIPTION     
            "Maximum number of credits in the server congestion policer bucket.
             This controls call burst handling capability during server congestion."
    DEFVAL          { 20 }
    ::= { sonusServerCongestionAdmnEntry 10 }

sonusServerCongestionPolicerNonpriorityCallThreshold OBJECT-TYPE
    SYNTAX          INTEGER (0..20)
    ACCESS          read-write
    STATUS          mandatory
    DESCRIPTION     
            "Number of credits in the server congestion policer bucket above which
             non-priority (i.e. not Emergency or HPC) calls are allowed."
    DEFVAL          { 0 }
    ::= { sonusServerCongestionAdmnEntry 11 }

sonusServerCongestionPolicerRegistrationThreshold OBJECT-TYPE
    SYNTAX          INTEGER (0..20)
    ACCESS          read-write
    STATUS          mandatory
    DESCRIPTION     
            "Number of credits in the server congestion policer bucket above
             which SIP registrations are allowed."
    DEFVAL          { 0 }
    ::= { sonusServerCongestionAdmnEntry 12 }

sonusSysCongestionStatTable OBJECT-TYPE
    SYNTAX          SEQUENCE OF SonusSysCongestionStatEntry
    ACCESS          not-accessible
    STATUS          mandatory
    DESCRIPTION     
            ""
    ::= { sonusOverloadObjects 4 }

sonusSysCongestionStatEntry OBJECT-TYPE
    SYNTAX          SonusSysCongestionStatEntry
    ACCESS          not-accessible
    STATUS          mandatory
    DESCRIPTION     
            ""
    INDEX           { sonusSysCongestionStatShelfIndex }
    ::= { sonusSysCongestionStatTable 1 }

SonusSysCongestionStatEntry ::=
    SEQUENCE {
        sonusSysCongestionStatShelfIndex SonusShelfIndex,
        sonusSysCongestionMCLevel       Gauge,
        sonusSysCongestionCPULevel      Gauge,
        sonusSysCongestionMemLevel      Gauge,
        sonusSysCongestionPsxLevel      Gauge,
        sonusSysCongestionCallRateLevel Gauge,
        sonusSysCongestionMCDuration    Counter,
        sonusSysCongestionCallArrivalRate Gauge,
        sonusSysCongestionLogLevel      Gauge,
        sonusSysCongestionCallAcceptRate Gauge,
        sonusSysCongestionCallAcceptCount Gauge,
        sonusSysCongestionICMLevel      Gauge,
        sonusSysCongestionRegArrivalRate Gauge,
        sonusSysCongestionCallEqArrivalRate   Gauge,
        sonusSysCongestionCDRLevel      Gauge
    }

sonusSysCongestionStatShelfIndex OBJECT-TYPE
    SYNTAX          SonusShelfIndex
    ACCESS          read-only
    STATUS          mandatory
    DESCRIPTION     
            "Shelf Index of the system."
    ::= { sonusSysCongestionStatEntry 1 }

sonusSysCongestionMCLevel OBJECT-TYPE
    SYNTAX          Gauge
    ACCESS          read-only
    STATUS          mandatory
    DESCRIPTION     
            "System congestion level."
    ::= { sonusSysCongestionStatEntry 2 }

sonusSysCongestionCPULevel OBJECT-TYPE
    SYNTAX          Gauge
    ACCESS          read-only
    STATUS          mandatory
    DESCRIPTION     
            "CPU congestion level."
    ::= { sonusSysCongestionStatEntry 3 }

sonusSysCongestionMemLevel OBJECT-TYPE
    SYNTAX          Gauge
    ACCESS          read-only
    STATUS          mandatory
    DESCRIPTION     
            "Memory congestion level."
    ::= { sonusSysCongestionStatEntry 4 }

sonusSysCongestionPsxLevel OBJECT-TYPE
    SYNTAX          Gauge
    ACCESS          read-only
    STATUS          mandatory
    DESCRIPTION     
            "PSX congestion level."
    ::= { sonusSysCongestionStatEntry 5 }

sonusSysCongestionCallRateLevel OBJECT-TYPE
    SYNTAX          Gauge
    ACCESS          read-only
    STATUS          mandatory
    DESCRIPTION     
            "Call rate congestion level."
    ::= { sonusSysCongestionStatEntry 6 }

sonusSysCongestionMCDuration OBJECT-TYPE
    SYNTAX          Counter
    ACCESS          read-only
    STATUS          mandatory
    DESCRIPTION     
            "Number of seconds the system has been at this congestion level."
    ::= { sonusSysCongestionStatEntry 7 }

sonusSysCongestionCallArrivalRate OBJECT-TYPE
    SYNTAX          Gauge
    ACCESS          read-only
    STATUS          mandatory
    DESCRIPTION     
            "Current system call arrival rate."
    ::= { sonusSysCongestionStatEntry 8 }

sonusSysCongestionLogLevel OBJECT-TYPE
    SYNTAX          Gauge
    ACCESS          read-only
    STATUS          mandatory
    DESCRIPTION     
            "Log spooler congestion level."
    ::= { sonusSysCongestionStatEntry 9 }

sonusSysCongestionCallAcceptRate OBJECT-TYPE
    SYNTAX          Gauge
    ACCESS          read-only
    STATUS          mandatory
    DESCRIPTION     
            "Current rate at which calls are being accepted by the system."
    ::= { sonusSysCongestionStatEntry 10 }

sonusSysCongestionCallAcceptCount OBJECT-TYPE
    SYNTAX          Gauge
    ACCESS          read-only
    STATUS          mandatory
    DESCRIPTION     
            "Current number of calls being accepted by the system in cps."
    ::= { sonusSysCongestionStatEntry 11 }

sonusSysCongestionICMLevel OBJECT-TYPE
    SYNTAX          Gauge
    ACCESS          read-only
    STATUS          mandatory
    DESCRIPTION     
            "ICM congestion level."
    ::= { sonusSysCongestionStatEntry 12 }

sonusSysCongestionRegArrivalRate OBJECT-TYPE
    SYNTAX          Gauge
    ACCESS          read-only
    STATUS          mandatory
    DESCRIPTION     
            "Current system SIP registration arrival rate."
    ::= { sonusSysCongestionStatEntry 13 }

sonusSysCongestionCallEqArrivalRate OBJECT-TYPE
    SYNTAX          Gauge
    ACCESS          read-only
    STATUS          mandatory
    DESCRIPTION     
            "Current system call equivalence (real call + registration) arrival rate."
    ::= { sonusSysCongestionStatEntry 14 }

sonusSysCongestionCDRLevel OBJECT-TYPE
    SYNTAX          Gauge
    ACCESS          read-only
    STATUS          mandatory
    DESCRIPTION     
            "CDR spooler congestion level."
    ::= { sonusSysCongestionStatEntry 15 }

sonusServerCongestionStatTable OBJECT-TYPE
    SYNTAX          SEQUENCE OF SonusServerCongestionStatEntry
    ACCESS          not-accessible
    STATUS          mandatory
    DESCRIPTION     
            ""
    ::= { sonusOverloadObjects 5 }

sonusServerCongestionStatEntry OBJECT-TYPE
    SYNTAX          SonusServerCongestionStatEntry
    ACCESS          not-accessible
    STATUS          mandatory
    DESCRIPTION     
            ""
    INDEX           { sonusServerCongestionShelfIndex, 
                      sonusServerCongestionSlotIndex }
    ::= { sonusServerCongestionStatTable 1 }

SonusServerCongestionStatEntry ::=
    SEQUENCE {
        sonusServerCongestionShelfIndex SonusShelfIndex,
        sonusServerCongestionSlotIndex  SonusSlotIndex,
        sonusServerCongestionCardLevel  Gauge,
        sonusServerCongestionCPULevel   Gauge,
        sonusServerCongestionMemLevel   Gauge,
        sonusServerCongestionCallRateLevel  Gauge,
        sonusServerCongestionDuration   Counter,
        sonusServerCongestionCallArrivalRate    Gauge,
        sonusServerCongestionCallAcceptRate   Gauge,
        sonusServerCongestionCallAcceptCount    Gauge,
        sonusServerCongestionICMLevel   Gauge,
        sonusServerCongestionRegArrivalRate   Gauge,
        sonusServerCongestionCallEqArrivalRate      Gauge
    }

sonusServerCongestionShelfIndex OBJECT-TYPE
    SYNTAX          SonusShelfIndex
    ACCESS          read-only
    STATUS          mandatory
    DESCRIPTION     
            "Shelf index of the server."
    ::= { sonusServerCongestionStatEntry 1 }

sonusServerCongestionSlotIndex OBJECT-TYPE
    SYNTAX          SonusSlotIndex
    ACCESS          read-only
    STATUS          mandatory
    DESCRIPTION     
            "Slot index of the server."
    ::= { sonusServerCongestionStatEntry 2 }

sonusServerCongestionCardLevel OBJECT-TYPE
    SYNTAX          Gauge
    ACCESS          read-only
    STATUS          mandatory
    DESCRIPTION     
            "per server congestion level."
    ::= { sonusServerCongestionStatEntry 3 }

sonusServerCongestionCPULevel OBJECT-TYPE
    SYNTAX          Gauge
    ACCESS          read-only
    STATUS          mandatory
    DESCRIPTION     
            "per server CPU congestion level."
    ::= { sonusServerCongestionStatEntry 4 }

sonusServerCongestionMemLevel OBJECT-TYPE
    SYNTAX          Gauge
    ACCESS          read-only
    STATUS          mandatory
    DESCRIPTION     
            "per server memory congestion level."
    ::= { sonusServerCongestionStatEntry 5 }

sonusServerCongestionCallRateLevel OBJECT-TYPE
    SYNTAX          Gauge
    ACCESS          read-only
    STATUS          mandatory
    DESCRIPTION     
            "per server call rate congestion level."
    ::= { sonusServerCongestionStatEntry 6 }

sonusServerCongestionDuration OBJECT-TYPE
    SYNTAX          Counter
    ACCESS          read-only
    STATUS          mandatory
    DESCRIPTION     
            "per server number of seconds the server has been at this congestion level."
    ::= { sonusServerCongestionStatEntry 7 }

sonusServerCongestionCallArrivalRate OBJECT-TYPE
    SYNTAX          Gauge
    ACCESS          read-only
    STATUS          mandatory
    DESCRIPTION     
            "per server current call arrival rate."
    ::= { sonusServerCongestionStatEntry 8 }

sonusServerCongestionCallAcceptRate OBJECT-TYPE
    SYNTAX          Gauge
    ACCESS          read-only
    STATUS          mandatory
    DESCRIPTION     
            "Current rate at which calls are being accepted by the server."
    ::= { sonusServerCongestionStatEntry 9 }

sonusServerCongestionCallAcceptCount OBJECT-TYPE
    SYNTAX          Gauge
    ACCESS          read-only
    STATUS          mandatory
    DESCRIPTION     
            "Current number of calls being accepted by the server in cps."
    ::= { sonusServerCongestionStatEntry 10 }

sonusServerCongestionICMLevel OBJECT-TYPE
    SYNTAX          Gauge
    ACCESS          read-only
    STATUS          mandatory
    DESCRIPTION     
            "per server ICM congestion level."
    ::= { sonusServerCongestionStatEntry 11 }

sonusServerCongestionRegArrivalRate OBJECT-TYPE
    SYNTAX          Gauge
    ACCESS          read-only
    STATUS          mandatory
    DESCRIPTION     
            "per server current SIP registration arrival rate."
    ::= { sonusServerCongestionStatEntry 12 }

sonusServerCongestionCallEqArrivalRate OBJECT-TYPE
    SYNTAX          Gauge
    ACCESS          read-only
    STATUS          mandatory
    DESCRIPTION     
            "per server current call equivalence (real call + registration) arrival rate."
    ::= { sonusServerCongestionStatEntry 13 }

sonusDtmfTrigger OBJECT IDENTIFIER
    ::= { sonusNodeResourcesMIBObjects 21 }

sonusDtmfTriggerNextIndex OBJECT-TYPE
    SYNTAX          INTEGER
    ACCESS          read-only
    STATUS          mandatory
    DESCRIPTION     
            "The next valid index to use when creating an entry in
             the sonusDtmfTriggerTable."
    ::= { sonusDtmfTrigger 1 }

sonusDtmfTriggerTable OBJECT-TYPE
    SYNTAX          SEQUENCE OF SonusDtmfTriggerEntry
    ACCESS          not-accessible
    STATUS          mandatory
    DESCRIPTION     
            "This table contains dtmf triggers for the node."
    ::= { sonusDtmfTrigger 2 }

sonusDtmfTriggerEntry OBJECT-TYPE
    SYNTAX          SonusDtmfTriggerEntry
    ACCESS          not-accessible
    STATUS          mandatory
    DESCRIPTION     
            ""
    INDEX           { sonusDtmfTriggerIndex }
    ::= { sonusDtmfTriggerTable 1 }

SonusDtmfTriggerEntry ::=
    SEQUENCE {
        sonusDtmfTriggerIndex           INTEGER,
        sonusDtmfTriggerAdmnState       SonusAdminState,
        sonusDtmfTriggerName            SonusName,
        sonusDtmfTriggerPattern         DisplayString,
        sonusDtmfTriggerInterdigitTimeout INTEGER,
        sonusDtmfTriggerLongdigitDuration INTEGER,
        sonusDtmfTriggerRowStatus       RowStatus
    }

sonusDtmfTriggerIndex OBJECT-TYPE
    SYNTAX          INTEGER
    ACCESS          read-only
    STATUS          mandatory
    DESCRIPTION     
            "Identifies the dtmf trigger entry."
    ::= { sonusDtmfTriggerEntry 1 }

sonusDtmfTriggerAdmnState OBJECT-TYPE
    SYNTAX          SonusAdminState
    ACCESS          read-write
    STATUS          mandatory
    DESCRIPTION     
            "The administrative state of this dtmf trigger."
    DEFVAL          { disabled }
    ::= { sonusDtmfTriggerEntry 2 }

sonusDtmfTriggerName OBJECT-TYPE
    SYNTAX          SonusName
    ACCESS          read-write
    STATUS          mandatory
    DESCRIPTION     
            "The user name of this dtmf trigger."
    ::= { sonusDtmfTriggerEntry 3 }

sonusDtmfTriggerPattern OBJECT-TYPE
    SYNTAX          DisplayString (SIZE(0..30))
    ACCESS          read-write
    STATUS          mandatory
    DESCRIPTION     
            "The trigger pattern."
    ::= { sonusDtmfTriggerEntry 4 }

sonusDtmfTriggerInterdigitTimeout OBJECT-TYPE
    SYNTAX          INTEGER (0..65535)
    ACCESS          read-write
    STATUS          mandatory
    DESCRIPTION     
            "Specifies interdigit timer in milliseconds. 
             If 0, then timer is disabled"
    DEFVAL          { 4000 }
    ::= { sonusDtmfTriggerEntry 5 }

sonusDtmfTriggerLongdigitDuration OBJECT-TYPE
    SYNTAX          INTEGER (0..65535)
    ACCESS          read-write
    STATUS          mandatory
    DESCRIPTION     
            "Specifies minimum duration in milliseconds for 
             a digit to be considered long. If 0, then long
             digits are disabled"
    DEFVAL          { 2000 }
    ::= { sonusDtmfTriggerEntry 6 }

sonusDtmfTriggerRowStatus OBJECT-TYPE
    SYNTAX          RowStatus
    ACCESS          read-write
    STATUS          mandatory
    DESCRIPTION     
            ""
    ::= { sonusDtmfTriggerEntry 7 }

sonusAnnounceObjects OBJECT IDENTIFIER
    ::= { sonusNodeResourcesMIBObjects 22 }

sonusAnnouncePackage OBJECT IDENTIFIER
    ::= { sonusAnnounceObjects 1 }

sonusAnnouncePackageNextIndex OBJECT-TYPE
    SYNTAX          INTEGER
    ACCESS          read-only
    STATUS          mandatory
    DESCRIPTION     
            "The next valid index to use when creating an entry in
             the sonusAnnouncePackageTable."
    ::= { sonusAnnouncePackage 1 }

sonusAnnouncePackageTable OBJECT-TYPE
    SYNTAX          SEQUENCE OF SonusAnnouncePackageEntry
    ACCESS          not-accessible
    STATUS          mandatory
    DESCRIPTION     
            "This table contains announcement packages for the node."
    ::= { sonusAnnouncePackage 2 }

sonusAnnouncePackageEntry OBJECT-TYPE
    SYNTAX          SonusAnnouncePackageEntry
    ACCESS          not-accessible
    STATUS          mandatory
    DESCRIPTION     
            ""
    INDEX           { sonusAnnouncePackageIndex }
    ::= { sonusAnnouncePackageTable 1 }

SonusAnnouncePackageEntry ::=
    SEQUENCE {
        sonusAnnouncePackageIndex       INTEGER,
        sonusAnnouncePackageName        SonusName,
        sonusAnnouncePackageId          INTEGER,
        sonusAnnouncePackageRowStatus   RowStatus
    }

sonusAnnouncePackageIndex OBJECT-TYPE
    SYNTAX          INTEGER
    ACCESS          read-only
    STATUS          mandatory
    DESCRIPTION     
            "Identifies the announcement package."
    ::= { sonusAnnouncePackageEntry 1 }

sonusAnnouncePackageName OBJECT-TYPE
    SYNTAX          SonusName
    ACCESS          read-write
    STATUS          mandatory
    DESCRIPTION     
            "The name of this announcement package."
    ::= { sonusAnnouncePackageEntry 2 }

sonusAnnouncePackageId OBJECT-TYPE
    SYNTAX          INTEGER (0..65535)
    ACCESS          read-write
    STATUS          mandatory
    DESCRIPTION     
            "The announcement package identifier defined by the 
             Sonus Softswitch for this package."
    ::= { sonusAnnouncePackageEntry 3 }

sonusAnnouncePackageRowStatus OBJECT-TYPE
    SYNTAX          RowStatus
    ACCESS          read-write
    STATUS          mandatory
    DESCRIPTION     
            ""
    ::= { sonusAnnouncePackageEntry 4 }

sonusAnnouncePkgElem OBJECT IDENTIFIER
    ::= { sonusAnnounceObjects 2 }

sonusAnnouncePkgElemTable OBJECT-TYPE
    SYNTAX          SEQUENCE OF SonusAnnouncePkgElemEntry
    ACCESS          not-accessible
    STATUS          mandatory
    DESCRIPTION     
            "This table contains elements which bind announcement names
             to segment ID values for a given announcement package."
    ::= { sonusAnnouncePkgElem 1 }

sonusAnnouncePkgElemEntry OBJECT-TYPE
    SYNTAX          SonusAnnouncePkgElemEntry
    ACCESS          not-accessible
    STATUS          mandatory
    DESCRIPTION     
            ""
    INDEX           { sonusAnnouncePkgElemIndex }
    ::= { sonusAnnouncePkgElemTable 1 }

SonusAnnouncePkgElemEntry ::=
    SEQUENCE {
        sonusAnnouncePkgElemIndex       INTEGER,
        sonusAnnouncePkgElemAnnouncePackageRef      SonusNameReference,
        sonusAnnouncePkgElemAnnounceNameRef   SonusName,
        sonusAnnouncePkgElemAnnounceSegmentId     INTEGER,
        sonusAnnouncePkgElemRowStatus   RowStatus
    }

sonusAnnouncePkgElemIndex OBJECT-TYPE
    SYNTAX          INTEGER
    ACCESS          read-only
    STATUS          mandatory
    DESCRIPTION     
            "Identifies the target announcement package element."
    ::= { sonusAnnouncePkgElemEntry 1 }

sonusAnnouncePkgElemAnnouncePackageRef OBJECT-TYPE
    SYNTAX          SonusNameReference
    ACCESS          read-write
    STATUS          mandatory
    DESCRIPTION     
            "Identifies the announcement package for this element."
    ::= { sonusAnnouncePkgElemEntry 2 }

sonusAnnouncePkgElemAnnounceNameRef OBJECT-TYPE
    SYNTAX          SonusName
    ACCESS          read-write
    STATUS          mandatory
    DESCRIPTION     
            "Identifies the announcement name for this element."
    ::= { sonusAnnouncePkgElemEntry 3 }

sonusAnnouncePkgElemAnnounceSegmentId OBJECT-TYPE
    SYNTAX          INTEGER (0..65535)
    ACCESS          read-write
    STATUS          mandatory
    DESCRIPTION     
            "The Segment ID for the announcement segment file that this
             announcement name is mapped to for this announcement package.
             Starting in V07.00.00R000, 0 is no longer a valid value."
    ::= { sonusAnnouncePkgElemEntry 4 }

sonusAnnouncePkgElemRowStatus OBJECT-TYPE
    SYNTAX          RowStatus
    ACCESS          read-write
    STATUS          mandatory
    DESCRIPTION     
            ""
    ::= { sonusAnnouncePkgElemEntry 5 }

sonusCallTraceGlobalConfigDataObjects OBJECT IDENTIFIER
    ::= { sonusNodeResourcesMIBObjects 23 }

sonusCallTraceErrorFilterType OBJECT-TYPE
    SYNTAX          INTEGER { none(0), any(1), parseerror(2), 
                        earlyattempt(3), outofdialog(4) }
    ACCESS          read-write
    STATUS          mandatory
    DESCRIPTION     
            "The error trace filter type"
    DEFVAL          { none }
    ::= { sonusCallTraceGlobalConfigDataObjects 1 }

sonusCallTraceTriggerCount OBJECT-TYPE
    SYNTAX          INTEGER (0..16)
    ACCESS          read-write
    STATUS          mandatory
    DESCRIPTION     
            "The trigger count for both call and error trace filters"
    DEFVAL          { 10 }
    ::= { sonusCallTraceGlobalConfigDataObjects 2 }

sonusCallTraceTimer OBJECT-TYPE
    SYNTAX          INTEGER (1..360)
    ACCESS          read-write
    STATUS          mandatory
    DESCRIPTION     
            "The timer value in minutes for both call and error filters, once the call trace timer expires call tracing will be stopped"
    DEFVAL          { 180 }
    ::= { sonusCallTraceGlobalConfigDataObjects 3 }

sonusMonitorEndpoint OBJECT IDENTIFIER
    ::= { sonusNodeResourcesMIBObjects 24 }

sonusMonitorEndpointNextIndex OBJECT-TYPE
    SYNTAX          INTEGER
    ACCESS          read-only
    STATUS          mandatory
    DESCRIPTION     
            "The next valid index to use when creating an entry in
             the sonusMonitorEndpointAdmnTable"
    ::= { sonusMonitorEndpoint 1 }

sonusMonitorEndpointAdmnTable OBJECT-TYPE
    SYNTAX          SEQUENCE OF SonusMonitorEndpointAdmnEntry
    ACCESS          not-accessible
    STATUS          mandatory
    DESCRIPTION     
            "This table specifies the monitor endpoint list for the node."
    ::= { sonusMonitorEndpoint 2 }

sonusMonitorEndpointAdmnEntry OBJECT-TYPE
    SYNTAX          SonusMonitorEndpointAdmnEntry
    ACCESS          not-accessible
    STATUS          mandatory
    DESCRIPTION     
            ""
    INDEX           { sonusMonitorEndpointAdmnIndex }
    ::= { sonusMonitorEndpointAdmnTable 1 }

SonusMonitorEndpointAdmnEntry ::=
    SEQUENCE {
        sonusMonitorEndpointAdmnIndex   INTEGER,
        sonusMonitorEndpointAdmnState   INTEGER,
        sonusMonitorEndpointAdmnName    SonusName,
        sonusMonitorEndpointAdmnEndpointTelNumber         DisplayString,
        sonusMonitorEndpointAdmnRowStatus RowStatus,
        sonusMonitorEndpointAdmnType    INTEGER,
        sonusMonitorEndpointAdmnRxShelf SonusShelfIndex,
        sonusMonitorEndpointAdmnRxSlot  SonusSlotIndex,
        sonusMonitorEndpointAdmnRxPort  INTEGER,
        sonusMonitorEndpointAdmnRxChannel INTEGER,
        sonusMonitorEndpointAdmnTxShelf SonusShelfIndex,
        sonusMonitorEndpointAdmnTxSlot  SonusSlotIndex,
        sonusMonitorEndpointAdmnTxPort  INTEGER,
        sonusMonitorEndpointAdmnTxChannel INTEGER,
        sonusMonitorEndpointAdmnEndpointNatureOfAddr            INTEGER,
        sonusMonitorEndpointAdmnEndpointNumberingPlan             INTEGER
    }

sonusMonitorEndpointAdmnIndex OBJECT-TYPE
    SYNTAX          INTEGER
    ACCESS          read-only
    STATUS          mandatory
    DESCRIPTION     
            "Identifies the target monitor endpoint entry."
    ::= { sonusMonitorEndpointAdmnEntry 1 }

sonusMonitorEndpointAdmnState OBJECT-TYPE
    SYNTAX          INTEGER { disabled(1), enabled(2) }
    ACCESS          read-write
    STATUS          mandatory
    DESCRIPTION     
            "The administrative state of this monitor endpoint entry."
    DEFVAL          { disabled }
    ::= { sonusMonitorEndpointAdmnEntry 2 }

sonusMonitorEndpointAdmnName OBJECT-TYPE
    SYNTAX          SonusName
    ACCESS          read-write
    STATUS          mandatory
    DESCRIPTION     
            "The endpoint name of this monitor endpoint."
    ::= { sonusMonitorEndpointAdmnEntry 3 }

sonusMonitorEndpointAdmnEndpointTelNumber OBJECT-TYPE
    SYNTAX          DisplayString (SIZE(0..30))
    ACCESS          read-write
    STATUS          mandatory
    DESCRIPTION     
            "The Telephone number for this monitor endpoint"
    ::= { sonusMonitorEndpointAdmnEntry 4 }

sonusMonitorEndpointAdmnRowStatus OBJECT-TYPE
    SYNTAX          RowStatus
    ACCESS          read-write
    STATUS          mandatory
    DESCRIPTION     
            ""
    ::= { sonusMonitorEndpointAdmnEntry 5 }

sonusMonitorEndpointAdmnType OBJECT-TYPE
    SYNTAX          INTEGER { signaledMixed(1), staticTap(2) }
    ACCESS          read-write
    STATUS          mandatory
    DESCRIPTION     
            "The monitor type. Default is signaledMixed"
    DEFVAL          { signaledMixed }
    ::= { sonusMonitorEndpointAdmnEntry 6 }

sonusMonitorEndpointAdmnRxShelf OBJECT-TYPE
    SYNTAX          SonusShelfIndex
    ACCESS          read-write
    STATUS          mandatory
    DESCRIPTION     
            "A 32-bit integer identifying the shelf thats hosts the DS0 that streams the Rx data"
    ::= { sonusMonitorEndpointAdmnEntry 7 }

sonusMonitorEndpointAdmnRxSlot OBJECT-TYPE
    SYNTAX          SonusSlotIndex
    ACCESS          read-write
    STATUS          mandatory
    DESCRIPTION     
            "A 32-bit integer identifying the slot thats hosts the DS0 that streams the Rx data"
    ::= { sonusMonitorEndpointAdmnEntry 8 }

sonusMonitorEndpointAdmnRxPort OBJECT-TYPE
    SYNTAX          INTEGER (1..65535)
    ACCESS          read-write
    STATUS          mandatory
    DESCRIPTION     
            "A 32-bit integer identifying the port thats hosts the DS0 that streams the Rx data"
    ::= { sonusMonitorEndpointAdmnEntry 9 }

sonusMonitorEndpointAdmnRxChannel OBJECT-TYPE
    SYNTAX          INTEGER (1..31)
    ACCESS          read-write
    STATUS          mandatory
    DESCRIPTION     
            "A 32-bit integer identifying the Channel (DS0) that streams the Rx data"
    ::= { sonusMonitorEndpointAdmnEntry 10 }

sonusMonitorEndpointAdmnTxShelf OBJECT-TYPE
    SYNTAX          SonusShelfIndex
    ACCESS          read-write
    STATUS          mandatory
    DESCRIPTION     
            "A 32-bit integer identifying the shelf thats hosts the DS0 that streams the Tx data"
    ::= { sonusMonitorEndpointAdmnEntry 11 }

sonusMonitorEndpointAdmnTxSlot OBJECT-TYPE
    SYNTAX          SonusSlotIndex
    ACCESS          read-write
    STATUS          mandatory
    DESCRIPTION     
            "A 32-bit integer identifying the slot thats hosts the DS0 that streams the Tx data"
    ::= { sonusMonitorEndpointAdmnEntry 12 }

sonusMonitorEndpointAdmnTxPort OBJECT-TYPE
    SYNTAX          INTEGER (1..65535)
    ACCESS          read-write
    STATUS          mandatory
    DESCRIPTION     
            "A 32-bit integer identifying the port thats hosts the DS0 that streams the Tx data"
    ::= { sonusMonitorEndpointAdmnEntry 13 }

sonusMonitorEndpointAdmnTxChannel OBJECT-TYPE
    SYNTAX          INTEGER (1..31)
    ACCESS          read-write
    STATUS          mandatory
    DESCRIPTION     
            "A 32-bit integer identifying the Channel (DS0) that streams the Tx data"
    ::= { sonusMonitorEndpointAdmnEntry 14 }

sonusMonitorEndpointAdmnEndpointNatureOfAddr OBJECT-TYPE
    SYNTAX          INTEGER { none(0), subscriber(1), national(2), 
                        international(3), subscriberOperator(4), 
                        nationalOperator(5), internationalOperator(6), 
                        testCode(7), noNumberOpRequested(8), 
                        noNumberCutThrough(9), na950(10), unknown(17), 
                        networkSpecific(19), ss7Reserved(20), 
                        apnNodal(23), sidNumber(24), 
                        partialCallingLineId(25) }
    ACCESS          read-write
    STATUS          mandatory
    DESCRIPTION     
            "The endpoint telephone number Nature of Address."
    DEFVAL          { national }
    ::= { sonusMonitorEndpointAdmnEntry 15 }

sonusMonitorEndpointAdmnEndpointNumberingPlan OBJECT-TYPE
    SYNTAX          INTEGER { none(0), isdn(1), data(2), telex(3), 
                        private(4), spare0(8), spare1(9), spare2(10), 
                        spare3(11), spare4(12), spare5(13), spare6(14), 
                        spare7(15) }
    ACCESS          read-write
    STATUS          mandatory
    DESCRIPTION     
            "The endpoint telephone number Numbering Plan."
    DEFVAL          { isdn }
    ::= { sonusMonitorEndpointAdmnEntry 16 }

sonusMonitorTarget OBJECT IDENTIFIER
    ::= { sonusNodeResourcesMIBObjects 25 }

sonusMonitorTargetNextIndex OBJECT-TYPE
    SYNTAX          INTEGER
    ACCESS          read-only
    STATUS          mandatory
    DESCRIPTION     
            "The next valid index to use when creating an entry in
             the sonusMonitorTargetAdmnTable"
    ::= { sonusMonitorTarget 1 }

sonusMonitorTargetAdmnTable OBJECT-TYPE
    SYNTAX          SEQUENCE OF SonusMonitorTargetAdmnEntry
    ACCESS          not-accessible
    STATUS          mandatory
    DESCRIPTION     
            "This table specifies the monitor target list for the node."
    ::= { sonusMonitorTarget 2 }

sonusMonitorTargetAdmnEntry OBJECT-TYPE
    SYNTAX          SonusMonitorTargetAdmnEntry
    ACCESS          not-accessible
    STATUS          mandatory
    DESCRIPTION     
            ""
    INDEX           { sonusMonitorTargetAdmnIndex }
    ::= { sonusMonitorTargetAdmnTable 1 }

SonusMonitorTargetAdmnEntry ::=
    SEQUENCE {
        sonusMonitorTargetAdmnIndex     INTEGER,
        sonusMonitorTargetAdmnName      SonusName,
        sonusMonitorTargetAdmnState     INTEGER,
        sonusMonitorTargetAdmnType      INTEGER,
        sonusMonitorTargetAdmnCallId    INTEGER,
        sonusMonitorTargetAdmnShelf     SonusShelfIndex,
        sonusMonitorTargetAdmnSlot      SonusSlotIndex,
        sonusMonitorTargetAdmnPort      INTEGER,
        sonusMonitorTargetAdmnChannel   INTEGER,
        sonusMonitorTargetAdmnServiceGroup  SonusNameReference,
        sonusMonitorTargetAdmnIsupCic   INTEGER,
        sonusMonitorTargetAdmnEndpointName  SonusNameReference,
        sonusMonitorTargetAdmnRowStatus RowStatus
    }

sonusMonitorTargetAdmnIndex OBJECT-TYPE
    SYNTAX          INTEGER
    ACCESS          read-only
    STATUS          mandatory
    DESCRIPTION     
            "Identifies the target monitor target entry."
    ::= { sonusMonitorTargetAdmnEntry 1 }

sonusMonitorTargetAdmnName OBJECT-TYPE
    SYNTAX          SonusName
    ACCESS          read-write
    STATUS          mandatory
    DESCRIPTION     
            "The target name of this monitor target."
    ::= { sonusMonitorTargetAdmnEntry 2 }

sonusMonitorTargetAdmnState OBJECT-TYPE
    SYNTAX          INTEGER { disabled(1), enabled(2) }
    ACCESS          read-write
    STATUS          mandatory
    DESCRIPTION     
            "The administrative state of this monitor target entry."
    DEFVAL          { disabled }
    ::= { sonusMonitorTargetAdmnEntry 3 }

sonusMonitorTargetAdmnType OBJECT-TYPE
    SYNTAX          INTEGER { gcid(1), channel(2), cic(3) }
    ACCESS          read-write
    STATUS          mandatory
    DESCRIPTION     
            "The target type gcid,shelf/slot/port/channel, or ISUP service group/CIC."
    DEFVAL          { gcid }
    ::= { sonusMonitorTargetAdmnEntry 4 }

sonusMonitorTargetAdmnCallId OBJECT-TYPE
    SYNTAX          INTEGER
    ACCESS          read-write
    STATUS          mandatory
    DESCRIPTION     
            "This is the Monitor Target call's GCID."
    ::= { sonusMonitorTargetAdmnEntry 5 }

sonusMonitorTargetAdmnShelf OBJECT-TYPE
    SYNTAX          SonusShelfIndex
    ACCESS          read-write
    STATUS          mandatory
    DESCRIPTION     
            "A 32-bit integer identifying the shelf of the monitor target"
    ::= { sonusMonitorTargetAdmnEntry 6 }

sonusMonitorTargetAdmnSlot OBJECT-TYPE
    SYNTAX          SonusSlotIndex
    ACCESS          read-write
    STATUS          mandatory
    DESCRIPTION     
            "An integer identifying the slot of the monitor target"
    ::= { sonusMonitorTargetAdmnEntry 7 }

sonusMonitorTargetAdmnPort OBJECT-TYPE
    SYNTAX          INTEGER (1..65535)
    ACCESS          read-write
    STATUS          mandatory
    DESCRIPTION     
            "An integer identifying the port of the monitor target"
    ::= { sonusMonitorTargetAdmnEntry 8 }

sonusMonitorTargetAdmnChannel OBJECT-TYPE
    SYNTAX          INTEGER (1..32)
    ACCESS          read-write
    STATUS          mandatory
    DESCRIPTION     
            "An integer identifying the logical channel of the monitor target"
    ::= { sonusMonitorTargetAdmnEntry 9 }

sonusMonitorTargetAdmnServiceGroup OBJECT-TYPE
    SYNTAX          SonusNameReference
    ACCESS          read-write
    STATUS          mandatory
    DESCRIPTION     
            "The Service Group associated with the monitor target"
    ::= { sonusMonitorTargetAdmnEntry 10 }

sonusMonitorTargetAdmnIsupCic OBJECT-TYPE
    SYNTAX          INTEGER (0..16383)
    ACCESS          read-write
    STATUS          mandatory
    DESCRIPTION     
            "The base cicuit identity code (CIC) for the monitor target"
    ::= { sonusMonitorTargetAdmnEntry 11 }

sonusMonitorTargetAdmnEndpointName OBJECT-TYPE
    SYNTAX          SonusNameReference
    ACCESS          read-write
    STATUS          mandatory
    DESCRIPTION     
            "The endpoint name used to monitor target."
    ::= { sonusMonitorTargetAdmnEntry 12 }

sonusMonitorTargetAdmnRowStatus OBJECT-TYPE
    SYNTAX          RowStatus
    ACCESS          read-write
    STATUS          mandatory
    DESCRIPTION     
            ""
    ::= { sonusMonitorTargetAdmnEntry 13 }

sonusMonitorTargetStatTable OBJECT-TYPE
    SYNTAX          SEQUENCE OF SonusMonitorTargetStatEntry
    ACCESS          not-accessible
    STATUS          mandatory
    DESCRIPTION     
            "This table shows the Monitor call stats"
    ::= { sonusNodeResourcesMIBObjects 26 }

sonusMonitorTargetStatEntry OBJECT-TYPE
    SYNTAX          SonusMonitorTargetStatEntry
    ACCESS          not-accessible
    STATUS          mandatory
    DESCRIPTION     
            "This is the entry into Monitor call stats"
    INDEX           { sonusMonitorTargetStatIndex, 
                      sonusMonitorTargetStatEndpointIndex }
    ::= { sonusMonitorTargetStatTable 1 }

SonusMonitorTargetStatEntry ::=
    SEQUENCE {
        sonusMonitorTargetStatIndex     INTEGER,
        sonusMonitorTargetStatEndpointIndex   INTEGER,
        sonusMonitorTargetStatCallId    INTEGER,
        sonusMonitorTargetStatMonId     INTEGER,
        sonusMonitorTargetStatCallState DisplayString,
        sonusMonitorTargetStatMonState  DisplayString,
        sonusMonitorTargetStatTime      DisplayString,
        sonusMonitorTargetStatError     DisplayString
    }

sonusMonitorTargetStatIndex OBJECT-TYPE
    SYNTAX          INTEGER
    ACCESS          read-only
    STATUS          mandatory
    DESCRIPTION     
            "The index for target monitor target stats."
    ::= { sonusMonitorTargetStatEntry 1 }

sonusMonitorTargetStatEndpointIndex OBJECT-TYPE
    SYNTAX          INTEGER
    ACCESS          read-only
    STATUS          mandatory
    DESCRIPTION     
            "The index for target monitor endpoint stats."
    ::= { sonusMonitorTargetStatEntry 2 }

sonusMonitorTargetStatCallId OBJECT-TYPE
    SYNTAX          INTEGER
    ACCESS          read-only
    STATUS          mandatory
    DESCRIPTION     
            "The call identifier(GCID) assigned to the call being monitored"
    ::= { sonusMonitorTargetStatEntry 3 }

sonusMonitorTargetStatMonId OBJECT-TYPE
    SYNTAX          INTEGER
    ACCESS          read-only
    STATUS          mandatory
    DESCRIPTION     
            "The call identifier(GCID) assigned to the monitor leg"
    ::= { sonusMonitorTargetStatEntry 4 }

sonusMonitorTargetStatCallState OBJECT-TYPE
    SYNTAX          DisplayString (SIZE(0..23))
    ACCESS          read-only
    STATUS          mandatory
    DESCRIPTION     
            "The status of the call being monitored"
    ::= { sonusMonitorTargetStatEntry 5 }

sonusMonitorTargetStatMonState OBJECT-TYPE
    SYNTAX          DisplayString (SIZE(0..23))
    ACCESS          read-only
    STATUS          mandatory
    DESCRIPTION     
            "The status of the endpoint being used to monitor the call"
    ::= { sonusMonitorTargetStatEntry 6 }

sonusMonitorTargetStatTime OBJECT-TYPE
    SYNTAX          DisplayString (SIZE(0..23))
    ACCESS          read-only
    STATUS          mandatory
    DESCRIPTION     
            "Displays the Date/time the monitor target call  was created"
    ::= { sonusMonitorTargetStatEntry 7 }

sonusMonitorTargetStatError OBJECT-TYPE
    SYNTAX          DisplayString (SIZE(0..23))
    ACCESS          read-only
    STATUS          mandatory
    DESCRIPTION     
            "String that displays the error (if any) encounterted while activating the tap"
    ::= { sonusMonitorTargetStatEntry 8 }

sonusZoneObjects OBJECT IDENTIFIER
    ::= { sonusNodeResourcesMIBObjects 27 }

sonusZone OBJECT IDENTIFIER
    ::= { sonusZoneObjects 1 }

sonusZoneNextIndex OBJECT-TYPE
    SYNTAX          INTEGER
    ACCESS          not-accessible
    STATUS          mandatory
    DESCRIPTION     
            "The next valid index to use when creating an entry in
             the sonusZoneTable."
    ::= { sonusZone 1 }

sonusZoneTable OBJECT-TYPE
    SYNTAX          SEQUENCE OF SonusZoneEntry
    ACCESS          not-accessible
    STATUS          mandatory
    DESCRIPTION     
            "This table contains zones for the node."
    ::= { sonusZone 2 }

sonusZoneEntry OBJECT-TYPE
    SYNTAX          SonusZoneEntry
    ACCESS          not-accessible
    STATUS          mandatory
    DESCRIPTION     
            ""
    INDEX           { sonusZoneIndex }
    ::= { sonusZoneTable 1 }

SonusZoneEntry ::=
    SEQUENCE {
        sonusZoneIndex                  Gauge,
        sonusZoneName                   SonusName,
        sonusZoneId                     Gauge,
        sonusZoneRowStatus              RowStatus,
        sonusZoneTcpConnectTimeOut      Gauge,
        sonusZoneTransportProtocolAllowed OCTET STRING,
        sonusZoneTlsProfileName         SonusNameReference,
        sonusZoneDnsNifGroupName        SonusNameReference,
        sonusZoneDnsEdnsSupport         SonusAdminState,
        sonusZoneDnsExtendedTtl         Gauge,
        sonusZoneRemoteDeviceType       INTEGER,
        sonusZoneUseConfiguredDnsServer SonusAdminState
    }

sonusZoneIndex OBJECT-TYPE
    SYNTAX          Gauge
    ACCESS          read-only
    STATUS          mandatory
    DESCRIPTION     
            "Table index of this zone."
    ::= { sonusZoneEntry 1 }

sonusZoneName OBJECT-TYPE
    SYNTAX          SonusName
    ACCESS          read-write
    STATUS          mandatory
    DESCRIPTION     
            "Name of this zone."
    ::= { sonusZoneEntry 2 }

sonusZoneId OBJECT-TYPE
    SYNTAX          Gauge (0..2048)
    ACCESS          read-write
    STATUS          mandatory
    DESCRIPTION     
            "Unique ID of this zone. The user can either supply this,
             or have it automatically generated."
    ::= { sonusZoneEntry 3 }

sonusZoneRowStatus OBJECT-TYPE
    SYNTAX          RowStatus
    ACCESS          read-write
    STATUS          mandatory
    DESCRIPTION     
            "The object indicates the row status for this table."
    ::= { sonusZoneEntry 4 }

sonusZoneTcpConnectTimeOut OBJECT-TYPE
    SYNTAX          Gauge (0..180)
    ACCESS          read-write
    STATUS          mandatory
    DESCRIPTION     
            "This object indicates the maximum time, in seconds, allowed
             for GSX/NBS to establish an outbound TCP connection."
    DEFVAL          { 5 }
    ::= { sonusZoneEntry 5 }

sonusZoneTransportProtocolAllowed OBJECT-TYPE
    SYNTAX          OCTET STRING
--                       { sip-udp(0), sip-tcp(1), sip-tls-tcp(2), 
--                         sip-sctp(3) }
    ACCESS          read-write
    STATUS          mandatory
    DESCRIPTION     
            "This object indicates the transport protocols allowed
             whinin a signaling zone."
    DEFVAL          { {sip-udp} }
    ::= { sonusZoneEntry 6 }

sonusZoneTlsProfileName OBJECT-TYPE
    SYNTAX          SonusNameReference
    ACCESS          read-write
    STATUS          mandatory
    DESCRIPTION     
            "Identifies the TLS Profile for this zone."
    DEFVAL          { "defaultTlsProfile" }
    ::= { sonusZoneEntry 7 }

sonusZoneDnsNifGroupName OBJECT-TYPE
    SYNTAX          SonusNameReference
    ACCESS          read-write
    STATUS          mandatory
    DESCRIPTION     
            "The DNS NIF Group to be used for DNS queries in this zone."
    ::= { sonusZoneEntry 9 }

sonusZoneDnsEdnsSupport OBJECT-TYPE
    SYNTAX          SonusAdminState
    ACCESS          read-write
    STATUS          mandatory
    DESCRIPTION     
            "If E-DNS is enabled, GSX sends e-dns queries to all Name Servers in this zone."
    DEFVAL          { disabled }
    ::= { sonusZoneEntry 10 }

sonusZoneDnsExtendedTtl OBJECT-TYPE
    SYNTAX          Gauge (0..1440)
    ACCESS          read-write
    STATUS          mandatory
    DESCRIPTION     
            "The time for which the record entries can be used after the TTL expires"
    DEFVAL          { 0 }
    ::= { sonusZoneEntry 11 }

sonusZoneRemoteDeviceType OBJECT-TYPE
    SYNTAX          INTEGER { none(0), access(1), appServer(2) }
    ACCESS          read-write
    STATUS          mandatory
    DESCRIPTION     
            "This Field indicates whether remoteDeviceType is Access or AppServer.
             Default Value of this field is none"
    DEFVAL          { none }
    ::= { sonusZoneEntry 12 }

sonusZoneUseConfiguredDnsServer OBJECT-TYPE
    SYNTAX          SonusAdminState
    ACCESS          read-write
    STATUS          mandatory
    DESCRIPTION     
            " If this flag is enabled , GSX will use the configured DNS server instead of quering servers returned in response of DNS query 
             when 'Recursive Desired' flag is enabled"
    DEFVAL          { disabled }
    ::= { sonusZoneEntry 13 }

sonusFeatureCtrlObjects OBJECT IDENTIFIER
    ::= { sonusNodeResourcesMIBObjects 28 }

sonusFeatureCtrlTable OBJECT-TYPE
    SYNTAX          SEQUENCE OF SonusFeatureCtrlEntry
    ACCESS          not-accessible
    STATUS          mandatory
    DESCRIPTION     
            "This table presents feature state information from each shelf."
    ::= { sonusFeatureCtrlObjects 1 }

sonusFeatureCtrlEntry OBJECT-TYPE
    SYNTAX          SonusFeatureCtrlEntry
    ACCESS          not-accessible
    STATUS          mandatory
    DESCRIPTION     
            "This table contains feature states for various feature for the node."
    INDEX           { sonusFeatureCtrlShelfIndex }
    ::= { sonusFeatureCtrlTable 1 }

SonusFeatureCtrlEntry ::=
    SEQUENCE {
        sonusFeatureCtrlShelfIndex      SonusShelfIndex,
        sonusFeatureCtrlValidData       TruthValue,
        sonusFeatureCtrlHpcName         SonusName,
        sonusFeatureCtrlHpcState        SonusAdminState,
        sonusFeatureCtrlMlppName        SonusName,
        sonusFeatureCtrlMlppState       SonusAdminState
    }

sonusFeatureCtrlShelfIndex OBJECT-TYPE
    SYNTAX          SonusShelfIndex
    ACCESS          not-accessible
    STATUS          mandatory
    DESCRIPTION     
            "Index of this table entry. This is equivalent to the GSX
             shelf index, i.e. one entry per GSX shelf."
    ::= { sonusFeatureCtrlEntry 1 }

sonusFeatureCtrlValidData OBJECT-TYPE
    SYNTAX          TruthValue
    ACCESS          read-only
    STATUS          mandatory
    DESCRIPTION     
            "This variable indicates if the data for feature state is valid."
    ::= { sonusFeatureCtrlEntry 2 }

sonusFeatureCtrlHpcName OBJECT-TYPE
    SYNTAX          SonusName
    ACCESS          read-only
    STATUS          mandatory
    DESCRIPTION     
            "This holds name of the HPC feature."
    ::= { sonusFeatureCtrlEntry 3 }

sonusFeatureCtrlHpcState OBJECT-TYPE
    SYNTAX          SonusAdminState
    ACCESS          read-only
    STATUS          mandatory
    DESCRIPTION     
            "This holds state of the HPC feature."
    ::= { sonusFeatureCtrlEntry 4 }

sonusFeatureCtrlMlppName OBJECT-TYPE
    SYNTAX          SonusName
    ACCESS          read-only
    STATUS          mandatory
    DESCRIPTION     
            "This holds name of the MLPP feature."
    ::= { sonusFeatureCtrlEntry 5 }

sonusFeatureCtrlMlppState OBJECT-TYPE
    SYNTAX          SonusAdminState
    ACCESS          read-only
    STATUS          mandatory
    DESCRIPTION     
            "This holds state of the MLPP feature."
    ::= { sonusFeatureCtrlEntry 6 }

sonusCallFailNoDspThresholdTable OBJECT-TYPE
    SYNTAX          SEQUENCE OF SonusCallFailNoDspThresholdEntry
    ACCESS          not-accessible
    STATUS          mandatory
    DESCRIPTION     
            "This table presents Call Failure due to no DSP trap configuration."
    ::= { sonusNodeResourcesMIBObjects 29 }

sonusCallFailNoDspThresholdEntry OBJECT-TYPE
    SYNTAX          SonusCallFailNoDspThresholdEntry
    ACCESS          not-accessible
    STATUS          mandatory
    DESCRIPTION     
            "An entry in the Sonus Call Failure NO DSP Threshold table"
    INDEX           { sonusCallFailNoDspThresholdShelfIndex }
    ::= { sonusCallFailNoDspThresholdTable 1 }

SonusCallFailNoDspThresholdEntry ::=
    SEQUENCE {
        sonusCallFailNoDspThresholdShelfIndex     SonusShelfIndex,
        sonusCallFailNoDspThresholdNumCallFailure         Gauge,
        sonusCallFailNoDspThresholdNumCallFailureInterval                 Gauge
    }

sonusCallFailNoDspThresholdShelfIndex OBJECT-TYPE
    SYNTAX          SonusShelfIndex
    ACCESS          read-only
    STATUS          mandatory
    DESCRIPTION     
            "the index into SonusCallFailNoDspThresholdEntry table"
    ::= { sonusCallFailNoDspThresholdEntry 1 }

sonusCallFailNoDspThresholdNumCallFailure OBJECT-TYPE
    SYNTAX          Gauge (0..65535)
    ACCESS          read-write
    STATUS          mandatory
    DESCRIPTION     
            "Indicates the number of call failure due to lack of DSP pad threshold."
    ::= { sonusCallFailNoDspThresholdEntry 2 }

sonusCallFailNoDspThresholdNumCallFailureInterval OBJECT-TYPE
    SYNTAX          Gauge (0..65535)
    ACCESS          read-write
    STATUS          mandatory
    DESCRIPTION     
            "Indicates the time interval for the threshold of call failure due to lack of DSP pad."
    ::= { sonusCallFailNoDspThresholdEntry 3 }

sonusDspAvailabilityTrapConfigTable OBJECT-TYPE
    SYNTAX          SEQUENCE OF SonusDspAvailabilityTrapConfigEntry
    ACCESS          not-accessible
    STATUS          mandatory
    DESCRIPTION     
            "This table presents DSP Availability trap configuration."
    ::= { sonusNodeResourcesMIBObjects 30 }

sonusDspAvailabilityTrapConfigEntry OBJECT-TYPE
    SYNTAX          SonusDspAvailabilityTrapConfigEntry
    ACCESS          not-accessible
    STATUS          mandatory
    DESCRIPTION     
            "An entry in the Sonus DSP pad availibility threshold table"
    INDEX           { sonusDspAvailabilityShelfIndex }
    ::= { sonusDspAvailabilityTrapConfigTable 1 }

SonusDspAvailabilityTrapConfigEntry ::=
    SEQUENCE {
        sonusDspAvailabilityShelfIndex  SonusShelfIndex,
        sonusDspAvailabilityG711CircuitThreshold        Gauge,
        sonusDspAvailabilityToneThreshold Gauge,
        sonusDspAvailabilityBridgePortThreshold       Gauge,
        sonusDspAvailabilityG729Threshold Gauge,
        sonusDspAvailabilityG726Threshold Gauge,
        sonusDspAvailabilityG723Threshold Gauge,
        sonusDspAvailabilityG711PacketThreshold       Gauge,
        sonusDspAvailabilityT38Threshold Gauge,
        sonusDspAvailabilityEvrcThreshold Gauge,
        sonusDspAvailabilityGsmThreshold Gauge,
        sonusDspAvailabilityT38EcmThreshold   Gauge,
        sonusDspAvailabilityEvrcb0Threshold   Gauge,
        sonusDspAvailabilityiLBCThreshold Gauge,
        sonusDspAvailabilityG722Threshold Gauge,
        sonusDspAvailabilityAmrwbThreshold  Gauge,
        sonusDspPollTimer               INTEGER
    }

sonusDspAvailabilityShelfIndex OBJECT-TYPE
    SYNTAX          SonusShelfIndex
    ACCESS          read-only
    STATUS          mandatory
    DESCRIPTION     
            "the index into SonusDspAvailabilityTrapConfigEntry table"
    ::= { sonusDspAvailabilityTrapConfigEntry 1 }

sonusDspAvailabilityG711CircuitThreshold OBJECT-TYPE
    SYNTAX          Gauge (0..100)
    ACCESS          read-write
    STATUS          mandatory
    DESCRIPTION     
            "Indicates the percentage of  G711Circuit type DSP usage threshold."
    ::= { sonusDspAvailabilityTrapConfigEntry 2 }

sonusDspAvailabilityToneThreshold OBJECT-TYPE
    SYNTAX          Gauge (0..100)
    ACCESS          read-write
    STATUS          mandatory
    DESCRIPTION     
            "Indicates the percentage of  tone type DSP Availability threshold."
    ::= { sonusDspAvailabilityTrapConfigEntry 3 }

sonusDspAvailabilityBridgePortThreshold OBJECT-TYPE
    SYNTAX          Gauge (0..100)
    ACCESS          read-write
    STATUS          mandatory
    DESCRIPTION     
            "Indicates the percentage of  bridge port type DSP Availability threshold."
    ::= { sonusDspAvailabilityTrapConfigEntry 4 }

sonusDspAvailabilityG729Threshold OBJECT-TYPE
    SYNTAX          Gauge (0..100)
    ACCESS          read-write
    STATUS          mandatory
    DESCRIPTION     
            "Indicates the percentage of  G729 type DSP Availability threshold."
    ::= { sonusDspAvailabilityTrapConfigEntry 5 }

sonusDspAvailabilityG726Threshold OBJECT-TYPE
    SYNTAX          Gauge (0..100)
    ACCESS          read-write
    STATUS          mandatory
    DESCRIPTION     
            "Indicates the percentage of G726 type DSP Availability threshold."
    ::= { sonusDspAvailabilityTrapConfigEntry 6 }

sonusDspAvailabilityG723Threshold OBJECT-TYPE
    SYNTAX          Gauge (0..100)
    ACCESS          read-write
    STATUS          mandatory
    DESCRIPTION     
            "Indicates the percentage of G723 type DSP Availability threshold."
    ::= { sonusDspAvailabilityTrapConfigEntry 7 }

sonusDspAvailabilityG711PacketThreshold OBJECT-TYPE
    SYNTAX          Gauge (0..100)
    ACCESS          read-write
    STATUS          mandatory
    DESCRIPTION     
            "Indicates the percentage of G711 Packet type DSP Availability threshold."
    ::= { sonusDspAvailabilityTrapConfigEntry 8 }

sonusDspAvailabilityT38Threshold OBJECT-TYPE
    SYNTAX          Gauge (0..100)
    ACCESS          read-write
    STATUS          mandatory
    DESCRIPTION     
            "Indicates the percentage of T38 type DSP Availability threshold."
    ::= { sonusDspAvailabilityTrapConfigEntry 9 }

sonusDspAvailabilityEvrcThreshold OBJECT-TYPE
    SYNTAX          Gauge (0..100)
    ACCESS          read-write
    STATUS          mandatory
    DESCRIPTION     
            "Indicates the percentage of EVRC type DSP Availability threshold."
    ::= { sonusDspAvailabilityTrapConfigEntry 10 }

sonusDspAvailabilityGsmThreshold OBJECT-TYPE
    SYNTAX          Gauge (0..100)
    ACCESS          read-write
    STATUS          mandatory
    DESCRIPTION     
            "Indicates the percentage of GSM type DSP Availability threshold."
    ::= { sonusDspAvailabilityTrapConfigEntry 11 }

sonusDspAvailabilityT38EcmThreshold OBJECT-TYPE
    SYNTAX          Gauge (0..100)
    ACCESS          read-write
    STATUS          mandatory
    DESCRIPTION     
            "Indicates the percentage of T38 ECM capable type DSP Availability threshold."
    ::= { sonusDspAvailabilityTrapConfigEntry 12 }

sonusDspAvailabilityEvrcb0Threshold OBJECT-TYPE
    SYNTAX          Gauge (0..100)
    ACCESS          read-write
    STATUS          mandatory
    DESCRIPTION     
            "Indicates the percentage of EVRCB0 type DSP Availability threshold."
    ::= { sonusDspAvailabilityTrapConfigEntry 13 }

sonusDspAvailabilityiLBCThreshold OBJECT-TYPE
    SYNTAX          Gauge (0..100)
    ACCESS          read-write
    STATUS          mandatory
    DESCRIPTION     
            "Indicates the percentage of iLBC type DSP Availability threshold."
    ::= { sonusDspAvailabilityTrapConfigEntry 14 }

sonusDspAvailabilityG722Threshold OBJECT-TYPE
    SYNTAX          Gauge (0..100)
    ACCESS          read-write
    STATUS          mandatory
    DESCRIPTION     
            "Indicates the percentage of G722 type DSP Availability threshold."
    ::= { sonusDspAvailabilityTrapConfigEntry 15 }

sonusDspAvailabilityAmrwbThreshold OBJECT-TYPE
    SYNTAX          Gauge (0..100)
    ACCESS          read-write
    STATUS          mandatory
    DESCRIPTION     
            "Indicates the percentage of AMRWB type DSP Availability threshold."
    ::= { sonusDspAvailabilityTrapConfigEntry 16 }

sonusDspPollTimer OBJECT-TYPE
    SYNTAX          INTEGER { twohundredms(0), twofiftyms(1), 
                        fivehundredms(2), sevenfiftyms(3), thousandms(4), 
                        onethousandtwofiftyms(5), 
                        onethousandfivehundredms(6) }
    ACCESS          read-write
    STATUS          mandatory
    DESCRIPTION     
            "Indicates the DSPPOLL REFRESH TIMER."
    DEFVAL          { thousandms }
    ::= { sonusDspAvailabilityTrapConfigEntry 17 }

sonusTestCallNumberObjects OBJECT IDENTIFIER
    ::= { sonusNodeResourcesMIBObjects 31 }

sonusTestCallNumberNextIndex OBJECT-TYPE
    SYNTAX          INTEGER
    ACCESS          read-only
    STATUS          mandatory
    DESCRIPTION     
            "The next valid index to use when creating an entry in
             the sonusTestCallNumberTable."
    ::= { sonusTestCallNumberObjects 1 }

sonusTestCallNumberTable OBJECT-TYPE
    SYNTAX          SEQUENCE OF SonusTestCallNumberEntry
    ACCESS          not-accessible
    STATUS          mandatory
    DESCRIPTION     
            "This table specifies the Test Call Number Table"
    ::= { sonusTestCallNumberObjects 2 }

sonusTestCallNumberEntry OBJECT-TYPE
    SYNTAX          SonusTestCallNumberEntry
    ACCESS          not-accessible
    STATUS          mandatory
    DESCRIPTION     
            ""
    INDEX           { sonusTestCallNumberIndex }
    ::= { sonusTestCallNumberTable 1 }

SonusTestCallNumberEntry ::=
    SEQUENCE {
        sonusTestCallNumberIndex        INTEGER,
        sonusTestCallNumber             DisplayString,
        sonusTestCallNumberRowStatus    RowStatus
    }

sonusTestCallNumberIndex OBJECT-TYPE
    SYNTAX          INTEGER
    ACCESS          read-only
    STATUS          mandatory
    DESCRIPTION     
            "The index of this Test Call Number entry."
    ::= { sonusTestCallNumberEntry 1 }

sonusTestCallNumber OBJECT-TYPE
    SYNTAX          DisplayString (SIZE(0..31))
    ACCESS          read-write
    STATUS          mandatory
    DESCRIPTION     
            "The Test Call Number entry is stored in this field"
    ::= { sonusTestCallNumberEntry 2 }

sonusTestCallNumberRowStatus OBJECT-TYPE
    SYNTAX          RowStatus
    ACCESS          read-write
    STATUS          mandatory
    DESCRIPTION     
            "The object indicates the row status for this table"
    ::= { sonusTestCallNumberEntry 3 }

sonusSonicBusUsageObjects OBJECT IDENTIFIER
    ::= { sonusNodeResourcesMIBObjects 33 }

sonusSonicBusUsageConfigObjects OBJECT IDENTIFIER
    ::= { sonusSonicBusUsageObjects 1 }

sonusSonicBusUsageStatisticsState OBJECT-TYPE
    SYNTAX          SonusAdminState
    ACCESS          read-write
    STATUS          mandatory
    DESCRIPTION     
            "This configures whether Media usage statistics collection in midplane Enabled or Disabled for the Node"
    DEFVAL          { disabled }
    ::= { sonusSonicBusUsageConfigObjects 1 }

sonusSonicBusUsageStatisticsOnSetThreshold OBJECT-TYPE
    SYNTAX          Gauge (0..100)
    ACCESS          read-write
    STATUS          mandatory
    DESCRIPTION     
            "If the midplane usage goes beyond this configured threshold a trap will be raised to indicate that the midplane usage is high."
    DEFVAL          { 0 }
    ::= { sonusSonicBusUsageConfigObjects 2 }

sonusSonicBusUsageStatisticsAbatingThreshold OBJECT-TYPE
    SYNTAX          Gauge (0..100)
    ACCESS          read-write
    STATUS          mandatory
    DESCRIPTION     
            "If the midplane usage comes below this configured threshold a trap will be raised to indicate that the midplane usage is normal."
    DEFVAL          { 0 }
    ::= { sonusSonicBusUsageConfigObjects 3 }

sonusSonicBusUsageStatisticsSamplingInterval OBJECT-TYPE
    SYNTAX          INTEGER (1..60)
    ACCESS          read-write
    STATUS          mandatory
    DESCRIPTION     
            "This configures the Interval in seconds in which the midplane usage will be sampled for statistics collection."
    DEFVAL          { 5 }
    ::= { sonusSonicBusUsageConfigObjects 4 }

sonusSonicBusUsageStatisticsTrapInterval OBJECT-TYPE
    SYNTAX          INTEGER (1..5)
    ACCESS          read-write
    STATUS          mandatory
    DESCRIPTION     
            "This configures the Interval in minutes in the trap will be raised if the usage in the midplane goes beyond configured on-set threshold"
    DEFVAL          { 1 }
    ::= { sonusSonicBusUsageConfigObjects 5 }

sonusNodeResourcesMIBNotifications OBJECT IDENTIFIER
    ::= { sonusNodeResourcesMIB 2 }

sonusNodeResourcesMIBNotificationsPrefix OBJECT IDENTIFIER
    ::= { sonusNodeResourcesMIBNotifications 0 }

sonusNodeResourcesMIBNotificationsObjects OBJECT IDENTIFIER
    ::= { sonusNodeResourcesMIBNotifications 1 }

sonusCallAdmissionChangeReason OBJECT-TYPE
    SYNTAX          DisplayString (SIZE(1..101))
    ACCESS          read-only
    STATUS          mandatory
    DESCRIPTION     
            "The reason why the call admission control state has changes."
    ::= { sonusNodeResourcesMIBNotificationsObjects 1 }

sonusNodeResourceIsupCircuit OBJECT-TYPE
    SYNTAX          INTEGER (0..16383)
    ACCESS          read-only
    STATUS          mandatory
    DESCRIPTION     
            "Base circuit identity code (CIC) for the circuit."
    ::= { sonusNodeResourcesMIBNotificationsObjects 2 }

sonusFeatureName OBJECT-TYPE
    SYNTAX          DisplayString (SIZE(1..31))
    ACCESS          read-only
    STATUS          mandatory
    DESCRIPTION     
            "Name of the feature in the context."
    ::= { sonusNodeResourcesMIBNotificationsObjects 3 }

sonusFeatureState OBJECT-TYPE
    SYNTAX          SonusAdminState
    ACCESS          read-only
    STATUS          mandatory
    DESCRIPTION     
            "State of the feature in context"
    ::= { sonusNodeResourcesMIBNotificationsObjects 4 }

sonusNumCallFailureNoDspExceedThreshold OBJECT-TYPE
    SYNTAX          Gauge
    ACCESS          read-only
    STATUS          mandatory
    DESCRIPTION     
            "The number of times call failure due to lack of DSP resource exceeded threshold since last trap notification."
    ::= { sonusNodeResourcesMIBNotificationsObjects 5 }

sonusNumDspAvailabilityG711CircuitCrossThreshold OBJECT-TYPE
    SYNTAX          Gauge
    ACCESS          read-only
    STATUS          mandatory
    DESCRIPTION     
            "The number of times the availability of G711 circuit DSP resource crossed threshold since last trap notification."
    ::= { sonusNodeResourcesMIBNotificationsObjects 6 }

sonusNumDspAvailabilityToneCrossThreshold OBJECT-TYPE
    SYNTAX          Gauge
    ACCESS          read-only
    STATUS          mandatory
    DESCRIPTION     
            "The number of times the availability of Tone DSP resource crossed threshold since last trap notification."
    ::= { sonusNodeResourcesMIBNotificationsObjects 7 }

sonusNumDspAvailabilityBridgePortCrossThreshold OBJECT-TYPE
    SYNTAX          Gauge
    ACCESS          read-only
    STATUS          mandatory
    DESCRIPTION     
            "The number of times the availability of Bridge Port DSP resource crossed threshold since last trap notification."
    ::= { sonusNodeResourcesMIBNotificationsObjects 8 }

sonusNumDspAvailabilityG729CrossThreshold OBJECT-TYPE
    SYNTAX          Gauge
    ACCESS          read-only
    STATUS          mandatory
    DESCRIPTION     
            "The number of times the availability of G729 DSP resource crossed threshold since last trap notification."
    ::= { sonusNodeResourcesMIBNotificationsObjects 9 }

sonusNumDspAvailabilityG726CrossThreshold OBJECT-TYPE
    SYNTAX          Gauge
    ACCESS          read-only
    STATUS          mandatory
    DESCRIPTION     
            "The number of times the availability of G726 DSP resource crossed threshold since last trap notification."
    ::= { sonusNodeResourcesMIBNotificationsObjects 10 }

sonusNumDspAvailabilityG723CrossThreshold OBJECT-TYPE
    SYNTAX          Gauge
    ACCESS          read-only
    STATUS          mandatory
    DESCRIPTION     
            "The number of times the availability of G723 DSP resource crossed threshold since last trap notification."
    ::= { sonusNodeResourcesMIBNotificationsObjects 11 }

sonusNumDspAvailabilityG711PacketCrossThreshold OBJECT-TYPE
    SYNTAX          Gauge
    ACCESS          read-only
    STATUS          mandatory
    DESCRIPTION     
            "The number of times the availability of G711 Packet DSP resource crossed threshold since last trap notification."
    ::= { sonusNodeResourcesMIBNotificationsObjects 12 }

sonusNumDspAvailabilityT38CrossThreshold OBJECT-TYPE
    SYNTAX          Gauge
    ACCESS          read-only
    STATUS          mandatory
    DESCRIPTION     
            "The number of times the availability of T38 DSP resource crossed threshold since last trap notification."
    ::= { sonusNodeResourcesMIBNotificationsObjects 13 }

sonusNumDspAvailabilityEvrcCrossThreshold OBJECT-TYPE
    SYNTAX          Gauge
    ACCESS          read-only
    STATUS          mandatory
    DESCRIPTION     
            "The number of times the availability of EVRC DSP resource crossed threshold since last trap notification."
    ::= { sonusNodeResourcesMIBNotificationsObjects 14 }

sonusNumDspAvailabilityGsmCrossThreshold OBJECT-TYPE
    SYNTAX          Gauge
    ACCESS          read-only
    STATUS          mandatory
    DESCRIPTION     
            "The number of times the availability of GSM DSP resource crossed threshold since last trap notification."
    ::= { sonusNodeResourcesMIBNotificationsObjects 15 }

sonusNumDspAvailabilityT38EcmCrossThreshold OBJECT-TYPE
    SYNTAX          Gauge
    ACCESS          read-only
    STATUS          mandatory
    DESCRIPTION     
            "The number of times the availability of T38 ECM
             capable DSP resource crossed threshold since last trap notification."
    ::= { sonusNodeResourcesMIBNotificationsObjects 16 }

sonusNumDspAvailabilityEvrcb0CrossThreshold OBJECT-TYPE
    SYNTAX          Gauge
    ACCESS          read-only
    STATUS          mandatory
    DESCRIPTION     
            "The number of times the availability of EVRCB0 DSP resource crossed threshold since last trap notification."
    ::= { sonusNodeResourcesMIBNotificationsObjects 17 }

sonusNumDspAvailabilityG722CrossThreshold OBJECT-TYPE
    SYNTAX          Gauge
    ACCESS          read-only
    STATUS          mandatory
    DESCRIPTION     
            "The number of times the availability of G722 DSP resource crossed threshold since last trap notification."
    ::= { sonusNodeResourcesMIBNotificationsObjects 19 }

sonusNumDspAvailabilityAmrwbCrossThreshold OBJECT-TYPE
    SYNTAX          Gauge
    ACCESS          read-only
    STATUS          mandatory
    DESCRIPTION     
            "The number of times the availability of AMRWB DSP resource crossed threshold since last trap notification."
    ::= { sonusNodeResourcesMIBNotificationsObjects 20 }

sonusCallTraceDisableReason OBJECT-TYPE
    SYNTAX          DisplayString (SIZE(1..31))
    ACCESS          read-only
    STATUS          mandatory
    DESCRIPTION     
            "Reason to Disable the call Trace "
    ::= { sonusNodeResourcesMIBNotificationsObjects 21 }

sonusNodeResourcesCallAdmissionSuspendedNotification TRAP-TYPE
    ENTERPRISE      sonusNodeResourcesMIBNotifications
    VARIABLES       { sonusCallAdmissionChangeReason, 
                      sonusEventDescription, sonusEventClass, 
                      sonusEventLevel, sonusSequenceId, sonusEventTime }
--     STATUS          mandatory
    DESCRIPTION     
            "This trap indicates that call admission into the GSX has been
             suspended. Information provided by this trap includes the reason
             why call admission has been suspended."
    ::= 1

sonusNodeResourcesCallAdmissionEnabledNotification TRAP-TYPE
    ENTERPRISE      sonusNodeResourcesMIBNotifications
    VARIABLES       { sonusCallAdmissionChangeReason, 
                      sonusEventDescription, sonusEventClass, 
                      sonusEventLevel, sonusSequenceId, sonusEventTime }
--     STATUS          mandatory
    DESCRIPTION     
            "This trap indicates that call admission into the GSX has been
             enabled. Information provided by this trap includes the reason
             why call admission has been enabled."
    ::= 2

sonusNodeResourcesCallTraceHitNotification TRAP-TYPE
    ENTERPRISE      sonusNodeResourcesMIBNotifications
    VARIABLES       { sonusCallTraceCalledNumber, 
                      sonusCallTraceCallingNumber, sonusEventDescription, 
                      sonusEventClass, sonusEventLevel, sonusSequenceId, 
                      sonusEventTime }
--     STATUS          mandatory
    DESCRIPTION     
            "This trap indicates that call trace filter had a hit.
             Information provided by this trap includes the called number
             and the calling number."
    ::= 3

sonusNodeResourcesCallTraceHitGAPNotification TRAP-TYPE
    ENTERPRISE      sonusNodeResourcesMIBNotifications
    VARIABLES       { sonusCallTraceCalledNumber, 
                      sonusCallTraceCallingNumber, 
                      sonusActiveCallOrigCalledNum, 
                      sonusEventDescription, sonusEventClass, 
                      sonusEventLevel, sonusSequenceId, sonusEventTime }
--     STATUS          mandatory
    DESCRIPTION     
            "This trap indicates that call trace filter had a hit.
             Information provided by this trap includes the called number,
             the calling number, and the original called number (in GAP)."
    ::= 4

sonusNodeResEmerCallNoRouteNotification TRAP-TYPE
    ENTERPRISE      sonusNodeResourcesMIBNotifications
    VARIABLES       { sonusActiveCallIngressPstnTrunk, 
                      sonusNodeResourceIsupCircuit, 
                      sonusActiveCallCallingNum, 
                      sonusActiveCallCalledNum, 
                      sonusActiveCallOrigCalledNum, 
                      sonusEventDescription, sonusEventClass, 
                      sonusEventLevel, sonusSequenceId, sonusEventTime }
--     STATUS          mandatory
    DESCRIPTION     
            "This trap indicates that an emergency call was placed
             that failed to route."
    ::= 5

sonusNodeResourcesMaxIpCallLimitSetNotification TRAP-TYPE
    ENTERPRISE      sonusNodeResourcesMIBNotifications
    VARIABLES       { sonusEventDescription, sonusEventClass, 
                      sonusEventLevel, sonusSequenceId, sonusEventTime }
--     STATUS          mandatory
    DESCRIPTION     
            "This trap indicates that MAX IP call Limit set."
    ::= 6

sonusNodeResourcesMaxIpCallLimitClearNotification TRAP-TYPE
    ENTERPRISE      sonusNodeResourcesMIBNotifications
    VARIABLES       { sonusEventDescription, sonusEventClass, 
                      sonusEventLevel, sonusSequenceId, sonusEventTime }
--     STATUS          mandatory
    DESCRIPTION     
            "This trap indicates that MAX IP call Limit cleared."
    ::= 7

sonusNodeResourcesMaxSysCallLimitSetNotification TRAP-TYPE
    ENTERPRISE      sonusNodeResourcesMIBNotifications
    VARIABLES       { sonusEventDescription, sonusEventClass, 
                      sonusEventLevel, sonusSequenceId, sonusEventTime }
--     STATUS          mandatory
    DESCRIPTION     
            "This trap indicates that MAX System call limit set."
    ::= 8

sonusNodeResourcesMaxSysCallLimitClearNotification TRAP-TYPE
    ENTERPRISE      sonusNodeResourcesMIBNotifications
    VARIABLES       { sonusEventDescription, sonusEventClass, 
                      sonusEventLevel, sonusSequenceId, sonusEventTime }
--     STATUS          mandatory
    DESCRIPTION     
            "This trap indicates that MAX system call limit cleared."
    ::= 9

sonusNodeResourcesFeatureKeyStateChangeNotification TRAP-TYPE
    ENTERPRISE      sonusNodeResourcesMIBNotifications
    VARIABLES       { sonusFeatureName, sonusFeatureState, 
                      sonusEventDescription, sonusEventClass, 
                      sonusEventLevel, sonusSequenceId, sonusEventTime }
--     STATUS          mandatory
    DESCRIPTION     
            "This trap indicates that there is change in feature key state."
    ::= 10

sonusCallFailureNoDspExceedThresholdNotification TRAP-TYPE
    ENTERPRISE      sonusNodeResourcesMIBNotifications
    VARIABLES       { sonusNumCallFailureNoDspExceedThreshold, 
                      sonusEventDescription, sonusEventClass, 
                      sonusEventLevel, sonusSequenceId, sonusEventTime }
--     STATUS          deprecated
    DESCRIPTION     
            "This trap is deprecated. This trap indicates that number of call failure due to lack of DSP resource exceed the threshold."
    ::= 11

sonusDspAvailabilityG711CircuitOnSetCrossThresholdNotification TRAP-TYPE
    ENTERPRISE      sonusNodeResourcesMIBNotifications
    VARIABLES       { sonusNumDspAvailabilityG711CircuitCrossThreshold, 
                      sonusEventDescription, sonusEventClass, 
                      sonusEventLevel, sonusSequenceId, sonusEventTime }
--     STATUS          mandatory
    DESCRIPTION     
            "This trap indicates that the Availability of type G711 Circuit DSP Cross the threshold downward."
    ::= 20

sonusDspAvailabilityToneOnSetCrossThresholdNotification TRAP-TYPE
    ENTERPRISE      sonusNodeResourcesMIBNotifications
    VARIABLES       { sonusNumDspAvailabilityToneCrossThreshold, 
                      sonusEventDescription, sonusEventClass, 
                      sonusEventLevel, sonusSequenceId, sonusEventTime }
--     STATUS          mandatory
    DESCRIPTION     
            "This trap indicates that the Availability of type Tone DSP Cross the threshold downward."
    ::= 21

sonusDspAvailabilityBridgePortOnSetCrossThresholdNotification TRAP-TYPE
    ENTERPRISE      sonusNodeResourcesMIBNotifications
    VARIABLES       { sonusNumDspAvailabilityBridgePortCrossThreshold, 
                      sonusEventDescription, sonusEventClass, 
                      sonusEventLevel, sonusSequenceId, sonusEventTime }
--     STATUS          mandatory
    DESCRIPTION     
            "This trap indicates that the Availability of type Bridge Port DSP Cross the threshold downward."
    ::= 22

sonusDspAvailabilityG729OnSetCrossThresholdNotification TRAP-TYPE
    ENTERPRISE      sonusNodeResourcesMIBNotifications
    VARIABLES       { sonusNumDspAvailabilityG729CrossThreshold, 
                      sonusEventDescription, sonusEventClass, 
                      sonusEventLevel, sonusSequenceId, sonusEventTime }
--     STATUS          mandatory
    DESCRIPTION     
            "This trap indicates that the Availability of type G729 DSP Cross the threshold downward."
    ::= 23

sonusDspAvailabilityG726OnSetCrossThresholdNotification TRAP-TYPE
    ENTERPRISE      sonusNodeResourcesMIBNotifications
    VARIABLES       { sonusNumDspAvailabilityG726CrossThreshold, 
                      sonusEventDescription, sonusEventClass, 
                      sonusEventLevel, sonusSequenceId, sonusEventTime }
--     STATUS          mandatory
    DESCRIPTION     
            "This trap indicates that the Availability of type G726 DSP Cross the threshold downward."
    ::= 24

sonusDspAvailabilityG723OnSetCrossThresholdNotification TRAP-TYPE
    ENTERPRISE      sonusNodeResourcesMIBNotifications
    VARIABLES       { sonusNumDspAvailabilityG723CrossThreshold, 
                      sonusEventDescription, sonusEventClass, 
                      sonusEventLevel, sonusSequenceId, sonusEventTime }
--     STATUS          mandatory
    DESCRIPTION     
            "This trap indicates that the Availability of type G723 DSP Cross the threshold downward."
    ::= 25

sonusDspAvailabilityG711PacketOnSetCrossThresholdNotification TRAP-TYPE
    ENTERPRISE      sonusNodeResourcesMIBNotifications
    VARIABLES       { sonusNumDspAvailabilityG711PacketCrossThreshold, 
                      sonusEventDescription, sonusEventClass, 
                      sonusEventLevel, sonusSequenceId, sonusEventTime }
--     STATUS          mandatory
    DESCRIPTION     
            "This trap indicates that the Availability of type G711 Packet DSP Cross the threshold downward."
    ::= 26

sonusDspAvailabilityT38OnSetCrossThresholdNotification TRAP-TYPE
    ENTERPRISE      sonusNodeResourcesMIBNotifications
    VARIABLES       { sonusNumDspAvailabilityT38CrossThreshold, 
                      sonusEventDescription, sonusEventClass, 
                      sonusEventLevel, sonusSequenceId, sonusEventTime }
--     STATUS          mandatory
    DESCRIPTION     
            "This trap indicates that the Availability of type T38 DSP Cross the threshold downward."
    ::= 27

sonusDspAvailabilityG711CircuitAbateCrossThresholdNotification TRAP-TYPE
    ENTERPRISE      sonusNodeResourcesMIBNotifications
    VARIABLES       { sonusNumDspAvailabilityG711CircuitCrossThreshold, 
                      sonusEventDescription, sonusEventClass, 
                      sonusEventLevel, sonusSequenceId, sonusEventTime }
--     STATUS          mandatory
    DESCRIPTION     
            "This trap indicates that the Availability of type G711 Circuit DSP Cross the threshold upward."
    ::= 28

sonusDspAvailabilityToneAbateCrossThresholdNotification TRAP-TYPE
    ENTERPRISE      sonusNodeResourcesMIBNotifications
    VARIABLES       { sonusNumDspAvailabilityToneCrossThreshold, 
                      sonusEventDescription, sonusEventClass, 
                      sonusEventLevel, sonusSequenceId, sonusEventTime }
--     STATUS          mandatory
    DESCRIPTION     
            "This trap indicates that the Availability of type Tone DSP Cross the threshold downward."
    ::= 29

sonusDspAvailabilityBridgePortAbateCrossThresholdNotification TRAP-TYPE
    ENTERPRISE      sonusNodeResourcesMIBNotifications
    VARIABLES       { sonusNumDspAvailabilityBridgePortCrossThreshold, 
                      sonusEventDescription, sonusEventClass, 
                      sonusEventLevel, sonusSequenceId, sonusEventTime }
--     STATUS          mandatory
    DESCRIPTION     
            "This trap indicates that the Availability of type Bridge Port DSP Cross the threshold downward."
    ::= 30

sonusDspAvailabilityG729AbateCrossThresholdNotification TRAP-TYPE
    ENTERPRISE      sonusNodeResourcesMIBNotifications
    VARIABLES       { sonusNumDspAvailabilityG729CrossThreshold, 
                      sonusEventDescription, sonusEventClass, 
                      sonusEventLevel, sonusSequenceId, sonusEventTime }
--     STATUS          mandatory
    DESCRIPTION     
            "This trap indicates that the Availability of type G729 DSP Cross the threshold downward."
    ::= 31

sonusDspAvailabilityG726AbateCrossThresholdNotification TRAP-TYPE
    ENTERPRISE      sonusNodeResourcesMIBNotifications
    VARIABLES       { sonusNumDspAvailabilityG726CrossThreshold, 
                      sonusEventDescription, sonusEventClass, 
                      sonusEventLevel, sonusSequenceId, sonusEventTime }
--     STATUS          mandatory
    DESCRIPTION     
            "This trap indicates that the Availability of type G726 DSP Cross the threshold downward."
    ::= 32

sonusDspAvailabilityG723AbateCrossThresholdNotification TRAP-TYPE
    ENTERPRISE      sonusNodeResourcesMIBNotifications
    VARIABLES       { sonusNumDspAvailabilityG723CrossThreshold, 
                      sonusEventDescription, sonusEventClass, 
                      sonusEventLevel, sonusSequenceId, sonusEventTime }
--     STATUS          mandatory
    DESCRIPTION     
            "This trap indicates that the Availability of type G723 DSP Cross the threshold downward."
    ::= 33

sonusDspAvailabilityG711PacketAbateCrossThresholdNotification TRAP-TYPE
    ENTERPRISE      sonusNodeResourcesMIBNotifications
    VARIABLES       { sonusNumDspAvailabilityG711PacketCrossThreshold, 
                      sonusEventDescription, sonusEventClass, 
                      sonusEventLevel, sonusSequenceId, sonusEventTime }
--     STATUS          mandatory
    DESCRIPTION     
            "This trap indicates that the Availability of type G711 Packet DSP Cross the threshold downward."
    ::= 34

sonusDspAvailabilityT38AbateCrossThresholdNotification TRAP-TYPE
    ENTERPRISE      sonusNodeResourcesMIBNotifications
    VARIABLES       { sonusNumDspAvailabilityT38CrossThreshold, 
                      sonusEventDescription, sonusEventClass, 
                      sonusEventLevel, sonusSequenceId, sonusEventTime }
--     STATUS          mandatory
    DESCRIPTION     
            "This trap indicates that the Availability of type T38 DSP Cross the threshold downward."
    ::= 35

sonusDspAvailabilityT38EcmOnSetCrossThresholdNotification TRAP-TYPE
    ENTERPRISE      sonusNodeResourcesMIBNotifications
    VARIABLES       { sonusNumDspAvailabilityT38EcmCrossThreshold, 
                      sonusEventDescription, sonusEventClass, 
                      sonusEventLevel, sonusSequenceId, sonusEventTime }
--     STATUS          mandatory
    DESCRIPTION     
            "This trap indicates that the Availability of type T38 ECM
             capable DSP Cross the threshold downward."
    ::= 36

sonusDspAvailabilityT38EcmAbateCrossThresholdNotification TRAP-TYPE
    ENTERPRISE      sonusNodeResourcesMIBNotifications
    VARIABLES       { sonusNumDspAvailabilityT38EcmCrossThreshold, 
                      sonusEventDescription, sonusEventClass, 
                      sonusEventLevel, sonusSequenceId, sonusEventTime }
--     STATUS          mandatory
    DESCRIPTION     
            "This trap indicates that the Availability of type T38 ECM
             capable DSP Cross the threshold downward."
    ::= 37

sonusDspAvailabilityEvrcOnSetCrossThresholdNotification TRAP-TYPE
    ENTERPRISE      sonusNodeResourcesMIBNotifications
    VARIABLES       { sonusNumDspAvailabilityEvrcCrossThreshold, 
                      sonusEventDescription, sonusEventClass, 
                      sonusEventLevel, sonusSequenceId, sonusEventTime }
--     STATUS          mandatory
    DESCRIPTION     
            "This trap indicates that the Availability of type EVRC DSP Cross the threshold downward."
    ::= 38

sonusDspAvailabilityEvrcAbateCrossThresholdNotification TRAP-TYPE
    ENTERPRISE      sonusNodeResourcesMIBNotifications
    VARIABLES       { sonusNumDspAvailabilityEvrcCrossThreshold, 
                      sonusEventDescription, sonusEventClass, 
                      sonusEventLevel, sonusSequenceId, sonusEventTime }
--     STATUS          mandatory
    DESCRIPTION     
            "This trap indicates that the Availability of type EVRC DSP Cross the threshold downward."
    ::= 39

sonusDspAvailabilityGsmOnSetCrossThresholdNotification TRAP-TYPE
    ENTERPRISE      sonusNodeResourcesMIBNotifications
    VARIABLES       { sonusNumDspAvailabilityGsmCrossThreshold, 
                      sonusEventDescription, sonusEventClass, 
                      sonusEventLevel, sonusSequenceId, sonusEventTime }
--     STATUS          mandatory
    DESCRIPTION     
            "This trap indicates that the Availability of type GSM DSP Cross the threshold downward."
    ::= 40

sonusDspAvailabilityGsmAbateCrossThresholdNotification TRAP-TYPE
    ENTERPRISE      sonusNodeResourcesMIBNotifications
    VARIABLES       { sonusNumDspAvailabilityGsmCrossThreshold, 
                      sonusEventDescription, sonusEventClass, 
                      sonusEventLevel, sonusSequenceId, sonusEventTime }
--     STATUS          mandatory
    DESCRIPTION     
            "This trap indicates that the Availability of type GSM DSP Cross the threshold downward."
    ::= 41

sonusDspAvailabilityEvrcb0OnSetCrossThresholdNotification TRAP-TYPE
    ENTERPRISE      sonusNodeResourcesMIBNotifications
    VARIABLES       { sonusNumDspAvailabilityEvrcb0CrossThreshold, 
                      sonusEventDescription, sonusEventClass, 
                      sonusEventLevel, sonusSequenceId, sonusEventTime }
--     STATUS          mandatory
    DESCRIPTION     
            "This trap indicates that the Availability of type EVRCB0 DSP Cross the threshold downward."
    ::= 42

sonusDspAvailabilityEvrcb0AbateCrossThresholdNotification TRAP-TYPE
    ENTERPRISE      sonusNodeResourcesMIBNotifications
    VARIABLES       { sonusNumDspAvailabilityEvrcb0CrossThreshold, 
                      sonusEventDescription, sonusEventClass, 
                      sonusEventLevel, sonusSequenceId, sonusEventTime }
--     STATUS          mandatory
    DESCRIPTION     
            "This trap indicates that the Availability of type EVRCB0 DSP Cross the threshold downward."
    ::= 43

sonusDspAvailabilityG722OnSetCrossThresholdNotification TRAP-TYPE
    ENTERPRISE      sonusNodeResourcesMIBNotifications
    VARIABLES       { sonusNumDspAvailabilityG722CrossThreshold, 
                      sonusEventDescription, sonusEventClass, 
                      sonusEventLevel, sonusSequenceId, sonusEventTime }
--     STATUS          mandatory
    DESCRIPTION     
            "This trap indicates that the Availability of type G722 DSP Cross the threshold downward."
    ::= 46

sonusDspAvailabilityG722AbateCrossThresholdNotification TRAP-TYPE
    ENTERPRISE      sonusNodeResourcesMIBNotifications
    VARIABLES       { sonusNumDspAvailabilityG722CrossThreshold, 
                      sonusEventDescription, sonusEventClass, 
                      sonusEventLevel, sonusSequenceId, sonusEventTime }
--     STATUS          mandatory
    DESCRIPTION     
            "This trap indicates that the Availability of type G722 DSP Cross the threshold downward."
    ::= 47

sonusDspAvailabilityAmrwbOnSetCrossThresholdNotification TRAP-TYPE
    ENTERPRISE      sonusNodeResourcesMIBNotifications
    VARIABLES       { sonusNumDspAvailabilityAmrwbCrossThreshold, 
                      sonusEventDescription, sonusEventClass, 
                      sonusEventLevel, sonusSequenceId, sonusEventTime }
--     STATUS          mandatory
    DESCRIPTION     
            "This trap indicates that the Availability of type AMRWB DSP Cross the threshold downward."
    ::= 48

sonusDspAvailabilityAmrwbAbateCrossThresholdNotification TRAP-TYPE
    ENTERPRISE      sonusNodeResourcesMIBNotifications
    VARIABLES       { sonusNumDspAvailabilityAmrwbCrossThreshold, 
                      sonusEventDescription, sonusEventClass, 
                      sonusEventLevel, sonusSequenceId, sonusEventTime }
--     STATUS          mandatory
    DESCRIPTION     
            "This trap indicates that the Availability of type G72MRWB DSP Cross the threshold downward."
    ::= 49

sonusNodeResourcesSonicBusUsageHighSetNotification TRAP-TYPE
    ENTERPRISE      sonusNodeResourcesMIBNotifications
    VARIABLES       { sonusEventDescription, sonusEventClass, 
                      sonusEventLevel, sonusSequenceId, sonusEventTime }
--     STATUS          mandatory
    DESCRIPTION     
            "This trap indicates that Midplane usage has crossed the on-set threshold configured."
    ::= 50

sonusNodeResourcesSonicBusUsageHighClearNotification TRAP-TYPE
    ENTERPRISE      sonusNodeResourcesMIBNotifications
    VARIABLES       { sonusEventDescription, sonusEventClass, 
                      sonusEventLevel, sonusSequenceId, sonusEventTime }
--     STATUS          mandatory
    DESCRIPTION     
            "This trap indicates that Midplane usage has come down below the abating threshold configured."
    ::= 51

sonusNodeResourcesCallTraceActiveNotification TRAP-TYPE
    ENTERPRISE      sonusNodeResourcesMIBNotifications
    VARIABLES       { sonusEventDescription, sonusEventClass, 
                      sonusEventLevel, sonusSequenceId, sonusEventTime }
--     STATUS          mandatory
    DESCRIPTION     
            "This trap indicates that call trace started."
    ::= 52

sonusNodeResourcesCallTraceDisableNotification TRAP-TYPE
    ENTERPRISE      sonusNodeResourcesMIBNotifications
    VARIABLES       { sonusEventDescription, sonusEventClass, 
                      sonusEventLevel, sonusSequenceId, sonusEventTime, 
                      sonusCallTraceDisableReason }
--     STATUS          mandatory
    DESCRIPTION     
            "This trap indicates that call trace is disabled/inactive. This trap clears the ALARM raised by the trap 'callTraceActive'. "
    ::= 53

END -- end of module SONUS-NODE-RESOURCES-MIB.
