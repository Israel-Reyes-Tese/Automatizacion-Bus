--
-- This SMIv1 module has been generated by smidump 0.2-cvs. Do not edit.
--

RIVERSTONE-PRODUCTS-MIB DEFINITIONS ::= BEGIN

IMPORTS
    riverstoneProducts
        FROM RIVERSTONE-SMI-MIB;

rsFamilyMIB OBJECT IDENTIFIER
    ::= { riverstoneProducts 1 }

-- rsFamilyMIB MODULE-IDENTITY
--     LAST-UPDATED    "200210100000Z"
--     ORGANIZATION    
--             "Riverstone Networks, Inc"
--     CONTACT-INFO    
--             "Riverstone Networks, Inc
--              5200 Great America Parkway
--              Santa Clara CA USA 95054
--              PHONE:+1 408.878.6500
--              EMAIL: nms-eng@riverstonenet.com
--              WEB: http://www.riverstonenet.com"
--     DESCRIPTION     
--             "This mib module defines system Object Identifier values for sysObjectID.0 for 
--              network elements manufactured and sold by Riverstone Networks, Inc
--              http://www.riverstonenet.com/products. 
--              
--              Contains sysObjectIDs for RS Procut Line of Multi Layer Switch Routers.
--              
--              Copyright (C) Riverstone Networks, Inc 2000"
--     REVISION        "200004160000Z"
--     DESCRIPTION     
--             "Riverstone RS Family of products object IDs added."
--     REVISION        "200011280000Z"
--     DESCRIPTION     
--             "Riverstone RS1000 object ID added. Changed IA1000->IA1100, IA1100->IA1200(typo)"
--     REVISION        "200011290000Z"
--     DESCRIPTION     
--             "Riverstone IA1500 object ID added."
--     REVISION        "200011300000Z"
--     DESCRIPTION     
--             "Riverstone RS38000 object ID added."
--     REVISION        "200106140000Z"
--     DESCRIPTION     
--             "Riverstone RS16000 object ID added; Changed IA1500 to IA3000."
--     REVISION        "200208130000Z"
--     DESCRIPTION     
--             "Riverstone ES family object IDs added - ES 500, ES 10170."
--     REVISION        "200210100000Z"
--     DESCRIPTION     
--             "Riverstone RS1100, RS3100, RS3200 object IDs added."
--     ::= { riverstoneProducts 1 }


rs8000 OBJECT IDENTIFIER
    ::= { rsFamilyMIB 1 }

rs8600 OBJECT IDENTIFIER
    ::= { rsFamilyMIB 2 }

rs2000 OBJECT IDENTIFIER
    ::= { rsFamilyMIB 3 }

rs2100 OBJECT IDENTIFIER
    ::= { rsFamilyMIB 4 }

rs3000 OBJECT IDENTIFIER
    ::= { rsFamilyMIB 5 }

rs32000 OBJECT IDENTIFIER
    ::= { rsFamilyMIB 6 }

rs1000 OBJECT IDENTIFIER
    ::= { rsFamilyMIB 8 }

rs38000 OBJECT IDENTIFIER
    ::= { rsFamilyMIB 9 }

rs16000 OBJECT IDENTIFIER
    ::= { rsFamilyMIB 10 }

rs3100 OBJECT IDENTIFIER
    ::= { rsFamilyMIB 11 }

rs3200 OBJECT IDENTIFIER
    ::= { rsFamilyMIB 12 }

rs1100 OBJECT IDENTIFIER
    ::= { rsFamilyMIB 13 }

rsIA1100 OBJECT IDENTIFIER
    ::= { rsFamilyMIB 22 }

rsIA1200 OBJECT IDENTIFIER
    ::= { rsFamilyMIB 23 }

rsIA3000 OBJECT IDENTIFIER
    ::= { rsFamilyMIB 27 }

es500 OBJECT IDENTIFIER
    ::= { rsFamilyMIB 31 }

es10170 OBJECT IDENTIFIER
    ::= { rsFamilyMIB 32 }

xgs9016 OBJECT IDENTIFIER
    ::= { rsFamilyMIB 51 }

xgs9008 OBJECT IDENTIFIER
    ::= { rsFamilyMIB 52 }

END -- end of module RIVERSTONE-PRODUCTS-MIB.
