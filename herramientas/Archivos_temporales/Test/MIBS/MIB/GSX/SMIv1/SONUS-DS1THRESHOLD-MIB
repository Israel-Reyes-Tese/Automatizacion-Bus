--
-- This SMIv1 module has been generated by smidump 0.2-cvs. Do not edit.
--

SONUS-DS1THRESHOLD-MIB DEFINITIONS ::= BEGIN

IMPORTS
    OBJECT-TYPE
        FROM RFC-1212
    TRAP-TYPE
        FROM RFC-1215
    sonusDs1Index, sonusEventClass, sonusEventDescription, 
    sonusEventLevel, sonusEventTime, sonusPortIndex, sonusSequenceId, 
    sonusShelfIndex, sonusSlotIndex
        FROM SONUS-COMMON-MIB
    sonusDs1Profile, sonusDs1ThresholdType, 
    sonusDsx1MIBNotificationsObjects, sonusDsx1MIBNotificationsPrefix, 
    sonusDsx1MIBObjects
        FROM SONUS-DS1-MIB
    sonusCircuitMIBs
        FROM SONUS-SMI
    SonusAdminState, SonusShelfIndex, SonusSlotIndex
        FROM SONUS-TC;

sonusDsx1ThresholdMIB OBJECT IDENTIFIER
    ::= { sonusCircuitMIBs 5 }

-- sonusDsx1ThresholdMIB MODULE-IDENTITY
--     LAST-UPDATED    "200703280000Z"
--     ORGANIZATION    
--             "Sonus Networks, Inc."
--     CONTACT-INFO    
--             "   Customer Support    
--              Sonus Networks, Inc.
--              7 Technology Park Drive
--              Westford, MA 01886
--              USA
--              
--              Tel: 978-614-8100
--              Fax: 978-614-8609"
--     DESCRIPTION     
--             "The MIB Module for DS1 Management."
--     ::= { sonusCircuitMIBs 5 }


sonusDs1ThresholdProfileTable OBJECT-TYPE
    SYNTAX          SEQUENCE OF SonusDs1ThresholdProfileEntry
    ACCESS          not-accessible
    STATUS          mandatory
    DESCRIPTION     
            "Table for T1/E1 threshold profile"
    ::= { sonusDs1Profile 3 }

sonusDs1ThresholdProfileEntry OBJECT-TYPE
    SYNTAX          SonusDs1ThresholdProfileEntry
    ACCESS          not-accessible
    STATUS          mandatory
    DESCRIPTION     
            "Entry in Table consisting of T1/E1 threshold profile."
    INDEX           { sonusDs1ThresholdProfileIndex }
    ::= { sonusDs1ThresholdProfileTable 1 }

SonusDs1ThresholdProfileEntry ::=
    SEQUENCE {
        sonusDs1ThresholdProfileIndex   INTEGER,
        sonusDs1ThresholdProfileMinorLCVThreshold         INTEGER,
        sonusDs1ThresholdProfileMinorLESThreshold         INTEGER,
        sonusDs1ThresholdProfileMinorLSESThreshold          INTEGER,
        sonusDs1ThresholdProfileMinorPCVThreshold         INTEGER,
        sonusDs1ThresholdProfileMinorPESThreshold         INTEGER,
        sonusDs1ThresholdProfileMinorPSESThreshold          INTEGER,
        sonusDs1ThresholdProfileMinorCSSThreshold         INTEGER,
        sonusDs1ThresholdProfileMinorSASThreshold         INTEGER,
        sonusDs1ThresholdProfileMinorUASThreshold         INTEGER,
        sonusDs1ThresholdProfileDayMinorLCVThreshold            INTEGER,
        sonusDs1ThresholdProfileDayMinorLESThreshold            INTEGER,
        sonusDs1ThresholdProfileDayMinorLSESThreshold             INTEGER,
        sonusDs1ThresholdProfileDayMinorPCVThreshold            INTEGER,
        sonusDs1ThresholdProfileDayMinorPESThreshold            INTEGER,
        sonusDs1ThresholdProfileDayMinorPSESThreshold             INTEGER,
        sonusDs1ThresholdProfileDayMinorCSSThreshold            INTEGER,
        sonusDs1ThresholdProfileDayMinorSASThreshold            INTEGER,
        sonusDs1ThresholdProfileDayMinorUASThreshold            INTEGER,
        sonusDs1ThresholdProfileMajorLCVThreshold         INTEGER,
        sonusDs1ThresholdProfileMajorLESThreshold         INTEGER,
        sonusDs1ThresholdProfileMajorLSESThreshold          INTEGER,
        sonusDs1ThresholdProfileMajorPCVThreshold         INTEGER,
        sonusDs1ThresholdProfileMajorPESThreshold         INTEGER,
        sonusDs1ThresholdProfileMajorPSESThreshold          INTEGER,
        sonusDs1ThresholdProfileMajorCSSThreshold         INTEGER,
        sonusDs1ThresholdProfileMajorSASThreshold         INTEGER,
        sonusDs1ThresholdProfileMajorUASThreshold         INTEGER,
        sonusDs1ThresholdProfileDayMajorLCVThreshold            INTEGER,
        sonusDs1ThresholdProfileDayMajorLESThreshold            INTEGER,
        sonusDs1ThresholdProfileDayMajorLSESThreshold             INTEGER,
        sonusDs1ThresholdProfileDayMajorPCVThreshold            INTEGER,
        sonusDs1ThresholdProfileDayMajorPESThreshold            INTEGER,
        sonusDs1ThresholdProfileDayMajorPSESThreshold             INTEGER,
        sonusDs1ThresholdProfileDayMajorCSSThreshold            INTEGER,
        sonusDs1ThresholdProfileDayMajorSASThreshold            INTEGER,
        sonusDs1ThresholdProfileDayMajorUASThreshold            INTEGER,
        sonusDs1ThresholdProfileCriticalLCVThreshold            INTEGER,
        sonusDs1ThresholdProfileCriticalLESThreshold            INTEGER,
        sonusDs1ThresholdProfileCriticalLSESThreshold             INTEGER,
        sonusDs1ThresholdProfileCriticalPCVThreshold            INTEGER,
        sonusDs1ThresholdProfileCriticalPESThreshold            INTEGER,
        sonusDs1ThresholdProfileCriticalPSESThreshold             INTEGER,
        sonusDs1ThresholdProfileCriticalCSSThreshold            INTEGER,
        sonusDs1ThresholdProfileCriticalSASThreshold            INTEGER,
        sonusDs1ThresholdProfileCriticalUASThreshold            INTEGER,
        sonusDs1ThresholdProfileDayCriticalLCVThreshold               INTEGER,
        sonusDs1ThresholdProfileDayCriticalLESThreshold               INTEGER,
        sonusDs1ThresholdProfileDayCriticalLSESThreshold                INTEGER,
        sonusDs1ThresholdProfileDayCriticalPCVThreshold               INTEGER,
        sonusDs1ThresholdProfileDayCriticalPESThreshold               INTEGER,
        sonusDs1ThresholdProfileDayCriticalPSESThreshold                INTEGER,
        sonusDs1ThresholdProfileDayCriticalCSSThreshold               INTEGER,
        sonusDs1ThresholdProfileDayCriticalSASThreshold               INTEGER,
        sonusDs1ThresholdProfileDayCriticalUASThreshold               INTEGER,
        sonusDs1ThresholdProfileLCVTcaFilter    SonusAdminState,
        sonusDs1ThresholdProfileLESTcaFilter    SonusAdminState,
        sonusDs1ThresholdProfileLSESTcaFilter     SonusAdminState,
        sonusDs1ThresholdProfilePCVTcaFilter    SonusAdminState,
        sonusDs1ThresholdProfilePESTcaFilter    SonusAdminState,
        sonusDs1ThresholdProfilePSESTcaFilter     SonusAdminState,
        sonusDs1ThresholdProfileCSSTcaFilter    SonusAdminState,
        sonusDs1ThresholdProfileSASTcaFilter    SonusAdminState,
        sonusDs1ThresholdProfileUASTcaFilter    SonusAdminState,
        sonusDs1ThresholdProfileReportMinorCriticalTca              SonusAdminState,
        sonusDs1ThresholdProfileReportDs1OosTca       SonusAdminState,
        sonusDs1ThresholdProfileMinorLCVThresholdState              SonusAdminState,
        sonusDs1ThresholdProfileMinorLESThresholdState              SonusAdminState,
        sonusDs1ThresholdProfileMinorLSESThresholdState               SonusAdminState,
        sonusDs1ThresholdProfileMinorPCVThresholdState              SonusAdminState,
        sonusDs1ThresholdProfileMinorPESThresholdState              SonusAdminState,
        sonusDs1ThresholdProfileMinorPSESThresholdState               SonusAdminState,
        sonusDs1ThresholdProfileMinorCSSThresholdState              SonusAdminState,
        sonusDs1ThresholdProfileMinorSASThresholdState              SonusAdminState,
        sonusDs1ThresholdProfileMinorUASThresholdState              SonusAdminState,
        sonusDs1ThresholdProfileDayMinorLCVThresholdState                 SonusAdminState,
        sonusDs1ThresholdProfileDayMinorLESThresholdState                 SonusAdminState,
        sonusDs1ThresholdProfileDayMinorLSESThresholdState                  SonusAdminState,
        sonusDs1ThresholdProfileDayMinorPCVThresholdState                 SonusAdminState,
        sonusDs1ThresholdProfileDayMinorPESThresholdState                 SonusAdminState,
        sonusDs1ThresholdProfileDayMinorPSESThresholdState                  SonusAdminState,
        sonusDs1ThresholdProfileDayMinorCSSThresholdState                 SonusAdminState,
        sonusDs1ThresholdProfileDayMinorSASThresholdState                 SonusAdminState,
        sonusDs1ThresholdProfileDayMinorUASThresholdState                 SonusAdminState,
        sonusDs1ThresholdProfileMajorLCVThresholdState              SonusAdminState,
        sonusDs1ThresholdProfileMajorLESThresholdState              SonusAdminState,
        sonusDs1ThresholdProfileMajorLSESThresholdState               SonusAdminState,
        sonusDs1ThresholdProfileMajorPCVThresholdState              SonusAdminState,
        sonusDs1ThresholdProfileMajorPESThresholdState              SonusAdminState,
        sonusDs1ThresholdProfileMajorPSESThresholdState               SonusAdminState,
        sonusDs1ThresholdProfileMajorCSSThresholdState              SonusAdminState,
        sonusDs1ThresholdProfileMajorSASThresholdState              SonusAdminState,
        sonusDs1ThresholdProfileMajorUASThresholdState              SonusAdminState,
        sonusDs1ThresholdProfileDayMajorLCVThresholdState                 SonusAdminState,
        sonusDs1ThresholdProfileDayMajorLESThresholdState                 SonusAdminState,
        sonusDs1ThresholdProfileDayMajorLSESThresholdState                  SonusAdminState,
        sonusDs1ThresholdProfileDayMajorPCVThresholdState                 SonusAdminState,
        sonusDs1ThresholdProfileDayMajorPESThresholdState                 SonusAdminState,
        sonusDs1ThresholdProfileDayMajorPSESThresholdState                  SonusAdminState,
        sonusDs1ThresholdProfileDayMajorCSSThresholdState                 SonusAdminState,
        sonusDs1ThresholdProfileDayMajorSASThresholdState                 SonusAdminState,
        sonusDs1ThresholdProfileDayMajorUASThresholdState                 SonusAdminState,
        sonusDs1ThresholdProfileCriticalLCVThresholdState                 SonusAdminState,
        sonusDs1ThresholdProfileCriticalLESThresholdState                 SonusAdminState,
        sonusDs1ThresholdProfileCriticalLSESThresholdState                  SonusAdminState,
        sonusDs1ThresholdProfileCriticalPCVThresholdState                 SonusAdminState,
        sonusDs1ThresholdProfileCriticalPESThresholdState                 SonusAdminState,
        sonusDs1ThresholdProfileCriticalPSESThresholdState                  SonusAdminState,
        sonusDs1ThresholdProfileCriticalCSSThresholdState                 SonusAdminState,
        sonusDs1ThresholdProfileCriticalSASThresholdState                 SonusAdminState,
        sonusDs1ThresholdProfileCriticalUASThresholdState                 SonusAdminState,
        sonusDs1ThresholdProfileDayCriticalLCVThresholdState                    SonusAdminState,
        sonusDs1ThresholdProfileDayCriticalLESThresholdState                    SonusAdminState,
        sonusDs1ThresholdProfileDayCriticalLSESThresholdState                     SonusAdminState,
        sonusDs1ThresholdProfileDayCriticalPCVThresholdState                    SonusAdminState,
        sonusDs1ThresholdProfileDayCriticalPESThresholdState                    SonusAdminState,
        sonusDs1ThresholdProfileDayCriticalPSESThresholdState                     SonusAdminState,
        sonusDs1ThresholdProfileDayCriticalCSSThresholdState                    SonusAdminState,
        sonusDs1ThresholdProfileDayCriticalSASThresholdState                    SonusAdminState,
        sonusDs1ThresholdProfileDayCriticalUASThresholdState                    SonusAdminState,
        sonusDs1ThresholdProfileLCVTcaFilterState         SonusAdminState,
        sonusDs1ThresholdProfileLESTcaFilterState         SonusAdminState,
        sonusDs1ThresholdProfileLSESTcaFilterState          SonusAdminState,
        sonusDs1ThresholdProfilePCVTcaFilterState         SonusAdminState,
        sonusDs1ThresholdProfilePESTcaFilterState         SonusAdminState,
        sonusDs1ThresholdProfilePSESTcaFilterState          SonusAdminState,
        sonusDs1ThresholdProfileCSSTcaFilterState         SonusAdminState,
        sonusDs1ThresholdProfileSASTcaFilterState         SonusAdminState,
        sonusDs1ThresholdProfileUASTcaFilterState         SonusAdminState,
        sonusDs1ThresholdProfileReportMinorCriticalTcaState                   SonusAdminState,
        sonusDs1ThresholdProfileReportDs1OosTcaState            SonusAdminState
    }

sonusDs1ThresholdProfileIndex OBJECT-TYPE
    SYNTAX          INTEGER
    ACCESS          read-only
    STATUS          mandatory
    DESCRIPTION     
            "Index into the profile table"
    ::= { sonusDs1ThresholdProfileEntry 1 }

sonusDs1ThresholdProfileMinorLCVThreshold OBJECT-TYPE
    SYNTAX          INTEGER (1..16383)
    ACCESS          read-write
    STATUS          mandatory
    DESCRIPTION     
            "Line Code Violations Minor threshold value for 15 minute interval."
    DEFVAL          { 10672 }
    ::= { sonusDs1ThresholdProfileEntry 2 }

sonusDs1ThresholdProfileMinorLESThreshold OBJECT-TYPE
    SYNTAX          INTEGER (1..900)
    ACCESS          read-write
    STATUS          mandatory
    DESCRIPTION     
            "Line Errored Seconds Minor threshold value for 15 minute interval."
    DEFVAL          { 52 }
    ::= { sonusDs1ThresholdProfileEntry 3 }

sonusDs1ThresholdProfileMinorLSESThreshold OBJECT-TYPE
    SYNTAX          INTEGER (1..900)
    ACCESS          read-write
    STATUS          mandatory
    DESCRIPTION     
            "Line Severely Errored Seconds Minor threshold value for 15 minute interval."
    DEFVAL          { 8 }
    ::= { sonusDs1ThresholdProfileEntry 4 }

sonusDs1ThresholdProfileMinorPCVThreshold OBJECT-TYPE
    SYNTAX          INTEGER (1..16383)
    ACCESS          read-write
    STATUS          mandatory
    DESCRIPTION     
            "Path Code Violations Minor threshold value for 15 minute interval."
    DEFVAL          { 10637 }
    ::= { sonusDs1ThresholdProfileEntry 5 }

sonusDs1ThresholdProfileMinorPESThreshold OBJECT-TYPE
    SYNTAX          INTEGER (1..900)
    ACCESS          read-write
    STATUS          mandatory
    DESCRIPTION     
            "Path Errored Seconds Minor threshold value for 15 minute interval."
    DEFVAL          { 52 }
    ::= { sonusDs1ThresholdProfileEntry 6 }

sonusDs1ThresholdProfileMinorPSESThreshold OBJECT-TYPE
    SYNTAX          INTEGER (1..900)
    ACCESS          read-write
    STATUS          mandatory
    DESCRIPTION     
            "Path Severely Errored Seconds Minor threshold value for 15 minute interval."
    DEFVAL          { 8 }
    ::= { sonusDs1ThresholdProfileEntry 7 }

sonusDs1ThresholdProfileMinorCSSThreshold OBJECT-TYPE
    SYNTAX          INTEGER (1..900)
    ACCESS          read-write
    STATUS          mandatory
    DESCRIPTION     
            "Controlled Slip Seconds Minor threshold value for 15 minute interval."
    DEFVAL          { 1 }
    ::= { sonusDs1ThresholdProfileEntry 8 }

sonusDs1ThresholdProfileMinorSASThreshold OBJECT-TYPE
    SYNTAX          INTEGER (1..900)
    ACCESS          read-write
    STATUS          mandatory
    DESCRIPTION     
            "SEF/AIS Seconds Minor threshold value for 15 minute interval."
    DEFVAL          { 1 }
    ::= { sonusDs1ThresholdProfileEntry 9 }

sonusDs1ThresholdProfileMinorUASThreshold OBJECT-TYPE
    SYNTAX          INTEGER (1..900)
    ACCESS          read-write
    STATUS          mandatory
    DESCRIPTION     
            "Unavailable Seconds Minor threshold value for 15 minute interval."
    DEFVAL          { 8 }
    ::= { sonusDs1ThresholdProfileEntry 10 }

sonusDs1ThresholdProfileDayMinorLCVThreshold OBJECT-TYPE
    SYNTAX          INTEGER (1..1048575)
    ACCESS          read-write
    STATUS          mandatory
    DESCRIPTION     
            "Line Code Violations Minor threshold value for 24 hour interval."
    DEFVAL          { 106720 }
    ::= { sonusDs1ThresholdProfileEntry 11 }

sonusDs1ThresholdProfileDayMinorLESThreshold OBJECT-TYPE
    SYNTAX          INTEGER (1..65535)
    ACCESS          read-write
    STATUS          mandatory
    DESCRIPTION     
            "Line Errored Seconds Minor threshold value for 24 hour interval."
    DEFVAL          { 518 }
    ::= { sonusDs1ThresholdProfileEntry 12 }

sonusDs1ThresholdProfileDayMinorLSESThreshold OBJECT-TYPE
    SYNTAX          INTEGER (1..65535)
    ACCESS          read-write
    STATUS          mandatory
    DESCRIPTION     
            "Line Severely Errored Seconds Minor threshold value for 24 hour interval."
    DEFVAL          { 80 }
    ::= { sonusDs1ThresholdProfileEntry 13 }

sonusDs1ThresholdProfileDayMinorPCVThreshold OBJECT-TYPE
    SYNTAX          INTEGER (1..1048575)
    ACCESS          read-write
    STATUS          mandatory
    DESCRIPTION     
            "Path Code Violations Minor threshold value for 24 hour interval."
    DEFVAL          { 106368 }
    ::= { sonusDs1ThresholdProfileEntry 14 }

sonusDs1ThresholdProfileDayMinorPESThreshold OBJECT-TYPE
    SYNTAX          INTEGER (1..65535)
    ACCESS          read-write
    STATUS          mandatory
    DESCRIPTION     
            "Path Errored Seconds Minor threshold value for 24 hour interval."
    DEFVAL          { 518 }
    ::= { sonusDs1ThresholdProfileEntry 15 }

sonusDs1ThresholdProfileDayMinorPSESThreshold OBJECT-TYPE
    SYNTAX          INTEGER (1..65535)
    ACCESS          read-write
    STATUS          mandatory
    DESCRIPTION     
            "Path Severely Errored Seconds Minor threshold value for 24 hour interval."
    DEFVAL          { 80 }
    ::= { sonusDs1ThresholdProfileEntry 16 }

sonusDs1ThresholdProfileDayMinorCSSThreshold OBJECT-TYPE
    SYNTAX          INTEGER (1..65535)
    ACCESS          read-write
    STATUS          mandatory
    DESCRIPTION     
            "Controlled Slip Seconds Minor threshold value for 24 hour interval."
    DEFVAL          { 4 }
    ::= { sonusDs1ThresholdProfileEntry 17 }

sonusDs1ThresholdProfileDayMinorSASThreshold OBJECT-TYPE
    SYNTAX          INTEGER (1..65535)
    ACCESS          read-write
    STATUS          mandatory
    DESCRIPTION     
            "SES/AIS Seconds Minor threshold value for 24 hour interval."
    DEFVAL          { 14 }
    ::= { sonusDs1ThresholdProfileEntry 18 }

sonusDs1ThresholdProfileDayMinorUASThreshold OBJECT-TYPE
    SYNTAX          INTEGER (1..65535)
    ACCESS          read-write
    STATUS          mandatory
    DESCRIPTION     
            "Unavailable Seconds Minor threshold value for 24 hour interval."
    DEFVAL          { 8 }
    ::= { sonusDs1ThresholdProfileEntry 19 }

sonusDs1ThresholdProfileMajorLCVThreshold OBJECT-TYPE
    SYNTAX          INTEGER (1..16383)
    ACCESS          read-write
    STATUS          mandatory
    DESCRIPTION     
            "Line Code Violations Major threshold value for 15 minute interval."
    DEFVAL          { 13340 }
    ::= { sonusDs1ThresholdProfileEntry 20 }

sonusDs1ThresholdProfileMajorLESThreshold OBJECT-TYPE
    SYNTAX          INTEGER (1..900)
    ACCESS          read-write
    STATUS          mandatory
    DESCRIPTION     
            "Line Errored Seconds Major threshold value for 15 minute interval."
    DEFVAL          { 65 }
    ::= { sonusDs1ThresholdProfileEntry 21 }

sonusDs1ThresholdProfileMajorLSESThreshold OBJECT-TYPE
    SYNTAX          INTEGER (1..900)
    ACCESS          read-write
    STATUS          mandatory
    DESCRIPTION     
            "Line Severely Errored Seconds Major threshold value for 15 minute interval."
    DEFVAL          { 10 }
    ::= { sonusDs1ThresholdProfileEntry 22 }

sonusDs1ThresholdProfileMajorPCVThreshold OBJECT-TYPE
    SYNTAX          INTEGER (1..16383)
    ACCESS          read-write
    STATUS          mandatory
    DESCRIPTION     
            "Path Code Violations Major threshold value for 15 minute interval."
    DEFVAL          { 13296 }
    ::= { sonusDs1ThresholdProfileEntry 23 }

sonusDs1ThresholdProfileMajorPESThreshold OBJECT-TYPE
    SYNTAX          INTEGER (1..900)
    ACCESS          read-write
    STATUS          mandatory
    DESCRIPTION     
            "Path Errored Seconds Major threshold value for 15 minute interval."
    DEFVAL          { 65 }
    ::= { sonusDs1ThresholdProfileEntry 24 }

sonusDs1ThresholdProfileMajorPSESThreshold OBJECT-TYPE
    SYNTAX          INTEGER (1..900)
    ACCESS          read-write
    STATUS          mandatory
    DESCRIPTION     
            "Path Severely Errored Seconds Major threshold value for 15 minute interval."
    DEFVAL          { 10 }
    ::= { sonusDs1ThresholdProfileEntry 25 }

sonusDs1ThresholdProfileMajorCSSThreshold OBJECT-TYPE
    SYNTAX          INTEGER (1..900)
    ACCESS          read-write
    STATUS          mandatory
    DESCRIPTION     
            "Controlled Slip Seconds Major threshold value for 15 minute interval."
    DEFVAL          { 2 }
    ::= { sonusDs1ThresholdProfileEntry 26 }

sonusDs1ThresholdProfileMajorSASThreshold OBJECT-TYPE
    SYNTAX          INTEGER (1..900)
    ACCESS          read-write
    STATUS          mandatory
    DESCRIPTION     
            "SEF/AIS Seconds Major threshold value for 15 minute interval."
    DEFVAL          { 2 }
    ::= { sonusDs1ThresholdProfileEntry 27 }

sonusDs1ThresholdProfileMajorUASThreshold OBJECT-TYPE
    SYNTAX          INTEGER (1..900)
    ACCESS          read-write
    STATUS          mandatory
    DESCRIPTION     
            "Unavailable Seconds Major threshold value for 15 minute interval."
    DEFVAL          { 10 }
    ::= { sonusDs1ThresholdProfileEntry 28 }

sonusDs1ThresholdProfileDayMajorLCVThreshold OBJECT-TYPE
    SYNTAX          INTEGER (1..1048575)
    ACCESS          read-write
    STATUS          mandatory
    DESCRIPTION     
            "Line Code Violations Major threshold value for 24 hour interval."
    DEFVAL          { 133400 }
    ::= { sonusDs1ThresholdProfileEntry 29 }

sonusDs1ThresholdProfileDayMajorLESThreshold OBJECT-TYPE
    SYNTAX          INTEGER (1..65535)
    ACCESS          read-write
    STATUS          mandatory
    DESCRIPTION     
            "Line Errored Seconds Major threshold value for 24 hour interval."
    DEFVAL          { 648 }
    ::= { sonusDs1ThresholdProfileEntry 30 }

sonusDs1ThresholdProfileDayMajorLSESThreshold OBJECT-TYPE
    SYNTAX          INTEGER (1..65535)
    ACCESS          read-write
    STATUS          mandatory
    DESCRIPTION     
            "Line Severely Errored Seconds Major threshold value for 24 hour interval."
    DEFVAL          { 100 }
    ::= { sonusDs1ThresholdProfileEntry 31 }

sonusDs1ThresholdProfileDayMajorPCVThreshold OBJECT-TYPE
    SYNTAX          INTEGER (1..1048575)
    ACCESS          read-write
    STATUS          mandatory
    DESCRIPTION     
            "Path Code Violations Major threshold value for 24 hour interval."
    DEFVAL          { 132960 }
    ::= { sonusDs1ThresholdProfileEntry 32 }

sonusDs1ThresholdProfileDayMajorPESThreshold OBJECT-TYPE
    SYNTAX          INTEGER (1..65535)
    ACCESS          read-write
    STATUS          mandatory
    DESCRIPTION     
            "Path Errored Seconds Major threshold value for 24 hour interval."
    DEFVAL          { 648 }
    ::= { sonusDs1ThresholdProfileEntry 33 }

sonusDs1ThresholdProfileDayMajorPSESThreshold OBJECT-TYPE
    SYNTAX          INTEGER (1..65535)
    ACCESS          read-write
    STATUS          mandatory
    DESCRIPTION     
            "Path Severely Errored Seconds Major threshold value for 24 hour interval."
    DEFVAL          { 100 }
    ::= { sonusDs1ThresholdProfileEntry 34 }

sonusDs1ThresholdProfileDayMajorCSSThreshold OBJECT-TYPE
    SYNTAX          INTEGER (1..65535)
    ACCESS          read-write
    STATUS          mandatory
    DESCRIPTION     
            "Controlled Slip Seconds Major threshold value for 24 hour interval."
    DEFVAL          { 5 }
    ::= { sonusDs1ThresholdProfileEntry 35 }

sonusDs1ThresholdProfileDayMajorSASThreshold OBJECT-TYPE
    SYNTAX          INTEGER (1..65535)
    ACCESS          read-write
    STATUS          mandatory
    DESCRIPTION     
            "SES/AIS Seconds Major threshold value for 24 hour interval."
    DEFVAL          { 17 }
    ::= { sonusDs1ThresholdProfileEntry 36 }

sonusDs1ThresholdProfileDayMajorUASThreshold OBJECT-TYPE
    SYNTAX          INTEGER (1..65535)
    ACCESS          read-write
    STATUS          mandatory
    DESCRIPTION     
            "Unavailable Seconds Major threshold value for 24 hour interval."
    DEFVAL          { 10 }
    ::= { sonusDs1ThresholdProfileEntry 37 }

sonusDs1ThresholdProfileCriticalLCVThreshold OBJECT-TYPE
    SYNTAX          INTEGER (1..16383)
    ACCESS          read-write
    STATUS          mandatory
    DESCRIPTION     
            "Line Code Violations Critical threshold value for 15 minute interval."
    DEFVAL          { 16008 }
    ::= { sonusDs1ThresholdProfileEntry 38 }

sonusDs1ThresholdProfileCriticalLESThreshold OBJECT-TYPE
    SYNTAX          INTEGER (1..900)
    ACCESS          read-write
    STATUS          mandatory
    DESCRIPTION     
            "Line Errored Seconds Critical threshold value for 15 minute interval."
    DEFVAL          { 78 }
    ::= { sonusDs1ThresholdProfileEntry 39 }

sonusDs1ThresholdProfileCriticalLSESThreshold OBJECT-TYPE
    SYNTAX          INTEGER (1..900)
    ACCESS          read-write
    STATUS          mandatory
    DESCRIPTION     
            "Line Severely Errored Seconds Critical threshold value for 15 minute interval."
    DEFVAL          { 12 }
    ::= { sonusDs1ThresholdProfileEntry 40 }

sonusDs1ThresholdProfileCriticalPCVThreshold OBJECT-TYPE
    SYNTAX          INTEGER (1..16383)
    ACCESS          read-write
    STATUS          mandatory
    DESCRIPTION     
            "Path Code Violations Critical threshold value for 15 minute interval."
    DEFVAL          { 15955 }
    ::= { sonusDs1ThresholdProfileEntry 41 }

sonusDs1ThresholdProfileCriticalPESThreshold OBJECT-TYPE
    SYNTAX          INTEGER (1..900)
    ACCESS          read-write
    STATUS          mandatory
    DESCRIPTION     
            "Path Errored Seconds Critical threshold value for 15 minute interval."
    DEFVAL          { 78 }
    ::= { sonusDs1ThresholdProfileEntry 42 }

sonusDs1ThresholdProfileCriticalPSESThreshold OBJECT-TYPE
    SYNTAX          INTEGER (1..900)
    ACCESS          read-write
    STATUS          mandatory
    DESCRIPTION     
            "Path Severely Errored Seconds Critical threshold value for 15 minute interval."
    DEFVAL          { 12 }
    ::= { sonusDs1ThresholdProfileEntry 43 }

sonusDs1ThresholdProfileCriticalCSSThreshold OBJECT-TYPE
    SYNTAX          INTEGER (1..900)
    ACCESS          read-write
    STATUS          mandatory
    DESCRIPTION     
            "Controlled Slip Seconds Critical threshold value for 15 minute interval."
    DEFVAL          { 3 }
    ::= { sonusDs1ThresholdProfileEntry 44 }

sonusDs1ThresholdProfileCriticalSASThreshold OBJECT-TYPE
    SYNTAX          INTEGER (1..900)
    ACCESS          read-write
    STATUS          mandatory
    DESCRIPTION     
            "SEF/AIS Seconds Critical threshold value for 15 minute interval."
    DEFVAL          { 3 }
    ::= { sonusDs1ThresholdProfileEntry 45 }

sonusDs1ThresholdProfileCriticalUASThreshold OBJECT-TYPE
    SYNTAX          INTEGER (1..900)
    ACCESS          read-write
    STATUS          mandatory
    DESCRIPTION     
            "Unavailable Seconds Critical threshold value for 15 minute interval."
    DEFVAL          { 12 }
    ::= { sonusDs1ThresholdProfileEntry 46 }

sonusDs1ThresholdProfileDayCriticalLCVThreshold OBJECT-TYPE
    SYNTAX          INTEGER (1..1048575)
    ACCESS          read-write
    STATUS          mandatory
    DESCRIPTION     
            "Line Code Violations Critical threshold value for 24 hour interval."
    DEFVAL          { 160080 }
    ::= { sonusDs1ThresholdProfileEntry 47 }

sonusDs1ThresholdProfileDayCriticalLESThreshold OBJECT-TYPE
    SYNTAX          INTEGER (1..65535)
    ACCESS          read-write
    STATUS          mandatory
    DESCRIPTION     
            "Line Errored Seconds Critical threshold value for 24 hour interval."
    DEFVAL          { 778 }
    ::= { sonusDs1ThresholdProfileEntry 48 }

sonusDs1ThresholdProfileDayCriticalLSESThreshold OBJECT-TYPE
    SYNTAX          INTEGER (1..65535)
    ACCESS          read-write
    STATUS          mandatory
    DESCRIPTION     
            "Line Severely Errored Seconds Critical threshold value for 24 hour interval."
    DEFVAL          { 120 }
    ::= { sonusDs1ThresholdProfileEntry 49 }

sonusDs1ThresholdProfileDayCriticalPCVThreshold OBJECT-TYPE
    SYNTAX          INTEGER (1..1048575)
    ACCESS          read-write
    STATUS          mandatory
    DESCRIPTION     
            "Path Code Violations Critical threshold value for 24 hour interval."
    DEFVAL          { 159552 }
    ::= { sonusDs1ThresholdProfileEntry 50 }

sonusDs1ThresholdProfileDayCriticalPESThreshold OBJECT-TYPE
    SYNTAX          INTEGER (1..65535)
    ACCESS          read-write
    STATUS          mandatory
    DESCRIPTION     
            "Path Errored Seconds Critical threshold value for 24 hour interval."
    DEFVAL          { 778 }
    ::= { sonusDs1ThresholdProfileEntry 51 }

sonusDs1ThresholdProfileDayCriticalPSESThreshold OBJECT-TYPE
    SYNTAX          INTEGER (1..65535)
    ACCESS          read-write
    STATUS          mandatory
    DESCRIPTION     
            "Path Severely Errored Seconds Critical threshold value for 24 hour interval."
    DEFVAL          { 120 }
    ::= { sonusDs1ThresholdProfileEntry 52 }

sonusDs1ThresholdProfileDayCriticalCSSThreshold OBJECT-TYPE
    SYNTAX          INTEGER (1..65535)
    ACCESS          read-write
    STATUS          mandatory
    DESCRIPTION     
            "Controlled Slip Seconds Critical threshold value for 24 hour interval."
    DEFVAL          { 6 }
    ::= { sonusDs1ThresholdProfileEntry 53 }

sonusDs1ThresholdProfileDayCriticalSASThreshold OBJECT-TYPE
    SYNTAX          INTEGER (1..65535)
    ACCESS          read-write
    STATUS          mandatory
    DESCRIPTION     
            "SES/AIS Seconds Critical threshold value for 24 hour interval."
    DEFVAL          { 20 }
    ::= { sonusDs1ThresholdProfileEntry 54 }

sonusDs1ThresholdProfileDayCriticalUASThreshold OBJECT-TYPE
    SYNTAX          INTEGER (1..65535)
    ACCESS          read-write
    STATUS          mandatory
    DESCRIPTION     
            "Unavailable Seconds Critical threshold value for 24 hour interval."
    DEFVAL          { 12 }
    ::= { sonusDs1ThresholdProfileEntry 55 }

sonusDs1ThresholdProfileLCVTcaFilter OBJECT-TYPE
    SYNTAX          SonusAdminState
    ACCESS          read-write
    STATUS          mandatory
    DESCRIPTION     
            "Controls whether a threshold Crossing Alert (TCA) is reported (via
             an event log and trap). Setting this object to Enabled will prevent
             the TCA from being reported (i.e will Filter the TCA report)."
    DEFVAL          { disabled }
    ::= { sonusDs1ThresholdProfileEntry 56 }

sonusDs1ThresholdProfileLESTcaFilter OBJECT-TYPE
    SYNTAX          SonusAdminState
    ACCESS          read-write
    STATUS          mandatory
    DESCRIPTION     
            "Controls whether a threshold Crossing Alert (TCA) is reported (via
             an event log and trap). Setting this object to Enabled will prevent
             the TCA from being reported (i.e will Filter the TCA report)."
    DEFVAL          { disabled }
    ::= { sonusDs1ThresholdProfileEntry 57 }

sonusDs1ThresholdProfileLSESTcaFilter OBJECT-TYPE
    SYNTAX          SonusAdminState
    ACCESS          read-write
    STATUS          mandatory
    DESCRIPTION     
            "Controls whether a threshold Crossing Alert (TCA) is reported (via
             an event log and trap). Setting this object to Enabled will prevent
             the TCA from being reported (i.e will Filter the TCA report)."
    DEFVAL          { disabled }
    ::= { sonusDs1ThresholdProfileEntry 58 }

sonusDs1ThresholdProfilePCVTcaFilter OBJECT-TYPE
    SYNTAX          SonusAdminState
    ACCESS          read-write
    STATUS          mandatory
    DESCRIPTION     
            "Controls whether a threshold Crossing Alert (TCA) is reported (via
             an event log and trap). Setting this object to Enabled will prevent
             the TCA from being reported (i.e will Filter the TCA report)."
    DEFVAL          { disabled }
    ::= { sonusDs1ThresholdProfileEntry 59 }

sonusDs1ThresholdProfilePESTcaFilter OBJECT-TYPE
    SYNTAX          SonusAdminState
    ACCESS          read-write
    STATUS          mandatory
    DESCRIPTION     
            "Controls whether a threshold Crossing Alert (TCA) is reported (via
             an event log and trap). Setting this object to Enabled will prevent
             the TCA from being reported (i.e will Filter the TCA report)."
    DEFVAL          { disabled }
    ::= { sonusDs1ThresholdProfileEntry 60 }

sonusDs1ThresholdProfilePSESTcaFilter OBJECT-TYPE
    SYNTAX          SonusAdminState
    ACCESS          read-write
    STATUS          mandatory
    DESCRIPTION     
            "Controls whether a threshold Crossing Alert (TCA) is reported (via
             an event log and trap). Setting this object to Enabled will prevent
             the TCA from being reported (i.e will Filter the TCA report)."
    DEFVAL          { disabled }
    ::= { sonusDs1ThresholdProfileEntry 61 }

sonusDs1ThresholdProfileCSSTcaFilter OBJECT-TYPE
    SYNTAX          SonusAdminState
    ACCESS          read-write
    STATUS          mandatory
    DESCRIPTION     
            "Controls whether a threshold Crossing Alert (TCA) is reported (via
             an event log and trap). Setting this object to Enabled will prevent
             the TCA from being reported (i.e will Filter the TCA report)."
    DEFVAL          { disabled }
    ::= { sonusDs1ThresholdProfileEntry 62 }

sonusDs1ThresholdProfileSASTcaFilter OBJECT-TYPE
    SYNTAX          SonusAdminState
    ACCESS          read-write
    STATUS          mandatory
    DESCRIPTION     
            "Controls whether a threshold Crossing Alert (TCA) is reported (via
             an event log and trap). Setting this object to Enabled will prevent
             the TCA from being reported (i.e will Filter the TCA report)."
    DEFVAL          { disabled }
    ::= { sonusDs1ThresholdProfileEntry 63 }

sonusDs1ThresholdProfileUASTcaFilter OBJECT-TYPE
    SYNTAX          SonusAdminState
    ACCESS          read-write
    STATUS          mandatory
    DESCRIPTION     
            "Controls whether a threshold Crossing Alert (TCA) is reported (via
             an event log and trap). Setting this object to Enabled will prevent
             the TCA from being reported (i.e will Filter the TCA report)."
    DEFVAL          { disabled }
    ::= { sonusDs1ThresholdProfileEntry 64 }

sonusDs1ThresholdProfileReportMinorCriticalTca OBJECT-TYPE
    SYNTAX          SonusAdminState
    ACCESS          read-write
    STATUS          mandatory
    DESCRIPTION     
            "Controls whether Minor-level and Critical-level Threshold Crossing
             Alerts (TCA) are reported (via an event log and trap). Setting this
             object to Disabled will prevent all Minor and Critical TCAs from being
             reported."
    DEFVAL          { disabled }
    ::= { sonusDs1ThresholdProfileEntry 65 }

sonusDs1ThresholdProfileReportDs1OosTca OBJECT-TYPE
    SYNTAX          SonusAdminState
    ACCESS          read-write
    STATUS          mandatory
    DESCRIPTION     
            "Controls whether threshold Crossing Alerts (TCA) are reported
             (via an event log and trap) while the DS1 is Out of Service. Setting
             this object to Enabled allows TCAs to be reported while the DS1 is
             Out of Service."
    DEFVAL          { disabled }
    ::= { sonusDs1ThresholdProfileEntry 66 }

sonusDs1ThresholdProfileMinorLCVThresholdState OBJECT-TYPE
    SYNTAX          SonusAdminState
    ACCESS          read-write
    STATUS          mandatory
    DESCRIPTION     
            "Profile State"
    DEFVAL          { enabled }
    ::= { sonusDs1ThresholdProfileEntry 67 }

sonusDs1ThresholdProfileMinorLESThresholdState OBJECT-TYPE
    SYNTAX          SonusAdminState
    ACCESS          read-write
    STATUS          mandatory
    DESCRIPTION     
            "Profile State"
    DEFVAL          { enabled }
    ::= { sonusDs1ThresholdProfileEntry 68 }

sonusDs1ThresholdProfileMinorLSESThresholdState OBJECT-TYPE
    SYNTAX          SonusAdminState
    ACCESS          read-write
    STATUS          mandatory
    DESCRIPTION     
            "Profile State"
    DEFVAL          { enabled }
    ::= { sonusDs1ThresholdProfileEntry 69 }

sonusDs1ThresholdProfileMinorPCVThresholdState OBJECT-TYPE
    SYNTAX          SonusAdminState
    ACCESS          read-write
    STATUS          mandatory
    DESCRIPTION     
            "Profile State"
    DEFVAL          { enabled }
    ::= { sonusDs1ThresholdProfileEntry 70 }

sonusDs1ThresholdProfileMinorPESThresholdState OBJECT-TYPE
    SYNTAX          SonusAdminState
    ACCESS          read-write
    STATUS          mandatory
    DESCRIPTION     
            "Profile State"
    DEFVAL          { enabled }
    ::= { sonusDs1ThresholdProfileEntry 71 }

sonusDs1ThresholdProfileMinorPSESThresholdState OBJECT-TYPE
    SYNTAX          SonusAdminState
    ACCESS          read-write
    STATUS          mandatory
    DESCRIPTION     
            "Profile State"
    DEFVAL          { enabled }
    ::= { sonusDs1ThresholdProfileEntry 72 }

sonusDs1ThresholdProfileMinorCSSThresholdState OBJECT-TYPE
    SYNTAX          SonusAdminState
    ACCESS          read-write
    STATUS          mandatory
    DESCRIPTION     
            "Profile State"
    DEFVAL          { enabled }
    ::= { sonusDs1ThresholdProfileEntry 73 }

sonusDs1ThresholdProfileMinorSASThresholdState OBJECT-TYPE
    SYNTAX          SonusAdminState
    ACCESS          read-write
    STATUS          mandatory
    DESCRIPTION     
            "Profile State"
    DEFVAL          { enabled }
    ::= { sonusDs1ThresholdProfileEntry 74 }

sonusDs1ThresholdProfileMinorUASThresholdState OBJECT-TYPE
    SYNTAX          SonusAdminState
    ACCESS          read-write
    STATUS          mandatory
    DESCRIPTION     
            "Profile State"
    DEFVAL          { enabled }
    ::= { sonusDs1ThresholdProfileEntry 75 }

sonusDs1ThresholdProfileDayMinorLCVThresholdState OBJECT-TYPE
    SYNTAX          SonusAdminState
    ACCESS          read-write
    STATUS          mandatory
    DESCRIPTION     
            "Profile State"
    DEFVAL          { enabled }
    ::= { sonusDs1ThresholdProfileEntry 76 }

sonusDs1ThresholdProfileDayMinorLESThresholdState OBJECT-TYPE
    SYNTAX          SonusAdminState
    ACCESS          read-write
    STATUS          mandatory
    DESCRIPTION     
            "Profile State"
    DEFVAL          { enabled }
    ::= { sonusDs1ThresholdProfileEntry 77 }

sonusDs1ThresholdProfileDayMinorLSESThresholdState OBJECT-TYPE
    SYNTAX          SonusAdminState
    ACCESS          read-write
    STATUS          mandatory
    DESCRIPTION     
            "Profile State"
    DEFVAL          { enabled }
    ::= { sonusDs1ThresholdProfileEntry 78 }

sonusDs1ThresholdProfileDayMinorPCVThresholdState OBJECT-TYPE
    SYNTAX          SonusAdminState
    ACCESS          read-write
    STATUS          mandatory
    DESCRIPTION     
            "Profile State"
    DEFVAL          { enabled }
    ::= { sonusDs1ThresholdProfileEntry 79 }

sonusDs1ThresholdProfileDayMinorPESThresholdState OBJECT-TYPE
    SYNTAX          SonusAdminState
    ACCESS          read-write
    STATUS          mandatory
    DESCRIPTION     
            "Profile State"
    DEFVAL          { enabled }
    ::= { sonusDs1ThresholdProfileEntry 80 }

sonusDs1ThresholdProfileDayMinorPSESThresholdState OBJECT-TYPE
    SYNTAX          SonusAdminState
    ACCESS          read-write
    STATUS          mandatory
    DESCRIPTION     
            "Profile State"
    DEFVAL          { enabled }
    ::= { sonusDs1ThresholdProfileEntry 81 }

sonusDs1ThresholdProfileDayMinorCSSThresholdState OBJECT-TYPE
    SYNTAX          SonusAdminState
    ACCESS          read-write
    STATUS          mandatory
    DESCRIPTION     
            "Profile State"
    DEFVAL          { enabled }
    ::= { sonusDs1ThresholdProfileEntry 82 }

sonusDs1ThresholdProfileDayMinorSASThresholdState OBJECT-TYPE
    SYNTAX          SonusAdminState
    ACCESS          read-write
    STATUS          mandatory
    DESCRIPTION     
            "Profile State"
    DEFVAL          { enabled }
    ::= { sonusDs1ThresholdProfileEntry 83 }

sonusDs1ThresholdProfileDayMinorUASThresholdState OBJECT-TYPE
    SYNTAX          SonusAdminState
    ACCESS          read-write
    STATUS          mandatory
    DESCRIPTION     
            "Profile State"
    DEFVAL          { enabled }
    ::= { sonusDs1ThresholdProfileEntry 84 }

sonusDs1ThresholdProfileMajorLCVThresholdState OBJECT-TYPE
    SYNTAX          SonusAdminState
    ACCESS          read-write
    STATUS          mandatory
    DESCRIPTION     
            "Profile State"
    DEFVAL          { enabled }
    ::= { sonusDs1ThresholdProfileEntry 85 }

sonusDs1ThresholdProfileMajorLESThresholdState OBJECT-TYPE
    SYNTAX          SonusAdminState
    ACCESS          read-write
    STATUS          mandatory
    DESCRIPTION     
            "Profile State"
    DEFVAL          { enabled }
    ::= { sonusDs1ThresholdProfileEntry 86 }

sonusDs1ThresholdProfileMajorLSESThresholdState OBJECT-TYPE
    SYNTAX          SonusAdminState
    ACCESS          read-write
    STATUS          mandatory
    DESCRIPTION     
            "Profile State"
    DEFVAL          { enabled }
    ::= { sonusDs1ThresholdProfileEntry 87 }

sonusDs1ThresholdProfileMajorPCVThresholdState OBJECT-TYPE
    SYNTAX          SonusAdminState
    ACCESS          read-write
    STATUS          mandatory
    DESCRIPTION     
            "Profile State"
    DEFVAL          { enabled }
    ::= { sonusDs1ThresholdProfileEntry 88 }

sonusDs1ThresholdProfileMajorPESThresholdState OBJECT-TYPE
    SYNTAX          SonusAdminState
    ACCESS          read-write
    STATUS          mandatory
    DESCRIPTION     
            "Profile State"
    DEFVAL          { enabled }
    ::= { sonusDs1ThresholdProfileEntry 89 }

sonusDs1ThresholdProfileMajorPSESThresholdState OBJECT-TYPE
    SYNTAX          SonusAdminState
    ACCESS          read-write
    STATUS          mandatory
    DESCRIPTION     
            "Profile State"
    DEFVAL          { enabled }
    ::= { sonusDs1ThresholdProfileEntry 90 }

sonusDs1ThresholdProfileMajorCSSThresholdState OBJECT-TYPE
    SYNTAX          SonusAdminState
    ACCESS          read-write
    STATUS          mandatory
    DESCRIPTION     
            "Profile State"
    DEFVAL          { enabled }
    ::= { sonusDs1ThresholdProfileEntry 91 }

sonusDs1ThresholdProfileMajorSASThresholdState OBJECT-TYPE
    SYNTAX          SonusAdminState
    ACCESS          read-write
    STATUS          mandatory
    DESCRIPTION     
            "Profile State"
    DEFVAL          { enabled }
    ::= { sonusDs1ThresholdProfileEntry 92 }

sonusDs1ThresholdProfileMajorUASThresholdState OBJECT-TYPE
    SYNTAX          SonusAdminState
    ACCESS          read-write
    STATUS          mandatory
    DESCRIPTION     
            "Profile State"
    DEFVAL          { enabled }
    ::= { sonusDs1ThresholdProfileEntry 93 }

sonusDs1ThresholdProfileDayMajorLCVThresholdState OBJECT-TYPE
    SYNTAX          SonusAdminState
    ACCESS          read-write
    STATUS          mandatory
    DESCRIPTION     
            "Profile State"
    DEFVAL          { enabled }
    ::= { sonusDs1ThresholdProfileEntry 94 }

sonusDs1ThresholdProfileDayMajorLESThresholdState OBJECT-TYPE
    SYNTAX          SonusAdminState
    ACCESS          read-write
    STATUS          mandatory
    DESCRIPTION     
            "Profile State"
    DEFVAL          { enabled }
    ::= { sonusDs1ThresholdProfileEntry 95 }

sonusDs1ThresholdProfileDayMajorLSESThresholdState OBJECT-TYPE
    SYNTAX          SonusAdminState
    ACCESS          read-write
    STATUS          mandatory
    DESCRIPTION     
            "Profile State"
    DEFVAL          { enabled }
    ::= { sonusDs1ThresholdProfileEntry 96 }

sonusDs1ThresholdProfileDayMajorPCVThresholdState OBJECT-TYPE
    SYNTAX          SonusAdminState
    ACCESS          read-write
    STATUS          mandatory
    DESCRIPTION     
            "Profile State"
    DEFVAL          { enabled }
    ::= { sonusDs1ThresholdProfileEntry 97 }

sonusDs1ThresholdProfileDayMajorPESThresholdState OBJECT-TYPE
    SYNTAX          SonusAdminState
    ACCESS          read-write
    STATUS          mandatory
    DESCRIPTION     
            "Profile State"
    DEFVAL          { enabled }
    ::= { sonusDs1ThresholdProfileEntry 98 }

sonusDs1ThresholdProfileDayMajorPSESThresholdState OBJECT-TYPE
    SYNTAX          SonusAdminState
    ACCESS          read-write
    STATUS          mandatory
    DESCRIPTION     
            "Profile State"
    DEFVAL          { enabled }
    ::= { sonusDs1ThresholdProfileEntry 99 }

sonusDs1ThresholdProfileDayMajorCSSThresholdState OBJECT-TYPE
    SYNTAX          SonusAdminState
    ACCESS          read-write
    STATUS          mandatory
    DESCRIPTION     
            "Profile State"
    DEFVAL          { enabled }
    ::= { sonusDs1ThresholdProfileEntry 100 }

sonusDs1ThresholdProfileDayMajorSASThresholdState OBJECT-TYPE
    SYNTAX          SonusAdminState
    ACCESS          read-write
    STATUS          mandatory
    DESCRIPTION     
            "Profile State"
    DEFVAL          { enabled }
    ::= { sonusDs1ThresholdProfileEntry 101 }

sonusDs1ThresholdProfileDayMajorUASThresholdState OBJECT-TYPE
    SYNTAX          SonusAdminState
    ACCESS          read-write
    STATUS          mandatory
    DESCRIPTION     
            "Profile State"
    DEFVAL          { enabled }
    ::= { sonusDs1ThresholdProfileEntry 102 }

sonusDs1ThresholdProfileCriticalLCVThresholdState OBJECT-TYPE
    SYNTAX          SonusAdminState
    ACCESS          read-write
    STATUS          mandatory
    DESCRIPTION     
            "Profile State"
    DEFVAL          { enabled }
    ::= { sonusDs1ThresholdProfileEntry 103 }

sonusDs1ThresholdProfileCriticalLESThresholdState OBJECT-TYPE
    SYNTAX          SonusAdminState
    ACCESS          read-write
    STATUS          mandatory
    DESCRIPTION     
            "Profile State"
    DEFVAL          { enabled }
    ::= { sonusDs1ThresholdProfileEntry 104 }

sonusDs1ThresholdProfileCriticalLSESThresholdState OBJECT-TYPE
    SYNTAX          SonusAdminState
    ACCESS          read-write
    STATUS          mandatory
    DESCRIPTION     
            "Profile State"
    DEFVAL          { enabled }
    ::= { sonusDs1ThresholdProfileEntry 105 }

sonusDs1ThresholdProfileCriticalPCVThresholdState OBJECT-TYPE
    SYNTAX          SonusAdminState
    ACCESS          read-write
    STATUS          mandatory
    DESCRIPTION     
            "Profile State"
    DEFVAL          { enabled }
    ::= { sonusDs1ThresholdProfileEntry 106 }

sonusDs1ThresholdProfileCriticalPESThresholdState OBJECT-TYPE
    SYNTAX          SonusAdminState
    ACCESS          read-write
    STATUS          mandatory
    DESCRIPTION     
            "Profile State"
    DEFVAL          { enabled }
    ::= { sonusDs1ThresholdProfileEntry 107 }

sonusDs1ThresholdProfileCriticalPSESThresholdState OBJECT-TYPE
    SYNTAX          SonusAdminState
    ACCESS          read-write
    STATUS          mandatory
    DESCRIPTION     
            "Profile State"
    DEFVAL          { enabled }
    ::= { sonusDs1ThresholdProfileEntry 108 }

sonusDs1ThresholdProfileCriticalCSSThresholdState OBJECT-TYPE
    SYNTAX          SonusAdminState
    ACCESS          read-write
    STATUS          mandatory
    DESCRIPTION     
            "Profile State"
    DEFVAL          { enabled }
    ::= { sonusDs1ThresholdProfileEntry 109 }

sonusDs1ThresholdProfileCriticalSASThresholdState OBJECT-TYPE
    SYNTAX          SonusAdminState
    ACCESS          read-write
    STATUS          mandatory
    DESCRIPTION     
            "Profile State"
    DEFVAL          { enabled }
    ::= { sonusDs1ThresholdProfileEntry 110 }

sonusDs1ThresholdProfileCriticalUASThresholdState OBJECT-TYPE
    SYNTAX          SonusAdminState
    ACCESS          read-write
    STATUS          mandatory
    DESCRIPTION     
            "Profile State"
    DEFVAL          { enabled }
    ::= { sonusDs1ThresholdProfileEntry 111 }

sonusDs1ThresholdProfileDayCriticalLCVThresholdState OBJECT-TYPE
    SYNTAX          SonusAdminState
    ACCESS          read-write
    STATUS          mandatory
    DESCRIPTION     
            "Profile State"
    DEFVAL          { enabled }
    ::= { sonusDs1ThresholdProfileEntry 112 }

sonusDs1ThresholdProfileDayCriticalLESThresholdState OBJECT-TYPE
    SYNTAX          SonusAdminState
    ACCESS          read-write
    STATUS          mandatory
    DESCRIPTION     
            "Profile State"
    DEFVAL          { enabled }
    ::= { sonusDs1ThresholdProfileEntry 113 }

sonusDs1ThresholdProfileDayCriticalLSESThresholdState OBJECT-TYPE
    SYNTAX          SonusAdminState
    ACCESS          read-write
    STATUS          mandatory
    DESCRIPTION     
            "Profile State"
    DEFVAL          { enabled }
    ::= { sonusDs1ThresholdProfileEntry 114 }

sonusDs1ThresholdProfileDayCriticalPCVThresholdState OBJECT-TYPE
    SYNTAX          SonusAdminState
    ACCESS          read-write
    STATUS          mandatory
    DESCRIPTION     
            "Profile State"
    DEFVAL          { enabled }
    ::= { sonusDs1ThresholdProfileEntry 115 }

sonusDs1ThresholdProfileDayCriticalPESThresholdState OBJECT-TYPE
    SYNTAX          SonusAdminState
    ACCESS          read-write
    STATUS          mandatory
    DESCRIPTION     
            "Profile State"
    DEFVAL          { enabled }
    ::= { sonusDs1ThresholdProfileEntry 116 }

sonusDs1ThresholdProfileDayCriticalPSESThresholdState OBJECT-TYPE
    SYNTAX          SonusAdminState
    ACCESS          read-write
    STATUS          mandatory
    DESCRIPTION     
            "Profile State"
    DEFVAL          { enabled }
    ::= { sonusDs1ThresholdProfileEntry 117 }

sonusDs1ThresholdProfileDayCriticalCSSThresholdState OBJECT-TYPE
    SYNTAX          SonusAdminState
    ACCESS          read-write
    STATUS          mandatory
    DESCRIPTION     
            "Profile State"
    DEFVAL          { enabled }
    ::= { sonusDs1ThresholdProfileEntry 118 }

sonusDs1ThresholdProfileDayCriticalSASThresholdState OBJECT-TYPE
    SYNTAX          SonusAdminState
    ACCESS          read-write
    STATUS          mandatory
    DESCRIPTION     
            "Profile State"
    DEFVAL          { enabled }
    ::= { sonusDs1ThresholdProfileEntry 119 }

sonusDs1ThresholdProfileDayCriticalUASThresholdState OBJECT-TYPE
    SYNTAX          SonusAdminState
    ACCESS          read-write
    STATUS          mandatory
    DESCRIPTION     
            "Profile State"
    DEFVAL          { enabled }
    ::= { sonusDs1ThresholdProfileEntry 120 }

sonusDs1ThresholdProfileLCVTcaFilterState OBJECT-TYPE
    SYNTAX          SonusAdminState
    ACCESS          read-write
    STATUS          mandatory
    DESCRIPTION     
            "Profile State"
    DEFVAL          { enabled }
    ::= { sonusDs1ThresholdProfileEntry 121 }

sonusDs1ThresholdProfileLESTcaFilterState OBJECT-TYPE
    SYNTAX          SonusAdminState
    ACCESS          read-write
    STATUS          mandatory
    DESCRIPTION     
            "Profile State"
    DEFVAL          { enabled }
    ::= { sonusDs1ThresholdProfileEntry 122 }

sonusDs1ThresholdProfileLSESTcaFilterState OBJECT-TYPE
    SYNTAX          SonusAdminState
    ACCESS          read-write
    STATUS          mandatory
    DESCRIPTION     
            "Profile State"
    DEFVAL          { enabled }
    ::= { sonusDs1ThresholdProfileEntry 123 }

sonusDs1ThresholdProfilePCVTcaFilterState OBJECT-TYPE
    SYNTAX          SonusAdminState
    ACCESS          read-write
    STATUS          mandatory
    DESCRIPTION     
            "Profile State"
    DEFVAL          { enabled }
    ::= { sonusDs1ThresholdProfileEntry 124 }

sonusDs1ThresholdProfilePESTcaFilterState OBJECT-TYPE
    SYNTAX          SonusAdminState
    ACCESS          read-write
    STATUS          mandatory
    DESCRIPTION     
            "Profile State"
    DEFVAL          { enabled }
    ::= { sonusDs1ThresholdProfileEntry 125 }

sonusDs1ThresholdProfilePSESTcaFilterState OBJECT-TYPE
    SYNTAX          SonusAdminState
    ACCESS          read-write
    STATUS          mandatory
    DESCRIPTION     
            "Profile State"
    DEFVAL          { enabled }
    ::= { sonusDs1ThresholdProfileEntry 126 }

sonusDs1ThresholdProfileCSSTcaFilterState OBJECT-TYPE
    SYNTAX          SonusAdminState
    ACCESS          read-write
    STATUS          mandatory
    DESCRIPTION     
            "Profile State"
    DEFVAL          { enabled }
    ::= { sonusDs1ThresholdProfileEntry 127 }

sonusDs1ThresholdProfileSASTcaFilterState OBJECT-TYPE
    SYNTAX          SonusAdminState
    ACCESS          read-write
    STATUS          mandatory
    DESCRIPTION     
            "Profile State"
    DEFVAL          { enabled }
    ::= { sonusDs1ThresholdProfileEntry 128 }

sonusDs1ThresholdProfileUASTcaFilterState OBJECT-TYPE
    SYNTAX          SonusAdminState
    ACCESS          read-write
    STATUS          mandatory
    DESCRIPTION     
            "Profile State"
    DEFVAL          { enabled }
    ::= { sonusDs1ThresholdProfileEntry 129 }

sonusDs1ThresholdProfileReportMinorCriticalTcaState OBJECT-TYPE
    SYNTAX          SonusAdminState
    ACCESS          read-write
    STATUS          mandatory
    DESCRIPTION     
            "Profile State"
    DEFVAL          { enabled }
    ::= { sonusDs1ThresholdProfileEntry 130 }

sonusDs1ThresholdProfileReportDs1OosTcaState OBJECT-TYPE
    SYNTAX          SonusAdminState
    ACCESS          read-write
    STATUS          mandatory
    DESCRIPTION     
            "Profile State"
    DEFVAL          { enabled }
    ::= { sonusDs1ThresholdProfileEntry 132 }

sonusDsx1Threshold OBJECT IDENTIFIER
    ::= { sonusDsx1MIBObjects 13 }

sonusDsx1ThresholdTable OBJECT-TYPE
    SYNTAX          SEQUENCE OF SonusDsx1ThresholdEntry
    ACCESS          not-accessible
    STATUS          mandatory
    DESCRIPTION     
            " "
    ::= { sonusDsx1Threshold 1 }

sonusDsx1ThresholdEntry OBJECT-TYPE
    SYNTAX          SonusDsx1ThresholdEntry
    ACCESS          not-accessible
    STATUS          mandatory
    DESCRIPTION     
            "Entry in Sonus Dsx1 Threshold Table"
    INDEX           { sonusDsx1ThresholdShelfIndex, 
                      sonusDsx1ThresholdSlotIndex, 
                      sonusDsx1ThresholdPortIndex, 
                      sonusDsx1ThresholdDs1Index }
    ::= { sonusDsx1ThresholdTable 1 }

SonusDsx1ThresholdEntry ::=
    SEQUENCE {
        sonusDsx1ThresholdShelfIndex    SonusShelfIndex,
        sonusDsx1ThresholdSlotIndex     SonusSlotIndex,
        sonusDsx1ThresholdPortIndex     INTEGER,
        sonusDsx1ThresholdDs1Index      INTEGER,
        sonusDsx1ThresholdMinorLCVThreshold   INTEGER,
        sonusDsx1ThresholdMinorLESThreshold   INTEGER,
        sonusDsx1ThresholdMinorLSESThreshold    INTEGER,
        sonusDsx1ThresholdMinorPCVThreshold   INTEGER,
        sonusDsx1ThresholdMinorPESThreshold   INTEGER,
        sonusDsx1ThresholdMinorPSESThreshold    INTEGER,
        sonusDsx1ThresholdMinorCSSThreshold   INTEGER,
        sonusDsx1ThresholdMinorSASThreshold   INTEGER,
        sonusDsx1ThresholdMinorUASThreshold   INTEGER,
        sonusDsx1ThresholdDayMinorLCVThreshold      INTEGER,
        sonusDsx1ThresholdDayMinorLESThreshold      INTEGER,
        sonusDsx1ThresholdDayMinorLSESThreshold       INTEGER,
        sonusDsx1ThresholdDayMinorPCVThreshold      INTEGER,
        sonusDsx1ThresholdDayMinorPESThreshold      INTEGER,
        sonusDsx1ThresholdDayMinorPSESThreshold       INTEGER,
        sonusDsx1ThresholdDayMinorCSSThreshold      INTEGER,
        sonusDsx1ThresholdDayMinorSASThreshold      INTEGER,
        sonusDsx1ThresholdDayMinorUASThreshold      INTEGER,
        sonusDsx1ThresholdMajorLCVThreshold   INTEGER,
        sonusDsx1ThresholdMajorLESThreshold   INTEGER,
        sonusDsx1ThresholdMajorLSESThreshold    INTEGER,
        sonusDsx1ThresholdMajorPCVThreshold   INTEGER,
        sonusDsx1ThresholdMajorPESThreshold   INTEGER,
        sonusDsx1ThresholdMajorPSESThreshold    INTEGER,
        sonusDsx1ThresholdMajorCSSThreshold   INTEGER,
        sonusDsx1ThresholdMajorSASThreshold   INTEGER,
        sonusDsx1ThresholdMajorUASThreshold   INTEGER,
        sonusDsx1ThresholdDayMajorLCVThreshold      INTEGER,
        sonusDsx1ThresholdDayMajorLESThreshold      INTEGER,
        sonusDsx1ThresholdDayMajorLSESThreshold       INTEGER,
        sonusDsx1ThresholdDayMajorPCVThreshold      INTEGER,
        sonusDsx1ThresholdDayMajorPESThreshold      INTEGER,
        sonusDsx1ThresholdDayMajorPSESThreshold       INTEGER,
        sonusDsx1ThresholdDayMajorCSSThreshold      INTEGER,
        sonusDsx1ThresholdDayMajorSASThreshold      INTEGER,
        sonusDsx1ThresholdDayMajorUASThreshold      INTEGER,
        sonusDsx1ThresholdCriticalLCVThreshold      INTEGER,
        sonusDsx1ThresholdCriticalLESThreshold      INTEGER,
        sonusDsx1ThresholdCriticalLSESThreshold       INTEGER,
        sonusDsx1ThresholdCriticalPCVThreshold      INTEGER,
        sonusDsx1ThresholdCriticalPESThreshold      INTEGER,
        sonusDsx1ThresholdCriticalPSESThreshold       INTEGER,
        sonusDsx1ThresholdCriticalCSSThreshold      INTEGER,
        sonusDsx1ThresholdCriticalSASThreshold      INTEGER,
        sonusDsx1ThresholdCriticalUASThreshold      INTEGER,
        sonusDsx1ThresholdDayCriticalLCVThreshold         INTEGER,
        sonusDsx1ThresholdDayCriticalLESThreshold         INTEGER,
        sonusDsx1ThresholdDayCriticalLSESThreshold          INTEGER,
        sonusDsx1ThresholdDayCriticalPCVThreshold         INTEGER,
        sonusDsx1ThresholdDayCriticalPESThreshold         INTEGER,
        sonusDsx1ThresholdDayCriticalPSESThreshold          INTEGER,
        sonusDsx1ThresholdDayCriticalCSSThreshold         INTEGER,
        sonusDsx1ThresholdDayCriticalSASThreshold         INTEGER,
        sonusDsx1ThresholdDayCriticalUASThreshold         INTEGER,
        sonusDsx1ThresholdLCVTcaFilter  SonusAdminState,
        sonusDsx1ThresholdLESTcaFilter  SonusAdminState,
        sonusDsx1ThresholdLSESTcaFilter SonusAdminState,
        sonusDsx1ThresholdPCVTcaFilter  SonusAdminState,
        sonusDsx1ThresholdPESTcaFilter  SonusAdminState,
        sonusDsx1ThresholdPSESTcaFilter SonusAdminState,
        sonusDsx1ThresholdCSSTcaFilter  SonusAdminState,
        sonusDsx1ThresholdSASTcaFilter  SonusAdminState,
        sonusDsx1ThresholdUASTcaFilter  SonusAdminState,
        sonusDsx1ThresholdReportMinorCriticalTca        SonusAdminState,
        sonusDsx1ThresholdReportDs1OosTca SonusAdminState
    }

sonusDsx1ThresholdShelfIndex OBJECT-TYPE
    SYNTAX          SonusShelfIndex
    ACCESS          read-only
    STATUS          mandatory
    DESCRIPTION     
            "Shelf index for this table"
    ::= { sonusDsx1ThresholdEntry 1 }

sonusDsx1ThresholdSlotIndex OBJECT-TYPE
    SYNTAX          SonusSlotIndex
    ACCESS          read-only
    STATUS          mandatory
    DESCRIPTION     
            "Slot index for this table"
    ::= { sonusDsx1ThresholdEntry 2 }

sonusDsx1ThresholdPortIndex OBJECT-TYPE
    SYNTAX          INTEGER
    ACCESS          read-only
    STATUS          mandatory
    DESCRIPTION     
            "Port index for this table"
    ::= { sonusDsx1ThresholdEntry 3 }

sonusDsx1ThresholdDs1Index OBJECT-TYPE
    SYNTAX          INTEGER
    ACCESS          read-only
    STATUS          mandatory
    DESCRIPTION     
            "DS1 index for this table"
    ::= { sonusDsx1ThresholdEntry 4 }

sonusDsx1ThresholdMinorLCVThreshold OBJECT-TYPE
    SYNTAX          INTEGER (1..16383)
    ACCESS          read-write
    STATUS          mandatory
    DESCRIPTION     
            "Line Code Violations Minor threshold value for 15 minute interval."
    DEFVAL          { 10672 }
    ::= { sonusDsx1ThresholdEntry 5 }

sonusDsx1ThresholdMinorLESThreshold OBJECT-TYPE
    SYNTAX          INTEGER (1..900)
    ACCESS          read-write
    STATUS          mandatory
    DESCRIPTION     
            "Line Errored Seconds Minor threshold value for 15 minute interval."
    DEFVAL          { 52 }
    ::= { sonusDsx1ThresholdEntry 6 }

sonusDsx1ThresholdMinorLSESThreshold OBJECT-TYPE
    SYNTAX          INTEGER (1..900)
    ACCESS          read-write
    STATUS          mandatory
    DESCRIPTION     
            "Line Severely Errored Seconds Minor threshold value for 15 minute interval."
    DEFVAL          { 8 }
    ::= { sonusDsx1ThresholdEntry 7 }

sonusDsx1ThresholdMinorPCVThreshold OBJECT-TYPE
    SYNTAX          INTEGER (1..16383)
    ACCESS          read-write
    STATUS          mandatory
    DESCRIPTION     
            "Path Code Violations Minor threshold value for 15 minute interval."
    DEFVAL          { 10637 }
    ::= { sonusDsx1ThresholdEntry 8 }

sonusDsx1ThresholdMinorPESThreshold OBJECT-TYPE
    SYNTAX          INTEGER (1..900)
    ACCESS          read-write
    STATUS          mandatory
    DESCRIPTION     
            "Path Errored Seconds Minor threshold value for 15 minute interval."
    DEFVAL          { 52 }
    ::= { sonusDsx1ThresholdEntry 9 }

sonusDsx1ThresholdMinorPSESThreshold OBJECT-TYPE
    SYNTAX          INTEGER (1..900)
    ACCESS          read-write
    STATUS          mandatory
    DESCRIPTION     
            "Path Severely Errored Seconds Minor threshold value for 15 minute interval."
    DEFVAL          { 8 }
    ::= { sonusDsx1ThresholdEntry 10 }

sonusDsx1ThresholdMinorCSSThreshold OBJECT-TYPE
    SYNTAX          INTEGER (1..900)
    ACCESS          read-write
    STATUS          mandatory
    DESCRIPTION     
            "Controlled Slip Seconds Minor threshold value for 15 minute interval."
    DEFVAL          { 1 }
    ::= { sonusDsx1ThresholdEntry 11 }

sonusDsx1ThresholdMinorSASThreshold OBJECT-TYPE
    SYNTAX          INTEGER (1..900)
    ACCESS          read-write
    STATUS          mandatory
    DESCRIPTION     
            "SEF/AIS Seconds Minor threshold value for 15 minute interval."
    DEFVAL          { 1 }
    ::= { sonusDsx1ThresholdEntry 12 }

sonusDsx1ThresholdMinorUASThreshold OBJECT-TYPE
    SYNTAX          INTEGER (1..900)
    ACCESS          read-write
    STATUS          mandatory
    DESCRIPTION     
            "Unavailable Seconds Minor threshold value for 15 minute interval."
    DEFVAL          { 8 }
    ::= { sonusDsx1ThresholdEntry 13 }

sonusDsx1ThresholdDayMinorLCVThreshold OBJECT-TYPE
    SYNTAX          INTEGER (1..1048575)
    ACCESS          read-write
    STATUS          mandatory
    DESCRIPTION     
            "Line Code Violations Minor threshold value for 24 hour interval."
    DEFVAL          { 106720 }
    ::= { sonusDsx1ThresholdEntry 14 }

sonusDsx1ThresholdDayMinorLESThreshold OBJECT-TYPE
    SYNTAX          INTEGER (1..65535)
    ACCESS          read-write
    STATUS          mandatory
    DESCRIPTION     
            "Line Errored Seconds Minor threshold value for 24 hour interval."
    DEFVAL          { 518 }
    ::= { sonusDsx1ThresholdEntry 15 }

sonusDsx1ThresholdDayMinorLSESThreshold OBJECT-TYPE
    SYNTAX          INTEGER (1..65535)
    ACCESS          read-write
    STATUS          mandatory
    DESCRIPTION     
            "Line Severely Errored Seconds Minor threshold value for 24 hour interval."
    DEFVAL          { 80 }
    ::= { sonusDsx1ThresholdEntry 16 }

sonusDsx1ThresholdDayMinorPCVThreshold OBJECT-TYPE
    SYNTAX          INTEGER (1..1048575)
    ACCESS          read-write
    STATUS          mandatory
    DESCRIPTION     
            "Path Code Violations Minor threshold value for 24 hour interval."
    DEFVAL          { 106368 }
    ::= { sonusDsx1ThresholdEntry 17 }

sonusDsx1ThresholdDayMinorPESThreshold OBJECT-TYPE
    SYNTAX          INTEGER (1..65535)
    ACCESS          read-write
    STATUS          mandatory
    DESCRIPTION     
            "Path Errored Seconds Minor threshold value for 24 hour interval."
    DEFVAL          { 518 }
    ::= { sonusDsx1ThresholdEntry 18 }

sonusDsx1ThresholdDayMinorPSESThreshold OBJECT-TYPE
    SYNTAX          INTEGER (1..65535)
    ACCESS          read-write
    STATUS          mandatory
    DESCRIPTION     
            "Path Severely Errored Seconds Minor threshold value for 24 hour interval."
    DEFVAL          { 80 }
    ::= { sonusDsx1ThresholdEntry 19 }

sonusDsx1ThresholdDayMinorCSSThreshold OBJECT-TYPE
    SYNTAX          INTEGER (1..65535)
    ACCESS          read-write
    STATUS          mandatory
    DESCRIPTION     
            "Controlled Slip Seconds Minor threshold value for 24 hour interval."
    DEFVAL          { 4 }
    ::= { sonusDsx1ThresholdEntry 20 }

sonusDsx1ThresholdDayMinorSASThreshold OBJECT-TYPE
    SYNTAX          INTEGER (1..65535)
    ACCESS          read-write
    STATUS          mandatory
    DESCRIPTION     
            "SES/AIS Seconds Minor threshold value for 24 hour interval."
    DEFVAL          { 14 }
    ::= { sonusDsx1ThresholdEntry 21 }

sonusDsx1ThresholdDayMinorUASThreshold OBJECT-TYPE
    SYNTAX          INTEGER (1..65535)
    ACCESS          read-write
    STATUS          mandatory
    DESCRIPTION     
            "Unavailable Seconds Minor threshold value for 24 hour interval."
    DEFVAL          { 8 }
    ::= { sonusDsx1ThresholdEntry 22 }

sonusDsx1ThresholdMajorLCVThreshold OBJECT-TYPE
    SYNTAX          INTEGER (1..16383)
    ACCESS          read-write
    STATUS          mandatory
    DESCRIPTION     
            "Line Code Violations Major threshold value for 15 minute interval."
    DEFVAL          { 13340 }
    ::= { sonusDsx1ThresholdEntry 23 }

sonusDsx1ThresholdMajorLESThreshold OBJECT-TYPE
    SYNTAX          INTEGER (1..900)
    ACCESS          read-write
    STATUS          mandatory
    DESCRIPTION     
            "Line Errored Seconds Major threshold value for 15 minute interval."
    DEFVAL          { 65 }
    ::= { sonusDsx1ThresholdEntry 24 }

sonusDsx1ThresholdMajorLSESThreshold OBJECT-TYPE
    SYNTAX          INTEGER (1..900)
    ACCESS          read-write
    STATUS          mandatory
    DESCRIPTION     
            "Line Severely Errored Seconds Major threshold value for 15 minute interval."
    DEFVAL          { 10 }
    ::= { sonusDsx1ThresholdEntry 25 }

sonusDsx1ThresholdMajorPCVThreshold OBJECT-TYPE
    SYNTAX          INTEGER (1..16383)
    ACCESS          read-write
    STATUS          mandatory
    DESCRIPTION     
            "Path Code Violations Major threshold value for 15 minute interval."
    DEFVAL          { 13296 }
    ::= { sonusDsx1ThresholdEntry 26 }

sonusDsx1ThresholdMajorPESThreshold OBJECT-TYPE
    SYNTAX          INTEGER (1..900)
    ACCESS          read-write
    STATUS          mandatory
    DESCRIPTION     
            "Path Errored Seconds Major threshold value for 15 minute interval."
    DEFVAL          { 65 }
    ::= { sonusDsx1ThresholdEntry 27 }

sonusDsx1ThresholdMajorPSESThreshold OBJECT-TYPE
    SYNTAX          INTEGER (1..900)
    ACCESS          read-write
    STATUS          mandatory
    DESCRIPTION     
            "Path Severely Errored Seconds Major threshold value for 15 minute interval."
    DEFVAL          { 10 }
    ::= { sonusDsx1ThresholdEntry 28 }

sonusDsx1ThresholdMajorCSSThreshold OBJECT-TYPE
    SYNTAX          INTEGER (1..900)
    ACCESS          read-write
    STATUS          mandatory
    DESCRIPTION     
            "Controlled Slip Seconds Major threshold value for 15 minute interval."
    DEFVAL          { 2 }
    ::= { sonusDsx1ThresholdEntry 29 }

sonusDsx1ThresholdMajorSASThreshold OBJECT-TYPE
    SYNTAX          INTEGER (1..900)
    ACCESS          read-write
    STATUS          mandatory
    DESCRIPTION     
            "SEF/AIS Seconds Major threshold value for 15 minute interval."
    DEFVAL          { 2 }
    ::= { sonusDsx1ThresholdEntry 30 }

sonusDsx1ThresholdMajorUASThreshold OBJECT-TYPE
    SYNTAX          INTEGER (1..900)
    ACCESS          read-write
    STATUS          mandatory
    DESCRIPTION     
            "Unavailable Seconds Major threshold value for 15 minute interval."
    DEFVAL          { 10 }
    ::= { sonusDsx1ThresholdEntry 31 }

sonusDsx1ThresholdDayMajorLCVThreshold OBJECT-TYPE
    SYNTAX          INTEGER (1..1048575)
    ACCESS          read-write
    STATUS          mandatory
    DESCRIPTION     
            "Line Code Violations Major threshold value for 24 hour interval."
    DEFVAL          { 133400 }
    ::= { sonusDsx1ThresholdEntry 32 }

sonusDsx1ThresholdDayMajorLESThreshold OBJECT-TYPE
    SYNTAX          INTEGER (1..65535)
    ACCESS          read-write
    STATUS          mandatory
    DESCRIPTION     
            "Line Errored Seconds Major threshold value for 24 hour interval."
    DEFVAL          { 648 }
    ::= { sonusDsx1ThresholdEntry 33 }

sonusDsx1ThresholdDayMajorLSESThreshold OBJECT-TYPE
    SYNTAX          INTEGER (1..65535)
    ACCESS          read-write
    STATUS          mandatory
    DESCRIPTION     
            "Line Severely Errored Seconds Major threshold value for 24 hour interval."
    DEFVAL          { 100 }
    ::= { sonusDsx1ThresholdEntry 34 }

sonusDsx1ThresholdDayMajorPCVThreshold OBJECT-TYPE
    SYNTAX          INTEGER (1..1048575)
    ACCESS          read-write
    STATUS          mandatory
    DESCRIPTION     
            "Path Code Violations Major threshold value for 24 hour interval."
    DEFVAL          { 132960 }
    ::= { sonusDsx1ThresholdEntry 35 }

sonusDsx1ThresholdDayMajorPESThreshold OBJECT-TYPE
    SYNTAX          INTEGER (1..65535)
    ACCESS          read-write
    STATUS          mandatory
    DESCRIPTION     
            "Path Errored Seconds Major threshold value for 24 hour interval."
    DEFVAL          { 648 }
    ::= { sonusDsx1ThresholdEntry 36 }

sonusDsx1ThresholdDayMajorPSESThreshold OBJECT-TYPE
    SYNTAX          INTEGER (1..65535)
    ACCESS          read-write
    STATUS          mandatory
    DESCRIPTION     
            "Path Severely Errored Seconds Major threshold value for 24 hour interval."
    DEFVAL          { 100 }
    ::= { sonusDsx1ThresholdEntry 37 }

sonusDsx1ThresholdDayMajorCSSThreshold OBJECT-TYPE
    SYNTAX          INTEGER (1..65535)
    ACCESS          read-write
    STATUS          mandatory
    DESCRIPTION     
            "Controlled Slip Seconds Major threshold value for 24 hour interval."
    DEFVAL          { 5 }
    ::= { sonusDsx1ThresholdEntry 38 }

sonusDsx1ThresholdDayMajorSASThreshold OBJECT-TYPE
    SYNTAX          INTEGER (1..65535)
    ACCESS          read-write
    STATUS          mandatory
    DESCRIPTION     
            "SES/AIS Seconds Major threshold value for 24 hour interval."
    DEFVAL          { 17 }
    ::= { sonusDsx1ThresholdEntry 39 }

sonusDsx1ThresholdDayMajorUASThreshold OBJECT-TYPE
    SYNTAX          INTEGER (1..65535)
    ACCESS          read-write
    STATUS          mandatory
    DESCRIPTION     
            "Unavailable Seconds Major threshold value for 24 hour interval."
    DEFVAL          { 10 }
    ::= { sonusDsx1ThresholdEntry 40 }

sonusDsx1ThresholdCriticalLCVThreshold OBJECT-TYPE
    SYNTAX          INTEGER (1..16383)
    ACCESS          read-write
    STATUS          mandatory
    DESCRIPTION     
            "Line Code Violations Critical threshold value for 15 minute interval."
    DEFVAL          { 16008 }
    ::= { sonusDsx1ThresholdEntry 41 }

sonusDsx1ThresholdCriticalLESThreshold OBJECT-TYPE
    SYNTAX          INTEGER (1..900)
    ACCESS          read-write
    STATUS          mandatory
    DESCRIPTION     
            "Line Errored Seconds Critical threshold value for 15 minute interval."
    DEFVAL          { 78 }
    ::= { sonusDsx1ThresholdEntry 42 }

sonusDsx1ThresholdCriticalLSESThreshold OBJECT-TYPE
    SYNTAX          INTEGER (1..900)
    ACCESS          read-write
    STATUS          mandatory
    DESCRIPTION     
            "Line Severely Errored Seconds Critical threshold value for 15 minute interval."
    DEFVAL          { 12 }
    ::= { sonusDsx1ThresholdEntry 43 }

sonusDsx1ThresholdCriticalPCVThreshold OBJECT-TYPE
    SYNTAX          INTEGER (1..16383)
    ACCESS          read-write
    STATUS          mandatory
    DESCRIPTION     
            "Path Code Violations Critical threshold value for 15 minute interval."
    DEFVAL          { 15955 }
    ::= { sonusDsx1ThresholdEntry 44 }

sonusDsx1ThresholdCriticalPESThreshold OBJECT-TYPE
    SYNTAX          INTEGER (1..900)
    ACCESS          read-write
    STATUS          mandatory
    DESCRIPTION     
            "Path Errored Seconds Critical threshold value for 15 minute interval."
    DEFVAL          { 78 }
    ::= { sonusDsx1ThresholdEntry 45 }

sonusDsx1ThresholdCriticalPSESThreshold OBJECT-TYPE
    SYNTAX          INTEGER (1..900)
    ACCESS          read-write
    STATUS          mandatory
    DESCRIPTION     
            "Path Severely Errored Seconds Critical threshold value for 15 minute interval."
    DEFVAL          { 12 }
    ::= { sonusDsx1ThresholdEntry 46 }

sonusDsx1ThresholdCriticalCSSThreshold OBJECT-TYPE
    SYNTAX          INTEGER (1..900)
    ACCESS          read-write
    STATUS          mandatory
    DESCRIPTION     
            "Controlled Slip Seconds Critical threshold value for 15 minute interval."
    DEFVAL          { 3 }
    ::= { sonusDsx1ThresholdEntry 47 }

sonusDsx1ThresholdCriticalSASThreshold OBJECT-TYPE
    SYNTAX          INTEGER (1..900)
    ACCESS          read-write
    STATUS          mandatory
    DESCRIPTION     
            "SEF/AIS Seconds Critical threshold value for 15 minute interval."
    DEFVAL          { 3 }
    ::= { sonusDsx1ThresholdEntry 48 }

sonusDsx1ThresholdCriticalUASThreshold OBJECT-TYPE
    SYNTAX          INTEGER (1..900)
    ACCESS          read-write
    STATUS          mandatory
    DESCRIPTION     
            "Unavailable Seconds Critical threshold value for 15 minute interval."
    DEFVAL          { 12 }
    ::= { sonusDsx1ThresholdEntry 49 }

sonusDsx1ThresholdDayCriticalLCVThreshold OBJECT-TYPE
    SYNTAX          INTEGER (1..1048575)
    ACCESS          read-write
    STATUS          mandatory
    DESCRIPTION     
            "Line Code Violations Critical threshold value for 24 hour interval."
    DEFVAL          { 160080 }
    ::= { sonusDsx1ThresholdEntry 50 }

sonusDsx1ThresholdDayCriticalLESThreshold OBJECT-TYPE
    SYNTAX          INTEGER (1..65535)
    ACCESS          read-write
    STATUS          mandatory
    DESCRIPTION     
            "Line Errored Seconds Critical threshold value for 24 hour interval."
    DEFVAL          { 778 }
    ::= { sonusDsx1ThresholdEntry 51 }

sonusDsx1ThresholdDayCriticalLSESThreshold OBJECT-TYPE
    SYNTAX          INTEGER (1..65535)
    ACCESS          read-write
    STATUS          mandatory
    DESCRIPTION     
            "Line Severely Errored Seconds Critical threshold value for 24 hour interval."
    DEFVAL          { 120 }
    ::= { sonusDsx1ThresholdEntry 52 }

sonusDsx1ThresholdDayCriticalPCVThreshold OBJECT-TYPE
    SYNTAX          INTEGER (1..1048575)
    ACCESS          read-write
    STATUS          mandatory
    DESCRIPTION     
            "Path Code Violations Critical threshold value for 24 hour interval."
    DEFVAL          { 159552 }
    ::= { sonusDsx1ThresholdEntry 53 }

sonusDsx1ThresholdDayCriticalPESThreshold OBJECT-TYPE
    SYNTAX          INTEGER (1..65535)
    ACCESS          read-write
    STATUS          mandatory
    DESCRIPTION     
            "Path Errored Seconds Critical threshold value for 24 hour interval."
    DEFVAL          { 778 }
    ::= { sonusDsx1ThresholdEntry 54 }

sonusDsx1ThresholdDayCriticalPSESThreshold OBJECT-TYPE
    SYNTAX          INTEGER (1..65535)
    ACCESS          read-write
    STATUS          mandatory
    DESCRIPTION     
            "Path Severely Errored Seconds Critical threshold value for 24 hour interval."
    DEFVAL          { 120 }
    ::= { sonusDsx1ThresholdEntry 55 }

sonusDsx1ThresholdDayCriticalCSSThreshold OBJECT-TYPE
    SYNTAX          INTEGER (1..65535)
    ACCESS          read-write
    STATUS          mandatory
    DESCRIPTION     
            "Controlled Slip Seconds Critical threshold value for 24 hour interval."
    DEFVAL          { 6 }
    ::= { sonusDsx1ThresholdEntry 56 }

sonusDsx1ThresholdDayCriticalSASThreshold OBJECT-TYPE
    SYNTAX          INTEGER (1..65535)
    ACCESS          read-write
    STATUS          mandatory
    DESCRIPTION     
            "SES/AIS Seconds Critical threshold value for 24 hour interval."
    DEFVAL          { 20 }
    ::= { sonusDsx1ThresholdEntry 57 }

sonusDsx1ThresholdDayCriticalUASThreshold OBJECT-TYPE
    SYNTAX          INTEGER (1..65535)
    ACCESS          read-write
    STATUS          mandatory
    DESCRIPTION     
            "Unavailable Seconds Critical threshold value for 24 hour interval."
    DEFVAL          { 12 }
    ::= { sonusDsx1ThresholdEntry 58 }

sonusDsx1ThresholdLCVTcaFilter OBJECT-TYPE
    SYNTAX          SonusAdminState
    ACCESS          read-write
    STATUS          mandatory
    DESCRIPTION     
            "Controls whether a threshold Crossing Alert (TCA) is reported (via
             an event log and trap). Setting this object to Enabled will prevent
             the TCA from being reported (i.e will Filter the TCA report)."
    DEFVAL          { disabled }
    ::= { sonusDsx1ThresholdEntry 59 }

sonusDsx1ThresholdLESTcaFilter OBJECT-TYPE
    SYNTAX          SonusAdminState
    ACCESS          read-write
    STATUS          mandatory
    DESCRIPTION     
            "Controls whether a threshold Crossing Alert (TCA) is reported (via
             an event log and trap). Setting this object to Enabled will prevent
             the TCA from being reported (i.e will Filter the TCA report)."
    DEFVAL          { disabled }
    ::= { sonusDsx1ThresholdEntry 60 }

sonusDsx1ThresholdLSESTcaFilter OBJECT-TYPE
    SYNTAX          SonusAdminState
    ACCESS          read-write
    STATUS          mandatory
    DESCRIPTION     
            "Controls whether a threshold Crossing Alert (TCA) is reported (via
             an event log and trap). Setting this object to Enabled will prevent
             the TCA from being reported (i.e will Filter the TCA report)."
    DEFVAL          { disabled }
    ::= { sonusDsx1ThresholdEntry 61 }

sonusDsx1ThresholdPCVTcaFilter OBJECT-TYPE
    SYNTAX          SonusAdminState
    ACCESS          read-write
    STATUS          mandatory
    DESCRIPTION     
            "Controls whether a threshold Crossing Alert (TCA) is reported (via
             an event log and trap). Setting this object to Enabled will prevent
             the TCA from being reported (i.e will Filter the TCA report)."
    DEFVAL          { disabled }
    ::= { sonusDsx1ThresholdEntry 62 }

sonusDsx1ThresholdPESTcaFilter OBJECT-TYPE
    SYNTAX          SonusAdminState
    ACCESS          read-write
    STATUS          mandatory
    DESCRIPTION     
            "Controls whether a threshold Crossing Alert (TCA) is reported (via
             an event log and trap). Setting this object to Enabled will prevent
             the TCA from being reported (i.e will Filter the TCA report)."
    DEFVAL          { disabled }
    ::= { sonusDsx1ThresholdEntry 63 }

sonusDsx1ThresholdPSESTcaFilter OBJECT-TYPE
    SYNTAX          SonusAdminState
    ACCESS          read-write
    STATUS          mandatory
    DESCRIPTION     
            "Controls whether a threshold Crossing Alert (TCA) is reported (via
             an event log and trap). Setting this object to Enabled will prevent
             the TCA from being reported (i.e will Filter the TCA report)."
    DEFVAL          { disabled }
    ::= { sonusDsx1ThresholdEntry 64 }

sonusDsx1ThresholdCSSTcaFilter OBJECT-TYPE
    SYNTAX          SonusAdminState
    ACCESS          read-write
    STATUS          mandatory
    DESCRIPTION     
            "Controls whether a threshold Crossing Alert (TCA) is reported (via
             an event log and trap). Setting this object to Enabled will prevent
             the TCA from being reported (i.e will Filter the TCA report)."
    DEFVAL          { disabled }
    ::= { sonusDsx1ThresholdEntry 65 }

sonusDsx1ThresholdSASTcaFilter OBJECT-TYPE
    SYNTAX          SonusAdminState
    ACCESS          read-write
    STATUS          mandatory
    DESCRIPTION     
            "Controls whether a threshold Crossing Alert (TCA) is reported (via
             an event log and trap). Setting this object to Enabled will prevent
             the TCA from being reported (i.e will Filter the TCA report)."
    DEFVAL          { disabled }
    ::= { sonusDsx1ThresholdEntry 66 }

sonusDsx1ThresholdUASTcaFilter OBJECT-TYPE
    SYNTAX          SonusAdminState
    ACCESS          read-write
    STATUS          mandatory
    DESCRIPTION     
            "Controls whether a threshold Crossing Alert (TCA) is reported (via
             an event log and trap). Setting this object to Enabled will prevent
             the TCA from being reported (i.e will Filter the TCA report)."
    DEFVAL          { disabled }
    ::= { sonusDsx1ThresholdEntry 67 }

sonusDsx1ThresholdReportMinorCriticalTca OBJECT-TYPE
    SYNTAX          SonusAdminState
    ACCESS          read-write
    STATUS          mandatory
    DESCRIPTION     
            "Controls whether Minor-level and Critical-level threshold Crossing
             Alerts (TCA) are reported (via an event log and trap). Setting this
             object to Disabled will prevent all Minor and Critical TCAs from being
             reported."
    DEFVAL          { disabled }
    ::= { sonusDsx1ThresholdEntry 68 }

sonusDsx1ThresholdReportDs1OosTca OBJECT-TYPE
    SYNTAX          SonusAdminState
    ACCESS          read-write
    STATUS          mandatory
    DESCRIPTION     
            "Controls whether threshold Crossing Alerts (TCA) are reported
             (via an event log and trap) while the DS1 is Out of Service. Setting
             this object to Enabled allows TCAs to be reported while the DS1 is
             Out of Service."
    DEFVAL          { disabled }
    ::= { sonusDsx1ThresholdEntry 69 }

sonusDs1PmonIntervalType OBJECT-TYPE
    SYNTAX          INTEGER { fifteenMin(1), day(2) }
    ACCESS          read-only
    STATUS          mandatory
    DESCRIPTION     
            "Pmon interval type."
    ::= { sonusDsx1MIBNotificationsObjects 8 }

sonusDsx1PerfmonThresholdCrossingNotification TRAP-TYPE
    ENTERPRISE      sonusDsx1MIBNotifications
    VARIABLES       { sonusShelfIndex, sonusSlotIndex, sonusPortIndex, 
                      sonusDs1Index, sonusDs1ThresholdType, 
                      sonusEventDescription, sonusEventClass, 
                      sonusEventLevel, sonusSequenceId, sonusEventTime }
--     STATUS          mandatory
    DESCRIPTION     
            "A sonusDsx1PerfmonThresholdCrossingNotification trap indicates that a T1/E1 span
             performance monitoring threshold has been crossed. The type indicates the type
             of threshold."
    ::= 8

sonusDsx1PerfmonIntervalStartedNotification TRAP-TYPE
    ENTERPRISE      sonusDsx1MIBNotifications
    VARIABLES       { sonusShelfIndex, sonusSlotIndex, sonusPortIndex, 
                      sonusDs1Index, sonusDs1PmonIntervalType, 
                      sonusEventDescription, sonusEventClass, 
                      sonusEventLevel, sonusSequenceId, sonusEventTime }
--     STATUS          mandatory
    DESCRIPTION     
            "A  sonusDsx1PerfmonIntervalStartedNotification trap indicates that a new
             15 minute or 24 hour performance monitoring interval has started."
    ::= 10

END -- end of module SONUS-DS1THRESHOLD-MIB.
