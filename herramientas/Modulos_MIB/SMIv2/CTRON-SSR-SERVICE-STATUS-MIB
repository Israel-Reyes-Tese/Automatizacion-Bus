--
-- This SMIv2 module has been generated by smidump 0.2-cvs. Do not edit.
--

CTRON-SSR-SERVICE-STATUS-MIB DEFINITIONS ::= BEGIN

IMPORTS
    ssrMibs
        FROM CTRON-SSR-SMI-MIB
    MODULE-COMPLIANCE, OBJECT-GROUP
        FROM SNMPv2-CONF
    MODULE-IDENTITY, OBJECT-TYPE
        FROM SNMPv2-SMI
    TEXTUAL-CONVENTION
        FROM SNMPv2-TC;

serviceStatusMIB MODULE-IDENTITY
    LAST-UPDATED    "200006270000Z"
    ORGANIZATION    
            "Cabletron Systems, Inc."
    CONTACT-INFO    
            "Riverstone Networks, Inc
             5200 Great America Parkway
             Santa Clara, CA 95054
             (408) 878-6500
             nms-eng@riverstonenet.com
             http://www.riverstonenet.com"
    DESCRIPTION     
            "This module describes a schema for accessing the
             Smart Switch Router subsystems."
    REVISION        "200006270000Z"
    DESCRIPTION     
            "Revision 2.0 Update contact information for Riverstone Networks as this mib
             is found on the Riverstione RS product line as well as Enterasys SSR product line."
    REVISION        "199808040000Z"
    DESCRIPTION     
            "Revision 1.1 Flow Accounting Function and RMON visible."
    REVISION        "199804081200Z"
    DESCRIPTION     
            "Revision 1.0 Initial mib revision."
    ::= { ssrMibs 700 }


ServiceStatus ::= TEXTUAL-CONVENTION
    DISPLAY-HINT    "d"
    STATUS          current
    DESCRIPTION     
            "The current state of the service: started indicates 
             the service is configured and running. Stopped indicates
             the service is administratively down. notWorking indicates
             the service has failed."
    SYNTAX          INTEGER { started(1), stopped(2), notWorking(3) }

serviceStatusGroup OBJECT IDENTIFIER
    ::= { ssrMibs 4 }

serviceStatusRip OBJECT-TYPE
    SYNTAX          ServiceStatus
    MAX-ACCESS      read-only
    STATUS          current
    DESCRIPTION     
            "The current status of RIP in the switch."
    ::= { serviceStatusGroup 1 }

serviceStatusOspf OBJECT-TYPE
    SYNTAX          ServiceStatus
    MAX-ACCESS      read-only
    STATUS          current
    DESCRIPTION     
            "The current status of OSPF in the switch."
    ::= { serviceStatusGroup 2 }

serviceStatusBgp OBJECT-TYPE
    SYNTAX          ServiceStatus
    MAX-ACCESS      read-only
    STATUS          current
    DESCRIPTION     
            "The current status of BGP in the switch."
    ::= { serviceStatusGroup 3 }

serviceStatusDvmrp OBJECT-TYPE
    SYNTAX          ServiceStatus
    MAX-ACCESS      read-only
    STATUS          current
    DESCRIPTION     
            "The current status of DVMRP in the switch."
    ::= { serviceStatusGroup 4 }

serviceStatusIgmp OBJECT-TYPE
    SYNTAX          ServiceStatus
    MAX-ACCESS      read-only
    STATUS          current
    DESCRIPTION     
            "The current status of IGMP in the switch."
    ::= { serviceStatusGroup 5 }

serviceStatusPim OBJECT-TYPE
    SYNTAX          ServiceStatus
    MAX-ACCESS      read-only
    STATUS          current
    DESCRIPTION     
            "The current status of PIM in the switch."
    ::= { serviceStatusGroup 6 }

serviceStatusStp OBJECT-TYPE
    SYNTAX          ServiceStatus
    MAX-ACCESS      read-only
    STATUS          current
    DESCRIPTION     
            "The current status of STP in the switch."
    ::= { serviceStatusGroup 7 }

serviceStatusIpxRip OBJECT-TYPE
    SYNTAX          ServiceStatus
    MAX-ACCESS      read-only
    STATUS          current
    DESCRIPTION     
            "The current status of IPX in the switch."
    ::= { serviceStatusGroup 8 }

serviceStatusIpxSap OBJECT-TYPE
    SYNTAX          ServiceStatus
    MAX-ACCESS      read-only
    STATUS          current
    DESCRIPTION     
            "The current status of IPX in the switch."
    ::= { serviceStatusGroup 9 }

serviceStatusLfap OBJECT-TYPE
    SYNTAX          ServiceStatus
    MAX-ACCESS      read-only
    STATUS          current
    DESCRIPTION     
            "The current status of Lightweight Flow Accounting Protocol."
    ::= { serviceStatusGroup 10 }

serviceStatusRmon OBJECT-TYPE
    SYNTAX          ServiceStatus
    MAX-ACCESS      read-only
    STATUS          current
    DESCRIPTION     
            "The current status of RMON."
    ::= { serviceStatusGroup 11 }

ssConformance OBJECT IDENTIFIER
    ::= { serviceStatusMIB 2 }

ssCompliances OBJECT IDENTIFIER
    ::= { ssConformance 1 }

ssGroups OBJECT IDENTIFIER
    ::= { ssConformance 2 }

ssConfGroupV10 OBJECT-GROUP
    OBJECTS         { serviceStatusRip, serviceStatusOspf, 
                      serviceStatusBgp, serviceStatusDvmrp, 
                      serviceStatusIgmp, serviceStatusPim, 
                      serviceStatusStp, serviceStatusIpxRip, 
                      serviceStatusIpxSap }
    STATUS          obsolete
    DESCRIPTION     
            "A set of managed objects that make up version 1.0 of the SSR Service Status mib."
    ::= { ssGroups 1 }

ssConfGroupV11 OBJECT-GROUP
    OBJECTS         { serviceStatusRip, serviceStatusOspf, 
                      serviceStatusBgp, serviceStatusDvmrp, 
                      serviceStatusIgmp, serviceStatusPim, 
                      serviceStatusStp, serviceStatusIpxRip, 
                      serviceStatusIpxSap, serviceStatusLfap, 
                      serviceStatusRmon }
    STATUS          current
    DESCRIPTION     
            "A set of managed objects that make up version 1.1 of the SSR Service Status mib."
    ::= { ssGroups 2 }

ssComplianceV10 MODULE-COMPLIANCE
    STATUS          obsolete
    DESCRIPTION     
            "The compliance statement for the CTRON-SSR-SERVICE-STATUS-MIB."

    MODULE          -- this module

    ::= { ssConfGroupV10 1 }

ssComplianceV11 MODULE-COMPLIANCE
    STATUS          current
    DESCRIPTION     
            "The compliance statement for the CTRON-SSR-SERVICE-STATUS-MIB."

    MODULE          -- this module

        MANDATORY-GROUPS    { ssConfGroupV11 }

    ::= { ssConfGroupV10 2 }

END -- end of module CTRON-SSR-SERVICE-STATUS-MIB.
