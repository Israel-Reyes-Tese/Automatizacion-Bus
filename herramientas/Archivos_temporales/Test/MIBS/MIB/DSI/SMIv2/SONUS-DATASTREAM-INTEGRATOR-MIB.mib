--
-- This SMIv2 module has been generated by smidump 0.2-cvs. Do not edit.
--

SONUS-DATASTREAM-INTEGRATOR-MIB DEFINITIONS ::= BEGIN

IMPORTS
    amaInPriFilesMiss, amaOutPriFilesMiss, amaStoragePriOccuThres, 
    sessionCompIndex, sessionFtpAuthenFailLoc, sessionFtpAuthenFailRem, 
    sessionFtpMSessionsFail, sessionFtpMaxConsecRetries, 
    sessionFtpSessionFail
        FROM Gr1343Core-MIB
    hrDeviceErrors, hrDeviceIndex, hrStorageAllocationFailures, 
    hrStorageIndex
        FROM HOST-RESOURCES-MIB
    InetAddress, InetAddressType
        FROM INET-ADDRESS-MIB
    ifIndex, ifOperStatus
        FROM RFC1213-MIB
    Counter32, Integer32, MODULE-IDENTITY, NOTIFICATION-TYPE, 
    OBJECT-TYPE
        FROM SNMPv2-SMI
    DisplayString, RowStatus, TEXTUAL-CONVENTION
        FROM SNMPv2-TC
    sonusEventClass, sonusEventDescription, sonusEventLevel, 
    sonusEventTime
        FROM SONUS-COMMON-MIB
    sonusHostID
        FROM SONUS-HOST-MIB
    sonusSystemMIBs
        FROM SONUS-SMI;

sonusDSIMIB MODULE-IDENTITY
    LAST-UPDATED    "201109230000Z"
    ORGANIZATION    
            "Sonus Networks, Inc."
    CONTACT-INFO    
            "   Customer Support    
             Sonus Networks, Inc.
             250 Apollo Drive
             Chelmsford, MA 01824
             USA
             
             Tel: 978-614-8100
             Fax: 978-614-8609"
    DESCRIPTION     
            "The MIB Module for DataStreamIntegrator (DSI) Server Management."
    ::= { sonusSystemMIBs 9 }


SonusDSIAlarmStatus ::= TEXTUAL-CONVENTION
    STATUS          current
    DESCRIPTION     
            "Describes whether alarm is set or clear."
    SYNTAX          INTEGER { clear(1), set(2) }

SonusDSIClusterName ::= TEXTUAL-CONVENTION
    STATUS          current
    DESCRIPTION     
            "Describes which dsi cluster raised this alarm."
    SYNTAX          DisplayString (SIZE(0..64))

SonusDSINodeType ::= TEXTUAL-CONVENTION
    STATUS          current
    DESCRIPTION     
            "Describes which dsi cluster raised this alarm."
    SYNTAX          INTEGER { none(0), mnode(1), cnode(2) }

SonusDSIConnStatus ::= TEXTUAL-CONVENTION
    STATUS          current
    DESCRIPTION     
            "Describes the connection status."
    SYNTAX          INTEGER { up(1), down(2) }

SonusDSIProcessName ::= TEXTUAL-CONVENTION
    STATUS          current
    DESCRIPTION     
            "Describes which process this alarm relates to."
    SYNTAX          DisplayString (SIZE(0..64))

sonusDSIMIBObjects OBJECT IDENTIFIER
    ::= { sonusDSIMIB 1 }

sonusDSIMIBNotifications OBJECT IDENTIFIER
    ::= { sonusDSIMIB 2 }

sonusDSIMIBNotificationsPrefix OBJECT IDENTIFIER
    ::= { sonusDSIMIBNotifications 0 }

sonusDSIMIBNotificationsObjects OBJECT IDENTIFIER
    ::= { sonusDSIMIBNotifications 1 }

sonusDSIAlarmStatus OBJECT-TYPE
    SYNTAX          SonusDSIAlarmStatus
    MAX-ACCESS      read-only
    STATUS          current
    DESCRIPTION     
            "A description of the event that generated the trap."
    ::= { sonusDSIMIBNotificationsObjects 1 }

sonusDSIhrStorageWriteFailures OBJECT-TYPE
    SYNTAX          Counter32
    MAX-ACCESS      read-only
    STATUS          current
    DESCRIPTION     
            " "
    ::= { sonusDSIMIBNotificationsObjects 2 }

sonusDSIhrStorageReadFailures OBJECT-TYPE
    SYNTAX          Counter32
    MAX-ACCESS      read-only
    STATUS          current
    DESCRIPTION     
            " "
    ::= { sonusDSIMIBNotificationsObjects 3 }

sonusDSIClusterName OBJECT-TYPE
    SYNTAX          SonusDSIClusterName
    MAX-ACCESS      read-only
    STATUS          current
    DESCRIPTION     
            "A description of the dsi cluster name that generated the trap."
    ::= { sonusDSIMIBNotificationsObjects 4 }

sonusDSINodeType OBJECT-TYPE
    SYNTAX          SonusDSINodeType
    MAX-ACCESS      read-only
    STATUS          current
    DESCRIPTION     
            "A description of the dsi cluster node type that generated the trap."
    ::= { sonusDSIMIBNotificationsObjects 5 }

sonusDSIBPAConnStatus OBJECT-TYPE
    SYNTAX          SonusDSIConnStatus
    MAX-ACCESS      read-only
    STATUS          current
    DESCRIPTION     
            "BPA connection status."
    ::= { sonusDSIMIBNotificationsObjects 6 }

sonusDSISaiConnStatus OBJECT-TYPE
    SYNTAX          SonusDSIConnStatus
    MAX-ACCESS      read-only
    STATUS          current
    DESCRIPTION     
            "Transporter client connection status."
    ::= { sonusDSIMIBNotificationsObjects 7 }

sonusDSIBECommErrorReason OBJECT-TYPE
    SYNTAX          INTEGER { connectionfailure(1), portqueryfailure(2), 
                        portconnectionfailure(3), cdrtransferfailure(4), 
                        healthcheckfailure(5), invaliddelimiter(6), 
                        invalidusertype(7), brokensocket(8), 
                        streamingConnectionFailure(17), 
                        streamingHealthcheckFailure(18), 
                        streamingBrokenSocket(19) }
    MAX-ACCESS      read-only
    STATUS          current
    DESCRIPTION     
            "Specifies a communication problem between 
             the backend stream server and the BPA."
    ::= { sonusDSIMIBNotificationsObjects 8 }

sonusDSIFileSourceAddressType OBJECT-TYPE
    SYNTAX          InetAddressType
    MAX-ACCESS      read-only
    STATUS          current
    DESCRIPTION     
            "The IP Address type of the file source."
    ::= { sonusDSIMIBNotificationsObjects 9 }

sonusDSIFileSourceAddress OBJECT-TYPE
    SYNTAX          InetAddress
    MAX-ACCESS      read-only
    STATUS          deprecated
    DESCRIPTION     
            "The IP Address of the file source."
    ::= { sonusDSIMIBNotificationsObjects 10 }

sonusDSIProcessName OBJECT-TYPE
    SYNTAX          SonusDSIProcessName
    MAX-ACCESS      read-only
    STATUS          current
    DESCRIPTION     
            "The dsi process name for which the trap is raised."
    ::= { sonusDSIMIBNotificationsObjects 11 }

sonusDSIVersionErrorFileName OBJECT-TYPE
    SYNTAX          DisplayString (SIZE(0..64))
    MAX-ACCESS      read-only
    STATUS          current
    DESCRIPTION     
            "The file name which contains a version error."
    ::= { sonusDSIMIBNotificationsObjects 12 }

sonusDSIUnprocessedFileCount OBJECT-TYPE
    SYNTAX          Integer32
    MAX-ACCESS      read-only
    STATUS          current
    DESCRIPTION     
            "Number of unprocessed files."
    ::= { sonusDSIMIBNotificationsObjects 13 }

sonusDSINewMaster OBJECT-TYPE
    SYNTAX          DisplayString (SIZE(0..64))
    MAX-ACCESS      read-only
    STATUS          current
    DESCRIPTION     
            "The new master dsi."
    ::= { sonusDSIMIBNotificationsObjects 14 }

sonusDSINewLoadPolicy OBJECT-TYPE
    SYNTAX          INTEGER { roundrobin(1), weightedroundrobin(2), 
                        leastloaded(3) }
    MAX-ACCESS      read-only
    STATUS          current
    DESCRIPTION     
            "Specifies the new load distribution policy."
    ::= { sonusDSIMIBNotificationsObjects 15 }

sonusDsiBEAmaClosingStatus OBJECT-TYPE
    SYNTAX          INTEGER { manualClosingSuccessful(1), 
                        manualClosingRejected(2), 
                        automaticClosingSuccessful(3), 
                        automaticClosingRejected(4), 
                        automaticClosing64CdrFilesReached(5) }
    MAX-ACCESS      read-only
    STATUS          current
    DESCRIPTION     
            "Specifies the AMA file automatic or manual  
             closing request status."
    ::= { sonusDSIMIBNotificationsObjects 16 }

sonusDsiBEAmaClosingFileName OBJECT-TYPE
    SYNTAX          DisplayString (SIZE(0..255))
    MAX-ACCESS      read-only
    STATUS          current
    DESCRIPTION     
            "Specifies the name of current AMA file being   
             closed or close request is rejected for 
             automatic or manual closing."
    ::= { sonusDSIMIBNotificationsObjects 17 }

sonusDsiBEDatTransferStatus OBJECT-TYPE
    SYNTAX          INTEGER { transferCompleted(1), 
                        transferRequestRejected(2) }
    MAX-ACCESS      read-only
    STATUS          current
    DESCRIPTION     
            "Specifies the AMA file DAT Transfer status."
    ::= { sonusDSIMIBNotificationsObjects 18 }

sonusDsiBEDatTransferFileName OBJECT-TYPE
    SYNTAX          DisplayString (SIZE(0..255))
    MAX-ACCESS      read-only
    STATUS          current
    DESCRIPTION     
            "Specifies the name of the TAR for created by 
             DAT Transfer command."
    ::= { sonusDSIMIBNotificationsObjects 19 }

sonusDsiBERtTransferStatus OBJECT-TYPE
    SYNTAX          INTEGER { realtimeTransferResumed(1), 
                        realtimeTransferSuspended(2) }
    MAX-ACCESS      read-only
    STATUS          current
    DESCRIPTION     
            "Specifies the Backend Stream Server 
             Real-time Transfer status."
    ::= { sonusDSIMIBNotificationsObjects 20 }

sonusDSIRecoveryFileName OBJECT-TYPE
    SYNTAX          DisplayString
    MAX-ACCESS      read-only
    STATUS          current
    DESCRIPTION     
            "The absolute filename of failed job moved to recovery."
    ::= { sonusDSIMIBNotificationsObjects 21 }

sonusDSIDropFileName OBJECT-TYPE
    SYNTAX          DisplayString
    MAX-ACCESS      read-only
    STATUS          current
    DESCRIPTION     
            "The relative filename contains dropped records from a job due to field validations."
    ::= { sonusDSIMIBNotificationsObjects 22 }

sonusDSIStrandedFile OBJECT-TYPE
    SYNTAX          DisplayString
    MAX-ACCESS      read-only
    STATUS          current
    DESCRIPTION     
            "Health Monitor found Stranded file,duration crossed high watermark."
    ::= { sonusDSIMIBNotificationsObjects 23 }

sonusDSIIdleTime OBJECT-TYPE
    SYNTAX          DisplayString
    MAX-ACCESS      read-only
    STATUS          current
    DESCRIPTION     
            "Health Monitor Idle time threshold crossed."
    ::= { sonusDSIMIBNotificationsObjects 24 }

sonusDSIClearIdleTime OBJECT-TYPE
    SYNTAX          DisplayString
    MAX-ACCESS      read-only
    STATUS          current
    DESCRIPTION     
            "Clear Health Monitor Idle time threshold crossed alarm."
    ::= { sonusDSIMIBNotificationsObjects 25 }

sonusDSIAppValidation OBJECT-TYPE
    SYNTAX          DisplayString
    MAX-ACCESS      read-only
    STATUS          current
    DESCRIPTION     
            "Health Monitor App File validation failed."
    ::= { sonusDSIMIBNotificationsObjects 26 }

sonusDSISAIDuplicateCDR OBJECT-TYPE
    SYNTAX          DisplayString
    MAX-ACCESS      read-only
    STATUS          current
    DESCRIPTION     
            "Duplicate CDR received by SAI server from TC."
    ::= { sonusDSIMIBNotificationsObjects 27 }

sonusDSISAIRetransmittedCDR OBJECT-TYPE
    SYNTAX          DisplayString
    MAX-ACCESS      read-only
    STATUS          current
    DESCRIPTION     
            "Retransmitted CDR received by SAI server from TC."
    ::= { sonusDSIMIBNotificationsObjects 28 }

sonusDsiMemInfo OBJECT-TYPE
    SYNTAX          DisplayString
    MAX-ACCESS      read-only
    STATUS          current
    DESCRIPTION     
            "Health Monitor detected process memory growth reached high watermark."
    ::= { sonusDSIMIBNotificationsObjects 29 }

sonusDsiDiskInfo OBJECT-TYPE
    SYNTAX          DisplayString
    MAX-ACCESS      read-only
    STATUS          current
    DESCRIPTION     
            "Health Monitor detected disk usage reached high watermark."
    ::= { sonusDSIMIBNotificationsObjects 30 }

sonusDsiCoreInfo OBJECT-TYPE
    SYNTAX          DisplayString
    MAX-ACCESS      read-only
    STATUS          current
    DESCRIPTION     
            "Health Monitor detected number of core files reached high watermark."
    ::= { sonusDSIMIBNotificationsObjects 31 }

sonusDsiFileInfo OBJECT-TYPE
    SYNTAX          DisplayString
    MAX-ACCESS      read-only
    STATUS          current
    DESCRIPTION     
            "Health Monitor detected number of files reached high watermark."
    ::= { sonusDSIMIBNotificationsObjects 32 }

sonusDSIFileSourceInetAddress OBJECT-TYPE
    SYNTAX          InetAddress
    MAX-ACCESS      read-only
    STATUS          current
    DESCRIPTION     
            "The IP Address of the file source."
    ::= { sonusDSIMIBNotificationsObjects 33 }

sonusDSIDisk100PercentFullNotification NOTIFICATION-TYPE
    OBJECTS         { sonusEventDescription, sonusEventClass, 
                      sonusEventLevel, sonusEventTime, 
                      sonusDSIAlarmStatus, hrStorageIndex, 
                      hrStorageAllocationFailures, sonusDSIClusterName, 
                      sonusDSINodeType, sonusHostID }
    STATUS          current
    DESCRIPTION     
            "This trap with SonusDSIAlarmStatus=set indicates that
             the DSI has used all the disk space assigned to it.
             with SonusDSIAlarmStatus=clear it indicates that the disk 
             no longer full."
    ::= { sonusDSIMIBNotificationsPrefix 1 }

sonusDSIPriAMAOccuThresExcededNotification NOTIFICATION-TYPE
    OBJECTS         { sonusEventDescription, sonusEventClass, 
                      sonusEventLevel, sonusEventTime, 
                      sonusDSIAlarmStatus, hrDeviceIndex, 
                      amaStoragePriOccuThres, sonusDSIClusterName, 
                      sonusDSINodeType, sonusHostID }
    STATUS          current
    DESCRIPTION     
            "This trap with SonusDSIAlarmStatus=set indicates that the DSI has 
             used 90 percent of the disk space assigned to it. With 
             SonusDSIAlarmStatus=clear it indicates that the disk no longer 
             90 percent full, the value of amaStoragePriOccuThres=90%"
    ::= { sonusDSIMIBNotificationsPrefix 2 }

sonusDSIDisk75PercentFullNotification NOTIFICATION-TYPE
    OBJECTS         { sonusEventDescription, sonusEventClass, 
                      sonusEventLevel, sonusEventTime, 
                      sonusDSIAlarmStatus, sonusDSIClusterName, 
                      sonusDSINodeType, sonusHostID }
    STATUS          current
    DESCRIPTION     
            "This trap with SonusDSIAlarmStatus=set indicates that
             the DSI has used 75 percent of the disk space assigned to it.
             with SonusDSIAlarmStatus=clear it indicates that the disk 
             no longer 75 percent full."
    ::= { sonusDSIMIBNotificationsPrefix 3 }

sonusDSIDisk50PercentFullNotification NOTIFICATION-TYPE
    OBJECTS         { sonusEventDescription, sonusEventClass, 
                      sonusEventLevel, sonusEventTime, 
                      sonusDSIAlarmStatus, sonusDSIClusterName, 
                      sonusDSINodeType, sonusHostID }
    STATUS          current
    DESCRIPTION     
            "This trap with SonusDSIAlarmStatus=set indicates that
             the DSI has used 50 percent of the disk space assigned to it.
             with SonusDSIAlarmStatus=clear it indicates that the disk 
             no longer 50 percent full."
    ::= { sonusDSIMIBNotificationsPrefix 4 }

sonusDSIDiskWriteStatusNotification NOTIFICATION-TYPE
    OBJECTS         { sonusEventDescription, sonusEventClass, 
                      sonusEventLevel, sonusEventTime, 
                      sonusDSIAlarmStatus, hrStorageIndex, 
                      sonusDSIhrStorageWriteFailures, 
                      sonusDSIClusterName, sonusDSINodeType, sonusHostID }
    STATUS          current
    DESCRIPTION     
            "This trap is a warning to indicate that the DSI has failed 
             to write to the disk. Value of SonusDSIAlarmStatus indecates
             whether it is to set or clear."
    ::= { sonusDSIMIBNotificationsPrefix 5 }

sonusDSICDRFileReadStatusNotification NOTIFICATION-TYPE
    OBJECTS         { sonusEventDescription, sonusEventClass, 
                      sonusEventLevel, sonusEventTime, 
                      sonusDSIAlarmStatus, sonusDSIClusterName, 
                      sonusDSINodeType, sonusHostID }
    STATUS          current
    DESCRIPTION     
            "This trap is a warning to indicate that the DSI has failed to 
             open or read a CDR file. Value of SonusDSIAlarmStatus indecates
             whether it is to set or clear."
    ::= { sonusDSIMIBNotificationsPrefix 6 }

sonusDSICDRRecordStatusNotification NOTIFICATION-TYPE
    OBJECTS         { sonusEventDescription, sonusEventClass, 
                      sonusEventLevel, sonusEventTime, 
                      sonusDSIAlarmStatus, sonusDSIClusterName, 
                      sonusDSINodeType, sonusHostID }
    STATUS          current
    DESCRIPTION     
            "This trap is a warning to indicate that the DSI has detected
             a bad CDR record. Value of SonusDSIAlarmStatus indecates
             whether it is to set or clear."
    ::= { sonusDSIMIBNotificationsPrefix 7 }

sonusDSICDRSequenceStatusNotification NOTIFICATION-TYPE
    OBJECTS         { sonusEventDescription, sonusEventClass, 
                      sonusEventLevel, sonusEventTime, 
                      sonusDSIAlarmStatus, sonusDSIClusterName, 
                      sonusDSINodeType, sonusHostID }
    STATUS          current
    DESCRIPTION     
            "This trap is a warning to indicate that the DSI has detected 
             a missing CDR. Value of SonusDSIAlarmStatus indecates
             whether it is to set or clear."
    ::= { sonusDSIMIBNotificationsPrefix 8 }

sonusDSIFilePullStatusNotification NOTIFICATION-TYPE
    OBJECTS         { sonusEventDescription, sonusEventClass, 
                      sonusEventLevel, sonusEventTime, 
                      sonusDSIAlarmStatus, sonusDSIClusterName, 
                      sonusDSINodeType, sonusHostID }
    STATUS          current
    DESCRIPTION     
            "This trap is a warning to indicate that the DM of the DSI has 
             failed to transfer an AMA file to the DM. Value of
             SonusDSIAlarmStatus indecates whether it is to set or clear."
    ::= { sonusDSIMIBNotificationsPrefix 9 }

sonusDSIDDIProtocolDM1StatusNotification NOTIFICATION-TYPE
    OBJECTS         { sonusEventDescription, sonusEventClass, 
                      sonusEventLevel, sonusEventTime, 
                      sonusDSIAlarmStatus, sonusDSIClusterName, 
                      sonusDSINodeType, sonusHostID }
    STATUS          current
    DESCRIPTION     
            "This trap is a warning to indicate that the DSI has detected an
             FTP protocol error during an AMA file pull session. Value of 
             SonusDSIAlarmStatus indecates whether it is to set or clear."
    ::= { sonusDSIMIBNotificationsPrefix 10 }

sonusDSIDDIProtocolDM2StatusNotification NOTIFICATION-TYPE
    OBJECTS         { sonusEventDescription, sonusEventClass, 
                      sonusEventLevel, sonusEventTime, 
                      sonusDSIAlarmStatus, sonusDSIClusterName, 
                      sonusDSINodeType, sonusHostID }
    STATUS          current
    DESCRIPTION     
            "This trap is a warning to indicate that the DSI has detected an
             FTP protocol error during an AMA file pull session. Value of
             SonusDSIAlarmStatus indecates whether it is to set or clear."
    ::= { sonusDSIMIBNotificationsPrefix 11 }

sonusDSIDDIProtocolDM3StatusNotification NOTIFICATION-TYPE
    OBJECTS         { sonusEventDescription, sonusEventClass, 
                      sonusEventLevel, sonusEventTime, 
                      sonusDSIAlarmStatus, sonusDSIClusterName, 
                      sonusDSINodeType, sonusHostID }
    STATUS          current
    DESCRIPTION     
            "This trap is a warning to indicate that the DSI has detected an
             FTP protocol error during an AMA file pull session. Value of 
             SonusDSIAlarmStatus indecates whether it is to set or clear."
    ::= { sonusDSIMIBNotificationsPrefix 12 }

sonusDSIDDIProtocolDM4StatusNotification NOTIFICATION-TYPE
    OBJECTS         { sonusEventDescription, sonusEventClass, 
                      sonusEventLevel, sonusEventTime, 
                      sonusDSIAlarmStatus, sonusDSIClusterName, 
                      sonusDSINodeType, sonusHostID }
    STATUS          current
    DESCRIPTION     
            "This trap is a warning to indicate that the DSI has detected an
             FTP protocol error during an AMA file pull session. Value of
             SonusDSIAlarmStatus indecates whether it is to set or clear."
    ::= { sonusDSIMIBNotificationsPrefix 13 }

sonusDSIDDIProtocolGenericStatusNotification NOTIFICATION-TYPE
    OBJECTS         { sonusEventDescription, sonusEventClass, 
                      sonusEventLevel, sonusEventTime, 
                      sonusDSIAlarmStatus, sonusDSIClusterName, 
                      sonusDSINodeType, sonusHostID }
    STATUS          current
    DESCRIPTION     
            "This trap is a warning to indicate that the DSI has detected an 
             FTP protocol error during an AMA file pull session. Value of
             SonusDSIAlarmStatus indecates whether it is to set or clear."
    ::= { sonusDSIMIBNotificationsPrefix 14 }

sonusDSITestAlarmNotification NOTIFICATION-TYPE
    OBJECTS         { sonusEventDescription, sonusEventClass, 
                      sonusEventLevel, sonusEventTime, 
                      sonusDSIAlarmStatus, sonusDSIClusterName, 
                      sonusDSINodeType, sonusHostID }
    STATUS          current
    DESCRIPTION     
            "This trap indicates that the DSI has received a Test Alarm command
             from the CLI. Value of SonusDSIAlarmStatus indecates whether it is
             to set or clear."
    ::= { sonusDSIMIBNotificationsPrefix 15 }

sonusDSIDiskReadStatusNotificatin NOTIFICATION-TYPE
    OBJECTS         { sonusEventDescription, sonusEventClass, 
                      sonusEventLevel, sonusEventTime, 
                      sonusDSIAlarmStatus, hrStorageIndex, 
                      sonusDSIhrStorageReadFailures, sonusDSIClusterName, 
                      sonusDSINodeType, sonusHostID }
    STATUS          current
    DESCRIPTION     
            ""
    ::= { sonusDSIMIBNotificationsPrefix 16 }

sonusDSIFtpSessionFailNotification NOTIFICATION-TYPE
    OBJECTS         { sonusEventDescription, sonusEventClass, 
                      sonusEventLevel, sonusEventTime, 
                      sonusDSIAlarmStatus, sessionCompIndex, 
                      sessionFtpSessionFail, sonusDSIClusterName, 
                      sonusDSINodeType, sonusHostID }
    STATUS          current
    DESCRIPTION     
            "An attempt to establish FTP session failed. Automatically clears when the
             next FTP session is completed successfully, or when a Persistent FTP
             session failure alarm is issued."
    ::= { sonusDSIMIBNotificationsPrefix 17 }

sonusDSIFtpPersSessionFailNotification NOTIFICATION-TYPE
    OBJECTS         { sonusEventDescription, sonusEventClass, 
                      sonusEventLevel, sonusEventTime, 
                      sonusDSIAlarmStatus, sessionCompIndex, 
                      sessionFtpMaxConsecRetries, 
                      sessionFtpMSessionsFail, sonusDSIClusterName, 
                      sonusDSINodeType, sonusHostID }
    STATUS          current
    DESCRIPTION     
            "When FTP Session Failure counter reaches the value of the
             sessionFtpMaxConsecRetries. Automatically clears when the next FTP
             session is completed successfully."
    ::= { sonusDSIMIBNotificationsPrefix 18 }

sonusDSIFtpFailedAuthenNotification NOTIFICATION-TYPE
    OBJECTS         { sonusEventDescription, sonusEventClass, 
                      sonusEventLevel, sonusEventTime, 
                      sonusDSIAlarmStatus, sessionCompIndex, 
                      sessionFtpAuthenFailLoc, sonusDSIClusterName, 
                      sonusDSINodeType, sonusHostID }
    STATUS          current
    DESCRIPTION     
            "The DSI received a notification of FTP session authentication failure from
             the DPMS. Automatically clears when the next FTP session authentication
             is completed successfully."
    ::= { sonusDSIMIBNotificationsPrefix 19 }

sonusDSIFtpFailedAuthenRemoteNotification NOTIFICATION-TYPE
    OBJECTS         { sonusEventDescription, sonusEventClass, 
                      sonusEventLevel, sonusEventTime, 
                      sonusDSIAlarmStatus, sessionCompIndex, 
                      sessionFtpAuthenFailRem, sonusDSIClusterName, 
                      sonusDSINodeType, sonusHostID }
    STATUS          current
    DESCRIPTION     
            "The DSI failed an FTP session authentication attempt by the DPMS.
             Automatically clears when the next FTP session authentication is
             completed successfully."
    ::= { sonusDSIMIBNotificationsPrefix 20 }

sonusDSIFtpOutPriFileMissNotification NOTIFICATION-TYPE
    OBJECTS         { sonusEventDescription, sonusEventClass, 
                      sonusEventLevel, sonusEventTime, 
                      sonusDSIAlarmStatus, sessionCompIndex, 
                      amaOutPriFilesMiss, sonusDSIClusterName, 
                      sonusDSINodeType, sonusHostID }
    STATUS          current
    DESCRIPTION     
            "The DSI detected missing primary AMA files, which should have been sent to
             the DPMS. Automatically clears when the next FTP session is completed
             successfully."
    ::= { sonusDSIMIBNotificationsPrefix 21 }

sonusDSIInPriFilesMissNotification NOTIFICATION-TYPE
    OBJECTS         { sonusEventDescription, sonusEventClass, 
                      sonusEventLevel, sonusEventTime, 
                      sonusDSIAlarmStatus, sessionCompIndex, 
                      amaInPriFilesMiss, sonusDSIClusterName, 
                      sonusDSINodeType, sonusHostID }
    STATUS          current
    DESCRIPTION     
            "The DSI detected missing primary AMA/CDR files, which were not received
             from the GSX/PSX. Automatically clears when the next AMA/CDR files is
             received successfully by FCP."
    ::= { sonusDSIMIBNotificationsPrefix 22 }

sonusDSIDeviceStatusNotification NOTIFICATION-TYPE
    OBJECTS         { sonusEventDescription, sonusEventClass, 
                      sonusEventLevel, sonusEventTime, 
                      sonusDSIAlarmStatus, hrDeviceIndex, hrDeviceErrors, 
                      sonusDSIClusterName, sonusDSINodeType, sonusHostID }
    STATUS          deprecated
    DESCRIPTION     
            "HA Monitor detected a device error occurred. Automatically clears when the 
             device is working without any error again."
    ::= { sonusDSIMIBNotificationsPrefix 23 }

sonusDSIInterfaceDownNotification NOTIFICATION-TYPE
    OBJECTS         { sonusEventDescription, sonusEventClass, 
                      sonusEventLevel, sonusEventTime, 
                      sonusDSIAlarmStatus, ifIndex, ifOperStatus, 
                      sonusDSIClusterName, sonusDSINodeType, sonusHostID }
    STATUS          deprecated
    DESCRIPTION     
            "The operational status of the interface has just been changed to 
             down(2) by HA Monitor. Automatically clears when the interface is up again."
    ::= { sonusDSIMIBNotificationsPrefix 24 }

sonusDSIStorageStatusNotification NOTIFICATION-TYPE
    OBJECTS         { sonusEventDescription, sonusEventClass, 
                      sonusEventLevel, sonusEventTime, 
                      sonusDSIAlarmStatus, hrStorageIndex, 
                      sonusDSIClusterName, sonusDSINodeType, sonusHostID }
    STATUS          current
    DESCRIPTION     
            "HA Monitor detected a storage (disk) error occurred, Automatically clears
             when the storage is working without any error again."
    ::= { sonusDSIMIBNotificationsPrefix 25 }

sonusDSIApplicationFailureNotification NOTIFICATION-TYPE
    OBJECTS         { sonusEventDescription, sonusEventClass, 
                      sonusEventLevel, sonusEventTime, 
                      sonusDSIAlarmStatus, hrDeviceIndex, 
                      sonusDSIClusterName, sonusDSINodeType, sonusHostID }
    STATUS          current
    DESCRIPTION     
            "HA Monitor detected a DSI software failure, Automatically clears when the
             DSI software is running successfully again."
    ::= { sonusDSIMIBNotificationsPrefix 26 }

sonusDSIFailoverEventNotification NOTIFICATION-TYPE
    OBJECTS         { sonusEventDescription, sonusEventClass, 
                      sonusEventLevel, sonusEventTime, 
                      sonusDSIAlarmStatus, hrDeviceIndex, 
                      sonusDSIClusterName, sonusDSINodeType, sonusHostID }
    STATUS          current
    DESCRIPTION     
            "A system fail-over (from an active server to a standby server) occurred, 
             Must be cleared manually."
    ::= { sonusDSIMIBNotificationsPrefix 27 }

sonusDSITelnetFailedAuthenNotification NOTIFICATION-TYPE
    OBJECTS         { sonusEventDescription, sonusEventClass, 
                      sonusEventLevel, sonusEventTime, 
                      sonusDSIAlarmStatus, sessionCompIndex, 
                      sonusDSIClusterName, sonusDSINodeType, sonusHostID }
    STATUS          current
    DESCRIPTION     
            "The DSI received a notification of cli telnet authentication failure. 
             Requires a manual clear."
    ::= { sonusDSIMIBNotificationsPrefix 28 }

sonusDSIStorageAllocFailureNotification NOTIFICATION-TYPE
    OBJECTS         { sonusEventDescription, sonusEventClass, 
                      sonusEventLevel, sonusEventTime, 
                      sonusDSIAlarmStatus, sessionCompIndex, 
                      sonusDSIClusterName, sonusDSINodeType, sonusHostID }
    STATUS          current
    DESCRIPTION     
            "The DSI failed to allocate needed storage on a disk drive. 
             Requires a manual clear."
    ::= { sonusDSIMIBNotificationsPrefix 29 }

sonusDSIStorageWriteFailureNotification NOTIFICATION-TYPE
    OBJECTS         { sonusEventDescription, sonusEventClass, 
                      sonusEventLevel, sonusEventTime, 
                      sonusDSIAlarmStatus, sessionCompIndex, 
                      sonusDSIClusterName, sonusDSINodeType, sonusHostID }
    STATUS          current
    DESCRIPTION     
            "The DSI failed to write to needed storage on a disk drive. 
             Requires a manual clear."
    ::= { sonusDSIMIBNotificationsPrefix 30 }

sonusDSIStorageReadFailureNotification NOTIFICATION-TYPE
    OBJECTS         { sonusEventDescription, sonusEventClass, 
                      sonusEventLevel, sonusEventTime, 
                      sonusDSIAlarmStatus, sessionCompIndex, 
                      sonusDSIClusterName, sonusDSINodeType, sonusHostID }
    STATUS          current
    DESCRIPTION     
            "The DSI failed to read needed storage on a disk drive. 
             Requires a manual clear."
    ::= { sonusDSIMIBNotificationsPrefix 31 }

sonusDSISequenceRestartNotification NOTIFICATION-TYPE
    OBJECTS         { sonusEventDescription, sonusEventClass, 
                      sonusEventLevel, sonusEventTime, 
                      sonusDSIAlarmStatus, sessionCompIndex, 
                      sonusDSIClusterName, sonusDSINodeType, sonusHostID }
    STATUS          current
    DESCRIPTION     
            "The DSI lost the AMA sequence and has restarted. 
             Requires a manual clear."
    ::= { sonusDSIMIBNotificationsPrefix 32 }

sonusDSISoftwareErrorNotification NOTIFICATION-TYPE
    OBJECTS         { sonusEventDescription, sonusEventClass, 
                      sonusEventLevel, sonusEventTime, 
                      sonusDSIAlarmStatus, sessionCompIndex, 
                      sonusDSIClusterName, sonusDSINodeType, sonusHostID }
    STATUS          current
    DESCRIPTION     
            "The DSI had a critical software error. 
             Requires a manual clear."
    ::= { sonusDSIMIBNotificationsPrefix 33 }

sonusDSIShutdownNotification NOTIFICATION-TYPE
    OBJECTS         { sonusEventDescription, sonusEventClass, 
                      sonusEventLevel, sonusEventTime, 
                      sonusDSIAlarmStatus, sessionCompIndex, 
                      sonusDSIClusterName, sonusDSINodeType, sonusHostID }
    STATUS          current
    DESCRIPTION     
            "The DSI has shutdown.  Automatically clears when DSI is  
             restarted."
    ::= { sonusDSIMIBNotificationsPrefix 34 }

sonusDSISNMPRestartNotification NOTIFICATION-TYPE
    OBJECTS         { sonusEventDescription, sonusEventClass, 
                      sonusEventLevel, sonusEventTime, 
                      sonusDSIAlarmStatus }
    STATUS          current
    DESCRIPTION     
            "The DSI SNMP Agent has restarted.  Automatically clears when DSI 
             SNMP Agent has recovered."
    ::= { sonusDSIMIBNotificationsPrefix 35 }

sonusDSICommFtpErrNotification NOTIFICATION-TYPE
    OBJECTS         { sonusEventDescription, sonusEventClass, 
                      sonusEventLevel, sonusEventTime, 
                      sonusDSIAlarmStatus }
    STATUS          current
    DESCRIPTION     
            "The DSI has experienced a Transporter Ftp Session Error. Cleared 
             when session error is resolved."
    ::= { sonusDSIMIBNotificationsPrefix 36 }

sonusDSICommFtpLoginErrNotification NOTIFICATION-TYPE
    OBJECTS         { sonusEventDescription, sonusEventClass, 
                      sonusEventLevel, sonusEventTime, 
                      sonusDSIAlarmStatus }
    STATUS          current
    DESCRIPTION     
            "The DSI has experienced a Transporter Ftp Login Error. Cleared 
             when login error is resolved."
    ::= { sonusDSIMIBNotificationsPrefix 37 }

sonusDSIFileSizeErrNotification NOTIFICATION-TYPE
    OBJECTS         { sonusEventDescription, sonusEventClass, 
                      sonusEventLevel, sonusEventTime, 
                      sonusDSIAlarmStatus }
    STATUS          current
    DESCRIPTION     
            "The DSI has experienced a File Size Error. Cleared 
             when File Size error is resolved."
    ::= { sonusDSIMIBNotificationsPrefix 38 }

sonusDSIFileTimeErrNotification NOTIFICATION-TYPE
    OBJECTS         { sonusEventDescription, sonusEventClass, 
                      sonusEventLevel, sonusEventTime, 
                      sonusDSIAlarmStatus }
    STATUS          current
    DESCRIPTION     
            "The DSI has experienced a File Time Error. Cleared 
             when File Time error is resolved."
    ::= { sonusDSIMIBNotificationsPrefix 39 }

sonusDSIDupRecordErrNotification NOTIFICATION-TYPE
    OBJECTS         { sonusEventDescription, sonusEventClass, 
                      sonusEventLevel, sonusEventTime, 
                      sonusDSIAlarmStatus }
    STATUS          current
    DESCRIPTION     
            "The DSI has experienced a Duplicate Record Error. Cleared 
             when the error is resolved."
    ::= { sonusDSIMIBNotificationsPrefix 40 }

sonusDSIIORenameErrNotification NOTIFICATION-TYPE
    OBJECTS         { sonusEventDescription, sonusEventClass, 
                      sonusEventLevel, sonusEventTime, 
                      sonusDSIAlarmStatus }
    STATUS          current
    DESCRIPTION     
            "The DSI has experienced an IO Error when renaming the file. Cleared 
             when error is resolved."
    ::= { sonusDSIMIBNotificationsPrefix 41 }

sonusDSIIORemoveErrNotification NOTIFICATION-TYPE
    OBJECTS         { sonusEventDescription, sonusEventClass, 
                      sonusEventLevel, sonusEventTime, 
                      sonusDSIAlarmStatus }
    STATUS          current
    DESCRIPTION     
            "The DSI has experienced an IO Error when removing the file. Cleared
             when error is resolved."
    ::= { sonusDSIMIBNotificationsPrefix 42 }

sonusDSIDBNotAccessibleNotification NOTIFICATION-TYPE
    OBJECTS         { sonusEventDescription, sonusEventClass, 
                      sonusEventLevel, sonusEventTime, 
                      sonusDSIAlarmStatus, sonusDSIClusterName, 
                      sonusDSINodeType, sonusHostID }
    STATUS          current
    DESCRIPTION     
            "The DSI had a critical DB Not Accessible error. 
             Automatically clears when DB is accessible."
    ::= { sonusDSIMIBNotificationsPrefix 43 }

sonusDSIConnectionAttemptFailNotifiction NOTIFICATION-TYPE
    OBJECTS         { sonusEventDescription, sonusEventClass, 
                      sonusEventLevel, sonusEventTime, 
                      sonusDSIAlarmStatus, sonusDSIClusterName, 
                      sonusDSINodeType, sonusHostID }
    STATUS          deprecated
    DESCRIPTION     
            "The DSI had a node connection attempt failed (Local %s, Remote %s, Reason %s) 
             Automatically clears when node connects ."
    ::= { sonusDSIMIBNotificationsPrefix 44 }

sonusDSINodeDisconnectedNotification NOTIFICATION-TYPE
    OBJECTS         { sonusEventDescription, sonusEventClass, 
                      sonusEventLevel, sonusEventTime, 
                      sonusDSIAlarmStatus, sonusDSIClusterName, 
                      sonusDSINodeType, sonusHostID }
    STATUS          deprecated
    DESCRIPTION     
            "The DSI had a node disconnected (with remote node name).
             Automatically clears with sonusDSINodeConnectedNotification ."
    ::= { sonusDSIMIBNotificationsPrefix 45 }

sonusDSINodeConnectedNotification NOTIFICATION-TYPE
    OBJECTS         { sonusEventDescription, sonusEventClass, 
                      sonusEventLevel, sonusEventTime, 
                      sonusDSIAlarmStatus, sonusDSIClusterName, 
                      sonusDSINodeType, sonusHostID }
    STATUS          deprecated
    DESCRIPTION     
            "The DSI had a node disconnected (with remote node name).
             Automatically clears when node connects ."
    ::= { sonusDSIMIBNotificationsPrefix 46 }

sonusDSINodeNotAccessibleNotification NOTIFICATION-TYPE
    OBJECTS         { sonusEventDescription, sonusEventClass, 
                      sonusEventLevel, sonusEventTime, 
                      sonusDSIAlarmStatus, sonusDSIClusterName, 
                      sonusDSINodeType, sonusHostID }
    STATUS          deprecated
    DESCRIPTION     
            "The DSI had a node not accessible (with remote node name).
             Automatically clears when node is accessible ."
    ::= { sonusDSIMIBNotificationsPrefix 47 }

sonusDSINodeRejectedNotification NOTIFICATION-TYPE
    OBJECTS         { sonusEventDescription, sonusEventClass, 
                      sonusEventLevel, sonusEventTime, 
                      sonusDSIAlarmStatus, sonusDSIClusterName, 
                      sonusDSINodeType, sonusHostID }
    STATUS          current
    DESCRIPTION     
            "The DSI rejected a node (with reason and node name).
             Automatically clears when node is accepted ."
    ::= { sonusDSIMIBNotificationsPrefix 48 }

sonusDSINodeOutOfServiceNotification NOTIFICATION-TYPE
    OBJECTS         { sonusEventDescription, sonusEventClass, 
                      sonusEventLevel, sonusEventTime, 
                      sonusDSIAlarmStatus, sonusDSIClusterName, 
                      sonusDSINodeType, sonusHostID }
    STATUS          current
    DESCRIPTION     
            "The DSI has a node out of service (with proc name).
             Automatically clears with sonusDSINodeInServiceNotification  ."
    ::= { sonusDSIMIBNotificationsPrefix 49 }

sonusDSINodeInServiceNotification NOTIFICATION-TYPE
    OBJECTS         { sonusEventDescription, sonusEventClass, 
                      sonusEventLevel, sonusEventTime, 
                      sonusDSIAlarmStatus, sonusDSIClusterName, 
                      sonusDSINodeType, sonusHostID }
    STATUS          current
    DESCRIPTION     
            "The DSI has a node out of service (with proc name).
             Automatically clears when node is in-service ."
    ::= { sonusDSIMIBNotificationsPrefix 50 }

sonusDSIConfigChangeFailureNotification NOTIFICATION-TYPE
    OBJECTS         { sonusEventDescription, sonusEventClass, 
                      sonusEventLevel, sonusEventTime, 
                      sonusDSIAlarmStatus, sonusDSIClusterName, 
                      sonusDSINodeType, sonusHostID }
    STATUS          deprecated
    DESCRIPTION     
            "The DSI has a Configuration change failed (with which command on which node).
             Automatically clears when configurations are upto date."
    ::= { sonusDSIMIBNotificationsPrefix 51 }

sonusDSINoInputActivityNotification NOTIFICATION-TYPE
    OBJECTS         { sonusEventDescription, sonusEventClass, 
                      sonusEventLevel, sonusEventTime, 
                      sonusDSIAlarmStatus, sonusDSIClusterName, 
                      sonusDSINodeType, sonusHostID }
    STATUS          current
    DESCRIPTION     
            "The DSI has a No input activity in %s since %s
             Operator clears when  neccesary."
    ::= { sonusDSIMIBNotificationsPrefix 52 }

sonusDSIClearNoInputActivityNotification NOTIFICATION-TYPE
    OBJECTS         { sonusEventDescription, sonusEventClass, 
                      sonusEventLevel, sonusEventTime, 
                      sonusDSIAlarmStatus, sonusDSIClusterName, 
                      sonusDSINodeType, sonusHostID }
    STATUS          current
    DESCRIPTION     
            "The DSI has resumed input activity in %s since %s
             Clears No Input activity alarm."
    ::= { sonusDSIMIBNotificationsPrefix 53 }

sonusDSINoOutputActivityNotification NOTIFICATION-TYPE
    OBJECTS         { sonusEventDescription, sonusEventClass, 
                      sonusEventLevel, sonusEventTime, 
                      sonusDSIAlarmStatus, sonusDSIClusterName, 
                      sonusDSINodeType, sonusHostID }
    STATUS          current
    DESCRIPTION     
            "The DSI has not output activity in %s since %s
             Operator clears when  neccesary."
    ::= { sonusDSIMIBNotificationsPrefix 54 }

sonusDSIClearNoOutputActivityNotification NOTIFICATION-TYPE
    OBJECTS         { sonusEventDescription, sonusEventClass, 
                      sonusEventLevel, sonusEventTime, 
                      sonusDSIAlarmStatus, sonusDSIClusterName, 
                      sonusDSINodeType, sonusHostID }
    STATUS          current
    DESCRIPTION     
            "The DSI has resumed output activity in %s since %s
             Clear No Output activity alarm."
    ::= { sonusDSIMIBNotificationsPrefix 55 }

sonusDSISaiAuthErrNotification NOTIFICATION-TYPE
    OBJECTS         { sonusEventDescription, sonusEventClass, 
                      sonusEventLevel, sonusEventTime, 
                      sonusDSIAlarmStatus, sonusDSIClusterName, 
                      sonusDSINodeType, sonusHostID }
    STATUS          current
    DESCRIPTION     
            "The DSI SAI Server has received an invalid 
             authentication response from the BPA."
    ::= { sonusDSIMIBNotificationsPrefix 56 }

sonusDSISaiBPAConnStatusNotification NOTIFICATION-TYPE
    OBJECTS         { sonusEventDescription, sonusEventClass, 
                      sonusEventLevel, sonusEventTime, 
                      sonusDSIBPAConnStatus, sonusDSIAlarmStatus, 
                      sonusDSIClusterName, sonusDSINodeType, sonusHostID }
    STATUS          current
    DESCRIPTION     
            "The DSI SAI Server has detected a change of 
             the connection status from the BPA."
    ::= { sonusDSIMIBNotificationsPrefix 57 }

sonusDSISaiConnStatusNotification NOTIFICATION-TYPE
    OBJECTS         { sonusEventDescription, sonusEventClass, 
                      sonusEventLevel, sonusEventTime, 
                      sonusDSISaiConnStatus, sonusDSIAlarmStatus, 
                      sonusDSIClusterName, sonusDSINodeType, sonusHostID }
    STATUS          current
    DESCRIPTION     
            "The DSI SAI Server has detected a change of
             the connection status from the Transporter client."
    ::= { sonusDSIMIBNotificationsPrefix 58 }

sonusDSINoOperatingLicenseNotification NOTIFICATION-TYPE
    OBJECTS         { sonusEventDescription, sonusEventClass, 
                      sonusEventLevel, sonusEventTime, 
                      sonusDSIAlarmStatus, sonusDSIClusterName, 
                      sonusDSINodeType, sonusHostID }
    STATUS          current
    DESCRIPTION     
            "The system does not have a license to operate."
    ::= { sonusDSIMIBNotificationsPrefix 59 }

sonusDSIMismatchedOperatingLicenseNotification NOTIFICATION-TYPE
    OBJECTS         { sonusEventDescription, sonusEventClass, 
                      sonusEventLevel, sonusEventTime, 
                      sonusDSIAlarmStatus, sonusDSIClusterName, 
                      sonusDSINodeType, sonusHostID }
    STATUS          current
    DESCRIPTION     
            "An attempt was made to use an unlicensed feature."
    ::= { sonusDSIMIBNotificationsPrefix 60 }

sonusDsiBECommDownNotification NOTIFICATION-TYPE
    OBJECTS         { sonusEventDescription, sonusEventClass, 
                      sonusEventLevel, sonusEventTime, 
                      sonusDSIAlarmStatus, sonusDSIClusterName, 
                      sonusDSINodeType, sonusHostID }
    STATUS          current
    DESCRIPTION     
            "The Backend Stream Server is shut down."
    ::= { sonusDSIMIBNotificationsPrefix 61 }

sonusDsiBECommErrorNotification NOTIFICATION-TYPE
    OBJECTS         { sonusEventDescription, sonusEventClass, 
                      sonusEventLevel, sonusEventTime, 
                      sonusDSIClusterName, sonusDSINodeType, 
                      sonusDSIBECommErrorReason, sonusHostID }
    STATUS          current
    DESCRIPTION     
            "The Backend Stream Server has experienced a 
             problem when communicating with the BPA."
    ::= { sonusDSIMIBNotificationsPrefix 62 }

sonusDsiFileServicesProcessingFailNotification NOTIFICATION-TYPE
    OBJECTS         { sonusEventDescription, sonusEventClass, 
                      sonusEventLevel, sonusEventTime, 
                      sonusDSIClusterName, sonusDSINodeType, sonusHostID }
    STATUS          current
    DESCRIPTION     
            "FileServices has encountered a possibly-global error 
             while manipulating directories or files."
    ::= { sonusDSIMIBNotificationsPrefix 63 }

sonusDsiFileServicesSoftwareFailNotification NOTIFICATION-TYPE
    OBJECTS         { sonusEventDescription, sonusEventClass, 
                      sonusEventLevel, sonusEventTime, 
                      sonusDSIClusterName, sonusDSINodeType, sonusHostID }
    STATUS          current
    DESCRIPTION     
            "FileServices encountered an error while processing 
             configuration parameters or invoking a filter."
    ::= { sonusDSIMIBNotificationsPrefix 64 }

sonusDsiFileServicesPeerCommFailNotification NOTIFICATION-TYPE
    OBJECTS         { sonusEventDescription, sonusEventClass, 
                      sonusEventLevel, sonusEventTime, 
                      sonusDSIClusterName, sonusDSINodeType, sonusHostID }
    STATUS          current
    DESCRIPTION     
            "FileServices cannot communicate with its peer process 
             on the specified server."
    ::= { sonusDSIMIBNotificationsPrefix 65 }

sonusDsiFileServicesSwitchoverNotification NOTIFICATION-TYPE
    OBJECTS         { sonusEventDescription, sonusEventClass, 
                      sonusEventLevel, sonusEventTime, 
                      sonusDSIClusterName, sonusDSINodeType, sonusHostID }
    STATUS          current
    DESCRIPTION     
            "FileServices detected that a source has failed over to 
             the other FileServices peer process."
    ::= { sonusDSIMIBNotificationsPrefix 66 }

sonusDsiFileServicesFileSourceFailNotification NOTIFICATION-TYPE
    OBJECTS         { sonusEventDescription, sonusEventClass, 
                      sonusEventLevel, sonusEventTime, 
                      sonusDSIClusterName, sonusDSINodeType, 
                      sonusDSIFileSourceAddressType, 
                      sonusDSIFileSourceAddress, sonusHostID }
    STATUS          deprecated
    DESCRIPTION     
            "FileServices cannot correctly handle a single source 
             and/or source's files. The source is identified by 
             sonusDSIFileSourceAddress."
    ::= { sonusDSIMIBNotificationsPrefix 67 }

sonusDsiOperatingModeErrorNotification NOTIFICATION-TYPE
    OBJECTS         { sonusEventDescription, sonusEventClass, 
                      sonusEventLevel, sonusEventTime, 
                      sonusDSIClusterName, sonusDSINodeType, 
                      sonusDSIProcessName, sonusHostID }
    STATUS          current
    DESCRIPTION     
            "The process raising the alarm is not allowed to run 
             under the current operating mode settings. The name 
             of the process and the current operating mode settings 
             are included in the description."
    ::= { sonusDSIMIBNotificationsPrefix 68 }

sonusDsiUnsupportedVersionError NOTIFICATION-TYPE
    OBJECTS         { sonusEventDescription, sonusEventClass, 
                      sonusEventLevel, sonusEventTime, 
                      sonusDSIClusterName, sonusDSINodeType, 
                      sonusDSIVersionErrorFileName, sonusHostID }
    STATUS          current
    DESCRIPTION     
            "The file <filename> has unsupported version in the header."
    ::= { sonusDSIMIBNotificationsPrefix 69 }

sonusDsiUnprocessedFilesNotification NOTIFICATION-TYPE
    OBJECTS         { sonusEventDescription, sonusEventClass, 
                      sonusEventLevel, sonusEventTime, 
                      sonusDSIAlarmStatus, sonusDSIClusterName, 
                      sonusDSINodeType, sonusDSIUnprocessedFileCount, 
                      sonusHostID }
    STATUS          current
    DESCRIPTION     
            "Unprocessed files found in miscFiles directory. File count = <count>."
    ::= { sonusDSIMIBNotificationsPrefix 70 }

sonusDsiLoadPolicyChangeNotification NOTIFICATION-TYPE
    OBJECTS         { sonusEventDescription, sonusEventClass, 
                      sonusEventLevel, sonusEventTime, 
                      sonusDSIClusterName, sonusDSINodeType, 
                      sonusDSINewLoadPolicy, sonusHostID }
    STATUS          current
    DESCRIPTION     
            "Load distribution policy changed to <newPolicy>"
    ::= { sonusDSIMIBNotificationsPrefix 71 }

sonusDsiMaintStartedNotification NOTIFICATION-TYPE
    OBJECTS         { sonusEventDescription, sonusEventClass, 
                      sonusEventLevel, sonusEventTime, 
                      sonusDSIAlarmStatus, sonusDSIClusterName, 
                      sonusDSINodeType, sonusHostID }
    STATUS          deprecated
    DESCRIPTION     
            "Maintenance started."
    ::= { sonusDSIMIBNotificationsPrefix 72 }

sonusDsiMasterSwitchoverNotification NOTIFICATION-TYPE
    OBJECTS         { sonusEventDescription, sonusEventClass, 
                      sonusEventLevel, sonusEventTime, 
                      sonusDSIClusterName, sonusDSINodeType, 
                      sonusDSINewMaster, sonusHostID }
    STATUS          deprecated
    DESCRIPTION     
            "Switchover to <newMaster>"
    ::= { sonusDSIMIBNotificationsPrefix 73 }

sonusDsiBEAmaClosingNotification NOTIFICATION-TYPE
    OBJECTS         { sonusEventDescription, sonusEventClass, 
                      sonusEventLevel, sonusEventTime, 
                      sonusDSIClusterName, sonusDSINodeType, 
                      sonusDsiBEAmaClosingFileName, 
                      sonusDsiBEAmaClosingStatus, sonusHostID }
    STATUS          current
    DESCRIPTION     
            "AMA file closing for (%1$s) status (%2$s)"
    ::= { sonusDSIMIBNotificationsPrefix 74 }

sonusDsiBEDatTransferNotification NOTIFICATION-TYPE
    OBJECTS         { sonusEventDescription, sonusEventClass, 
                      sonusEventLevel, sonusEventTime, 
                      sonusDSIClusterName, sonusDSINodeType, 
                      sonusDsiBEDatTransferFileName, 
                      sonusDsiBEDatTransferStatus, sonusHostID }
    STATUS          current
    DESCRIPTION     
            "DAT transfer request (%1$s) status (%2$s)"
    ::= { sonusDSIMIBNotificationsPrefix 75 }

sonusDsiBERtTransferNotification NOTIFICATION-TYPE
    OBJECTS         { sonusEventDescription, sonusEventClass, 
                      sonusEventLevel, sonusEventTime, 
                      sonusDSIClusterName, sonusDSINodeType, 
                      sonusDsiBERtTransferStatus, sonusHostID }
    STATUS          current
    DESCRIPTION     
            "Real-time transfer status has changed to (%1$s)"
    ::= { sonusDSIMIBNotificationsPrefix 76 }

sonusDsiOutOfSynchNotification NOTIFICATION-TYPE
    OBJECTS         { sonusEventDescription, sonusEventClass, 
                      sonusEventLevel, sonusEventTime, 
                      sonusDSIClusterName, sonusDSINodeType, sonusHostID }
    STATUS          deprecated
    DESCRIPTION     
            "M-nodes may be out of synch"
    ::= { sonusDSIMIBNotificationsPrefix 77 }

sonusDsiDBFailoverEventNotification NOTIFICATION-TYPE
    OBJECTS         { sonusEventDescription, sonusEventClass, 
                      sonusEventLevel, sonusEventTime, 
                      sonusDSIClusterName, sonusDSINodeType, sonusHostID }
    STATUS          current
    DESCRIPTION     
            "ORACLE Failover event occuring: status in description"
    ::= { sonusDSIMIBNotificationsPrefix 78 }

sonusDsiDBClearFailoverEventNotification NOTIFICATION-TYPE
    OBJECTS         { sonusEventDescription, sonusEventClass, 
                      sonusEventLevel, sonusEventTime, 
                      sonusDSIClusterName, sonusDSINodeType, sonusHostID }
    STATUS          current
    DESCRIPTION     
            "Clearing ORACLE Failover event occuring: status in description "
    ::= { sonusDSIMIBNotificationsPrefix 79 }

sonusDsiOracleErrorNotification NOTIFICATION-TYPE
    OBJECTS         { sonusEventDescription, sonusEventClass, 
                      sonusEventLevel, sonusEventTime, 
                      sonusDSIClusterName, sonusDSINodeType, sonusHostID }
    STATUS          current
    DESCRIPTION     
            "ORACLE generated error code & msg in description"
    ::= { sonusDSIMIBNotificationsPrefix 80 }

sonusDsiClearOracleErrorNotification NOTIFICATION-TYPE
    OBJECTS         { sonusEventDescription, sonusEventClass, 
                      sonusEventLevel, sonusEventTime, 
                      sonusDSIClusterName, sonusDSINodeType, sonusHostID }
    STATUS          current
    DESCRIPTION     
            "Clearing ORACLE error"
    ::= { sonusDSIMIBNotificationsPrefix 81 }

sonusDsiMemHiWatermarkNotification NOTIFICATION-TYPE
    OBJECTS         { sonusEventDescription, sonusEventClass, 
                      sonusEventLevel, sonusEventTime, 
                      sonusDSIAlarmStatus, sonusDSIClusterName, 
                      sonusDSINodeType, sonusDsiMemInfo, sonusHostID }
    STATUS          current
    DESCRIPTION     
            "Health Monitor detected process memory growth reached high watermark:(%1$s)"
    ::= { sonusDSIMIBNotificationsPrefix 82 }

sonusDsiDiskHiWatermarkNotification NOTIFICATION-TYPE
    OBJECTS         { sonusEventDescription, sonusEventClass, 
                      sonusEventLevel, sonusEventTime, 
                      sonusDSIAlarmStatus, sonusDSIClusterName, 
                      sonusDSINodeType, sonusDsiDiskInfo, sonusHostID }
    STATUS          current
    DESCRIPTION     
            "Health Monitor detected disk usage reached high watermark:(%1$s)"
    ::= { sonusDSIMIBNotificationsPrefix 83 }

sonusDsiCoreHiWatermarkNotification NOTIFICATION-TYPE
    OBJECTS         { sonusEventDescription, sonusEventClass, 
                      sonusEventLevel, sonusEventTime, 
                      sonusDSIAlarmStatus, sonusDSIClusterName, 
                      sonusDSINodeType, sonusDsiCoreInfo, sonusHostID }
    STATUS          current
    DESCRIPTION     
            "Health Monitor detected number of core files reached high watermark:(%1$s)"
    ::= { sonusDSIMIBNotificationsPrefix 84 }

sonusDsiFileToRecoveryNotification NOTIFICATION-TYPE
    OBJECTS         { sonusEventDescription, sonusEventClass, 
                      sonusEventLevel, sonusEventTime, 
                      sonusDSIClusterName, sonusDSINodeType, 
                      sonusDSIRecoveryFileName, sonusHostID }
    STATUS          current
    DESCRIPTION     
            "Maintainer detected a failed job, moved job file (%1$s) to recovery"
    ::= { sonusDSIMIBNotificationsPrefix 85 }

sonusDSICdrFileDuplicateNotification NOTIFICATION-TYPE
    OBJECTS         { sonusEventDescription, sonusEventClass, 
                      sonusEventLevel, sonusEventTime, 
                      sonusDSIClusterName, sonusDSINodeType, sonusHostID }
    STATUS          current
    DESCRIPTION     
            "The DSI IMDS Merger accumulates CDR records and generates CDR file in the temporary directory before moving the final CDR file to the CDR storage directory. If the CDR file with the same file name is present in the CDR storage, the alarm is raised."
    ::= { sonusDSIMIBNotificationsPrefix 86 }

sonusDSIFileHiWatermarkNotification NOTIFICATION-TYPE
    OBJECTS         { sonusEventDescription, sonusEventClass, 
                      sonusEventLevel, sonusEventTime, 
                      sonusDSIAlarmStatus, sonusDSIClusterName, 
                      sonusDSINodeType, sonusDsiFileInfo, sonusHostID }
    STATUS          current
    DESCRIPTION     
            "The DSI Health Monitor periodically checks for presence of files in the configured directory. If the number of files present is equal to or more than the configured high watermark, the alarm is raised:(%1$s)"
    ::= { sonusDSIMIBNotificationsPrefix 87 }

sonusDSICDRRecordDropNotification NOTIFICATION-TYPE
    OBJECTS         { sonusEventDescription, sonusEventClass, 
                      sonusEventLevel, sonusEventTime, 
                      sonusDSIClusterName, sonusDSINodeType, 
                      sonusDSIDropFileName, sonusHostID }
    STATUS          current
    DESCRIPTION     
            "TP Processing detected Originating TrunkType field Mismatch, dropped record to (%1$s) file"
    ::= { sonusDSIMIBNotificationsPrefix 88 }

sonusDsiTransporterDownNotification NOTIFICATION-TYPE
    OBJECTS         { sonusEventDescription, sonusEventClass, 
                      sonusEventLevel, sonusEventTime }
    STATUS          current
    DESCRIPTION     
            "."
    ::= { sonusDSIMIBNotificationsPrefix 89 }

sonusDsiTransporterConnDownNotification NOTIFICATION-TYPE
    OBJECTS         { sonusEventDescription, sonusEventClass, 
                      sonusEventLevel, sonusEventTime }
    STATUS          current
    DESCRIPTION     
            "."
    ::= { sonusDSIMIBNotificationsPrefix 90 }

sonusDSIStrandedFileFoundNotification NOTIFICATION-TYPE
    OBJECTS         { sonusEventDescription, sonusEventClass, 
                      sonusEventLevel, sonusEventTime, 
                      sonusDSIClusterName, sonusDSINodeType, 
                      sonusDSIStrandedFile, sonusHostID }
    STATUS          current
    DESCRIPTION     
            "Health Monitor found Stranded file,duration crossed high watermark: (%1$s)"
    ::= { sonusDSIMIBNotificationsPrefix 91 }

sonusDSIIdleTimeThresholdReachedNotification NOTIFICATION-TYPE
    OBJECTS         { sonusEventDescription, sonusEventClass, 
                      sonusEventLevel, sonusEventTime, 
                      sonusDSIClusterName, sonusDSINodeType, 
                      sonusDSIIdleTime, sonusHostID }
    STATUS          current
    DESCRIPTION     
            "Health Monitor Idle time threshold crossed: (%1$s)"
    ::= { sonusDSIMIBNotificationsPrefix 92 }

sonusDSIClearIdleTimeThresholdReachedNotification NOTIFICATION-TYPE
    OBJECTS         { sonusEventDescription, sonusEventClass, 
                      sonusEventLevel, sonusEventTime, 
                      sonusDSIClusterName, sonusDSINodeType, 
                      sonusDSIClearIdleTime, sonusHostID }
    STATUS          current
    DESCRIPTION     
            "Clear Health Monitor Idle time threshold crossed alarm:(%1$s)"
    ::= { sonusDSIMIBNotificationsPrefix 93 }

sonusDSIAppValidationFailedNotification NOTIFICATION-TYPE
    OBJECTS         { sonusEventDescription, sonusEventClass, 
                      sonusEventLevel, sonusEventTime, 
                      sonusDSIClusterName, sonusDSINodeType, 
                      sonusDSIAppValidation, sonusHostID }
    STATUS          current
    DESCRIPTION     
            "Health Monitor App File validation failed: (%1$s)"
    ::= { sonusDSIMIBNotificationsPrefix 94 }

sonusDSITransporterAbortNotification NOTIFICATION-TYPE
    OBJECTS         { sonusEventDescription, sonusEventClass, 
                      sonusEventLevel, sonusEventTime, 
                      sonusDSIAlarmStatus }
    STATUS          current
    DESCRIPTION     
            "Transporter aborted file transfer to all hosts "
    ::= { sonusDSIMIBNotificationsPrefix 95 }

sonusDSISAIDuplicateCDRNotification NOTIFICATION-TYPE
    OBJECTS         { sonusEventDescription, sonusEventClass, 
                      sonusEventLevel, sonusEventTime, 
                      sonusDSIClusterName, sonusDSINodeType, 
                      sonusDSISAIDuplicateCDR, sonusHostID }
    STATUS          current
    DESCRIPTION     
            "Duplicate CDR received by SAI server from TC.: (%1$s)"
    ::= { sonusDSIMIBNotificationsPrefix 96 }

sonusDSISAIRetransmittedCDRReceivedNotification NOTIFICATION-TYPE
    OBJECTS         { sonusEventDescription, sonusEventClass, 
                      sonusEventLevel, sonusEventTime, 
                      sonusDSIClusterName, sonusDSINodeType, 
                      sonusDSISAIRetransmittedCDR, sonusHostID }
    STATUS          current
    DESCRIPTION     
            "Retransmitted CDR received by SAI server from TC, Requires operator to take appropriate action.: (%1$s)"
    ::= { sonusDSIMIBNotificationsPrefix 97 }

sonusDsiFileServicesFileSourceFailNotificationV6 NOTIFICATION-TYPE
    OBJECTS         { sonusEventDescription, sonusEventClass, 
                      sonusEventLevel, sonusEventTime, 
                      sonusDSIClusterName, sonusDSINodeType, 
                      sonusDSIFileSourceAddressType, 
                      sonusDSIFileSourceInetAddress, sonusHostID }
    STATUS          current
    DESCRIPTION     
            "FileServices cannot correctly handle a single source
             and/or source's files. The source is identified by
             sonusDSIFileSourceInetAddress."
    ::= { sonusDSIMIBNotificationsPrefix 98 }

END -- end of module SONUS-DATASTREAM-INTEGRATOR-MIB.
