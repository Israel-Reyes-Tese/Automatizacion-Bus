--
-- This SMIv1 module has been generated by smidump 0.2-cvs. Do not edit.
--

SONUS-SOFTSWITCH-PROXY-GATEKEEPER-MIB DEFINITIONS ::= BEGIN

IMPORTS
    OBJECT-TYPE
        FROM RFC-1212
    TRAP-TYPE
        FROM RFC-1215
    sonusEventClass, sonusEventDescription, sonusEventLevel, 
    sonusEventTime
        FROM SONUS-COMMON-MIB
    sonusServicesMIBs
        FROM SONUS-SMI;

sonusSoftSwitchProxyGatekeeperMIB OBJECT IDENTIFIER
    ::= { sonusServicesMIBs 13 }

-- sonusSoftSwitchProxyGatekeeperMIB MODULE-IDENTITY
--     LAST-UPDATED    "200004230000Z"
--     ORGANIZATION    
--             "Sonus Networks, Inc."
--     CONTACT-INFO    
--             "   Customer Support    
--              Sonus Networks, Inc.
--              250 Apollo Drive
--              Chelmsford, MA 01824
--              USA
--              
--              Tel: 978-614-8100
--              Fax: 978-614-8609"
--     DESCRIPTION     
--             "The MIB Module for SoftSwitch Proxy Gatekeeper Management."
--     ::= { sonusServicesMIBs 13 }


sonusSoftSwitchProxyGatekeeperMIBObjects OBJECT IDENTIFIER
    ::= { sonusSoftSwitchProxyGatekeeperMIB 1 }

sonusSoftSwitchProxyGatekeeperMIBNotifications OBJECT IDENTIFIER
    ::= { sonusSoftSwitchProxyGatekeeperMIB 2 }

sonusSoftSwitchProxyGatekeeperMIBNotificationsPrefix OBJECT IDENTIFIER
    ::= { sonusSoftSwitchProxyGatekeeperMIBNotifications 0 }

sonusSoftSwitchProxyGatekeeperMIBNotificationsObjects OBJECT IDENTIFIER
    ::= { sonusSoftSwitchProxyGatekeeperMIBNotifications 1 }

sonusPesInterfaceIdentifier OBJECT-TYPE
    SYNTAX          INTEGER { primary(1), secondary(2) }
    ACCESS          read-only
    STATUS          mandatory
    DESCRIPTION     
            "PGK redundant interface identifier"
    ::= { sonusSoftSwitchProxyGatekeeperMIBNotificationsObjects 1 }

sonusSoftSwitchPgkUpNotification TRAP-TYPE
    ENTERPRISE      sonusSoftSwitchProxyGatekeeperMIBNotifications
    VARIABLES       { sonusEventDescription, sonusEventClass, 
                      sonusEventLevel, sonusEventTime }
--     STATUS          mandatory
    DESCRIPTION     
            "SoftSwitch Proxy Gatekeeper is up."
    ::= 1

sonusSoftSwitchPgkDownNotification TRAP-TYPE
    ENTERPRISE      sonusSoftSwitchProxyGatekeeperMIBNotifications
    VARIABLES       { sonusEventDescription, sonusEventClass, 
                      sonusEventLevel, sonusEventTime }
--     STATUS          mandatory
    DESCRIPTION     
            "SoftSwitch Proxy Gatekeeper is down."
    ::= 2

sonusSoftSwitchPgkPesServiceUpNotification TRAP-TYPE
    ENTERPRISE      sonusSoftSwitchProxyGatekeeperMIBNotifications
    VARIABLES       { sonusEventDescription, sonusEventClass, 
                      sonusEventLevel, sonusEventTime }
--     STATUS          mandatory
    DESCRIPTION     
            "PES is up."
    ::= 3

sonusSoftSwitchPgkPesServiceDownNotification TRAP-TYPE
    ENTERPRISE      sonusSoftSwitchProxyGatekeeperMIBNotifications
    VARIABLES       { sonusEventDescription, sonusEventClass, 
                      sonusEventLevel, sonusEventTime }
--     STATUS          mandatory
    DESCRIPTION     
            "PES is down."
    ::= 4

sonusSoftSwitchPgkPesInterfaceUpNotification TRAP-TYPE
    ENTERPRISE      sonusSoftSwitchProxyGatekeeperMIBNotifications
    VARIABLES       { sonusPesInterfaceIdentifier, sonusEventDescription, 
                      sonusEventClass, sonusEventLevel, sonusEventTime }
--     STATUS          mandatory
    DESCRIPTION     
            "PES Interface is up."
    ::= 5

sonusSoftSwitchPgkPesInterfaceDownNotification TRAP-TYPE
    ENTERPRISE      sonusSoftSwitchProxyGatekeeperMIBNotifications
    VARIABLES       { sonusPesInterfaceIdentifier, sonusEventDescription, 
                      sonusEventClass, sonusEventLevel, sonusEventTime }
--     STATUS          mandatory
    DESCRIPTION     
            "PES Interface is down."
    ::= 6

sonusSoftSwitchPgkPesChangeoverNotification TRAP-TYPE
    ENTERPRISE      sonusSoftSwitchProxyGatekeeperMIBNotifications
    VARIABLES       { sonusPesInterfaceIdentifier, sonusEventDescription, 
                      sonusEventClass, sonusEventLevel, sonusEventTime }
--     STATUS          mandatory
    DESCRIPTION     
            "Changing Active PES."
    ::= 7

END -- end of module SONUS-SOFTSWITCH-PROXY-GATEKEEPER-MIB.
