MIB-EMSPLUS-IPASOLINK-SYSTEM-MIB DEFINITIONS ::= BEGIN
    
    IMPORTS
        Timeout
            FROM BRIDGE-MIB
        InterfaceIndex
            FROM IF-MIB
        InetAddress, InetAddressPrefixLength, InetAddressType
            FROM INET-ADDRESS-MIB
        Ipv6Address
            FROM IPV6-TC
        OBJECT-TYPE
            FROM RFC-1212
        Counter, Gauge, IpAddress
            FROM RFC1155-SMI
        enterprises
            FROM SNMPv2-SMI
        DateAndTime, DisplayString, MacAddress, PhysAddress, RowStatus
            FROM SNMPv2-TC;
    
    AlarmTypeValue ::=
        INTEGER { invalid(0), communicationsAlarm(1),
                        qualityOfServiceAlarm(2), processingErrorAlarm(3),
                        equipmentAlarm(4), environmentalAlarm(5),
                        integrityViolationAlarm(6),
                        operationalViolationAlarm(7),
                        physicalViolationAlarm(8), securityViolationAlarm(9),
                        timeDomainViolationAlarm(10) }
    
    EnableDisableValue ::=
        INTEGER { invalid(0), disable(1), enable(2) }
    
    IpeNtpKeyAdminIndex ::=
        INTEGER (1..4)
    
    IpeNtpKeyAdminIndexOrZero ::=
        INTEGER (0..4)
    
    OffOnValue ::=
        INTEGER { invalid(0), off(1), on(2) }
    
    ProbableCauseValue ::=
        INTEGER { invalid(0), aIS(1), callSetUpFailure(2), degradedSignal(3),
                        farEndReceiverFailure(4), framingError(5),
                        lossOfFrame(6), lossOfPointer(7), lossOfSignal(8),
                        payloadTypeMismatch(9), transmissionError(10),
                        remoteAlarmInterface(11), excessiveBER(12),
                        pathTraceMismatch(13), unavailable(14),
                        signalLabelMismatch(15), lossOfMultiFrame(16),
                        receiveFailure(17), transmitFailure(18),
                        modulationFailure(19), demodulationFailure(20),
                        broadcastChannelFailure(21),
                        connectionEstablishmentError(22),
                        invalidMessageReceived(23),
                        localNodeTransmissionError(24),
                        remoteNodeTransmissionError(25), routingFailure(26),
                        backplaneFailure(51), dataSetProblem(52),
                        equipmentIdentifierDuplication(53),
                        externalIFDeviceProblem(54), lineCardProblem(55),
                        multiplexerProblem(56), nEIdentifierDuplication(57),
                        powerProblem(58), processorProblem(59),
                        protectionPathFailure(60), receiverFailure(61),
                        replaceableUnitMissing(62),
                        replaceableUnitTypeMismatch(63),
                        synchronizationSourceMismatch(64),
                        terminalProblem(65), timingProblem(66),
                        transmitterFailure(67), trunkCardProblem(68),
                        replaceableUnitProblem(69), realTimeClockFailure(70),
                        antennaFailure(71), batteryChargingFailure(72),
                        diskFailure(73), frequencyHoppingFailure(74),
                        iODeviceError(75), lossOfSynchronisation(76),
                        lossOfRedundancy(77), powerSupplyFailure(78),
                        signalQualityEvaluationFailure(79),
                        tranceiverFailure(80),
                        protectionMechanismFailure(81),
                        protectingResourceFailure(82),
                        airCompressorFailure(101),
                        airConditioningFailure(102), airDryerFailure(103),
                        batteryDischarging(104), batteryFailure(105),
                        commercialPowerFailure(106), coolingFanFailure(107),
                        engineFailure(108), fireDetectorFailure(109),
                        fuseFailure(110), generatorFailure(111),
                        lowBatteryThreshold(112), pumpFailure(113),
                        rectifierFailure(114), rectifierHighVoltage(115),
                        rectifierLowFVoltage(116),
                        ventilationsSystemFailure(117),
                        enclosureDoorOpen(118), explosiveGas(119), fire(120),
                        flood(121), highHumidity(122), highTemperature(123),
                        highWind(124), iceBuildUp(125),
                        intrusionDetection(126), lowFuel(127),
                        lowHumidity(128), lowCablePressure(129),
                        lowTemperatue(130), lowWater(131), smoke(132),
                        toxicGas(133), coolingSystemFailure(134),
                        externalEquipmentFailure(135),
                        externalPointFailure(136),
                        storageCapacityProblem(151), memoryMismatch(152),
                        corruptData(153), outOfCPUCycles(154),
                        sfwrEnvironmentProblem(155),
                        sfwrDownloadFailure(156), lossOfRealTimel(157),
                        applicationSubsystemFailure(158),
                        configurationOrCustomisationError(159),
                        databaseInconsistency(160), fileError(161),
                        outOfMemory(162), softwareError(163),
                        timeoutExpired(164),
                        underlayingResourceUnavailable(165),
                        versionMismatch(166), bandwidthReduced(201),
                        congestion(202), excessiveErrorRate(203),
                        excessiveResponseTime(204),
                        excessiveRetransmissionRate(205),
                        reducedLoggingCapability(206),
                        systemResourcesOverload(207), adapterError(500),
                        applicationSubsystemFailture(501),
                        bandwidthReducedX733(502),
                        callEstablishmentError(503),
                        communicationsProtocolError(504),
                        communicationsSubsystemFailure(505),
                        configurationOrCustomizationError(506),
                        congestionX733(507), coruptData(508),
                        cpuCyclesLimitExceeded(509),
                        dataSetOrModemError(510), degradedSignalX733(511),
                        dteDceInterfaceError(512),
                        enclosureDoorOpenX733(513),
                        equipmentMalfunction(514), excessiveVibration(515),
                        fileErrorX733(516), fireDetected(517),
                        framingErrorX733(518),
                        heatingVentCoolingSystemProblem(519),
                        humidityUnacceptable(520),
                        inputOutputDeviceError(521), inputDeviceError(522),
                        lanError(523), leakDetected(524),
                        localNodeTransmissionErrorX733(525),
                        lossOfFrameX733(526), lossOfSignalX733(527),
                        materialSupplyExhausted(528),
                        multiplexerProblemX733(529), outOfMemoryX733(530),
                        ouputDeviceError(531), performanceDegraded(532),
                        powerProblems(533), pressureUnacceptable(534),
                        processorProblems(535), pumpFailureX733(536),
                        queueSizeExceeded(537), receiveFailureX733(538),
                        receiverFailureX733(539),
                        remoteNodeTransmissionErrorX733(540),
                        resourceAtOrNearingCapacity(541),
                        responseTimeExecessive(542),
                        retransmissionRateExcessive(543),
                        softwareErrorX733(544),
                        softwareProgramAbnormallyTerminated(545),
                        softwareProgramError(546),
                        storageCapacityProblemX733(547),
                        temperatureUnacceptable(548), thresholdCrossed(549),
                        timingProblemX733(550), toxicLeakDetected(551),
                        transmitFailureX733(552), transmiterFailure(553),
                        underlyingResourceUnavailable(554),
                        versionMismatchX733(555), authenticationFailure(600),
                        breachOfConfidentiality(601), cableTamper(602),
                        delayedInformation(603), denialOfService(604),
                        duplicateInformation(605), informationMissing(606),
                        informationModificationDetected(607),
                        informationOutOfSequence(608), keyExpired(609),
                        nonRepudiationFailure(610), outOfHoursActivity(611),
                        outOfService(612), proceduralError(613),
                        unauthorizedAccessAttempt(614),
                        unexpectedInformation(615), other(1024) }
    
    UsedNotusedValue ::=
        INTEGER { invalid(0), notUsed(1), used(2) }
    
    -- 1.3.6.1.4.1.119
    nec OBJECT IDENTIFIER
        ::= { enterprises 119 }
    
    -- 1.3.6.1.4.1.119.2
    nec-mib OBJECT IDENTIFIER
        ::= { nec 2 }
    
    -- 1.3.6.1.4.1.119.2.3
    necProductDepend OBJECT IDENTIFIER
        ::= { nec-mib 3 }
    
    -- 1.3.6.1.4.1.119.2.3.69
    radioEquipment OBJECT IDENTIFIER
        ::= { necProductDepend 69 }
    
    -- 1.3.6.1.4.1.119.2.3.69.213
    commonPnmsPlus OBJECT IDENTIFIER
        ::= { radioEquipment 213 }
    
    -- 1.3.6.1.4.1.119.2.3.69.213.502
    ipasolink OBJECT IDENTIFIER
        ::= { commonPnmsPlus 502 }
    
    -- 1.3.6.1.4.1.119.2.3.69.213.502.5
    system5 OBJECT IDENTIFIER
        ::= { ipasolink 5 }
    
    -- 1.3.6.1.4.1.119.2.3.69.213.502.5.1
    ipeSystemGroup OBJECT IDENTIFIER
        ::= { system5 1 }
    
    -- 1.3.6.1.4.1.119.2.3.69.213.502.5.1.1
    ipeSysInfoTable OBJECT-TYPE
        SYNTAX      SEQUENCE OF IpeSysInfoEntry
        ACCESS      not-accessible
        STATUS      mandatory
        DESCRIPTION
            "Table of System Information."
        ::= { ipeSystemGroup 1 }
    
    -- 1.3.6.1.4.1.119.2.3.69.213.502.5.1.1.1
    ipeSysInfoEntry OBJECT-TYPE
        SYNTAX      IpeSysInfoEntry
        ACCESS      not-accessible
        STATUS      mandatory
        DESCRIPTION
            "Entry of System Information."
        INDEX       { ipeSysInfoNEAddressAddrType, ipeSysInfoNEAddress, ipeSysInfoIndex }
        ::= { ipeSysInfoTable 1 }
    
    IpeSysInfoEntry ::= SEQUENCE {
        ipeSysInfoIndex                         INTEGER,
        ipeSysInfoNEAddress                     InetAddress,
        ipeSysNeName                            DisplayString,
        ipeSysAreaName                          DisplayString,
        ipeSysNote                              DisplayString,
        ipeSysPrimaryIpAddress                  IpAddress,
        ipeSysSubnetMask                        IpAddress,
        ipeSysDefaultGateway                    IpAddress,
        ipeSysMacAddress                        MacAddress,
        ipeSysMibVersion                        DisplayString,
        ipeSysEquipmentType                     INTEGER,
        ipeSysPmType                            INTEGER,
        ipeSysPrimaryIpv6Address                Ipv6Address,
        ipeSysPrimaryIpv6AddressPrefixLength    InetAddressPrefixLength,
        ipeSysIpv6DefaultGateway                Ipv6Address,
        ipeSysIpv6DefaultGatewayIfIndex         INTEGER,
        ipeSysPrimaryIfIndex                    INTEGER,
        ipeSysIpv4DropFilterEnable              EnableDisableValue,
        ipeSysInfoNEAddressAddrType             InetAddressType
    }
    
    -- 1.3.6.1.4.1.119.2.3.69.213.502.5.1.1.1.1
    ipeSysInfoIndex OBJECT-TYPE
        SYNTAX      INTEGER (1)
        ACCESS      not-accessible
        STATUS      mandatory
        DESCRIPTION
            "Index of Table."
        ::= { ipeSysInfoEntry 1 }
    
    -- 1.3.6.1.4.1.119.2.3.69.213.502.5.1.1.1.2
    ipeSysInfoNEAddress OBJECT-TYPE
        SYNTAX      InetAddress
        ACCESS      not-accessible
        STATUS      mandatory
        DESCRIPTION
            ""
        ::= { ipeSysInfoEntry 2 }
    
    -- 1.3.6.1.4.1.119.2.3.69.213.502.5.1.1.1.3
    ipeSysNeName OBJECT-TYPE
        SYNTAX      DisplayString
        ACCESS      read-only
        STATUS      mandatory
        DESCRIPTION
            "Equipment name (for display)."
        ::= { ipeSysInfoEntry 3 }
    
    -- 1.3.6.1.4.1.119.2.3.69.213.502.5.1.1.1.4
    ipeSysAreaName OBJECT-TYPE
        SYNTAX      DisplayString
        ACCESS      read-only
        STATUS      mandatory
        DESCRIPTION
            "Area name (for display)."
        ::= { ipeSysInfoEntry 4 }
    
    -- 1.3.6.1.4.1.119.2.3.69.213.502.5.1.1.1.5
    ipeSysNote OBJECT-TYPE
        SYNTAX      DisplayString
        ACCESS      read-only
        STATUS      mandatory
        DESCRIPTION
            "Memorandum (for display)."
        ::= { ipeSysInfoEntry 5 }
    
    -- 1.3.6.1.4.1.119.2.3.69.213.502.5.1.1.1.6
    ipeSysPrimaryIpAddress OBJECT-TYPE
        SYNTAX      IpAddress
        ACCESS      read-only
        STATUS      mandatory
        DESCRIPTION
            "Primary IP Address (for display and setting)."
        ::= { ipeSysInfoEntry 6 }
    
    -- 1.3.6.1.4.1.119.2.3.69.213.502.5.1.1.1.7
    ipeSysSubnetMask OBJECT-TYPE
        SYNTAX      IpAddress
        ACCESS      read-only
        STATUS      mandatory
        DESCRIPTION
            "Subnet mask (for display)."
        ::= { ipeSysInfoEntry 7 }
    
    -- 1.3.6.1.4.1.119.2.3.69.213.502.5.1.1.1.8
    ipeSysDefaultGateway OBJECT-TYPE
        SYNTAX      IpAddress
        ACCESS      read-only
        STATUS      mandatory
        DESCRIPTION
            "Default gateway (for display)."
        ::= { ipeSysInfoEntry 8 }
    
    -- 1.3.6.1.4.1.119.2.3.69.213.502.5.1.1.1.9
    ipeSysMacAddress OBJECT-TYPE
        SYNTAX      MacAddress
        ACCESS      read-only
        STATUS      mandatory
        DESCRIPTION
            "MAC address (for display)."
        ::= { ipeSysInfoEntry 9 }
    
    -- 1.3.6.1.4.1.119.2.3.69.213.502.5.1.1.1.10
    ipeSysMibVersion OBJECT-TYPE
        SYNTAX      DisplayString
        ACCESS      read-only
        STATUS      mandatory
        DESCRIPTION
            "MIB version."
        ::= { ipeSysInfoEntry 10 }
    
    -- 1.3.6.1.4.1.119.2.3.69.213.502.5.1.1.1.11
    ipeSysEquipmentType OBJECT-TYPE
        SYNTAX      INTEGER
        ACCESS      read-only
        STATUS      mandatory
        DESCRIPTION
            "Equipment type."
        ::= { ipeSysInfoEntry 11 }
    
    -- 1.3.6.1.4.1.119.2.3.69.213.502.5.1.1.1.12
    ipeSysPmType OBJECT-TYPE
        SYNTAX      INTEGER (1..20)
        ACCESS      read-only
        STATUS      mandatory
        DESCRIPTION
            "Number of Branch.
             1=normalNE mode.
             1!=branchNE mode (2<= ipeSysPmType <= 20).
             7Branches(7), 8Branches(8) can not be set to this (iPASOLINK EX
             Advanced).
             The value Bridge1(11), Bridge2(12), Bridge3(13),
             Bridge4(14), Bridge5(15) Bridge6(16) are available (iPASOLINK EX
             Advanced)."
        ::= { ipeSysInfoEntry 12 }
    
    -- 1.3.6.1.4.1.119.2.3.69.213.502.5.1.1.1.13
    ipeSysPrimaryIpv6Address OBJECT-TYPE
        SYNTAX      Ipv6Address
        ACCESS      read-only
        STATUS      mandatory
        DESCRIPTION
            "Primary IPv6 Address (for display)."
        ::= { ipeSysInfoEntry 13 }
    
    -- 1.3.6.1.4.1.119.2.3.69.213.502.5.1.1.1.14
    ipeSysPrimaryIpv6AddressPrefixLength OBJECT-TYPE
        SYNTAX      InetAddressPrefixLength
        ACCESS      read-only
        STATUS      mandatory
        DESCRIPTION
            "Primary IPv6 Address Prefix Length (for display)."
        ::= { ipeSysInfoEntry 14 }
    
    -- 1.3.6.1.4.1.119.2.3.69.213.502.5.1.1.1.15
    ipeSysIpv6DefaultGateway OBJECT-TYPE
        SYNTAX      Ipv6Address
        ACCESS      read-only
        STATUS      mandatory
        DESCRIPTION
            "IPv6 Default gateway (for display)."
        ::= { ipeSysInfoEntry 15 }
    
    -- 1.3.6.1.4.1.119.2.3.69.213.502.5.1.1.1.16
    ipeSysIpv6DefaultGatewayIfIndex OBJECT-TYPE
        SYNTAX      INTEGER { any(0), bridge1(11), bridge2(12), bridge3(13),
                        bridge4(14), bridge5(15), bridge6(16), bridge7(17),
                        bridge8(18), bridge9(19), bridge10(20), bridge11(21),
                        bridge12(22), bridge13(23), bridge14(24),
                        bridge15(25), bridge16(26), bridge17(27),
                        bridge18(28), bridge19(29), bridge20(30) }
        ACCESS      read-only
        STATUS      mandatory
        DESCRIPTION
            "The index value which uniquely identifies the local
             interface through which the default gateway is
             reachable."
        ::= { ipeSysInfoEntry 16 }
    
    -- 1.3.6.1.4.1.119.2.3.69.213.502.5.1.1.1.17
    ipeSysPrimaryIfIndex OBJECT-TYPE
        SYNTAX      INTEGER { any(0), bridge1(11), bridge2(12), bridge3(13),
                        bridge4(14), bridge5(15), bridge6(16), bridge7(17),
                        bridge8(18), bridge9(19), bridge10(20), bridge11(21),
                        bridge12(22), bridge13(23), bridge14(24),
                        bridge15(25), bridge16(26), bridge17(27),
                        bridge18(28), bridge19(29), bridge20(30) }
        ACCESS      read-only
        STATUS      mandatory
        DESCRIPTION
            "Interface index of Prymary Ip Address."
        ::= { ipeSysInfoEntry 17 }
    
    -- 1.3.6.1.4.1.119.2.3.69.213.502.5.1.1.1.18
    ipeSysIpv4DropFilterEnable OBJECT-TYPE
        SYNTAX      EnableDisableValue
        ACCESS      read-only
        STATUS      mandatory
        DESCRIPTION
            "Enables or disables the drop filter for IPv4 packets on bridge
             and LCT interfaces.
             The disable(1) means to pass both incoming and outgoing IPv4
             packets on these interfaces.
             The enable(2) means to drop both incoming and outgoing IPv4
             packets on these interfaces.
             Note that ipeCfgBridgeIpStackMode: ipv4(1) and
             ipeSysIpv4DropFilterEnable: enable(2) cannot be set for the
             establishment of IPv4 communication."
        ::= { ipeSysInfoEntry 18 }
    
    -- 1.3.6.1.4.1.119.2.3.69.213.502.5.1.1.1.1001
    ipeSysInfoNEAddressAddrType OBJECT-TYPE
        SYNTAX      InetAddressType
        ACCESS      not-accessible
        STATUS      mandatory
        DESCRIPTION
            "Represents the IP address type of NE address index.
             Only ipv4(1) and ipv6(2) are supported."
        ::= { ipeSysInfoEntry 1001 }
    
    -- 1.3.6.1.4.1.119.2.3.69.213.502.5.1.2
    ipeSysInventoryInfoTable OBJECT-TYPE
        SYNTAX      SEQUENCE OF IpeSysInventoryInfoEntry
        ACCESS      not-accessible
        STATUS      mandatory
        DESCRIPTION
            "Table of system basic information."
        ::= { ipeSystemGroup 2 }
    
    -- 1.3.6.1.4.1.119.2.3.69.213.502.5.1.2.1
    ipeSysInventoryInfoEntry OBJECT-TYPE
        SYNTAX      IpeSysInventoryInfoEntry
        ACCESS      not-accessible
        STATUS      mandatory
        DESCRIPTION
            "Entry of system basic information."
        INDEX       { ipeSysInventoryInfoNEAddressAddrType, ipeSysInventoryInfoNEAddress, ipeSysInventoryInfoIndex }
        ::= { ipeSysInventoryInfoTable 1 }
    
    IpeSysInventoryInfoEntry ::= SEQUENCE {
        ipeSysInventoryInfoIndex                INTEGER,
        ipeSysInventoryInfoNEAddress            InetAddress,
        ipeSysInvSoftwareVersion                DisplayString,
        ipeSysInvSoftwareReleaseDate            DateAndTime,
        ipeSysInvDlSoftwareVersion              DisplayString,
        ipeSysInvOperationSide                  INTEGER,
        ipeSysInvStandbySoftwareVersion         DisplayString,
        ipeSysInventoryInfoNEAddressAddrType    InetAddressType
    }
    
    -- 1.3.6.1.4.1.119.2.3.69.213.502.5.1.2.1.1
    ipeSysInventoryInfoIndex OBJECT-TYPE
        SYNTAX      INTEGER (1)
        ACCESS      not-accessible
        STATUS      mandatory
        DESCRIPTION
            "Index of table."
        ::= { ipeSysInventoryInfoEntry 1 }
    
    -- 1.3.6.1.4.1.119.2.3.69.213.502.5.1.2.1.2
    ipeSysInventoryInfoNEAddress OBJECT-TYPE
        SYNTAX      InetAddress
        ACCESS      not-accessible
        STATUS      mandatory
        DESCRIPTION
            ""
        ::= { ipeSysInventoryInfoEntry 2 }
    
    -- 1.3.6.1.4.1.119.2.3.69.213.502.5.1.2.1.3
    ipeSysInvSoftwareVersion OBJECT-TYPE
        SYNTAX      DisplayString
        ACCESS      read-only
        STATUS      mandatory
        DESCRIPTION
            "Software version."
        ::= { ipeSysInventoryInfoEntry 3 }
    
    -- 1.3.6.1.4.1.119.2.3.69.213.502.5.1.2.1.4
    ipeSysInvSoftwareReleaseDate OBJECT-TYPE
        SYNTAX      DateAndTime
        ACCESS      read-only
        STATUS      mandatory
        DESCRIPTION
            "Software update date and time."
        ::= { ipeSysInventoryInfoEntry 4 }
    
    -- 1.3.6.1.4.1.119.2.3.69.213.502.5.1.2.1.5
    ipeSysInvDlSoftwareVersion OBJECT-TYPE
        SYNTAX      DisplayString
        ACCESS      read-only
        STATUS      mandatory
        DESCRIPTION
            "Download control."
        ::= { ipeSysInventoryInfoEntry 5 }
    
    -- 1.3.6.1.4.1.119.2.3.69.213.502.5.1.2.1.6
    ipeSysInvOperationSide OBJECT-TYPE
        SYNTAX      INTEGER
        ACCESS      read-only
        STATUS      mandatory
        DESCRIPTION
            "Active side information."
        ::= { ipeSysInventoryInfoEntry 6 }
    
    -- 1.3.6.1.4.1.119.2.3.69.213.502.5.1.2.1.7
    ipeSysInvStandbySoftwareVersion OBJECT-TYPE
        SYNTAX      DisplayString
        ACCESS      read-only
        STATUS      mandatory
        DESCRIPTION
            "Firmware version of inactive side."
        ::= { ipeSysInventoryInfoEntry 7 }
    
    -- 1.3.6.1.4.1.119.2.3.69.213.502.5.1.2.1.1001
    ipeSysInventoryInfoNEAddressAddrType OBJECT-TYPE
        SYNTAX      InetAddressType
        ACCESS      not-accessible
        STATUS      mandatory
        DESCRIPTION
            "Represents the IP address type of NE address index.
             Only ipv4(1) and ipv6(2) are supported."
        ::= { ipeSysInventoryInfoEntry 1001 }
    
    -- 1.3.6.1.4.1.119.2.3.69.213.502.5.1.3
    ipeSysOperationGroup OBJECT IDENTIFIER
        ::= { ipeSystemGroup 3 }
    
    -- 1.3.6.1.4.1.119.2.3.69.213.502.5.1.3.1
    ipeSysOpTimeTable OBJECT-TYPE
        SYNTAX      SEQUENCE OF IpeSysOpTimeEntry
        ACCESS      not-accessible
        STATUS      mandatory
        DESCRIPTION
            "Table of date and time."
        ::= { ipeSysOperationGroup 1 }
    
    -- 1.3.6.1.4.1.119.2.3.69.213.502.5.1.3.1.1
    ipeSysOpTimeEntry OBJECT-TYPE
        SYNTAX      IpeSysOpTimeEntry
        ACCESS      not-accessible
        STATUS      mandatory
        DESCRIPTION
            "Entry of date and time."
        INDEX       { ipeSysOpTimeNEAddressAddrType, ipeSysOpTimeNEAddress, ipeSysOpTimeIndex }
        ::= { ipeSysOpTimeTable 1 }
    
    IpeSysOpTimeEntry ::= SEQUENCE {
        ipeSysOpTimeIndex               INTEGER,
        ipeSysOpTimeNEAddress           InetAddress,
        ipeSysOpCurrentTime             DateAndTime,
        ipeSysOpStartTime               DateAndTime,
        ipeSysOpUpTime                  Counter,
        ipeSysOpTimeNEAddressAddrType   InetAddressType
    }
    
    -- 1.3.6.1.4.1.119.2.3.69.213.502.5.1.3.1.1.1
    ipeSysOpTimeIndex OBJECT-TYPE
        SYNTAX      INTEGER (1)
        ACCESS      not-accessible
        STATUS      mandatory
        DESCRIPTION
            "Index of table."
        ::= { ipeSysOpTimeEntry 1 }
    
    -- 1.3.6.1.4.1.119.2.3.69.213.502.5.1.3.1.1.2
    ipeSysOpTimeNEAddress OBJECT-TYPE
        SYNTAX      InetAddress
        ACCESS      not-accessible
        STATUS      mandatory
        DESCRIPTION
            ""
        ::= { ipeSysOpTimeEntry 2 }
    
    -- 1.3.6.1.4.1.119.2.3.69.213.502.5.1.3.1.1.3
    ipeSysOpCurrentTime OBJECT-TYPE
        SYNTAX      DateAndTime
        ACCESS      read-only
        STATUS      mandatory
        DESCRIPTION
            "Current time."
        ::= { ipeSysOpTimeEntry 3 }
    
    -- 1.3.6.1.4.1.119.2.3.69.213.502.5.1.3.1.1.4
    ipeSysOpStartTime OBJECT-TYPE
        SYNTAX      DateAndTime
        ACCESS      read-only
        STATUS      mandatory
        DESCRIPTION
            "OS started time."
        ::= { ipeSysOpTimeEntry 4 }
    
    -- 1.3.6.1.4.1.119.2.3.69.213.502.5.1.3.1.1.5
    ipeSysOpUpTime OBJECT-TYPE
        SYNTAX      Counter
        ACCESS      read-only
        STATUS      mandatory
        DESCRIPTION
            "Duration after OS started (second)."
        ::= { ipeSysOpTimeEntry 5 }
    
    -- 1.3.6.1.4.1.119.2.3.69.213.502.5.1.3.1.1.1001
    ipeSysOpTimeNEAddressAddrType OBJECT-TYPE
        SYNTAX      InetAddressType
        ACCESS      not-accessible
        STATUS      mandatory
        DESCRIPTION
            "Represents the IP address type of NE address index.
             Only ipv4(1) and ipv6(2) are supported."
        ::= { ipeSysOpTimeEntry 1001 }
    
    -- 1.3.6.1.4.1.119.2.3.69.213.502.5.1.3.2
    ipeSysOpFileDownloadTable OBJECT-TYPE
        SYNTAX      SEQUENCE OF IpeSysOpFileDownloadEntry
        ACCESS      not-accessible
        STATUS      mandatory
        DESCRIPTION
            "Table of file download."
        ::= { ipeSysOperationGroup 2 }
    
    -- 1.3.6.1.4.1.119.2.3.69.213.502.5.1.3.2.1
    ipeSysOpFileDownloadEntry OBJECT-TYPE
        SYNTAX      IpeSysOpFileDownloadEntry
        ACCESS      not-accessible
        STATUS      mandatory
        DESCRIPTION
            "Entry of file download."
        INDEX       { ipeSysOpFileDownloadNEAddressAddrType, ipeSysOpFileDownloadNEAddress, ipeSysOpFileDownloadIndex }
        ::= { ipeSysOpFileDownloadTable 1 }
    
    IpeSysOpFileDownloadEntry ::= SEQUENCE {
        ipeSysOpFileDownloadIndex               INTEGER,
        ipeSysOpFileDownloadNEAddress           InetAddress,
        ipeSysOpFileDownloadModule              INTEGER,
        ipeSysOpFileDownloadCpuResetDetail      INTEGER,
        ipeSysOpFileDownloadStatus              INTEGER,
        ipeSysOpFileDownloadCtrl                INTEGER,
        ipeSysOpFileDownloadProtocolType        INTEGER,
        ipeSysOpFileDownloadNEAddressAddrType   InetAddressType
    }
    
    -- 1.3.6.1.4.1.119.2.3.69.213.502.5.1.3.2.1.1
    ipeSysOpFileDownloadIndex OBJECT-TYPE
        SYNTAX      INTEGER (1)
        ACCESS      not-accessible
        STATUS      mandatory
        DESCRIPTION
            "Index of table."
        ::= { ipeSysOpFileDownloadEntry 1 }
    
    -- 1.3.6.1.4.1.119.2.3.69.213.502.5.1.3.2.1.2
    ipeSysOpFileDownloadNEAddress OBJECT-TYPE
        SYNTAX      InetAddress
        ACCESS      not-accessible
        STATUS      mandatory
        DESCRIPTION
            ""
        ::= { ipeSysOpFileDownloadEntry 2 }
    
    -- 1.3.6.1.4.1.119.2.3.69.213.502.5.1.3.2.1.3
    ipeSysOpFileDownloadModule OBJECT-TYPE
        SYNTAX      INTEGER { invalid(0), idu(1), odu(2), mdprm(3),
                        raFpga(4), ipeFpga(5), mse(6), softkey(7), cfgNet(8),
                        cfgEqu(9), cfgUser(10), https(11), cliScript(15),
                        httpsKey(19), httpsCrt(21), mdctrl(22), controller(23),
                        sd(50), trp(51), trintfc(52) }
        ACCESS      read-only
        STATUS      mandatory
        DESCRIPTION
            "Program type. *'0:Invalidity' is used as an initial state.
             cliScripo(15) can not be set to this (iPASOLINK EX Advanced).
             The value controller(23) is available only for the iPASOLINK EX
             Advanced."
        ::= { ipeSysOpFileDownloadEntry 3 }
    
    -- 1.3.6.1.4.1.119.2.3.69.213.502.5.1.3.2.1.4
    ipeSysOpFileDownloadCpuResetDetail OBJECT-TYPE
        SYNTAX      INTEGER { invalid(0), revertReset(1), normReset(2) }
        ACCESS      read-only
        STATUS      mandatory
        DESCRIPTION
            "CPU reset control.
    
             0:Invalidity
             1:revert reset
             2:normal reset( without revert )
    
             *'0:Invalidity' is used as an initial state."
        ::= { ipeSysOpFileDownloadEntry 4 }
    
    -- 1.3.6.1.4.1.119.2.3.69.213.502.5.1.3.2.1.5
    ipeSysOpFileDownloadStatus OBJECT-TYPE
        SYNTAX      INTEGER { invalid(0), downloadCompleted(1),
                        downloadFailed(2), downloadExecuting(3),
                        downloadSuspending(4) }
        ACCESS      read-only
        STATUS      mandatory
        DESCRIPTION
            "Download result.
    
             0:Invalidity
             1:Completed
             2:Failed
             3:Executing
             4:Suspending
    
             *'0:Invalidity' is used as an initial state.
    
             *A change state is the following three kinds.
             1)When it operates normally:
               (Start)->(3:Executing)->(1:Completed)
             2)When it cancels on the way:
               (Start)->(3:Executing)->(4:Suspending)-> (Completed)
             3)When unusual detection is carried out on the way:
               (Start)->(3:Executing)->(2:Failed)
    
             *The download start from excluding (3:Executing) is permitted.
             *The download start from (3:Executing) is not permitted.
    
             *Pertinent details: ipeSysOpFileDownloadCtrl"
        ::= { ipeSysOpFileDownloadEntry 5 }
    
    -- 1.3.6.1.4.1.119.2.3.69.213.502.5.1.3.2.1.6
    ipeSysOpFileDownloadCtrl OBJECT-TYPE
        SYNTAX      INTEGER { invalid(0), startDownload(1),
                        suspendDownload(2), startUpload(3), endUpload(4),
                        resetDownload(5) }
        ACCESS      read-only
        STATUS      mandatory
        DESCRIPTION
            "Download control.
    
             0:Invalidity
             1:Download start
             2:Download suspend
             3:Upload start
             4:Upload end
             5:Download reset
    
             *'0:Invalidity' is used as an initial state.
             *'5:Download reset' terminates the FTP server(vsftpd) with the
             deletion processing in the type of the file for all download
             directory.
    
             *The object file name allows only alphanumeric character '0-9',
             'a-z', 'A-Z' of ASCII code, and sign '-_.+'.
    
             *Pertinent details: ipeSysOpFileDownloadProtocolType
             *Pertinent details: ipeSysOpFileDownloadModule
             *Pertinent details: ipeSysOpFileDownloadStatus
             *Pertinent details: ipeFsUpdateFileStatus
             *Pertinent details: ipeFsUsbProcStatus
    
             [Race condition]
             *When ipeSysOpFileDownloadStatus is (3:Executing) or
             (4:Suspending), (1:Download start) is invalid.
             *When ipeSysOpFileDownloadStatus is (4:Suspending), (2:Download
             suspend) is invalid.
             *When ipeSysOpFileDownloadStatus is (0:Invalidity), (1:Download
             start) is valid, but do nothing.
             *When ipeFsUpdateFileStatusis(3:Executing), it is invalid. Other
             one is valid.
             *When ipeFsUsbProcStatus is (2:Normal:Process executing), it is
             invalid. Other one is valid.
    
             [Indispensable condition]
             *When it is  (1:Download start) or (3:Upload start), (4:Upload
             end),ipeSysOpFileDownloadProtocolType setup is indispensable."
        ::= { ipeSysOpFileDownloadEntry 6 }
    
    -- 1.3.6.1.4.1.119.2.3.69.213.502.5.1.3.2.1.7
    ipeSysOpFileDownloadProtocolType OBJECT-TYPE
        SYNTAX      INTEGER { invalid(0), ftp(1), sftp(2), http(3) }
        ACCESS      read-only
        STATUS      mandatory
        DESCRIPTION
            "Kind of protocol,
    
             *'0:Invalidity' is used as an initial state.
    
             *Pertinent details: ipeSysOpFileDownloadCtrl"
        ::= { ipeSysOpFileDownloadEntry 7 }
    
    -- 1.3.6.1.4.1.119.2.3.69.213.502.5.1.3.2.1.1001
    ipeSysOpFileDownloadNEAddressAddrType OBJECT-TYPE
        SYNTAX      InetAddressType
        ACCESS      not-accessible
        STATUS      mandatory
        DESCRIPTION
            "Represents the IP address type of NE address index.
             Only ipv4(1) and ipv6(2) are supported."
        ::= { ipeSysOpFileDownloadEntry 1001 }
    
    -- 1.3.6.1.4.1.119.2.3.69.213.502.5.1.3.3
    ipeSysOpProgramPmonRmonClearTable OBJECT-TYPE
        SYNTAX      SEQUENCE OF IpeSysOpProgramPmonRmonClearEntry
        ACCESS      not-accessible
        STATUS      mandatory
        DESCRIPTION
            ""
        ::= { ipeSysOperationGroup 3 }
    
    -- 1.3.6.1.4.1.119.2.3.69.213.502.5.1.3.3.1
    ipeSysOpProgramPmonRmonClearEntry OBJECT-TYPE
        SYNTAX      IpeSysOpProgramPmonRmonClearEntry
        ACCESS      not-accessible
        STATUS      mandatory
        DESCRIPTION
            ""
        INDEX       { ipeSysOpProgramPmonRmonClearNEAddressAddrType, ipeSysOpProgramPmonRmonClearNEAddress, ipeSysOpProgramPmonRmonClearIndex }
        ::= { ipeSysOpProgramPmonRmonClearTable 1 }
    
    IpeSysOpProgramPmonRmonClearEntry ::= SEQUENCE {
        ipeSysOpProgramPmonRmonClearIndex               INTEGER,
        ipeSysOpProgramPmonRmonClearNEAddress           InetAddress,
        ipeSysOpProgramPmonRmonClear                    INTEGER,
        ipeSysOpProgramPmonRmonClearResult              INTEGER,
        ipeSysOpProgramPmonRmonClearNEAddressAddrType   InetAddressType
    }
    
    -- 1.3.6.1.4.1.119.2.3.69.213.502.5.1.3.3.1.1
    ipeSysOpProgramPmonRmonClearIndex OBJECT-TYPE
        SYNTAX      INTEGER (1)
        ACCESS      not-accessible
        STATUS      mandatory
        DESCRIPTION
            ""
        ::= { ipeSysOpProgramPmonRmonClearEntry 1 }
    
    -- 1.3.6.1.4.1.119.2.3.69.213.502.5.1.3.3.1.2
    ipeSysOpProgramPmonRmonClearNEAddress OBJECT-TYPE
        SYNTAX      InetAddress
        ACCESS      not-accessible
        STATUS      mandatory
        DESCRIPTION
            ""
        ::= { ipeSysOpProgramPmonRmonClearEntry 2 }
    
    -- 1.3.6.1.4.1.119.2.3.69.213.502.5.1.3.3.1.3
    ipeSysOpProgramPmonRmonClear OBJECT-TYPE
        SYNTAX      INTEGER
        ACCESS      read-only
        STATUS      mandatory
        DESCRIPTION
            "PMON data clear control
             0:FIXED VALUE 1:REQUEST"
        ::= { ipeSysOpProgramPmonRmonClearEntry 3 }
    
    -- 1.3.6.1.4.1.119.2.3.69.213.502.5.1.3.3.1.4
    ipeSysOpProgramPmonRmonClearResult OBJECT-TYPE
        SYNTAX      INTEGER { invalid(0), completed(1), failed(2),
                        executing(3) }
        ACCESS      read-only
        STATUS      mandatory
        DESCRIPTION
            "PMON data clear control response
             1:COMPLETED
             2:FAILED
             3:EXECUTING"
        ::= { ipeSysOpProgramPmonRmonClearEntry 4 }
    
    -- 1.3.6.1.4.1.119.2.3.69.213.502.5.1.3.3.1.1001
    ipeSysOpProgramPmonRmonClearNEAddressAddrType OBJECT-TYPE
        SYNTAX      InetAddressType
        ACCESS      not-accessible
        STATUS      mandatory
        DESCRIPTION
            "Represents the IP address type of NE address index.
             Only ipv4(1) and ipv6(2) are supported."
        ::= { ipeSysOpProgramPmonRmonClearEntry 1001 }
    
    -- 1.3.6.1.4.1.119.2.3.69.213.502.5.2
    ipeFileSystemGroup OBJECT IDENTIFIER
        ::= { system5 2 }
    
    -- 1.3.6.1.4.1.119.2.3.69.213.502.5.2.1
    ipeFsFileInfoTable OBJECT-TYPE
        SYNTAX      SEQUENCE OF IpeFsFileInfoEntry
        ACCESS      not-accessible
        STATUS      mandatory
        DESCRIPTION
            "Table of file information."
        ::= { ipeFileSystemGroup 1 }
    
    -- 1.3.6.1.4.1.119.2.3.69.213.502.5.2.1.1
    ipeFsFileInfoEntry OBJECT-TYPE
        SYNTAX      IpeFsFileInfoEntry
        ACCESS      not-accessible
        STATUS      mandatory
        DESCRIPTION
            "Entry of file information."
        INDEX       { ipeFsFileInfoNEAddressAddrType, ipeFsFileInfoNEAddress, ipeFsFileInfoIndex }
        ::= { ipeFsFileInfoTable 1 }
    
    IpeFsFileInfoEntry ::= SEQUENCE {
        ipeFsFileInfoIndex              INTEGER,
        ipeFsFileInfoNEAddress          InetAddress,
        ipeFsFileListType               INTEGER,
        ipeFsFileListCurrent            DisplayString,
        ipeFsFileListTemp               DisplayString,
        ipeFsUpdateFileDetail           DisplayString,
        ipeFsUpdateFileStatus           INTEGER,
        ipeFsUpdateFileStatusDetail     OCTET STRING,
        ipeFsUpdateFileProgressBase     INTEGER,
        ipeFsUpdateFileProgress         INTEGER,
        ipeFsUpdateFileUpdateList       DisplayString,
        ipeFsUpdateFileConfigPartial    OCTET STRING,
        ipeFsFileInfoNEAddressAddrType  InetAddressType
    }
    
    -- 1.3.6.1.4.1.119.2.3.69.213.502.5.2.1.1.1
    ipeFsFileInfoIndex OBJECT-TYPE
        SYNTAX      INTEGER (1)
        ACCESS      not-accessible
        STATUS      mandatory
        DESCRIPTION
            "Index of Table."
        ::= { ipeFsFileInfoEntry 1 }
    
    -- 1.3.6.1.4.1.119.2.3.69.213.502.5.2.1.1.2
    ipeFsFileInfoNEAddress OBJECT-TYPE
        SYNTAX      InetAddress
        ACCESS      not-accessible
        STATUS      mandatory
        DESCRIPTION
            ""
        ::= { ipeFsFileInfoEntry 2 }
    
    -- 1.3.6.1.4.1.119.2.3.69.213.502.5.2.1.1.3
    ipeFsFileListType OBJECT-TYPE
        SYNTAX      INTEGER { invalid(0), idu(1), odu(2), mdprm(3),
                        raFpga(4), ipeFpga(5), softkey(7), cfgNet(8),
                        cfgEqu(9), cfgUser(10), https(11), pmon(12),
                        rmon(13), log(14), inventory(15), mac(16), all(17),
                        cardFw(18), httpsKey(19), httpsCsr(20), httpsCrt(21),
                        mdCtrl(22), controller(23), sd(50), trp(51), trintfc(52) }
        ACCESS      read-only
        STATUS      mandatory
        DESCRIPTION
            "Type for acquisition
    
             0:Invalidity
             1: IDU
             2: ODU
             3: MODEM Parameter
             4: FPGA(Other slot)
             5: FPGA(Ctrl)
             6: MSE
             7: Software Key License
             8: Network Config
             9: Equipment Config
             10: User Config
             11: Server Certificate for HTTPS/HTTPS certificate issue request
             12: PMON data
             13: RMON data
             14: Command/event/alarm LOG
             15: Device Inventory file
             16: MAC learning entry
             17: all(All types)
             18: Card Firmware
             19: Private key for SSL Server Certificate
             20: CSR (Certificate Signing Request) for SSL Server Certificate
             21: CA (Certification Authority) certificate for SSL Server
             Certificate
             22: Modem Controller(valid for MODEM-AV)
             50: SD
             51: TRP
             52: TR Interface
    
             *'0:Invalidity' is used as an initial state.
             *'8: Network Config' can not be set to this (iPASOLINK EX
             Advanced).
             *'9: Equipment Config' is used for Equipment and Network
             Configuration only for the iPASOLINK EX Advanced.
    
             *Pertinent details: ipeFsFileListCurrent
             *Pertinent details: ipeFsFileListTemp"
        ::= { ipeFsFileInfoEntry 3 }
    
    -- 1.3.6.1.4.1.119.2.3.69.213.502.5.2.1.1.4
    ipeFsFileListCurrent OBJECT-TYPE
        SYNTAX      DisplayString
        ACCESS      read-only
        STATUS      mandatory
        DESCRIPTION
            "Current file list (Flash-ROM).
    
             The list of the type set to ipeFsFileListType is acquired.
    
             Form of file list:
    
             It's 1 item by  'file name (It included in a path),file
             size,CRC'.
             Each item is divided at space.
    
             *CRC is fixed '0'.
    
             Ex) FilePath1/FileName1,size,CRC FilePath2/FileName2,size,CRC...
    
             [Indispensable condition]
             *ipeFsFileListType setup is indispensable."
        ::= { ipeFsFileInfoEntry 4 }
    
    -- 1.3.6.1.4.1.119.2.3.69.213.502.5.2.1.1.5
    ipeFsFileListTemp OBJECT-TYPE
        SYNTAX      DisplayString
        ACCESS      read-only
        STATUS      mandatory
        DESCRIPTION
            "Temporary file list (DRAM).
    
             The list of the type set to ipeFsFileListType is acquired.
    
             Form of file list:
    
             It's 1 item by 'file name (It isn't included in a pass),file
             size,CRC'.
             Each item is divided at space.
    
             *CRC is fixed '0'.
    
             Ex) Filename1,size,CRC Filename2,size,CRC...
    
             [Indispensable condition]
             *ipeFsFileListType setup is indispensable."
        ::= { ipeFsFileInfoEntry 5 }
    
    -- 1.3.6.1.4.1.119.2.3.69.213.502.5.2.1.1.6
    ipeFsUpdateFileDetail OBJECT-TYPE
        SYNTAX      DisplayString
        ACCESS      read-only
        STATUS      mandatory
        DESCRIPTION
            "File update control.
    
             Thing to specify object file after it downloads it by
             'ipeSysOpFileDownloadCtrl','ipeFsUsbCommand' and to demand file
             update.
    
             Ex) Filename1
    
             *The object file name allows only alphanumeric character '0-9',
             'a-z', 'A-Z' of ASCII code, and sign '-_.+'.
    
             *Pertinent details: ipeSysOpFileDownloadModule
             *Pertinent details: ipeFsUpdateFileUpdateList
             *Pertinent details: ipeSysOpFileDownloadStatus
             *Pertinent details: ipeFsUpdateFileStatus
             *Pertinent details: ipeFsUsbProcStatus
    
             [Race condition]
             *When ipeSysOpFileDownloadStatus is (3:Executing) or
             (4:Suspending), it is invalid.
             *When ipeFsUpdateFileStatusis(3:Executing), it is invalid.
             *When ipeFsUsbProcStatus is (2:Normal :Process executing), it is
             invalid.
    
             [Indispensable condition]
             *When ipeSysOpFileDownloadModule is 'odu(2)', 'mdprm(3)', or
             'raFpga(4)', ipeFsUpdateFileUpdateList setup is indispensable."
        ::= { ipeFsFileInfoEntry 6 }
    
    -- 1.3.6.1.4.1.119.2.3.69.213.502.5.2.1.1.7
    ipeFsUpdateFileStatus OBJECT-TYPE
        SYNTAX      INTEGER { invalid(0), success(1), failure(2),
                        executing(3), checking(4),
                        successWithoutRestrictedUser(5) }
        ACCESS      read-only
        STATUS      mandatory
        DESCRIPTION
            "Update result.
             0:Invalidity
             1:Success
             2:Failed
             3:Executing
             4:Checking
             5:Success but some restricted UserName(s) are ignored
    
             *'0:Invalidity' is used as an initial state.
    
             *The slot result of the correspondence is set to
             'IpeFsUpdateFileStatusDetail',
             and processing is continued when failing in the two or more
             slot update.
    
             *Pertinent details: ipeFsUpdateFileDetail
             *Pertinent details: ipeFsUpdateFileStatusDetail"
        ::= { ipeFsFileInfoEntry 7 }
    
    -- 1.3.6.1.4.1.119.2.3.69.213.502.5.2.1.1.8
    ipeFsUpdateFileStatusDetail OBJECT-TYPE
        SYNTAX      OCTET STRING (SIZE(42))
        ACCESS      read-only
        STATUS      mandatory
        DESCRIPTION
            "Update result is detailed.
    
             OCT: Update result of each slot
                   1: Completed
                   2: Failed
    
             The slot for which the current state is used becomes the
             following.
    
             OCT[0] : MainBoard(iPASO200)   or SLOT0
             OCT[1] : MODEM1(iPASO200)      or SLOT1
             OCT[2] : MODEM2(iPASO200)      or SLOT2
             OCT[3] : Option Card(iPASO200) or SLOT3
               :
             OCT[33]: ODU1
             OCT[34]: ODU2
             OCT[35]: ODU3
               :
    
             *Pertinent details: ipeSysOpFileDownloadCtrl
             *Pertinent details: ipeFsUpdateFileDetail
             *Pertinent details: ipeFsUsbCommand"
        ::= { ipeFsFileInfoEntry 8 }
    
    -- 1.3.6.1.4.1.119.2.3.69.213.502.5.2.1.1.9
    ipeFsUpdateFileProgressBase OBJECT-TYPE
        SYNTAX      INTEGER
        ACCESS      read-only
        STATUS      mandatory
        DESCRIPTION
            "Progress of update (denominator).
    
             *Pertinent details: ipeSysOpFileDownloadModule
             *Pertinent details: ipeFsUpdateFileStatus"
        ::= { ipeFsFileInfoEntry 9 }
    
    -- 1.3.6.1.4.1.119.2.3.69.213.502.5.2.1.1.10
    ipeFsUpdateFileProgress OBJECT-TYPE
        SYNTAX      INTEGER
        ACCESS      read-only
        STATUS      mandatory
        DESCRIPTION
            "Progress of update (molecule).
    
             *Pertinent details: ipeSysOpFileDownloadModule
             *Pertinent details: ipeFsUpdateFileStatus"
        ::= { ipeFsFileInfoEntry 10 }
    
    -- 1.3.6.1.4.1.119.2.3.69.213.502.5.2.1.1.11
    ipeFsUpdateFileUpdateList OBJECT-TYPE
        SYNTAX      DisplayString
        ACCESS      read-only
        STATUS      mandatory
        DESCRIPTION
            "Definition of update slot number.
    
             Form of file list:
             When downloading it to ODU/FPGA/MDPRM, the forwarding site slot
             number is enumerated by a comma end.
    
             Ex) 0,5,1,6,10...
               The slot number of relating MODEM and fpga must set the slot
             number of
               Option Card to odu and mdprm according to inventory
             information.
    
             The slot number to which the current state can be set becomes the
             following.
    
             iPASO200             iPASO400,1000
             0 : MainBoard     or SLOT0
             1 : MODEM1        or SLOT1
             2 : MODEM2        or SLOT2
             3 : Option Card   or SLOT3
                   :
             33: ODU1
             34: ODU2
             35: ODU3
                   :
    
             *Pertinent details: ipeFsUpdateFileDetail"
        ::= { ipeFsFileInfoEntry 11 }
    
    -- 1.3.6.1.4.1.119.2.3.69.213.502.5.2.1.1.12
    ipeFsUpdateFileConfigPartial OBJECT-TYPE
        SYNTAX      OCTET STRING (SIZE(4))
        ACCESS      read-only
        STATUS      mandatory
        DESCRIPTION
            "Specify Equipment Configuration Partial Download pattern.
             If this object is set with ipeFsUpdateFileDetail, the system will
             perform the partial download, otherwise the system will perform
             the normal download. And Partial Download is performed only when
             Equipment Configuration Dowload.
    
             SYNTAX is 32bit string. The definition of each bit is shown
             below.
    
             - bit1-4: specify download mode.
              0001 : normal mode
              other value : reserved (system rejects the request)
             - bit5-32: specify the equipment config part. Setting 1 to each
             bit means corresponding config download is activated.
              Bit5 : Equipment Configuration (must set when the normal mode)
              Bit6 : Radio Configuration
              Bit7 : Radio Configuration w/o Radio Frequency
                     Bit6 and Bit7 cannot be set to 1 simultaneously.
              Bit8 : E1/STM1 Mapping (must set when Bit6 or Bit7 is activated)
              Bit9 : MODEM Function setting
              Bit10: ETH Function setting
              Bit11: E1/STM1/Cross Connect Setting
              Bit12: PWE Setting
              Bit13: Equipment Clock/Synchronization Setting
              Bit14: Relay-Alarm Mapping
              Bit15: V11/OW Setting
              Bit16: Alarm/AIS Setting
              Bit17: PMON/RMON Setting
              Bit18: AUX Setting
    
              other: reserved (don't care)
    
             Example)
              the pattern of downloading the equipment configuration, radio
             configuration, E1/STM1 mapping, ETH Function Setting on normal
             mode.
               ipeFsUpdateFileConfigPartial =
                       '00011101010000000000000000000000'"
        ::= { ipeFsFileInfoEntry 12 }
    
    -- 1.3.6.1.4.1.119.2.3.69.213.502.5.2.1.1.1001
    ipeFsFileInfoNEAddressAddrType OBJECT-TYPE
        SYNTAX      InetAddressType
        ACCESS      not-accessible
        STATUS      mandatory
        DESCRIPTION
            "Represents the IP address type of NE address index.
             Only ipv4(1) and ipv6(2) are supported."
        ::= { ipeFsFileInfoEntry 1001 }
    
    -- 1.3.6.1.4.1.119.2.3.69.213.502.5.2.2
    ipeFsUsbInfoTable OBJECT-TYPE
        SYNTAX      SEQUENCE OF IpeFsUsbInfoEntry
        ACCESS      not-accessible
        STATUS      mandatory
        DESCRIPTION
            "Table of USB memory information."
        ::= { ipeFileSystemGroup 2 }
    
    -- 1.3.6.1.4.1.119.2.3.69.213.502.5.2.2.1
    ipeFsUsbInfoEntry OBJECT-TYPE
        SYNTAX      IpeFsUsbInfoEntry
        ACCESS      not-accessible
        STATUS      mandatory
        DESCRIPTION
            "Entry of USB mamory information."
        INDEX       { ipeFsUsbInfoNEAddressAddrType, ipeFsUsbInfoNEAddress, ipeFsUsbInfoIndex }
        ::= { ipeFsUsbInfoTable 1 }
    
    IpeFsUsbInfoEntry ::= SEQUENCE {
        ipeFsUsbInfoIndex               INTEGER,
        ipeFsUsbInfoNEAddress           InetAddress,
        ipeFsUsbCommand                 DisplayString,
        ipeFsUsbProcStatus              INTEGER,
        ipeFsUsbList                    DisplayString,
        ipeFsUsbConnectStatus           INTEGER,
        ipeFsUsbInfoNEAddressAddrType   InetAddressType
    }
    
    -- 1.3.6.1.4.1.119.2.3.69.213.502.5.2.2.1.1
    ipeFsUsbInfoIndex OBJECT-TYPE
        SYNTAX      INTEGER (1)
        ACCESS      not-accessible
        STATUS      mandatory
        DESCRIPTION
            "Index of Table."
        ::= { ipeFsUsbInfoEntry 1 }
    
    -- 1.3.6.1.4.1.119.2.3.69.213.502.5.2.2.1.2
    ipeFsUsbInfoNEAddress OBJECT-TYPE
        SYNTAX      InetAddress
        ACCESS      not-accessible
        STATUS      mandatory
        DESCRIPTION
            ""
        ::= { ipeFsUsbInfoEntry 2 }
    
    -- 1.3.6.1.4.1.119.2.3.69.213.502.5.2.2.1.3
    ipeFsUsbCommand OBJECT-TYPE
        SYNTAX      DisplayString
        ACCESS      read-only
        STATUS      mandatory
        DESCRIPTION
            "USB control mode/USB file path/Program type specification.
    
             [Mode],[Arg1],[Type]
               Mode:USB control mode
                 0:DL, 1:UL
               Arg1:object file path -1 (original file path (path from a
             chroot subordinate) When DL: Inside of USB, When UL: Inside of
             IPE)
                   Case of DL: Ex.) idu/iPASOLINK200-idufw-v1.00.XX.bin
                   Case of UL: Ex.) export/config/iPASOLINK-network.cfg
               Type:Program type
                   The program type set to  'ipeSysOpFileDownloadModule' is
             specified.
                   *The unsetting is allowed for an arbitrary, set item.
    
                  0: Invalid
                  1: IDU F/W
                  2: ODU F/W
                  3: MODEM Parameter
                  4: FPGA(Option Card)
                  5: FPGA(MainBoard)
                  6: MSE Card F/W
                  7: Software License Key
                  8: Network Config
                  9: Equipment Config
                 10: User Config
                 11: HTTPS Server Certificate
    
             *The object file name allows only alphanumeric character '0-9',
             'a-z', 'A-Z' of ASCII code, and sign '-_.+'.
    
             *Pertinent details: ipeSysOpFileDownloadModule
             *Pertinent details: ipeSysOpFileDownloadStatus
             *Pertinent details: ipeFsUpdateFileStatus
             *Pertinent details: ipeFsUsbProcStatus
    
             [Race condition]
             *When ipeSysOpFileDownloadStatus is (3:Executing) or
             (4:Suspending), (0:DL) is invalid.
             *When ipeFsUpdateFileStatusis (3:Executing),  (0:DL) is invalid.
             *When ipeFsUsbProcStatus is (2:Normal :Process executing),
             (0:DL) is invalid."
        ::= { ipeFsUsbInfoEntry 3 }
    
    -- 1.3.6.1.4.1.119.2.3.69.213.502.5.2.2.1.4
    ipeFsUsbProcStatus OBJECT-TYPE
        SYNTAX      INTEGER { invalid(0), completed(1), executing(2),
                        diskFullError(98), noSuchFileError(99),
                        unKnownFileError(101), notInsertError(102),
                        accessError(103), otherError(127) }
        ACCESS      read-only
        STATUS      mandatory
        DESCRIPTION
            "Status of USB memory control result.
    
             The classification of a setting value and the meaning are as
             follows.
               0:Invalidity
               1:NORMAL:Normal end
               2:NORMAL:Executing
              98:ERROR:The lack of free space on disk or media
              99:ERROR:File/directory not found
             101:ERROR:The kind of designated files,the size, contents, etc.
             are unjust
             102:ERROR:Media aren't inserted
             103:ERROR:Media access error (ex:unjust format)
             127:ERROR:Undefined error (other errors)
             When having a control instruction, it's made '2:Executing'.
    
             *'0:Invalidity' is used as an initial state.
    
             *Pertinent details: ipeFsUsbCommand"
        ::= { ipeFsUsbInfoEntry 4 }
    
    -- 1.3.6.1.4.1.119.2.3.69.213.502.5.2.2.1.5
    ipeFsUsbList OBJECT-TYPE
        SYNTAX      DisplayString
        ACCESS      read-only
        STATUS      mandatory
        DESCRIPTION
            "File list format.
    
             Form of file list:
    
             It's 1 item by 'file name (path from a chroot subordinate),file
             size,CRC'.
             Each item is divided at space.
    
             *CRC is fixed '0'.
    
             Ex) FilePath1/FileName1,size,CRC FilePath2/FileName2,size,CRC..."
        ::= { ipeFsUsbInfoEntry 5 }
    
    -- 1.3.6.1.4.1.119.2.3.69.213.502.5.2.2.1.6
    ipeFsUsbConnectStatus OBJECT-TYPE
        SYNTAX      INTEGER { usbConnect(1), usbNoConnect(2) }
        ACCESS      read-only
        STATUS      mandatory
        DESCRIPTION
            "Status of connection USB memory.
    
             1:Connect
             2:Not connect"
        ::= { ipeFsUsbInfoEntry 6 }
    
    -- 1.3.6.1.4.1.119.2.3.69.213.502.5.2.2.1.1001
    ipeFsUsbInfoNEAddressAddrType OBJECT-TYPE
        SYNTAX      InetAddressType
        ACCESS      not-accessible
        STATUS      mandatory
        DESCRIPTION
            "Represents the IP address type of NE address index.
             Only ipv4(1) and ipv6(2) are supported."
        ::= { ipeFsUsbInfoEntry 1001 }
    
    -- 1.3.6.1.4.1.119.2.3.69.213.502.5.3
    ipeConfigurationGroup OBJECT IDENTIFIER
        ::= { system5 3 }
    
    -- 1.3.6.1.4.1.119.2.3.69.213.502.5.3.1
    ipeCfgSystemTable OBJECT-TYPE
        SYNTAX      SEQUENCE OF IpeCfgSystemEntry
        ACCESS      not-accessible
        STATUS      mandatory
        DESCRIPTION
            "Table of System Item Information."
        ::= { ipeConfigurationGroup 1 }
    
    -- 1.3.6.1.4.1.119.2.3.69.213.502.5.3.1.1
    ipeCfgSystemEntry OBJECT-TYPE
        SYNTAX      IpeCfgSystemEntry
        ACCESS      not-accessible
        STATUS      mandatory
        DESCRIPTION
            "Entry of System Item Information."
        INDEX       { ipeCfgSystemNEAddressAddrType, ipeCfgSystemNEAddress, ipeCfgSystemIndex }
        ::= { ipeCfgSystemTable 1 }
    
    IpeCfgSystemEntry ::= SEQUENCE {
        ipeCfgSystemIndex               INTEGER,
        ipeCfgSystemNEAddress           InetAddress,
        ipeCfgNeName                    DisplayString,
        ipeCfgAreaName                  DisplayString,
        ipeCfgMemo                      DisplayString,
        ipeCfgSystemNEAddressAddrType   InetAddressType
    }
    
    -- 1.3.6.1.4.1.119.2.3.69.213.502.5.3.1.1.1
    ipeCfgSystemIndex OBJECT-TYPE
        SYNTAX      INTEGER (1)
        ACCESS      not-accessible
        STATUS      mandatory
        DESCRIPTION
            "Index of table."
        ::= { ipeCfgSystemEntry 1 }
    
    -- 1.3.6.1.4.1.119.2.3.69.213.502.5.3.1.1.2
    ipeCfgSystemNEAddress OBJECT-TYPE
        SYNTAX      InetAddress
        ACCESS      not-accessible
        STATUS      mandatory
        DESCRIPTION
            ""
        ::= { ipeCfgSystemEntry 2 }
    
    -- 1.3.6.1.4.1.119.2.3.69.213.502.5.3.1.1.3
    ipeCfgNeName OBJECT-TYPE
        SYNTAX      DisplayString
        ACCESS      read-only
        STATUS      mandatory
        DESCRIPTION
            "PASOLINK unit name. White space characters are not allowed for
             head or tail of characters."
        ::= { ipeCfgSystemEntry 3 }
    
    -- 1.3.6.1.4.1.119.2.3.69.213.502.5.3.1.1.4
    ipeCfgAreaName OBJECT-TYPE
        SYNTAX      DisplayString
        ACCESS      read-only
        STATUS      mandatory
        DESCRIPTION
            "Area name. White space characters are not allowed for head or
             tail of characters."
        ::= { ipeCfgSystemEntry 4 }
    
    -- 1.3.6.1.4.1.119.2.3.69.213.502.5.3.1.1.5
    ipeCfgMemo OBJECT-TYPE
        SYNTAX      DisplayString
        ACCESS      read-only
        STATUS      mandatory
        DESCRIPTION
            "Memorandum. White space characters are not allowed for head or
             tail of characters."
        ::= { ipeCfgSystemEntry 5 }
    
    -- 1.3.6.1.4.1.119.2.3.69.213.502.5.3.1.1.1001
    ipeCfgSystemNEAddressAddrType OBJECT-TYPE
        SYNTAX      InetAddressType
        ACCESS      not-accessible
        STATUS      mandatory
        DESCRIPTION
            "Represents the IP address type of NE address index.
             Only ipv4(1) and ipv6(2) are supported."
        ::= { ipeCfgSystemEntry 1001 }
    
    -- 1.3.6.1.4.1.119.2.3.69.213.502.5.3.2
    ipeCfgOemTable OBJECT-TYPE
        SYNTAX      SEQUENCE OF IpeCfgOemEntry
        ACCESS      not-accessible
        STATUS      mandatory
        DESCRIPTION
            "Table of Equipment Item Information."
        ::= { ipeConfigurationGroup 2 }
    
    -- 1.3.6.1.4.1.119.2.3.69.213.502.5.3.2.1
    ipeCfgOemEntry OBJECT-TYPE
        SYNTAX      IpeCfgOemEntry
        ACCESS      not-accessible
        STATUS      mandatory
        DESCRIPTION
            "Entry of Equipment Item Information."
        INDEX       { ipeCfgOemNEAddressAddrType, ipeCfgOemNEAddress, ipeCfgOemIndex }
        ::= { ipeCfgOemTable 1 }
    
    IpeCfgOemEntry ::= SEQUENCE {
        ipeCfgOemIndex              INTEGER,
        ipeCfgOemNEAddress          InetAddress,
        ipeCfgOemSysDescr           DisplayString,
        ipeCfgOemSysContact         DisplayString,
        ipeCfgOemSysName            DisplayString,
        ipeCfgOemSysLocation        DisplayString,
        ipeCfgOemNEAddressAddrType  InetAddressType
    }
    
    -- 1.3.6.1.4.1.119.2.3.69.213.502.5.3.2.1.1
    ipeCfgOemIndex OBJECT-TYPE
        SYNTAX      INTEGER (1)
        ACCESS      not-accessible
        STATUS      mandatory
        DESCRIPTION
            "Index of table."
        ::= { ipeCfgOemEntry 1 }
    
    -- 1.3.6.1.4.1.119.2.3.69.213.502.5.3.2.1.2
    ipeCfgOemNEAddress OBJECT-TYPE
        SYNTAX      InetAddress
        ACCESS      not-accessible
        STATUS      mandatory
        DESCRIPTION
            ""
        ::= { ipeCfgOemEntry 2 }
    
    -- 1.3.6.1.4.1.119.2.3.69.213.502.5.3.2.1.3
    ipeCfgOemSysDescr OBJECT-TYPE
        SYNTAX      DisplayString
        ACCESS      read-only
        STATUS      mandatory
        DESCRIPTION
            "System Description.
             The space of the begininng and end dose not permit it."
        ::= { ipeCfgOemEntry 3 }
    
    -- 1.3.6.1.4.1.119.2.3.69.213.502.5.3.2.1.4
    ipeCfgOemSysContact OBJECT-TYPE
        SYNTAX      DisplayString
        ACCESS      read-only
        STATUS      mandatory
        DESCRIPTION
            "System contact.
             The space of the begininng and end dose not permit it."
        ::= { ipeCfgOemEntry 4 }
    
    -- 1.3.6.1.4.1.119.2.3.69.213.502.5.3.2.1.5
    ipeCfgOemSysName OBJECT-TYPE
        SYNTAX      DisplayString
        ACCESS      read-only
        STATUS      mandatory
        DESCRIPTION
            "System name.
             The space of the begininng and end dose not permit it."
        ::= { ipeCfgOemEntry 5 }
    
    -- 1.3.6.1.4.1.119.2.3.69.213.502.5.3.2.1.6
    ipeCfgOemSysLocation OBJECT-TYPE
        SYNTAX      DisplayString
        ACCESS      read-only
        STATUS      mandatory
        DESCRIPTION
            "System location.
             The space of the begininng and end dose not permit it."
        ::= { ipeCfgOemEntry 6 }
    
    -- 1.3.6.1.4.1.119.2.3.69.213.502.5.3.2.1.1001
    ipeCfgOemNEAddressAddrType OBJECT-TYPE
        SYNTAX      InetAddressType
        ACCESS      not-accessible
        STATUS      mandatory
        DESCRIPTION
            "Represents the IP address type of NE address index.
             Only ipv4(1) and ipv6(2) are supported."
        ::= { ipeCfgOemEntry 1001 }
    
    -- 1.3.6.1.4.1.119.2.3.69.213.502.5.3.3
    ipeCfgAux OBJECT IDENTIFIER
        ::= { ipeConfigurationGroup 3 }
    
    -- 1.3.6.1.4.1.119.2.3.69.213.502.5.3.3.1
    ipeCfgAuxInTable OBJECT-TYPE
        SYNTAX      SEQUENCE OF IpeCfgAuxInEntry
        ACCESS      not-accessible
        STATUS      mandatory
        DESCRIPTION
            "Aux Input Table"
        ::= { ipeCfgAux 1 }
    
    -- 1.3.6.1.4.1.119.2.3.69.213.502.5.3.3.1.1
    ipeCfgAuxInEntry OBJECT-TYPE
        SYNTAX      IpeCfgAuxInEntry
        ACCESS      not-accessible
        STATUS      mandatory
        DESCRIPTION
            ""
        INDEX       { ipeCfgAuxInNEAddressAddrType, ipeCfgAuxInNEAddress, ipeCfgAuxInIndex }
        ::= { ipeCfgAuxInTable 1 }
    
    IpeCfgAuxInEntry ::= SEQUENCE {
        ipeCfgAuxInIndex                INTEGER,
        ipeCfgAuxInNEAddress            InetAddress,
        ipeCfgAuxInItemName             DisplayString,
        ipeCfgAuxInItemType             INTEGER,
        ipeCfgAuxInOpenState            DisplayString,
        ipeCfgAuxInCloseState           DisplayString,
        ipeCfgAuxInSeverity             INTEGER,
        ipeCfgAuxInAlarmType            AlarmTypeValue,
        ipeCfgAuxInProbableCause        ProbableCauseValue,
        ipeCfgAuxInNEAddressAddrType    InetAddressType
    }
    
    -- 1.3.6.1.4.1.119.2.3.69.213.502.5.3.3.1.1.1
    ipeCfgAuxInIndex OBJECT-TYPE
        SYNTAX      INTEGER
        ACCESS      not-accessible
        STATUS      mandatory
        DESCRIPTION
            "Index of this table."
        ::= { ipeCfgAuxInEntry 1 }
    
    -- 1.3.6.1.4.1.119.2.3.69.213.502.5.3.3.1.1.2
    ipeCfgAuxInNEAddress OBJECT-TYPE
        SYNTAX      InetAddress
        ACCESS      not-accessible
        STATUS      mandatory
        DESCRIPTION
            "reserved."
        ::= { ipeCfgAuxInEntry 2 }
    
    -- 1.3.6.1.4.1.119.2.3.69.213.502.5.3.3.1.1.3
    ipeCfgAuxInItemName OBJECT-TYPE
        SYNTAX      DisplayString (SIZE(0..32))
        ACCESS      read-only
        STATUS      mandatory
        DESCRIPTION
            "Item Name"
        ::= { ipeCfgAuxInEntry 3 }
    
    -- 1.3.6.1.4.1.119.2.3.69.213.502.5.3.3.1.1.4
    ipeCfgAuxInItemType OBJECT-TYPE
        SYNTAX      INTEGER { alarmInOpen(1), alarmInClose(2), status(3) }
        ACCESS      read-only
        STATUS      mandatory
        DESCRIPTION
            "Item Type"
        ::= { ipeCfgAuxInEntry 4 }
    
    -- 1.3.6.1.4.1.119.2.3.69.213.502.5.3.3.1.1.5
    ipeCfgAuxInOpenState OBJECT-TYPE
        SYNTAX      DisplayString (SIZE(0..32))
        ACCESS      read-only
        STATUS      mandatory
        DESCRIPTION
            "Status Strings (Event Off (Open))"
        ::= { ipeCfgAuxInEntry 5 }
    
    -- 1.3.6.1.4.1.119.2.3.69.213.502.5.3.3.1.1.6
    ipeCfgAuxInCloseState OBJECT-TYPE
        SYNTAX      DisplayString (SIZE(0..32))
        ACCESS      read-only
        STATUS      mandatory
        DESCRIPTION
            "Status Strings (Event On (Close))"
        ::= { ipeCfgAuxInEntry 6 }
    
    -- 1.3.6.1.4.1.119.2.3.69.213.502.5.3.3.1.1.7
    ipeCfgAuxInSeverity OBJECT-TYPE
        SYNTAX      INTEGER { invalid(0), critical(1), major(2), minor(3),
                        warning(4) }
        ACCESS      read-only
        STATUS      mandatory
        DESCRIPTION
            "Severity (X.733)"
        ::= { ipeCfgAuxInEntry 7 }
    
    -- 1.3.6.1.4.1.119.2.3.69.213.502.5.3.3.1.1.8
    ipeCfgAuxInAlarmType OBJECT-TYPE
        SYNTAX      AlarmTypeValue
        ACCESS      read-only
        STATUS      mandatory
        DESCRIPTION
            "Alarm Type (X.733)"
        ::= { ipeCfgAuxInEntry 8 }
    
    -- 1.3.6.1.4.1.119.2.3.69.213.502.5.3.3.1.1.9
    ipeCfgAuxInProbableCause OBJECT-TYPE
        SYNTAX      ProbableCauseValue
        ACCESS      read-only
        STATUS      mandatory
        DESCRIPTION
            "Probable Cause (X.733)"
        ::= { ipeCfgAuxInEntry 9 }
    
    -- 1.3.6.1.4.1.119.2.3.69.213.502.5.3.3.1.1.1001
    ipeCfgAuxInNEAddressAddrType OBJECT-TYPE
        SYNTAX      InetAddressType
        ACCESS      not-accessible
        STATUS      mandatory
        DESCRIPTION
            "Represents the IP address type of NE address index.
             Only ipv4(1) and ipv6(2) are supported."
        ::= { ipeCfgAuxInEntry 1001 }
    
    -- 1.3.6.1.4.1.119.2.3.69.213.502.5.3.3.2
    ipeCfgAuxOutTable OBJECT-TYPE
        SYNTAX      SEQUENCE OF IpeCfgAuxOutEntry
        ACCESS      not-accessible
        STATUS      mandatory
        DESCRIPTION
            "AUX Output Table"
        ::= { ipeCfgAux 2 }
    
    -- 1.3.6.1.4.1.119.2.3.69.213.502.5.3.3.2.1
    ipeCfgAuxOutEntry OBJECT-TYPE
        SYNTAX      IpeCfgAuxOutEntry
        ACCESS      not-accessible
        STATUS      mandatory
        DESCRIPTION
            ""
        INDEX       { ipeCfgAuxOutNEAddressAddrType, ipeCfgAuxOutNEAddress, ipeCfgAuxOutIndex }
        ::= { ipeCfgAuxOutTable 1 }
    
    IpeCfgAuxOutEntry ::= SEQUENCE {
        ipeCfgAuxOutIndex               INTEGER,
        ipeCfgAuxOutNEAddress           InetAddress,
        ipeCfgAuxOutItemName            DisplayString,
        ipeCfgAuxOutOpenState           DisplayString,
        ipeCfgAuxOutCloseState          DisplayString,
        ipeCfgAuxOutNEAddressAddrType   InetAddressType
    }
    
    -- 1.3.6.1.4.1.119.2.3.69.213.502.5.3.3.2.1.1
    ipeCfgAuxOutIndex OBJECT-TYPE
        SYNTAX      INTEGER
        ACCESS      not-accessible
        STATUS      mandatory
        DESCRIPTION
            "Index of this table."
        ::= { ipeCfgAuxOutEntry 1 }
    
    -- 1.3.6.1.4.1.119.2.3.69.213.502.5.3.3.2.1.2
    ipeCfgAuxOutNEAddress OBJECT-TYPE
        SYNTAX      InetAddress
        ACCESS      not-accessible
        STATUS      mandatory
        DESCRIPTION
            "reserved."
        ::= { ipeCfgAuxOutEntry 2 }
    
    -- 1.3.6.1.4.1.119.2.3.69.213.502.5.3.3.2.1.3
    ipeCfgAuxOutItemName OBJECT-TYPE
        SYNTAX      DisplayString (SIZE(0..32))
        ACCESS      read-only
        STATUS      mandatory
        DESCRIPTION
            "Item Name"
        ::= { ipeCfgAuxOutEntry 3 }
    
    -- 1.3.6.1.4.1.119.2.3.69.213.502.5.3.3.2.1.4
    ipeCfgAuxOutOpenState OBJECT-TYPE
        SYNTAX      DisplayString (SIZE(0..32))
        ACCESS      read-only
        STATUS      mandatory
        DESCRIPTION
            "Status Strings (Event Off (Open))"
        ::= { ipeCfgAuxOutEntry 4 }
    
    -- 1.3.6.1.4.1.119.2.3.69.213.502.5.3.3.2.1.5
    ipeCfgAuxOutCloseState OBJECT-TYPE
        SYNTAX      DisplayString (SIZE(0..32))
        ACCESS      read-only
        STATUS      mandatory
        DESCRIPTION
            "Status Strings (Event On (Close))"
        ::= { ipeCfgAuxOutEntry 5 }
    
    -- 1.3.6.1.4.1.119.2.3.69.213.502.5.3.3.2.1.1001
    ipeCfgAuxOutNEAddressAddrType OBJECT-TYPE
        SYNTAX      InetAddressType
        ACCESS      not-accessible
        STATUS      mandatory
        DESCRIPTION
            "Represents the IP address type of NE address index.
             Only ipv4(1) and ipv6(2) are supported."
        ::= { ipeCfgAuxOutEntry 1001 }
    
    -- 1.3.6.1.4.1.119.2.3.69.213.502.5.3.4
    ipeCfgNtp OBJECT IDENTIFIER
        ::= { ipeConfigurationGroup 4 }
    
    -- 1.3.6.1.4.1.119.2.3.69.213.502.5.3.4.1
    ipeCfgNtpServiceTable OBJECT-TYPE
        SYNTAX      SEQUENCE OF IpeCfgNtpServiceEntry
        ACCESS      not-accessible
        STATUS      mandatory
        DESCRIPTION
            "Table of NTP configuration information."
        ::= { ipeCfgNtp 1 }
    
    -- 1.3.6.1.4.1.119.2.3.69.213.502.5.3.4.1.1
    ipeCfgNtpServiceEntry OBJECT-TYPE
        SYNTAX      IpeCfgNtpServiceEntry
        ACCESS      not-accessible
        STATUS      mandatory
        DESCRIPTION
            "Entry of NTP configuration information."
        INDEX       { ipeCfgNtpServiceNEAddressAddrType, ipeCfgNtpServiceNEAddress, ipeCfgNtpServiceIndex }
        ::= { ipeCfgNtpServiceTable 1 }
    
    IpeCfgNtpServiceEntry ::= SEQUENCE {
        ipeCfgNtpServiceIndex                   INTEGER,
        ipeCfgNtpServiceNEAddress               InetAddress,
        ipeCfgNtpServiceEnable                  INTEGER,
        ipeCfgNtpServerMode                     INTEGER,
        ipeCfgNtpClientMode                     INTEGER,
        ipeCfgNtpServerStratum                  INTEGER,
        ipeCfgNtpServerMulticastPort            INTEGER,
        ipeCfgNtpServerMulticastIntervalTime    INTEGER,
        ipeCfgNtpAuthenticationEnable           EnableDisableValue,
        ipeCfgNtpServerMulticastAuthKeyIndex    IpeNtpKeyAdminIndexOrZero,
        ipeCfgNtpServiceNEAddressAddrType       InetAddressType
    }
    
    -- 1.3.6.1.4.1.119.2.3.69.213.502.5.3.4.1.1.1
    ipeCfgNtpServiceIndex OBJECT-TYPE
        SYNTAX      INTEGER (1)
        ACCESS      not-accessible
        STATUS      mandatory
        DESCRIPTION
            "Index of table."
        ::= { ipeCfgNtpServiceEntry 1 }
    
    -- 1.3.6.1.4.1.119.2.3.69.213.502.5.3.4.1.1.2
    ipeCfgNtpServiceNEAddress OBJECT-TYPE
        SYNTAX      InetAddress
        ACCESS      not-accessible
        STATUS      mandatory
        DESCRIPTION
            ""
        ::= { ipeCfgNtpServiceEntry 2 }
    
    -- 1.3.6.1.4.1.119.2.3.69.213.502.5.3.4.1.1.3
    ipeCfgNtpServiceEnable OBJECT-TYPE
        SYNTAX      INTEGER { invalid(0), disabled(1), enabled(2) }
        ACCESS      read-only
        STATUS      mandatory
        DESCRIPTION
            "NTP control enable."
        ::= { ipeCfgNtpServiceEntry 3 }
    
    -- 1.3.6.1.4.1.119.2.3.69.213.502.5.3.4.1.1.4
    ipeCfgNtpServerMode OBJECT-TYPE
        SYNTAX      INTEGER { invalid(0), unicast(1), multicast(2),
                        disabled(3) }
        ACCESS      read-only
        STATUS      mandatory
        DESCRIPTION
            "NTP server mode."
        ::= { ipeCfgNtpServiceEntry 4 }
    
    -- 1.3.6.1.4.1.119.2.3.69.213.502.5.3.4.1.1.5
    ipeCfgNtpClientMode OBJECT-TYPE
        SYNTAX      INTEGER { invalid(0), unicast(1), multicast(2),
                        disabled(3) }
        ACCESS      read-only
        STATUS      mandatory
        DESCRIPTION
            "NTP client mode."
        ::= { ipeCfgNtpServiceEntry 5 }
    
    -- 1.3.6.1.4.1.119.2.3.69.213.502.5.3.4.1.1.6
    ipeCfgNtpServerStratum OBJECT-TYPE
        SYNTAX      INTEGER (2..15)
        ACCESS      read-only
        STATUS      mandatory
        DESCRIPTION
            "NTP Stratum."
        ::= { ipeCfgNtpServiceEntry 6 }
    
    -- 1.3.6.1.4.1.119.2.3.69.213.502.5.3.4.1.1.7
    ipeCfgNtpServerMulticastPort OBJECT-TYPE
        SYNTAX      INTEGER
        ACCESS      read-only
        STATUS      mandatory
        DESCRIPTION
            "NTP server multicast port.
             Bridge7(17), Bridge8(18) can not be set to this (iPASOLINK EX
             Advanced).
             The value Bridge1(11), Bridge2(12), Bridge3(13),
             Bridge4(14), Bridge5(15) Bridge6(16) are available (iPASOLINK EX
             Advanced)."
        ::= { ipeCfgNtpServiceEntry 7 }
    
    -- 1.3.6.1.4.1.119.2.3.69.213.502.5.3.4.1.1.8
    ipeCfgNtpServerMulticastIntervalTime OBJECT-TYPE
        SYNTAX      INTEGER (4..17)
        ACCESS      read-only
        STATUS      mandatory
        DESCRIPTION
            "Value of NTP multicast polling time."
        ::= { ipeCfgNtpServiceEntry 8 }
    
    -- 1.3.6.1.4.1.119.2.3.69.213.502.5.3.4.1.1.9
    ipeCfgNtpAuthenticationEnable OBJECT-TYPE
        SYNTAX      EnableDisableValue
        ACCESS      read-only
        STATUS      mandatory
        DESCRIPTION
            "Enabling NTP authentication."
        ::= { ipeCfgNtpServiceEntry 9 }
    
    -- 1.3.6.1.4.1.119.2.3.69.213.502.5.3.4.1.1.10
    ipeCfgNtpServerMulticastAuthKeyIndex OBJECT-TYPE
        SYNTAX      IpeNtpKeyAdminIndexOrZero
        ACCESS      read-only
        STATUS      mandatory
        DESCRIPTION
            "Configuring Authentication Key Index.
             This value is available only when the system is running on the
             NTP multicast server mode."
        ::= { ipeCfgNtpServiceEntry 10 }
    
    -- 1.3.6.1.4.1.119.2.3.69.213.502.5.3.4.1.1.1001
    ipeCfgNtpServiceNEAddressAddrType OBJECT-TYPE
        SYNTAX      InetAddressType
        ACCESS      not-accessible
        STATUS      mandatory
        DESCRIPTION
            "Represents the IP address type of NE address index.
             Only ipv4(1) and ipv6(2) are supported."
        ::= { ipeCfgNtpServiceEntry 1001 }
    
    -- 1.3.6.1.4.1.119.2.3.69.213.502.5.3.4.2
    ipeCfgNtpServerTable OBJECT-TYPE
        SYNTAX      SEQUENCE OF IpeCfgNtpServerEntry
        ACCESS      not-accessible
        STATUS      mandatory
        DESCRIPTION
            "Table of NTP server information."
        ::= { ipeCfgNtp 2 }
    
    -- 1.3.6.1.4.1.119.2.3.69.213.502.5.3.4.2.1
    ipeCfgNtpServerEntry OBJECT-TYPE
        SYNTAX      IpeCfgNtpServerEntry
        ACCESS      not-accessible
        STATUS      mandatory
        DESCRIPTION
            "Entry of NTP server information."
        INDEX       { ipeCfgNtpServerNEAddressAddrType, ipeCfgNtpServerNEAddress, ipeCfgNtpServerIndex }
        ::= { ipeCfgNtpServerTable 1 }
    
    IpeCfgNtpServerEntry ::= SEQUENCE {
        ipeCfgNtpServerIndex                INTEGER,
        ipeCfgNtpServerNEAddress            InetAddress,
        ipeCfgNtpServerAddress              IpAddress,
        ipeCfgNtpVersion                    INTEGER,
        ipeCfgNtpPollTime                   INTEGER,
        ipeCfgNtpServerAuthKeyIndex         IpeNtpKeyAdminIndexOrZero,
        ipeCfgNtpServerV6Address            Ipv6Address,
        ipeCfgNtpServerAddressType          INTEGER,
        ipeCfgNtpServerNEAddressAddrType    InetAddressType
    }
    
    -- 1.3.6.1.4.1.119.2.3.69.213.502.5.3.4.2.1.1
    ipeCfgNtpServerIndex OBJECT-TYPE
        SYNTAX      INTEGER (1..4)
        ACCESS      not-accessible
        STATUS      mandatory
        DESCRIPTION
            "Index of table."
        ::= { ipeCfgNtpServerEntry 1 }
    
    -- 1.3.6.1.4.1.119.2.3.69.213.502.5.3.4.2.1.2
    ipeCfgNtpServerNEAddress OBJECT-TYPE
        SYNTAX      InetAddress
        ACCESS      not-accessible
        STATUS      mandatory
        DESCRIPTION
            ""
        ::= { ipeCfgNtpServerEntry 2 }
    
    -- 1.3.6.1.4.1.119.2.3.69.213.502.5.3.4.2.1.3
    ipeCfgNtpServerAddress OBJECT-TYPE
        SYNTAX      IpAddress
        ACCESS      read-only
        STATUS      mandatory
        DESCRIPTION
            "IP Address of NTP server."
        ::= { ipeCfgNtpServerEntry 3 }
    
    -- 1.3.6.1.4.1.119.2.3.69.213.502.5.3.4.2.1.4
    ipeCfgNtpVersion OBJECT-TYPE
        SYNTAX      INTEGER (3..4)
        ACCESS      read-only
        STATUS      mandatory
        DESCRIPTION
            "Version of supported NTP message."
        ::= { ipeCfgNtpServerEntry 4 }
    
    -- 1.3.6.1.4.1.119.2.3.69.213.502.5.3.4.2.1.5
    ipeCfgNtpPollTime OBJECT-TYPE
        SYNTAX      INTEGER (4..17)
        ACCESS      read-only
        STATUS      mandatory
        DESCRIPTION
            "NTP Polling Time, in seconds as a power of two.
             For instance, a value of six indicates a interval of 64 seconds.
    
             Note) The value less than 6 is rejected by the agent because of
             the system recommendation.
              iPASOLINK 200/400/1000 series : R3.5 or later.
              iPASOLINK AOR : R1.0 or later."
        ::= { ipeCfgNtpServerEntry 5 }
    
    -- 1.3.6.1.4.1.119.2.3.69.213.502.5.3.4.2.1.6
    ipeCfgNtpServerAuthKeyIndex OBJECT-TYPE
        SYNTAX      IpeNtpKeyAdminIndexOrZero
        ACCESS      read-only
        STATUS      mandatory
        DESCRIPTION
            "Configuring Authentication Key Index per NTP server."
        ::= { ipeCfgNtpServerEntry 6 }
    
    -- 1.3.6.1.4.1.119.2.3.69.213.502.5.3.4.2.1.7
    ipeCfgNtpServerV6Address OBJECT-TYPE
        SYNTAX      Ipv6Address
        ACCESS      read-only
        STATUS      mandatory
        DESCRIPTION
            "IPv6 Address of NTP Server.
    
             When this object is configured, the NTP Client will run
             over IPv6 and the ipeCfgNtpServerAddress will be
             unconfigured (reset to 0.0.0.0).
    
             When configuring ipeCfgNtpServerAddress, the NTP Client
             will run over IPv4 and this object will be unconfigured
             (reset to ::).
    
             The following are not valid addresses:
               ::1/128 IPv6 Loopback
               FE80::/10 Link local
               FF00::/8 IPv6 Multicasts"
        ::= { ipeCfgNtpServerEntry 7 }
    
    -- 1.3.6.1.4.1.119.2.3.69.213.502.5.3.4.2.1.8
    ipeCfgNtpServerAddressType OBJECT-TYPE
        SYNTAX      INTEGER { invalid(0), ipv4(1), ipv6(2) }
        ACCESS      read-only
        STATUS      mandatory
        DESCRIPTION
            "Indicate IP address type of this server.
    
             ipv4 : server has IPv4 address.
             ipv6 : server has IPv6 address."
        ::= { ipeCfgNtpServerEntry 8 }
    
    -- 1.3.6.1.4.1.119.2.3.69.213.502.5.3.4.2.1.1001
    ipeCfgNtpServerNEAddressAddrType OBJECT-TYPE
        SYNTAX      InetAddressType
        ACCESS      not-accessible
        STATUS      mandatory
        DESCRIPTION
            "Represents the IP address type of NE address index.
             Only ipv4(1) and ipv6(2) are supported."
        ::= { ipeCfgNtpServerEntry 1001 }
    
    -- 1.3.6.1.4.1.119.2.3.69.213.502.5.3.4.3
    ipeCfgNtpAuthenticationKeyTable OBJECT-TYPE
        SYNTAX      SEQUENCE OF IpeCfgNtpAuthenticationKeyEntry
        ACCESS      not-accessible
        STATUS      mandatory
        DESCRIPTION
            "This table contains the NTP authentication keys."
        ::= { ipeCfgNtp 3 }
    
    -- 1.3.6.1.4.1.119.2.3.69.213.502.5.3.4.3.1
    ipeCfgNtpAuthenticationKeyEntry OBJECT-TYPE
        SYNTAX      IpeCfgNtpAuthenticationKeyEntry
        ACCESS      not-accessible
        STATUS      mandatory
        DESCRIPTION
            ""
        INDEX       { ipeCfgNtpAuthenticationNEAddressAddrType, ipeCfgNtpAuthenticationNEAddress, ipeCfgNtpAuthenticationKeyIndex }
        ::= { ipeCfgNtpAuthenticationKeyTable 1 }
    
    IpeCfgNtpAuthenticationKeyEntry ::= SEQUENCE {
        ipeCfgNtpAuthenticationKeyIndex             IpeNtpKeyAdminIndex,
        ipeCfgNtpAuthenticationNEAddress            InetAddress,
        ipeCfgNtpAuthenticationAlgorithm            INTEGER,
        ipeCfgNtpAuthenticationKey                  DisplayString,
        ipeCfgNtpAuthenticationKeyId                Gauge,
        ipeCfgNtpAuthenticationKeyTrusted           OffOnValue,
        ipeCfgNtpAuthKeyRowStatus                   RowStatus,
        ipeCfgNtpAuthenticationNEAddressAddrType    InetAddressType
    }
    
    -- 1.3.6.1.4.1.119.2.3.69.213.502.5.3.4.3.1.1
    ipeCfgNtpAuthenticationKeyIndex OBJECT-TYPE
        SYNTAX      IpeNtpKeyAdminIndex
        ACCESS      not-accessible
        STATUS      mandatory
        DESCRIPTION
            "Administrative index of this table.
             The value is different from ipeCfgNtpAuthenticationKeyId."
        ::= { ipeCfgNtpAuthenticationKeyEntry 1 }
    
    -- 1.3.6.1.4.1.119.2.3.69.213.502.5.3.4.3.1.2
    ipeCfgNtpAuthenticationNEAddress OBJECT-TYPE
        SYNTAX      InetAddress
        ACCESS      not-accessible
        STATUS      mandatory
        DESCRIPTION
            "reserved."
        ::= { ipeCfgNtpAuthenticationKeyEntry 2 }
    
    -- 1.3.6.1.4.1.119.2.3.69.213.502.5.3.4.3.1.3
    ipeCfgNtpAuthenticationAlgorithm OBJECT-TYPE
        SYNTAX      INTEGER { invalid(0), md5(1) }
        ACCESS      read-only
        STATUS      mandatory
        DESCRIPTION
            "configuring the NTP Authentication algorithm."
        ::= { ipeCfgNtpAuthenticationKeyEntry 3 }
    
    -- 1.3.6.1.4.1.119.2.3.69.213.502.5.3.4.3.1.4
    ipeCfgNtpAuthenticationKey OBJECT-TYPE
        SYNTAX      DisplayString (SIZE(8..128))
        ACCESS      read-only
        STATUS      mandatory
        DESCRIPTION
            "configuring the NTP Authentication key. This object can be
             operated in secure way."
        ::= { ipeCfgNtpAuthenticationKeyEntry 4 }
    
    -- 1.3.6.1.4.1.119.2.3.69.213.502.5.3.4.3.1.5
    ipeCfgNtpAuthenticationKeyId OBJECT-TYPE
        SYNTAX      Gauge (1..65535)
        ACCESS      read-only
        STATUS      mandatory
        DESCRIPTION
            "Configuring the NTP Authentication key Identifier. The key
             identifier is used for protocol operation."
        ::= { ipeCfgNtpAuthenticationKeyEntry 5 }
    
    -- 1.3.6.1.4.1.119.2.3.69.213.502.5.3.4.3.1.6
    ipeCfgNtpAuthenticationKeyTrusted OBJECT-TYPE
        SYNTAX      OffOnValue
        ACCESS      read-only
        STATUS      mandatory
        DESCRIPTION
            "Configuring the key is trusted or not. The trusted key is ready
             to use in NTP Packets."
        ::= { ipeCfgNtpAuthenticationKeyEntry 6 }
    
    -- 1.3.6.1.4.1.119.2.3.69.213.502.5.3.4.3.1.7
    ipeCfgNtpAuthKeyRowStatus OBJECT-TYPE
        SYNTAX      RowStatus
        ACCESS      read-only
        STATUS      mandatory
        DESCRIPTION
            "This object is used to create a new row or delete an existing
             row in this table."
        ::= { ipeCfgNtpAuthenticationKeyEntry 7 }
    
    -- 1.3.6.1.4.1.119.2.3.69.213.502.5.3.4.3.1.1001
    ipeCfgNtpAuthenticationNEAddressAddrType OBJECT-TYPE
        SYNTAX      InetAddressType
        ACCESS      not-accessible
        STATUS      mandatory
        DESCRIPTION
            "Represents the IP address type of NE address index.
             Only ipv4(1) and ipv6(2) are supported."
        ::= { ipeCfgNtpAuthenticationKeyEntry 1001 }
    
    -- 1.3.6.1.4.1.119.2.3.69.213.502.5.3.6
    ipeCfgSsh OBJECT IDENTIFIER
        ::= { ipeConfigurationGroup 6 }
    
    -- 1.3.6.1.4.1.119.2.3.69.213.502.5.3.6.1
    ipeCfgSshServerTable OBJECT-TYPE
        SYNTAX      SEQUENCE OF IpeCfgSshServerEntry
        ACCESS      not-accessible
        STATUS      mandatory
        DESCRIPTION
            "Table of SSH configuration information."
        ::= { ipeCfgSsh 1 }
    
    -- 1.3.6.1.4.1.119.2.3.69.213.502.5.3.6.1.1
    ipeCfgSshServerEntry OBJECT-TYPE
        SYNTAX      IpeCfgSshServerEntry
        ACCESS      not-accessible
        STATUS      mandatory
        DESCRIPTION
            "Entry of SSH configuration information."
        INDEX       { ipeCfgSshServerNEAddressAddrType, ipeCfgSshServerNEAddress, ipeCfgSshServerIndex }
        ::= { ipeCfgSshServerTable 1 }
    
    IpeCfgSshServerEntry ::= SEQUENCE {
        ipeCfgSshServerIndex                INTEGER,
        ipeCfgSshServerNEAddress            InetAddress,
        ipeCfgSshServerEnable               INTEGER,
        ipeCfgSshServerDH1024Bits           EnableDisableValue,
        ipeCfgSshServerNEAddressAddrType    InetAddressType
    }
    
    -- 1.3.6.1.4.1.119.2.3.69.213.502.5.3.6.1.1.1
    ipeCfgSshServerIndex OBJECT-TYPE
        SYNTAX      INTEGER (1)
        ACCESS      not-accessible
        STATUS      mandatory
        DESCRIPTION
            "Index of table."
        ::= { ipeCfgSshServerEntry 1 }
    
    -- 1.3.6.1.4.1.119.2.3.69.213.502.5.3.6.1.1.2
    ipeCfgSshServerNEAddress OBJECT-TYPE
        SYNTAX      InetAddress
        ACCESS      not-accessible
        STATUS      mandatory
        DESCRIPTION
            ""
        ::= { ipeCfgSshServerEntry 2 }
    
    -- 1.3.6.1.4.1.119.2.3.69.213.502.5.3.6.1.1.3
    ipeCfgSshServerEnable OBJECT-TYPE
        SYNTAX      INTEGER { invalid(0), disabled(1), enabled(2) }
        ACCESS      read-only
        STATUS      mandatory
        DESCRIPTION
            "SSH control enable."
        DEFVAL      { enabled }
        ::= { ipeCfgSshServerEntry 3 }
    
    -- 1.3.6.1.4.1.119.2.3.69.213.502.5.3.6.1.1.5
    ipeCfgSshServerDH1024Bits OBJECT-TYPE
        SYNTAX      EnableDisableValue
        ACCESS      read-only
        STATUS      mandatory
        DESCRIPTION
            "Indicates SSH Diffie-Hellman Modulus of 1024 Bit"
        ::= { ipeCfgSshServerEntry 5 }
    
    -- 1.3.6.1.4.1.119.2.3.69.213.502.5.3.6.1.1.1001
    ipeCfgSshServerNEAddressAddrType OBJECT-TYPE
        SYNTAX      InetAddressType
        ACCESS      not-accessible
        STATUS      mandatory
        DESCRIPTION
            "Represents the IP address type of NE address index.
             Only ipv4(1) and ipv6(2) are supported."
        ::= { ipeCfgSshServerEntry 1001 }
    
    -- 1.3.6.1.4.1.119.2.3.69.213.502.5.3.6.2
    ipeCfgSshClientTable OBJECT-TYPE
        SYNTAX      SEQUENCE OF IpeCfgSshClientEntry
        ACCESS      not-accessible
        STATUS      mandatory
        DESCRIPTION
            "Table of SSH configuration information."
        ::= { ipeCfgSsh 2 }
    
    -- 1.3.6.1.4.1.119.2.3.69.213.502.5.3.6.2.1
    ipeCfgSshClientEntry OBJECT-TYPE
        SYNTAX      IpeCfgSshClientEntry
        ACCESS      not-accessible
        STATUS      mandatory
        DESCRIPTION
            "Entry of SSH configuration information."
        INDEX       { ipeCfgSshClientNEAddressAddrType, ipeCfgSshClientNEAddress, ipeCfgSshClientIndex }
        ::= { ipeCfgSshClientTable 1 }
    
    IpeCfgSshClientEntry ::= SEQUENCE {
        ipeCfgSshClientIndex                INTEGER,
        ipeCfgSshClientNEAddress            InetAddress,
        ipeCfgSshClientEnable               INTEGER,
        ipeCfgSshClientNEAddressAddrType    InetAddressType
    }
    
    -- 1.3.6.1.4.1.119.2.3.69.213.502.5.3.6.2.1.1
    ipeCfgSshClientIndex OBJECT-TYPE
        SYNTAX      INTEGER (1)
        ACCESS      not-accessible
        STATUS      mandatory
        DESCRIPTION
            "Index of table."
        ::= { ipeCfgSshClientEntry 1 }
    
    -- 1.3.6.1.4.1.119.2.3.69.213.502.5.3.6.2.1.2
    ipeCfgSshClientNEAddress OBJECT-TYPE
        SYNTAX      InetAddress
        ACCESS      not-accessible
        STATUS      mandatory
        DESCRIPTION
            ""
        ::= { ipeCfgSshClientEntry 2 }
    
    -- 1.3.6.1.4.1.119.2.3.69.213.502.5.3.6.2.1.3
    ipeCfgSshClientEnable OBJECT-TYPE
        SYNTAX      INTEGER { invalid(0), disabled(1), enabled(2) }
        ACCESS      read-only
        STATUS      mandatory
        DESCRIPTION
            "SSH control enable."
        DEFVAL      { disabled }
        ::= { ipeCfgSshClientEntry 3 }
    
    -- 1.3.6.1.4.1.119.2.3.69.213.502.5.3.6.2.1.1001
    ipeCfgSshClientNEAddressAddrType OBJECT-TYPE
        SYNTAX      InetAddressType
        ACCESS      not-accessible
        STATUS      mandatory
        DESCRIPTION
            "Represents the IP address type of NE address index.
             Only ipv4(1) and ipv6(2) are supported."
        ::= { ipeCfgSshClientEntry 1001 }
    
    -- 1.3.6.1.4.1.119.2.3.69.213.502.5.3.7
    ipeCfgFtp OBJECT IDENTIFIER
        ::= { ipeConfigurationGroup 7 }
    
    -- 1.3.6.1.4.1.119.2.3.69.213.502.5.3.7.1
    ipeCfgFtpServerTable OBJECT-TYPE
        SYNTAX      SEQUENCE OF IpeCfgFtpServerEntry
        ACCESS      not-accessible
        STATUS      mandatory
        DESCRIPTION
            "Table of FTP server configuration information."
        ::= { ipeCfgFtp 1 }
    
    -- 1.3.6.1.4.1.119.2.3.69.213.502.5.3.7.1.1
    ipeCfgFtpServerEntry OBJECT-TYPE
        SYNTAX      IpeCfgFtpServerEntry
        ACCESS      not-accessible
        STATUS      mandatory
        DESCRIPTION
            "Entry of FTP server configuration information."
        INDEX       { ipeCfgFtpServerNEAddressAddrType, ipeCfgFtpServerNEAddress, ipeCfgFtpServerIndex }
        ::= { ipeCfgFtpServerTable 1 }
    
    IpeCfgFtpServerEntry ::= SEQUENCE {
        ipeCfgFtpServerIndex                INTEGER,
        ipeCfgFtpServerNEAddress            InetAddress,
        ipeCfgFtpServerEnable               INTEGER,
        ipeCfgFtpServerCommandTcpPort       INTEGER,
        ipeCfgFtpServerDataTcpPort          INTEGER,
        ipeCfgFtpServerMaxSession           INTEGER,
        ipeCfgFtpServerAutoDisable          INTEGER,
        ipeCfgFtpServerNEAddressAddrType    InetAddressType
    }
    
    -- 1.3.6.1.4.1.119.2.3.69.213.502.5.3.7.1.1.1
    ipeCfgFtpServerIndex OBJECT-TYPE
        SYNTAX      INTEGER (1)
        ACCESS      not-accessible
        STATUS      mandatory
        DESCRIPTION
            "Index of table."
        ::= { ipeCfgFtpServerEntry 1 }
    
    -- 1.3.6.1.4.1.119.2.3.69.213.502.5.3.7.1.1.2
    ipeCfgFtpServerNEAddress OBJECT-TYPE
        SYNTAX      InetAddress
        ACCESS      not-accessible
        STATUS      mandatory
        DESCRIPTION
            ""
        ::= { ipeCfgFtpServerEntry 2 }
    
    -- 1.3.6.1.4.1.119.2.3.69.213.502.5.3.7.1.1.3
    ipeCfgFtpServerEnable OBJECT-TYPE
        SYNTAX      INTEGER { invalid(0), serviceDisable(1),
                        serviceEnable(2), alwaysEnable(3) }
        ACCESS      read-only
        STATUS      mandatory
        DESCRIPTION
            "FTP control enable."
        ::= { ipeCfgFtpServerEntry 3 }
    
    -- 1.3.6.1.4.1.119.2.3.69.213.502.5.3.7.1.1.4
    ipeCfgFtpServerCommandTcpPort OBJECT-TYPE
        SYNTAX      INTEGER (1..65535)
        ACCESS      read-only
        STATUS      mandatory
        DESCRIPTION
            "Port number of FTP command."
        ::= { ipeCfgFtpServerEntry 4 }
    
    -- 1.3.6.1.4.1.119.2.3.69.213.502.5.3.7.1.1.5
    ipeCfgFtpServerDataTcpPort OBJECT-TYPE
        SYNTAX      INTEGER (1..65535)
        ACCESS      read-only
        STATUS      mandatory
        DESCRIPTION
            "Port number of FTP data transfer."
        ::= { ipeCfgFtpServerEntry 5 }
    
    -- 1.3.6.1.4.1.119.2.3.69.213.502.5.3.7.1.1.6
    ipeCfgFtpServerMaxSession OBJECT-TYPE
        SYNTAX      INTEGER (1..3)
        ACCESS      read-only
        STATUS      mandatory
        DESCRIPTION
            "Number of max connections."
        ::= { ipeCfgFtpServerEntry 6 }
    
    -- 1.3.6.1.4.1.119.2.3.69.213.502.5.3.7.1.1.7
    ipeCfgFtpServerAutoDisable OBJECT-TYPE
        SYNTAX      INTEGER { invalid(0), disabled(1), enabled(2) }
        ACCESS      read-only
        STATUS      mandatory
        DESCRIPTION
            "FTP automatic stop control enable."
        ::= { ipeCfgFtpServerEntry 7 }
    
    -- 1.3.6.1.4.1.119.2.3.69.213.502.5.3.7.1.1.1001
    ipeCfgFtpServerNEAddressAddrType OBJECT-TYPE
        SYNTAX      InetAddressType
        ACCESS      not-accessible
        STATUS      mandatory
        DESCRIPTION
            "Represents the IP address type of NE address index.
             Only ipv4(1) and ipv6(2) are supported."
        ::= { ipeCfgFtpServerEntry 1001 }
    
    -- 1.3.6.1.4.1.119.2.3.69.213.502.5.3.8
    ipeCfgSftp OBJECT IDENTIFIER
        ::= { ipeConfigurationGroup 8 }
    
    -- 1.3.6.1.4.1.119.2.3.69.213.502.5.3.8.1
    ipeCfgSftpServerTable OBJECT-TYPE
        SYNTAX      SEQUENCE OF IpeCfgSftpServerEntry
        ACCESS      not-accessible
        STATUS      mandatory
        DESCRIPTION
            "Table of SFTP server configuration information."
        ::= { ipeCfgSftp 1 }
    
    -- 1.3.6.1.4.1.119.2.3.69.213.502.5.3.8.1.1
    ipeCfgSftpServerEntry OBJECT-TYPE
        SYNTAX      IpeCfgSftpServerEntry
        ACCESS      not-accessible
        STATUS      mandatory
        DESCRIPTION
            "Entry of SFTP server configuration information."
        INDEX       { ipeCfgSftpServerNEAddressAddrType, ipeCfgSftpServerNEAddress, ipeCfgSftpServerIndex }
        ::= { ipeCfgSftpServerTable 1 }
    
    IpeCfgSftpServerEntry ::= SEQUENCE {
        ipeCfgSftpServerIndex               INTEGER,
        ipeCfgSftpServerNEAddress           InetAddress,
        ipeCfgSftpServerEnable              INTEGER,
        ipeCfgSftpServerAutoDisable         INTEGER,
        ipeCfgSftpServerNEAddressAddrType   InetAddressType
    }
    
    -- 1.3.6.1.4.1.119.2.3.69.213.502.5.3.8.1.1.1
    ipeCfgSftpServerIndex OBJECT-TYPE
        SYNTAX      INTEGER (1)
        ACCESS      not-accessible
        STATUS      mandatory
        DESCRIPTION
            "Index of table."
        ::= { ipeCfgSftpServerEntry 1 }
    
    -- 1.3.6.1.4.1.119.2.3.69.213.502.5.3.8.1.1.2
    ipeCfgSftpServerNEAddress OBJECT-TYPE
        SYNTAX      InetAddress
        ACCESS      not-accessible
        STATUS      mandatory
        DESCRIPTION
            ""
        ::= { ipeCfgSftpServerEntry 2 }
    
    -- 1.3.6.1.4.1.119.2.3.69.213.502.5.3.8.1.1.3
    ipeCfgSftpServerEnable OBJECT-TYPE
        SYNTAX      INTEGER { invalid(0), serviceDisable(1),
                        serviceEnable(2), alwaysEnable(3) }
        ACCESS      read-only
        STATUS      mandatory
        DESCRIPTION
            "SFTP control enable."
        ::= { ipeCfgSftpServerEntry 3 }
    
    -- 1.3.6.1.4.1.119.2.3.69.213.502.5.3.8.1.1.4
    ipeCfgSftpServerAutoDisable OBJECT-TYPE
        SYNTAX      INTEGER { invalid(0), disabled(1), enabled(2) }
        ACCESS      read-only
        STATUS      mandatory
        DESCRIPTION
            "SFTP automatic stop control enable."
        ::= { ipeCfgSftpServerEntry 4 }
    
    -- 1.3.6.1.4.1.119.2.3.69.213.502.5.3.8.1.1.1001
    ipeCfgSftpServerNEAddressAddrType OBJECT-TYPE
        SYNTAX      InetAddressType
        ACCESS      not-accessible
        STATUS      mandatory
        DESCRIPTION
            "Represents the IP address type of NE address index.
             Only ipv4(1) and ipv6(2) are supported."
        ::= { ipeCfgSftpServerEntry 1001 }
    
    -- 1.3.6.1.4.1.119.2.3.69.213.502.5.3.9
    ipeCfgHttp OBJECT IDENTIFIER
        ::= { ipeConfigurationGroup 9 }
    
    -- 1.3.6.1.4.1.119.2.3.69.213.502.5.3.9.1
    ipeCfgHttpServerTable OBJECT-TYPE
        SYNTAX      SEQUENCE OF IpeCfgHttpServerEntry
        ACCESS      not-accessible
        STATUS      mandatory
        DESCRIPTION
            "Table of HTTP configuration information."
        ::= { ipeCfgHttp 1 }
    
    -- 1.3.6.1.4.1.119.2.3.69.213.502.5.3.9.1.1
    ipeCfgHttpServerEntry OBJECT-TYPE
        SYNTAX      IpeCfgHttpServerEntry
        ACCESS      not-accessible
        STATUS      mandatory
        DESCRIPTION
            "Entry of HTTP configuration information."
        INDEX       { ipeCfgHttpServerNEAddressAddrType, ipeCfgHttpServerNEAddress, ipeCfgHttpServerIndex }
        ::= { ipeCfgHttpServerTable 1 }
    
    IpeCfgHttpServerEntry ::= SEQUENCE {
        ipeCfgHttpServerIndex               INTEGER,
        ipeCfgHttpServerNEAddress           InetAddress,
        ipeCfgHttpServerEnable              INTEGER,
        ipeCfgHttpServerTcpPort             INTEGER,
        ipeCfgHttpServerNEAddressAddrType   InetAddressType
    }
    
    -- 1.3.6.1.4.1.119.2.3.69.213.502.5.3.9.1.1.1
    ipeCfgHttpServerIndex OBJECT-TYPE
        SYNTAX      INTEGER (1)
        ACCESS      not-accessible
        STATUS      mandatory
        DESCRIPTION
            "Index of table."
        ::= { ipeCfgHttpServerEntry 1 }
    
    -- 1.3.6.1.4.1.119.2.3.69.213.502.5.3.9.1.1.2
    ipeCfgHttpServerNEAddress OBJECT-TYPE
        SYNTAX      InetAddress
        ACCESS      not-accessible
        STATUS      mandatory
        DESCRIPTION
            ""
        ::= { ipeCfgHttpServerEntry 2 }
    
    -- 1.3.6.1.4.1.119.2.3.69.213.502.5.3.9.1.1.3
    ipeCfgHttpServerEnable OBJECT-TYPE
        SYNTAX      INTEGER { invalid(0), disabled(1), enabled(2) }
        ACCESS      read-only
        STATUS      mandatory
        DESCRIPTION
            "HTTP control enable."
        ::= { ipeCfgHttpServerEntry 3 }
    
    -- 1.3.6.1.4.1.119.2.3.69.213.502.5.3.9.1.1.4
    ipeCfgHttpServerTcpPort OBJECT-TYPE
        SYNTAX      INTEGER (1..65535)
        ACCESS      read-only
        STATUS      mandatory
        DESCRIPTION
            "Port number of HTTP."
        ::= { ipeCfgHttpServerEntry 4 }
    
    -- 1.3.6.1.4.1.119.2.3.69.213.502.5.3.9.1.1.1001
    ipeCfgHttpServerNEAddressAddrType OBJECT-TYPE
        SYNTAX      InetAddressType
        ACCESS      not-accessible
        STATUS      mandatory
        DESCRIPTION
            "Represents the IP address type of NE address index.
             Only ipv4(1) and ipv6(2) are supported."
        ::= { ipeCfgHttpServerEntry 1001 }
    
    -- 1.3.6.1.4.1.119.2.3.69.213.502.5.3.10
    ipeCfgHttps OBJECT IDENTIFIER
        ::= { ipeConfigurationGroup 10 }
    
    -- 1.3.6.1.4.1.119.2.3.69.213.502.5.3.10.1
    ipeCfgHttpsServerTable OBJECT-TYPE
        SYNTAX      SEQUENCE OF IpeCfgHttpsServerEntry
        ACCESS      not-accessible
        STATUS      mandatory
        DESCRIPTION
            "Table of HTTPS configuration information."
        ::= { ipeCfgHttps 1 }
    
    -- 1.3.6.1.4.1.119.2.3.69.213.502.5.3.10.1.1
    ipeCfgHttpsServerEntry OBJECT-TYPE
        SYNTAX      IpeCfgHttpsServerEntry
        ACCESS      not-accessible
        STATUS      mandatory
        DESCRIPTION
            "Entry of HTTPS configuration information."
        INDEX       { ipeCfgHttpsServerNEAddressAddrType, ipeCfgHttpsServerNEAddress, ipeCfgHttpsServerIndex }
        ::= { ipeCfgHttpsServerTable 1 }
    
    IpeCfgHttpsServerEntry ::= SEQUENCE {
        ipeCfgHttpsServerIndex              INTEGER,
        ipeCfgHttpsServerNEAddress          InetAddress,
        ipeCfgHttpsServerEnable             INTEGER,
        ipeCfgHttpsServerTcpPort            INTEGER,
        ipeCfgHttpsServerNEAddressAddrType  InetAddressType
    }
    
    -- 1.3.6.1.4.1.119.2.3.69.213.502.5.3.10.1.1.1
    ipeCfgHttpsServerIndex OBJECT-TYPE
        SYNTAX      INTEGER (1)
        ACCESS      not-accessible
        STATUS      mandatory
        DESCRIPTION
            "Index of table."
        ::= { ipeCfgHttpsServerEntry 1 }
    
    -- 1.3.6.1.4.1.119.2.3.69.213.502.5.3.10.1.1.2
    ipeCfgHttpsServerNEAddress OBJECT-TYPE
        SYNTAX      InetAddress
        ACCESS      not-accessible
        STATUS      mandatory
        DESCRIPTION
            ""
        ::= { ipeCfgHttpsServerEntry 2 }
    
    -- 1.3.6.1.4.1.119.2.3.69.213.502.5.3.10.1.1.3
    ipeCfgHttpsServerEnable OBJECT-TYPE
        SYNTAX      INTEGER { invalid(0), disabled(1), enabled(2) }
        ACCESS      read-only
        STATUS      mandatory
        DESCRIPTION
            "HTTPS control enable."
        ::= { ipeCfgHttpsServerEntry 3 }
    
    -- 1.3.6.1.4.1.119.2.3.69.213.502.5.3.10.1.1.4
    ipeCfgHttpsServerTcpPort OBJECT-TYPE
        SYNTAX      INTEGER (1..65535)
        ACCESS      read-only
        STATUS      mandatory
        DESCRIPTION
            "TCP port number of HTTPS."
        ::= { ipeCfgHttpsServerEntry 4 }
    
    -- 1.3.6.1.4.1.119.2.3.69.213.502.5.3.10.1.1.1001
    ipeCfgHttpsServerNEAddressAddrType OBJECT-TYPE
        SYNTAX      InetAddressType
        ACCESS      not-accessible
        STATUS      mandatory
        DESCRIPTION
            "Represents the IP address type of NE address index.
             Only ipv4(1) and ipv6(2) are supported."
        ::= { ipeCfgHttpsServerEntry 1001 }
    
    -- 1.3.6.1.4.1.119.2.3.69.213.502.5.3.10.2
    ipeCfgHttpsRsaTable OBJECT-TYPE
        SYNTAX      SEQUENCE OF IpeCfgHttpsRsaEntry
        ACCESS      not-accessible
        STATUS      mandatory
        DESCRIPTION
            "Table of HTTPS RSA configuration information."
        ::= { ipeCfgHttps 2 }
    
    -- 1.3.6.1.4.1.119.2.3.69.213.502.5.3.10.2.1
    ipeCfgHttpsRsaEntry OBJECT-TYPE
        SYNTAX      IpeCfgHttpsRsaEntry
        ACCESS      not-accessible
        STATUS      mandatory
        DESCRIPTION
            "Entry of HTTPS RSA configuration information."
        INDEX       { ipeCfgHttpsRsaNEAddressAddrType, ipeCfgHttpsRsaNEAddress, ipeCfgHttpsRsaIndex }
        ::= { ipeCfgHttpsRsaTable 1 }
    
    IpeCfgHttpsRsaEntry ::= SEQUENCE {
        ipeCfgHttpsRsaIndex                 INTEGER,
        ipeCfgHttpsRsaNEAddress             InetAddress,
        ipeCfgHttpsRsaPassPhrase            DisplayString,
        ipeCfgHttpsRsaEncryptAlgorithm      INTEGER,
        ipeCfgHttpsRsaNEAddressAddrType     InetAddressType
    }
    
    -- 1.3.6.1.4.1.119.2.3.69.213.502.5.3.10.2.1.1
    ipeCfgHttpsRsaIndex OBJECT-TYPE
        SYNTAX      INTEGER (1)
        ACCESS      not-accessible
        STATUS      mandatory
        DESCRIPTION
            "Index of table."
        ::= { ipeCfgHttpsRsaEntry 1 }
    
    -- 1.3.6.1.4.1.119.2.3.69.213.502.5.3.10.2.1.2
    ipeCfgHttpsRsaNEAddress OBJECT-TYPE
        SYNTAX      InetAddress
        ACCESS      not-accessible
        STATUS      mandatory
        DESCRIPTION
            ""
        ::= { ipeCfgHttpsRsaEntry 2 }
    
    -- 1.3.6.1.4.1.119.2.3.69.213.502.5.3.10.2.1.3
    ipeCfgHttpsRsaPassPhrase OBJECT-TYPE
        SYNTAX      DisplayString (SIZE(8..128))
        ACCESS      read-only
        STATUS      mandatory
        DESCRIPTION
            "Pass-phrase for the RSA private key. The valid length of user
             input value must be 8 to 64 chars.  After the encryption, the
             contents will be changed, and the length might be longer than 64
             chars."
        ::= { ipeCfgHttpsRsaEntry 3 }
    
    -- 1.3.6.1.4.1.119.2.3.69.213.502.5.3.10.2.1.4
    ipeCfgHttpsRsaEncryptAlgorithm OBJECT-TYPE
        SYNTAX      INTEGER { invalid(0), aes128(1), aes192(2), aes256(3),
                        camellia128(4), camellia192(5), camellia256(6),
                        des3(7) }
        ACCESS      read-only
        STATUS      mandatory
        DESCRIPTION
            "Encryption algorithm for the RSA private key."
        ::= { ipeCfgHttpsRsaEntry 4 }
    
    -- 1.3.6.1.4.1.119.2.3.69.213.502.5.3.10.2.1.1001
    ipeCfgHttpsRsaNEAddressAddrType OBJECT-TYPE
        SYNTAX      InetAddressType
        ACCESS      not-accessible
        STATUS      mandatory
        DESCRIPTION
            "Represents the IP address type of NE address index.
             Only ipv4(1) and ipv6(2) are supported."
        ::= { ipeCfgHttpsRsaEntry 1001 }
    
    -- 1.3.6.1.4.1.119.2.3.69.213.502.5.3.10.3
    ipeCfgHttpsCsrTable OBJECT-TYPE
        SYNTAX      SEQUENCE OF IpeCfgHttpsCsrEntry
        ACCESS      not-accessible
        STATUS      mandatory
        DESCRIPTION
            "Table of HTTPS CSR configuration information."
        ::= { ipeCfgHttps 3 }
    
    -- 1.3.6.1.4.1.119.2.3.69.213.502.5.3.10.3.1
    ipeCfgHttpsCsrEntry OBJECT-TYPE
        SYNTAX      IpeCfgHttpsCsrEntry
        ACCESS      not-accessible
        STATUS      mandatory
        DESCRIPTION
            "Entry of HTTPS CSR configuration information."
        INDEX       { ipeCfgHttpsCsrNEAddressAddrType, ipeCfgHttpsCsrNEAddress, ipeCfgHttpsCsrIndex }
        ::= { ipeCfgHttpsCsrTable 1 }
    
    IpeCfgHttpsCsrEntry ::= SEQUENCE {
        ipeCfgHttpsCsrIndex                     INTEGER,
        ipeCfgHttpsCsrNEAddress                 InetAddress,
        ipeCfgHttpsCsrRsaPassPhrase             DisplayString,
        ipeCfgHttpsCsrMessageDigestAlgorithm    INTEGER,
        ipeCfgHttpsCsrCountry                   DisplayString,
        ipeCfgHttpsCsrState                     DisplayString,
        ipeCfgHttpsCsrLocality                  DisplayString,
        ipeCfgHttpsCsrOrganization              DisplayString,
        ipeCfgHttpsCsrOrganizationalUnit        DisplayString,
        ipeCfgHttpsCsrCommonName                DisplayString,
        ipeCfgHttpsCsrNEAddressAddrType         InetAddressType
    }
    
    -- 1.3.6.1.4.1.119.2.3.69.213.502.5.3.10.3.1.1
    ipeCfgHttpsCsrIndex OBJECT-TYPE
        SYNTAX      INTEGER (1)
        ACCESS      not-accessible
        STATUS      mandatory
        DESCRIPTION
            "Index of table."
        ::= { ipeCfgHttpsCsrEntry 1 }
    
    -- 1.3.6.1.4.1.119.2.3.69.213.502.5.3.10.3.1.2
    ipeCfgHttpsCsrNEAddress OBJECT-TYPE
        SYNTAX      InetAddress
        ACCESS      not-accessible
        STATUS      mandatory
        DESCRIPTION
            ""
        ::= { ipeCfgHttpsCsrEntry 2 }
    
    -- 1.3.6.1.4.1.119.2.3.69.213.502.5.3.10.3.1.3
    ipeCfgHttpsCsrRsaPassPhrase OBJECT-TYPE
        SYNTAX      DisplayString (SIZE(8..128))
        ACCESS      read-only
        STATUS      mandatory
        DESCRIPTION
            "Pass-phrase for the RSA private key. This is same as
             ipeCfgHttpsRsaPassPhrase."
        ::= { ipeCfgHttpsCsrEntry 3 }
    
    -- 1.3.6.1.4.1.119.2.3.69.213.502.5.3.10.3.1.4
    ipeCfgHttpsCsrMessageDigestAlgorithm OBJECT-TYPE
        SYNTAX      INTEGER { invalid(0), sha224(1), sha256(2), sha384(3),
                        sha512(4) }
        ACCESS      read-only
        STATUS      mandatory
        DESCRIPTION
            "Message Digest algorithm for the CSR."
        ::= { ipeCfgHttpsCsrEntry 4 }
    
    -- 1.3.6.1.4.1.119.2.3.69.213.502.5.3.10.3.1.5
    ipeCfgHttpsCsrCountry OBJECT-TYPE
        SYNTAX      DisplayString (SIZE(2))
        ACCESS      read-only
        STATUS      mandatory
        DESCRIPTION
            "HTTPS CSR country name. 2 letter code. eg, US."
        ::= { ipeCfgHttpsCsrEntry 5 }
    
    -- 1.3.6.1.4.1.119.2.3.69.213.502.5.3.10.3.1.6
    ipeCfgHttpsCsrState OBJECT-TYPE
        SYNTAX      DisplayString (SIZE(2..64))
        ACCESS      read-only
        STATUS      mandatory
        DESCRIPTION
            "HTTPS CSR state or province name. eg, California (full name)."
        ::= { ipeCfgHttpsCsrEntry 6 }
    
    -- 1.3.6.1.4.1.119.2.3.69.213.502.5.3.10.3.1.7
    ipeCfgHttpsCsrLocality OBJECT-TYPE
        SYNTAX      DisplayString (SIZE(2..64))
        ACCESS      read-only
        STATUS      mandatory
        DESCRIPTION
            "HTTPS CSR locality name. eg, Saint Louis (city)."
        ::= { ipeCfgHttpsCsrEntry 7 }
    
    -- 1.3.6.1.4.1.119.2.3.69.213.502.5.3.10.3.1.8
    ipeCfgHttpsCsrOrganization OBJECT-TYPE
        SYNTAX      DisplayString (SIZE(2..64))
        ACCESS      read-only
        STATUS      mandatory
        DESCRIPTION
            "HTTPS CSR organization. eg, NEC Corporation."
        ::= { ipeCfgHttpsCsrEntry 8 }
    
    -- 1.3.6.1.4.1.119.2.3.69.213.502.5.3.10.3.1.9
    ipeCfgHttpsCsrOrganizationalUnit OBJECT-TYPE
        SYNTAX      DisplayString (SIZE(2..64))
        ACCESS      read-only
        STATUS      mandatory
        DESCRIPTION
            "HTTPS CSR organizational unit. eg, SSL Department (section)."
        ::= { ipeCfgHttpsCsrEntry 9 }
    
    -- 1.3.6.1.4.1.119.2.3.69.213.502.5.3.10.3.1.10
    ipeCfgHttpsCsrCommonName OBJECT-TYPE
        SYNTAX      DisplayString (SIZE(2..64))
        ACCESS      read-only
        STATUS      mandatory
        DESCRIPTION
            "HTTPS CSR common name. eg, apache.netsure.net (your name or your
             server's hostname)."
        ::= { ipeCfgHttpsCsrEntry 10 }
    
    -- 1.3.6.1.4.1.119.2.3.69.213.502.5.3.10.3.1.1001
    ipeCfgHttpsCsrNEAddressAddrType OBJECT-TYPE
        SYNTAX      InetAddressType
        ACCESS      not-accessible
        STATUS      mandatory
        DESCRIPTION
            "Represents the IP address type of NE address index.
             Only ipv4(1) and ipv6(2) are supported."
        ::= { ipeCfgHttpsCsrEntry 1001 }
    
    -- 1.3.6.1.4.1.119.2.3.69.213.502.5.3.11
    ipeCfgSnmp OBJECT IDENTIFIER
        ::= { ipeConfigurationGroup 11 }
    
    -- 1.3.6.1.4.1.119.2.3.69.213.502.5.3.11.1
    ipeCfgSnmpServerTable OBJECT-TYPE
        SYNTAX      SEQUENCE OF IpeCfgSnmpServerEntry
        ACCESS      not-accessible
        STATUS      mandatory
        DESCRIPTION
            "A table of SNMP configuration information."
        ::= { ipeCfgSnmp 1 }
    
    -- 1.3.6.1.4.1.119.2.3.69.213.502.5.3.11.1.1
    ipeCfgSnmpServerEntry OBJECT-TYPE
        SYNTAX      IpeCfgSnmpServerEntry
        ACCESS      not-accessible
        STATUS      mandatory
        DESCRIPTION
            "A set of SNMP configuration information."
        INDEX       { ipeCfgSnmpServerNEAddressAddrType, ipeCfgSnmpServerNEAddress, ipeCfgSnmpServerIndex }
        ::= { ipeCfgSnmpServerTable 1 }
    
    IpeCfgSnmpServerEntry ::= SEQUENCE {
        ipeCfgSnmpServerIndex               INTEGER,
        ipeCfgSnmpServerNEAddress           InetAddress,
        ipeCfgSnmpV1V2cEnable               INTEGER,
        ipeCfgSnmpV3Enable                  INTEGER,
        ipeCfgSnmpServerPort                INTEGER,
        ipeCfgSnmpServerToBigError          INTEGER,
        ipeCfgSnmpV1AccessMode              INTEGER,
        ipeCfgSnmpServerNEAddressAddrType   InetAddressType
    }
    
    -- 1.3.6.1.4.1.119.2.3.69.213.502.5.3.11.1.1.1
    ipeCfgSnmpServerIndex OBJECT-TYPE
        SYNTAX      INTEGER (1)
        ACCESS      not-accessible
        STATUS      mandatory
        DESCRIPTION
            "Index of this ipeCfgSnmpServerEntry.
             It's a fiexed value(= 1)."
        ::= { ipeCfgSnmpServerEntry 1 }
    
    -- 1.3.6.1.4.1.119.2.3.69.213.502.5.3.11.1.1.2
    ipeCfgSnmpServerNEAddress OBJECT-TYPE
        SYNTAX      InetAddress
        ACCESS      not-accessible
        STATUS      mandatory
        DESCRIPTION
            ""
        ::= { ipeCfgSnmpServerEntry 2 }
    
    -- 1.3.6.1.4.1.119.2.3.69.213.502.5.3.11.1.1.3
    ipeCfgSnmpV1V2cEnable OBJECT-TYPE
        SYNTAX      INTEGER { invalid(0), disabled(1), enabled(2) }
        ACCESS      read-only
        STATUS      mandatory
        DESCRIPTION
            "Indicates the SNMP entity is permitted to receive & process
             SNMPv1/v2c PDU or is not permitted to do.
    
             Even if it is disabled, SNMPv1/v2c Traps is sent."
        ::= { ipeCfgSnmpServerEntry 3 }
    
    -- 1.3.6.1.4.1.119.2.3.69.213.502.5.3.11.1.1.4
    ipeCfgSnmpV3Enable OBJECT-TYPE
        SYNTAX      INTEGER { invalid(0), disabled(1), enabled(2) }
        ACCESS      read-only
        STATUS      mandatory
        DESCRIPTION
            "Indicates the SNMP entity is permitted to receive & process
             SNMPv3 PDU or is not permitted to do.
    
             Even if it is disabled, SNMPv3 Traps is sent."
        ::= { ipeCfgSnmpServerEntry 4 }
    
    -- 1.3.6.1.4.1.119.2.3.69.213.502.5.3.11.1.1.5
    ipeCfgSnmpServerPort OBJECT-TYPE
        SYNTAX      INTEGER (1..65535)
        ACCESS      read-only
        STATUS      mandatory
        DESCRIPTION
            "A UDP port number to receive all SNMP Request-PDU.
             The reboot of the system is necessary to reflect setting."
        ::= { ipeCfgSnmpServerEntry 5 }
    
    -- 1.3.6.1.4.1.119.2.3.69.213.502.5.3.11.1.1.6
    ipeCfgSnmpServerToBigError OBJECT-TYPE
        SYNTAX      INTEGER
        ACCESS      read-only
        STATUS      obsolete
        DESCRIPTION
            "Indicates the PDU size of SNMP Too Big Error Response."
        ::= { ipeCfgSnmpServerEntry 6 }
    
    -- 1.3.6.1.4.1.119.2.3.69.213.502.5.3.11.1.1.7
    ipeCfgSnmpV1AccessMode OBJECT-TYPE
        SYNTAX      INTEGER { invalid(0), standardMode(1),
                        proprietaryMode(2) }
        ACCESS      read-only
        STATUS      mandatory
        DESCRIPTION
            "Indicates SNMPv1 Access Mode."
        ::= { ipeCfgSnmpServerEntry 7 }
    
    -- 1.3.6.1.4.1.119.2.3.69.213.502.5.3.11.1.1.1001
    ipeCfgSnmpServerNEAddressAddrType OBJECT-TYPE
        SYNTAX      InetAddressType
        ACCESS      not-accessible
        STATUS      mandatory
        DESCRIPTION
            "Represents the IP address type of NE address index.
             Only ipv4(1) and ipv6(2) are supported."
        ::= { ipeCfgSnmpServerEntry 1001 }
    
    -- 1.3.6.1.4.1.119.2.3.69.213.502.5.3.11.2
    ipeCfgSnmpCommunityTable OBJECT-TYPE
        SYNTAX      SEQUENCE OF IpeCfgSnmpCommunityEntry
        ACCESS      not-accessible
        STATUS      mandatory
        DESCRIPTION
            "A table of SNMP community information."
        ::= { ipeCfgSnmp 2 }
    
    -- 1.3.6.1.4.1.119.2.3.69.213.502.5.3.11.2.1
    ipeCfgSnmpCommunityEntry OBJECT-TYPE
        SYNTAX      IpeCfgSnmpCommunityEntry
        ACCESS      not-accessible
        STATUS      mandatory
        DESCRIPTION
            "A set of SNMP community information."
        INDEX       { ipeCfgSnmpCommunityNEAddressAddrType, ipeCfgSnmpCommunityNEAddress, ipeCfgSnmpCommunityIndex }
        ::= { ipeCfgSnmpCommunityTable 1 }
    
    IpeCfgSnmpCommunityEntry ::= SEQUENCE {
        ipeCfgSnmpCommunityIndex                    INTEGER,
        ipeCfgSnmpCommunityNEAddress                InetAddress,
        ipeCfgSnmpCommunityName                     DisplayString,
        ipeCfgSnmpCommunityAccessLevel              INTEGER,
        ipeCfgSnmpCommunityAccessAddress            IpAddress,
        ipeCfgSnmpCommunityAccessPrefixLength       INTEGER,
        ipeCfgSnmpCommunityRowStatus                RowStatus,
        ipeCfgSnmpCommunityAccessAddress2           IpAddress,
        ipeCfgSnmpCommunityAccessPrefixLength2      INTEGER,
        ipeCfgSnmpCommunityAccessAddress3           IpAddress,
        ipeCfgSnmpCommunityAccessPrefixLength3      INTEGER,
        ipeCfgSnmpCommunityAccessUsage              UsedNotusedValue,
        ipeCfgSnmpCommunityAccessUsage2             UsedNotusedValue,
        ipeCfgSnmpCommunityAccessUsage3             UsedNotusedValue,
        ipeCfgSnmpCommunityAccessV6Address          Ipv6Address,
        ipeCfgSnmpCommunityAccessV6PrefixLength     INTEGER,
        ipeCfgSnmpCommunityAccessV6Address2         Ipv6Address,
        ipeCfgSnmpCommunityAccessV6PrefixLength2    INTEGER,
        ipeCfgSnmpCommunityAccessV6Address3         Ipv6Address,
        ipeCfgSnmpCommunityAccessV6PrefixLength3    INTEGER,
        ipeCfgSnmpCommunityAccessAddressType        INTEGER,
        ipeCfgSnmpCommunityAccessV6Usage            UsedNotusedValue,
        ipeCfgSnmpCommunityAccessV6Usage2           UsedNotusedValue,
        ipeCfgSnmpCommunityAccessV6Usage3           UsedNotusedValue,
        ipeCfgSnmpCommunityNEAddressAddrType        InetAddressType
    }
    
    -- 1.3.6.1.4.1.119.2.3.69.213.502.5.3.11.2.1.1
    ipeCfgSnmpCommunityIndex OBJECT-TYPE
        SYNTAX      INTEGER (1..10)
        ACCESS      not-accessible
        STATUS      mandatory
        DESCRIPTION
            "Index of this ipeCfgSnmpCommunityEntry.
             You have to choose a value  from 1 to 10."
        ::= { ipeCfgSnmpCommunityEntry 1 }
    
    -- 1.3.6.1.4.1.119.2.3.69.213.502.5.3.11.2.1.2
    ipeCfgSnmpCommunityNEAddress OBJECT-TYPE
        SYNTAX      InetAddress
        ACCESS      not-accessible
        STATUS      mandatory
        DESCRIPTION
            ""
        ::= { ipeCfgSnmpCommunityEntry 2 }
    
    -- 1.3.6.1.4.1.119.2.3.69.213.502.5.3.11.2.1.3
    ipeCfgSnmpCommunityName OBJECT-TYPE
        SYNTAX      DisplayString (SIZE(1..31))
        ACCESS      read-only
        STATUS      mandatory
        DESCRIPTION
            "This entity's community name.
    
             Please use ASCII code.
    
             The characters which can be used are '-', '_','0'-'9', 'a'-'z'
             and 'A'-'Z'."
        ::= { ipeCfgSnmpCommunityEntry 3 }
    
    -- 1.3.6.1.4.1.119.2.3.69.213.502.5.3.11.2.1.4
    ipeCfgSnmpCommunityAccessLevel OBJECT-TYPE
        SYNTAX      INTEGER { invalid(0), operatorLevel(1), configLevel(2),
                        adminLevel(3), debugLevel(4) }
        ACCESS      read-only
        STATUS      mandatory
        DESCRIPTION
            "A access level of a connection using this entry's community
             name."
        ::= { ipeCfgSnmpCommunityEntry 4 }
    
    -- 1.3.6.1.4.1.119.2.3.69.213.502.5.3.11.2.1.5
    ipeCfgSnmpCommunityAccessAddress OBJECT-TYPE
        SYNTAX      IpAddress
        ACCESS      read-only
        STATUS      mandatory
        DESCRIPTION
            "An address which is permitted to use this entry's community
             name.
             When masking in ipeCfgSnmpCommunityAccessPrefixLength, the host
             address part has to be a zero, if any.
    
             Also the following address can't be used.
             127.0.0.0/8 Loopback
             224.0.0.0/4 Multicasts (former Class D)
             240.0.0.0/4 Reserved (former Class E)"
        ::= { ipeCfgSnmpCommunityEntry 5 }
    
    -- 1.3.6.1.4.1.119.2.3.69.213.502.5.3.11.2.1.6
    ipeCfgSnmpCommunityAccessPrefixLength OBJECT-TYPE
        SYNTAX      INTEGER (0..32)
        ACCESS      read-only
        STATUS      mandatory
        DESCRIPTION
            "A prefix length of ipeCfgSnmpCommunityAccessAddress."
        ::= { ipeCfgSnmpCommunityEntry 6 }
    
    -- 1.3.6.1.4.1.119.2.3.69.213.502.5.3.11.2.1.7
    ipeCfgSnmpCommunityRowStatus OBJECT-TYPE
        SYNTAX      RowStatus { active(1), createAndGo(4), destroy(6) }
        ACCESS      read-only
        STATUS      mandatory
        DESCRIPTION
            "This RowStatus has a status only  active(1).
             You can SET only createAndGo(4) or Destroy(6).
    
             1) how to create
             To create a new row, you must SET objects indicated below.
    
             ipeCfgSnmpCommunityName
             ipeCfgSnmpCommunityAccessLevel
             ipeCfgSnmpCommunityAccessAddress
             ipeCfgSnmpCommunityAccessPrefixLength
             ipeCfgSnmpCommunityAccessAddress2 *
             ipeCfgSnmpCommunityAccessPrefixLength2 *
             ipeCfgSnmpCommunityAccessAddress3 *
             ipeCfgSnmpCommunityAccessPrefixLength3 *
             ipeCfgSnmpCommunityAccessUsage *
             ipeCfgSnmpCommunityAccessUsage2 *
             ipeCfgSnmpCommunityAccessUsage3 *
             ipeCfgSnmpCommunityAccessV6Address
             ipeCfgSnmpCommunityAccessV6PrefixLength
             ipeCfgSnmpCommunityAccessV6Address2 *
             ipeCfgSnmpCommunityAccessV6PrefixLength2 *
             ipeCfgSnmpCommunityAccessV6Address3 *
             ipeCfgSnmpCommunityAccessV6PrefixLength3 *
             ipeCfgSnmpCommunityAccessAddressType *
             ipeCfgSnmpCommunityAccessV6Usage *
             ipeCfgSnmpCommunityAccessV6Usage2 *
             ipeCfgSnmpCommunityAccessV6Usage3 *
             ipeCfgSnmpCommunityRowStatus <- createAndGo(4)
    
             * NOT for EX CPRI
    
             Either ipeCfgSnmpCommunityAccessAddress/Address2/Address3 or
             ipeCfgSnmpCommunityAccessV6Address/Address2/Address3 can be
             configured depending on ipeCfgSnmpCommunityAccessAddressType.
    
             ipeCfgSnmpCommunityIndex is an index of this entry.
    
             2) how to destroy
             To destroy a exist row, you must SET a destory(6) to
             ipeCfgSnmpCommunityRowStatus.
    
             3) how to modify
             It is not possible.
             Please destroy a exist row, and create a new row.
             < Attention >
             You have to restart equipment to apply this entry(creating,
             deleting) to actual movement."
        ::= { ipeCfgSnmpCommunityEntry 7 }
    
    -- 1.3.6.1.4.1.119.2.3.69.213.502.5.3.11.2.1.8
    ipeCfgSnmpCommunityAccessAddress2 OBJECT-TYPE
        SYNTAX      IpAddress
        ACCESS      read-only
        STATUS      mandatory
        DESCRIPTION
            "An address which is permitted to use this entry's community
             name.
             When masking in ipeCfgSnmpCommunityAccessPrefixLength, the host
             address part has to be a zero, if any.
    
             Also the following address can't be used.
             127.0.0.0/8 Loopback
             224.0.0.0/4 Multicasts (former Class D)
             240.0.0.0/4 Reserved (former Class E)"
        ::= { ipeCfgSnmpCommunityEntry 8 }
    
    -- 1.3.6.1.4.1.119.2.3.69.213.502.5.3.11.2.1.9
    ipeCfgSnmpCommunityAccessPrefixLength2 OBJECT-TYPE
        SYNTAX      INTEGER (0..32)
        ACCESS      read-only
        STATUS      mandatory
        DESCRIPTION
            "A prefix length of ipeCfgSnmpCommunityAccessAddress."
        ::= { ipeCfgSnmpCommunityEntry 9 }
    
    -- 1.3.6.1.4.1.119.2.3.69.213.502.5.3.11.2.1.10
    ipeCfgSnmpCommunityAccessAddress3 OBJECT-TYPE
        SYNTAX      IpAddress
        ACCESS      read-only
        STATUS      mandatory
        DESCRIPTION
            "An address which is permitted to use this entry's community
             name.
             When masking in ipeCfgSnmpCommunityAccessPrefixLength, the host
             address part has to be a zero, if any.
    
             Also the following address can't be used.
             127.0.0.0/8 Loopback
             224.0.0.0/4 Multicasts (former Class D)
             240.0.0.0/4 Reserved (former Class E)"
        ::= { ipeCfgSnmpCommunityEntry 10 }
    
    -- 1.3.6.1.4.1.119.2.3.69.213.502.5.3.11.2.1.11
    ipeCfgSnmpCommunityAccessPrefixLength3 OBJECT-TYPE
        SYNTAX      INTEGER (0..32)
        ACCESS      read-only
        STATUS      mandatory
        DESCRIPTION
            "A prefix length of ipeCfgSnmpCommunityAccessAddress."
        ::= { ipeCfgSnmpCommunityEntry 11 }
    
    -- 1.3.6.1.4.1.119.2.3.69.213.502.5.3.11.2.1.12
    ipeCfgSnmpCommunityAccessUsage OBJECT-TYPE
        SYNTAX      UsedNotusedValue
        ACCESS      read-only
        STATUS      mandatory
        DESCRIPTION
            "Access Control Usage."
        DEFVAL      { notUsed }
        ::= { ipeCfgSnmpCommunityEntry 12 }
    
    -- 1.3.6.1.4.1.119.2.3.69.213.502.5.3.11.2.1.13
    ipeCfgSnmpCommunityAccessUsage2 OBJECT-TYPE
        SYNTAX      UsedNotusedValue
        ACCESS      read-only
        STATUS      mandatory
        DESCRIPTION
            "Access Control Usage."
        DEFVAL      { notUsed }
        ::= { ipeCfgSnmpCommunityEntry 13 }
    
    -- 1.3.6.1.4.1.119.2.3.69.213.502.5.3.11.2.1.14
    ipeCfgSnmpCommunityAccessUsage3 OBJECT-TYPE
        SYNTAX      UsedNotusedValue
        ACCESS      read-only
        STATUS      mandatory
        DESCRIPTION
            "Access Control Usage."
        DEFVAL      { notUsed }
        ::= { ipeCfgSnmpCommunityEntry 14 }
    
    -- 1.3.6.1.4.1.119.2.3.69.213.502.5.3.11.2.1.15
    ipeCfgSnmpCommunityAccessV6Address OBJECT-TYPE
        SYNTAX      Ipv6Address
        ACCESS      read-only
        STATUS      mandatory
        DESCRIPTION
            "An IPv6 address which is permitted to use this entry's community
             name.
             The following are not valid addresses:
               ::1/128 IPv6 Loopback
               FF00::/8 IPv6 Multicasts
               FE80::/10 Link local"
        ::= { ipeCfgSnmpCommunityEntry 15 }
    
    -- 1.3.6.1.4.1.119.2.3.69.213.502.5.3.11.2.1.16
    ipeCfgSnmpCommunityAccessV6PrefixLength OBJECT-TYPE
        SYNTAX      INTEGER (0..128)
        ACCESS      read-only
        STATUS      mandatory
        DESCRIPTION
            "A prefix length of ipeCfgSnmpCommunityAccessV6Address."
        ::= { ipeCfgSnmpCommunityEntry 16 }
    
    -- 1.3.6.1.4.1.119.2.3.69.213.502.5.3.11.2.1.17
    ipeCfgSnmpCommunityAccessV6Address2 OBJECT-TYPE
        SYNTAX      Ipv6Address
        ACCESS      read-only
        STATUS      mandatory
        DESCRIPTION
            "An IPv6 address which is permitted to use this entry's community
             name.
             The following are not valid addresses
               ::1/128 IPv6 Loopback
               FF00::/8 IPv6 Multicasts
               FE80::/10 Link local"
        ::= { ipeCfgSnmpCommunityEntry 17 }
    
    -- 1.3.6.1.4.1.119.2.3.69.213.502.5.3.11.2.1.18
    ipeCfgSnmpCommunityAccessV6PrefixLength2 OBJECT-TYPE
        SYNTAX      INTEGER (0..128)
        ACCESS      read-only
        STATUS      mandatory
        DESCRIPTION
            "A prefix length of ipeCfgSnmpCommunityAccessV6Address."
        ::= { ipeCfgSnmpCommunityEntry 18 }
    
    -- 1.3.6.1.4.1.119.2.3.69.213.502.5.3.11.2.1.19
    ipeCfgSnmpCommunityAccessV6Address3 OBJECT-TYPE
        SYNTAX      Ipv6Address
        ACCESS      read-only
        STATUS      mandatory
        DESCRIPTION
            "An IPv6 address which is permitted to use this entry's community
             name.
             The following are not valid addresses
               ::1/128 IPv6 Loopback
               FF00::/8 IPv6 Multicasts
               FE80::/10 Link local"
        ::= { ipeCfgSnmpCommunityEntry 19 }
    
    -- 1.3.6.1.4.1.119.2.3.69.213.502.5.3.11.2.1.20
    ipeCfgSnmpCommunityAccessV6PrefixLength3 OBJECT-TYPE
        SYNTAX      INTEGER (0..128)
        ACCESS      read-only
        STATUS      mandatory
        DESCRIPTION
            "A prefix length of ipeCfgSnmpCommunityAccessV6Address."
        ::= { ipeCfgSnmpCommunityEntry 20 }
    
    -- 1.3.6.1.4.1.119.2.3.69.213.502.5.3.11.2.1.21
    ipeCfgSnmpCommunityAccessAddressType OBJECT-TYPE
        SYNTAX      INTEGER { invalid(0), ipv4(1), ipv6(2) }
        ACCESS      read-only
        STATUS      mandatory
        DESCRIPTION
            "An address type to be used for the community access."
        ::= { ipeCfgSnmpCommunityEntry 21 }
    
    -- 1.3.6.1.4.1.119.2.3.69.213.502.5.3.11.2.1.22
    ipeCfgSnmpCommunityAccessV6Usage OBJECT-TYPE
        SYNTAX      UsedNotusedValue
        ACCESS      read-only
        STATUS      mandatory
        DESCRIPTION
            "Access Control IPv6 Usage."
        ::= { ipeCfgSnmpCommunityEntry 22 }
    
    -- 1.3.6.1.4.1.119.2.3.69.213.502.5.3.11.2.1.23
    ipeCfgSnmpCommunityAccessV6Usage2 OBJECT-TYPE
        SYNTAX      UsedNotusedValue
        ACCESS      read-only
        STATUS      mandatory
        DESCRIPTION
            "Access Control IPv6 Usage."
        ::= { ipeCfgSnmpCommunityEntry 23 }
    
    -- 1.3.6.1.4.1.119.2.3.69.213.502.5.3.11.2.1.24
    ipeCfgSnmpCommunityAccessV6Usage3 OBJECT-TYPE
        SYNTAX      UsedNotusedValue
        ACCESS      read-only
        STATUS      mandatory
        DESCRIPTION
            "Access Control IPv6 Usage."
        ::= { ipeCfgSnmpCommunityEntry 24 }
    
    -- 1.3.6.1.4.1.119.2.3.69.213.502.5.3.11.2.1.1001
    ipeCfgSnmpCommunityNEAddressAddrType OBJECT-TYPE
        SYNTAX      InetAddressType
        ACCESS      not-accessible
        STATUS      mandatory
        DESCRIPTION
            "Represents the IP address type of NE address index.
             Only ipv4(1) and ipv6(2) are supported."
        ::= { ipeCfgSnmpCommunityEntry 1001 }
    
    -- 1.3.6.1.4.1.119.2.3.69.213.502.5.3.11.3
    ipeCfgSnmpTrapTable OBJECT-TYPE
        SYNTAX      SEQUENCE OF IpeCfgSnmpTrapEntry
        ACCESS      not-accessible
        STATUS      mandatory
        DESCRIPTION
            "A table of notification information."
        ::= { ipeCfgSnmp 3 }
    
    -- 1.3.6.1.4.1.119.2.3.69.213.502.5.3.11.3.1
    ipeCfgSnmpTrapEntry OBJECT-TYPE
        SYNTAX      IpeCfgSnmpTrapEntry
        ACCESS      not-accessible
        STATUS      mandatory
        DESCRIPTION
            "A set of notification information."
        INDEX       { ipeCfgSnmpTrapEntryNEAddressAddrType, ipeCfgSnmpTrapEntryNEAddress, ipeCfgSnmpTrapEntryIndex }
        ::= { ipeCfgSnmpTrapTable 1 }
    
    IpeCfgSnmpTrapEntry ::= SEQUENCE {
        ipeCfgSnmpTrapEntryIndex                INTEGER,
        ipeCfgSnmpTrapEntryNEAddress            InetAddress,
        ipeCfgSnmpTrapVersion                   INTEGER,
        ipeCfgSnmpTrapNotifyType                INTEGER,
        ipeCfgSnmpTrapTargetAddress             IpAddress,
        ipeCfgSnmpTrapTargetPort                INTEGER,
        ipeCfgSnmpTrapSecurityName              DisplayString,
        ipeCfgSnmpTrapSecurityLevel             INTEGER,
        ipeCfgSnmpTrapEngineId                  OCTET STRING,
        ipeCfgSnmpTrapAuthAlgorithm             INTEGER,
        ipeCfgSnmpTrapAuthKey                   DisplayString,
        ipeCfgSnmpTrapPrivAlgorithm             INTEGER,
        ipeCfgSnmpTrapPrivKey                   DisplayString,
        ipeCfgSnmpTrapRowStatus                 RowStatus,
        ipeCfgSnmpTrapTargetV6Address           Ipv6Address,
        ipeCfgSnmpTrapTargetIfIndex             INTEGER,
        ipeCfgSnmpTrapTargetAddressType         INTEGER,
        ipeCfgSnmpTrapEntryNEAddressAddrType    InetAddressType
    }
    
    -- 1.3.6.1.4.1.119.2.3.69.213.502.5.3.11.3.1.1
    ipeCfgSnmpTrapEntryIndex OBJECT-TYPE
        SYNTAX      INTEGER (1..6)
        ACCESS      not-accessible
        STATUS      mandatory
        DESCRIPTION
            "Index of this ipeCfgSnmpTrapEntry.
             You have to choose a value from 1 to 6.
    
             The entry by which an index is 4,5 and 6 is volatile. Those entry
             is eliminated at the equipment reboot."
        ::= { ipeCfgSnmpTrapEntry 1 }
    
    -- 1.3.6.1.4.1.119.2.3.69.213.502.5.3.11.3.1.2
    ipeCfgSnmpTrapEntryNEAddress OBJECT-TYPE
        SYNTAX      InetAddress
        ACCESS      not-accessible
        STATUS      mandatory
        DESCRIPTION
            ""
        ::= { ipeCfgSnmpTrapEntry 2 }
    
    -- 1.3.6.1.4.1.119.2.3.69.213.502.5.3.11.3.1.3
    ipeCfgSnmpTrapVersion OBJECT-TYPE
        SYNTAX      INTEGER { invalid(0), v1(1), v2c(2), v3(3) }
        ACCESS      read-only
        STATUS      mandatory
        DESCRIPTION
            "A version of this entry's notification."
        ::= { ipeCfgSnmpTrapEntry 3 }
    
    -- 1.3.6.1.4.1.119.2.3.69.213.502.5.3.11.3.1.4
    ipeCfgSnmpTrapNotifyType OBJECT-TYPE
        SYNTAX      INTEGER { invalid(0), trap(1), inform(2) }
        ACCESS      read-only
        STATUS      mandatory
        DESCRIPTION
            "A notification type of this entry's notification."
        ::= { ipeCfgSnmpTrapEntry 4 }
    
    -- 1.3.6.1.4.1.119.2.3.69.213.502.5.3.11.3.1.5
    ipeCfgSnmpTrapTargetAddress OBJECT-TYPE
        SYNTAX      IpAddress
        ACCESS      read-only
        STATUS      mandatory
        DESCRIPTION
            "Destination IP address of this entry's notification.
    
             The following address can't be used.
             127.0.0.0/8 Loopback
             0.0.0.0/0    Current network
             224.0.0.0/4 Multicasts (former Class D)
             240.0.0.0/4 Reserved (former Class E)"
        ::= { ipeCfgSnmpTrapEntry 5 }
    
    -- 1.3.6.1.4.1.119.2.3.69.213.502.5.3.11.3.1.6
    ipeCfgSnmpTrapTargetPort OBJECT-TYPE
        SYNTAX      INTEGER (1..65535)
        ACCESS      read-only
        STATUS      mandatory
        DESCRIPTION
            "Destination UDP port this entry's notification."
        ::= { ipeCfgSnmpTrapEntry 6 }
    
    -- 1.3.6.1.4.1.119.2.3.69.213.502.5.3.11.3.1.7
    ipeCfgSnmpTrapSecurityName OBJECT-TYPE
        SYNTAX      DisplayString (SIZE(1..31))
        ACCESS      read-only
        STATUS      mandatory
        DESCRIPTION
            "A security name.
             The meaning is different depending on ipeCfgSnmpTrapVersion.
    
             v1/v2c  : It's meaning a community name.
             v3      : It's meaning a user name.
    
             Please use ASCII code.
    
             The characters which can be used are '-', '_','0'-'9', 'a'-'z'
             and 'A'-'Z'.
    
             When there was the same combination to the other index,
             ipeCfgSnmpTrapSecurityName and ipeCfgSnmpTrapEngineId become
             error."
        ::= { ipeCfgSnmpTrapEntry 7 }
    
    -- 1.3.6.1.4.1.119.2.3.69.213.502.5.3.11.3.1.8
    ipeCfgSnmpTrapSecurityLevel OBJECT-TYPE
        SYNTAX      INTEGER { invalid(0), noAuthNoPriv(1), authNoPriv(2),
                        authPriv(3) }
        ACCESS      read-only
        STATUS      mandatory
        DESCRIPTION
            "A security level of this entry's notification.
    
             When ipeCfgSnmpTrapVersion is v1(1) or v2c(2), you have to SET
             noAuthNoPriv(1)."
        ::= { ipeCfgSnmpTrapEntry 8 }
    
    -- 1.3.6.1.4.1.119.2.3.69.213.502.5.3.11.3.1.9
    ipeCfgSnmpTrapEngineId OBJECT-TYPE
        SYNTAX      OCTET STRING (SIZE(5..32))
        ACCESS      read-only
        STATUS      mandatory
        DESCRIPTION
            "A snmpEngineID which this entry's notification uses.(5-32 octet)
             ipeCfgSnmpTrapNotifyType is effective only at the time of
             inform(2).
             A snmpEngineID of a destination SNMP entity.
    
             When there was the same combination to the other index,
             ipeCfgSnmpTrapSecurityName and ipeCfgSnmpTrapEngineId become
             error."
        ::= { ipeCfgSnmpTrapEntry 9 }
    
    -- 1.3.6.1.4.1.119.2.3.69.213.502.5.3.11.3.1.10
    ipeCfgSnmpTrapAuthAlgorithm OBJECT-TYPE
        SYNTAX      INTEGER { invalid(0), md5(1), sha(2) }
        ACCESS      read-only
        STATUS      mandatory
        DESCRIPTION
            "Authentication protocol.
    
             ipeCfgSnmpTrapNotifyType is effective for the SET only at the
             time of inform(2). Even if it is done SET in the case of trap(1),
             I am ignored. In addition, a value of
             ipeCfgAccountUserSnmpV3AuthAlgorithm is acquired at time to get."
        ::= { ipeCfgSnmpTrapEntry 10 }
    
    -- 1.3.6.1.4.1.119.2.3.69.213.502.5.3.11.3.1.11
    ipeCfgSnmpTrapAuthKey OBJECT-TYPE
        SYNTAX      DisplayString (SIZE(8..128))
        ACCESS      read-only
        STATUS      mandatory
        DESCRIPTION
            "Authenticate password for SNMP inform PDU.
             This object can be operated only when in secure way.
             When the object 'ipeCfgSnmpTrapNotifyType' is trap(1), SET
             request is not processed (discarded), and GET request returns the
             same value as 'ipeCfgAccountUserSnmpV3AuthKey'."
        ::= { ipeCfgSnmpTrapEntry 11 }
    
    -- 1.3.6.1.4.1.119.2.3.69.213.502.5.3.11.3.1.12
    ipeCfgSnmpTrapPrivAlgorithm OBJECT-TYPE
        SYNTAX      INTEGER { invalid(0), des(1), aes(2) }
        ACCESS      read-only
        STATUS      mandatory
        DESCRIPTION
            "privacy protocol.
    
             ipeCfgSnmpTrapNotifyType is effective for the SET only at the
             time of inform(2). Even if it is done SET in the case of trap(1),
             I am ignored. In addition, a value of
             ipeCfgAccountUserSnmpV3PrivAlgorithm is acquired at time to get."
        ::= { ipeCfgSnmpTrapEntry 12 }
    
    -- 1.3.6.1.4.1.119.2.3.69.213.502.5.3.11.3.1.13
    ipeCfgSnmpTrapPrivKey OBJECT-TYPE
        SYNTAX      DisplayString (SIZE(8..128))
        ACCESS      read-only
        STATUS      mandatory
        DESCRIPTION
            "Privacy password for SNMP inform PDU.
             This objet can be operated only when in secure way.
             When the object 'ipeCfgSnmpTrapNotifyType' is trap(1), SET
             request is not processed (discarded), and GET request returns the
             same value as 'ipeCfgAccountUserSnmpV3PrivKey'."
        ::= { ipeCfgSnmpTrapEntry 13 }
    
    -- 1.3.6.1.4.1.119.2.3.69.213.502.5.3.11.3.1.14
    ipeCfgSnmpTrapRowStatus OBJECT-TYPE
        SYNTAX      RowStatus { active(1), createAndGo(4), destroy(6) }
        ACCESS      read-only
        STATUS      mandatory
        DESCRIPTION
            "This RowStatus has a status only  active(1).
             You can SET only createAndGo(4) or destroy(6).
    
             1) how to create
             1.1) SNMPv1/v2c
             To create a new row, you must SET objects indicated below.
    
             ipeCfgSnmpTrapEntryIndex, ipeCfgSnmpTrapVersion,
             ipeCfgSnmpTrapNotifyType, ipeCfgSnmpTrapTargetAddress,
             ipeCfgSnmpTrapTargetV6Address,
             ipeCfgSnmpTrapTargetAddressType(*), ipeCfgSnmpTrapTaergetPort,
             ipeCfgSnmpTrapSecurityName
             ipeCfgSnmpTrapRowStatus     # Only createAndGo(4).
    
             It isn't necessary to set ipeCfgSnmpTrapSecurityLevel. When set
             it, the value is checked, so all except for noAuthNoPriv (1) will
             be NG.
             And, the other object is not necessary. Even if it is done SET,
             it is checked the value, but ignored.
    
             1.2) SNMPv3 (ipeCfgSnmpTrapNotifyType = trap(1))
             ipeCfgSnmpTrapVersion, ipeCfgSnmpTrapNotifyType,
             ipeCfgSnmpTrapTargetAddress, ipeCfgSnmpTrapTargetV6Address,
             ipeCfgSnmpTrapTargetAddressType(*), ipeCfgSnmpTrapTaergetPort,
             ipeCfgSnmpTrapSecurityName
             ipeCfgSnmpTrapRowStatus     # Only createAndGo(4).
    
             Other object is not necessary. Even if it is done SET, it is
             checked the value, but ignored.
    
             1.3) SNMPv3 (ipeCfgSnmpTrapNotifyType = inform(2))
             To create a new row, you must SET objects indicated below.
    
             ipeCfgSnmpTrapVersion, ipeCfgSnmpTrapNotifyType,
             ipeCfgSnmpTrapTargetAddress, ipeCfgSnmpTrapTargetV6Address,
             ipeCfgSnmpTrapTargetAddressType(*), ipeCfgSnmpTrapTaergetPort,
             ipeCfgSnmpTrapSecurityName, ipeCfgSnmpTrapSecurityLevel,
             ipeCfgSnmpTrapEngineId, ipeCfgSnmpTrapAuthAlgorithm,
             ipeCfgSnmpTrapAuthKey, ipeCfgSnmpTrapPrivAlgorithm,
             ipeCfgSnmpTrapPrivKey
             ipeCfgSnmpTrapRowStatus    # Only createAndGo(4).
    
             * NOT for EX CPRI
    
             ipeCfgSnmpTrapEntryIndex is an index of this entry.
    
             2) how to destroy
             To destroy a exist row, you must SET a destory(6) to
             ipeCfgSnmpCommunityRowStatus.
    
             3) how to modify
             It is not possible.
             Please destroy a exist row, and create a new row."
        ::= { ipeCfgSnmpTrapEntry 14 }
    
    -- 1.3.6.1.4.1.119.2.3.69.213.502.5.3.11.3.1.15
    ipeCfgSnmpTrapTargetV6Address OBJECT-TYPE
        SYNTAX      Ipv6Address
        ACCESS      read-only
        STATUS      mandatory
        DESCRIPTION
            "Destination IPv6 address of this entry's notification.
             The following are not valid addresses:
                 ::1/128 IPv6 Loopback
                 ::/128 Unspecified
                 FF00::/8 IPv6 Multicasts"
        ::= { ipeCfgSnmpTrapEntry 15 }
    
    -- 1.3.6.1.4.1.119.2.3.69.213.502.5.3.11.3.1.16
    ipeCfgSnmpTrapTargetIfIndex OBJECT-TYPE
        SYNTAX      INTEGER { invalid(0), bridge1(11), bridge2(12),
                        bridge3(13), bridge4(14), bridge5(15), bridge6(16),
                        bridge7(17), bridge8(18), bridge9(19), bridge10(20),
                        bridge11(21), bridge12(22), bridge13(23),
                        bridge14(24), bridge15(25), bridge16(26),
                        bridge17(27), bridge18(28), bridge19(29),
                        bridge20(30) }
        ACCESS      read-only
        STATUS      mandatory
        DESCRIPTION
            "The interface index through which the Server is reachable.
             When ipeCfgSnmpTrapTargetV6Address is configured with
             Link-local address, this object must be configured
             to proper Interface index. For any other address type,
             value of this object shall be 0."
        ::= { ipeCfgSnmpTrapEntry 16 }
    
    -- 1.3.6.1.4.1.119.2.3.69.213.502.5.3.11.3.1.17
    ipeCfgSnmpTrapTargetAddressType OBJECT-TYPE
        SYNTAX      INTEGER { invalid(0), ipv4(1), ipv6(2) }
        ACCESS      read-only
        STATUS      mandatory
        DESCRIPTION
            "Indicate IP address type of this trap target.
    
             ipv4 : trap target address has IPv4 address.
             ipv6 : trap target address has IPv6 address.
             When this object is not specified at the object creation with the
             index 4 through 6, 'ipv4' is as the default."
        ::= { ipeCfgSnmpTrapEntry 17 }
    
    -- 1.3.6.1.4.1.119.2.3.69.213.502.5.3.11.3.1.1001
    ipeCfgSnmpTrapEntryNEAddressAddrType OBJECT-TYPE
        SYNTAX      InetAddressType
        ACCESS      not-accessible
        STATUS      mandatory
        DESCRIPTION
            "Represents the IP address type of NE address index.
             Only ipv4(1) and ipv6(2) are supported."
        ::= { ipeCfgSnmpTrapEntry 1001 }
    
    -- 1.3.6.1.4.1.119.2.3.69.213.502.5.3.12
    ipeCfgAccount OBJECT IDENTIFIER
        ::= { ipeConfigurationGroup 12 }
    
    -- 1.3.6.1.4.1.119.2.3.69.213.502.5.3.12.1
    ipeCfgAccountUserInfoTable OBJECT-TYPE
        SYNTAX      SEQUENCE OF IpeCfgAccountUserInfoEntry
        ACCESS      not-accessible
        STATUS      mandatory
        DESCRIPTION
            "Table of user Information."
        ::= { ipeCfgAccount 1 }
    
    -- 1.3.6.1.4.1.119.2.3.69.213.502.5.3.12.1.1
    ipeCfgAccountUserInfoEntry OBJECT-TYPE
        SYNTAX      IpeCfgAccountUserInfoEntry
        ACCESS      not-accessible
        STATUS      mandatory
        DESCRIPTION
            "Entry of user information."
        INDEX       { ipeCfgAccountUserNEAddressAddrType, ipeCfgAccountUserNEAddress, ipeCfgAccountUserIndex }
        ::= { ipeCfgAccountUserInfoTable 1 }
    
    IpeCfgAccountUserInfoEntry ::= SEQUENCE {
        ipeCfgAccountUserIndex                  INTEGER,
        ipeCfgAccountUserNEAddress              InetAddress,
        ipeCfgAccountUserName                   DisplayString,
        ipeCfgAccountUserKey                    DisplayString,
        ipeCfgAccountUserGroup                  DisplayString,
        ipeCfgAccountUserSnmpV3SecurityLevel    INTEGER,
        ipeCfgAccountUserSnmpV3AuthAlgorithm    INTEGER,
        ipeCfgAccountUserSnmpV3AuthKey          DisplayString,
        ipeCfgAccountUserSnmpV3PrivAlgorithm    INTEGER,
        ipeCfgAccountUserSnmpV3PrivKey          DisplayString,
        ipeCfgAccountUserRowStatus              RowStatus,
        ipeCfgAccountUserNEAddressAddrType      InetAddressType
    }
    
    -- 1.3.6.1.4.1.119.2.3.69.213.502.5.3.12.1.1.1
    ipeCfgAccountUserIndex OBJECT-TYPE
        SYNTAX      INTEGER (1..102)
        ACCESS      not-accessible
        STATUS      mandatory
        DESCRIPTION
            "Index of table."
        ::= { ipeCfgAccountUserInfoEntry 1 }
    
    -- 1.3.6.1.4.1.119.2.3.69.213.502.5.3.12.1.1.2
    ipeCfgAccountUserNEAddress OBJECT-TYPE
        SYNTAX      InetAddress
        ACCESS      not-accessible
        STATUS      mandatory
        DESCRIPTION
            ""
        ::= { ipeCfgAccountUserInfoEntry 2 }
    
    -- 1.3.6.1.4.1.119.2.3.69.213.502.5.3.12.1.1.3
    ipeCfgAccountUserName OBJECT-TYPE
        SYNTAX      DisplayString (SIZE(1..31))
        ACCESS      read-only
        STATUS      mandatory
        DESCRIPTION
            "User Name.
             An overlap of a user name isn't permitted.
    
             Please use ASCII code.
    
             The characters which can be used are '-', '_','0'-'9', 'a'-'z'
             and 'A'-'Z'."
        ::= { ipeCfgAccountUserInfoEntry 3 }
    
    -- 1.3.6.1.4.1.119.2.3.69.213.502.5.3.12.1.1.4
    ipeCfgAccountUserKey OBJECT-TYPE
        SYNTAX      DisplayString (SIZE(8..128))
        ACCESS      read-only
        STATUS      mandatory
        DESCRIPTION
            "User password.
             This object can be operated only when in secure way. Acceptable
             characters for this object is shown below.
    
             '-', '_','0'-'9', 'a'-'z' and 'A'-'Z'."
        ::= { ipeCfgAccountUserInfoEntry 4 }
    
    -- 1.3.6.1.4.1.119.2.3.69.213.502.5.3.12.1.1.5
    ipeCfgAccountUserGroup OBJECT-TYPE
        SYNTAX      DisplayString (SIZE(1..31))
        ACCESS      read-only
        STATUS      mandatory
        DESCRIPTION
            "This object defines the privilege for the user.
             Acceptable characters for this object is shown below.
    
             '-', '_','0'-'9', 'a'-'z' and 'A'-'Z'."
        ::= { ipeCfgAccountUserInfoEntry 5 }
    
    -- 1.3.6.1.4.1.119.2.3.69.213.502.5.3.12.1.1.6
    ipeCfgAccountUserSnmpV3SecurityLevel OBJECT-TYPE
        SYNTAX      INTEGER { invalid(0), noAuthNoPriv(1), authNoPriv(2),
                        authPriv(3) }
        ACCESS      read-only
        STATUS      mandatory
        DESCRIPTION
            "SNMPv3 security level.
    
             Setting for SET/GET/TRAP at the time of the SNMPv3 use(INFORM is
             inapplicable)"
        ::= { ipeCfgAccountUserInfoEntry 6 }
    
    -- 1.3.6.1.4.1.119.2.3.69.213.502.5.3.12.1.1.7
    ipeCfgAccountUserSnmpV3AuthAlgorithm OBJECT-TYPE
        SYNTAX      INTEGER { invalid(0), md5(1), sha(2) }
        ACCESS      read-only
        STATUS      mandatory
        DESCRIPTION
            "Hash calculate algorithm of authenticate password.
    
             Setting for SET/GET/TRAP at the time of the SNMPv3 use(INFORM is
             inapplicable)"
        ::= { ipeCfgAccountUserInfoEntry 7 }
    
    -- 1.3.6.1.4.1.119.2.3.69.213.502.5.3.12.1.1.8
    ipeCfgAccountUserSnmpV3AuthKey OBJECT-TYPE
        SYNTAX      DisplayString (SIZE(8..128))
        ACCESS      read-only
        STATUS      mandatory
        DESCRIPTION
            "Authenticate password for SNMP SET/GET/TRAP PDU.
             This object can be operated only when in secure way. When the
             object 'ipeCfgSnmpTrapNotifyType' is set to inform(2), the INFORM
             PDU Authenticate key is configured by 'ipeCfgSnmpTrapAuthKey'."
        ::= { ipeCfgAccountUserInfoEntry 8 }
    
    -- 1.3.6.1.4.1.119.2.3.69.213.502.5.3.12.1.1.9
    ipeCfgAccountUserSnmpV3PrivAlgorithm OBJECT-TYPE
        SYNTAX      INTEGER { invalid(0), des(1), aes(2) }
        ACCESS      read-only
        STATUS      mandatory
        DESCRIPTION
            "Cipher algorithm.
    
             Setting for SET/GET/TRAP at the time of the SNMPv3 use(INFORM is
             inapplicable)"
        ::= { ipeCfgAccountUserInfoEntry 9 }
    
    -- 1.3.6.1.4.1.119.2.3.69.213.502.5.3.12.1.1.10
    ipeCfgAccountUserSnmpV3PrivKey OBJECT-TYPE
        SYNTAX      DisplayString (SIZE(8..128))
        ACCESS      read-only
        STATUS      mandatory
        DESCRIPTION
            "Privacy password for SNMP SET/GET/TRAP PDU.
             This object can be operated only when in secure way. When the
             'ipeCfgSnmpTrapNotifyType' is set to inform(2), the INFORM PDU
             Authenticate key is configured by 'ipeCfgSnmpTrapAuthKey'."
        ::= { ipeCfgAccountUserInfoEntry 10 }
    
    -- 1.3.6.1.4.1.119.2.3.69.213.502.5.3.12.1.1.11
    ipeCfgAccountUserRowStatus OBJECT-TYPE
        SYNTAX      RowStatus { active(1), createAndGo(4), destroy(6) }
        ACCESS      read-only
        STATUS      mandatory
        DESCRIPTION
            "This RowStatus has a status only active(1).
    
             1) creating a entry
             When you make a new entry, you must SET objects indicated below.
    
             ipeCfgAccountUserIndex
             ipeCfgAccountUserName
             ipeCfgAccountUserKey
             ipeCfgAccountUserGroup
             ipeCfgAccountUserSnmpV3SecurityLevel
             ipeCfgAccountUserSnmpV3AuthAlgorithm
             ipeCfgAccountUserSnmpV3AuthKey
             ipeCfgAccountUserSnmpV3PrivAlgorithm
             ipeCfgAccountUserSnmpV3PrivKey
             ipeCfgAccountUserRowStatus <- createAndGo(4)
    
             2) modifing a entry
             ipeCfgAccountUserKey can only be changed.
             Other items can not be updated. Please do destroy of entry and a
             create.
    
             3) deleting a entry
             When you SET a destroy(6) to ipeCfgAccountUserRowStatus, the
             entry is destroyed.
    
             4) About SNMPv3
             When there is not ipeCfgAccountGroupInfoEntry corresponding to
             ipeCfgAccountUserGroup, SNMPv3-TRAP which I used
             ipeCfgAccountUserName for is output, but cannot use
             SNMPv3-Set/Get-Request."
        ::= { ipeCfgAccountUserInfoEntry 11 }
    
    -- 1.3.6.1.4.1.119.2.3.69.213.502.5.3.12.1.1.1001
    ipeCfgAccountUserNEAddressAddrType OBJECT-TYPE
        SYNTAX      InetAddressType
        ACCESS      not-accessible
        STATUS      mandatory
        DESCRIPTION
            "Represents the IP address type of NE address index.
             Only ipv4(1) and ipv6(2) are supported."
        ::= { ipeCfgAccountUserInfoEntry 1001 }
    
    -- 1.3.6.1.4.1.119.2.3.69.213.502.5.3.12.2
    ipeCfgAccountGroupInfoTable OBJECT-TYPE
        SYNTAX      SEQUENCE OF IpeCfgAccountGroupInfoEntry
        ACCESS      not-accessible
        STATUS      mandatory
        DESCRIPTION
            "Table of Group Information."
        ::= { ipeCfgAccount 2 }
    
    -- 1.3.6.1.4.1.119.2.3.69.213.502.5.3.12.2.1
    ipeCfgAccountGroupInfoEntry OBJECT-TYPE
        SYNTAX      IpeCfgAccountGroupInfoEntry
        ACCESS      not-accessible
        STATUS      mandatory
        DESCRIPTION
            "Entry of Group Information."
        INDEX       { ipeCfgAccountGroupNEAddressAddrType, ipeCfgAccountGroupNEAddress, ipeCfgAccountGroupIndex }
        ::= { ipeCfgAccountGroupInfoTable 1 }
    
    IpeCfgAccountGroupInfoEntry ::= SEQUENCE {
        ipeCfgAccountGroupIndex                 INTEGER,
        ipeCfgAccountGroupNEAddress             InetAddress,
        ipeCfgAccountGroupName                  DisplayString,
        ipeCfgAccountGroupTelnet                INTEGER,
        ipeCfgAccountGroupSsh                   INTEGER,
        ipeCfgAccountGroupFtp                   INTEGER,
        ipeCfgAccountGroupSftp                  INTEGER,
        ipeCfgAccountGroupHttp                  INTEGER,
        ipeCfgAccountGroupHttps                 INTEGER,
        ipeCfgAccountGroupSnmp                  INTEGER,
        ipeCfgAccountGroupAccessLevel           INTEGER,
        ipeCfgAccountGroupRowStatus             RowStatus,
        ipeCfgAccountGroupNEAddressAddrType     InetAddressType
    }
    
    -- 1.3.6.1.4.1.119.2.3.69.213.502.5.3.12.2.1.1
    ipeCfgAccountGroupIndex OBJECT-TYPE
        SYNTAX      INTEGER (1..10)
        ACCESS      not-accessible
        STATUS      mandatory
        DESCRIPTION
            "Index of table."
        ::= { ipeCfgAccountGroupInfoEntry 1 }
    
    -- 1.3.6.1.4.1.119.2.3.69.213.502.5.3.12.2.1.2
    ipeCfgAccountGroupNEAddress OBJECT-TYPE
        SYNTAX      InetAddress
        ACCESS      not-accessible
        STATUS      mandatory
        DESCRIPTION
            ""
        ::= { ipeCfgAccountGroupInfoEntry 2 }
    
    -- 1.3.6.1.4.1.119.2.3.69.213.502.5.3.12.2.1.3
    ipeCfgAccountGroupName OBJECT-TYPE
        SYNTAX      DisplayString (SIZE(1..31))
        ACCESS      read-only
        STATUS      mandatory
        DESCRIPTION
            "Group name.
             An overlap of a group name isn't permitted.
    
             Please use ASCII code.
    
             The characters which can be used are '-', '_','0'-'9', 'a'-'z'
             and 'A'-'Z'."
        ::= { ipeCfgAccountGroupInfoEntry 3 }
    
    -- 1.3.6.1.4.1.119.2.3.69.213.502.5.3.12.2.1.4
    ipeCfgAccountGroupTelnet OBJECT-TYPE
        SYNTAX      INTEGER { invalid(0), disabled(1), enabled(2) }
        ACCESS      read-only
        STATUS      mandatory
        DESCRIPTION
            "TELNET enable."
        ::= { ipeCfgAccountGroupInfoEntry 4 }
    
    -- 1.3.6.1.4.1.119.2.3.69.213.502.5.3.12.2.1.5
    ipeCfgAccountGroupSsh OBJECT-TYPE
        SYNTAX      INTEGER { invalid(0), disabled(1), enabled(2) }
        ACCESS      read-only
        STATUS      mandatory
        DESCRIPTION
            "SSH enable."
        ::= { ipeCfgAccountGroupInfoEntry 5 }
    
    -- 1.3.6.1.4.1.119.2.3.69.213.502.5.3.12.2.1.6
    ipeCfgAccountGroupFtp OBJECT-TYPE
        SYNTAX      INTEGER { invalid(0), disabled(1), enabled(2) }
        ACCESS      read-only
        STATUS      mandatory
        DESCRIPTION
            "FTP enable."
        ::= { ipeCfgAccountGroupInfoEntry 6 }
    
    -- 1.3.6.1.4.1.119.2.3.69.213.502.5.3.12.2.1.7
    ipeCfgAccountGroupSftp OBJECT-TYPE
        SYNTAX      INTEGER { invalid(0), disabled(1), enabled(2) }
        ACCESS      read-only
        STATUS      mandatory
        DESCRIPTION
            "SFTP enable."
        ::= { ipeCfgAccountGroupInfoEntry 7 }
    
    -- 1.3.6.1.4.1.119.2.3.69.213.502.5.3.12.2.1.8
    ipeCfgAccountGroupHttp OBJECT-TYPE
        SYNTAX      INTEGER { invalid(0), disabled(1), enabled(2) }
        ACCESS      read-only
        STATUS      mandatory
        DESCRIPTION
            "HTTP enable."
        ::= { ipeCfgAccountGroupInfoEntry 8 }
    
    -- 1.3.6.1.4.1.119.2.3.69.213.502.5.3.12.2.1.9
    ipeCfgAccountGroupHttps OBJECT-TYPE
        SYNTAX      INTEGER { invalid(0), disabled(1), enabled(2) }
        ACCESS      read-only
        STATUS      mandatory
        DESCRIPTION
            "HTTPS enable."
        ::= { ipeCfgAccountGroupInfoEntry 9 }
    
    -- 1.3.6.1.4.1.119.2.3.69.213.502.5.3.12.2.1.10
    ipeCfgAccountGroupSnmp OBJECT-TYPE
        SYNTAX      INTEGER { invalid(0), disabled(1), enabled(2) }
        ACCESS      read-only
        STATUS      mandatory
        DESCRIPTION
            "SNMP enable."
        ::= { ipeCfgAccountGroupInfoEntry 10 }
    
    -- 1.3.6.1.4.1.119.2.3.69.213.502.5.3.12.2.1.11
    ipeCfgAccountGroupAccessLevel OBJECT-TYPE
        SYNTAX      INTEGER { invalid(0), operatorLevel(1), configLevel(2),
                        adminLevel(3), debugLevel(4) }
        ACCESS      read-only
        STATUS      mandatory
        DESCRIPTION
            "Access level."
        ::= { ipeCfgAccountGroupInfoEntry 11 }
    
    -- 1.3.6.1.4.1.119.2.3.69.213.502.5.3.12.2.1.12
    ipeCfgAccountGroupRowStatus OBJECT-TYPE
        SYNTAX      RowStatus { active(1), createAndGo(4), destroy(6) }
        ACCESS      read-only
        STATUS      mandatory
        DESCRIPTION
            "This RowStatus has a status only 'active(1)'.
    
             1) creating a entry.
             When you make a new entry, you must SET objects indicated below.
    
             ipeCfgAccountGroupName
             ipeCfgAccountGroupTelnet
             ipeCfgAccountGroupSsh
             ipeCfgAccountGroupFtp
             ipeCfgAccountGroupSftp
             ipeCfgAccountGroupHttp
             ipeCfgAccountGroupHttps
             ipeCfgAccountGroupSnmp
             ipeCfgAccountGroupAccessLevel
             ipeCfgAccountGroupRowStatus <- createAndGo(4)
    
             ipeCfgAccountGroupIndex is an index of this entry.
    
             2) deleting a entry.
             When you SET a destroy(6) to ipeCfgAccountGroupRowStatus, the
             entry is destroyed.
    
             Information that synchronizes and is deleted:
              User Information setting(ssh/ftp/http login information)
              SNMPv3-Set/Get-Req user info
             (The SNMPv3-TRAP information is left)
    
             3) modifing a entry
             It can change it other than ipeCfgAccountGroupName,
             ipeCfgAccountGroupRowStatus. But the 'ipeCfgAccountGroupName' of
             predefined groups cannot be changed."
        ::= { ipeCfgAccountGroupInfoEntry 12 }
    
    -- 1.3.6.1.4.1.119.2.3.69.213.502.5.3.12.2.1.1001
    ipeCfgAccountGroupNEAddressAddrType OBJECT-TYPE
        SYNTAX      InetAddressType
        ACCESS      not-accessible
        STATUS      mandatory
        DESCRIPTION
            "Represents the IP address type of NE address index.
             Only ipv4(1) and ipv6(2) are supported."
        ::= { ipeCfgAccountGroupInfoEntry 1001 }
    
    -- 1.3.6.1.4.1.119.2.3.69.213.502.5.3.12.4
    ipeCfgUserAccountAuthTable OBJECT-TYPE
        SYNTAX      SEQUENCE OF IpeCfgUserAccountAuthEntry
        ACCESS      not-accessible
        STATUS      mandatory
        DESCRIPTION
            "Configure user authentication method about Web LCT."
        ::= { ipeCfgAccount 4 }
    
    -- 1.3.6.1.4.1.119.2.3.69.213.502.5.3.12.4.1
    ipeCfgUserAccountAuthEntry OBJECT-TYPE
        SYNTAX      IpeCfgUserAccountAuthEntry
        ACCESS      not-accessible
        STATUS      mandatory
        DESCRIPTION
            "..."
        INDEX       { ipeCfgUserAccountAuthNEAddressAddrType, ipeCfgUserAccountAuthNEAddress, ipeCfgUserAccountAuthIndex }
        ::= { ipeCfgUserAccountAuthTable 1 }
    
    IpeCfgUserAccountAuthEntry ::= SEQUENCE {
        ipeCfgUserAccountAuthIndex              INTEGER,
        ipeCfgUserAccountAuthNEAddress          InetAddress,
        ipeCfgUserAccountAuthMode               INTEGER,
        ipeCfgUserAccountAuthOrder              INTEGER,
        ipeCfgUserAccountAuthTrapEnable         INTEGER,
        ipeCfgUserAccountAuthTrapLocal          INTEGER,
        ipeCfgUserAccountAuthTrapExternal       INTEGER,
        ipeCfgUserAccountAuthProtection         EnableDisableValue,
        ipeCfgUserAccountAuthTotalNumber        INTEGER,
        ipeCfgUserAcctAuthUserNameStrength      EnableDisableValue,
        ipeCfgUserAcctAuthPasswdStrength        EnableDisableValue,
        ipeCfgUserAcctAuthLoginAttempts         INTEGER,
        ipeCfgUserAcctAuthAutoLogout            EnableDisableValue,
        ipeCfgUserAccountAuthNEAddressAddrType  InetAddressType
    }
    
    -- 1.3.6.1.4.1.119.2.3.69.213.502.5.3.12.4.1.1
    ipeCfgUserAccountAuthIndex OBJECT-TYPE
        SYNTAX      INTEGER (1)
        ACCESS      not-accessible
        STATUS      mandatory
        DESCRIPTION
            "The index of this table."
        ::= { ipeCfgUserAccountAuthEntry 1 }
    
    -- 1.3.6.1.4.1.119.2.3.69.213.502.5.3.12.4.1.2
    ipeCfgUserAccountAuthNEAddress OBJECT-TYPE
        SYNTAX      InetAddress
        ACCESS      not-accessible
        STATUS      mandatory
        DESCRIPTION
            "Reserved object for northbound interface."
        ::= { ipeCfgUserAccountAuthEntry 2 }
    
    -- 1.3.6.1.4.1.119.2.3.69.213.502.5.3.12.4.1.3
    ipeCfgUserAccountAuthMode OBJECT-TYPE
        SYNTAX      INTEGER { invalid(0), mode1(1), mode2(2), mode3(3) }
        ACCESS      read-only
        STATUS      mandatory
        DESCRIPTION
            "Indicate the user authentication mode.
    
             mode1 : local authentication only.
             mode2 : local and LDAP authentication. (NOT SUPPORTED)
             mode3 : local and RADIUS authentication.
    
             mode2 will be supprted in future version."
        DEFVAL      { mode1 }
        ::= { ipeCfgUserAccountAuthEntry 3 }
    
    -- 1.3.6.1.4.1.119.2.3.69.213.502.5.3.12.4.1.4
    ipeCfgUserAccountAuthOrder OBJECT-TYPE
        SYNTAX      INTEGER { invalid(0), localAuthFirst(1),
                        externalAuthFirst(2) }
        ACCESS      read-only
        STATUS      mandatory
        DESCRIPTION
            "Indicate the user authentication order.
             This object is effective only if ipeCfgUserAccountAuthMode
             is set to mode2 or mode3.
             External authentication means authentication with RADIUS or
             LDAP.
    
             localAuthFirst    : local -> external
             externalAuthFirst : external -> local"
        DEFVAL      { localAuthFirst }
        ::= { ipeCfgUserAccountAuthEntry 4 }
    
    -- 1.3.6.1.4.1.119.2.3.69.213.502.5.3.12.4.1.5
    ipeCfgUserAccountAuthTrapEnable OBJECT-TYPE
        SYNTAX      INTEGER { invalid(0), disable(1), enable(2) }
        ACCESS      read-only
        STATUS      mandatory
        DESCRIPTION
            "Enable or disable user login trap.
             In case this object is set to enable, the system sends trap
             when user attempt to login to Web LCT."
        DEFVAL      { enable }
        ::= { ipeCfgUserAccountAuthEntry 5 }
    
    -- 1.3.6.1.4.1.119.2.3.69.213.502.5.3.12.4.1.6
    ipeCfgUserAccountAuthTrapLocal OBJECT-TYPE
        SYNTAX      INTEGER { invalid(0), success(1), failure(2) }
        ACCESS      read-only
        STATUS      mandatory
        DESCRIPTION
            "Indicate authentication result of local authentication.
             This object is dedicated for login control trap.
             If you read this object, the system returns invalid(0)."
        DEFVAL      { invalid }
        ::= { ipeCfgUserAccountAuthEntry 6 }
    
    -- 1.3.6.1.4.1.119.2.3.69.213.502.5.3.12.4.1.7
    ipeCfgUserAccountAuthTrapExternal OBJECT-TYPE
        SYNTAX      INTEGER { invalid(0), success(1), failure(2) }
        ACCESS      read-only
        STATUS      mandatory
        DESCRIPTION
            "Indicate authentication result of externel authentication.
             This object is dedicated for login control trap.
             If you read this object, the system returns invalid(0)."
        DEFVAL      { invalid }
        ::= { ipeCfgUserAccountAuthEntry 7 }
    
    -- 1.3.6.1.4.1.119.2.3.69.213.502.5.3.12.4.1.8
    ipeCfgUserAccountAuthProtection OBJECT-TYPE
        SYNTAX      EnableDisableValue
        ACCESS      read-only
        STATUS      mandatory
        DESCRIPTION
            "Indicates whether login protection is enabled."
        ::= { ipeCfgUserAccountAuthEntry 8 }
    
    -- 1.3.6.1.4.1.119.2.3.69.213.502.5.3.12.4.1.9
    ipeCfgUserAccountAuthTotalNumber OBJECT-TYPE
        SYNTAX      INTEGER (1..5)
        ACCESS      read-only
        STATUS      mandatory
        DESCRIPTION
            "The maximum sessions of users belong to the predefined groups
             which have configuration privilege."
        DEFVAL      { 5 }
        ::= { ipeCfgUserAccountAuthEntry 9 }
    
    -- 1.3.6.1.4.1.119.2.3.69.213.502.5.3.12.4.1.10
    ipeCfgUserAcctAuthUserNameStrength OBJECT-TYPE
        SYNTAX      EnableDisableValue
        ACCESS      read-only
        STATUS      mandatory
        DESCRIPTION
            "Indicates User Name Strength Enforcement for LCT only."
        ::= { ipeCfgUserAccountAuthEntry 10 }
    
    -- 1.3.6.1.4.1.119.2.3.69.213.502.5.3.12.4.1.11
    ipeCfgUserAcctAuthPasswdStrength OBJECT-TYPE
        SYNTAX      EnableDisableValue
        ACCESS      read-only
        STATUS      mandatory
        DESCRIPTION
            "Indicates Password Strength Enforcement for LCT only."
        ::= { ipeCfgUserAccountAuthEntry 11 }
    
    -- 1.3.6.1.4.1.119.2.3.69.213.502.5.3.12.4.1.12
    ipeCfgUserAcctAuthLoginAttempts OBJECT-TYPE
        SYNTAX      INTEGER { invalid(0), protectIn3Attempts(3),
                        protectIn5Attempts(5) }
        ACCESS      read-only
        STATUS      mandatory
        DESCRIPTION
            "Indicates the number of Unsuccessful Login Attempts for the
             login protection.
             When changing this setting the ipeStsAccountUserStatus for all
             accounts indicates 'normal' forcibly based on the state
             transition."
        ::= { ipeCfgUserAccountAuthEntry 12 }
    
    -- 1.3.6.1.4.1.119.2.3.69.213.502.5.3.12.4.1.13
    ipeCfgUserAcctAuthAutoLogout OBJECT-TYPE
        SYNTAX      EnableDisableValue
        ACCESS      read-only
        STATUS      mandatory
        DESCRIPTION
            "Indicates Auto-Logout for LCT only."
        ::= { ipeCfgUserAccountAuthEntry 13 }
    
    -- 1.3.6.1.4.1.119.2.3.69.213.502.5.3.12.4.1.1001
    ipeCfgUserAccountAuthNEAddressAddrType OBJECT-TYPE
        SYNTAX      InetAddressType
        ACCESS      not-accessible
        STATUS      mandatory
        DESCRIPTION
            "Represents the IP address type of NE address index.
             Only ipv4(1) and ipv6(2) are supported."
        ::= { ipeCfgUserAccountAuthEntry 1001 }
    
    -- 1.3.6.1.4.1.119.2.3.69.213.502.5.3.13
    ipeCfgDhcpGroup OBJECT IDENTIFIER
        ::= { ipeConfigurationGroup 13 }
    
    -- 1.3.6.1.4.1.119.2.3.69.213.502.5.3.13.1
    ipeCfgDhcpServerTable OBJECT-TYPE
        SYNTAX      SEQUENCE OF IpeCfgDhcpServerEntry
        ACCESS      not-accessible
        STATUS      mandatory
        DESCRIPTION
            "DHCPserver table."
        ::= { ipeCfgDhcpGroup 1 }
    
    -- 1.3.6.1.4.1.119.2.3.69.213.502.5.3.13.1.1
    ipeCfgDhcpServerEntry OBJECT-TYPE
        SYNTAX      IpeCfgDhcpServerEntry
        ACCESS      not-accessible
        STATUS      mandatory
        DESCRIPTION
            "entry of DHCPserver table."
        INDEX       { ipeCfgDhcpServerNEAddressAddrType, ipeCfgDhcpServerNEAddress, ipeCfgDhcpServerIndex }
        ::= { ipeCfgDhcpServerTable 1 }
    
    IpeCfgDhcpServerEntry ::= SEQUENCE {
        ipeCfgDhcpServerIndex               INTEGER,
        ipeCfgDhcpServerNEAddress           InetAddress,
        ipeCfgDhcpServerEnable              INTEGER,
        ipeCfgDhcpLeaseAddrRangeBegin       IpAddress,
        ipeCfgDhcpLeaseAddrRangeEnd         IpAddress,
        ipeCfgDhcpServerNEAddressAddrType   InetAddressType
    }
    
    -- 1.3.6.1.4.1.119.2.3.69.213.502.5.3.13.1.1.1
    ipeCfgDhcpServerIndex OBJECT-TYPE
        SYNTAX      INTEGER (1..2)
        ACCESS      not-accessible
        STATUS      mandatory
        DESCRIPTION
            "Index of this table.
             Index value '2' is used for redundant Ctrl card."
        ::= { ipeCfgDhcpServerEntry 1 }
    
    -- 1.3.6.1.4.1.119.2.3.69.213.502.5.3.13.1.1.2
    ipeCfgDhcpServerNEAddress OBJECT-TYPE
        SYNTAX      InetAddress
        ACCESS      not-accessible
        STATUS      mandatory
        DESCRIPTION
            ""
        ::= { ipeCfgDhcpServerEntry 2 }
    
    -- 1.3.6.1.4.1.119.2.3.69.213.502.5.3.13.1.1.3
    ipeCfgDhcpServerEnable OBJECT-TYPE
        SYNTAX      INTEGER { start(1), stop(2), restart(3) }
        ACCESS      read-only
        STATUS      mandatory
        DESCRIPTION
            "Effective/invalid setting of DHCP.
             value range:start(1)
                         stop(2)
                         restart(3)
             DHCPD has already started. When the start is specified, DHCPD
             restart."
        ::= { ipeCfgDhcpServerEntry 3 }
    
    -- 1.3.6.1.4.1.119.2.3.69.213.502.5.3.13.1.1.4
    ipeCfgDhcpLeaseAddrRangeBegin OBJECT-TYPE
        SYNTAX      IpAddress
        ACCESS      read-only
        STATUS      mandatory
        DESCRIPTION
            "Beginning IPaddress within the range of lease address.
             value range:Dotted decimal notation
             denial value:0.0.0.0 , 127.0.0.1 , 255.255.255.255
             ipeCfgDhcpLeaseAddrRangeBegin don't same as
             ipeCfgPortLctIpAddress value"
        ::= { ipeCfgDhcpServerEntry 4 }
    
    -- 1.3.6.1.4.1.119.2.3.69.213.502.5.3.13.1.1.5
    ipeCfgDhcpLeaseAddrRangeEnd OBJECT-TYPE
        SYNTAX      IpAddress
        ACCESS      read-only
        STATUS      mandatory
        DESCRIPTION
            "End IPaddress within the range of lease address.
             value range:Dotted decimal notation
             denial value:0.0.0.0 , 127.0.0.1 , 255.255.255.255
             ipeCfgDhcpLeaseAddrRangeEnd don't same as ipeCfgPortLctIpAddress
             value"
        ::= { ipeCfgDhcpServerEntry 5 }
    
    -- 1.3.6.1.4.1.119.2.3.69.213.502.5.3.13.1.1.1001
    ipeCfgDhcpServerNEAddressAddrType OBJECT-TYPE
        SYNTAX      InetAddressType
        ACCESS      not-accessible
        STATUS      mandatory
        DESCRIPTION
            "Represents the IP address type of NE address index.
             Only ipv4(1) and ipv6(2) are supported."
        ::= { ipeCfgDhcpServerEntry 1001 }
    
    -- 1.3.6.1.4.1.119.2.3.69.213.502.5.3.14
    ipeCfgStpGroup OBJECT IDENTIFIER
        ::= { ipeConfigurationGroup 14 }
    
    -- 1.3.6.1.4.1.119.2.3.69.213.502.5.3.14.1
    ipeCfgStpBridgeTable OBJECT-TYPE
        SYNTAX      SEQUENCE OF IpeCfgStpBridgeEntry
        ACCESS      not-accessible
        STATUS      mandatory
        DESCRIPTION
            "STP state setting table."
        ::= { ipeCfgStpGroup 1 }
    
    -- 1.3.6.1.4.1.119.2.3.69.213.502.5.3.14.1.1
    ipeCfgStpBridgeEntry OBJECT-TYPE
        SYNTAX      IpeCfgStpBridgeEntry
        ACCESS      not-accessible
        STATUS      mandatory
        DESCRIPTION
            "entry of STP state setting table."
        INDEX       { ipeCfgStpBridgeNEAddressAddrType, ipeCfgStpBridgeNEAddress, ipeCfgStpBridgeIndex }
        ::= { ipeCfgStpBridgeTable 1 }
    
    IpeCfgStpBridgeEntry ::= SEQUENCE {
        ipeCfgStpBridgeIndex                INTEGER,
        ipeCfgStpBridgeNEAddress            InetAddress,
        ipeCfgStpEnable                     INTEGER,
        ipeCfgStpPriority                   INTEGER,
        ipeCfgStpBridgeMaxAge               Timeout,
        ipeCfgStpBridgeHelloTime            Timeout,
        ipeCfgStpBridgeForwardDelay         Timeout,
        ipeCfgStpBridgeAutoEnable           OffOnValue,
        ipeCfgStpBridgeNEAddressAddrType    InetAddressType
    }
    
    -- 1.3.6.1.4.1.119.2.3.69.213.502.5.3.14.1.1.1
    ipeCfgStpBridgeIndex OBJECT-TYPE
        SYNTAX      INTEGER (1..20)
        ACCESS      not-accessible
        STATUS      mandatory
        DESCRIPTION
            "Index of this ipeCfgStpBridgeEntry.
             Range from 1 o 20."
        ::= { ipeCfgStpBridgeEntry 1 }
    
    -- 1.3.6.1.4.1.119.2.3.69.213.502.5.3.14.1.1.2
    ipeCfgStpBridgeNEAddress OBJECT-TYPE
        SYNTAX      InetAddress
        ACCESS      not-accessible
        STATUS      mandatory
        DESCRIPTION
            ""
        ::= { ipeCfgStpBridgeEntry 2 }
    
    -- 1.3.6.1.4.1.119.2.3.69.213.502.5.3.14.1.1.3
    ipeCfgStpEnable OBJECT-TYPE
        SYNTAX      INTEGER { enabled(1), disabled(2) }
        ACCESS      read-only
        STATUS      mandatory
        DESCRIPTION
            "Effective/invalid setting of STP.
             value :enabled
                    disabled"
        ::= { ipeCfgStpBridgeEntry 3 }
    
    -- 1.3.6.1.4.1.119.2.3.69.213.502.5.3.14.1.1.4
    ipeCfgStpPriority OBJECT-TYPE
        SYNTAX      INTEGER (0..65535)
        ACCESS      read-only
        STATUS      mandatory
        DESCRIPTION
            "Bridge priority.
             value range:0 to 65535"
        ::= { ipeCfgStpBridgeEntry 4 }
    
    -- 1.3.6.1.4.1.119.2.3.69.213.502.5.3.14.1.1.5
    ipeCfgStpBridgeMaxAge OBJECT-TYPE
        SYNTAX      Timeout (600..4000)
        ACCESS      read-only
        STATUS      mandatory
        DESCRIPTION
            "MaxAge (in units of hundredths of a second).
             value range:600 to 4000
             rule: 2 * (ipeCfgStpBridgeForwardDelay - 1) =>
             ipeCfgStpBridgeMaxAge
                  ipeCfgStpBridgeMaxAge >= 2 * (ipeCfgStpBridgeHelloTime + 1)"
        ::= { ipeCfgStpBridgeEntry 5 }
    
    -- 1.3.6.1.4.1.119.2.3.69.213.502.5.3.14.1.1.6
    ipeCfgStpBridgeHelloTime OBJECT-TYPE
        SYNTAX      Timeout (100..1000)
        ACCESS      read-only
        STATUS      mandatory
        DESCRIPTION
            "HelloTime (in units of hundredths of a second).
             value range:100 to 1000
             rule:ipeCfgStpBridgeMaxAge >= 2x(ipeCfgStpBridgeHelloTime + 1)"
        ::= { ipeCfgStpBridgeEntry 6 }
    
    -- 1.3.6.1.4.1.119.2.3.69.213.502.5.3.14.1.1.7
    ipeCfgStpBridgeForwardDelay OBJECT-TYPE
        SYNTAX      Timeout (400..3000)
        ACCESS      read-only
        STATUS      mandatory
        DESCRIPTION
            "ForwardDelay (in units of hundredths of a second).
             value range:400 to 3000
             rule: 2 * (ipeCfgStpBridgeForwardDelay - 1) >=
             ipeCfgStpBridgeMaxAge"
        ::= { ipeCfgStpBridgeEntry 7 }
    
    -- 1.3.6.1.4.1.119.2.3.69.213.502.5.3.14.1.1.8
    ipeCfgStpBridgeAutoEnable OBJECT-TYPE
        SYNTAX      OffOnValue
        ACCESS      read-only
        STATUS      mandatory
        DESCRIPTION
            "This object configures automatic enabling M-plane STP.
             When the automatic enabling is configured, 'ipeCfgStpEnable' does
             not control STP function, STP function will be enabled by the
             system automatically."
        ::= { ipeCfgStpBridgeEntry 8 }
    
    -- 1.3.6.1.4.1.119.2.3.69.213.502.5.3.14.1.1.1001
    ipeCfgStpBridgeNEAddressAddrType OBJECT-TYPE
        SYNTAX      InetAddressType
        ACCESS      not-accessible
        STATUS      mandatory
        DESCRIPTION
            "Represents the IP address type of NE address index.
             Only ipv4(1) and ipv6(2) are supported."
        ::= { ipeCfgStpBridgeEntry 1001 }
    
    -- 1.3.6.1.4.1.119.2.3.69.213.502.5.3.14.2
    ipeCfgStpPortTable OBJECT-TYPE
        SYNTAX      SEQUENCE OF IpeCfgStpPortEntry
        ACCESS      not-accessible
        STATUS      mandatory
        DESCRIPTION
            "STP port information table."
        ::= { ipeCfgStpGroup 2 }
    
    -- 1.3.6.1.4.1.119.2.3.69.213.502.5.3.14.2.1
    ipeCfgStpPortEntry OBJECT-TYPE
        SYNTAX      IpeCfgStpPortEntry
        ACCESS      not-accessible
        STATUS      mandatory
        DESCRIPTION
            "entry of  STP port information table."
        INDEX       { ipeCfgStpPortNEAddressAddrType, ipeCfgStpPortNEAddress, ipeCfgStpPortIfIndex }
        ::= { ipeCfgStpPortTable 1 }
    
    IpeCfgStpPortEntry ::= SEQUENCE {
        ipeCfgStpPortIfIndex            InterfaceIndex,
        ipeCfgStpPortNEAddress          InetAddress,
        ipeCfgStpPortPriority           INTEGER,
        ipeCfgStpPortPathCost           INTEGER,
        ipeCfgStpPortEdgeEnable         INTEGER,
        ipeCfgStpPortNEAddressAddrType  InetAddressType
    }
    
    -- 1.3.6.1.4.1.119.2.3.69.213.502.5.3.14.2.1.1
    ipeCfgStpPortIfIndex OBJECT-TYPE
        SYNTAX      InterfaceIndex
        ACCESS      not-accessible
        STATUS      mandatory
        DESCRIPTION
            "Index of I/F table."
        ::= { ipeCfgStpPortEntry 1 }
    
    -- 1.3.6.1.4.1.119.2.3.69.213.502.5.3.14.2.1.2
    ipeCfgStpPortNEAddress OBJECT-TYPE
        SYNTAX      InetAddress
        ACCESS      not-accessible
        STATUS      mandatory
        DESCRIPTION
            ""
        ::= { ipeCfgStpPortEntry 2 }
    
    -- 1.3.6.1.4.1.119.2.3.69.213.502.5.3.14.2.1.3
    ipeCfgStpPortPriority OBJECT-TYPE
        SYNTAX      INTEGER (0..63)
        ACCESS      read-only
        STATUS      mandatory
        DESCRIPTION
            "Port priority.
             value range:0 to 63"
        ::= { ipeCfgStpPortEntry 3 }
    
    -- 1.3.6.1.4.1.119.2.3.69.213.502.5.3.14.2.1.4
    ipeCfgStpPortPathCost OBJECT-TYPE
        SYNTAX      INTEGER (1..65535)
        ACCESS      read-only
        STATUS      mandatory
        DESCRIPTION
            "Pathcost.
             value range:1 to 65535"
        ::= { ipeCfgStpPortEntry 4 }
    
    -- 1.3.6.1.4.1.119.2.3.69.213.502.5.3.14.2.1.5
    ipeCfgStpPortEdgeEnable OBJECT-TYPE
        SYNTAX      INTEGER { enabled(1), disabled(2) }
        ACCESS      read-only
        STATUS      mandatory
        DESCRIPTION
            "Effective/invalid setting of BPDU.
             value range:enabled(1)
                         disabled(2)"
        ::= { ipeCfgStpPortEntry 5 }
    
    -- 1.3.6.1.4.1.119.2.3.69.213.502.5.3.14.2.1.1001
    ipeCfgStpPortNEAddressAddrType OBJECT-TYPE
        SYNTAX      InetAddressType
        ACCESS      not-accessible
        STATUS      mandatory
        DESCRIPTION
            "Represents the IP address type of NE address index.
             Only ipv4(1) and ipv6(2) are supported."
        ::= { ipeCfgStpPortEntry 1001 }
    
    -- 1.3.6.1.4.1.119.2.3.69.213.502.5.3.15
    ipeCfgPortGroup OBJECT IDENTIFIER
        ::= { ipeConfigurationGroup 15 }
    
    -- 1.3.6.1.4.1.119.2.3.69.213.502.5.3.15.1
    ipeCfgPortModemTable OBJECT-TYPE
        SYNTAX      SEQUENCE OF IpeCfgPortModemEntry
        ACCESS      not-accessible
        STATUS      mandatory
        DESCRIPTION
            "MODEM port set up information table."
        ::= { ipeCfgPortGroup 1 }
    
    -- 1.3.6.1.4.1.119.2.3.69.213.502.5.3.15.1.1
    ipeCfgPortModemEntry OBJECT-TYPE
        SYNTAX      IpeCfgPortModemEntry
        ACCESS      not-accessible
        STATUS      mandatory
        DESCRIPTION
            "entry of  MODEM port set up information table."
        INDEX       { ipeCfgPortModemNEAddressAddrType, ipeCfgPortModemNEAddress, ipeCfgPortModemIfIndex }
        ::= { ipeCfgPortModemTable 1 }
    
    IpeCfgPortModemEntry ::= SEQUENCE {
        ipeCfgPortModemIfIndex              InterfaceIndex,
        ipeCfgPortModemNEAddress            InetAddress,
        ipeCfgPortModemEnable               INTEGER,
        ipeCfgPortModemNEAddressAddrType    InetAddressType
    }
    
    -- 1.3.6.1.4.1.119.2.3.69.213.502.5.3.15.1.1.1
    ipeCfgPortModemIfIndex OBJECT-TYPE
        SYNTAX      InterfaceIndex
        ACCESS      not-accessible
        STATUS      mandatory
        DESCRIPTION
            "Index of table."
        ::= { ipeCfgPortModemEntry 1 }
    
    -- 1.3.6.1.4.1.119.2.3.69.213.502.5.3.15.1.1.2
    ipeCfgPortModemNEAddress OBJECT-TYPE
        SYNTAX      InetAddress
        ACCESS      not-accessible
        STATUS      mandatory
        DESCRIPTION
            ""
        ::= { ipeCfgPortModemEntry 2 }
    
    -- 1.3.6.1.4.1.119.2.3.69.213.502.5.3.15.1.1.3
    ipeCfgPortModemEnable OBJECT-TYPE
        SYNTAX      INTEGER { enabled(1), disabled(2) }
        ACCESS      read-only
        STATUS      mandatory
        DESCRIPTION
            "Effective/invalid setting of MODEM port.
             value range: enabled(1)
                         disabled(2)"
        ::= { ipeCfgPortModemEntry 3 }
    
    -- 1.3.6.1.4.1.119.2.3.69.213.502.5.3.15.1.1.1001
    ipeCfgPortModemNEAddressAddrType OBJECT-TYPE
        SYNTAX      InetAddressType
        ACCESS      not-accessible
        STATUS      mandatory
        DESCRIPTION
            "Represents the IP address type of NE address index.
             Only ipv4(1) and ipv6(2) are supported."
        ::= { ipeCfgPortModemEntry 1001 }
    
    -- 1.3.6.1.4.1.119.2.3.69.213.502.5.3.15.2
    ipeCfgPortLctTable OBJECT-TYPE
        SYNTAX      SEQUENCE OF IpeCfgPortLctEntry
        ACCESS      not-accessible
        STATUS      mandatory
        DESCRIPTION
            "LCT port set up information table."
        ::= { ipeCfgPortGroup 2 }
    
    -- 1.3.6.1.4.1.119.2.3.69.213.502.5.3.15.2.1
    ipeCfgPortLctEntry OBJECT-TYPE
        SYNTAX      IpeCfgPortLctEntry
        ACCESS      not-accessible
        STATUS      mandatory
        DESCRIPTION
            "entry of  LCT port set up information table."
        INDEX       { ipeCfgPortLctNEAddressAddrType, ipeCfgPortLctNEAddress, ipeCfgPortLctIfIndex }
        ::= { ipeCfgPortLctTable 1 }
    
    IpeCfgPortLctEntry ::= SEQUENCE {
        ipeCfgPortLctIfIndex                    InterfaceIndex,
        ipeCfgPortLctNEAddress                  InetAddress,
        ipeCfgPortLctIpAddress                  IpAddress,
        ipeCfgPortLctNetMask                    IpAddress,
        ipeCfgPortLctEnable                     INTEGER,
        ipeCfgPortLctMtu                        INTEGER,
        ipeCfgPortLctAutoNeg                    INTEGER,
        ipeCfgPortLctLinkLocalAddress           Ipv6Address,
        ipeCfgPortLctLinkLocalAddressOrigin     INTEGER,
        ipeCfgPortLctHttpReverseProxyEnable     EnableDisableValue,
        ipeCfgPortLctNEAddressAddrType          InetAddressType
    }
    
    -- 1.3.6.1.4.1.119.2.3.69.213.502.5.3.15.2.1.1
    ipeCfgPortLctIfIndex OBJECT-TYPE
        SYNTAX      InterfaceIndex
        ACCESS      not-accessible
        STATUS      mandatory
        DESCRIPTION
            "Index of table."
        ::= { ipeCfgPortLctEntry 1 }
    
    -- 1.3.6.1.4.1.119.2.3.69.213.502.5.3.15.2.1.2
    ipeCfgPortLctNEAddress OBJECT-TYPE
        SYNTAX      InetAddress
        ACCESS      not-accessible
        STATUS      mandatory
        DESCRIPTION
            ""
        ::= { ipeCfgPortLctEntry 2 }
    
    -- 1.3.6.1.4.1.119.2.3.69.213.502.5.3.15.2.1.3
    ipeCfgPortLctIpAddress OBJECT-TYPE
        SYNTAX      IpAddress
        ACCESS      read-only
        STATUS      mandatory
        DESCRIPTION
            "IPaddress of LCT port.
             It makes an error of the Internet Protocol address setting that
             overlaps in the port in the device.
             The object port and the range of the value are described as
             follows.
             Object port: Lct, InbandMngVLAN1-16, Bridge1-Bridge20, NE2
             Value range:0x00000000-0xdfffffff(0.0.0.0-223.255.255.255)
             The relation is not in the state and the number of Branch of
             interfaces and the Internet Protocol address repetition check is
             checked.
    
             When 0.0.0.0 is set to ipeCfgPortLctIpAddress, it becomes an
             Internet Protocol address deletion."
        ::= { ipeCfgPortLctEntry 3 }
    
    -- 1.3.6.1.4.1.119.2.3.69.213.502.5.3.15.2.1.4
    ipeCfgPortLctNetMask OBJECT-TYPE
        SYNTAX      IpAddress
        ACCESS      read-only
        STATUS      mandatory
        DESCRIPTION
            "Subnet mask of LCT port.
             When it isn't proper as subnetmask, it'll be an error.
             Value range:0x00000000-0xfffffffc(0-30bit)"
        ::= { ipeCfgPortLctEntry 4 }
    
    -- 1.3.6.1.4.1.119.2.3.69.213.502.5.3.15.2.1.5
    ipeCfgPortLctEnable OBJECT-TYPE
        SYNTAX      INTEGER { enabled(1), disabled(2) }
        ACCESS      read-only
        STATUS      mandatory
        DESCRIPTION
            "Effective/invalid setting of LCT port.
             value range: enabled
                         disabled"
        ::= { ipeCfgPortLctEntry 5 }
    
    -- 1.3.6.1.4.1.119.2.3.69.213.502.5.3.15.2.1.6
    ipeCfgPortLctMtu OBJECT-TYPE
        SYNTAX      INTEGER (256..1500)
        ACCESS      read-only
        STATUS      mandatory
        DESCRIPTION
            "MTU value of LCT.
             value range:256 to 1500"
        ::= { ipeCfgPortLctEntry 6 }
    
    -- 1.3.6.1.4.1.119.2.3.69.213.502.5.3.15.2.1.7
    ipeCfgPortLctAutoNeg OBJECT-TYPE
        SYNTAX      INTEGER { enabled(1), disabled(2) }
        ACCESS      read-only
        STATUS      mandatory
        DESCRIPTION
            "Effective/invalid setting of LCT AUTO NEGOTIATION.
             value range: enabled
                         disabled"
        ::= { ipeCfgPortLctEntry 7 }
    
    -- 1.3.6.1.4.1.119.2.3.69.213.502.5.3.15.2.1.8
    ipeCfgPortLctLinkLocalAddress OBJECT-TYPE
        SYNTAX      Ipv6Address
        ACCESS      read-only
        STATUS      mandatory
        DESCRIPTION
            "The IPv6 Link Local address of the LCT port."
        ::= { ipeCfgPortLctEntry 8 }
    
    -- 1.3.6.1.4.1.119.2.3.69.213.502.5.3.15.2.1.9
    ipeCfgPortLctLinkLocalAddressOrigin OBJECT-TYPE
        SYNTAX      INTEGER { invalid(0), manual(1), linklayer(2) }
        ACCESS      read-only
        STATUS      mandatory
        DESCRIPTION
            "The origin of the address.
             manual(1) indicates that the address was manually
                    configured to a specified address, e.g., by user
                    configuration.
    
             linklayer(2) indicates the address to be created
                       by IPv6 stateless address auto-configuration."
        DEFVAL      { manual }
        ::= { ipeCfgPortLctEntry 9 }
    
    -- 1.3.6.1.4.1.119.2.3.69.213.502.5.3.15.2.1.10
    ipeCfgPortLctHttpReverseProxyEnable OBJECT-TYPE
        SYNTAX      EnableDisableValue
        ACCESS      read-only
        STATUS      mandatory
        DESCRIPTION
            "Enables or disables HTTP/HTTPS Reverse proxy on this interface."
        DEFVAL      { enable }
        ::= { ipeCfgPortLctEntry 10 }
    
    -- 1.3.6.1.4.1.119.2.3.69.213.502.5.3.15.2.1.1001
    ipeCfgPortLctNEAddressAddrType OBJECT-TYPE
        SYNTAX      InetAddressType
        ACCESS      not-accessible
        STATUS      mandatory
        DESCRIPTION
            "Represents the IP address type of NE address index.
             Only ipv4(1) and ipv6(2) are supported."
        ::= { ipeCfgPortLctEntry 1001 }
    
    -- 1.3.6.1.4.1.119.2.3.69.213.502.5.3.15.3
    ipeCfgPortEtherTable OBJECT-TYPE
        SYNTAX      SEQUENCE OF IpeCfgPortEtherEntry
        ACCESS      not-accessible
        STATUS      mandatory
        DESCRIPTION
            "NMS/NE1 port set up information table."
        ::= { ipeCfgPortGroup 3 }
    
    -- 1.3.6.1.4.1.119.2.3.69.213.502.5.3.15.3.1
    ipeCfgPortEtherEntry OBJECT-TYPE
        SYNTAX      IpeCfgPortEtherEntry
        ACCESS      not-accessible
        STATUS      mandatory
        DESCRIPTION
            "entry of  NMS/NE1 port set up information table."
        INDEX       { ipeCfgPortEtherNEAddressAddrType, ipeCfgPortEtherNEAddress, ipeCfgPortEtherIfIndex }
        ::= { ipeCfgPortEtherTable 1 }
    
    IpeCfgPortEtherEntry ::= SEQUENCE {
        ipeCfgPortEtherIfIndex              InterfaceIndex,
        ipeCfgPortEtherNEAddress            InetAddress,
        ipeCfgPortEtherEnable               INTEGER,
        ipeCfgPortEtherAutoNeg              INTEGER,
        ipeCfgPortEtherSpecialFilter        INTEGER,
        ipeCfgPortEtherLldpMode             INTEGER,
        ipeCfgPortEtherVlanPortType         INTEGER,
        ipeCfgPortEtherNEAddressAddrType    InetAddressType
    }
    
    -- 1.3.6.1.4.1.119.2.3.69.213.502.5.3.15.3.1.1
    ipeCfgPortEtherIfIndex OBJECT-TYPE
        SYNTAX      InterfaceIndex
        ACCESS      not-accessible
        STATUS      mandatory
        DESCRIPTION
            "Index of table."
        ::= { ipeCfgPortEtherEntry 1 }
    
    -- 1.3.6.1.4.1.119.2.3.69.213.502.5.3.15.3.1.2
    ipeCfgPortEtherNEAddress OBJECT-TYPE
        SYNTAX      InetAddress
        ACCESS      not-accessible
        STATUS      mandatory
        DESCRIPTION
            ""
        ::= { ipeCfgPortEtherEntry 2 }
    
    -- 1.3.6.1.4.1.119.2.3.69.213.502.5.3.15.3.1.3
    ipeCfgPortEtherEnable OBJECT-TYPE
        SYNTAX      INTEGER { enabled(1), disabled(2) }
        ACCESS      read-only
        STATUS      mandatory
        DESCRIPTION
            "Effective/invalid setting of NMS/NE1 port.
             value range: enabled(1)
                         disabled(2)
             default value is 'enabled'.(iPASOLINK EX Advanced)"
        DEFVAL      { enabled }
        ::= { ipeCfgPortEtherEntry 3 }
    
    -- 1.3.6.1.4.1.119.2.3.69.213.502.5.3.15.3.1.4
    ipeCfgPortEtherAutoNeg OBJECT-TYPE
        SYNTAX      INTEGER { enabled(1), disabled(2) }
        ACCESS      read-only
        STATUS      mandatory
        DESCRIPTION
            "Auto negotiation invalid effective/setting of NMS/NE1 port.
             value range: enabled(1)
                         disabled(2)"
        ::= { ipeCfgPortEtherEntry 4 }
    
    -- 1.3.6.1.4.1.119.2.3.69.213.502.5.3.15.3.1.5
    ipeCfgPortEtherSpecialFilter OBJECT-TYPE
        SYNTAX      INTEGER { true(1), false(2) }
        ACCESS      read-only
        STATUS      mandatory
        DESCRIPTION
            "Setting of whether a special broadcast packet is blocked."
        ::= { ipeCfgPortEtherEntry 5 }
    
    -- 1.3.6.1.4.1.119.2.3.69.213.502.5.3.15.3.1.6
    ipeCfgPortEtherLldpMode OBJECT-TYPE
        SYNTAX      INTEGER { invalid(0), standardMode(1),
                        proprietaryMode(2) }
        ACCESS      read-only
        STATUS      mandatory
        DESCRIPTION
            "Switch to select MAC address of LLDP Frame.
    
             standardMode    : MAC address of LLDP Frame is
                               01-80-C2-00-00-0E.
             proprietaryMode : MAC address of LLDP Frame is configured in
                               ipeCfgLldpProprietaryModeMacAddress."
        DEFVAL      { standardMode }
        ::= { ipeCfgPortEtherEntry 6 }
    
    -- 1.3.6.1.4.1.119.2.3.69.213.502.5.3.15.3.1.7
    ipeCfgPortEtherVlanPortType OBJECT-TYPE
        SYNTAX      INTEGER { access(1), trunk(3) }
        ACCESS      read-only
        STATUS      mandatory
        DESCRIPTION
            "VLAN Port Type of NMS port.
             This value is not available (iPASOLINK EX Advanced)."
        ::= { ipeCfgPortEtherEntry 7 }
    
    -- 1.3.6.1.4.1.119.2.3.69.213.502.5.3.15.3.1.1001
    ipeCfgPortEtherNEAddressAddrType OBJECT-TYPE
        SYNTAX      InetAddressType
        ACCESS      not-accessible
        STATUS      mandatory
        DESCRIPTION
            "Represents the IP address type of NE address index.
             Only ipv4(1) and ipv6(2) are supported."
        ::= { ipeCfgPortEtherEntry 1001 }
    
    -- 1.3.6.1.4.1.119.2.3.69.213.502.5.3.15.4
    ipeCfgPortNe2Table OBJECT-TYPE
        SYNTAX      SEQUENCE OF IpeCfgPortNe2Entry
        ACCESS      not-accessible
        STATUS      mandatory
        DESCRIPTION
            "NE2 port set up information table."
        ::= { ipeCfgPortGroup 4 }
    
    -- 1.3.6.1.4.1.119.2.3.69.213.502.5.3.15.4.1
    ipeCfgPortNe2Entry OBJECT-TYPE
        SYNTAX      IpeCfgPortNe2Entry
        ACCESS      not-accessible
        STATUS      mandatory
        DESCRIPTION
            "entry of NE2 port set up information table."
        INDEX       { ipeCfgPortNe2NEAddressAddrType, ipeCfgPortNe2NEAddress, ipeCfgPortNe2IfIndex }
        ::= { ipeCfgPortNe2Table 1 }
    
    IpeCfgPortNe2Entry ::= SEQUENCE {
        ipeCfgPortNe2IfIndex            InterfaceIndex,
        ipeCfgPortNe2NEAddress          InetAddress,
        ipeCfgPortNe2IpAddress          IpAddress,
        ipeCfgPortNe2Enable             INTEGER,
        ipeCfgPortNe2Speed              INTEGER,
        ipeCfgPortNe2NeighborMibEnable  INTEGER,
        ipeCfgPortNe2NEAddressAddrType  InetAddressType
    }
    
    -- 1.3.6.1.4.1.119.2.3.69.213.502.5.3.15.4.1.1
    ipeCfgPortNe2IfIndex OBJECT-TYPE
        SYNTAX      InterfaceIndex
        ACCESS      not-accessible
        STATUS      mandatory
        DESCRIPTION
            "Index of table."
        ::= { ipeCfgPortNe2Entry 1 }
    
    -- 1.3.6.1.4.1.119.2.3.69.213.502.5.3.15.4.1.2
    ipeCfgPortNe2NEAddress OBJECT-TYPE
        SYNTAX      InetAddress
        ACCESS      not-accessible
        STATUS      mandatory
        DESCRIPTION
            ""
        ::= { ipeCfgPortNe2Entry 2 }
    
    -- 1.3.6.1.4.1.119.2.3.69.213.502.5.3.15.4.1.3
    ipeCfgPortNe2IpAddress OBJECT-TYPE
        SYNTAX      IpAddress
        ACCESS      read-only
        STATUS      mandatory
        DESCRIPTION
            "NE2 port IP Address.
             value range:0x00000000 - 0xdfffffff(0.0.0.0 - 223.255.255.255)
             The ppp function is restarted when setting it."
        ::= { ipeCfgPortNe2Entry 3 }
    
    -- 1.3.6.1.4.1.119.2.3.69.213.502.5.3.15.4.1.4
    ipeCfgPortNe2Enable OBJECT-TYPE
        SYNTAX      INTEGER { enabled(1), disabled(2) }
        ACCESS      read-only
        STATUS      mandatory
        DESCRIPTION
            "NE2 port enable.
             value range:enabled(1)
                         disabled(2)"
        ::= { ipeCfgPortNe2Entry 4 }
    
    -- 1.3.6.1.4.1.119.2.3.69.213.502.5.3.15.4.1.5
    ipeCfgPortNe2Speed OBJECT-TYPE
        SYNTAX      INTEGER { speed9600(9600), speed19200(19200) }
        ACCESS      read-only
        STATUS      mandatory
        DESCRIPTION
            "NE2 port baud rate.
             value range:9600bps(9600)
                         19200bps(19200)
             The ppp function is restarted when setting it."
        ::= { ipeCfgPortNe2Entry 5 }
    
    -- 1.3.6.1.4.1.119.2.3.69.213.502.5.3.15.4.1.6
    ipeCfgPortNe2NeighborMibEnable OBJECT-TYPE
        SYNTAX      INTEGER { enabled(1), disabled(2) }
        ACCESS      read-only
        STATUS      mandatory
        DESCRIPTION
            "NE2 port neighbor detection enable.
             value range:enabled(1)
                         disabled(2)
             The ppp function is restarted when setting it."
        ::= { ipeCfgPortNe2Entry 6 }
    
    -- 1.3.6.1.4.1.119.2.3.69.213.502.5.3.15.4.1.1001
    ipeCfgPortNe2NEAddressAddrType OBJECT-TYPE
        SYNTAX      InetAddressType
        ACCESS      not-accessible
        STATUS      mandatory
        DESCRIPTION
            "Represents the IP address type of NE address index.
             Only ipv4(1) and ipv6(2) are supported."
        ::= { ipeCfgPortNe2Entry 1001 }
    
    -- 1.3.6.1.4.1.119.2.3.69.213.502.5.3.15.5
    ipeCfgPortE1Table OBJECT-TYPE
        SYNTAX      SEQUENCE OF IpeCfgPortE1Entry
        ACCESS      not-accessible
        STATUS      mandatory
        DESCRIPTION
            "E1 port set up information table."
        ::= { ipeCfgPortGroup 5 }
    
    -- 1.3.6.1.4.1.119.2.3.69.213.502.5.3.15.5.1
    ipeCfgPortE1Entry OBJECT-TYPE
        SYNTAX      IpeCfgPortE1Entry
        ACCESS      not-accessible
        STATUS      mandatory
        DESCRIPTION
            "entry of  E1 port set up information table."
        INDEX       { ipeCfgPortE1NEAddressAddrType, ipeCfgPortE1NEAddress, ipeCfgPortE1IfIndex }
        ::= { ipeCfgPortE1Table 1 }
    
    IpeCfgPortE1Entry ::= SEQUENCE {
        ipeCfgPortE1IfIndex             InterfaceIndex,
        ipeCfgPortE1NEAddress           InetAddress,
        ipeCfgPortE1Enable              INTEGER,
        ipeCfgPortE1ChannelNumber       INTEGER,
        ipeCfgPortE1NEAddressAddrType   InetAddressType
    }
    
    -- 1.3.6.1.4.1.119.2.3.69.213.502.5.3.15.5.1.1
    ipeCfgPortE1IfIndex OBJECT-TYPE
        SYNTAX      InterfaceIndex
        ACCESS      not-accessible
        STATUS      mandatory
        DESCRIPTION
            "Index of table."
        ::= { ipeCfgPortE1Entry 1 }
    
    -- 1.3.6.1.4.1.119.2.3.69.213.502.5.3.15.5.1.2
    ipeCfgPortE1NEAddress OBJECT-TYPE
        SYNTAX      InetAddress
        ACCESS      not-accessible
        STATUS      mandatory
        DESCRIPTION
            ""
        ::= { ipeCfgPortE1Entry 2 }
    
    -- 1.3.6.1.4.1.119.2.3.69.213.502.5.3.15.5.1.3
    ipeCfgPortE1Enable OBJECT-TYPE
        SYNTAX      INTEGER { enabled(1), disabled(2) }
        ACCESS      read-only
        STATUS      mandatory
        DESCRIPTION
            "Effective/invalid setting of E1 port.
             value range: enabled(1)
                         disabled(2)"
        ::= { ipeCfgPortE1Entry 3 }
    
    -- 1.3.6.1.4.1.119.2.3.69.213.502.5.3.15.5.1.4
    ipeCfgPortE1ChannelNumber OBJECT-TYPE
        SYNTAX      INTEGER (1..16)
        ACCESS      read-only
        STATUS      mandatory
        DESCRIPTION
            "Use channel of E1 port.
             value range:1 to 16"
        ::= { ipeCfgPortE1Entry 4 }
    
    -- 1.3.6.1.4.1.119.2.3.69.213.502.5.3.15.5.1.1001
    ipeCfgPortE1NEAddressAddrType OBJECT-TYPE
        SYNTAX      InetAddressType
        ACCESS      not-accessible
        STATUS      mandatory
        DESCRIPTION
            "Represents the IP address type of NE address index.
             Only ipv4(1) and ipv6(2) are supported."
        ::= { ipeCfgPortE1Entry 1001 }
    
    -- 1.3.6.1.4.1.119.2.3.69.213.502.5.3.15.6
    ipeCfgPortInbandTable OBJECT-TYPE
        SYNTAX      SEQUENCE OF IpeCfgPortInbandEntry
        ACCESS      not-accessible
        STATUS      mandatory
        DESCRIPTION
            "InBand Management VLAN port set up information table."
        ::= { ipeCfgPortGroup 6 }
    
    -- 1.3.6.1.4.1.119.2.3.69.213.502.5.3.15.6.1
    ipeCfgPortInbandEntry OBJECT-TYPE
        SYNTAX      IpeCfgPortInbandEntry
        ACCESS      not-accessible
        STATUS      mandatory
        DESCRIPTION
            "entry of  INBAND Management VLAN port set up information table."
        INDEX       { ipeCfgPortInbandNEAddressAddrType, ipeCfgPortInbandNEAddress, ipeCfgPortInbandIfIndex }
        ::= { ipeCfgPortInbandTable 1 }
    
    IpeCfgPortInbandEntry ::= SEQUENCE {
        ipeCfgPortInbandIfIndex             InterfaceIndex,
        ipeCfgPortInbandNEAddress           InetAddress,
        ipeCfgPortInbandIpAddress           IpAddress,
        ipeCfgPortInbandNetMask             IpAddress,
        ipeCfgPortInbandEnable              INTEGER,
        ipeCfgPortInbandVlanId              INTEGER,
        ipeCfgPortInbandMtu                 INTEGER,
        ipeCfgPortInbandCos                 INTEGER,
        ipeCfgPortInbandSVlanId             INTEGER,
        ipeCfgPortInbandNEAddressAddrType   InetAddressType
    }
    
    -- 1.3.6.1.4.1.119.2.3.69.213.502.5.3.15.6.1.1
    ipeCfgPortInbandIfIndex OBJECT-TYPE
        SYNTAX      InterfaceIndex
        ACCESS      not-accessible
        STATUS      mandatory
        DESCRIPTION
            "Index of table."
        ::= { ipeCfgPortInbandEntry 1 }
    
    -- 1.3.6.1.4.1.119.2.3.69.213.502.5.3.15.6.1.2
    ipeCfgPortInbandNEAddress OBJECT-TYPE
        SYNTAX      InetAddress
        ACCESS      not-accessible
        STATUS      mandatory
        DESCRIPTION
            ""
        ::= { ipeCfgPortInbandEntry 2 }
    
    -- 1.3.6.1.4.1.119.2.3.69.213.502.5.3.15.6.1.3
    ipeCfgPortInbandIpAddress OBJECT-TYPE
        SYNTAX      IpAddress
        ACCESS      read-only
        STATUS      obsolete
        DESCRIPTION
            "IPaddress of INBAND Management VLAN port.
             It makes an error of the Internet Protocol address setting that
             overlaps in the port in the device.
             The object port and the range of the value are described as
             follows.
             Object port: Lct, InbandMngVLAN1-16, Bridge1-20, NE2
             Value range: 0x00000000 - 0xdfffffff(0.0.0.0 - 223.255.255.255)
             The relation is not in the state and the number of Branch of
             interfaces and the Internet Protocol address repetition check is
             checked.
    
             When 0.0.0.0 is set to ipeCfgPortInbandIpAddress, it becomes an
             Internet Protocol address deletion."
        ::= { ipeCfgPortInbandEntry 3 }
    
    -- 1.3.6.1.4.1.119.2.3.69.213.502.5.3.15.6.1.4
    ipeCfgPortInbandNetMask OBJECT-TYPE
        SYNTAX      IpAddress
        ACCESS      read-only
        STATUS      obsolete
        DESCRIPTION
            "Subnet mask of INBAND Management VLAN port.
             When it isn't proper as subnetmask, it'll be an error.
             Value range:0x00000000 - 0xfffffffc(0 - 30bit)"
        ::= { ipeCfgPortInbandEntry 4 }
    
    -- 1.3.6.1.4.1.119.2.3.69.213.502.5.3.15.6.1.5
    ipeCfgPortInbandEnable OBJECT-TYPE
        SYNTAX      INTEGER { enabled(1), disabled(2) }
        ACCESS      read-only
        STATUS      mandatory
        DESCRIPTION
            "Effective/invalid setting of INBAND Management VLAN port.
             value range: enabled(1)
                         disabled(2)"
        ::= { ipeCfgPortInbandEntry 5 }
    
    -- 1.3.6.1.4.1.119.2.3.69.213.502.5.3.15.6.1.6
    ipeCfgPortInbandVlanId OBJECT-TYPE
        SYNTAX      INTEGER (1..4094)
        ACCESS      read-only
        STATUS      mandatory
        DESCRIPTION
            "VLAN ID of INBAND Management VLAN port.
             value range:1 to 4094"
        ::= { ipeCfgPortInbandEntry 6 }
    
    -- 1.3.6.1.4.1.119.2.3.69.213.502.5.3.15.6.1.7
    ipeCfgPortInbandMtu OBJECT-TYPE
        SYNTAX      INTEGER (256..1500)
        ACCESS      read-only
        STATUS      obsolete
        DESCRIPTION
            "MTU value of INBAND Management VLAN port.
             value range:256 to 1500"
        ::= { ipeCfgPortInbandEntry 7 }
    
    -- 1.3.6.1.4.1.119.2.3.69.213.502.5.3.15.6.1.8
    ipeCfgPortInbandCos OBJECT-TYPE
        SYNTAX      INTEGER (0..7)
        ACCESS      read-only
        STATUS      mandatory
        DESCRIPTION
            "CoS value of INBAND Management VLAN port"
        DEFVAL      { 7 }
        ::= { ipeCfgPortInbandEntry 8 }
    
    -- 1.3.6.1.4.1.119.2.3.69.213.502.5.3.15.6.1.9
    ipeCfgPortInbandSVlanId OBJECT-TYPE
        SYNTAX      INTEGER (1..4094)
        ACCESS      read-only
        STATUS      mandatory
        DESCRIPTION
            "Service VLAN ID of INBAND Management VLAN port.
             value range: 1 to 4094"
        ::= { ipeCfgPortInbandEntry 9 }
    
    -- 1.3.6.1.4.1.119.2.3.69.213.502.5.3.15.6.1.1001
    ipeCfgPortInbandNEAddressAddrType OBJECT-TYPE
        SYNTAX      InetAddressType
        ACCESS      not-accessible
        STATUS      mandatory
        DESCRIPTION
            "Represents the IP address type of NE address index.
             Only ipv4(1) and ipv6(2) are supported."
        ::= { ipeCfgPortInbandEntry 1001 }
    
    -- 1.3.6.1.4.1.119.2.3.69.213.502.5.3.15.7
    ipeCfgPortMainEtherTable OBJECT-TYPE
        SYNTAX      SEQUENCE OF IpeCfgPortMainEtherEntry
        ACCESS      not-accessible
        STATUS      mandatory
        DESCRIPTION
            "Main traffic ether port set up information table."
        ::= { ipeCfgPortGroup 7 }
    
    -- 1.3.6.1.4.1.119.2.3.69.213.502.5.3.15.7.1
    ipeCfgPortMainEtherEntry OBJECT-TYPE
        SYNTAX      IpeCfgPortMainEtherEntry
        ACCESS      not-accessible
        STATUS      mandatory
        DESCRIPTION
            "entry of main traffic ether port set up information table."
        INDEX       { ipeCfgPortMainEtherNEAddressAddrType, ipeCfgPortMainEtherNEAddress, ipeCfgPortMainEtherIfIndex }
        ::= { ipeCfgPortMainEtherTable 1 }
    
    IpeCfgPortMainEtherEntry ::= SEQUENCE {
        ipeCfgPortMainEtherIfIndex              InterfaceIndex,
        ipeCfgPortMainEtherNEAddress            InetAddress,
        ipeCfgPortMainEtherLldpMode             INTEGER,
        ipeCfgPortMainEtherNEAddressAddrType    InetAddressType
    }
    
    -- 1.3.6.1.4.1.119.2.3.69.213.502.5.3.15.7.1.1
    ipeCfgPortMainEtherIfIndex OBJECT-TYPE
        SYNTAX      InterfaceIndex
        ACCESS      not-accessible
        STATUS      mandatory
        DESCRIPTION
            "Index of table.
             Ifindex of main traffic ether port."
        ::= { ipeCfgPortMainEtherEntry 1 }
    
    -- 1.3.6.1.4.1.119.2.3.69.213.502.5.3.15.7.1.2
    ipeCfgPortMainEtherNEAddress OBJECT-TYPE
        SYNTAX      InetAddress
        ACCESS      not-accessible
        STATUS      mandatory
        DESCRIPTION
            "reserved."
        ::= { ipeCfgPortMainEtherEntry 2 }
    
    -- 1.3.6.1.4.1.119.2.3.69.213.502.5.3.15.7.1.3
    ipeCfgPortMainEtherLldpMode OBJECT-TYPE
        SYNTAX      INTEGER { invalid(0), standardMode(1),
                        proprietaryMode(2) }
        ACCESS      read-only
        STATUS      mandatory
        DESCRIPTION
            "Switch to select MAC address of LLDP Frame.
    
             standardMode    : MAC address of LLDP Frame is 01-80-C2-00-00-0E.
             proprietaryMode : MAC address of LLDP Frame is configured in
                               ipeCfgLldpProprietaryModeMacAddress."
        DEFVAL      { standardMode }
        ::= { ipeCfgPortMainEtherEntry 3 }
    
    -- 1.3.6.1.4.1.119.2.3.69.213.502.5.3.15.7.1.1001
    ipeCfgPortMainEtherNEAddressAddrType OBJECT-TYPE
        SYNTAX      InetAddressType
        ACCESS      not-accessible
        STATUS      mandatory
        DESCRIPTION
            "Represents the IP address type of NE address index.
             Only ipv4(1) and ipv6(2) are supported."
        ::= { ipeCfgPortMainEtherEntry 1001 }
    
    -- 1.3.6.1.4.1.119.2.3.69.213.502.5.3.15.9
    ipeCfgPortNMSVlanTable OBJECT-TYPE
        SYNTAX      SEQUENCE OF IpeCfgPortNMSVlanEntry
        ACCESS      not-accessible
        STATUS      mandatory
        DESCRIPTION
            "NMS VLAN port set up information table."
        ::= { ipeCfgPortGroup 9 }
    
    -- 1.3.6.1.4.1.119.2.3.69.213.502.5.3.15.9.1
    ipeCfgPortNMSVlanEntry OBJECT-TYPE
        SYNTAX      IpeCfgPortNMSVlanEntry
        ACCESS      not-accessible
        STATUS      mandatory
        DESCRIPTION
            "entry of NMS VLAN port set up information table."
        INDEX       { ipeCfgPortNMSVlanNEAddressAddrType, ipeCfgPortNMSVlanNEAddress, ipeCfgPortNMSVlanIfIndex }
        ::= { ipeCfgPortNMSVlanTable 1 }
    
    IpeCfgPortNMSVlanEntry ::= SEQUENCE {
        ipeCfgPortNMSVlanIfIndex            InterfaceIndex,
        ipeCfgPortNMSVlanNEAddress          InetAddress,
        ipeCfgPortNMSVlanIpAddress          IpAddress,
        ipeCfgPortNMSVlanNetMask            IpAddress,
        ipeCfgPortNMSVlanEnable             EnableDisableValue,
        ipeCfgPortNMSVlanVlanId             INTEGER,
        ipeCfgPortNMSVlanCos                INTEGER,
        ipeCfgPortNMSVlanNEAddressAddrType  InetAddressType
    }
    
    -- 1.3.6.1.4.1.119.2.3.69.213.502.5.3.15.9.1.1
    ipeCfgPortNMSVlanIfIndex OBJECT-TYPE
        SYNTAX      InterfaceIndex
        ACCESS      not-accessible
        STATUS      mandatory
        DESCRIPTION
            "Index of table."
        ::= { ipeCfgPortNMSVlanEntry 1 }
    
    -- 1.3.6.1.4.1.119.2.3.69.213.502.5.3.15.9.1.2
    ipeCfgPortNMSVlanNEAddress OBJECT-TYPE
        SYNTAX      InetAddress
        ACCESS      not-accessible
        STATUS      mandatory
        DESCRIPTION
            ""
        ::= { ipeCfgPortNMSVlanEntry 2 }
    
    -- 1.3.6.1.4.1.119.2.3.69.213.502.5.3.15.9.1.3
    ipeCfgPortNMSVlanIpAddress OBJECT-TYPE
        SYNTAX      IpAddress
        ACCESS      read-only
        STATUS      obsolete
        DESCRIPTION
            "reserved. (IPaddress of NMS VLAN port.
             It makes an error of the Internet Protocol address setting that
             overlaps in the port in the device.
             The object port and the range of the value are described as
             follows.
             Object port: Lct, NMSMngVLAN1-16, Bridge1 )"
        ::= { ipeCfgPortNMSVlanEntry 3 }
    
    -- 1.3.6.1.4.1.119.2.3.69.213.502.5.3.15.9.1.4
    ipeCfgPortNMSVlanNetMask OBJECT-TYPE
        SYNTAX      IpAddress
        ACCESS      read-only
        STATUS      obsolete
        DESCRIPTION
            "Reserved. (Subnet mask of NMS VLAN port.
             When it isn't proper as subnetmask, it'll be an error.
             Value range:0x00000000 - 0xfffffffc(0 - 30bit) )"
        ::= { ipeCfgPortNMSVlanEntry 4 }
    
    -- 1.3.6.1.4.1.119.2.3.69.213.502.5.3.15.9.1.5
    ipeCfgPortNMSVlanEnable OBJECT-TYPE
        SYNTAX      EnableDisableValue
        ACCESS      read-only
        STATUS      mandatory
        DESCRIPTION
            "NMS VLAN port setting.
             This value is not available (iPASOLINK EX Advanced)."
        DEFVAL      { disable }
        ::= { ipeCfgPortNMSVlanEntry 5 }
    
    -- 1.3.6.1.4.1.119.2.3.69.213.502.5.3.15.9.1.6
    ipeCfgPortNMSVlanVlanId OBJECT-TYPE
        SYNTAX      INTEGER (2..4094)
        ACCESS      read-only
        STATUS      mandatory
        DESCRIPTION
            "VLAN ID of NMS VLAN port.
             value range: 2 to 4094
             This value is not available (iPASOLINK EX Advanced)."
        DEFVAL      { 4094 }
        ::= { ipeCfgPortNMSVlanEntry 6 }
    
    -- 1.3.6.1.4.1.119.2.3.69.213.502.5.3.15.9.1.7
    ipeCfgPortNMSVlanCos OBJECT-TYPE
        SYNTAX      INTEGER (0..7)
        ACCESS      read-only
        STATUS      mandatory
        DESCRIPTION
            "CoS value of NMS VLAN port
             This value is not available (iPASOLINK EX Advanced)."
        DEFVAL      { 7 }
        ::= { ipeCfgPortNMSVlanEntry 7 }
    
    -- 1.3.6.1.4.1.119.2.3.69.213.502.5.3.15.9.1.1001
    ipeCfgPortNMSVlanNEAddressAddrType OBJECT-TYPE
        SYNTAX      InetAddressType
        ACCESS      not-accessible
        STATUS      mandatory
        DESCRIPTION
            "Represents the IP address type of NE address index.
             Only ipv4(1) and ipv6(2) are supported."
        ::= { ipeCfgPortNMSVlanEntry 1001 }
    
    -- 1.3.6.1.4.1.119.2.3.69.213.502.5.3.16
    ipeCfgBridgeGroup OBJECT IDENTIFIER
        ::= { ipeConfigurationGroup 16 }
    
    -- 1.3.6.1.4.1.119.2.3.69.213.502.5.3.16.1
    ipeCfgBridgeTable OBJECT-TYPE
        SYNTAX      SEQUENCE OF IpeCfgBridgeEntry
        ACCESS      not-accessible
        STATUS      mandatory
        DESCRIPTION
            "Bridge set up information table."
        ::= { ipeCfgBridgeGroup 1 }
    
    -- 1.3.6.1.4.1.119.2.3.69.213.502.5.3.16.1.1
    ipeCfgBridgeEntry OBJECT-TYPE
        SYNTAX      IpeCfgBridgeEntry
        ACCESS      not-accessible
        STATUS      mandatory
        DESCRIPTION
            "entry of  Bridge set up information table."
        INDEX       { ipeCfgBridgeNEAddressAddrType, ipeCfgBridgeNEAddress, ipeCfgBridgeIndex }
        ::= { ipeCfgBridgeTable 1 }
    
    IpeCfgBridgeEntry ::= SEQUENCE {
        ipeCfgBridgeIndex                       INTEGER,
        ipeCfgBridgeNEAddress                   InetAddress,
        ipeCfgBridgeIpAddress                   IpAddress,
        ipeCfgBridgeNetMask                     IpAddress,
        ipeCfgBridgeMtu                         INTEGER,
        ipeCfgBridgeLinkLocalAddress            Ipv6Address,
        ipeCfgBridgeLinkLocalAddressOrigin      INTEGER,
        ipeCfgBridgeGlobalAddress               Ipv6Address,
        ipeCfgBridgeGlobalAddressOrigin         INTEGER,
        ipeCfgBridgeGlobalAddressPrefixLength   InetAddressPrefixLength,
        ipeCfgBridgeIpStackMode                 INTEGER,
        ipeCfgBridgeSendRouterAdvertisement     INTEGER,
        ipeCfgBridgeRADefaultLifeTime           INTEGER,
        ipeCfgBridgeReceiveIcmpRedirects        INTEGER,
        ipeCfgBridgeNEAddressAddrType           InetAddressType
    }
    
    -- 1.3.6.1.4.1.119.2.3.69.213.502.5.3.16.1.1.1
    ipeCfgBridgeIndex OBJECT-TYPE
        SYNTAX      INTEGER (1..20)
        ACCESS      not-accessible
        STATUS      mandatory
        DESCRIPTION
            "Index of table."
        ::= { ipeCfgBridgeEntry 1 }
    
    -- 1.3.6.1.4.1.119.2.3.69.213.502.5.3.16.1.1.2
    ipeCfgBridgeNEAddress OBJECT-TYPE
        SYNTAX      InetAddress
        ACCESS      not-accessible
        STATUS      mandatory
        DESCRIPTION
            ""
        ::= { ipeCfgBridgeEntry 2 }
    
    -- 1.3.6.1.4.1.119.2.3.69.213.502.5.3.16.1.1.3
    ipeCfgBridgeIpAddress OBJECT-TYPE
        SYNTAX      IpAddress
        ACCESS      read-only
        STATUS      mandatory
        DESCRIPTION
            "IPAddress set to bridge.
             Value range:0x00000000 - 0xdfffffff(0.0.0.0 - 223.255.255.255)
    
             It makes an error of the Internet Protocol address setting that
             overlaps in the port in the device.
             It becomes the following about the port of the Internet Protocol
             address repetition check object.
             Object port: Lct, InbandMngVLAN1-16, Bridge1-Bridge20, NE2
             The relation is not in the state and the number of Branch of
             interfaces and the Internet Protocol address repetition check is
             checked.
    
             There can not be relation and it sets, and it refer the number of
             branch.
             When 0.0.0.0 is set to ipeCfgBridgeIpAddress, it becomes an
             Internet Protocol address deletion."
        ::= { ipeCfgBridgeEntry 3 }
    
    -- 1.3.6.1.4.1.119.2.3.69.213.502.5.3.16.1.1.4
    ipeCfgBridgeNetMask OBJECT-TYPE
        SYNTAX      IpAddress
        ACCESS      read-only
        STATUS      mandatory
        DESCRIPTION
            "Netmask set to bridge.
             When it isn't proper as subnetmask, it'll be an error.
             Value range:0x00000000 - 0xfffffffc(0 - 30bit)
    
             There can not be relation and it sets, and it refer the number of
             branch."
        ::= { ipeCfgBridgeEntry 4 }
    
    -- 1.3.6.1.4.1.119.2.3.69.213.502.5.3.16.1.1.5
    ipeCfgBridgeMtu OBJECT-TYPE
        SYNTAX      INTEGER (256..1500)
        ACCESS      read-only
        STATUS      mandatory
        DESCRIPTION
            "MTU value of bridge.
             value range:256 to 1500
    
             There can not be relation and it sets, and it refer the number of
             branch."
        ::= { ipeCfgBridgeEntry 5 }
    
    -- 1.3.6.1.4.1.119.2.3.69.213.502.5.3.16.1.1.6
    ipeCfgBridgeLinkLocalAddress OBJECT-TYPE
        SYNTAX      Ipv6Address
        ACCESS      read-only
        STATUS      mandatory
        DESCRIPTION
            "IPv6 Link-local Address set to bridge."
        ::= { ipeCfgBridgeEntry 6 }
    
    -- 1.3.6.1.4.1.119.2.3.69.213.502.5.3.16.1.1.7
    ipeCfgBridgeLinkLocalAddressOrigin OBJECT-TYPE
        SYNTAX      INTEGER { invalid(0), manual(1), linklayer(2) }
        ACCESS      read-only
        STATUS      mandatory
        DESCRIPTION
            "The origin of the address.
             manual(1) indicates that the address was manually
             configured to a specified address, e.g., by user
             configuration.
    
             linklayer(2) indicates the address to be created
             by IPv6 stateless address auto-configuration."
        DEFVAL      { linklayer }
        ::= { ipeCfgBridgeEntry 7 }
    
    -- 1.3.6.1.4.1.119.2.3.69.213.502.5.3.16.1.1.8
    ipeCfgBridgeGlobalAddress OBJECT-TYPE
        SYNTAX      Ipv6Address
        ACCESS      read-only
        STATUS      mandatory
        DESCRIPTION
            "The IPv6 global address of this interface.
             The following are not valid addresses:
                ::1/128 IPv6 Loopback
                FE80::/10 Link local
                FF00::/8 IPv6 Multicasts"
        ::= { ipeCfgBridgeEntry 8 }
    
    -- 1.3.6.1.4.1.119.2.3.69.213.502.5.3.16.1.1.9
    ipeCfgBridgeGlobalAddressOrigin OBJECT-TYPE
        SYNTAX      INTEGER { invalid(0), manual(1), linklayer(4) }
        ACCESS      read-only
        STATUS      mandatory
        DESCRIPTION
            "The origin of the address.
             manual(1) indicates that the address was manually
                     configured to a specified address, e.g., by user
                     configuration.
    
             linklayer(4) indicates an address created based on the
                     prefix received from Router Advertisement and this
                     interface is considered as Host interface."
        DEFVAL      { linklayer }
        ::= { ipeCfgBridgeEntry 9 }
    
    -- 1.3.6.1.4.1.119.2.3.69.213.502.5.3.16.1.1.10
    ipeCfgBridgeGlobalAddressPrefixLength OBJECT-TYPE
        SYNTAX      InetAddressPrefixLength
        ACCESS      read-only
        STATUS      mandatory
        DESCRIPTION
            "The prefix length of Global Address."
        ::= { ipeCfgBridgeEntry 10 }
    
    -- 1.3.6.1.4.1.119.2.3.69.213.502.5.3.16.1.1.11
    ipeCfgBridgeIpStackMode OBJECT-TYPE
        SYNTAX      INTEGER { ipv4(1), ipv6(2), dual(3) }
        ACCESS      read-only
        STATUS      mandatory
        DESCRIPTION
            "Indicate IP Stack mode of this interface.
    
             ipv4 : Enable IPv4 support on this interface.
             ipv6 : Enable IPv6 support on this interface.
             dual : Enable IPv4 and IPv6 support on this interface.
    
             Note that ipeCfgBridgeIpStackMode: ipv4(1) and
             ipeSysIpv4DropFilterEnable: enable(2) cannot be set for the
             establishment of IPv4 communication."
        ::= { ipeCfgBridgeEntry 11 }
    
    -- 1.3.6.1.4.1.119.2.3.69.213.502.5.3.16.1.1.12
    ipeCfgBridgeSendRouterAdvertisement OBJECT-TYPE
        SYNTAX      INTEGER { invalid(0), true(1), false(2) }
        ACCESS      read-only
        STATUS      mandatory
        DESCRIPTION
            "A flag indicating whether the router sends periodic
             router advertisements and responds to router solicitations
             on this interface."
        ::= { ipeCfgBridgeEntry 12 }
    
    -- 1.3.6.1.4.1.119.2.3.69.213.502.5.3.16.1.1.13
    ipeCfgBridgeRADefaultLifeTime OBJECT-TYPE
        SYNTAX      INTEGER (0 | 600..9000)
        ACCESS      read-only
        STATUS      mandatory
        DESCRIPTION
            "The value to be placed in the router lifetime field of
             router advertisements sent from this interface.
             This value must be either 0 or between
             ipv6RouterAdvertMaxInterval and
             9000 seconds.
    
             A value of zero indicates that the router is not to be used
             as a default router.
    
             The default is 3 * ipv6RouterAdvertMaxInterval."
        ::= { ipeCfgBridgeEntry 13 }
    
    -- 1.3.6.1.4.1.119.2.3.69.213.502.5.3.16.1.1.14
    ipeCfgBridgeReceiveIcmpRedirects OBJECT-TYPE
        SYNTAX      INTEGER { invalid(0), true(1), false(2) }
        ACCESS      read-only
        STATUS      mandatory
        DESCRIPTION
            "The true/false value to process received ICMP Redirect
             messages from this bridge.
             For router, this object will always be false as router
             does not process Redirects."
        ::= { ipeCfgBridgeEntry 14 }
    
    -- 1.3.6.1.4.1.119.2.3.69.213.502.5.3.16.1.1.1001
    ipeCfgBridgeNEAddressAddrType OBJECT-TYPE
        SYNTAX      InetAddressType
        ACCESS      not-accessible
        STATUS      mandatory
        DESCRIPTION
            "Represents the IP address type of NE address index.
             Only ipv4(1) and ipv6(2) are supported."
        ::= { ipeCfgBridgeEntry 1001 }
    
    -- 1.3.6.1.4.1.119.2.3.69.213.502.5.3.16.2
    ipeCfgBridgePortTable OBJECT-TYPE
        SYNTAX      SEQUENCE OF IpeCfgBridgePortEntry
        ACCESS      not-accessible
        STATUS      mandatory
        DESCRIPTION
            "Bridge set up information table."
        ::= { ipeCfgBridgeGroup 2 }
    
    -- 1.3.6.1.4.1.119.2.3.69.213.502.5.3.16.2.1
    ipeCfgBridgePortEntry OBJECT-TYPE
        SYNTAX      IpeCfgBridgePortEntry
        ACCESS      not-accessible
        STATUS      mandatory
        DESCRIPTION
            "entry of  Bridge set up information table."
        INDEX       { ipeCfgBridgePortNEAddressAddrType, ipeCfgBridgePortNEAddress, ipeCfgBridgePortIfIndex }
        ::= { ipeCfgBridgePortTable 1 }
    
    IpeCfgBridgePortEntry ::= SEQUENCE {
        ipeCfgBridgePortIfIndex             InterfaceIndex,
        ipeCfgBridgePortNEAddress           InetAddress,
        ipeCfgBridgePortBridgeIndex         INTEGER,
        ipeCfgBridgePortNEAddressAddrType   InetAddressType
    }
    
    -- 1.3.6.1.4.1.119.2.3.69.213.502.5.3.16.2.1.1
    ipeCfgBridgePortIfIndex OBJECT-TYPE
        SYNTAX      InterfaceIndex
        ACCESS      not-accessible
        STATUS      mandatory
        DESCRIPTION
            "The interface identified by a particular value of this index is
             the same interface as identified by the same value of ifIndex.
             Valid Value(NMS,NE1,E1,RADIO00-10,InbandMngVLAN1-16)"
        ::= { ipeCfgBridgePortEntry 1 }
    
    -- 1.3.6.1.4.1.119.2.3.69.213.502.5.3.16.2.1.2
    ipeCfgBridgePortNEAddress OBJECT-TYPE
        SYNTAX      InetAddress
        ACCESS      not-accessible
        STATUS      mandatory
        DESCRIPTION
            ""
        ::= { ipeCfgBridgePortEntry 2 }
    
    -- 1.3.6.1.4.1.119.2.3.69.213.502.5.3.16.2.1.3
    ipeCfgBridgePortBridgeIndex OBJECT-TYPE
        SYNTAX      INTEGER (0..20)
        ACCESS      read-only
        STATUS      mandatory
        DESCRIPTION
            "Index value of bridge."
        ::= { ipeCfgBridgePortEntry 3 }
    
    -- 1.3.6.1.4.1.119.2.3.69.213.502.5.3.16.2.1.1001
    ipeCfgBridgePortNEAddressAddrType OBJECT-TYPE
        SYNTAX      InetAddressType
        ACCESS      not-accessible
        STATUS      mandatory
        DESCRIPTION
            "Represents the IP address type of NE address index.
             Only ipv4(1) and ipv6(2) are supported."
        ::= { ipeCfgBridgePortEntry 1001 }
    
    -- 1.3.6.1.4.1.119.2.3.69.213.502.5.3.16.3
    ipeCfgBridgeVlanTable OBJECT-TYPE
        SYNTAX      SEQUENCE OF IpeCfgBridgeVlanEntry
        ACCESS      not-accessible
        STATUS      mandatory
        DESCRIPTION
            "Bridge set up information table."
        ::= { ipeCfgBridgeGroup 3 }
    
    -- 1.3.6.1.4.1.119.2.3.69.213.502.5.3.16.3.1
    ipeCfgBridgeVlanEntry OBJECT-TYPE
        SYNTAX      IpeCfgBridgeVlanEntry
        ACCESS      not-accessible
        STATUS      mandatory
        DESCRIPTION
            "entry of  Bridge set up information table."
        INDEX       { ipeCfgBridgeVlanNEAddressAddrType, ipeCfgBridgeVlanNEAddress, ipeCfgBridgeVlanIndex }
        ::= { ipeCfgBridgeVlanTable 1 }
    
    IpeCfgBridgeVlanEntry ::= SEQUENCE {
        ipeCfgBridgeVlanIndex               INTEGER,
        ipeCfgBridgeVlanNEAddress           InetAddress,
        ipeCfgBridgeVlanVlanId              INTEGER,
        ipeCfgBridgeVlanNEAddressAddrType   InetAddressType
    }
    
    -- 1.3.6.1.4.1.119.2.3.69.213.502.5.3.16.3.1.1
    ipeCfgBridgeVlanIndex OBJECT-TYPE
        SYNTAX      INTEGER (1..20)
        ACCESS      not-accessible
        STATUS      mandatory
        DESCRIPTION
            "Index of table."
        ::= { ipeCfgBridgeVlanEntry 1 }
    
    -- 1.3.6.1.4.1.119.2.3.69.213.502.5.3.16.3.1.2
    ipeCfgBridgeVlanNEAddress OBJECT-TYPE
        SYNTAX      InetAddress
        ACCESS      not-accessible
        STATUS      mandatory
        DESCRIPTION
            ""
        ::= { ipeCfgBridgeVlanEntry 2 }
    
    -- 1.3.6.1.4.1.119.2.3.69.213.502.5.3.16.3.1.3
    ipeCfgBridgeVlanVlanId OBJECT-TYPE
        SYNTAX      INTEGER (0..4094)
        ACCESS      read-only
        STATUS      mandatory
        DESCRIPTION
            "VLAN ID of Bridge.
             value range : 1 - 4094, notUsed(0)"
        ::= { ipeCfgBridgeVlanEntry 3 }
    
    -- 1.3.6.1.4.1.119.2.3.69.213.502.5.3.16.3.1.1001
    ipeCfgBridgeVlanNEAddressAddrType OBJECT-TYPE
        SYNTAX      InetAddressType
        ACCESS      not-accessible
        STATUS      mandatory
        DESCRIPTION
            "Represents the IP address type of NE address index.
             Only ipv4(1) and ipv6(2) are supported."
        ::= { ipeCfgBridgeVlanEntry 1001 }
    
    -- 1.3.6.1.4.1.119.2.3.69.213.502.5.3.17
    ipeCfgPripGroup OBJECT IDENTIFIER
        ::= { ipeConfigurationGroup 17 }
    
    -- 1.3.6.1.4.1.119.2.3.69.213.502.5.3.17.1
    ipeCfgPripTable OBJECT-TYPE
        SYNTAX      SEQUENCE OF IpeCfgPripEntry
        ACCESS      not-accessible
        STATUS      mandatory
        DESCRIPTION
            "PRIP set up information table."
        ::= { ipeCfgPripGroup 1 }
    
    -- 1.3.6.1.4.1.119.2.3.69.213.502.5.3.17.1.1
    ipeCfgPripEntry OBJECT-TYPE
        SYNTAX      IpeCfgPripEntry
        ACCESS      not-accessible
        STATUS      mandatory
        DESCRIPTION
            "entry of PRIP set up information table."
        INDEX       { ipeCfgPripNEAddressAddrType, ipeCfgPripNEAddress, ipeCfgPripIndex }
        ::= { ipeCfgPripTable 1 }
    
    IpeCfgPripEntry ::= SEQUENCE {
        ipeCfgPripIndex                 INTEGER,
        ipeCfgPripNEAddress             InetAddress,
        ipeCfgPripRouteEnable           INTEGER,
        ipeCfgPripUdpPort               INTEGER,
        ipeCfgPripNEAddressAddrType     InetAddressType
    }
    
    -- 1.3.6.1.4.1.119.2.3.69.213.502.5.3.17.1.1.1
    ipeCfgPripIndex OBJECT-TYPE
        SYNTAX      INTEGER (1)
        ACCESS      not-accessible
        STATUS      mandatory
        DESCRIPTION
            "Index of this ipeCfgPripEntry.
             It's a fiexed value(= 1)."
        ::= { ipeCfgPripEntry 1 }
    
    -- 1.3.6.1.4.1.119.2.3.69.213.502.5.3.17.1.1.2
    ipeCfgPripNEAddress OBJECT-TYPE
        SYNTAX      InetAddress
        ACCESS      not-accessible
        STATUS      mandatory
        DESCRIPTION
            ""
        ::= { ipeCfgPripEntry 2 }
    
    -- 1.3.6.1.4.1.119.2.3.69.213.502.5.3.17.1.1.3
    ipeCfgPripRouteEnable OBJECT-TYPE
        SYNTAX      INTEGER { invalid(0), enabled(1), disabled(2) }
        ACCESS      read-only
        STATUS      mandatory
        DESCRIPTION
            "Enable or disables PRIP.
    
             enabled(1):PRIP is enabled.
             disabled(2):PRIP is disabled."
        ::= { ipeCfgPripEntry 3 }
    
    -- 1.3.6.1.4.1.119.2.3.69.213.502.5.3.17.1.1.4
    ipeCfgPripUdpPort OBJECT-TYPE
        SYNTAX      INTEGER { ripdefaultport(520), pripdefaultport(8520) }
        ACCESS      read-only
        STATUS      mandatory
        DESCRIPTION
            "Setting of UDP port number used with PRIP.
    
             Either of 8520 or 520 is set.
    
             This setting is valid since PRIP will start next time."
        ::= { ipeCfgPripEntry 4 }
    
    -- 1.3.6.1.4.1.119.2.3.69.213.502.5.3.17.1.1.1001
    ipeCfgPripNEAddressAddrType OBJECT-TYPE
        SYNTAX      InetAddressType
        ACCESS      not-accessible
        STATUS      mandatory
        DESCRIPTION
            "Represents the IP address type of NE address index.
             Only ipv4(1) and ipv6(2) are supported."
        ::= { ipeCfgPripEntry 1001 }
    
    -- 1.3.6.1.4.1.119.2.3.69.213.502.5.3.17.2
    ipeCfgPripPortTable OBJECT-TYPE
        SYNTAX      SEQUENCE OF IpeCfgPripPortEntry
        ACCESS      not-accessible
        STATUS      mandatory
        DESCRIPTION
            "PRIP set up information table.(per port)"
        ::= { ipeCfgPripGroup 2 }
    
    -- 1.3.6.1.4.1.119.2.3.69.213.502.5.3.17.2.1
    ipeCfgPripPortEntry OBJECT-TYPE
        SYNTAX      IpeCfgPripPortEntry
        ACCESS      not-accessible
        STATUS      mandatory
        DESCRIPTION
            "entry of PRIP set up information table.(per port)"
        INDEX       { ipeCfgPripPortNEAddressAddrType, ipeCfgPripPortNEAddress, ipeCfgPripPortIfIndex }
        ::= { ipeCfgPripPortTable 1 }
    
    IpeCfgPripPortEntry ::= SEQUENCE {
        ipeCfgPripPortIfIndex               InterfaceIndex,
        ipeCfgPripPortNEAddress             InetAddress,
        ipeCfgPripPortEnable                INTEGER,
        ipeCfgPripPortPropagateNetEnable    INTEGER,
        ipeCfgPripPortNEAddressAddrType     InetAddressType
    }
    
    -- 1.3.6.1.4.1.119.2.3.69.213.502.5.3.17.2.1.1
    ipeCfgPripPortIfIndex OBJECT-TYPE
        SYNTAX      InterfaceIndex
        ACCESS      not-accessible
        STATUS      mandatory
        DESCRIPTION
            "Index of table."
        ::= { ipeCfgPripPortEntry 1 }
    
    -- 1.3.6.1.4.1.119.2.3.69.213.502.5.3.17.2.1.2
    ipeCfgPripPortNEAddress OBJECT-TYPE
        SYNTAX      InetAddress
        ACCESS      not-accessible
        STATUS      mandatory
        DESCRIPTION
            ""
        ::= { ipeCfgPripPortEntry 2 }
    
    -- 1.3.6.1.4.1.119.2.3.69.213.502.5.3.17.2.1.3
    ipeCfgPripPortEnable OBJECT-TYPE
        SYNTAX      INTEGER { invalid(0), enabled(1), disabled(2) }
        ACCESS      read-only
        STATUS      mandatory
        DESCRIPTION
            "Setting of some port when PRIP will be enabled.
    
             enabled(1)  : this port is enabled.
             disabled(2) : this port is disable."
        ::= { ipeCfgPripPortEntry 3 }
    
    -- 1.3.6.1.4.1.119.2.3.69.213.502.5.3.17.2.1.4
    ipeCfgPripPortPropagateNetEnable OBJECT-TYPE
        SYNTAX      INTEGER { invalid(0), enabled(1), disabled(2) }
        ACCESS      read-only
        STATUS      mandatory
        DESCRIPTION
            "Propagate setting for neighbor NE.
    
             enabled(1)  : this port is propagated.
             disabled(2) : this port is not propagated.
                           (Do not register in the RIP route.)"
        ::= { ipeCfgPripPortEntry 4 }
    
    -- 1.3.6.1.4.1.119.2.3.69.213.502.5.3.17.2.1.1001
    ipeCfgPripPortNEAddressAddrType OBJECT-TYPE
        SYNTAX      InetAddressType
        ACCESS      not-accessible
        STATUS      mandatory
        DESCRIPTION
            "Represents the IP address type of NE address index.
             Only ipv4(1) and ipv6(2) are supported."
        ::= { ipeCfgPripPortEntry 1001 }
    
    -- 1.3.6.1.4.1.119.2.3.69.213.502.5.3.18
    ipeCfgNaptGroup OBJECT IDENTIFIER
        ::= { ipeConfigurationGroup 18 }
    
    -- 1.3.6.1.4.1.119.2.3.69.213.502.5.3.18.1
    ipeCfgNaptTable OBJECT-TYPE
        SYNTAX      SEQUENCE OF IpeCfgNaptEntry
        ACCESS      not-accessible
        STATUS      mandatory
        DESCRIPTION
            "NAPT set up information table."
        ::= { ipeCfgNaptGroup 1 }
    
    -- 1.3.6.1.4.1.119.2.3.69.213.502.5.3.18.1.1
    ipeCfgNaptEntry OBJECT-TYPE
        SYNTAX      IpeCfgNaptEntry
        ACCESS      not-accessible
        STATUS      mandatory
        DESCRIPTION
            "entry of  NAPT set up information table."
        INDEX       { ipeCfgNaptNEAddressAddrType, ipeCfgNaptNEAddress, ipeCfgNaptIndex }
        ::= { ipeCfgNaptTable 1 }
    
    IpeCfgNaptEntry ::= SEQUENCE {
        ipeCfgNaptIndex                 INTEGER,
        ipeCfgNaptNEAddress             InetAddress,
        ipeCfgNaptEnable                INTEGER,
        ipeCfgNaptNEAddressAddrType     InetAddressType
    }
    
    -- 1.3.6.1.4.1.119.2.3.69.213.502.5.3.18.1.1.1
    ipeCfgNaptIndex OBJECT-TYPE
        SYNTAX      INTEGER (1)
        ACCESS      not-accessible
        STATUS      mandatory
        DESCRIPTION
            "Index of this ipeCfgNaptEntry.
             It's a fixed value(=1)."
        ::= { ipeCfgNaptEntry 1 }
    
    -- 1.3.6.1.4.1.119.2.3.69.213.502.5.3.18.1.1.2
    ipeCfgNaptNEAddress OBJECT-TYPE
        SYNTAX      InetAddress
        ACCESS      not-accessible
        STATUS      mandatory
        DESCRIPTION
            ""
        ::= { ipeCfgNaptEntry 2 }
    
    -- 1.3.6.1.4.1.119.2.3.69.213.502.5.3.18.1.1.3
    ipeCfgNaptEnable OBJECT-TYPE
        SYNTAX      INTEGER { enabled(1), disabled(2), neighbor(3) }
        ACCESS      read-only
        STATUS      mandatory
        DESCRIPTION
            "Address translation invalid effective/setting by NAPT.
             value range: enabled
                         disabled"
        ::= { ipeCfgNaptEntry 3 }
    
    -- 1.3.6.1.4.1.119.2.3.69.213.502.5.3.18.1.1.1001
    ipeCfgNaptNEAddressAddrType OBJECT-TYPE
        SYNTAX      InetAddressType
        ACCESS      not-accessible
        STATUS      mandatory
        DESCRIPTION
            "Represents the IP address type of NE address index.
             Only ipv4(1) and ipv6(2) are supported."
        ::= { ipeCfgNaptEntry 1001 }
    
    -- 1.3.6.1.4.1.119.2.3.69.213.502.5.3.19
    ipeCfgStaticRouteGroup OBJECT IDENTIFIER
        ::= { ipeConfigurationGroup 19 }
    
    -- 1.3.6.1.4.1.119.2.3.69.213.502.5.3.19.1
    ipeCfgStaticRouteTable OBJECT-TYPE
        SYNTAX      SEQUENCE OF IpeCfgStaticRouteEntry
        ACCESS      not-accessible
        STATUS      mandatory
        DESCRIPTION
            "Static Routing set up information table."
        ::= { ipeCfgStaticRouteGroup 1 }
    
    -- 1.3.6.1.4.1.119.2.3.69.213.502.5.3.19.1.1
    ipeCfgStaticRouteEntry OBJECT-TYPE
        SYNTAX      IpeCfgStaticRouteEntry
        ACCESS      not-accessible
        STATUS      mandatory
        DESCRIPTION
            "entry of  Static Routing set up information table."
        INDEX       { ipeCfgRouteNEAddressAddrType, ipeCfgRouteNEAddress, ipeCfgRouteIndex }
        ::= { ipeCfgStaticRouteTable 1 }
    
    IpeCfgStaticRouteEntry ::= SEQUENCE {
        ipeCfgRouteIndex                INTEGER,
        ipeCfgRouteNEAddress            InetAddress,
        ipeCfgRouteDest                 IpAddress,
        ipeCfgRouteMask                 IpAddress,
        ipeCfgRouteNextHop              IpAddress,
        ipeCfgRouteRowStatus            RowStatus,
        ipeCfgRouteNEAddressAddrType    InetAddressType
    }
    
    -- 1.3.6.1.4.1.119.2.3.69.213.502.5.3.19.1.1.1
    ipeCfgRouteIndex OBJECT-TYPE
        SYNTAX      INTEGER (1..128)
        ACCESS      not-accessible
        STATUS      mandatory
        DESCRIPTION
            "Index of table(1 to 128)."
        ::= { ipeCfgStaticRouteEntry 1 }
    
    -- 1.3.6.1.4.1.119.2.3.69.213.502.5.3.19.1.1.2
    ipeCfgRouteNEAddress OBJECT-TYPE
        SYNTAX      InetAddress
        ACCESS      not-accessible
        STATUS      mandatory
        DESCRIPTION
            ""
        ::= { ipeCfgStaticRouteEntry 2 }
    
    -- 1.3.6.1.4.1.119.2.3.69.213.502.5.3.19.1.1.3
    ipeCfgRouteDest OBJECT-TYPE
        SYNTAX      IpAddress
        ACCESS      read-only
        STATUS      mandatory
        DESCRIPTION
            "Static routing object destination address.
             When masking in ipeCfgRouteMask, the host address part has to be
             a zero, if any.
             Value range:0x00000000-0xdfffffff(0.0.0.0-223.255.255.255)
             The value acquisition when unsetting it returns NoSuchObject."
        ::= { ipeCfgStaticRouteEntry 3 }
    
    -- 1.3.6.1.4.1.119.2.3.69.213.502.5.3.19.1.1.4
    ipeCfgRouteMask OBJECT-TYPE
        SYNTAX      IpAddress
        ACCESS      read-only
        STATUS      mandatory
        DESCRIPTION
            "Static routing object subnet mask.
             When it isn't proper as subnetmask, it'll be an error.
             Value range:0x00000000-0xffffffff(0-32bit)
             Only when ipeCfgRouteDest is 0, 0bit is allowed.
             The value acquisition when unsetting it returns NoSuchObject."
        ::= { ipeCfgStaticRouteEntry 4 }
    
    -- 1.3.6.1.4.1.119.2.3.69.213.502.5.3.19.1.1.5
    ipeCfgRouteNextHop OBJECT-TYPE
        SYNTAX      IpAddress
        ACCESS      read-only
        STATUS      mandatory
        DESCRIPTION
            "Static routing object gateway address.
             Value range:0x00000001 - 0xdfffffff(0.0.0.1 - 223.255.255.255)
             The value acquisition when unsetting it returns NoSuchObject."
        ::= { ipeCfgStaticRouteEntry 5 }
    
    -- 1.3.6.1.4.1.119.2.3.69.213.502.5.3.19.1.1.6
    ipeCfgRouteRowStatus OBJECT-TYPE
        SYNTAX      RowStatus { active(1), createAndGo(4), destroy(6) }
        ACCESS      read-only
        STATUS      mandatory
        DESCRIPTION
            "This RowStatus has a status only 'active(1)'.
    
             1) creating a entry
             When you make a new entry, you must SET objects indicated below.
             * ipeCfgRouteDest
             * ipeCfgRouteMask
             * ipeCfgRouteNextHop
             * ipeCfgRouteRowStatus <- createAndGo(4)
    
             2) modifing a entry
             When you make a existing entry, you must SET objects indicated
             below.
             * ipeCfgRouteDest
             * ipeCfgRouteMask
             * ipeCfgRouteNextHop
    
             3) deleting a entry
             When you SET a destroy(6) to ipeCfgRouteRowStatus, the entry is
             destroyed.
             * ipeCfgRouteRowStatus <- destory(6)"
        ::= { ipeCfgStaticRouteEntry 6 }
    
    -- 1.3.6.1.4.1.119.2.3.69.213.502.5.3.19.1.1.1001
    ipeCfgRouteNEAddressAddrType OBJECT-TYPE
        SYNTAX      InetAddressType
        ACCESS      not-accessible
        STATUS      mandatory
        DESCRIPTION
            "Represents the IP address type of NE address index.
             Only ipv4(1) and ipv6(2) are supported."
        ::= { ipeCfgStaticRouteEntry 1001 }
    
    -- 1.3.6.1.4.1.119.2.3.69.213.502.5.3.19.2
    ipeCfgV6StaticRouteTable OBJECT-TYPE
        SYNTAX      SEQUENCE OF IpeCfgV6StaticRouteEntry
        ACCESS      not-accessible
        STATUS      mandatory
        DESCRIPTION
            "IPv6 Static Routing set up information table."
        ::= { ipeCfgStaticRouteGroup 2 }
    
    -- 1.3.6.1.4.1.119.2.3.69.213.502.5.3.19.2.1
    ipeCfgV6StaticRouteEntry OBJECT-TYPE
        SYNTAX      IpeCfgV6StaticRouteEntry
        ACCESS      not-accessible
        STATUS      mandatory
        DESCRIPTION
            "entry of Static Routing set up information table."
        INDEX       { ipeCfgV6RouteNEAddressAddrType, ipeCfgV6RouteNEAddress, ipeCfgV6RouteIndex }
        ::= { ipeCfgV6StaticRouteTable 1 }
    
    IpeCfgV6StaticRouteEntry ::= SEQUENCE {
        ipeCfgV6RouteIndex              INTEGER,
        ipeCfgV6RouteNEAddress          InetAddress,
        ipeCfgV6RouteDest               Ipv6Address,
        ipeCfgV6RoutePrefixLength       InetAddressPrefixLength,
        ipeCfgV6RouteNextHop            Ipv6Address,
        ipeCfgV6RouteNextHopIfIndex     INTEGER,
        ipeCfgV6RouteRowStatus          RowStatus,
        ipeCfgV6RouteNEAddressAddrType  InetAddressType
    }
    
    -- 1.3.6.1.4.1.119.2.3.69.213.502.5.3.19.2.1.1
    ipeCfgV6RouteIndex OBJECT-TYPE
        SYNTAX      INTEGER (1..128)
        ACCESS      not-accessible
        STATUS      mandatory
        DESCRIPTION
            "Index of table(1 to 128)."
        ::= { ipeCfgV6StaticRouteEntry 1 }
    
    -- 1.3.6.1.4.1.119.2.3.69.213.502.5.3.19.2.1.2
    ipeCfgV6RouteNEAddress OBJECT-TYPE
        SYNTAX      InetAddress
        ACCESS      not-accessible
        STATUS      mandatory
        DESCRIPTION
            ""
        ::= { ipeCfgV6StaticRouteEntry 2 }
    
    -- 1.3.6.1.4.1.119.2.3.69.213.502.5.3.19.2.1.3
    ipeCfgV6RouteDest OBJECT-TYPE
        SYNTAX      Ipv6Address
        ACCESS      read-only
        STATUS      mandatory
        DESCRIPTION
            "Static routing object destination address.
             The value acquisition when unsetting it returns NoSuchObject."
        ::= { ipeCfgV6StaticRouteEntry 3 }
    
    -- 1.3.6.1.4.1.119.2.3.69.213.502.5.3.19.2.1.4
    ipeCfgV6RoutePrefixLength OBJECT-TYPE
        SYNTAX      InetAddressPrefixLength
        ACCESS      read-only
        STATUS      mandatory
        DESCRIPTION
            "Static routing object prefix length.
             When it isn't proper as prefix length, it'll be an error.
             Only when ipeCfgV6RouteDest is 0, 0bit is allowed.
             The value acquisition when unsetting it returns NoSuchObject."
        ::= { ipeCfgV6StaticRouteEntry 4 }
    
    -- 1.3.6.1.4.1.119.2.3.69.213.502.5.3.19.2.1.5
    ipeCfgV6RouteNextHop OBJECT-TYPE
        SYNTAX      Ipv6Address
        ACCESS      read-only
        STATUS      mandatory
        DESCRIPTION
            "Static routing object gateway address.
             The value acquisition when unsetting it returns NoSuchObject."
        ::= { ipeCfgV6StaticRouteEntry 5 }
    
    -- 1.3.6.1.4.1.119.2.3.69.213.502.5.3.19.2.1.6
    ipeCfgV6RouteNextHopIfIndex OBJECT-TYPE
        SYNTAX      INTEGER { any(0), bridge1(11), bridge2(12), bridge3(13),
                        bridge4(14), bridge5(15), bridge6(16), bridge7(17),
                        bridge8(18), bridge9(19), bridge10(20), bridge11(21),
                        bridge12(22), bridge13(23), bridge14(24),
                        bridge15(25), bridge16(26), bridge17(27),
                        bridge18(28), bridge19(29), bridge20(30) }
        ACCESS      read-only
        STATUS      mandatory
        DESCRIPTION
            "Static routing object gateway interface index.
             When ipeCfgV6RouteNextHop is specified, setting this value is not
             considered.
    
             When setting Link-local address for ipeCfgV6RouteNextHop, this
             object must be configured.
    
             The value acquisition when unsetting it returns NoSuchObject."
        ::= { ipeCfgV6StaticRouteEntry 6 }
    
    -- 1.3.6.1.4.1.119.2.3.69.213.502.5.3.19.2.1.7
    ipeCfgV6RouteRowStatus OBJECT-TYPE
        SYNTAX      RowStatus { active(1), createAndGo(4), destroy(6) }
        ACCESS      read-only
        STATUS      mandatory
        DESCRIPTION
            "This RowStatus has a status only 'active(1)'.
    
             1) creating a entry
             When you make a new entry, you must SET objects indicated below.
             * ipeCfgV6RouteDest
             * ipeCfgV6RoutePrefixLength
             * ipeCfgV6RouteNextHop
             * ipeCfgV6RouteNextHopIfIndex
             * ipeCfgV6RouteRowStatus <- createAndGo(4)
    
             2) modifing a entry
             When you make a existing entry, you must SET objects indicated
             below.
             * ipeCfgV6RouteDest
             * ipeCfgV6RoutePrefixLength
             * ipeCfgV6RouteNextHop
             * ipeCfgV6RouteNextHopIfIndex
    
             3) deleting a entry
             When you SET a destroy(6) to ipeCfgV6RouteRowStatus, the entry is
             destroyed.
             * ipeCfgV6RouteRowStatus <- destory(6)"
        ::= { ipeCfgV6StaticRouteEntry 7 }
    
    -- 1.3.6.1.4.1.119.2.3.69.213.502.5.3.19.2.1.1001
    ipeCfgV6RouteNEAddressAddrType OBJECT-TYPE
        SYNTAX      InetAddressType
        ACCESS      not-accessible
        STATUS      mandatory
        DESCRIPTION
            "Represents the IP address type of NE address index.
             Only ipv4(1) and ipv6(2) are supported."
        ::= { ipeCfgV6StaticRouteEntry 1001 }
    
    -- 1.3.6.1.4.1.119.2.3.69.213.502.5.3.21
    ipeCfgAccessListGroup OBJECT IDENTIFIER
        ::= { ipeConfigurationGroup 21 }
    
    -- 1.3.6.1.4.1.119.2.3.69.213.502.5.3.21.1
    ipeCfgAccessListRuleTable OBJECT-TYPE
        SYNTAX      SEQUENCE OF IpeCfgAccessListRuleEntry
        ACCESS      not-accessible
        STATUS      mandatory
        DESCRIPTION
            "Table of Access List(Rule)."
        ::= { ipeCfgAccessListGroup 1 }
    
    -- 1.3.6.1.4.1.119.2.3.69.213.502.5.3.21.1.1
    ipeCfgAccessListRuleEntry OBJECT-TYPE
        SYNTAX      IpeCfgAccessListRuleEntry
        ACCESS      not-accessible
        STATUS      mandatory
        DESCRIPTION
            "Entry of Access List(Rule)."
        INDEX       { ipeCfgAccessListRuleNEAddressAddrType, ipeCfgAccessListRuleNEAddress, ipeCfgAccessListRuleEnableIndex }
        ::= { ipeCfgAccessListRuleTable 1 }
    
    IpeCfgAccessListRuleEntry ::= SEQUENCE {
        ipeCfgAccessListRuleEnableIndex         INTEGER,
        ipeCfgAccessListRuleNEAddress           InetAddress,
        ipeCfgAccessListInputRuleEnable         INTEGER,
        ipeCfgAccessListForwardRuleEnable       INTEGER,
        ipeCfgAccessListInputDefaultAction      INTEGER,
        ipeCfgAccessListForwardDefaultAction    INTEGER,
        ipeCfgAccessListV6InputRuleEnable       INTEGER,
        ipeCfgAccessListV6ForwardRuleEnable     INTEGER,
        ipeCfgAccessListV6InputDefaultAction    INTEGER,
        ipeCfgAccessListV6ForwardDefaultAction  INTEGER,
        ipeCfgAccessListRuleNEAddressAddrType   InetAddressType
    }
    
    -- 1.3.6.1.4.1.119.2.3.69.213.502.5.3.21.1.1.1
    ipeCfgAccessListRuleEnableIndex OBJECT-TYPE
        SYNTAX      INTEGER (1)
        ACCESS      not-accessible
        STATUS      mandatory
        DESCRIPTION
            "Index of this ipeCfgAccessListRuleEntry.
             It's a fixed value(=1)."
        ::= { ipeCfgAccessListRuleEntry 1 }
    
    -- 1.3.6.1.4.1.119.2.3.69.213.502.5.3.21.1.1.2
    ipeCfgAccessListRuleNEAddress OBJECT-TYPE
        SYNTAX      InetAddress
        ACCESS      not-accessible
        STATUS      mandatory
        DESCRIPTION
            ""
        ::= { ipeCfgAccessListRuleEntry 2 }
    
    -- 1.3.6.1.4.1.119.2.3.69.213.502.5.3.21.1.1.3
    ipeCfgAccessListInputRuleEnable OBJECT-TYPE
        SYNTAX      INTEGER { invalid(0), disable(1), enable(2) }
        ACCESS      read-only
        STATUS      mandatory
        DESCRIPTION
            "IP Access Control Input Filter Rule"
        ::= { ipeCfgAccessListRuleEntry 3 }
    
    -- 1.3.6.1.4.1.119.2.3.69.213.502.5.3.21.1.1.4
    ipeCfgAccessListForwardRuleEnable OBJECT-TYPE
        SYNTAX      INTEGER { invalid(0), disable(1), enable(2) }
        ACCESS      read-only
        STATUS      mandatory
        DESCRIPTION
            "IP Access Control Forwarding Filter Rule"
        ::= { ipeCfgAccessListRuleEntry 4 }
    
    -- 1.3.6.1.4.1.119.2.3.69.213.502.5.3.21.1.1.5
    ipeCfgAccessListInputDefaultAction OBJECT-TYPE
        SYNTAX      INTEGER { permit(1), deny(2) }
        ACCESS      read-only
        STATUS      mandatory
        DESCRIPTION
            "IP Access Control Input Default Action."
        ::= { ipeCfgAccessListRuleEntry 5 }
    
    -- 1.3.6.1.4.1.119.2.3.69.213.502.5.3.21.1.1.6
    ipeCfgAccessListForwardDefaultAction OBJECT-TYPE
        SYNTAX      INTEGER { permit(1), deny(2) }
        ACCESS      read-only
        STATUS      mandatory
        DESCRIPTION
            "IP Access Control Forwarding Default Action"
        ::= { ipeCfgAccessListRuleEntry 6 }
    
    -- 1.3.6.1.4.1.119.2.3.69.213.502.5.3.21.1.1.7
    ipeCfgAccessListV6InputRuleEnable OBJECT-TYPE
        SYNTAX      INTEGER { invalid(0), disable(1), enable(2) }
        ACCESS      read-only
        STATUS      mandatory
        DESCRIPTION
            "IPv6 Access Control Input Filter Rule"
        ::= { ipeCfgAccessListRuleEntry 7 }
    
    -- 1.3.6.1.4.1.119.2.3.69.213.502.5.3.21.1.1.8
    ipeCfgAccessListV6ForwardRuleEnable OBJECT-TYPE
        SYNTAX      INTEGER { invalid(0), disable(1), enable(2) }
        ACCESS      read-only
        STATUS      mandatory
        DESCRIPTION
            "IPv6 Access Control Forwarding Filter Rule"
        ::= { ipeCfgAccessListRuleEntry 8 }
    
    -- 1.3.6.1.4.1.119.2.3.69.213.502.5.3.21.1.1.9
    ipeCfgAccessListV6InputDefaultAction OBJECT-TYPE
        SYNTAX      INTEGER { permit(1), deny(2) }
        ACCESS      read-only
        STATUS      mandatory
        DESCRIPTION
            "IPv6 Access Control Input Default Action."
        ::= { ipeCfgAccessListRuleEntry 9 }
    
    -- 1.3.6.1.4.1.119.2.3.69.213.502.5.3.21.1.1.10
    ipeCfgAccessListV6ForwardDefaultAction OBJECT-TYPE
        SYNTAX      INTEGER { permit(1), deny(2) }
        ACCESS      read-only
        STATUS      mandatory
        DESCRIPTION
            "IPv6 Access Control Forwarding Default Action"
        ::= { ipeCfgAccessListRuleEntry 10 }
    
    -- 1.3.6.1.4.1.119.2.3.69.213.502.5.3.21.1.1.1001
    ipeCfgAccessListRuleNEAddressAddrType OBJECT-TYPE
        SYNTAX      InetAddressType
        ACCESS      not-accessible
        STATUS      mandatory
        DESCRIPTION
            "Represents the IP address type of NE address index.
             Only ipv4(1) and ipv6(2) are supported."
        ::= { ipeCfgAccessListRuleEntry 1001 }
    
    -- 1.3.6.1.4.1.119.2.3.69.213.502.5.3.21.2
    ipeCfgAccessListInputTable OBJECT-TYPE
        SYNTAX      SEQUENCE OF IpeCfgAccessListInputEntry
        ACCESS      not-accessible
        STATUS      mandatory
        DESCRIPTION
            "Table of Access List(Input Direction)."
        ::= { ipeCfgAccessListGroup 2 }
    
    -- 1.3.6.1.4.1.119.2.3.69.213.502.5.3.21.2.1
    ipeCfgAccessListInputEntry OBJECT-TYPE
        SYNTAX      IpeCfgAccessListInputEntry
        ACCESS      not-accessible
        STATUS      mandatory
        DESCRIPTION
            "Entry of Access List(Input Direction)."
        INDEX       { ipeCfgAccessListInputNEAddressAddrType, ipeCfgAccessListInputNEAddress, ipeCfgAccessListInputOrderNum }
        ::= { ipeCfgAccessListInputTable 1 }
    
    IpeCfgAccessListInputEntry ::= SEQUENCE {
        ipeCfgAccessListInputOrderNum           INTEGER,
        ipeCfgAccessListInputNEAddress          InetAddress,
        ipeCfgAccessListInputInIfIndex          INTEGER,
        ipeCfgAccessListInputSrcIpAddress       IpAddress,
        ipeCfgAccessListInputSrcNetMask         IpAddress,
        ipeCfgAccessListInputProtocol           INTEGER,
        ipeCfgAccessListInputDstPortNum         INTEGER,
        ipeCfgAccessListInputAction             INTEGER,
        ipeCfgAccessListInputRowStatus          RowStatus,
        ipeCfgAccessListInputNEAddressAddrType  InetAddressType
    }
    
    -- 1.3.6.1.4.1.119.2.3.69.213.502.5.3.21.2.1.1
    ipeCfgAccessListInputOrderNum OBJECT-TYPE
        SYNTAX      INTEGER (1..50)
        ACCESS      not-accessible
        STATUS      mandatory
        DESCRIPTION
            "Index of table(1-50)."
        ::= { ipeCfgAccessListInputEntry 1 }
    
    -- 1.3.6.1.4.1.119.2.3.69.213.502.5.3.21.2.1.2
    ipeCfgAccessListInputNEAddress OBJECT-TYPE
        SYNTAX      InetAddress
        ACCESS      not-accessible
        STATUS      mandatory
        DESCRIPTION
            ""
        ::= { ipeCfgAccessListInputEntry 2 }
    
    -- 1.3.6.1.4.1.119.2.3.69.213.502.5.3.21.2.1.3
    ipeCfgAccessListInputInIfIndex OBJECT-TYPE
        SYNTAX      INTEGER { any(0), lct(2), inband(3), ne2(4),
                        bridge1(11), bridge2(12), bridge3(13), bridge4(14),
                        bridge5(15), bridge6(16), bridge7(17), bridge8(18),
                        bridge9(19), bridge10(20), bridge11(21), bridge12(22),
                        bridge13(23), bridge14(24), bridge15(25), bridge16(26),
                        bridge17(27), bridge18(28), bridge19(29), bridge20(30) }
        ACCESS      read-only
        STATUS      mandatory
        DESCRIPTION
            "IP Access Control Input Filter Interface.
             The value 'inband' and 'ne2' are not supported."
        ::= { ipeCfgAccessListInputEntry 3 }
    
    -- 1.3.6.1.4.1.119.2.3.69.213.502.5.3.21.2.1.4
    ipeCfgAccessListInputSrcIpAddress OBJECT-TYPE
        SYNTAX      IpAddress
        ACCESS      read-only
        STATUS      mandatory
        DESCRIPTION
            "IP Access Control Input Filter Source IP Address"
        ::= { ipeCfgAccessListInputEntry 4 }
    
    -- 1.3.6.1.4.1.119.2.3.69.213.502.5.3.21.2.1.5
    ipeCfgAccessListInputSrcNetMask OBJECT-TYPE
        SYNTAX      IpAddress
        ACCESS      read-only
        STATUS      mandatory
        DESCRIPTION
            "IP Access Control Input Filter Source Subnet Mask.
             '0.0.0.0' matches all IP addresses. i.e. '0.0.0.0' acts as
             'Any'."
        ::= { ipeCfgAccessListInputEntry 5 }
    
    -- 1.3.6.1.4.1.119.2.3.69.213.502.5.3.21.2.1.6
    ipeCfgAccessListInputProtocol OBJECT-TYPE
        SYNTAX      INTEGER
        ACCESS      read-only
        STATUS      mandatory
        DESCRIPTION
            "IP Access Control Input Filter Protocol.
             '-1' acts as 'Any'."
        ::= { ipeCfgAccessListInputEntry 6 }
    
    -- 1.3.6.1.4.1.119.2.3.69.213.502.5.3.21.2.1.7
    ipeCfgAccessListInputDstPortNum OBJECT-TYPE
        SYNTAX      INTEGER
        ACCESS      read-only
        STATUS      mandatory
        DESCRIPTION
            "IP Access Control Input Filter Port Number.
             '-1' acts as 'Any'."
        ::= { ipeCfgAccessListInputEntry 7 }
    
    -- 1.3.6.1.4.1.119.2.3.69.213.502.5.3.21.2.1.8
    ipeCfgAccessListInputAction OBJECT-TYPE
        SYNTAX      INTEGER { permit(1), deny(2) }
        ACCESS      read-only
        STATUS      mandatory
        DESCRIPTION
            "IP Access Control Input Filter Action."
        ::= { ipeCfgAccessListInputEntry 8 }
    
    -- 1.3.6.1.4.1.119.2.3.69.213.502.5.3.21.2.1.9
    ipeCfgAccessListInputRowStatus OBJECT-TYPE
        SYNTAX      RowStatus { active(1), createAndGo(4), destroy(6) }
        ACCESS      read-only
        STATUS      mandatory
        DESCRIPTION
            "This RowStatus has a status only 'active(1)'.
    
             1) creating a entry
             When you make a new entry, you must SET objects indicated below.
             ipeCfgAccessListInputAction
             ipeCfgAccessListInputRowStatus <- createAndGo(4)
    
    
             When you are not setting a value of items as follows, it is set
             as 'any'.
             ipeCfgAccessListInputInIfIndex
             ipeCfgAccessListInputSrcIpAddress
             ipeCfgAccessListInputSrcNetMask(*1)
             ipeCfgAccessListInputProtocol
             ipeCfgAccessListInputDstPortNum(*2)
    
             *1 When you not set ipeCfgAccessListInputSrcIpAddress, even when
             ipeCfgAccessListInputSrcNetMask is set, it is set as 'any'.When
             ipeCfgAccessListInputSrcIpAddress set to 'any',
             ipeCfgAccessListInputSrcNetMask is set as 'any'.
             *2 When you not set ipeCfgAccessListInputProtocol to '6' or '17',
             even when ipeCfgAccessListInputDstPortNum is set, it is set as
             'any'.
    
             2) modifing a entry
             It isn't possible.
    
             3) deleting a entry
             When you SET a destroy(6) to ipeCfgAccessListInputRowStatus, the
             entry is destroyed."
        ::= { ipeCfgAccessListInputEntry 9 }
    
    -- 1.3.6.1.4.1.119.2.3.69.213.502.5.3.21.2.1.1001
    ipeCfgAccessListInputNEAddressAddrType OBJECT-TYPE
        SYNTAX      InetAddressType
        ACCESS      not-accessible
        STATUS      mandatory
        DESCRIPTION
            "Represents the IP address type of NE address index.
             Only ipv4(1) and ipv6(2) are supported."
        ::= { ipeCfgAccessListInputEntry 1001 }
    
    -- 1.3.6.1.4.1.119.2.3.69.213.502.5.3.21.3
    ipeCfgAccessListForwardTable OBJECT-TYPE
        SYNTAX      SEQUENCE OF IpeCfgAccessListForwardEntry
        ACCESS      not-accessible
        STATUS      mandatory
        DESCRIPTION
            "Table of Access List(Forward Direction)."
        ::= { ipeCfgAccessListGroup 3 }
    
    -- 1.3.6.1.4.1.119.2.3.69.213.502.5.3.21.3.1
    ipeCfgAccessListForwardEntry OBJECT-TYPE
        SYNTAX      IpeCfgAccessListForwardEntry
        ACCESS      not-accessible
        STATUS      mandatory
        DESCRIPTION
            "Entry of Access List(Forward Direction)."
        INDEX       { ipeCfgAccessListForwardNEAddressAddrType, ipeCfgAccessListForwardNEAddress, ipeCfgAccessListForwardOrderNum }
        ::= { ipeCfgAccessListForwardTable 1 }
    
    IpeCfgAccessListForwardEntry ::= SEQUENCE {
        ipeCfgAccessListForwardOrderNum             INTEGER,
        ipeCfgAccessListForwardNEAddress            InetAddress,
        ipeCfgAccessListForwardInIfIndex            INTEGER,
        ipeCfgAccessListForwardOutIfIndex           INTEGER,
        ipeCfgAccessListForwardSrcIpAddress         IpAddress,
        ipeCfgAccessListForwardSrcNetMask           IpAddress,
        ipeCfgAccessListForwardDstIpAddress         IpAddress,
        ipeCfgAccessListForwardDstNetMask           IpAddress,
        ipeCfgAccessListForwardProtocol             INTEGER,
        ipeCfgAccessListForwardSrcPortNum           INTEGER,
        ipeCfgAccessListForwardDstPortNum           INTEGER,
        ipeCfgAccessListForwardAction               INTEGER,
        ipeCfgAccessListForwardRowStatus            RowStatus,
        ipeCfgAccessListForwardNEAddressAddrType    InetAddressType
    }
    
    -- 1.3.6.1.4.1.119.2.3.69.213.502.5.3.21.3.1.1
    ipeCfgAccessListForwardOrderNum OBJECT-TYPE
        SYNTAX      INTEGER (1..50)
        ACCESS      not-accessible
        STATUS      mandatory
        DESCRIPTION
            "Index of table(1-50)."
        ::= { ipeCfgAccessListForwardEntry 1 }
    
    -- 1.3.6.1.4.1.119.2.3.69.213.502.5.3.21.3.1.2
    ipeCfgAccessListForwardNEAddress OBJECT-TYPE
        SYNTAX      InetAddress
        ACCESS      not-accessible
        STATUS      mandatory
        DESCRIPTION
            ""
        ::= { ipeCfgAccessListForwardEntry 2 }
    
    -- 1.3.6.1.4.1.119.2.3.69.213.502.5.3.21.3.1.3
    ipeCfgAccessListForwardInIfIndex OBJECT-TYPE
        SYNTAX      INTEGER { any(0), lct(2), inband(3), ne2(4),
                        bridge1(11), bridge2(12),bridge3(13), bridge4(14),
                        bridge5(15), bridge6(16),bridge7(17), bridge8(18),
                        bridge9(19), bridge10(20),bridge11(21), bridge12(22), 
                        bridge13(23), bridge14(24), bridge15(25), bridge16(26),
                        bridge17(27), bridge18(28), bridge19(29), bridge20(30) }
        ACCESS      read-only
        STATUS      mandatory
        DESCRIPTION
            "IP Access Control Forward Filter Input Interface.
    
             The value 'inband' and 'ne2' are not supported."
        ::= { ipeCfgAccessListForwardEntry 3 }
    
    -- 1.3.6.1.4.1.119.2.3.69.213.502.5.3.21.3.1.4
    ipeCfgAccessListForwardOutIfIndex OBJECT-TYPE
        SYNTAX      INTEGER { any(0), lct(2), inband(3), ne2(4),
                        bridge1(11), bridge2(12), bridge3(13), bridge4(14),
                        bridge5(15), bridge6(16), bridge7(17), bridge8(18),
                        bridge9(19), bridge10(20), bridge11(21), bridge12(22),
                        bridge13(23), bridge14(24), bridge15(25), bridge16(26),
                        bridge17(27), bridge18(28), bridge19(29), bridge20(30) }
        ACCESS      read-only
        STATUS      mandatory
        DESCRIPTION
            "IP Access Control Forward Filter Output Interface.
    
             The value 'inband' and 'ne2' is not supported."
        ::= { ipeCfgAccessListForwardEntry 4 }
    
    -- 1.3.6.1.4.1.119.2.3.69.213.502.5.3.21.3.1.5
    ipeCfgAccessListForwardSrcIpAddress OBJECT-TYPE
        SYNTAX      IpAddress
        ACCESS      read-only
        STATUS      mandatory
        DESCRIPTION
            "IP Access Control Forward Filter Source IP Address."
        ::= { ipeCfgAccessListForwardEntry 5 }
    
    -- 1.3.6.1.4.1.119.2.3.69.213.502.5.3.21.3.1.6
    ipeCfgAccessListForwardSrcNetMask OBJECT-TYPE
        SYNTAX      IpAddress
        ACCESS      read-only
        STATUS      mandatory
        DESCRIPTION
            "IP Access Control Forward Filter Source Subnet Mask.
             '0.0.0.0' matches all IP addresses. i.e. '0.0.0.0' acts as 'Any'"
        ::= { ipeCfgAccessListForwardEntry 6 }
    
    -- 1.3.6.1.4.1.119.2.3.69.213.502.5.3.21.3.1.7
    ipeCfgAccessListForwardDstIpAddress OBJECT-TYPE
        SYNTAX      IpAddress
        ACCESS      read-only
        STATUS      mandatory
        DESCRIPTION
            "IP Access Control Forward Filter Destination IP Address."
        ::= { ipeCfgAccessListForwardEntry 7 }
    
    -- 1.3.6.1.4.1.119.2.3.69.213.502.5.3.21.3.1.8
    ipeCfgAccessListForwardDstNetMask OBJECT-TYPE
        SYNTAX      IpAddress
        ACCESS      read-only
        STATUS      mandatory
        DESCRIPTION
            "IP Access Control Forward Filter Destination Subnet Mask.
             '0.0.0.0' matches all IP addresses. i.e. '0.0.0.0' acts as
             'Any'."
        ::= { ipeCfgAccessListForwardEntry 8 }
    
    -- 1.3.6.1.4.1.119.2.3.69.213.502.5.3.21.3.1.9
    ipeCfgAccessListForwardProtocol OBJECT-TYPE
        SYNTAX      INTEGER
        ACCESS      read-only
        STATUS      mandatory
        DESCRIPTION
            "IP Access Control Forward Filter Protocol.
             '-1' acts as 'Any'."
        ::= { ipeCfgAccessListForwardEntry 9 }
    
    -- 1.3.6.1.4.1.119.2.3.69.213.502.5.3.21.3.1.10
    ipeCfgAccessListForwardSrcPortNum OBJECT-TYPE
        SYNTAX      INTEGER
        ACCESS      read-only
        STATUS      mandatory
        DESCRIPTION
            "IP Access Control Forward Filter Source Port Number.
             '-1' acts as 'Any'."
        ::= { ipeCfgAccessListForwardEntry 10 }
    
    -- 1.3.6.1.4.1.119.2.3.69.213.502.5.3.21.3.1.11
    ipeCfgAccessListForwardDstPortNum OBJECT-TYPE
        SYNTAX      INTEGER
        ACCESS      read-only
        STATUS      mandatory
        DESCRIPTION
            "IP Access Control Forward Filter Destination Port Number.
             '-1' acts as 'Any'."
        ::= { ipeCfgAccessListForwardEntry 11 }
    
    -- 1.3.6.1.4.1.119.2.3.69.213.502.5.3.21.3.1.12
    ipeCfgAccessListForwardAction OBJECT-TYPE
        SYNTAX      INTEGER { permit(1), deny(2) }
        ACCESS      read-only
        STATUS      mandatory
        DESCRIPTION
            "IP Access Control Forward Filter Action."
        ::= { ipeCfgAccessListForwardEntry 12 }
    
    -- 1.3.6.1.4.1.119.2.3.69.213.502.5.3.21.3.1.13
    ipeCfgAccessListForwardRowStatus OBJECT-TYPE
        SYNTAX      RowStatus { active(1), createAndGo(4), destroy(6) }
        ACCESS      read-only
        STATUS      mandatory
        DESCRIPTION
            "This RowStatus has a status only 'active(1)'.
    
             1) creating a entry
             When you make a new entry, you must SET objects indicated below.
             ipeCfgAccessListForwardAction
             ipeCfgAccessListForwardRowStatus <- createAndGo(4)
    
    
             When you are not setting a value of items as follows, it is set
             as 'any'.
             ipeCfgAccessListForwardInIfIndex
             ipeCfgAccessListForwardOutIfIndex
             ipeCfgAccessListForwardSrcIpAddress
             ipeCfgAccessListForwardSrcNetMask(*1)
             ipeCfgAccessListForwardDstIpAddress
             ipeCfgAccessListForwardDstNetMask(*2)
             ipeCfgAccessListForwardProtocol
             ipeCfgAccessListForwardSrcPortNum(*3)
             ipeCfgAccessListForwardDstPortNum(*3)
    
             *1 When you not set ipeCfgAccessListForwardSrcIpAddress, even
             when ipeCfgAccessListForwardSrcNetMask is set, it is set as
             'any'.When ipeCfgAccessListForwardSrcIpAddress set to 'any',
             ipeCfgAccessListForwardSrcNetMask is set as 'any'.
             *2 When you not set ipeCfgAccessListForwardDstIpAddress, even
             when ipeCfgAccessListForwardDstNetMask is set, it is set as
             'any'.When ipeCfgAccessListForwardDstIpAddress set to 'any',
             ipeCfgAccessListForwardDstNetMask is set as 'any'.
             *3 When you not set ipeCfgAccessListForwardProtocol to '6' or
             '17',, even when ipeCfgAccessListForwardSrcPortNum and
             ipeCfgAccessListForwardDstPortNum are set, it is set as 'any'.
    
             2) modifing a entry
             It isn't possible.
    
             3) deleting a entry
             When you SET a destroy(6) to ipeCfgAccessListForwardRowStatus,
             the entry is destroyed."
        ::= { ipeCfgAccessListForwardEntry 13 }
    
    -- 1.3.6.1.4.1.119.2.3.69.213.502.5.3.21.3.1.1001
    ipeCfgAccessListForwardNEAddressAddrType OBJECT-TYPE
        SYNTAX      InetAddressType
        ACCESS      not-accessible
        STATUS      mandatory
        DESCRIPTION
            "Represents the IP address type of NE address index.
             Only ipv4(1) and ipv6(2) are supported."
        ::= { ipeCfgAccessListForwardEntry 1001 }
    
    -- 1.3.6.1.4.1.119.2.3.69.213.502.5.3.21.4
    ipeCfgAccessListV6InputTable OBJECT-TYPE
        SYNTAX      SEQUENCE OF IpeCfgAccessListV6InputEntry
        ACCESS      not-accessible
        STATUS      mandatory
        DESCRIPTION
            "Table of Access List(Input Direction)."
        ::= { ipeCfgAccessListGroup 4 }
    
    -- 1.3.6.1.4.1.119.2.3.69.213.502.5.3.21.4.1
    ipeCfgAccessListV6InputEntry OBJECT-TYPE
        SYNTAX      IpeCfgAccessListV6InputEntry
        ACCESS      not-accessible
        STATUS      mandatory
        DESCRIPTION
            ""
        INDEX       { ipeCfgAccessListV6InputNEAddressAddrType, ipeCfgAccessListV6InputNEAddress, ipeCfgAccessListV6InputOrder }
        ::= { ipeCfgAccessListV6InputTable 1 }
    
    IpeCfgAccessListV6InputEntry ::= SEQUENCE {
        ipeCfgAccessListV6InputOrder                INTEGER,
        ipeCfgAccessListV6InputNEAddress            InetAddress,
        ipeCfgAccessListV6InputInIfIndex            INTEGER,
        ipeCfgAccessListV6InputSrcIpAddress         Ipv6Address,
        ipeCfgAccessListV6InputSrcPrefixLen         InetAddressPrefixLength,
        ipeCfgAccessListV6InputProtocol             INTEGER,
        ipeCfgAccessListV6InputDstPort              INTEGER,
        ipeCfgAccessListV6InputAction               INTEGER,
        ipeCfgAccessListV6InputRowStatus            RowStatus,
        ipeCfgAccessListV6InputNEAddressAddrType    InetAddressType
    }
    
    -- 1.3.6.1.4.1.119.2.3.69.213.502.5.3.21.4.1.1
    ipeCfgAccessListV6InputOrder OBJECT-TYPE
        SYNTAX      INTEGER (1..50)
        ACCESS      not-accessible
        STATUS      mandatory
        DESCRIPTION
            "Index of this table."
        ::= { ipeCfgAccessListV6InputEntry 1 }
    
    -- 1.3.6.1.4.1.119.2.3.69.213.502.5.3.21.4.1.2
    ipeCfgAccessListV6InputNEAddress OBJECT-TYPE
        SYNTAX      InetAddress
        ACCESS      not-accessible
        STATUS      mandatory
        DESCRIPTION
            "reserved"
        ::= { ipeCfgAccessListV6InputEntry 2 }
    
    -- 1.3.6.1.4.1.119.2.3.69.213.502.5.3.21.4.1.3
    ipeCfgAccessListV6InputInIfIndex OBJECT-TYPE
        SYNTAX      INTEGER { any(0), lct(2), inband(3), ne2(4), bridge1(11),
                        bridge2(12), bridge3(13), bridge4(14), bridge5(15),
                        bridge6(16), bridge7(17), bridge8(18), bridge9(19),
                        bridge10(20), bridge11(21), bridge12(22),
                        bridge13(23), bridge14(24), bridge15(25),
                        bridge16(26), bridge17(27), bridge18(28),
                        bridge19(29), bridge20(30) }
        ACCESS      read-only
        STATUS      mandatory
        DESCRIPTION
            "IP Access Control Input Filter Interface.
    
             The value 'inband' and 'ne2' are not supported."
        ::= { ipeCfgAccessListV6InputEntry 3 }
    
    -- 1.3.6.1.4.1.119.2.3.69.213.502.5.3.21.4.1.4
    ipeCfgAccessListV6InputSrcIpAddress OBJECT-TYPE
        SYNTAX      Ipv6Address
        ACCESS      read-only
        STATUS      mandatory
        DESCRIPTION
            "IP Access Control Input Filter Source IP Address"
        ::= { ipeCfgAccessListV6InputEntry 4 }
    
    -- 1.3.6.1.4.1.119.2.3.69.213.502.5.3.21.4.1.5
    ipeCfgAccessListV6InputSrcPrefixLen OBJECT-TYPE
        SYNTAX      InetAddressPrefixLength
        ACCESS      read-only
        STATUS      mandatory
        DESCRIPTION
            "IP Access Control Input Filter Source Prefix Length.
             '0' matches all IP addresses. i.e. '0' acts as 'Any'."
        ::= { ipeCfgAccessListV6InputEntry 5 }
    
    -- 1.3.6.1.4.1.119.2.3.69.213.502.5.3.21.4.1.6
    ipeCfgAccessListV6InputProtocol OBJECT-TYPE
        SYNTAX      INTEGER
        ACCESS      read-only
        STATUS      mandatory
        DESCRIPTION
            "IP Access Control Input Filter Protocol.
             '-1' acts as 'Any'."
        ::= { ipeCfgAccessListV6InputEntry 6 }
    
    -- 1.3.6.1.4.1.119.2.3.69.213.502.5.3.21.4.1.7
    ipeCfgAccessListV6InputDstPort OBJECT-TYPE
        SYNTAX      INTEGER
        ACCESS      read-only
        STATUS      mandatory
        DESCRIPTION
            "IP Access Control Input Filter Port Number.
             '-1' acts as 'Any'."
        ::= { ipeCfgAccessListV6InputEntry 7 }
    
    -- 1.3.6.1.4.1.119.2.3.69.213.502.5.3.21.4.1.8
    ipeCfgAccessListV6InputAction OBJECT-TYPE
        SYNTAX      INTEGER { permit(1), deny(2) }
        ACCESS      read-only
        STATUS      mandatory
        DESCRIPTION
            "IP Access Control Input Filter Action."
        ::= { ipeCfgAccessListV6InputEntry 8 }
    
    -- 1.3.6.1.4.1.119.2.3.69.213.502.5.3.21.4.1.9
    ipeCfgAccessListV6InputRowStatus OBJECT-TYPE
        SYNTAX      RowStatus
        ACCESS      read-only
        STATUS      mandatory
        DESCRIPTION
            "This RowStatus has a status only 'active(1)'.
    
             1) creating a entry
             When you make a new entry, you must SET objects indicated below.
             ipeCfgAccessListV6InputAction
             ipeCfgAccessListV6InputRowStatus <- createAndGo(4)
    
    
             When you are not setting a value of items as follows, it is set
             as 'any'.
             ipeCfgAccessListV6InputInIfIndex
             ipeCfgAccessListV6InputSrcIpAddress
             ipeCfgAccessListV6InputSrcPrefixLength(*1)
             ipeCfgAccessListV6InputProtocol
             ipeCfgAccessListV6InputDstPortNum(*2)
    
             *1 When you not set ipeCfgAccessListInputSrcIpAddress, even when
             ipeCfgAccessListV6InputSrcPrefixLength is set, it is set as
             'any'. When ipeCfgAccessListV6InputSrcIpAddress set to 'any',
             ipeCfgAccessListV6InputSrcPrefixLength is set as 'any'.
             *2 When you not set ipeCfgAccessListV6InputProtocol to '6' or
             '17', even when ipeCfgAccessListV6InputDstPortNum is set, it is
             set as 'any'.
    
             2) modifing a entry
             It isn't possible.
    
             3) deleting a entry
             When you SET a destroy(6) to ipeCfgAccessListV6InputRowStatus,
             the entry is destroyed."
        ::= { ipeCfgAccessListV6InputEntry 9 }
    
    -- 1.3.6.1.4.1.119.2.3.69.213.502.5.3.21.4.1.1001
    ipeCfgAccessListV6InputNEAddressAddrType OBJECT-TYPE
        SYNTAX      InetAddressType
        ACCESS      not-accessible
        STATUS      mandatory
        DESCRIPTION
            "Represents the IP address type of NE address index.
             Only ipv4(1) and ipv6(2) are supported."
        ::= { ipeCfgAccessListV6InputEntry 1001 }
    
    -- 1.3.6.1.4.1.119.2.3.69.213.502.5.3.21.5
    ipeCfgAccessListV6ForwardTable OBJECT-TYPE
        SYNTAX      SEQUENCE OF IpeCfgAccessListV6ForwardEntry
        ACCESS      not-accessible
        STATUS      mandatory
        DESCRIPTION
            "Table of Access List(Forward Direction)."
        ::= { ipeCfgAccessListGroup 5 }
    
    -- 1.3.6.1.4.1.119.2.3.69.213.502.5.3.21.5.1
    ipeCfgAccessListV6ForwardEntry OBJECT-TYPE
        SYNTAX      IpeCfgAccessListV6ForwardEntry
        ACCESS      not-accessible
        STATUS      mandatory
        DESCRIPTION
            ""
        INDEX       { ipeCfgAccessListV6ForwardNEAddressAddrType, ipeCfgAccessListV6ForwardNEAddress, ipeCfgAccessListV6ForwardOrder }
        ::= { ipeCfgAccessListV6ForwardTable 1 }
    
    IpeCfgAccessListV6ForwardEntry ::= SEQUENCE {
        ipeCfgAccessListV6ForwardOrder              INTEGER,
        ipeCfgAccessListV6ForwardNEAddress          InetAddress,
        ipeCfgAccessListV6ForwardInIfIndex          INTEGER,
        ipeCfgAccessListV6ForwardOutIfIndex         INTEGER,
        ipeCfgAccessListV6ForwardSrcIpAddress       Ipv6Address,
        ipeCfgAccessListV6ForwardSrcPrefixLen       InetAddressPrefixLength,
        ipeCfgAccessListV6ForwardDstIpAddress       Ipv6Address,
        ipeCfgAccessListV6ForwardDstPrefixLen       InetAddressPrefixLength,
        ipeCfgAccessListV6ForwardProtocol           INTEGER,
        ipeCfgAccessListV6ForwardSrcPort            INTEGER,
        ipeCfgAccessListV6ForwardDstPort            INTEGER,
        ipeCfgAccessListV6ForwardAction             INTEGER,
        ipeCfgAccessListV6ForwardRowStatus          RowStatus,
        ipeCfgAccessListV6ForwardNEAddressAddrType  InetAddressType
    }
    
    -- 1.3.6.1.4.1.119.2.3.69.213.502.5.3.21.5.1.1
    ipeCfgAccessListV6ForwardOrder OBJECT-TYPE
        SYNTAX      INTEGER (1..50)
        ACCESS      not-accessible
        STATUS      mandatory
        DESCRIPTION
            "Index of this table"
        ::= { ipeCfgAccessListV6ForwardEntry 1 }
    
    -- 1.3.6.1.4.1.119.2.3.69.213.502.5.3.21.5.1.2
    ipeCfgAccessListV6ForwardNEAddress OBJECT-TYPE
        SYNTAX      InetAddress
        ACCESS      not-accessible
        STATUS      mandatory
        DESCRIPTION
            "reserved"
        ::= { ipeCfgAccessListV6ForwardEntry 2 }
    
    -- 1.3.6.1.4.1.119.2.3.69.213.502.5.3.21.5.1.3
    ipeCfgAccessListV6ForwardInIfIndex OBJECT-TYPE
        SYNTAX      INTEGER { any(0), lct(2), inband(3), ne2(4), bridge1(11),
                        bridge2(12), bridge3(13), bridge4(14), bridge5(15),
                        bridge6(16), bridge7(17), bridge8(18), bridge9(19),
                        bridge10(20), bridge11(21), bridge12(22),
                        bridge13(23), bridge14(24), bridge15(25),
                        bridge16(26), bridge17(27), bridge18(28),
                        bridge19(29), bridge20(30) }
        ACCESS      read-only
        STATUS      mandatory
        DESCRIPTION
            "IP Access Control Forward Filter Input Interface.
    
             The value 'inband' and 'ne2' are not supported."
        ::= { ipeCfgAccessListV6ForwardEntry 3 }
    
    -- 1.3.6.1.4.1.119.2.3.69.213.502.5.3.21.5.1.4
    ipeCfgAccessListV6ForwardOutIfIndex OBJECT-TYPE
        SYNTAX      INTEGER { any(0), lct(2), inband(3), ne2(4), bridge1(11),
                        bridge2(12), bridge3(13), bridge4(14), bridge5(15),
                        bridge6(16), bridge7(17), bridge8(18), bridge9(19),
                        bridge10(20), bridge11(21), bridge12(22),
                        bridge13(23), bridge14(24), bridge15(25),
                        bridge16(26), bridge17(27), bridge18(28),
                        bridge19(29), bridge20(30) }
        ACCESS      read-only
        STATUS      mandatory
        DESCRIPTION
            "IP Access Control Forward Filter Input Interface.
    
             The value 'inband' and 'ne2' are not supported."
        ::= { ipeCfgAccessListV6ForwardEntry 4 }
    
    -- 1.3.6.1.4.1.119.2.3.69.213.502.5.3.21.5.1.5
    ipeCfgAccessListV6ForwardSrcIpAddress OBJECT-TYPE
        SYNTAX      Ipv6Address
        ACCESS      read-only
        STATUS      mandatory
        DESCRIPTION
            "IP Access Control Forward Filter Source IP Address."
        ::= { ipeCfgAccessListV6ForwardEntry 5 }
    
    -- 1.3.6.1.4.1.119.2.3.69.213.502.5.3.21.5.1.6
    ipeCfgAccessListV6ForwardSrcPrefixLen OBJECT-TYPE
        SYNTAX      InetAddressPrefixLength
        ACCESS      read-only
        STATUS      mandatory
        DESCRIPTION
            "IP Access Control Forward Filter Destination Prefix Length.
             '0' matches all IP addresses. i.e. '0' acts as 'Any'."
        ::= { ipeCfgAccessListV6ForwardEntry 6 }
    
    -- 1.3.6.1.4.1.119.2.3.69.213.502.5.3.21.5.1.7
    ipeCfgAccessListV6ForwardDstIpAddress OBJECT-TYPE
        SYNTAX      Ipv6Address
        ACCESS      read-only
        STATUS      mandatory
        DESCRIPTION
            "IP Access Control Forward Filter Destination IP Address."
        ::= { ipeCfgAccessListV6ForwardEntry 7 }
    
    -- 1.3.6.1.4.1.119.2.3.69.213.502.5.3.21.5.1.8
    ipeCfgAccessListV6ForwardDstPrefixLen OBJECT-TYPE
        SYNTAX      InetAddressPrefixLength
        ACCESS      read-only
        STATUS      mandatory
        DESCRIPTION
            "IP Access Control Forward Filter Destination Prefix Length.
             '0' matches all IP addresses. i.e. '0' acts as 'Any'."
        ::= { ipeCfgAccessListV6ForwardEntry 8 }
    
    -- 1.3.6.1.4.1.119.2.3.69.213.502.5.3.21.5.1.9
    ipeCfgAccessListV6ForwardProtocol OBJECT-TYPE
        SYNTAX      INTEGER
        ACCESS      read-only
        STATUS      mandatory
        DESCRIPTION
            "IP Access Control Forward Filter Protocol.
             '-1' acts as 'Any'."
        ::= { ipeCfgAccessListV6ForwardEntry 9 }
    
    -- 1.3.6.1.4.1.119.2.3.69.213.502.5.3.21.5.1.10
    ipeCfgAccessListV6ForwardSrcPort OBJECT-TYPE
        SYNTAX      INTEGER
        ACCESS      read-only
        STATUS      mandatory
        DESCRIPTION
            "IP Access Control Forward Filter Source Port Number.
             '-1' acts as 'Any'."
        ::= { ipeCfgAccessListV6ForwardEntry 10 }
    
    -- 1.3.6.1.4.1.119.2.3.69.213.502.5.3.21.5.1.11
    ipeCfgAccessListV6ForwardDstPort OBJECT-TYPE
        SYNTAX      INTEGER
        ACCESS      read-only
        STATUS      mandatory
        DESCRIPTION
            "IP Access Control Forward Filter Destination Port Number.
             '-1' acts as 'Any'."
        ::= { ipeCfgAccessListV6ForwardEntry 11 }
    
    -- 1.3.6.1.4.1.119.2.3.69.213.502.5.3.21.5.1.12
    ipeCfgAccessListV6ForwardAction OBJECT-TYPE
        SYNTAX      INTEGER { permit(1), deny(2) }
        ACCESS      read-only
        STATUS      mandatory
        DESCRIPTION
            "IP Access Control Forward Filter Action."
        ::= { ipeCfgAccessListV6ForwardEntry 12 }
    
    -- 1.3.6.1.4.1.119.2.3.69.213.502.5.3.21.5.1.13
    ipeCfgAccessListV6ForwardRowStatus OBJECT-TYPE
        SYNTAX      RowStatus
        ACCESS      read-only
        STATUS      mandatory
        DESCRIPTION
            "This RowStatus has a status only 'active(1)'.
    
             1) creating a entry
             When you make a new entry, you must SET objects indicated below.
             ipeCfgAccessListV6ForwardAction
             ipeCfgAccessListV6ForwardRowStatus <- createAndGo(4)
    
    
             When you are not setting a value of items as follows, it is set
             as 'any'.
             ipeCfgAccessListV6ForwardInIfIndex
             ipeCfgAccessListV6ForwardOutIfIndex
             ipeCfgAccessListV6ForwardSrcIpAddress
             ipeCfgAccessListV6ForwardSrcPrefixLength(*1)
             ipeCfgAccessListV6ForwardDstIpAddress
             ipeCfgAccessListV6ForwardDstPrefixLength(*2)
             ipeCfgAccessListV6ForwardProtocol
             ipeCfgAccessListV6ForwardSrcPortNum(*3)
             ipeCfgAccessListV6ForwardDstPortNum(*3)
    
             *1 When you not set ipeCfgAccessListV6ForwardSrcIpAddress, even
             when ipeCfgAccessListV6ForwardSrcPrefixLength is set, it is set
             as 'any'. When ipeCfgAccessListV6ForwardSrcIpAddress set to
             'any', ipeCfgAccessListV6ForwardSrcPrefixLength is set as 'any'.
             *2 When you not set ipeCfgAccessListV6ForwardDstIpAddress, even
             when ipeCfgAccessListV6ForwardDstPrefixLength is set, it is set
             as 'any'. When ipeCfgAccessListV6ForwardDstIpAddress set to
             'any', ipeCfgAccessListV6ForwardDstPrefixLength is set as 'any'.
             *3 When you not set ipeCfgAccessListV6ForwardProtocol to '6' or
             '17', even when ipeCfgAccessListV6ForwardSrcPortNum and
             ipeCfgAccessListV6ForwardDstPortNum are set, it is set as 'any'.
    
             2) modifing a entry
             It isn't possible.
    
             3) deleting a entry
             When you SET a destroy(6) to ipeCfgAccessListV6ForwardRowStatus,
             the entry is destroyed."
        ::= { ipeCfgAccessListV6ForwardEntry 13 }
    
    -- 1.3.6.1.4.1.119.2.3.69.213.502.5.3.21.5.1.1001
    ipeCfgAccessListV6ForwardNEAddressAddrType OBJECT-TYPE
        SYNTAX      InetAddressType
        ACCESS      not-accessible
        STATUS      mandatory
        DESCRIPTION
            "Represents the IP address type of NE address index.
             Only ipv4(1) and ipv6(2) are supported."
        ::= { ipeCfgAccessListV6ForwardEntry 1001 }
    
    -- 1.3.6.1.4.1.119.2.3.69.213.502.5.3.21.6
    ipeCfgAccessListDSCPTable OBJECT-TYPE
        SYNTAX      SEQUENCE OF IpeCfgAccessListDSCPEntry
        ACCESS      not-accessible
        STATUS      mandatory
        DESCRIPTION
            "Table of DSCP configuration information."
        ::= { ipeCfgAccessListGroup 6 }
    
    -- 1.3.6.1.4.1.119.2.3.69.213.502.5.3.21.6.1
    ipeCfgAccessListDSCPEntry OBJECT-TYPE
        SYNTAX      IpeCfgAccessListDSCPEntry
        ACCESS      not-accessible
        STATUS      mandatory
        DESCRIPTION
            "Entry of DSCP configuration information."
        INDEX       { ipeCfgAccessListDSCPNEAddressAddrType, ipeCfgAccessListDSCPNEAddress, ipeCfgAccessListDSCPIndex }
        ::= { ipeCfgAccessListDSCPTable 1 }
    
    IpeCfgAccessListDSCPEntry ::= SEQUENCE {
        ipeCfgAccessListDSCPIndex               INTEGER,
        ipeCfgAccessListDSCPNEAddress           InetAddress,
        ipeCfgAccessListDSCPValue               INTEGER,
        ipeCfgAccessListDSCPNEAddressAddrType   InetAddressType
    }
    
    -- 1.3.6.1.4.1.119.2.3.69.213.502.5.3.21.6.1.1
    ipeCfgAccessListDSCPIndex OBJECT-TYPE
        SYNTAX      INTEGER (1)
        ACCESS      not-accessible
        STATUS      mandatory
        DESCRIPTION
            "Index of this table. Only one instance is created."
        ::= { ipeCfgAccessListDSCPEntry 1 }
    
    -- 1.3.6.1.4.1.119.2.3.69.213.502.5.3.21.6.1.2
    ipeCfgAccessListDSCPNEAddress OBJECT-TYPE
        SYNTAX      InetAddress
        ACCESS      not-accessible
        STATUS      mandatory
        DESCRIPTION
            "reserved"
        ::= { ipeCfgAccessListDSCPEntry 2 }
    
    -- 1.3.6.1.4.1.119.2.3.69.213.502.5.3.21.6.1.3
    ipeCfgAccessListDSCPValue OBJECT-TYPE
        SYNTAX      INTEGER (0..63)
        ACCESS      read-only
        STATUS      mandatory
        DESCRIPTION
            "Indicates the DSCP value for the outgoing/forwarding packets
             from Bridge/LCT Interface in equipment unit."
        ::= { ipeCfgAccessListDSCPEntry 3 }
    
    -- 1.3.6.1.4.1.119.2.3.69.213.502.5.3.21.6.1.1001
    ipeCfgAccessListDSCPNEAddressAddrType OBJECT-TYPE
        SYNTAX      InetAddressType
        ACCESS      not-accessible
        STATUS      mandatory
        DESCRIPTION
            "Represents the IP address type of NE address index.
             Only ipv4(1) and ipv6(2) are supported."
        ::= { ipeCfgAccessListDSCPEntry 1001 }
    
    -- 1.3.6.1.4.1.119.2.3.69.213.502.5.3.22
    ipeCfgAutoIpGroup OBJECT IDENTIFIER
        ::= { ipeConfigurationGroup 22 }
    
    -- 1.3.6.1.4.1.119.2.3.69.213.502.5.3.22.1
    ipeCfgAutoIpTable OBJECT-TYPE
        SYNTAX      SEQUENCE OF IpeCfgAutoIpEntry
        ACCESS      not-accessible
        STATUS      mandatory
        DESCRIPTION
            "Table of AutoIP configuration information."
        ::= { ipeCfgAutoIpGroup 1 }
    
    -- 1.3.6.1.4.1.119.2.3.69.213.502.5.3.22.1.1
    ipeCfgAutoIpEntry OBJECT-TYPE
        SYNTAX      IpeCfgAutoIpEntry
        ACCESS      not-accessible
        STATUS      mandatory
        DESCRIPTION
            "Entry of AutoIP configuration information."
        INDEX       { ipeCfgAutoIpNEAddressAddrType, ipeCfgAutoIpNEAddress, ipeCfgAutoIpIndex }
        ::= { ipeCfgAutoIpTable 1 }
    
    IpeCfgAutoIpEntry ::= SEQUENCE {
        ipeCfgAutoIpIndex               INTEGER,
        ipeCfgAutoIpNEAddress           InetAddress,
        ipeCfgAutoIpNetworkAddress      IpAddress,
        ipeCfgAutoIpNetMask             IpAddress,
        ipeCfgAutoIpNEAddressAddrType   InetAddressType
    }
    
    -- 1.3.6.1.4.1.119.2.3.69.213.502.5.3.22.1.1.1
    ipeCfgAutoIpIndex OBJECT-TYPE
        SYNTAX      INTEGER (1)
        ACCESS      not-accessible
        STATUS      mandatory
        DESCRIPTION
            "Index of table.
             It's a fixed value(=1)."
        ::= { ipeCfgAutoIpEntry 1 }
    
    -- 1.3.6.1.4.1.119.2.3.69.213.502.5.3.22.1.1.2
    ipeCfgAutoIpNEAddress OBJECT-TYPE
        SYNTAX      InetAddress
        ACCESS      not-accessible
        STATUS      mandatory
        DESCRIPTION
            ""
        ::= { ipeCfgAutoIpEntry 2 }
    
    -- 1.3.6.1.4.1.119.2.3.69.213.502.5.3.22.1.1.3
    ipeCfgAutoIpNetworkAddress OBJECT-TYPE
        SYNTAX      IpAddress
        ACCESS      read-only
        STATUS      mandatory
        DESCRIPTION
            "Aggregation Net of AutoIP.
             A set value becomes a binary.
             Value range:0x00000000-0xdfffffff(0.0.0.0-223.255.255.255)
             If this value is changed in state of 'now setting' or 'automatic
             setting', AutoIP will set IP Address again."
        ::= { ipeCfgAutoIpEntry 3 }
    
    -- 1.3.6.1.4.1.119.2.3.69.213.502.5.3.22.1.1.4
    ipeCfgAutoIpNetMask OBJECT-TYPE
        SYNTAX      IpAddress
        ACCESS      read-only
        STATUS      mandatory
        DESCRIPTION
            "Aggregation NetMask of AutoIp.
             A set value becomes a binary.
             Value range:0x80000000-0xfffffffc(1-30bit)
             If this value is changed in state of 'now setting' or 'automatic
             setting', AutoIP will set IP Address again."
        ::= { ipeCfgAutoIpEntry 4 }
    
    -- 1.3.6.1.4.1.119.2.3.69.213.502.5.3.22.1.1.1001
    ipeCfgAutoIpNEAddressAddrType OBJECT-TYPE
        SYNTAX      InetAddressType
        ACCESS      not-accessible
        STATUS      mandatory
        DESCRIPTION
            "Represents the IP address type of NE address index.
             Only ipv4(1) and ipv6(2) are supported."
        ::= { ipeCfgAutoIpEntry 1001 }
    
    -- 1.3.6.1.4.1.119.2.3.69.213.502.5.3.25
    ipeCfgSysNE1PortTable OBJECT-TYPE
        SYNTAX      SEQUENCE OF IpeCfgSysNE1PortEntry
        ACCESS      not-accessible
        STATUS      mandatory
        DESCRIPTION
            "NE1 Port Mode Configuration Table."
        ::= { ipeConfigurationGroup 25 }
    
    -- 1.3.6.1.4.1.119.2.3.69.213.502.5.3.25.1
    ipeCfgSysNE1PortEntry OBJECT-TYPE
        SYNTAX      IpeCfgSysNE1PortEntry
        ACCESS      not-accessible
        STATUS      mandatory
        DESCRIPTION
            ""
        INDEX       { ipeCfgSysNE1PortNEAddressAddrType, ipeCfgSysNE1PortNEAddress, ipeCfgSysNE1PortIndex }
        ::= { ipeCfgSysNE1PortTable 1 }
    
    IpeCfgSysNE1PortEntry ::= SEQUENCE {
        ipeCfgSysNE1PortIndex               INTEGER,
        ipeCfgSysNE1PortNEAddress           InetAddress,
        ipeCfgSysNE1PortMode                INTEGER,
        ipeCfgSysNE1PortNEAddressAddrType   InetAddressType
    }
    
    -- 1.3.6.1.4.1.119.2.3.69.213.502.5.3.25.1.1
    ipeCfgSysNE1PortIndex OBJECT-TYPE
        SYNTAX      INTEGER (1)
        ACCESS      not-accessible
        STATUS      mandatory
        DESCRIPTION
            "Index of this table."
        ::= { ipeCfgSysNE1PortEntry 1 }
    
    -- 1.3.6.1.4.1.119.2.3.69.213.502.5.3.25.1.2
    ipeCfgSysNE1PortNEAddress OBJECT-TYPE
        SYNTAX      InetAddress
        ACCESS      not-accessible
        STATUS      mandatory
        DESCRIPTION
            ""
        ::= { ipeCfgSysNE1PortEntry 2 }
    
    -- 1.3.6.1.4.1.119.2.3.69.213.502.5.3.25.1.3
    ipeCfgSysNE1PortMode OBJECT-TYPE
        SYNTAX      INTEGER { invalid(0), userPort(1), mgmtPort(2) }
        ACCESS      read-only
        STATUS      mandatory
        DESCRIPTION
            "NE1 Port Mode Configuration
             This value is not available [iPASOLINK EX Advanced]"
        DEFVAL      { userPort }
        ::= { ipeCfgSysNE1PortEntry 3 }
    
    -- 1.3.6.1.4.1.119.2.3.69.213.502.5.3.25.1.1001
    ipeCfgSysNE1PortNEAddressAddrType OBJECT-TYPE
        SYNTAX      InetAddressType
        ACCESS      not-accessible
        STATUS      mandatory
        DESCRIPTION
            "Represents the IP address type of NE address index.
             Only ipv4(1) and ipv6(2) are supported."
        ::= { ipeCfgSysNE1PortEntry 1001 }
    
    -- 1.3.6.1.4.1.119.2.3.69.213.502.5.3.27
    ipeCfgRadiusGroup OBJECT IDENTIFIER
        ::= { ipeConfigurationGroup 27 }
    
    -- 1.3.6.1.4.1.119.2.3.69.213.502.5.3.27.1
    ipeCfgRadiusGeneralTable OBJECT-TYPE
        SYNTAX      SEQUENCE OF IpeCfgRadiusGeneralEntry
        ACCESS      not-accessible
        STATUS      mandatory
        DESCRIPTION
            "Configure RADIUS parameters."
        ::= { ipeCfgRadiusGroup 1 }
    
    -- 1.3.6.1.4.1.119.2.3.69.213.502.5.3.27.1.1
    ipeCfgRadiusGeneralEntry OBJECT-TYPE
        SYNTAX      IpeCfgRadiusGeneralEntry
        ACCESS      not-accessible
        STATUS      mandatory
        DESCRIPTION
            "..."
        INDEX       { ipeCfgRadiusGeneralNEAddressAddrType, ipeCfgRadiusGeneralNEAddress, ipeCfgRadiusGeneralIndex }
        ::= { ipeCfgRadiusGeneralTable 1 }
    
    IpeCfgRadiusGeneralEntry ::= SEQUENCE {
        ipeCfgRadiusGeneralIndex                    INTEGER,
        ipeCfgRadiusGeneralNEAddress                InetAddress,
        ipeCfgRadiusGeneralAuthClientRetransmit     INTEGER,
        ipeCfgRadiusGeneralAuthClientTimeout        INTEGER,
        ipeCfgRadiusGeneralNEAddressAddrType        InetAddressType
    }
    
    -- 1.3.6.1.4.1.119.2.3.69.213.502.5.3.27.1.1.1
    ipeCfgRadiusGeneralIndex OBJECT-TYPE
        SYNTAX      INTEGER (1)
        ACCESS      not-accessible
        STATUS      mandatory
        DESCRIPTION
            "The index of this table."
        ::= { ipeCfgRadiusGeneralEntry 1 }
    
    -- 1.3.6.1.4.1.119.2.3.69.213.502.5.3.27.1.1.2
    ipeCfgRadiusGeneralNEAddress OBJECT-TYPE
        SYNTAX      InetAddress
        ACCESS      not-accessible
        STATUS      mandatory
        DESCRIPTION
            "Reserved object for northbound interface."
        ::= { ipeCfgRadiusGeneralEntry 2 }
    
    -- 1.3.6.1.4.1.119.2.3.69.213.502.5.3.27.1.1.3
    ipeCfgRadiusGeneralAuthClientRetransmit OBJECT-TYPE
        SYNTAX      INTEGER (0..255)
        ACCESS      read-only
        STATUS      mandatory
        DESCRIPTION
            "Indicate maximum retransmit number of Access-Request
             message.
             The system retransmits Access-Request message to server
             according to this configuration."
        DEFVAL      { 3 }
        ::= { ipeCfgRadiusGeneralEntry 3 }
    
    -- 1.3.6.1.4.1.119.2.3.69.213.502.5.3.27.1.1.4
    ipeCfgRadiusGeneralAuthClientTimeout OBJECT-TYPE
        SYNTAX      INTEGER (0..65535)
        ACCESS      read-only
        STATUS      mandatory
        DESCRIPTION
            "Indicate timeout period for response to Access-Request
             message.
             In case response (Access-Accept message) is not received
             in this period, the system will retransmit message."
        DEFVAL      { 10 }
        ::= { ipeCfgRadiusGeneralEntry 4 }
    
    -- 1.3.6.1.4.1.119.2.3.69.213.502.5.3.27.1.1.1001
    ipeCfgRadiusGeneralNEAddressAddrType OBJECT-TYPE
        SYNTAX      InetAddressType
        ACCESS      not-accessible
        STATUS      mandatory
        DESCRIPTION
            "Represents the IP address type of NE address index.
             Only ipv4(1) and ipv6(2) are supported."
        ::= { ipeCfgRadiusGeneralEntry 1001 }
    
    -- 1.3.6.1.4.1.119.2.3.69.213.502.5.3.27.2
    ipeCfgRadiusAuthServerExtTable OBJECT-TYPE
        SYNTAX      SEQUENCE OF IpeCfgRadiusAuthServerExtEntry
        ACCESS      not-accessible
        STATUS      mandatory
        DESCRIPTION
            "Configure RADIUS authentication server parameters."
        ::= { ipeCfgRadiusGroup 2 }
    
    -- 1.3.6.1.4.1.119.2.3.69.213.502.5.3.27.2.1
    ipeCfgRadiusAuthServerExtEntry OBJECT-TYPE
        SYNTAX      IpeCfgRadiusAuthServerExtEntry
        ACCESS      not-accessible
        STATUS      mandatory
        DESCRIPTION
            "..."
        INDEX       { ipeCfgRadiusAuthServerNEAddressAddrType, ipeCfgRadiusAuthServerNEAddress, ipeCfgRadiusAuthServerExtIndex }
        ::= { ipeCfgRadiusAuthServerExtTable 1 }
    
    IpeCfgRadiusAuthServerExtEntry ::= SEQUENCE {
        ipeCfgRadiusAuthServerExtIndex              INTEGER,
        ipeCfgRadiusAuthServerNEAddress             InetAddress,
        ipeCfgRadiusAuthServerAddressType           INTEGER,
        ipeCfgRadiusAuthServerAddress               IpAddress,
        ipeCfgRadiusAuthClientServerPortNumber      INTEGER,
        ipeCfgRadiusAuthClientPasswordType          INTEGER,
        ipeCfgRadiusAuthClientSecretKey             DisplayString,
        ipeCfgRadiusAuthServerExtRowStatus          RowStatus,
        ipeCfgRadiusAuthServerNEAddressAddrType     InetAddressType
    }
    
    -- 1.3.6.1.4.1.119.2.3.69.213.502.5.3.27.2.1.1
    ipeCfgRadiusAuthServerExtIndex OBJECT-TYPE
        SYNTAX      INTEGER (1..3)
        ACCESS      not-accessible
        STATUS      mandatory
        DESCRIPTION
            "The index of this table."
        ::= { ipeCfgRadiusAuthServerExtEntry 1 }
    
    -- 1.3.6.1.4.1.119.2.3.69.213.502.5.3.27.2.1.2
    ipeCfgRadiusAuthServerNEAddress OBJECT-TYPE
        SYNTAX      InetAddress
        ACCESS      not-accessible
        STATUS      mandatory
        DESCRIPTION
            "Reserved object for northbound interface."
        ::= { ipeCfgRadiusAuthServerExtEntry 2 }
    
    -- 1.3.6.1.4.1.119.2.3.69.213.502.5.3.27.2.1.3
    ipeCfgRadiusAuthServerAddressType OBJECT-TYPE
        SYNTAX      INTEGER { invalid(0), ipv4(1), ipv6(2) }
        ACCESS      read-only
        STATUS      mandatory
        DESCRIPTION
            "Indicate IP address type of this server.
    
             ipv4 : server has IPv4 address.
             ipv6 : server has IPv6 address. (NOT SUPPORTED)
    
             ipv6 will be supprted in future version."
        DEFVAL      { ipv4 }
        ::= { ipeCfgRadiusAuthServerExtEntry 3 }
    
    -- 1.3.6.1.4.1.119.2.3.69.213.502.5.3.27.2.1.4
    ipeCfgRadiusAuthServerAddress OBJECT-TYPE
        SYNTAX      IpAddress
        ACCESS      read-only
        STATUS      mandatory
        DESCRIPTION
            "Indicate IP address of this server."
        ::= { ipeCfgRadiusAuthServerExtEntry 4 }
    
    -- 1.3.6.1.4.1.119.2.3.69.213.502.5.3.27.2.1.5
    ipeCfgRadiusAuthClientServerPortNumber OBJECT-TYPE
        SYNTAX      INTEGER (0..65535)
        ACCESS      read-only
        STATUS      mandatory
        DESCRIPTION
            "Indicate port number of RADIUS authentication protocol on
             this server."
        DEFVAL      { 1812 }
        ::= { ipeCfgRadiusAuthServerExtEntry 5 }
    
    -- 1.3.6.1.4.1.119.2.3.69.213.502.5.3.27.2.1.6
    ipeCfgRadiusAuthClientPasswordType OBJECT-TYPE
        SYNTAX      INTEGER { invalid(0), user(1), chap(2) }
        ACCESS      read-only
        STATUS      mandatory
        DESCRIPTION
            "Indicate password authentication type. The system select
             password attribute on Access-Request message.
    
             user : use User-Password attribute.
             chap : use CHAP-Password attribute.
    
             See RFC 2865 for details."
        DEFVAL      { user }
        ::= { ipeCfgRadiusAuthServerExtEntry 6 }
    
    -- 1.3.6.1.4.1.119.2.3.69.213.502.5.3.27.2.1.7
    ipeCfgRadiusAuthClientSecretKey OBJECT-TYPE
        SYNTAX      DisplayString (SIZE(8..128))
        ACCESS      read-only
        STATUS      mandatory
        DESCRIPTION
            "Indicate RADIUS shared secret. This object can be operated only
             when in secure way. This object is used to confirm  received
             RADIUS message is
             sent from authenticated server.
             This object is also used to encrypt User-Password attribute
             on Access-Request message.
             See RFC 2865 for details.
    
             The secret key(before encryption) range is 1-63 characters.
             The characters which can be used are '-', '_','0'-'9',
             'a'-'z' and 'A'-'Z'."
        ::= { ipeCfgRadiusAuthServerExtEntry 7 }
    
    -- 1.3.6.1.4.1.119.2.3.69.213.502.5.3.27.2.1.8
    ipeCfgRadiusAuthServerExtRowStatus OBJECT-TYPE
        SYNTAX      RowStatus
        ACCESS      read-only
        STATUS      mandatory
        DESCRIPTION
            "The row status of this table."
        ::= { ipeCfgRadiusAuthServerExtEntry 8 }
    
    -- 1.3.6.1.4.1.119.2.3.69.213.502.5.3.27.2.1.1001
    ipeCfgRadiusAuthServerNEAddressAddrType OBJECT-TYPE
        SYNTAX      InetAddressType
        ACCESS      not-accessible
        STATUS      mandatory
        DESCRIPTION
            "Represents the IP address type of NE address index.
             Only ipv4(1) and ipv6(2) are supported."
        ::= { ipeCfgRadiusAuthServerExtEntry 1001 }
    
    -- 1.3.6.1.4.1.119.2.3.69.213.502.5.3.27.3
    ipeCfgRadiusPrivLevelGeneralTable OBJECT-TYPE
        SYNTAX      SEQUENCE OF IpeCfgRadiusPrivLevelGeneralEntry
        ACCESS      not-accessible
        STATUS      mandatory
        DESCRIPTION
            "Configure general privilege level for RADIUS
             authetication."
        ::= { ipeCfgRadiusGroup 3 }
    
    -- 1.3.6.1.4.1.119.2.3.69.213.502.5.3.27.3.1
    ipeCfgRadiusPrivLevelGeneralEntry OBJECT-TYPE
        SYNTAX      IpeCfgRadiusPrivLevelGeneralEntry
        ACCESS      not-accessible
        STATUS      mandatory
        DESCRIPTION
            "..."
        INDEX       { ipeCfgRadiusPrivLevelGeneralNEAddressAddrType, ipeCfgRadiusPrivLevelGeneralNEAddress, ipeCfgRadiusPrivLevelGeneralIndex }
        ::= { ipeCfgRadiusPrivLevelGeneralTable 1 }
    
    IpeCfgRadiusPrivLevelGeneralEntry ::= SEQUENCE {
        ipeCfgRadiusPrivLevelGeneralIndex               INTEGER,
        ipeCfgRadiusPrivLevelGeneralNEAddress           InetAddress,
        ipeCfgRadiusPrivLevelGeneralDefaultAction       INTEGER,
        ipeCfgRadiusPrivLevelGeneralDefaultGroup        DisplayString,
        ipeCfgRadiusPrivLevelGeneralNEAddressAddrType   InetAddressType
    }
    
    -- 1.3.6.1.4.1.119.2.3.69.213.502.5.3.27.3.1.1
    ipeCfgRadiusPrivLevelGeneralIndex OBJECT-TYPE
        SYNTAX      INTEGER (1)
        ACCESS      not-accessible
        STATUS      mandatory
        DESCRIPTION
            "The index of this table."
        ::= { ipeCfgRadiusPrivLevelGeneralEntry 1 }
    
    -- 1.3.6.1.4.1.119.2.3.69.213.502.5.3.27.3.1.2
    ipeCfgRadiusPrivLevelGeneralNEAddress OBJECT-TYPE
        SYNTAX      InetAddress
        ACCESS      not-accessible
        STATUS      mandatory
        DESCRIPTION
            "Reserved object for northbound interface."
        ::= { ipeCfgRadiusPrivLevelGeneralEntry 2 }
    
    -- 1.3.6.1.4.1.119.2.3.69.213.502.5.3.27.3.1.3
    ipeCfgRadiusPrivLevelGeneralDefaultAction OBJECT-TYPE
        SYNTAX      INTEGER { invalid(0), denyLogin(1), useDefaultGroup(2) }
        ACCESS      read-only
        STATUS      mandatory
        DESCRIPTION
            "Indicate system default action in case privilege level
             is not specified on Access-Accept message or received
             privilege level is set to disable in
             ipeCfgRadiusGroupPrivLevelMappingEnable.
    
             denyLogin       : deny login.
             useDefaultGroup : use group specified in
                               ipeCfgRadiusPrivLevelGeneralDefaultGroup."
        DEFVAL      { useDefaultGroup }
        ::= { ipeCfgRadiusPrivLevelGeneralEntry 3 }
    
    -- 1.3.6.1.4.1.119.2.3.69.213.502.5.3.27.3.1.4
    ipeCfgRadiusPrivLevelGeneralDefaultGroup OBJECT-TYPE
        SYNTAX      DisplayString (SIZE(1..32))
        ACCESS      read-only
        STATUS      mandatory
        DESCRIPTION
            "Indicate default group in case privilege level is not
             specified.
             This object is effective only if
             ipeCfgRadiusPrivLevelGeneralDefaultAction is
             useDefaultGroup.
    
             The value of this object should be registered group name in
             the system (as ipeCfgAccountGroupName).
    
             The characters which can be used are '-', '_','0'-'9',
             'a'-'z' and 'A'-'Z'."
        DEFVAL      { "Operator" }
        ::= { ipeCfgRadiusPrivLevelGeneralEntry 4 }
    
    -- 1.3.6.1.4.1.119.2.3.69.213.502.5.3.27.3.1.1001
    ipeCfgRadiusPrivLevelGeneralNEAddressAddrType OBJECT-TYPE
        SYNTAX      InetAddressType
        ACCESS      not-accessible
        STATUS      mandatory
        DESCRIPTION
            "Represents the IP address type of NE address index.
             Only ipv4(1) and ipv6(2) are supported."
        ::= { ipeCfgRadiusPrivLevelGeneralEntry 1001 }
    
    -- 1.3.6.1.4.1.119.2.3.69.213.502.5.3.27.4
    ipeCfgRadiusGroupPrivLevelMappingTable OBJECT-TYPE
        SYNTAX      SEQUENCE OF IpeCfgRadiusGroupPrivLevelMappingEntry
        ACCESS      not-accessible
        STATUS      mandatory
        DESCRIPTION
            "Configure privilege level mapping for RADIUS
             authentication."
        ::= { ipeCfgRadiusGroup 4 }
    
    -- 1.3.6.1.4.1.119.2.3.69.213.502.5.3.27.4.1
    ipeCfgRadiusGroupPrivLevelMappingEntry OBJECT-TYPE
        SYNTAX      IpeCfgRadiusGroupPrivLevelMappingEntry
        ACCESS      not-accessible
        STATUS      mandatory
        DESCRIPTION
            "..."
        INDEX       { ipeCfgRadiusGroupPrivLevelMappingNEAddressAddrType, ipeCfgRadiusGroupPrivLevelMappingNEAddress, ipeCfgRadiusGroupPrivLevelMappingPrivLevel }
        ::= { ipeCfgRadiusGroupPrivLevelMappingTable 1 }
    
    IpeCfgRadiusGroupPrivLevelMappingEntry ::= SEQUENCE {
        ipeCfgRadiusGroupPrivLevelMappingPrivLevel          INTEGER,
        ipeCfgRadiusGroupPrivLevelMappingNEAddress          InetAddress,
        ipeCfgRadiusGroupPrivLevelMappingEnable             INTEGER,
        ipeCfgRadiusGroupPrivLevelMappingGroup              DisplayString,
        ipeCfgRadiusGroupPrivLevelMappingNEAddressAddrType  InetAddressType
    }
    
    -- 1.3.6.1.4.1.119.2.3.69.213.502.5.3.27.4.1.1
    ipeCfgRadiusGroupPrivLevelMappingPrivLevel OBJECT-TYPE
        SYNTAX      INTEGER (0..15)
        ACCESS      not-accessible
        STATUS      mandatory
        DESCRIPTION
            "The index of this table.
             The value corresponds to received privilege level on
             Access-Accept message."
        ::= { ipeCfgRadiusGroupPrivLevelMappingEntry 1 }
    
    -- 1.3.6.1.4.1.119.2.3.69.213.502.5.3.27.4.1.2
    ipeCfgRadiusGroupPrivLevelMappingNEAddress OBJECT-TYPE
        SYNTAX      InetAddress
        ACCESS      not-accessible
        STATUS      mandatory
        DESCRIPTION
            "Reserved object for northbound interface."
        ::= { ipeCfgRadiusGroupPrivLevelMappingEntry 2 }
    
    -- 1.3.6.1.4.1.119.2.3.69.213.502.5.3.27.4.1.3
    ipeCfgRadiusGroupPrivLevelMappingEnable OBJECT-TYPE
        SYNTAX      INTEGER { invalid(0), disable(1), enable(2) }
        ACCESS      read-only
        STATUS      mandatory
        DESCRIPTION
            "Enable or disable privilege level mapping on this
             privilege level.
    
             disable : privilege level mapping is disabled.
             enable  : privilege level mapping is enabled.
    
             The system default value of this object shown below.
    
             PrivLevel=1, 7, 15 : enable
             other PrivLevel    : disable
    
             In case this object is set to disable, the system
             behave according to
             ipeCfgRadiusPrivLevelGeneralDefaultAction."
        DEFVAL      { disable }
        ::= { ipeCfgRadiusGroupPrivLevelMappingEntry 3 }
    
    -- 1.3.6.1.4.1.119.2.3.69.213.502.5.3.27.4.1.4
    ipeCfgRadiusGroupPrivLevelMappingGroup OBJECT-TYPE
        SYNTAX      DisplayString (SIZE(1..32))
        ACCESS      read-only
        STATUS      mandatory
        DESCRIPTION
            "Indicate group name correspond to privilege level.
             This object is effective only if
             ipeCfgRadiusGroupPrivLevelMappingEnable is enable.
             When the system received Access-Accept message with certain
             privilege level, login user has same privilege as this
             group.
    
             The system default value of this object shown below.
    
             PrivLevel=1  : Operator
             PrivLevel=7  : Config
             PrivLevel=15 : Admin
    
             The value should be registered group name registerd in
             the system (as ipeCfgAccountGroupName).
             The characters which can be used are '-', '_','0'-'9',
             'a'-'z' and 'A'-'Z'."
        ::= { ipeCfgRadiusGroupPrivLevelMappingEntry 4 }
    
    -- 1.3.6.1.4.1.119.2.3.69.213.502.5.3.27.4.1.1001
    ipeCfgRadiusGroupPrivLevelMappingNEAddressAddrType OBJECT-TYPE
        SYNTAX      InetAddressType
        ACCESS      not-accessible
        STATUS      mandatory
        DESCRIPTION
            "Represents the IP address type of NE address index.
             Only ipv4(1) and ipv6(2) are supported."
        ::= { ipeCfgRadiusGroupPrivLevelMappingEntry 1001 }
    
    -- 1.3.6.1.4.1.119.2.3.69.213.502.5.3.28
    ipeCfgLldpGroup OBJECT IDENTIFIER
        ::= { ipeConfigurationGroup 28 }
    
    -- 1.3.6.1.4.1.119.2.3.69.213.502.5.3.28.1
    ipeCfgLldpTable OBJECT-TYPE
        SYNTAX      SEQUENCE OF IpeCfgLldpEntry
        ACCESS      not-accessible
        STATUS      mandatory
        DESCRIPTION
            "LLDP set up information table."
        ::= { ipeCfgLldpGroup 1 }
    
    -- 1.3.6.1.4.1.119.2.3.69.213.502.5.3.28.1.1
    ipeCfgLldpEntry OBJECT-TYPE
        SYNTAX      IpeCfgLldpEntry
        ACCESS      not-accessible
        STATUS      mandatory
        DESCRIPTION
            "entry of LLDP set up information table."
        INDEX       { ipeCfgLldpNEAddressAddrType, ipeCfgLldpNEAddress, ipeCfgLldpIndex }
        ::= { ipeCfgLldpTable 1 }
    
    IpeCfgLldpEntry ::= SEQUENCE {
        ipeCfgLldpIndex                         INTEGER,
        ipeCfgLldpNEAddress                     InetAddress,
        ipeCfgLldpProprietaryModeMacAddress     MacAddress,
        ipeCfgLldpNEAddressAddrType             InetAddressType
    }
    
    -- 1.3.6.1.4.1.119.2.3.69.213.502.5.3.28.1.1.1
    ipeCfgLldpIndex OBJECT-TYPE
        SYNTAX      INTEGER (1)
        ACCESS      not-accessible
        STATUS      mandatory
        DESCRIPTION
            "The index of this table."
        ::= { ipeCfgLldpEntry 1 }
    
    -- 1.3.6.1.4.1.119.2.3.69.213.502.5.3.28.1.1.2
    ipeCfgLldpNEAddress OBJECT-TYPE
        SYNTAX      InetAddress
        ACCESS      not-accessible
        STATUS      mandatory
        DESCRIPTION
            "reserved."
        ::= { ipeCfgLldpEntry 2 }
    
    -- 1.3.6.1.4.1.119.2.3.69.213.502.5.3.28.1.1.3
    ipeCfgLldpProprietaryModeMacAddress OBJECT-TYPE
        SYNTAX      MacAddress
        ACCESS      read-only
        STATUS      mandatory
        DESCRIPTION
            "MAC address of LLDP Frame in NEC mode.
             This object is effective only if ipeCfgPortXXXXXLldpMode is set
             to proprietaryMode."
        DEFVAL      { '01004c01da50'H }
        ::= { ipeCfgLldpEntry 3 }
    
    -- 1.3.6.1.4.1.119.2.3.69.213.502.5.3.28.1.1.1001
    ipeCfgLldpNEAddressAddrType OBJECT-TYPE
        SYNTAX      InetAddressType
        ACCESS      not-accessible
        STATUS      mandatory
        DESCRIPTION
            "Represents the IP address type of NE address index.
             Only ipv4(1) and ipv6(2) are supported."
        ::= { ipeCfgLldpEntry 1001 }
    
    -- 1.3.6.1.4.1.119.2.3.69.213.502.5.3.29
    ipeCfgMgmtTrafficGrop OBJECT IDENTIFIER
        ::= { ipeConfigurationGroup 29 }
    
    -- 1.3.6.1.4.1.119.2.3.69.213.502.5.3.29.1
    ipeCfgMgmtTrafficControlTable OBJECT-TYPE
        SYNTAX      SEQUENCE OF IpeCfgMgmtTrafficControlEntry
        ACCESS      not-accessible
        STATUS      mandatory
        DESCRIPTION
            "This table configures the M-plane traffic."
        ::= { ipeCfgMgmtTrafficGrop 1 }
    
    -- 1.3.6.1.4.1.119.2.3.69.213.502.5.3.29.1.1
    ipeCfgMgmtTrafficControlEntry OBJECT-TYPE
        SYNTAX      IpeCfgMgmtTrafficControlEntry
        ACCESS      not-accessible
        STATUS      mandatory
        DESCRIPTION
            ""
        INDEX       { ipeCfgMgmtTrafficControlNEAddressAddrType, ipeCfgMgmtTrafficControlNEAddress, ipeCfgMgmtTrafficControlIndex }
        ::= { ipeCfgMgmtTrafficControlTable 1 }
    
    IpeCfgMgmtTrafficControlEntry ::= SEQUENCE {
        ipeCfgMgmtTrafficControlIndex               INTEGER,
        ipeCfgMgmtTrafficControlNEAddress           InetAddress,
        ipeCfgMgmtTrafficRate                       INTEGER,
        ipeCfgMgmtTraffcEgressCos                   INTEGER,
        ipeCfgMgmtTrafficControlNEAddressAddrType   InetAddressType
    }
    
    -- 1.3.6.1.4.1.119.2.3.69.213.502.5.3.29.1.1.1
    ipeCfgMgmtTrafficControlIndex OBJECT-TYPE
        SYNTAX      INTEGER (1)
        ACCESS      not-accessible
        STATUS      mandatory
        DESCRIPTION
            "Indef of this table."
        ::= { ipeCfgMgmtTrafficControlEntry 1 }
    
    -- 1.3.6.1.4.1.119.2.3.69.213.502.5.3.29.1.1.2
    ipeCfgMgmtTrafficControlNEAddress OBJECT-TYPE
        SYNTAX      InetAddress
        ACCESS      not-accessible
        STATUS      mandatory
        DESCRIPTION
            "reserved."
        ::= { ipeCfgMgmtTrafficControlEntry 2 }
    
    -- 1.3.6.1.4.1.119.2.3.69.213.502.5.3.29.1.1.3
    ipeCfgMgmtTrafficRate OBJECT-TYPE
        SYNTAX      INTEGER (0 | 500..10000)
        ACCESS      read-only
        STATUS      mandatory
        DESCRIPTION
            "The maximum bandwidth of M-plane traffic.
             This object limits the rate of ingress traffic and limits the
             rate of egress traffic to Radio Link (i.e. excluding the
             NMS/NE1/Inband traffic).
    
             Value '0' means the rate limit is disabled.
    
    
             range: 0,500~10000[iPASOLINK200/400/1000series/EX/iX],
                    0,500~ 2000[iPASOLINK VR series]"
        ::= { ipeCfgMgmtTrafficControlEntry 3 }
    
    -- 1.3.6.1.4.1.119.2.3.69.213.502.5.3.29.1.1.4
    ipeCfgMgmtTraffcEgressCos OBJECT-TYPE
        SYNTAX      INTEGER (0..8)
        ACCESS      read-only
        STATUS      mandatory
        DESCRIPTION
            "CoS value for M-plane egress traffic to Radio Link.
             When the CPU sends M-plane data to the Radio link, the frame has
             the CoS value which is configured by this object.
             And the agent controls the priority of egress traffic depending
             on this CoS value.
    
             range: 5~7[iPASOLINK200/400/1000series/EX/iX],
                    0~7,8(highest)[iPASOLINK VR series]"
        ::= { ipeCfgMgmtTrafficControlEntry 4 }
    
    -- 1.3.6.1.4.1.119.2.3.69.213.502.5.3.29.1.1.1001
    ipeCfgMgmtTrafficControlNEAddressAddrType OBJECT-TYPE
        SYNTAX      InetAddressType
        ACCESS      not-accessible
        STATUS      mandatory
        DESCRIPTION
            "Represents the IP address type of NE address index.
             Only ipv4(1) and ipv6(2) are supported."
        ::= { ipeCfgMgmtTrafficControlEntry 1001 }
    
    -- 1.3.6.1.4.1.119.2.3.69.213.502.5.3.30
    ipeCfgMgmtInterfaceGroup OBJECT IDENTIFIER
        ::= { ipeConfigurationGroup 30 }
    
    -- 1.3.6.1.4.1.119.2.3.69.213.502.5.3.30.1
    ipeCfgMplaneInterfaceModeTable OBJECT-TYPE
        SYNTAX      SEQUENCE OF IpeCfgMplaneInterfaceModeEntry
        ACCESS      not-accessible
        STATUS      mandatory
        DESCRIPTION
            "This table contains management interface mode information."
        ::= { ipeCfgMgmtInterfaceGroup 1 }
    
    -- 1.3.6.1.4.1.119.2.3.69.213.502.5.3.30.1.1
    ipeCfgMplaneInterfaceModeEntry OBJECT-TYPE
        SYNTAX      IpeCfgMplaneInterfaceModeEntry
        ACCESS      not-accessible
        STATUS      mandatory
        DESCRIPTION
            ""
        INDEX       { ipeCfgMplaneInterfaceNEAddressAddrType, ipeCfgMplaneInterfaceNEAddress, ipeCfgMplaneInterfaceModeIndex }
        ::= { ipeCfgMplaneInterfaceModeTable 1 }
    
    IpeCfgMplaneInterfaceModeEntry ::= SEQUENCE {
        ipeCfgMplaneInterfaceModeIndex          INTEGER,
        ipeCfgMplaneInterfaceNEAddress          InetAddress,
        ipeCfgMplaneInterfaceMode               INTEGER,
        ipeCfgMplaneInterfaceNEAddressAddrType  InetAddressType
    }
    
    -- 1.3.6.1.4.1.119.2.3.69.213.502.5.3.30.1.1.1
    ipeCfgMplaneInterfaceModeIndex OBJECT-TYPE
        SYNTAX      INTEGER (1)
        ACCESS      not-accessible
        STATUS      mandatory
        DESCRIPTION
            "Index of this table."
        ::= { ipeCfgMplaneInterfaceModeEntry 1 }
    
    -- 1.3.6.1.4.1.119.2.3.69.213.502.5.3.30.1.1.2
    ipeCfgMplaneInterfaceNEAddress OBJECT-TYPE
        SYNTAX      InetAddress
        ACCESS      not-accessible
        STATUS      mandatory
        DESCRIPTION
            "reserved."
        ::= { ipeCfgMplaneInterfaceModeEntry 2 }
    
    -- 1.3.6.1.4.1.119.2.3.69.213.502.5.3.30.1.1.3
    ipeCfgMplaneInterfaceMode OBJECT-TYPE
        SYNTAX      INTEGER { invalid(0), lct(1), nms(2) }
        ACCESS      read-only
        STATUS      mandatory
        DESCRIPTION
            "This object configures the interface mode. The object is
             available only for the system which has shared port for LCT
             interface and NMS interface."
        ::= { ipeCfgMplaneInterfaceModeEntry 3 }
    
    -- 1.3.6.1.4.1.119.2.3.69.213.502.5.3.30.1.1.1001
    ipeCfgMplaneInterfaceNEAddressAddrType OBJECT-TYPE
        SYNTAX      InetAddressType
        ACCESS      not-accessible
        STATUS      mandatory
        DESCRIPTION
            "Represents the IP address type of NE address index.
             Only ipv4(1) and ipv6(2) are supported."
        ::= { ipeCfgMplaneInterfaceModeEntry 1001 }
    
    -- 1.3.6.1.4.1.119.2.3.69.213.502.5.3.31
    ipeCfgMgmtIpRouterGroup OBJECT IDENTIFIER
        ::= { ipeConfigurationGroup 31 }
    
    -- 1.3.6.1.4.1.119.2.3.69.213.502.5.3.31.1
    ipeCfgMgmtIpRouterTable OBJECT-TYPE
        SYNTAX      SEQUENCE OF IpeCfgMgmtIpRouterEntry
        ACCESS      not-accessible
        STATUS      mandatory
        DESCRIPTION
            "This table contains configurations for Management plane router
             behaviour."
        ::= { ipeCfgMgmtIpRouterGroup 1 }
    
    -- 1.3.6.1.4.1.119.2.3.69.213.502.5.3.31.1.1
    ipeCfgMgmtIpRouterEntry OBJECT-TYPE
        SYNTAX      IpeCfgMgmtIpRouterEntry
        ACCESS      not-accessible
        STATUS      mandatory
        DESCRIPTION
            ""
        INDEX       { ipeCfgMgmtIpRouterNEAddressAddrType, ipeCfgMgmtIpRouterNEAddress, ipeCfgMgmtIpRouterIndex }
        ::= { ipeCfgMgmtIpRouterTable 1 }
    
    IpeCfgMgmtIpRouterEntry ::= SEQUENCE {
        ipeCfgMgmtIpRouterIndex                 INTEGER,
        ipeCfgMgmtIpRouterNEAddress             InetAddress,
        ipeCfgMgmtIpRouterDiscardFragmented     EnableDisableValue,
        ipeCfgMgmtIpRouterNEAddressAddrType     InetAddressType
    }
    
    -- 1.3.6.1.4.1.119.2.3.69.213.502.5.3.31.1.1.1
    ipeCfgMgmtIpRouterIndex OBJECT-TYPE
        SYNTAX      INTEGER (1)
        ACCESS      not-accessible
        STATUS      mandatory
        DESCRIPTION
            "Index of this table. The instance is created automatically when
             agent boots."
        ::= { ipeCfgMgmtIpRouterEntry 1 }
    
    -- 1.3.6.1.4.1.119.2.3.69.213.502.5.3.31.1.1.2
    ipeCfgMgmtIpRouterNEAddress OBJECT-TYPE
        SYNTAX      InetAddress
        ACCESS      not-accessible
        STATUS      mandatory
        DESCRIPTION
            "reserved."
        ::= { ipeCfgMgmtIpRouterEntry 2 }
    
    -- 1.3.6.1.4.1.119.2.3.69.213.502.5.3.31.1.1.3
    ipeCfgMgmtIpRouterDiscardFragmented OBJECT-TYPE
        SYNTAX      EnableDisableValue
        ACCESS      read-only
        STATUS      mandatory
        DESCRIPTION
            "Indicates whether discarding fragmentation packet is enabled."
        ::= { ipeCfgMgmtIpRouterEntry 3 }
    
    -- 1.3.6.1.4.1.119.2.3.69.213.502.5.3.31.1.1.1001
    ipeCfgMgmtIpRouterNEAddressAddrType OBJECT-TYPE
        SYNTAX      InetAddressType
        ACCESS      not-accessible
        STATUS      mandatory
        DESCRIPTION
            "Represents the IP address type of NE address index.
             Only ipv4(1) and ipv6(2) are supported."
        ::= { ipeCfgMgmtIpRouterEntry 1001 }
    
    -- 1.3.6.1.4.1.119.2.3.69.213.502.5.3.32
    ipeCfgMgmtArpGroup OBJECT IDENTIFIER
        ::= { ipeConfigurationGroup 32 }
    
    -- 1.3.6.1.4.1.119.2.3.69.213.502.5.3.32.1
    ipeCfgNetToPhysicalTable OBJECT-TYPE
        SYNTAX      SEQUENCE OF IpeCfgNetToPhysicalEntry
        ACCESS      not-accessible
        STATUS      mandatory
        DESCRIPTION
            "This table configures IP Address Translation table used for
             mapping from IP addresses to physical addresses.
    
             The status of the entries which were created thru this table is
             reported by ipNetToPhysicalTable."
        ::= { ipeCfgMgmtArpGroup 1 }
    
    -- 1.3.6.1.4.1.119.2.3.69.213.502.5.3.32.1.1
    ipeCfgNetToPhysicalEntry OBJECT-TYPE
        SYNTAX      IpeCfgNetToPhysicalEntry
        ACCESS      not-accessible
        STATUS      mandatory
        DESCRIPTION
            ""
        INDEX       { ipeCfgNetToPhysicalNEAddressAddrType, ipeCfgNetToPhysicalNEAddress, ipeCfgNetToPhysicalNetAddressType,
                      ipeCfgNetToPhysicalNetAddress }
        ::= { ipeCfgNetToPhysicalTable 1 }
    
    IpeCfgNetToPhysicalEntry ::= SEQUENCE {
        ipeCfgNetToPhysicalNetAddressType       InetAddressType,
        ipeCfgNetToPhysicalNetAddress           InetAddress,
        ipeCfgNetToPhysicalNEAddress            InetAddress,
        ipeCfgNetToPhysicalPhysAddress          PhysAddress,
        ipeCfgNetToPhysicalRowStatus            RowStatus,
        ipeCfgNetToPhysicalNEAddressAddrType    InetAddressType
    }
    
    -- 1.3.6.1.4.1.119.2.3.69.213.502.5.3.32.1.1.1
    ipeCfgNetToPhysicalNetAddressType OBJECT-TYPE
        SYNTAX      InetAddressType
        ACCESS      not-accessible
        STATUS      mandatory
        DESCRIPTION
            "The type of ipeCfgNetToPhysicalNetAddress."
        ::= { ipeCfgNetToPhysicalEntry 1 }
    
    -- 1.3.6.1.4.1.119.2.3.69.213.502.5.3.32.1.1.2
    ipeCfgNetToPhysicalNetAddress OBJECT-TYPE
        SYNTAX      InetAddress
        ACCESS      not-accessible
        STATUS      mandatory
        DESCRIPTION
            "The IP Address corresponding to the media-dependent 'physical'
             address.  The address type of this object is specified in
             ipeCfgNetToPhysicalNetAddressType."
        ::= { ipeCfgNetToPhysicalEntry 2 }
    
    -- 1.3.6.1.4.1.119.2.3.69.213.502.5.3.32.1.1.3
    ipeCfgNetToPhysicalNEAddress OBJECT-TYPE
        SYNTAX      InetAddress
        ACCESS      not-accessible
        STATUS      mandatory
        DESCRIPTION
            "reserved"
        ::= { ipeCfgNetToPhysicalEntry 3 }
    
    -- 1.3.6.1.4.1.119.2.3.69.213.502.5.3.32.1.1.4
    ipeCfgNetToPhysicalPhysAddress OBJECT-TYPE
        SYNTAX      PhysAddress
        ACCESS      read-only
        STATUS      mandatory
        DESCRIPTION
            "The media-dependent 'physical' address."
        ::= { ipeCfgNetToPhysicalEntry 4 }
    
    -- 1.3.6.1.4.1.119.2.3.69.213.502.5.3.32.1.1.5
    ipeCfgNetToPhysicalRowStatus OBJECT-TYPE
        SYNTAX      RowStatus
        ACCESS      read-only
        STATUS      mandatory
        DESCRIPTION
            "The status of this conceptual row."
        ::= { ipeCfgNetToPhysicalEntry 5 }
    
    -- 1.3.6.1.4.1.119.2.3.69.213.502.5.3.32.1.1.1001
    ipeCfgNetToPhysicalNEAddressAddrType OBJECT-TYPE
        SYNTAX      InetAddressType
        ACCESS      not-accessible
        STATUS      mandatory
        DESCRIPTION
            "Represents the IP address type of NE address index.
             Only ipv4(1) and ipv6(2) are supported."
        ::= { ipeCfgNetToPhysicalEntry 1001 }
    
    -- 1.3.6.1.4.1.119.2.3.69.213.502.5.3.33
    ipeCfgMgmtInbandGroup OBJECT IDENTIFIER
        ::= { ipeConfigurationGroup 33 }
    
    -- 1.3.6.1.4.1.119.2.3.69.213.502.5.3.33.1
    ipeCfgMgmtInbandTable OBJECT-TYPE
        SYNTAX      SEQUENCE OF IpeCfgMgmtInbandEntry
        ACCESS      not-accessible
        STATUS      mandatory
        DESCRIPTION
            "This table contains management interface mode information."
        ::= { ipeCfgMgmtInbandGroup 1 }
    
    -- 1.3.6.1.4.1.119.2.3.69.213.502.5.3.33.1.1
    ipeCfgMgmtInbandEntry OBJECT-TYPE
        SYNTAX      IpeCfgMgmtInbandEntry
        ACCESS      not-accessible
        STATUS      mandatory
        DESCRIPTION
            ""
        INDEX       { ipeCfgMgmtInbandNEAddressAddrType, ipeCfgMgmtInbandNEAddress, ipeCfgMgmtInbandIndex }
        ::= { ipeCfgMgmtInbandTable 1 }
    
    IpeCfgMgmtInbandEntry ::= SEQUENCE {
        ipeCfgMgmtInbandIndex               INTEGER,
        ipeCfgMgmtInbandNEAddress           InetAddress,
        ipeCfgMgmtInbandVlanTagType         INTEGER,
        ipeCfgMgmtInbandNEAddressAddrType   InetAddressType
    }
    
    -- 1.3.6.1.4.1.119.2.3.69.213.502.5.3.33.1.1.1
    ipeCfgMgmtInbandIndex OBJECT-TYPE
        SYNTAX      INTEGER (1)
        ACCESS      not-accessible
        STATUS      mandatory
        DESCRIPTION
            "Index of this table."
        ::= { ipeCfgMgmtInbandEntry 1 }
    
    -- 1.3.6.1.4.1.119.2.3.69.213.502.5.3.33.1.1.2
    ipeCfgMgmtInbandNEAddress OBJECT-TYPE
        SYNTAX      InetAddress
        ACCESS      not-accessible
        STATUS      mandatory
        DESCRIPTION
            "reserved."
        ::= { ipeCfgMgmtInbandEntry 2 }
    
    -- 1.3.6.1.4.1.119.2.3.69.213.502.5.3.33.1.1.3
    ipeCfgMgmtInbandVlanTagType OBJECT-TYPE
        SYNTAX      INTEGER { ctag(2), stag(3) }
        ACCESS      read-only
        STATUS      mandatory
        DESCRIPTION
            "INBAND Management VLAN Tag Type."
        DEFVAL      { ctag }
        ::= { ipeCfgMgmtInbandEntry 3 }
    
    -- 1.3.6.1.4.1.119.2.3.69.213.502.5.3.33.1.1.1001
    ipeCfgMgmtInbandNEAddressAddrType OBJECT-TYPE
        SYNTAX      InetAddressType
        ACCESS      not-accessible
        STATUS      mandatory
        DESCRIPTION
            "Represents the IP address type of NE address index.
             Only ipv4(1) and ipv6(2) are supported."
        ::= { ipeCfgMgmtInbandEntry 1001 }
    
    -- 1.3.6.1.4.1.119.2.3.69.213.502.5.3.34
    ipeCfgSysDcnPortTable OBJECT-TYPE
        SYNTAX      SEQUENCE OF IpeCfgSysDcnPortEntry
        ACCESS      not-accessible
        STATUS      mandatory
        DESCRIPTION
            "DCN Port Mode Configuration Table."
        ::= { ipeConfigurationGroup 34 }
    
    -- 1.3.6.1.4.1.119.2.3.69.213.502.5.3.34.1
    ipeCfgSysDcnPortEntry OBJECT-TYPE
        SYNTAX      IpeCfgSysDcnPortEntry
        ACCESS      not-accessible
        STATUS      mandatory
        DESCRIPTION
            ""
        INDEX       { ipeCfgSysDcnPortNEAddressAddrType, ipeCfgSysDcnPortNEAddress, ipeCfgSysDcnPortIndex }
        ::= { ipeCfgSysDcnPortTable 1 }
    
    IpeCfgSysDcnPortEntry ::= SEQUENCE {
        ipeCfgSysDcnPortIndex               INTEGER,
        ipeCfgSysDcnPortNEAddress           InetAddress,
        ipeCfgSysDcnPortMode                INTEGER,
        ipeCfgSysDcnPortNEAddressAddrType   InetAddressType
    }
    
    -- 1.3.6.1.4.1.119.2.3.69.213.502.5.3.34.1.1
    ipeCfgSysDcnPortIndex OBJECT-TYPE
        SYNTAX      INTEGER (1)
        ACCESS      not-accessible
        STATUS      mandatory
        DESCRIPTION
            "Index of this table."
        ::= { ipeCfgSysDcnPortEntry 1 }
    
    -- 1.3.6.1.4.1.119.2.3.69.213.502.5.3.34.1.2
    ipeCfgSysDcnPortNEAddress OBJECT-TYPE
        SYNTAX      InetAddress
        ACCESS      not-accessible
        STATUS      mandatory
        DESCRIPTION
            ""
        ::= { ipeCfgSysDcnPortEntry 2 }
    
    -- 1.3.6.1.4.1.119.2.3.69.213.502.5.3.34.1.3
    ipeCfgSysDcnPortMode OBJECT-TYPE
        SYNTAX      INTEGER { invalid(0), userport(1), lctport(2),
                        nmsport(3) }
        ACCESS      read-only
        STATUS      mandatory
        DESCRIPTION
            "DCN Port Mode Configuration"
        DEFVAL      { lctport }
        ::= { ipeCfgSysDcnPortEntry 3 }
    
    -- 1.3.6.1.4.1.119.2.3.69.213.502.5.3.34.1.1001
    ipeCfgSysDcnPortNEAddressAddrType OBJECT-TYPE
        SYNTAX      InetAddressType
        ACCESS      not-accessible
        STATUS      mandatory
        DESCRIPTION
            "Represents the IP address type of NE address index.
             Only ipv4(1) and ipv6(2) are supported."
        ::= { ipeCfgSysDcnPortEntry 1001 }
    
    -- 1.3.6.1.4.1.119.2.3.69.213.502.5.4
    ipeCommunicationsGroup OBJECT IDENTIFIER
        ::= { system5 4 }
    
    -- 1.3.6.1.4.1.119.2.3.69.213.502.5.4.1
    ipeNeighborInfoTable OBJECT-TYPE
        SYNTAX      SEQUENCE OF IpeNeighborInfoEntry
        ACCESS      not-accessible
        STATUS      mandatory
        DESCRIPTION
            "Neighbor NE table."
        ::= { ipeCommunicationsGroup 1 }
    
    -- 1.3.6.1.4.1.119.2.3.69.213.502.5.4.1.1
    ipeNeighborInfoEntry OBJECT-TYPE
        SYNTAX      IpeNeighborInfoEntry
        ACCESS      not-accessible
        STATUS      mandatory
        DESCRIPTION
            "Neighbor NE entry."
        INDEX       { ipeNeighborInfoNEAddressAddrType, ipeNeighborInfoNEAddress, ipeNeighborInfoIndex }
        ::= { ipeNeighborInfoTable 1 }
    
    IpeNeighborInfoEntry ::= SEQUENCE {
        ipeNeighborInfoIndex                InterfaceIndex,
        ipeNeighborInfoNEAddress            InetAddress,
        ipeNeighborIpAddress                OCTET STRING,
        ipeNeighborIpv4Ipv6Address          OCTET STRING,
        ipeNeighborInfoNEAddressAddrType    InetAddressType
    }
    
    -- 1.3.6.1.4.1.119.2.3.69.213.502.5.4.1.1.1
    ipeNeighborInfoIndex OBJECT-TYPE
        SYNTAX      InterfaceIndex
        ACCESS      not-accessible
        STATUS      mandatory
        DESCRIPTION
            "Index of table."
        ::= { ipeNeighborInfoEntry 1 }
    
    -- 1.3.6.1.4.1.119.2.3.69.213.502.5.4.1.1.2
    ipeNeighborInfoNEAddress OBJECT-TYPE
        SYNTAX      InetAddress
        ACCESS      not-accessible
        STATUS      mandatory
        DESCRIPTION
            ""
        ::= { ipeNeighborInfoEntry 2 }
    
    -- 1.3.6.1.4.1.119.2.3.69.213.502.5.4.1.1.3
    ipeNeighborIpAddress OBJECT-TYPE
        SYNTAX      OCTET STRING (SIZE(0..240))
        ACCESS      read-only
        STATUS      mandatory
        DESCRIPTION
            "[iPASOLINK200/400/1000series/EX/iX]
             Neighbor NE is displayed as unit of registration every eight
             bytes of Internet Protocol address (4byte) + Node TYPE(4byte).The
             number of maximum registration is 30 (240byte). Attention: ne2
             set the IpAddress only, do not set the Node type.
    
             [iPASOLINK VR series/iPASOLINK EX Advanced]
             The number of maximum registration is 13.
             Type(1byte) and Length(1byte) are common information is 2byte.
    
             Unit of registration of each neighbor as
             IPv4 Address(4bytes) + Node Type(4bytes) + MAC Address(6bytes) +
             ifindex(4bytes)."
        ::= { ipeNeighborInfoEntry 3 }
    
    -- 1.3.6.1.4.1.119.2.3.69.213.502.5.4.1.1.4
    ipeNeighborIpv4Ipv6Address OBJECT-TYPE
        SYNTAX      OCTET STRING (SIZE(0..512))
        ACCESS      read-only
        STATUS      mandatory
        DESCRIPTION
            "[EX CPRI]
             The number of maximum registration is 17 (510byte).
             Type(7bit) and Length(9bit) are common information is 2byte.
    
             Unit of registration of each neighbor as IPv6 Address(16byte) +
             IPv4 Address(4byte) + Node Type(4byte) + MAC address(6byte).
    
             [iPASOLINK VR series/iPASOLINK iX/iPASOLINK EX Advanced]
             The number of maximum registration is 15.
             Type(7bit) and Length(9bit) are common information is 2byte.
    
             Unit of registration of each neighbor as IPv6 Address(16bytes) +
             IPv4 Address(4bytes) + Node Type(4bytes) + MAC Address(6bytes) +
             ifindex(4bytes)."
        ::= { ipeNeighborInfoEntry 4 }
    
    -- 1.3.6.1.4.1.119.2.3.69.213.502.5.4.1.1.1001
    ipeNeighborInfoNEAddressAddrType OBJECT-TYPE
        SYNTAX      InetAddressType
        ACCESS      not-accessible
        STATUS      mandatory
        DESCRIPTION
            "Represents the IP address type of NE address index.
             Only ipv4(1) and ipv6(2) are supported."
        ::= { ipeNeighborInfoEntry 1001 }
    
END -- end of module MIB-EMSPLUS-IPASOLINK-SYSTEM-MIB.
