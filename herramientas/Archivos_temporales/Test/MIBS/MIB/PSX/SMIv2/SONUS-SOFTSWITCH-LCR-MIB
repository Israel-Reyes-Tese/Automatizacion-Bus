--
-- This SMIv2 module has been generated by smidump 0.2-cvs. Do not edit.
--

SONUS-SOFTSWITCH-LCR-MIB DEFINITIONS ::= BEGIN

IMPORTS
    MODULE-IDENTITY, NOTIFICATION-TYPE
        FROM SNMPv2-SMI
    sonusEventClass, sonusEventDescription, sonusEventLevel, 
    sonusEventTime
        FROM SONUS-COMMON-MIB
    sonusServicesMIBs
        FROM SONUS-SMI;

sonusSoftSwitchLcrMIB MODULE-IDENTITY
    LAST-UPDATED    "200205030000Z"
    ORGANIZATION    
            "Sonus Networks, Inc."
    CONTACT-INFO    
            "   Customer Support    
             Sonus Networks, Inc.
             4 Technology Park Drive 
             Westford, MA 01886
             USA
             
             Tel: 978-614-8100
             Fax: 978-614-8609"
    DESCRIPTION     
            "The MIB Module for SoftSwitch Database Replication Management."
    ::= { sonusServicesMIBs 40 }


sonusSoftSwitchLcrMIBObjects OBJECT IDENTIFIER
    ::= { sonusSoftSwitchLcrMIB 1 }

sonusSoftSwitchLcrMIBNotifications OBJECT IDENTIFIER
    ::= { sonusSoftSwitchLcrMIB 2 }

sonusSoftSwitchLcrMIBNotificationsPrefix OBJECT IDENTIFIER
    ::= { sonusSoftSwitchLcrMIBNotifications 0 }

sonusSoftSwitchLcrMIBNotificationsObjects OBJECT IDENTIFIER
    ::= { sonusSoftSwitchLcrMIBNotifications 1 }

sonusSoftSwitchLcrKpiLoadFailedNotification NOTIFICATION-TYPE
    OBJECTS         { sonusEventDescription, sonusEventClass, 
                      sonusEventLevel, sonusEventTime }
    STATUS          current
    DESCRIPTION     
            "The KPI loader tool encounters an error while loading."
    ::= { sonusSoftSwitchLcrMIBNotificationsPrefix 1 }

sonusSoftSwitchLcrKpiRetrievalFailedNotification NOTIFICATION-TYPE
    OBJECTS         { sonusEventDescription, sonusEventClass, 
                      sonusEventLevel, sonusEventTime }
    STATUS          current
    DESCRIPTION     
            "The NetScore KPI pull utilities encounter an error."
    ::= { sonusSoftSwitchLcrMIBNotificationsPrefix 2 }

sonusSoftSwitchLcrCountryCapLoadFailedNotification NOTIFICATION-TYPE
    OBJECTS         { sonusEventDescription, sonusEventClass, 
                      sonusEventLevel, sonusEventTime }
    STATUS          current
    DESCRIPTION     
            "Country Cap file load failed."
    ::= { sonusSoftSwitchLcrMIBNotificationsPrefix 3 }

sonusSoftSwitchLcrCountryCapRetrievalFailedNotification NOTIFICATION-TYPE
    OBJECTS         { sonusEventDescription, sonusEventClass, 
                      sonusEventLevel, sonusEventTime }
    STATUS          current
    DESCRIPTION     
            "Country Cap file retrieval failed."
    ::= { sonusSoftSwitchLcrMIBNotificationsPrefix 4 }

sonusSoftSwitchLcrCountryCapReachedNotification NOTIFICATION-TYPE
    OBJECTS         { sonusEventDescription, sonusEventClass, 
                      sonusEventLevel, sonusEventTime }
    STATUS          current
    DESCRIPTION     
            "Country Cap limit reached or exceeded."
    ::= { sonusSoftSwitchLcrMIBNotificationsPrefix 5 }

END -- end of module SONUS-SOFTSWITCH-LCR-MIB.
