--
-- This SMIv1 module has been generated by smidump 0.2-cvs. Do not edit.
--

SONUS-SOFTSWITCH-ADA-MIB DEFINITIONS ::= BEGIN

IMPORTS
    OBJECT-TYPE
        FROM RFC-1212
    TRAP-TYPE
        FROM RFC-1215
    Counter, Gauge, TimeTicks
        FROM RFC1155-SMI
    sonusEventClass, sonusEventDescription, sonusEventLevel, 
    sonusEventTime
        FROM SONUS-COMMON-MIB
    sonusServicesMIBs
        FROM SONUS-SMI
    SonusSystemName
        FROM SONUS-TC;

sonusSoftSwitchADAMIB OBJECT IDENTIFIER
    ::= { sonusServicesMIBs 34 }

-- sonusSoftSwitchADAMIB MODULE-IDENTITY
--     LAST-UPDATED    "200707100000Z"
--     ORGANIZATION    
--             "Sonus Networks, Inc."
--     CONTACT-INFO    
--             "   Customer Support    
--              Sonus Networks, Inc.
--              7 Technology Park Drive
--              Westford, MA 01886
--              USA
--              
--              Tel: 978-614-8100
--              Fax: 978-614-8609"
--     DESCRIPTION     
--             "The MIB Module for the Diameter Agent."
--     ::= { sonusServicesMIBs 34 }


sonusSoftSwitchADAMIBObjects OBJECT IDENTIFIER
    ::= { sonusSoftSwitchADAMIB 1 }

sonusSoftSwitchADAMIBNotifications OBJECT IDENTIFIER
    ::= { sonusSoftSwitchADAMIB 2 }

sonusSoftSwitchADAMIBNotificationsPrefix OBJECT IDENTIFIER
    ::= { sonusSoftSwitchADAMIBNotifications 0 }

sonusSoftSwitchADAMIBNotificationsObjects OBJECT IDENTIFIER
    ::= { sonusSoftSwitchADAMIBNotifications 1 }

sonusSoftSwitchADADomainControllerProfileName OBJECT-TYPE
    SYNTAX          OCTET STRING
    ACCESS          read-only
    STATUS          mandatory
    DESCRIPTION     
            "Name of the Domain Controller configured."
    ::= { sonusSoftSwitchADAMIBNotificationsObjects 1 }

sonusSoftSwitchADAStatistics OBJECT IDENTIFIER
    ::= { sonusSoftSwitchADAMIB 3 }

sonusSoftSwitchAdaLookupCounters OBJECT IDENTIFIER
    ::= { sonusSoftSwitchADAStatistics 1 }

sonusSoftSwitchTotalAdaSuccessfullLookups OBJECT-TYPE
    SYNTAX          Counter
    ACCESS          read-only
    STATUS          mandatory
    DESCRIPTION     
            "Number of successful AD Lookups."
    ::= { sonusSoftSwitchAdaLookupCounters 1 }

sonusSoftSwitchTotalAdaFailedLookup OBJECT-TYPE
    SYNTAX          Counter
    ACCESS          read-only
    STATUS          mandatory
    DESCRIPTION     
            "Number of Failed AD Lookups."
    ::= { sonusSoftSwitchAdaLookupCounters 2 }

sonusSoftSwitchAdaDcCounters OBJECT IDENTIFIER
    ::= { sonusSoftSwitchADAStatistics 2 }

sonusSoftSwitchAdaDcCountersTable OBJECT-TYPE
    SYNTAX          SEQUENCE OF SonusSoftSwitchAdaDcCountersEntry
    ACCESS          not-accessible
    STATUS          mandatory
    DESCRIPTION     
            "These are domain controller related stats ."
    ::= { sonusSoftSwitchAdaDcCounters 1 }

sonusSoftSwitchAdaDcCountersEntry OBJECT-TYPE
    SYNTAX          SonusSoftSwitchAdaDcCountersEntry
    ACCESS          not-accessible
    STATUS          mandatory
    DESCRIPTION     
            "An entry per Domain Controller Name."
    INDEX           { sonusSoftSwitchAdaDcCountersName }
    ::= { sonusSoftSwitchAdaDcCountersTable 1 }

SonusSoftSwitchAdaDcCountersEntry ::=
    SEQUENCE {
        sonusSoftSwitchAdaDcCountersName SonusSystemName,
        sonusSoftSwitchAdaDcCountersConnectionStatus            Gauge,
        sonusSoftSwitchAdaDcCountersSyncStatus      Gauge,
        sonusSoftSwitchAdaDcCountersLastSyncTime        TimeTicks
    }

sonusSoftSwitchAdaDcCountersName OBJECT-TYPE
    SYNTAX          SonusSystemName
    ACCESS          read-only
    STATUS          mandatory
    DESCRIPTION     
            "The Domain Controller Name that the Counters apply to"
    ::= { sonusSoftSwitchAdaDcCountersEntry 1 }

sonusSoftSwitchAdaDcCountersConnectionStatus OBJECT-TYPE
    SYNTAX          Gauge
    ACCESS          read-only
    STATUS          mandatory
    DESCRIPTION     
            "Domain Controller Connection Status 0-UP and 1-DOWN"
    ::= { sonusSoftSwitchAdaDcCountersEntry 2 }

sonusSoftSwitchAdaDcCountersSyncStatus OBJECT-TYPE
    SYNTAX          Gauge
    ACCESS          read-only
    STATUS          mandatory
    DESCRIPTION     
            "Domain Controller Sync Status 0-Synced and 1-Sync Failed"
    ::= { sonusSoftSwitchAdaDcCountersEntry 3 }

sonusSoftSwitchAdaDcCountersLastSyncTime OBJECT-TYPE
    SYNTAX          TimeTicks
    ACCESS          read-only
    STATUS          mandatory
    DESCRIPTION     
            "This is Last Sync time from Domain Controller."
    ::= { sonusSoftSwitchAdaDcCountersEntry 4 }

sonusSoftSwitchAdaDownNotification TRAP-TYPE
    ENTERPRISE      sonusSoftSwitchADAMIBNotifications
    VARIABLES       { sonusEventDescription, sonusEventClass, 
                      sonusEventLevel, sonusEventTime }
--     STATUS          mandatory
    DESCRIPTION     
            "ADA shutdown event."
    ::= 1

sonusSoftSwitchAdaUpNotification TRAP-TYPE
    ENTERPRISE      sonusSoftSwitchADAMIBNotifications
    VARIABLES       { sonusEventDescription, sonusEventClass, 
                      sonusEventLevel, sonusEventTime }
--     STATUS          mandatory
    DESCRIPTION     
            "ADA startup event"
    ::= 2

sonusSoftSwitchADADomainControllerConnUp TRAP-TYPE
    ENTERPRISE      sonusSoftSwitchADAMIBNotifications
    VARIABLES       { sonusSoftSwitchADADomainControllerProfileName, 
                      sonusEventDescription, sonusEventClass, 
                      sonusEventLevel, sonusEventTime }
--     STATUS          mandatory
    DESCRIPTION     
            "Connection to a Domain Controller is UP."
    ::= 3

sonusSoftSwitchADADomainControllerConnDown TRAP-TYPE
    ENTERPRISE      sonusSoftSwitchADAMIBNotifications
    VARIABLES       { sonusSoftSwitchADADomainControllerProfileName, 
                      sonusEventDescription, sonusEventClass, 
                      sonusEventLevel, sonusEventTime }
--     STATUS          mandatory
    DESCRIPTION     
            "Connection to Domain Controller is down."
    ::= 4

sonusSoftSwitchADADomainControllerSyncUp TRAP-TYPE
    ENTERPRISE      sonusSoftSwitchADAMIBNotifications
    VARIABLES       { sonusSoftSwitchADADomainControllerProfileName, 
                      sonusEventDescription, sonusEventClass, 
                      sonusEventLevel, sonusEventTime }
--     STATUS          mandatory
    DESCRIPTION     
            "Connection to Domain Controller is down."
    ::= 5

sonusSoftSwitchADADomainControllerSyncFailure TRAP-TYPE
    ENTERPRISE      sonusSoftSwitchADAMIBNotifications
    VARIABLES       { sonusSoftSwitchADADomainControllerProfileName, 
                      sonusEventDescription, sonusEventClass, 
                      sonusEventLevel, sonusEventTime }
--     STATUS          mandatory
    DESCRIPTION     
            "Connection to Domain Controller is down."
    ::= 6

END -- end of module SONUS-SOFTSWITCH-ADA-MIB.
