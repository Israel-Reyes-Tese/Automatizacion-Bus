MIB-PNMSJ-IPASOLINK-400-MSTP-MIB DEFINITIONS ::= BEGIN
    
    IMPORTS
        BridgeId
            FROM BRIDGE-MIB
        InterfaceIndex
            FROM IF-MIB
        OBJECT-TYPE
            FROM RFC-1212
        Counter, IpAddress, Opaque
            FROM RFC1155-SMI
        enterprises
            FROM SNMPv2-SMI;
    
    EnableDisableValue ::=
        INTEGER { invalid(0), disable(1), enable(2) }
    
    
    IpeBridgePriority ::=
        INTEGER (0..61440)
    
    
    IpePortPathCost ::=
        INTEGER (0..200000000)
    
    
    IpePortPriority ::=
        INTEGER (0..240)
    
    
    IpePortRole ::=
        INTEGER { invalid(0), disabled(1), alternate(2), backup(3), root(4),
                        designated(5) }
    
    
    IpePortState ::=
        INTEGER { invalid(0), disabled(1), blocking(2), listening(3),
                        learning(4), forwarding(5), restricted(8),
                        guarded(9) }
    
    
    IpeVlanList ::=
        OCTET STRING (SIZE(512))
    
    
    -- 1.3.6.1.4.1.119
    nec OBJECT IDENTIFIER
        ::= { enterprises 119 }
    
    -- 1.3.6.1.4.1.119.2
    nec-mib OBJECT IDENTIFIER
        ::= { nec 2 }
    
    -- 1.3.6.1.4.1.119.2.3
    necProductDepend OBJECT IDENTIFIER
        ::= { nec-mib 3 }
    
    -- 1.3.6.1.4.1.119.2.3.69
    radioEquipment OBJECT IDENTIFIER
        ::= { necProductDepend 69 }
    
    -- 1.3.6.1.4.1.119.2.3.69.203
    commonPnms OBJECT IDENTIFIER
        ::= { radioEquipment 203 }
    
    -- 1.3.6.1.4.1.119.2.3.69.203.503
    ipasolink400 OBJECT IDENTIFIER
        ::= { commonPnms 503 }
    
    -- 1.3.6.1.4.1.119.2.3.69.203.503.501
    pasoNeoIpe-common OBJECT IDENTIFIER
        ::= { ipasolink400 501 }
    
    -- 1.3.6.1.4.1.119.2.3.69.203.503.501.3
    alarmStatusGroup OBJECT IDENTIFIER
        ::= { pasoNeoIpe-common 3 }
    
    -- 1.3.6.1.4.1.119.2.3.69.203.503.501.3.44
    asMstpGroup OBJECT IDENTIFIER
        ::= { alarmStatusGroup 44 }
    
    -- 1.3.6.1.4.1.119.2.3.69.203.503.501.3.44.1
    asMstpBridgeCistTable OBJECT-TYPE
        SYNTAX      SEQUENCE OF AsMstpBridgeCistEntry
        ACCESS      not-accessible
        STATUS      mandatory
        DESCRIPTION
            "The Common and Internal Spanning Tree (CIST) Alarm/Status
             table."
        ::= { asMstpGroup 1 }
    
    -- 1.3.6.1.4.1.119.2.3.69.203.503.501.3.44.1.1
    asMstpBridgeCistEntry OBJECT-TYPE
        SYNTAX      AsMstpBridgeCistEntry
        ACCESS      not-accessible
        STATUS      mandatory
        DESCRIPTION
            "A CIST Table Entry."
        INDEX       { asMstpBridgeCistNEAddress, asMstpBridgeCistIndex }
        ::= { asMstpBridgeCistTable 1 }
    
    AsMstpBridgeCistEntry ::= SEQUENCE {
        asMstpBridgeCistIndex           INTEGER,
        asMstpBridgeCistNEAddress       IpAddress,
        asMstpBridgeCistRegionalRoot    BridgeId,
        asMstpBridgeCistTopChanges      Counter,
        asMstpBridgeCistRoot            BridgeId
    }
    
    -- 1.3.6.1.4.1.119.2.3.69.203.503.501.3.44.1.1.1
    asMstpBridgeCistIndex OBJECT-TYPE
        SYNTAX      INTEGER (1)
        ACCESS      not-accessible
        STATUS      mandatory
        DESCRIPTION
            "Index of this table."
        ::= { asMstpBridgeCistEntry 1 }
    
    -- 1.3.6.1.4.1.119.2.3.69.203.503.501.3.44.1.1.2
    asMstpBridgeCistNEAddress OBJECT-TYPE
        SYNTAX      IpAddress
        ACCESS      not-accessible
        STATUS      obsolete
        DESCRIPTION
            "reserved."
        ::= { asMstpBridgeCistEntry 2 }
    
    -- 1.3.6.1.4.1.119.2.3.69.203.503.501.3.44.1.1.3
    asMstpBridgeCistRegionalRoot OBJECT-TYPE
        SYNTAX      BridgeId
        ACCESS      read-only
        STATUS      mandatory
        DESCRIPTION
            "In an MSTP Bridge, the CIST Regional Root Identifier parameter,
             i.e. the Bridge Identifier of the current CIST Regional Root."
        ::= { asMstpBridgeCistEntry 3 }
    
    -- 1.3.6.1.4.1.119.2.3.69.203.503.501.3.44.1.1.4
    asMstpBridgeCistTopChanges OBJECT-TYPE
        SYNTAX      Counter
        ACCESS      read-only
        STATUS      mandatory
        DESCRIPTION
            "MSTP Topology Changed Status. The total number of topology
             chagnes detected by this bridge since the equipment was last
             initialized."
        ::= { asMstpBridgeCistEntry 4 }
    
    -- 1.3.6.1.4.1.119.2.3.69.203.503.501.3.44.1.1.5
    asMstpBridgeCistRoot OBJECT-TYPE
        SYNTAX      BridgeId
        ACCESS      read-only
        STATUS      mandatory
        DESCRIPTION
            ""
        ::= { asMstpBridgeCistEntry 5 }
    
    -- 1.3.6.1.4.1.119.2.3.69.203.503.501.3.44.2
    asMstpBridgeMstTable OBJECT-TYPE
        SYNTAX      SEQUENCE OF AsMstpBridgeMstEntry
        ACCESS      not-accessible
        STATUS      mandatory
        DESCRIPTION
            "In an MSTP Bridge, the MSTP Table. Each row in the Table
             represents information regarding a Bridge's Bridge Protocol
             Entity for the specified Spanning Tree instance.
    
             Entries in this table is retained across reinitializations of the
             management system."
        ::= { asMstpGroup 2 }
    
    -- 1.3.6.1.4.1.119.2.3.69.203.503.501.3.44.2.1
    asMstpBridgeMstEntry OBJECT-TYPE
        SYNTAX      AsMstpBridgeMstEntry
        ACCESS      not-accessible
        STATUS      mandatory
        DESCRIPTION
            "A MSTP Table entry."
        INDEX       { asMstpBridgeMstNEAddress, asMstpBridgeMstIndex }
        ::= { asMstpBridgeMstTable 1 }
    
    AsMstpBridgeMstEntry ::= SEQUENCE {
        asMstpBridgeMstIndex            INTEGER,
        asMstpBridgeMstNEAddress        IpAddress,
        asMstpBridgeMstRegionalRoot     BridgeId,
        asMstpBridgeMstTopChanges       Counter
    }
    
    -- 1.3.6.1.4.1.119.2.3.69.203.503.501.3.44.2.1.1
    asMstpBridgeMstIndex OBJECT-TYPE
        SYNTAX      INTEGER (1..4)
        ACCESS      not-accessible
        STATUS      mandatory
        DESCRIPTION
            "In an MSTP Bridge, this parameter is the MSTID, i.e. the
             identifier of a Spanning Tree (or MST) Instance."
        ::= { asMstpBridgeMstEntry 1 }
    
    -- 1.3.6.1.4.1.119.2.3.69.203.503.501.3.44.2.1.2
    asMstpBridgeMstNEAddress OBJECT-TYPE
        SYNTAX      IpAddress
        ACCESS      not-accessible
        STATUS      obsolete
        DESCRIPTION
            "reserved."
        ::= { asMstpBridgeMstEntry 2 }
    
    -- 1.3.6.1.4.1.119.2.3.69.203.503.501.3.44.2.1.3
    asMstpBridgeMstRegionalRoot OBJECT-TYPE
        SYNTAX      BridgeId
        ACCESS      read-only
        STATUS      mandatory
        DESCRIPTION
            "In an MSTP Bridge, the Designated Root parameter value, i.e. the
             Bridge Identifier of the Root Bridge for the MSTI."
        ::= { asMstpBridgeMstEntry 3 }
    
    -- 1.3.6.1.4.1.119.2.3.69.203.503.501.3.44.2.1.4
    asMstpBridgeMstTopChanges OBJECT-TYPE
        SYNTAX      Counter
        ACCESS      read-only
        STATUS      mandatory
        DESCRIPTION
            "In an MSTP Bridge, count of the times tcWhile has been
             non-zero for any Port for the MSTI since the Bridge was powered
             on or initialized."
        ::= { asMstpBridgeMstEntry 4 }
    
    -- 1.3.6.1.4.1.119.2.3.69.203.503.501.3.44.3
    asMstpPortCistTable OBJECT-TYPE
        SYNTAX      SEQUENCE OF AsMstpPortCistEntry
        ACCESS      not-accessible
        STATUS      mandatory
        DESCRIPTION
            "The CIST Port Table. Each row in the Table represents
             information regarding a specific Port within the Bridge's Bridge
             Protocol Entity, for the CIST."
        ::= { asMstpGroup 3 }
    
    -- 1.3.6.1.4.1.119.2.3.69.203.503.501.3.44.3.1
    asMstpPortCistEntry OBJECT-TYPE
        SYNTAX      AsMstpPortCistEntry
        ACCESS      not-accessible
        STATUS      mandatory
        DESCRIPTION
            "A CIST Port Table entry."
        INDEX       { asMstpPortCistNEAddress, asMstpPortCistIfIndex }
        ::= { asMstpPortCistTable 1 }
    
    AsMstpPortCistEntry ::= SEQUENCE {
        asMstpPortCistIfIndex               InterfaceIndex,
        asMstpPortCistNEAddress             IpAddress,
        asMstpPortCistRole                  IpePortRole,
        asMstpPortCistState                 IpePortState,
        asMstpPortCistRegionalRoot          BridgeId,
        asMstpPortCistProtoVersion          INTEGER,
        asMstpPortCistPathCost              INTEGER,
        asMstpPortCistInvalidBpdu           INTEGER,
        asMstpPortCistDesignatedPathCost    INTEGER,
        asMstpPortCistDesignatedBridge      BridgeId,
        asMstpPortCistDesignatedPort        OCTET STRING,
        asMstpPortCistForwardTransitions    Counter,
        asMstpPortCistOperEdgePort          INTEGER
    }
    
    -- 1.3.6.1.4.1.119.2.3.69.203.503.501.3.44.3.1.1
    asMstpPortCistIfIndex OBJECT-TYPE
        SYNTAX      InterfaceIndex
        ACCESS      not-accessible
        STATUS      mandatory
        DESCRIPTION
            "Index of this table."
        ::= { asMstpPortCistEntry 1 }
    
    -- 1.3.6.1.4.1.119.2.3.69.203.503.501.3.44.3.1.2
    asMstpPortCistNEAddress OBJECT-TYPE
        SYNTAX      IpAddress
        ACCESS      not-accessible
        STATUS      obsolete
        DESCRIPTION
            "reserved."
        ::= { asMstpPortCistEntry 2 }
    
    -- 1.3.6.1.4.1.119.2.3.69.203.503.501.3.44.3.1.3
    asMstpPortCistRole OBJECT-TYPE
        SYNTAX      IpePortRole
        ACCESS      read-only
        STATUS      mandatory
        DESCRIPTION
            "The current Port Role for the Port (i.e., Root, Alternate,
             Designated, or Backup), for the CIST."
        ::= { asMstpPortCistEntry 3 }
    
    -- 1.3.6.1.4.1.119.2.3.69.203.503.501.3.44.3.1.4
    asMstpPortCistState OBJECT-TYPE
        SYNTAX      IpePortState
        ACCESS      read-only
        STATUS      mandatory
        DESCRIPTION
            "In an MSTP Bridge, the current state of the Port (i.e.,
             Disabled, Listening, Learning, Forwarding, or Blocking), for the
             MSTI."
        ::= { asMstpPortCistEntry 4 }
    
    -- 1.3.6.1.4.1.119.2.3.69.203.503.501.3.44.3.1.5
    asMstpPortCistRegionalRoot OBJECT-TYPE
        SYNTAX      BridgeId
        ACCESS      read-only
        STATUS      mandatory
        DESCRIPTION
            "In an MSTP Bridge, the CIST Regional Root Identifier, i.e. the
             Bridge Identifier of the current CIST Regional Root, for the
             CIST."
        ::= { asMstpPortCistEntry 5 }
    
    -- 1.3.6.1.4.1.119.2.3.69.203.503.501.3.44.3.1.6
    asMstpPortCistProtoVersion OBJECT-TYPE
        SYNTAX      INTEGER { invalid(0), stp(1), rstp(2), mstp(3) }
        ACCESS      read-only
        STATUS      mandatory
        DESCRIPTION
            "In an MSTP Bridge, the current version of xSTP Protocol for the
             Port."
        ::= { asMstpPortCistEntry 6 }
    
    -- 1.3.6.1.4.1.119.2.3.69.203.503.501.3.44.3.1.7
    asMstpPortCistPathCost OBJECT-TYPE
        SYNTAX      INTEGER
        ACCESS      read-only
        STATUS      mandatory
        DESCRIPTION
            "In an MSTP Bridge, the CIST Path Cost parameter, i.e. the
             CISTpath cost from the transmitting Bridge to the CIST Regional
             Root. The sum (about 20 possible out of the given range) of
             multiple port path costs. Also, if the 'transmitting Bridge' is
             the 'CIST Regional Root', then this value could be zero."
        ::= { asMstpPortCistEntry 7 }
    
    -- 1.3.6.1.4.1.119.2.3.69.203.503.501.3.44.3.1.8
    asMstpPortCistInvalidBpdu OBJECT-TYPE
        SYNTAX      INTEGER { invalid(0) }
        ACCESS      read-only
        STATUS      mandatory
        DESCRIPTION
            ""
        ::= { asMstpPortCistEntry 8 }
    
    -- 1.3.6.1.4.1.119.2.3.69.203.503.501.3.44.3.1.9
    asMstpPortCistDesignatedPathCost OBJECT-TYPE
        SYNTAX      INTEGER
        ACCESS      read-only
        STATUS      mandatory
        DESCRIPTION
            "In an MSTP Bridge, the CIST Path Cost parameter, i.e. the CIST
             path cost from the transmitting Bridge to the CIST Regional Root.
             The sum (about 20 possible out of the given range) of multiple
             port path costs. Also, if the 'transmitting Bridge' is the 'CIST
             Regional Root', then this value could be zero."
        ::= { asMstpPortCistEntry 9 }
    
    -- 1.3.6.1.4.1.119.2.3.69.203.503.501.3.44.3.1.10
    asMstpPortCistDesignatedBridge OBJECT-TYPE
        SYNTAX      BridgeId
        ACCESS      read-only
        STATUS      mandatory
        DESCRIPTION
            "In an MSTP Bridge, the Designated Root parameter value, i.e. the
             Bridge Identifier of the Root Bridge for the MSTI."
        ::= { asMstpPortCistEntry 10 }
    
    -- 1.3.6.1.4.1.119.2.3.69.203.503.501.3.44.3.1.11
    asMstpPortCistDesignatedPort OBJECT-TYPE
        SYNTAX      OCTET STRING
        ACCESS      read-only
        STATUS      mandatory
        DESCRIPTION
            "The CIST Regional Root Identifier component of the Port's port
             priority vector for the CIST."
        ::= { asMstpPortCistEntry 11 }
    
    -- 1.3.6.1.4.1.119.2.3.69.203.503.501.3.44.3.1.12
    asMstpPortCistForwardTransitions OBJECT-TYPE
        SYNTAX      Counter
        ACCESS      read-only
        STATUS      mandatory
        DESCRIPTION
            "The number of times this port has transitioned from the Learning
             state to the Forwarding state."
        ::= { asMstpPortCistEntry 12 }
    
    -- 1.3.6.1.4.1.119.2.3.69.203.503.501.3.44.3.1.13
    asMstpPortCistOperEdgePort OBJECT-TYPE
        SYNTAX      INTEGER { alarmOff(0), alarmOn(1) }
        ACCESS      read-only
        STATUS      mandatory
        DESCRIPTION
            "The operational value of the Edge Port parameter.
             If the port whose 'provMstpPortCistEdgePort' is 'enable' receives
             the BPDU, the object will be changed to alarmOn.
    
             When the 'provMstpPortCistEdgePort' is 'disable', the object
             always shows 'alarmOff'."
        ::= { asMstpPortCistEntry 13 }
    
    -- 1.3.6.1.4.1.119.2.3.69.203.503.501.3.44.4
    asMstpPortMstTable OBJECT-TYPE
        SYNTAX      SEQUENCE OF AsMstpPortMstEntry
        ACCESS      not-accessible
        STATUS      mandatory
        DESCRIPTION
            "The MSTP Port Table. Each row in the Table represents
             information
             regarding a specific Port within the Bridge's Bridge Protocol
             Entity, for a given MSTI."
        ::= { asMstpGroup 4 }
    
    -- 1.3.6.1.4.1.119.2.3.69.203.503.501.3.44.4.1
    asMstpPortMstEntry OBJECT-TYPE
        SYNTAX      AsMstpPortMstEntry
        ACCESS      not-accessible
        STATUS      mandatory
        DESCRIPTION
            "A MSTP Port Table entry."
        INDEX       { asMstpPortMstNEAddress, asMstpPortMstIfIndex, asMstpPortMstIndex }
        ::= { asMstpPortMstTable 1 }
    
    AsMstpPortMstEntry ::= SEQUENCE {
        asMstpPortMstIfIndex                InterfaceIndex,
        asMstpPortMstIndex                  INTEGER,
        asMstpPortMstNEAddress              IpAddress,
        asMstpPortMstRole                   IpePortRole,
        asMstpPortMstState                  IpePortState,
        asMstpPortMstRegionalRoot           BridgeId,
        asMstpPortMstPathCost               INTEGER,
        asMstpPortMstDesignatedPathCost     INTEGER,
        asMstpPortMstDesignatedBridge       BridgeId,
        asMstpPortMstDesignatedPort         OCTET STRING
    }
    
    -- 1.3.6.1.4.1.119.2.3.69.203.503.501.3.44.4.1.1
    asMstpPortMstIfIndex OBJECT-TYPE
        SYNTAX      InterfaceIndex
        ACCESS      not-accessible
        STATUS      mandatory
        DESCRIPTION
            "Index of this table. The object represents the interface."
        ::= { asMstpPortMstEntry 1 }
    
    -- 1.3.6.1.4.1.119.2.3.69.203.503.501.3.44.4.1.2
    asMstpPortMstIndex OBJECT-TYPE
        SYNTAX      INTEGER (1..4)
        ACCESS      not-accessible
        STATUS      mandatory
        DESCRIPTION
            "In an MSTP Bridge, this parameter is the MSTID, i.e. the
             identifier of a Spanning Tree (or MST) Instance."
        ::= { asMstpPortMstEntry 2 }
    
    -- 1.3.6.1.4.1.119.2.3.69.203.503.501.3.44.4.1.3
    asMstpPortMstNEAddress OBJECT-TYPE
        SYNTAX      IpAddress
        ACCESS      not-accessible
        STATUS      obsolete
        DESCRIPTION
            "reserved."
        ::= { asMstpPortMstEntry 3 }
    
    -- 1.3.6.1.4.1.119.2.3.69.203.503.501.3.44.4.1.4
    asMstpPortMstRole OBJECT-TYPE
        SYNTAX      IpePortRole
        ACCESS      read-only
        STATUS      mandatory
        DESCRIPTION
            "In an MSTP Bridge, the current Port Role for the Port (i.e.,
             Root, Alternate, Designated, or Backup), for the MSTI."
        ::= { asMstpPortMstEntry 4 }
    
    -- 1.3.6.1.4.1.119.2.3.69.203.503.501.3.44.4.1.5
    asMstpPortMstState OBJECT-TYPE
        SYNTAX      IpePortState
        ACCESS      read-only
        STATUS      mandatory
        DESCRIPTION
            "In an MSTP Bridge, the current state of the Port (i.e.,
             Disabled, Listening, Learning, Forwarding, or Blocking), for the
             MSTI."
        ::= { asMstpPortMstEntry 5 }
    
    -- 1.3.6.1.4.1.119.2.3.69.203.503.501.3.44.4.1.6
    asMstpPortMstRegionalRoot OBJECT-TYPE
        SYNTAX      BridgeId
        ACCESS      read-only
        STATUS      mandatory
        DESCRIPTION
            "In an MSTP Bridge, the Regional Root Identifier component of the
             Port's MSTI port priority vector for the MSTI."
        ::= { asMstpPortMstEntry 6 }
    
    -- 1.3.6.1.4.1.119.2.3.69.203.503.501.3.44.4.1.7
    asMstpPortMstPathCost OBJECT-TYPE
        SYNTAX      INTEGER
        ACCESS      read-only
        STATUS      mandatory
        DESCRIPTION
            "In an MSTP Bridge, the Port's Port Path Cost parameter value for
             the MSTI."
        ::= { asMstpPortMstEntry 7 }
    
    -- 1.3.6.1.4.1.119.2.3.69.203.503.501.3.44.4.1.8
    asMstpPortMstDesignatedPathCost OBJECT-TYPE
        SYNTAX      INTEGER
        ACCESS      read-only
        STATUS      mandatory
        DESCRIPTION
            "In an MSTP Bridge, the Internal Root Path Cost component of the
             Port's MSTI port priority vector for the MSTI."
        ::= { asMstpPortMstEntry 8 }
    
    -- 1.3.6.1.4.1.119.2.3.69.203.503.501.3.44.4.1.9
    asMstpPortMstDesignatedBridge OBJECT-TYPE
        SYNTAX      BridgeId
        ACCESS      read-only
        STATUS      mandatory
        DESCRIPTION
            "In an MSTP Bridge, the Designated Bridge Identifier component of
             the Port's MSTI port priority vector for the MSTI."
        ::= { asMstpPortMstEntry 9 }
    
    -- 1.3.6.1.4.1.119.2.3.69.203.503.501.3.44.4.1.10
    asMstpPortMstDesignatedPort OBJECT-TYPE
        SYNTAX      OCTET STRING
        ACCESS      read-only
        STATUS      mandatory
        DESCRIPTION
            "In an MSTP Bridge, the Designated Port Identifier component of
             the Port's MSTI port priority vector for the MSTI."
        ::= { asMstpPortMstEntry 10 }
    
END -- end of module MIB-PNMSJ-IPASOLINK-400-MSTP-MIB.
