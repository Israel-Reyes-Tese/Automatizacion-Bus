--
-- This SMIv1 module has been generated by smidump 0.2-cvs. Do not edit.
--

SONUS-COMMON-TRAP-MIB DEFINITIONS ::= BEGIN

IMPORTS
    OBJECT-TYPE
        FROM RFC-1212
    DateAndTime
        FROM SNMPv2-TC
    SonusAlarmLevel, SonusName, SonusShelfIndex, SonusSlotIndex
        FROM SONUS-COMMON-TC
    sonusCspsNotificationMIBs
        FROM SONUS-SMI;

sonusCommonTrapMIB OBJECT IDENTIFIER
    ::= { sonusCspsNotificationMIBs 1 }

-- sonusCommonTrapMIB MODULE-IDENTITY
--     LAST-UPDATED    "201310070000Z"
--     ORGANIZATION    
--             "Sonus Networks, Inc."
--     CONTACT-INFO    
--             "   Customer Support    
--              Sonus Networks, Inc.
--              4 Technology Park Drive
--              Westford, MA 01886
--              USA
--              
--              Tel: 978-614-8100
--              Fax: 978-614-8609"
--     DESCRIPTION     
--             "The MIB Module for common management of all Sonus devices."
--     ::= { sonusCspsNotificationMIBs 1 }


sonusCommonServicesNotifications OBJECT IDENTIFIER
    ::= { sonusCommonTrapMIB 1 }

sonusCommonServicesNotificationPrefix OBJECT IDENTIFIER
    ::= { sonusCommonServicesNotifications 0 }

sonusCommonServicesNotificationObjects OBJECT IDENTIFIER
    ::= { sonusCommonServicesNotifications 1 }

sonusAlarmNodeID OBJECT-TYPE
    SYNTAX          Gauge
    ACCESS          read-only
    STATUS          mandatory
    DESCRIPTION     
            "The unique indentifier of trap generating device."
    ::= { sonusCommonServicesNotificationObjects 1 }

sonusAlarmLevel OBJECT-TYPE
    SYNTAX          SonusAlarmLevel
    ACCESS          read-only
    STATUS          mandatory
    DESCRIPTION     
            "The severity level of the event that generated the trap."
    ::= { sonusCommonServicesNotificationObjects 2 }

sonusAlarmSequenceId OBJECT-TYPE
    SYNTAX          Gauge
    ACCESS          read-only
    STATUS          mandatory
    DESCRIPTION     
            "A consecutive number assigned to each trap in a
             sequence of traps that are sent to one management client.
             Each management client has its own set of sequence IDs."
    ::= { sonusCommonServicesNotificationObjects 3 }

sonusAlarmTime OBJECT-TYPE
    SYNTAX          DateAndTime
    ACCESS          read-only
    STATUS          mandatory
    DESCRIPTION     
            "The date and time of the event that generated the trap."
    ::= { sonusCommonServicesNotificationObjects 4 }

sonusAlarmDescription OBJECT-TYPE
    SYNTAX          OCTET STRING (SIZE(0..1023))
    ACCESS          read-only
    STATUS          mandatory
    DESCRIPTION     
            "A description of the alarm that generated the trap."
    ::= { sonusCommonServicesNotificationObjects 5 }

sonusShelfIndex OBJECT-TYPE
    SYNTAX          SonusShelfIndex
    ACCESS          read-only
    STATUS          mandatory
    DESCRIPTION     
            "The shelf index of the event that generated the trap."
    ::= { sonusCommonServicesNotificationObjects 6 }

sonusSlotIndex OBJECT-TYPE
    SYNTAX          SonusSlotIndex
    ACCESS          read-only
    STATUS          mandatory
    DESCRIPTION     
            "The slot index of the event that generated the trap."
    ::= { sonusCommonServicesNotificationObjects 7 }

sonusServerID OBJECT-TYPE
    SYNTAX          SonusName
    ACCESS          read-only
    STATUS          mandatory
    DESCRIPTION     
            "The identifier (name) of the server card."
    ::= { sonusCommonServicesNotificationObjects 8 }

END -- end of module SONUS-COMMON-TRAP-MIB.
