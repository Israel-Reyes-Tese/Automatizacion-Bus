--
-- This SMIv1 module has been generated by smidump 0.2-cvs. Do not edit.
--

SONUS-SYSTEM-TIMING-MIB DEFINITIONS ::= BEGIN

IMPORTS
    OBJECT-TYPE
        FROM RFC-1212
    TRAP-TYPE
        FROM RFC-1215
    RowStatus
        FROM SNMPv2-TC
    sonusEventClass, sonusEventDescription, sonusEventLevel, 
    sonusEventTime, sonusSequenceId, sonusShelfIndex, sonusSlotIndex
        FROM SONUS-COMMON-MIB
    sonusSystemMIBs
        FROM SONUS-SMI
    HwTypeID, SonusAdminState, SonusEventString, SonusMtaSlotIndex, 
    SonusShelfIndex, SonusSlotIndex, SonusTimingSource
        FROM SONUS-TC;

sonusSystemTimingMIB OBJECT IDENTIFIER
    ::= { sonusSystemMIBs 3 }

-- sonusSystemTimingMIB MODULE-IDENTITY
--     LAST-UPDATED    "200802230000Z"
--     ORGANIZATION    
--             "Sonus Networks, Inc."
--     CONTACT-INFO    
--             "   Customer Support    
--              Sonus Networks, Inc.
--              7 Technology Park Drive
--              Westford, MA 01886
--              USA
--              
--              Tel: 978-614-8100
--              Fax: 978-614-8609"
--     DESCRIPTION     
--             "The MIB Module for System Timing management."
--     ::= { sonusSystemMIBs 3 }


sonusSystemTimingMIBObjects OBJECT IDENTIFIER
    ::= { sonusSystemTimingMIB 1 }

sonusStShelfAdmnTable OBJECT-TYPE
    SYNTAX          SEQUENCE OF SonusStShelfAdmnEntry
    ACCESS          not-accessible
    STATUS          mandatory
    DESCRIPTION     
            "  "
    ::= { sonusSystemTimingMIBObjects 1 }

sonusStShelfAdmnEntry OBJECT-TYPE
    SYNTAX          SonusStShelfAdmnEntry
    ACCESS          not-accessible
    STATUS          mandatory
    DESCRIPTION     
            "  "
    INDEX           { sonusStShelfAdmnShelfIndex }
    ::= { sonusStShelfAdmnTable 1 }

SonusStShelfAdmnEntry ::=
    SEQUENCE {
        sonusStShelfAdmnShelfIndex      SonusShelfIndex,
        sonusStShelfAdmnFailoverGuardTime INTEGER,
        sonusStShelfAdmnRecoveryGuardTime INTEGER,
        sonusStShelfAdmnTransmitRemoteAlarm   INTEGER,
        sonusStShelfAdmnRevertRefSwitching  INTEGER,
        sonusStShelfAdmnRevertMtaSwitching  INTEGER,
        sonusStShelfAdmnRevertInsertDelay INTEGER,
        sonusStShelfAdmnFreeRunAlarm    INTEGER,
        sonusStShelfAdmnTimingSourceAction  INTEGER,
        sonusStShelfAdmnRowStatus       RowStatus,
        sonusStShelfAdmnSourceReconfigAlg INTEGER,
        sonusStShelfAdmnMtaSourceAffinity INTEGER
    }

sonusStShelfAdmnShelfIndex OBJECT-TYPE
    SYNTAX          SonusShelfIndex
    ACCESS          read-only
    STATUS          mandatory
    DESCRIPTION     
            "Identifies the target shelf within the node."
    ::= { sonusStShelfAdmnEntry 1 }

sonusStShelfAdmnFailoverGuardTime OBJECT-TYPE
    SYNTAX          INTEGER (2..5)
    ACCESS          read-write
    STATUS          mandatory
    DESCRIPTION     
            " Indicates how long a timing source can be faulting 
             before switchover to another source is initiated "
    DEFVAL          { 2 }
    ::= { sonusStShelfAdmnEntry 2 }

sonusStShelfAdmnRecoveryGuardTime OBJECT-TYPE
    SYNTAX          INTEGER (15..120)
    ACCESS          read-write
    STATUS          mandatory
    DESCRIPTION     
            " Indicates how long a timing source must be valid for, after
             it has faulted, before it will be considered valid again. "
    DEFVAL          { 15 }
    ::= { sonusStShelfAdmnEntry 3 }

sonusStShelfAdmnTransmitRemoteAlarm OBJECT-TYPE
    SYNTAX          INTEGER { disabled(1), enabled(2) }
    ACCESS          read-write
    STATUS          mandatory
    DESCRIPTION     
            " Not Supported "
    DEFVAL          { disabled }
    ::= { sonusStShelfAdmnEntry 4 }

sonusStShelfAdmnRevertRefSwitching OBJECT-TYPE
    SYNTAX          INTEGER { disabled(1), enabled(2) }
    ACCESS          read-write
    STATUS          mandatory
    DESCRIPTION     
            " If enabled, then a timing source which has failed, but then 
             becomes valid again, will be reconsidered for use.
             	  If disabled, then once a timing source fails, it will never
                 be automatically reconsidered for use. To use the source again
             	  requires manual user intervention. "
    DEFVAL          { enabled }
    ::= { sonusStShelfAdmnEntry 5 }

sonusStShelfAdmnRevertMtaSwitching OBJECT-TYPE
    SYNTAX          INTEGER { disabled(1), enabled(2) }
    ACCESS          read-write
    STATUS          mandatory
    DESCRIPTION     
            " If enabled, then an MTA which is hot-inserted will 
             automatically be brought on line and made available for use.
             If disabled, then an MTA which is hot-inserted will require
             manual user configuration before being available for use. "
    DEFVAL          { enabled }
    ::= { sonusStShelfAdmnEntry 6 }

sonusStShelfAdmnRevertInsertDelay OBJECT-TYPE
    SYNTAX          INTEGER (100..300)
    ACCESS          read-write
    STATUS          mandatory
    DESCRIPTION     
            " MTA warm-up period. When an MTA is hot-inserted, the card 
             will be allowed to warm up and stabilize for this amount
             of time before being put back into service.
             
             This warm-up period is also used during cold start of a shelf. "
    DEFVAL          { 100 }
    ::= { sonusStShelfAdmnEntry 7 }

sonusStShelfAdmnFreeRunAlarm OBJECT-TYPE
    SYNTAX          INTEGER { disabled(1), enabled(2) }
    ACCESS          read-write
    STATUS          mandatory
    DESCRIPTION     
            " Not Supported "
    DEFVAL          { disabled }
    ::= { sonusStShelfAdmnEntry 8 }

sonusStShelfAdmnTimingSourceAction OBJECT-TYPE
    SYNTAX          INTEGER { none(1), resequence(2) }
    ACCESS          read-write
    STATUS          mandatory
    DESCRIPTION     
            " Resequence will cause the timing sequence list to be re-evaluated.
             This may cause the current active timing source to change. "
    DEFVAL          { none }
    ::= { sonusStShelfAdmnEntry 9 }

sonusStShelfAdmnRowStatus OBJECT-TYPE
    SYNTAX          RowStatus
    ACCESS          read-write
    STATUS          mandatory
    DESCRIPTION     
            " This object indicates the row status for this table."
    ::= { sonusStShelfAdmnEntry 10 }

sonusStShelfAdmnSourceReconfigAlg OBJECT-TYPE
    SYNTAX          INTEGER { ordered-list(1), ssm-quality(2) }
    ACCESS          read-write
    STATUS          mandatory
    DESCRIPTION     
            " This object indicates which algorithm should be used to select timing sources
             for use as System Synchronized sources. Selecting Ordered_list causes sources
             to be selected for use in strict numerical order, as assigned by default or by 
             the operator. Selecting SSM_Quality will cause sources to be selected based upon
             the quality level of the timing source, as indicated by the sources Synchronized
             Status Messages.
             
             Do not select SSM_Quality unless all configured timing sources support SSM's"
    DEFVAL          { ordered-list }
    ::= { sonusStShelfAdmnEntry 11 }

sonusStShelfAdmnMtaSourceAffinity OBJECT-TYPE
    SYNTAX          INTEGER { none(1), sticky(2) }
    ACCESS          read-write
    STATUS          mandatory
    DESCRIPTION     
            " This object works in conjunction with the Source Reconfiguration Algorithm object. 
             If sticky is selected, System Timing Manager will exhaust oll timing sources on an
             MTA at all quality levels before selecting a timing source on the alternate MTA.
             If none is selected, timing sources will be chosen based on stratum quality only,
             reguardless of which MTA is providing the source.
             
             This object has no effect when the Source Reconfiguration Algorithm is set to Ordered_list."
    DEFVAL          { sticky }
    ::= { sonusStShelfAdmnEntry 12 }

sonusStShelfStatTable OBJECT-TYPE
    SYNTAX          SEQUENCE OF SonusStShelfStatEntry
    ACCESS          not-accessible
    STATUS          mandatory
    DESCRIPTION     
            "  "
    ::= { sonusSystemTimingMIBObjects 2 }

sonusStShelfStatEntry OBJECT-TYPE
    SYNTAX          SonusStShelfStatEntry
    ACCESS          not-accessible
    STATUS          mandatory
    DESCRIPTION     
            "  "
    INDEX           { sonusStShelfStatShelfIndex }
    ::= { sonusStShelfStatTable 1 }

SonusStShelfStatEntry ::=
    SEQUENCE {
        sonusStShelfStatShelfIndex      SonusShelfIndex,
        sonusStShelfStatActiveMtaSlot   SonusMtaSlotIndex,
        sonusStShelfStatActiveSource    SonusTimingSource
    }

sonusStShelfStatShelfIndex OBJECT-TYPE
    SYNTAX          SonusShelfIndex
    ACCESS          read-only
    STATUS          mandatory
    DESCRIPTION     
            "  "
    ::= { sonusStShelfStatEntry 1 }

sonusStShelfStatActiveMtaSlot OBJECT-TYPE
    SYNTAX          SonusMtaSlotIndex
    ACCESS          read-only
    STATUS          mandatory
    DESCRIPTION     
            " Identifies which MTA is providing the System Synchronized Timing signal."
    ::= { sonusStShelfStatEntry 2 }

sonusStShelfStatActiveSource OBJECT-TYPE
    SYNTAX          SonusTimingSource
    ACCESS          read-only
    STATUS          mandatory
    DESCRIPTION     
            " Identifies what timing source the active MTA is 
             using to provide System Synchronized Timing."
    ::= { sonusStShelfStatEntry 3 }

sonusStMtaAdmnTable OBJECT-TYPE
    SYNTAX          SEQUENCE OF SonusStMtaAdmnEntry
    ACCESS          not-accessible
    STATUS          mandatory
    DESCRIPTION     
            "  "
    ::= { sonusSystemTimingMIBObjects 3 }

sonusStMtaAdmnEntry OBJECT-TYPE
    SYNTAX          SonusStMtaAdmnEntry
    ACCESS          not-accessible
    STATUS          mandatory
    DESCRIPTION     
            "  "
    INDEX           { sonusStMtaAdmnShelfIndex, 
                      sonusStMtaAdmnMtaSlotIndex }
    ::= { sonusStMtaAdmnTable 1 }

SonusStMtaAdmnEntry ::=
    SEQUENCE {
        sonusStMtaAdmnShelfIndex        SonusShelfIndex,
        sonusStMtaAdmnMtaSlotIndex      SonusMtaSlotIndex,
        sonusStMtaAdmnState             SonusAdminState,
        sonusStMtaAdmnLineEncoding      INTEGER,
        sonusStMtaAdmnSsmChannelBit     INTEGER,
        sonusStMtaAdmnFramerMode        INTEGER,
        sonusStMtaAdmnFramerTransmitYellowAlarm       INTEGER,
        sonusStMtaAdmnLiuTransmitAllOnes INTEGER,
        sonusStMtaAdmnAction            INTEGER,
        sonusStMtaAdmnRowStatus         RowStatus,
        sonusStMtaAdmnOctetTiming       INTEGER,
        sonusStMtaAdmnLossOfLock        INTEGER,
        sonusStMtaAdmnLossOfSignal      INTEGER
    }

sonusStMtaAdmnShelfIndex OBJECT-TYPE
    SYNTAX          SonusShelfIndex
    ACCESS          read-only
    STATUS          mandatory
    DESCRIPTION     
            " Identifies the target shelf within the node. "
    ::= { sonusStMtaAdmnEntry 1 }

sonusStMtaAdmnMtaSlotIndex OBJECT-TYPE
    SYNTAX          SonusMtaSlotIndex
    ACCESS          read-only
    STATUS          mandatory
    DESCRIPTION     
            " Identifies the target slot within the shelf. "
    ::= { sonusStMtaAdmnEntry 2 }

sonusStMtaAdmnState OBJECT-TYPE
    SYNTAX          SonusAdminState
    ACCESS          read-write
    STATUS          mandatory
    DESCRIPTION     
            " If enabled, the MTA can participate in system timing. 
             If disabled, then it will be removed from service and
             not allowed to participate. All timing sequence entries
             bound to this node will be marked as out of service.
             In a non-redundant configuration the MTA admin state 
             cannot be disabled. "
    DEFVAL          { enabled }
    ::= { sonusStMtaAdmnEntry 3 }

sonusStMtaAdmnLineEncoding OBJECT-TYPE
    SYNTAX          INTEGER { ami(1), b8zs(2), hdb3(3) }
    ACCESS          read-write
    STATUS          mandatory
    DESCRIPTION     
            " Select AMI or B8ZS line coding for BITS LIU.
             
             Select HDB3 for SETS LIU"
    DEFVAL          { b8zs }
    ::= { sonusStMtaAdmnEntry 4 }

sonusStMtaAdmnSsmChannelBit OBJECT-TYPE
    SYNTAX          INTEGER { sa4(1), sa5(2), sa6(3), sa7(4), sa8(5) }
    ACCESS          read-write
    STATUS          mandatory
    DESCRIPTION     
            " MTA 20, E1 support only. Identifies which of the additional spare 
             bits, embedded within the framing pattern, contains the SSM channel "
    DEFVAL          { 1 }
    ::= { sonusStMtaAdmnEntry 5 }

sonusStMtaAdmnFramerMode OBJECT-TYPE
    SYNTAX          INTEGER { d4sf(1), esf(2), mf(3), mfcrc4(4), 
                        notConfigured(5) }
    ACCESS          read-write
    STATUS          mandatory
    DESCRIPTION     
            " Select ESF or D4/SF for BITS framer.
             ESF should be selected if B8ZS has been selected for the line encoding. 
             D4/SF should be selected if AMI has been selected for the line encoding. 
             
             Select MF or MF-CRC4 for SETS framer"
    DEFVAL          { notConfigured }
    ::= { sonusStMtaAdmnEntry 6 }

sonusStMtaAdmnFramerTransmitYellowAlarm OBJECT-TYPE
    SYNTAX          INTEGER { disabled(1), enabled(2) }
    ACCESS          read-write
    STATUS          mandatory
    DESCRIPTION     
            " Not supported "
    DEFVAL          { disabled }
    ::= { sonusStMtaAdmnEntry 7 }

sonusStMtaAdmnLiuTransmitAllOnes OBJECT-TYPE
    SYNTAX          INTEGER { disabled(1), enabled(2) }
    ACCESS          read-write
    STATUS          mandatory
    DESCRIPTION     
            " Not supported "
    DEFVAL          { disabled }
    ::= { sonusStMtaAdmnEntry 8 }

sonusStMtaAdmnAction OBJECT-TYPE
    SYNTAX          INTEGER { none(1), available(2) }
    ACCESS          read-write
    STATUS          mandatory
    DESCRIPTION     
            " Selecting AVAILABLE will cause the MTA to be moved from
             the Out-Of-Service state to the Available-For-Use state.
             
             This command is necessary to manually make an MTA available for use
             after it has failed, and revertive MTA switching is not enabled. 
             
             This may cause the current active timing source to change. "
    DEFVAL          { none }
    ::= { sonusStMtaAdmnEntry 9 }

sonusStMtaAdmnRowStatus OBJECT-TYPE
    SYNTAX          RowStatus
    ACCESS          read-write
    STATUS          mandatory
    DESCRIPTION     
            "This object indicates the row status for this table."
    ::= { sonusStMtaAdmnEntry 10 }

sonusStMtaAdmnOctetTiming OBJECT-TYPE
    SYNTAX          INTEGER { disabled(1), enabled(2) }
    ACCESS          read-write
    STATUS          mandatory
    DESCRIPTION     
            " Enables or disables alarm generation upon detection of an 
             Octet Timing violation."
    DEFVAL          { disabled }
    ::= { sonusStMtaAdmnEntry 11 }

sonusStMtaAdmnLossOfLock OBJECT-TYPE
    SYNTAX          INTEGER { disabled(1), enabled(2) }
    ACCESS          read-write
    STATUS          mandatory
    DESCRIPTION     
            " Enables or disables alarm generation upon detection of a 
             loss of lock."
    DEFVAL          { disabled }
    ::= { sonusStMtaAdmnEntry 12 }

sonusStMtaAdmnLossOfSignal OBJECT-TYPE
    SYNTAX          INTEGER { disabled(1), enabled(2) }
    ACCESS          read-write
    STATUS          mandatory
    DESCRIPTION     
            " Enables or disables alarm generation upon detection of a
             loss of signal."
    DEFVAL          { disabled }
    ::= { sonusStMtaAdmnEntry 13 }

sonusStMtaStatTable OBJECT-TYPE
    SYNTAX          SEQUENCE OF SonusStMtaStatEntry
    ACCESS          not-accessible
    STATUS          mandatory
    DESCRIPTION     
            "  "
    ::= { sonusSystemTimingMIBObjects 4 }

sonusStMtaStatEntry OBJECT-TYPE
    SYNTAX          SonusStMtaStatEntry
    ACCESS          not-accessible
    STATUS          mandatory
    DESCRIPTION     
            "  "
    INDEX           { sonusStMtaStatShelfIndex, 
                      sonusStMtaStatMtaSlotIndex }
    ::= { sonusStMtaStatTable 1 }

SonusStMtaStatEntry ::=
    SEQUENCE {
        sonusStMtaStatShelfIndex        SonusShelfIndex,
        sonusStMtaStatMtaSlotIndex      SonusMtaSlotIndex,
        sonusStMtaStatOperStat          INTEGER,
        sonusStMtaStatMtaHwDesc         DisplayString,
        sonusStMtaStatMtaHwType         HwTypeID,
        sonusStMtaStatMtaHwTypeRev      INTEGER,
        sonusStMtaStatMtaSerialNum      DisplayString,
        sonusStMtaStatMtaPartNum        DisplayString,
        sonusStMtaStatMtaHwRev          DisplayString
    }

sonusStMtaStatShelfIndex OBJECT-TYPE
    SYNTAX          SonusShelfIndex
    ACCESS          read-only
    STATUS          mandatory
    DESCRIPTION     
            "  "
    ::= { sonusStMtaStatEntry 1 }

sonusStMtaStatMtaSlotIndex OBJECT-TYPE
    SYNTAX          SonusMtaSlotIndex
    ACCESS          read-only
    STATUS          mandatory
    DESCRIPTION     
            "  "
    ::= { sonusStMtaStatEntry 2 }

sonusStMtaStatOperStat OBJECT-TYPE
    SYNTAX          INTEGER { notPresent(1), fault(2), warmupDelay(3), 
                        inService(4), outOfService(5), available(6) }
    ACCESS          read-only
    STATUS          mandatory
    DESCRIPTION     
            " Indicates the operational status of the MTA"
    ::= { sonusStMtaStatEntry 3 }

sonusStMtaStatMtaHwDesc OBJECT-TYPE
    SYNTAX          DisplayString (SIZE(0..16))
    ACCESS          read-only
    STATUS          mandatory
    DESCRIPTION     
            " Description of the MTA hardware in the form of 'hwtype_hwRev'. "
    ::= { sonusStMtaStatEntry 4 }

sonusStMtaStatMtaHwType OBJECT-TYPE
    SYNTAX          HwTypeID
    ACCESS          read-only
    STATUS          mandatory
    DESCRIPTION     
            " Description of the MTA hardware Type only. Entry 5+6 obsolete entry 4."
    ::= { sonusStMtaStatEntry 5 }

sonusStMtaStatMtaHwTypeRev OBJECT-TYPE
    SYNTAX          INTEGER
    ACCESS          read-only
    STATUS          mandatory
    DESCRIPTION     
            " Description of the MTA hardware type revision. Entry 5+6 obsolete entry 4."
    ::= { sonusStMtaStatEntry 6 }

sonusStMtaStatMtaSerialNum OBJECT-TYPE
    SYNTAX          DisplayString (SIZE(1..10))
    ACCESS          read-only
    STATUS          mandatory
    DESCRIPTION     
            " Identifies the serial number of the server module.  
             This is the serial number assigned to the mta module in manufacturing."
    ::= { sonusStMtaStatEntry 7 }

sonusStMtaStatMtaPartNum OBJECT-TYPE
    SYNTAX          DisplayString (SIZE(1..10))
    ACCESS          read-only
    STATUS          mandatory
    DESCRIPTION     
            " Identifies the part number of the server module. 
             This is the part number assigned to the mta module in manufacturing."
    ::= { sonusStMtaStatEntry 8 }

sonusStMtaStatMtaHwRev OBJECT-TYPE
    SYNTAX          DisplayString (SIZE(1..2))
    ACCESS          read-only
    STATUS          mandatory
    DESCRIPTION     
            " Description of the MTA hardware board revision."
    ::= { sonusStMtaStatEntry 9 }

sonusStTimingSourceTable OBJECT-TYPE
    SYNTAX          SEQUENCE OF SonusStTimingSourceEntry
    ACCESS          not-accessible
    STATUS          mandatory
    DESCRIPTION     
            "  "
    ::= { sonusSystemTimingMIBObjects 5 }

sonusStTimingSourceEntry OBJECT-TYPE
    SYNTAX          SonusStTimingSourceEntry
    ACCESS          not-accessible
    STATUS          mandatory
    DESCRIPTION     
            "  "
    INDEX           { sonusStTimingSourceShelfIndex, 
                      sonusStTimingSourceMtaSlotIndex, 
                      sonusStTimingSource }
    ::= { sonusStTimingSourceTable 1 }

SonusStTimingSourceEntry ::=
    SEQUENCE {
        sonusStTimingSourceShelfIndex   SonusShelfIndex,
        sonusStTimingSourceMtaSlotIndex SonusMtaSlotIndex,
        sonusStTimingSource             SonusTimingSource,
        sonusStTimingSourceState        SonusAdminState,
        sonusStTimingSourceSequenceNum  INTEGER,
        sonusStTimingSourceAction       INTEGER,
        sonusStTimingSourceRowStatus    RowStatus
    }

sonusStTimingSourceShelfIndex OBJECT-TYPE
    SYNTAX          SonusShelfIndex
    ACCESS          read-only
    STATUS          mandatory
    DESCRIPTION     
            "  "
    ::= { sonusStTimingSourceEntry 1 }

sonusStTimingSourceMtaSlotIndex OBJECT-TYPE
    SYNTAX          SonusMtaSlotIndex
    ACCESS          read-only
    STATUS          mandatory
    DESCRIPTION     
            " Indicates which MTA this timing node is bound to. "
    ::= { sonusStTimingSourceEntry 2 }

sonusStTimingSource OBJECT-TYPE
    SYNTAX          SonusTimingSource
    ACCESS          read-only
    STATUS          mandatory
    DESCRIPTION     
            " Indicates which physical timing source is bound to this node.
             
             External BITS sources are used by MTA 10's, in T1 based chassis'.
             External SETS sources are used by MTA 2X's, in E1 based chassis'.
             REFCLK's are based upon timing recovered from a CNS or PNS Server card.
             HOLDOVER mimics the last known good source before it failed.
             OSCILLATOR is used when no other valid sources exist on the currently active
             MTA. "
    DEFVAL          { oscillator }
    ::= { sonusStTimingSourceEntry 3 }

sonusStTimingSourceState OBJECT-TYPE
    SYNTAX          SonusAdminState
    ACCESS          read-write
    STATUS          mandatory
    DESCRIPTION     
            " If enabled, the source can participate in system timing. 
             If disabled, then it will be removed from service and
             not be allowed to participate. "
    DEFVAL          { enabled }
    ::= { sonusStTimingSourceEntry 4 }

sonusStTimingSourceSequenceNum OBJECT-TYPE
    SYNTAX          INTEGER (1..12)
    ACCESS          read-write
    STATUS          mandatory
    DESCRIPTION     
            " The timing sequence number is automatically generated "
    ::= { sonusStTimingSourceEntry 5 }

sonusStTimingSourceAction OBJECT-TYPE
    SYNTAX          INTEGER { none(1), available(2) }
    ACCESS          read-write
    STATUS          mandatory
    DESCRIPTION     
            " Selecting AVAILABLE will cause the timing source to be moved  
             from the Out-Of-Service state to the Available-For-Use state.
             
             This command is necessary to manually make a source available for use
             after it has failed, and revertive source switching is not enabled. 
             
             This may cause the current active timing source to change. "
    DEFVAL          { none }
    ::= { sonusStTimingSourceEntry 6 }

sonusStTimingSourceRowStatus OBJECT-TYPE
    SYNTAX          RowStatus
    ACCESS          read-write
    STATUS          mandatory
    DESCRIPTION     
            "This object indicates the row status for this table."
    ::= { sonusStTimingSourceEntry 7 }

sonusStTimingSourceStatTable OBJECT-TYPE
    SYNTAX          SEQUENCE OF SonusStTimingSourceStatEntry
    ACCESS          not-accessible
    STATUS          mandatory
    DESCRIPTION     
            "  "
    ::= { sonusSystemTimingMIBObjects 6 }

sonusStTimingSourceStatEntry OBJECT-TYPE
    SYNTAX          SonusStTimingSourceStatEntry
    ACCESS          not-accessible
    STATUS          mandatory
    DESCRIPTION     
            "  "
    INDEX           { sonusStTimingSourceStatShelfIndex, 
                      sonusStTimingSourceStatMtaSlotIndex, 
                      sonusStTimingSourceStat }
    ::= { sonusStTimingSourceStatTable 1 }

SonusStTimingSourceStatEntry ::=
    SEQUENCE {
        sonusStTimingSourceStatShelfIndex SonusShelfIndex,
        sonusStTimingSourceStatMtaSlotIndex   SonusMtaSlotIndex,
        sonusStTimingSourceStat         SonusTimingSource,
        sonusStTimingSourceStatState    INTEGER,
        sonusStTimingSourceStatTraceability   INTEGER,
        sonusStTimingSourceStatLineState INTEGER
    }

sonusStTimingSourceStatShelfIndex OBJECT-TYPE
    SYNTAX          SonusShelfIndex
    ACCESS          read-only
    STATUS          mandatory
    DESCRIPTION     
            " Indicates shelf. "
    ::= { sonusStTimingSourceStatEntry 1 }

sonusStTimingSourceStatMtaSlotIndex OBJECT-TYPE
    SYNTAX          SonusMtaSlotIndex
    ACCESS          read-only
    STATUS          mandatory
    DESCRIPTION     
            " Indicates which MTA this timing node is bound to. "
    ::= { sonusStTimingSourceStatEntry 2 }

sonusStTimingSourceStat OBJECT-TYPE
    SYNTAX          SonusTimingSource
    ACCESS          read-only
    STATUS          mandatory
    DESCRIPTION     
            " Indicates the physical timing source "
    DEFVAL          { oscillator }
    ::= { sonusStTimingSourceStatEntry 3 }

sonusStTimingSourceStatState OBJECT-TYPE
    SYNTAX          INTEGER { available(1), inservice(2), faulting(3), 
                        outofservice(4), cannotlocate(5), notpresent(6) }
    ACCESS          read-only
    STATUS          mandatory
    DESCRIPTION     
            " Indicates the current overall state of the timing source, including 
             the hardware state, adminitrative mode and shelf configuration "
    ::= { sonusStTimingSourceStatEntry 4 }

sonusStTimingSourceStatTraceability OBJECT-TYPE
    SYNTAX          INTEGER { synchronizedunknown(1), stratum1(2), 
                        stratum2(3), stratumTNC(4), stratum3e(5), 
                        stratum3(6), stratumSonetMinimum(7), stratum4(8), 
                        reserved(9), dontUse(10), indeterminate(11), 
                        qualityunknown(12), g811(13), g812transit(14), 
                        g812local(15), sets(16), g704rsvdql1(17), 
                        g704rsvdql3(18), g704rsvdql5(19), 
                        g704rsvdql6(20), g704rsvdql7(21), 
                        g704rsvdql9(22), g704rsvdql10(23), 
                        g704rsvdql12(24), g704rsvdql13(25), 
                        g704rsvdql14(26) }
    ACCESS          read-only
    STATUS          mandatory
    DESCRIPTION     
            " Indicates the Quality Level of the System Synchronized Timing Source"
    ::= { sonusStTimingSourceStatEntry 5 }

sonusStTimingSourceStatLineState OBJECT-TYPE
    SYNTAX          INTEGER { valid(1), notvalid(2) }
    ACCESS          read-only
    STATUS          mandatory
    DESCRIPTION     
            " Indicates the current physical status of the timing source "
    ::= { sonusStTimingSourceStatEntry 6 }

sonusStChannelBindingTable OBJECT-TYPE
    SYNTAX          SEQUENCE OF SonusStChannelBindingEntry
    ACCESS          not-accessible
    STATUS          deprecated
    DESCRIPTION     
            " This table describes how derived timing 
             sources should be mapped to the MTA hardware"
    ::= { sonusSystemTimingMIBObjects 7 }

sonusStChannelBindingEntry OBJECT-TYPE
    SYNTAX          SonusStChannelBindingEntry
    ACCESS          not-accessible
    STATUS          deprecated
    DESCRIPTION     
            " This table has been replaced by sonusStRefClkBindingEntry... "
    INDEX           { sonusStChannelBindingShelfIndex, 
                      sonusStChannelBindingSlotIndex, 
                      sonusStChannelBindingChannel, 
                      sonusStChannelBindingRefClk }
    ::= { sonusStChannelBindingTable 1 }

SonusStChannelBindingEntry ::=
    SEQUENCE {
        sonusStChannelBindingShelfIndex SonusShelfIndex,
        sonusStChannelBindingSlotIndex  SonusSlotIndex,
        sonusStChannelBindingChannel    INTEGER,
        sonusStChannelBindingRefClk     INTEGER,
        sonusStChannelBindingRowStatus  RowStatus
    }

sonusStChannelBindingShelfIndex OBJECT-TYPE
    SYNTAX          SonusShelfIndex
    ACCESS          read-only
    STATUS          deprecated
    DESCRIPTION     
            "  "
    ::= { sonusStChannelBindingEntry 1 }

sonusStChannelBindingSlotIndex OBJECT-TYPE
    SYNTAX          SonusSlotIndex
    ACCESS          read-only
    STATUS          deprecated
    DESCRIPTION     
            " Server slot number to provide a recovered clock source. The
             same server can be configured to provide both possible recovered 
             clocks as long as different channels(spans) are selected, and 
             the REFCLK each is bound to differs "
    ::= { sonusStChannelBindingEntry 2 }

sonusStChannelBindingChannel OBJECT-TYPE
    SYNTAX          INTEGER { pimUpper(85), pimLower(86) }
    ACCESS          read-only
    STATUS          deprecated
    DESCRIPTION     
            " T1/E1 span or OC12 port number to provide the recovered clock source.
             T1 span range is 1-12(CNS10), 1-28(CNS30), E1 span range is 1-8(CNS20), 
             OC12 port number(PNS20) is 1 only."
    ::= { sonusStChannelBindingEntry 3 }

sonusStChannelBindingRefClk OBJECT-TYPE
    SYNTAX          INTEGER { refClkA(1), refClkB(2) }
    ACCESS          read-only
    STATUS          deprecated
    DESCRIPTION     
            "  Backplane signal the recovered clock source should be 
             bound to. Each REFCLK must only be bound to a single 
             Server slot/span. "
    ::= { sonusStChannelBindingEntry 4 }

sonusStChannelBindingRowStatus OBJECT-TYPE
    SYNTAX          RowStatus
    ACCESS          read-write
    STATUS          deprecated
    DESCRIPTION     
            "This object indicates the row status for this table."
    ::= { sonusStChannelBindingEntry 5 }

sonusStRefClkBindingTable OBJECT-TYPE
    SYNTAX          SEQUENCE OF SonusStRefClkBindingEntry
    ACCESS          not-accessible
    STATUS          mandatory
    DESCRIPTION     
            " This table describes how derived timing 
             sources should be mapped to the MTA hardware"
    ::= { sonusSystemTimingMIBObjects 8 }

sonusStRefClkBindingEntry OBJECT-TYPE
    SYNTAX          SonusStRefClkBindingEntry
    ACCESS          not-accessible
    STATUS          mandatory
    DESCRIPTION     
            "  "
    INDEX           { sonusStRefClkBindingIndex }
    ::= { sonusStRefClkBindingTable 1 }

SonusStRefClkBindingEntry ::=
    SEQUENCE {
        sonusStRefClkBindingIndex       INTEGER,
        sonusStRefClkBindingShelfIndex  SonusShelfIndex,
        sonusStRefClkBindingSlotIndex   SonusSlotIndex,
        sonusStRefClkBindingPortIndex   INTEGER,
        sonusStRefClkBindingOcxIndex    INTEGER,
        sonusStRefClkBindingDs3Index    INTEGER,
        sonusStRefClkBindingDs1Index    INTEGER,
        sonusStRefClkBindingRefClk      INTEGER,
        sonusStRefClkBindingRowStatus   RowStatus
    }

sonusStRefClkBindingIndex OBJECT-TYPE
    SYNTAX          INTEGER (1..128)
    ACCESS          read-write
    STATUS          mandatory
    DESCRIPTION     
            "The index into the System Timing Reference Clock Bindings"
    ::= { sonusStRefClkBindingEntry 1 }

sonusStRefClkBindingShelfIndex OBJECT-TYPE
    SYNTAX          SonusShelfIndex
    ACCESS          read-write
    STATUS          mandatory
    DESCRIPTION     
            " The shelf in which the reference clock is located. "
    ::= { sonusStRefClkBindingEntry 2 }

sonusStRefClkBindingSlotIndex OBJECT-TYPE
    SYNTAX          SonusSlotIndex
    ACCESS          read-write
    STATUS          mandatory
    DESCRIPTION     
            " The slot in which the reference clock is located. "
    ::= { sonusStRefClkBindingEntry 3 }

sonusStRefClkBindingPortIndex OBJECT-TYPE
    SYNTAX          INTEGER (0..36)
    ACCESS          read-write
    STATUS          mandatory
    DESCRIPTION     
            "The physical port of the reference clock."
    ::= { sonusStRefClkBindingEntry 4 }

sonusStRefClkBindingOcxIndex OBJECT-TYPE
    SYNTAX          INTEGER (0..3)
    ACCESS          read-write
    STATUS          mandatory
    DESCRIPTION     
            "The oc index, if applicable, of the reference clock. "
    ::= { sonusStRefClkBindingEntry 5 }

sonusStRefClkBindingDs3Index OBJECT-TYPE
    SYNTAX          INTEGER (0..10)
    ACCESS          read-write
    STATUS          mandatory
    DESCRIPTION     
            "The DS3 index, if applicable, of the reference clock."
    ::= { sonusStRefClkBindingEntry 6 }

sonusStRefClkBindingDs1Index OBJECT-TYPE
    SYNTAX          INTEGER (0..99)
    ACCESS          read-write
    STATUS          mandatory
    DESCRIPTION     
            "The DS1 index, if applicable, of the reference clock."
    ::= { sonusStRefClkBindingEntry 7 }

sonusStRefClkBindingRefClk OBJECT-TYPE
    SYNTAX          INTEGER { refClkA(1), refClkB(2) }
    ACCESS          read-write
    STATUS          mandatory
    DESCRIPTION     
            "The reference clock binding A/B of the reference clock."
    ::= { sonusStRefClkBindingEntry 8 }

sonusStRefClkBindingRowStatus OBJECT-TYPE
    SYNTAX          RowStatus
    ACCESS          read-write
    STATUS          mandatory
    DESCRIPTION     
            ""
    ::= { sonusStRefClkBindingEntry 9 }

sonusStBitsStatTable OBJECT-TYPE
    SYNTAX          SEQUENCE OF SonusStBitsStatEntry
    ACCESS          not-accessible
    STATUS          mandatory
    DESCRIPTION     
            "  "
    ::= { sonusSystemTimingMIBObjects 9 }

sonusStBitsStatEntry OBJECT-TYPE
    SYNTAX          SonusStBitsStatEntry
    ACCESS          not-accessible
    STATUS          mandatory
    DESCRIPTION     
            "  "
    INDEX           { sonusStBitsStatShelfIndex, 
                      sonusStBitsStatMtaSlotIndex, 
                      sonusStBitsStatMtaFramerIndex }
    ::= { sonusStBitsStatTable 1 }

SonusStBitsStatEntry ::=
    SEQUENCE {
        sonusStBitsStatShelfIndex       SonusShelfIndex,
        sonusStBitsStatMtaSlotIndex     SonusMtaSlotIndex,
        sonusStBitsStatMtaFramerIndex   INTEGER,
        sonusStBitsStatBPV              INTEGER,
        sonusStBitsStatCRC              INTEGER,
        sonusStBitsStatFER              INTEGER,
        sonusStBitsStatOOF              INTEGER,
        sonusStBitsStatAIS              INTEGER,
        sonusStBitsStatYEL              INTEGER,
        sonusStBitsStatLOS              INTEGER,
        sonusStBitsStatCurrentStatus    INTEGER
    }

sonusStBitsStatShelfIndex OBJECT-TYPE
    SYNTAX          SonusShelfIndex
    ACCESS          read-only
    STATUS          mandatory
    DESCRIPTION     
            "  "
    ::= { sonusStBitsStatEntry 1 }

sonusStBitsStatMtaSlotIndex OBJECT-TYPE
    SYNTAX          SonusMtaSlotIndex
    ACCESS          read-only
    STATUS          mandatory
    DESCRIPTION     
            "  "
    ::= { sonusStBitsStatEntry 2 }

sonusStBitsStatMtaFramerIndex OBJECT-TYPE
    SYNTAX          INTEGER { primary(1), secondary(2) }
    ACCESS          read-only
    STATUS          mandatory
    DESCRIPTION     
            "  "
    ::= { sonusStBitsStatEntry 3 }

sonusStBitsStatBPV OBJECT-TYPE
    SYNTAX          INTEGER
    ACCESS          read-only
    STATUS          mandatory
    DESCRIPTION     
            "  "
    ::= { sonusStBitsStatEntry 4 }

sonusStBitsStatCRC OBJECT-TYPE
    SYNTAX          INTEGER
    ACCESS          read-only
    STATUS          mandatory
    DESCRIPTION     
            "  "
    ::= { sonusStBitsStatEntry 5 }

sonusStBitsStatFER OBJECT-TYPE
    SYNTAX          INTEGER
    ACCESS          read-only
    STATUS          mandatory
    DESCRIPTION     
            "  "
    ::= { sonusStBitsStatEntry 6 }

sonusStBitsStatOOF OBJECT-TYPE
    SYNTAX          INTEGER
    ACCESS          read-only
    STATUS          mandatory
    DESCRIPTION     
            "  "
    ::= { sonusStBitsStatEntry 7 }

sonusStBitsStatAIS OBJECT-TYPE
    SYNTAX          INTEGER
    ACCESS          read-only
    STATUS          mandatory
    DESCRIPTION     
            "  "
    ::= { sonusStBitsStatEntry 8 }

sonusStBitsStatYEL OBJECT-TYPE
    SYNTAX          INTEGER
    ACCESS          read-only
    STATUS          mandatory
    DESCRIPTION     
            "  "
    ::= { sonusStBitsStatEntry 9 }

sonusStBitsStatLOS OBJECT-TYPE
    SYNTAX          INTEGER
    ACCESS          read-only
    STATUS          mandatory
    DESCRIPTION     
            "  "
    ::= { sonusStBitsStatEntry 10 }

sonusStBitsStatCurrentStatus OBJECT-TYPE
    SYNTAX          INTEGER { noDefect(1), los(2), ais(3), lof(4), 
                        yellow(5) }
    ACCESS          read-only
    STATUS          mandatory
    DESCRIPTION     
            "  "
    ::= { sonusStBitsStatEntry 11 }

sonusSystemTimingMIBNotifications OBJECT IDENTIFIER
    ::= { sonusSystemTimingMIB 2 }

sonusSystemTimingMIBNotificationsPrefix OBJECT IDENTIFIER
    ::= { sonusSystemTimingMIBNotifications 0 }

sonusSystemTimingMIBNotificationsObjects OBJECT IDENTIFIER
    ::= { sonusSystemTimingMIBNotifications 1 }

sonusTimingSource OBJECT-TYPE
    SYNTAX          SonusTimingSource
    ACCESS          read-only
    STATUS          mandatory
    DESCRIPTION     
            "  "
    ::= { sonusSystemTimingMIBNotificationsObjects 1 }

sonusTimingSource2 OBJECT-TYPE
    SYNTAX          SonusEventString
    ACCESS          read-only
    STATUS          mandatory
    DESCRIPTION     
            "  "
    ::= { sonusSystemTimingMIBNotificationsObjects 2 }

sonusTimingDownReason OBJECT-TYPE
    SYNTAX          SonusEventString
    ACCESS          read-only
    STATUS          mandatory
    DESCRIPTION     
            "  "
    ::= { sonusSystemTimingMIBNotificationsObjects 3 }

sonusSystemTimingActiveFailedNotification TRAP-TYPE
    ENTERPRISE      sonusSystemTimingMIBNotifications
    VARIABLES       { sonusShelfIndex, sonusSlotIndex, sonusTimingSource, 
                      sonusEventDescription, sonusEventClass, 
                      sonusEventLevel, sonusSequenceId, sonusEventTime }
--     STATUS          deprecated
    DESCRIPTION     
            "This trap has been replaced by sonusSystemTimingActiveFailedNotification2."
    ::= 1

sonusSystemTimingActiveSwitchoverNotification TRAP-TYPE
    ENTERPRISE      sonusSystemTimingMIBNotifications
    VARIABLES       { sonusShelfIndex, sonusSlotIndex, sonusTimingSource, 
                      sonusEventDescription, sonusEventClass, 
                      sonusEventLevel, sonusSequenceId, sonusEventTime }
--     STATUS          mandatory
    DESCRIPTION     
            "This trap indicates that the active System Timing 
             clock source has been switched to another source."
    ::= 2

sonusSystemTimingOscillatorActiveNotification TRAP-TYPE
    ENTERPRISE      sonusSystemTimingMIBNotifications
    VARIABLES       { sonusShelfIndex, sonusSlotIndex, 
                      sonusEventDescription, sonusEventClass, 
                      sonusEventLevel, sonusSequenceId, sonusEventTime }
--     STATUS          mandatory
    DESCRIPTION     
            "This trap indicates that all external sources of
             System Timing have failed and that the current 
             source of timing is the MTA's internal oscillator."
    ::= 3

sonusSystemTimingMTAFailedNotification TRAP-TYPE
    ENTERPRISE      sonusSystemTimingMIBNotifications
    VARIABLES       { sonusShelfIndex, sonusSlotIndex, 
                      sonusEventDescription, sonusEventClass, 
                      sonusEventLevel, sonusSequenceId, sonusEventTime }
--     STATUS          mandatory
    DESCRIPTION     
            "This trap indicates that the MTA indicated 
             has failed or been removed from the shelf."
    ::= 4

sonusSystemTimingMTAOperationalNotification TRAP-TYPE
    ENTERPRISE      sonusSystemTimingMIBNotifications
    VARIABLES       { sonusShelfIndex, sonusSlotIndex, 
                      sonusEventDescription, sonusEventClass, 
                      sonusEventLevel, sonusSequenceId, sonusEventTime }
--     STATUS          mandatory
    DESCRIPTION     
            "This trap indicates that the specified MTA
             is now operational."
    ::= 6

sonusSystemTimingMTATotalFailureNotification TRAP-TYPE
    ENTERPRISE      sonusSystemTimingMIBNotifications
    VARIABLES       { sonusShelfIndex, sonusEventDescription, 
                      sonusEventClass, sonusEventLevel, sonusSequenceId, 
                      sonusEventTime }
--     STATUS          mandatory
    DESCRIPTION     
            "This trap indicates that no MTA's are available for 
             use to provide System Timing. They have either failed, 
             been removed from service or been removed from the shelf. 
             The shelf is no longer capable of being properly timed.
             
             Downstream Shelves or other equipment connected to this shelf's
             MITDC(Marlin Inter-chassis Timing Daisy Chain) may be affected."
    ::= 7

sonusSystemTimingActiveFailedNotification2 TRAP-TYPE
    ENTERPRISE      sonusSystemTimingMIBNotifications
    VARIABLES       { sonusShelfIndex, sonusSlotIndex, 
                      sonusTimingSource2, sonusTimingDownReason, 
                      sonusEventDescription, sonusEventClass, 
                      sonusEventLevel, sonusSequenceId, sonusEventTime }
--     STATUS          mandatory
    DESCRIPTION     
            "This trap indicates that the currently active System Timing clock source has failed 
             and adds a string interpretation of the source type."
    ::= 8

sonusSystemTimingNonActiveFailedNotification TRAP-TYPE
    ENTERPRISE      sonusSystemTimingMIBNotifications
    VARIABLES       { sonusShelfIndex, sonusSlotIndex, 
                      sonusTimingSource2, sonusTimingDownReason, 
                      sonusEventDescription, sonusEventClass, 
                      sonusEventLevel, sonusSequenceId, sonusEventTime }
--     STATUS          mandatory
    DESCRIPTION     
            "This trap indicates that a non-active System Timing clock source has failed 
             and adds a string interpretation of the source type."
    ::= 9

END -- end of module SONUS-SYSTEM-TIMING-MIB.
