--
-- This SMIv1 module has been generated by smidump 0.2-cvs. Do not edit.
--

OSPF-TRAP-MIB DEFINITIONS ::= BEGIN

IMPORTS
    ospf, ospfAddressLessIf, ospfExtLsdbLimit, ospfIfIpAddress, 
    ospfIfState, ospfLsdbAreaId, ospfLsdbLsid, ospfLsdbRouterId, 
    ospfLsdbType, ospfNbrAddressLessIndex, ospfNbrIpAddr, ospfNbrRtrId, 
    ospfNbrState, ospfRouterId, ospfVirtIfAreaId, ospfVirtIfNeighbor, 
    ospfVirtIfState, ospfVirtNbrArea, ospfVirtNbrRtrId, ospfVirtNbrState
        FROM OSPF-MIB
    OBJECT-TYPE
        FROM RFC-1212
    TRAP-TYPE
        FROM RFC-1215
    IpAddress
        FROM RFC1155-SMI;

ospfTrap OBJECT IDENTIFIER
    ::= { ospf 16 }

-- ospfTrap MODULE-IDENTITY
--     LAST-UPDATED    "199501201225Z"
--     ORGANIZATION    
--             "IETF OSPF Working Group"
--     CONTACT-INFO    
--             "                      Fred Baker
--              Postal:                Cisco Systems
--                                     519 Lado Drive
--                                     Santa Barbara, California 93111
--              Tel:                   +1 805 681 0115
--              E-Mail:                fred@cisco.com
--              
--                                     Rob Coltun
--              Postal:                RainbowBridge Communications
--              Tel:                   (301) 340-9416
--              E-Mail:                rcoltun@rainbow-bridge.com"
--     DESCRIPTION     
--             "The MIB module to describe traps for  the  OSPF
--              Version 2 Protocol."
--     ::= { ospf 16 }


ospfTrapControl OBJECT IDENTIFIER
    ::= { ospfTrap 1 }

ospfSetTrap OBJECT-TYPE
    SYNTAX          OCTET STRING (SIZE(4))
    ACCESS          read-write
    STATUS          mandatory
    DESCRIPTION     
            "A four-octet string serving as a bit  map  for
             the trap events defined by the OSPF traps. This
             object is used to enable and  disable  specific
             OSPF   traps   where  a  1  in  the  bit  field
             represents enabled.  The right-most bit  (least
             significant) represents trap 0."
    ::= { ospfTrapControl 1 }

ospfConfigErrorType OBJECT-TYPE
    SYNTAX          INTEGER { badVersion(1), areaMismatch(2), 
                        unknownNbmaNbr(3), unknownVirtualNbr(4), 
                        authTypeMismatch(5), authFailure(6), 
                        netMaskMismatch(7), helloIntervalMismatch(8), 
                        deadIntervalMismatch(9), optionMismatch(10) }
    ACCESS          read-only
    STATUS          mandatory
    DESCRIPTION     
            "Potential types  of  configuration  conflicts.
             Used  by the ospfConfigError and ospfConfigVir-
             tError traps."
    ::= { ospfTrapControl 2 }

ospfPacketType OBJECT-TYPE
    SYNTAX          INTEGER { hello(1), dbDescript(2), lsReq(3), 
                        lsUpdate(4), lsAck(5) }
    ACCESS          read-only
    STATUS          mandatory
    DESCRIPTION     
            "OSPF packet types."
    ::= { ospfTrapControl 3 }

ospfPacketSrc OBJECT-TYPE
    SYNTAX          IpAddress
    ACCESS          read-only
    STATUS          mandatory
    DESCRIPTION     
            "The IP address of an inbound packet that  can-
             not be identified by a neighbor instance."
    ::= { ospfTrapControl 4 }

ospfTraps OBJECT IDENTIFIER
    ::= { ospfTrap 2 }

ospfTrapConformance OBJECT IDENTIFIER
    ::= { ospfTrap 3 }

ospfTrapGroups OBJECT IDENTIFIER
    ::= { ospfTrapConformance 1 }

ospfTrapCompliances OBJECT IDENTIFIER
    ::= { ospfTrapConformance 2 }

ospfVirtIfStateChange TRAP-TYPE
    ENTERPRISE      ospfTraps
    VARIABLES       { ospfRouterId, ospfVirtIfAreaId, ospfVirtIfNeighbor, 
                      ospfVirtIfState }
--     STATUS          mandatory
    DESCRIPTION     
            "An ospfIfStateChange trap signifies that there
             has  been a change in the state of an OSPF vir-
             tual interface.
             This trap should be generated when  the  inter-
             face  state  regresses  (e.g., goes from Point-
             to-Point to Down) or progresses to  a  terminal
             state (i.e., Point-to-Point)."
    ::= 1

ospfNbrStateChange TRAP-TYPE
    ENTERPRISE      ospfTraps
    VARIABLES       { ospfRouterId, ospfNbrIpAddr, 
                      ospfNbrAddressLessIndex, ospfNbrRtrId, 
                      ospfNbrState }
--     STATUS          mandatory
    DESCRIPTION     
            "An  ospfNbrStateChange  trap  signifies   that
             there  has been a change in the state of a non-
             virtual OSPF neighbor.   This  trap  should  be
             generated  when  the  neighbor  state regresses
             (e.g., goes from Attempt or Full  to  1-Way  or
             Down)  or progresses to a terminal state (e.g.,
             2-Way or Full).  When an  neighbor  transitions
             from  or  to Full on non-broadcast multi-access
             and broadcast networks, the trap should be gen-
             erated  by the designated router.  A designated
             router transitioning to Down will be  noted  by
             ospfIfStateChange."
    ::= 2

ospfVirtNbrStateChange TRAP-TYPE
    ENTERPRISE      ospfTraps
    VARIABLES       { ospfRouterId, ospfVirtNbrArea, ospfVirtNbrRtrId, 
                      ospfVirtNbrState }
--     STATUS          mandatory
    DESCRIPTION     
            "An ospfIfStateChange trap signifies that there
             has  been a change in the state of an OSPF vir-
             tual neighbor.  This trap should  be  generated
             when  the  neighbor state regresses (e.g., goes
             from Attempt or  Full  to  1-Way  or  Down)  or
             progresses to a terminal state (e.g., Full)."
    ::= 3

ospfIfConfigError TRAP-TYPE
    ENTERPRISE      ospfTraps
    VARIABLES       { ospfRouterId, ospfIfIpAddress, ospfAddressLessIf, 
                      ospfPacketSrc, ospfConfigErrorType, ospfPacketType }
--     STATUS          mandatory
    DESCRIPTION     
            "An ospfIfConfigError  trap  signifies  that  a
             packet  has  been received on a non-virtual in-
             terface  from  a  router  whose   configuration
             parameters  conflict  with this router's confi-
             guration parameters.  Note that the  event  op-
             tionMismatch  should  cause  a  trap only if it
             prevents an adjacency from forming."
    ::= 4

ospfVirtIfConfigError TRAP-TYPE
    ENTERPRISE      ospfTraps
    VARIABLES       { ospfRouterId, ospfVirtIfAreaId, ospfVirtIfNeighbor, 
                      ospfConfigErrorType, ospfPacketType }
--     STATUS          mandatory
    DESCRIPTION     
            "An ospfConfigError trap signifies that a pack-
             et  has  been  received  on a virtual interface
             from a router  whose  configuration  parameters
             conflict   with   this  router's  configuration
             parameters.  Note that the event optionMismatch
             should  cause a trap only if it prevents an ad-
             jacency from forming."
    ::= 5

ospfIfAuthFailure TRAP-TYPE
    ENTERPRISE      ospfTraps
    VARIABLES       { ospfRouterId, ospfIfIpAddress, ospfAddressLessIf, 
                      ospfPacketSrc, ospfConfigErrorType, ospfPacketType }
--     STATUS          mandatory
    DESCRIPTION     
            "An ospfIfAuthFailure  trap  signifies  that  a
             packet  has  been received on a non-virtual in-
             terface from a router whose authentication  key
             or  authentication  type  conflicts  with  this
             router's authentication key  or  authentication
             type."
    ::= 6

ospfVirtIfAuthFailure TRAP-TYPE
    ENTERPRISE      ospfTraps
    VARIABLES       { ospfRouterId, ospfVirtIfAreaId, ospfVirtIfNeighbor, 
                      ospfConfigErrorType, ospfPacketType }
--     STATUS          mandatory
    DESCRIPTION     
            "An ospfVirtIfAuthFailure trap signifies that a
             packet has been received on a virtual interface
             from a router whose authentication key  or  au-
             thentication  type conflicts with this router's
             authentication key or authentication type."
    ::= 7

ospfIfRxBadPacket TRAP-TYPE
    ENTERPRISE      ospfTraps
    VARIABLES       { ospfRouterId, ospfIfIpAddress, ospfAddressLessIf, 
                      ospfPacketSrc, ospfPacketType }
--     STATUS          mandatory
    DESCRIPTION     
            "An ospfIfRxBadPacket trap  signifies  that  an
             OSPF  packet has been received on a non-virtual
             interface that cannot be parsed."
    ::= 8

ospfVirtIfRxBadPacket TRAP-TYPE
    ENTERPRISE      ospfTraps
    VARIABLES       { ospfRouterId, ospfVirtIfAreaId, ospfVirtIfNeighbor, 
                      ospfPacketType }
--     STATUS          mandatory
    DESCRIPTION     
            "An ospfRxBadPacket trap signifies that an OSPF
             packet has been received on a virtual interface
             that cannot be parsed."
    ::= 9

ospfTxRetransmit TRAP-TYPE
    ENTERPRISE      ospfTraps
    VARIABLES       { ospfRouterId, ospfIfIpAddress, ospfAddressLessIf, 
                      ospfNbrRtrId, ospfPacketType, ospfLsdbType, 
                      ospfLsdbLsid, ospfLsdbRouterId }
--     STATUS          mandatory
    DESCRIPTION     
            "An ospfTxRetransmit  trap  signifies  than  an
             OSPF  packet  has  been retransmitted on a non-
             virtual interface.  All packets that may be re-
             transmitted  are associated with an LSDB entry.
             The LS type, LS ID, and Router ID are  used  to
             identify the LSDB entry."
    ::= 10

ospfVirtIfTxRetransmit TRAP-TYPE
    ENTERPRISE      ospfTraps
    VARIABLES       { ospfRouterId, ospfVirtIfAreaId, ospfVirtIfNeighbor, 
                      ospfPacketType, ospfLsdbType, ospfLsdbLsid, 
                      ospfLsdbRouterId }
--     STATUS          mandatory
    DESCRIPTION     
            "An ospfTxRetransmit  trap  signifies  than  an
             OSPF packet has been retransmitted on a virtual
             interface.  All packets that may be retransmit-
             ted  are  associated with an LSDB entry. The LS
             type, LS ID, and Router ID are used to identify
             the LSDB entry."
    ::= 11

ospfOriginateLsa TRAP-TYPE
    ENTERPRISE      ospfTraps
    VARIABLES       { ospfRouterId, ospfLsdbAreaId, ospfLsdbType, 
                      ospfLsdbLsid, ospfLsdbRouterId }
--     STATUS          mandatory
    DESCRIPTION     
            "An ospfOriginateLsa trap signifies that a  new
             LSA  has  been originated by this router.  This
             trap should not be invoked for simple refreshes
             of  LSAs  (which happesn every 30 minutes), but
             instead will only be invoked  when  an  LSA  is
             (re)originated due to a topology change.  Addi-
             tionally, this trap does not include LSAs  that
             are  being  flushed  because  they have reached
             MaxAge."
    ::= 12

ospfMaxAgeLsa TRAP-TYPE
    ENTERPRISE      ospfTraps
    VARIABLES       { ospfRouterId, ospfLsdbAreaId, ospfLsdbType, 
                      ospfLsdbLsid, ospfLsdbRouterId }
--     STATUS          mandatory
    DESCRIPTION     
            "An ospfMaxAgeLsa trap signifies  that  one  of
             the LSA in the router's link-state database has
             aged to MaxAge."
    ::= 13

ospfLsdbOverflow TRAP-TYPE
    ENTERPRISE      ospfTraps
    VARIABLES       { ospfRouterId, ospfExtLsdbLimit }
--     STATUS          mandatory
    DESCRIPTION     
            "An ospfLsdbOverflow trap  signifies  that  the
             number of LSAs in the router's link-state data-
             base has exceeded ospfExtLsdbLimit."
    ::= 14

ospfLsdbApproachingOverflow TRAP-TYPE
    ENTERPRISE      ospfTraps
    VARIABLES       { ospfRouterId, ospfExtLsdbLimit }
--     STATUS          mandatory
    DESCRIPTION     
            "An ospfLsdbApproachingOverflow trap  signifies
             that  the  number of LSAs in the router's link-
             state database has exceeded ninety  percent  of
             ospfExtLsdbLimit."
    ::= 15

ospfIfStateChange TRAP-TYPE
    ENTERPRISE      ospfTraps
    VARIABLES       { ospfRouterId, ospfIfIpAddress, ospfAddressLessIf, 
                      ospfIfState }
--     STATUS          mandatory
    DESCRIPTION     
            "An ospfIfStateChange trap signifies that there
             has been a change in the state of a non-virtual
             OSPF interface. This trap should  be  generated
             when  the interface state regresses (e.g., goes
             from Dr to Down) or progresses  to  a  terminal
             state  (i.e.,  Point-to-Point, DR Other, Dr, or
             Backup)."
    ::= 16

ospfTrapControlGroup OBJECT IDENTIFIER
    ::= { ospfTrapGroups 1 }

-- ospfTrapControlGroup OBJECT-GROUP
--     OBJECTS         { ospfSetTrap, ospfConfigErrorType, 
--                       ospfPacketType, ospfPacketSrc }
--     STATUS          mandatory
--     DESCRIPTION     
--             "These objects are required  to  control  traps
--              from OSPF systems."
--     ::= { ospfTrapGroups 1 }

ospfTrapCompliance OBJECT IDENTIFIER
    ::= { ospfTrapCompliances 1 }

-- ospfTrapCompliance MODULE-COMPLIANCE
--     STATUS          mandatory
--     DESCRIPTION     
--             "The compliance statement "

--     MODULE          -- -- this module

--         MANDATORY-GROUPS    { ospfTrapControlGroup }

--         GROUP       ospfTrapControlGroup
--         DESCRIPTION 
--             "This group is optional but recommended for all
--              OSPF systems"

--     ::= { ospfTrapCompliances 1 }

END -- end of module OSPF-TRAP-MIB.
