MIB-EMS-IPASOLINK-IX-SYSTEM-MIB DEFINITIONS ::= BEGIN
    
    IMPORTS
        Timeout
            FROM BRIDGE-MIB
        InterfaceIndex
            FROM IF-MIB
        InetAddressPrefixLength
            FROM INET-ADDRESS-MIB
        Ipv6Address
            FROM IPV6-TC
        OBJECT-TYPE
            FROM RFC-1212
        Counter, IpAddress, Opaque
            FROM RFC1155-SMI
        enterprises
            FROM SNMPv2-SMI
        DateAndTime, DisplayString, MacAddress, RowStatus
            FROM SNMPv2-TC;
    
    EnableDisableValue ::=
        INTEGER { invalid(0), disable(1), enable(2) }
    
    
    OffOnValue ::=
        INTEGER { invalid(0), off(1), on(2) }
    
    
    UsedNotusedValue ::=
        INTEGER { invalid(0), notUsed(1), used(2) }
    
    
    -- 1.3.6.1.4.1.119
    nec OBJECT IDENTIFIER
        ::= { enterprises 119 }
    
    -- 1.3.6.1.4.1.119.2
    nec-mib OBJECT IDENTIFIER
        ::= { nec 2 }
    
    -- 1.3.6.1.4.1.119.2.3
    necProductDepend OBJECT IDENTIFIER
        ::= { nec-mib 3 }
    
    -- 1.3.6.1.4.1.119.2.3.69
    radioEquipment OBJECT IDENTIFIER
        ::= { necProductDepend 69 }
    
    -- 1.3.6.1.4.1.119.2.3.69.203
    commonPnms OBJECT IDENTIFIER
        ::= { radioEquipment 203 }
    
    -- 1.3.6.1.4.1.119.2.3.69.203.507
    ipasolinkIx OBJECT IDENTIFIER
        ::= { commonPnms 507 }
    
    -- 1.3.6.1.4.1.119.2.3.69.203.507.5
    system5 OBJECT IDENTIFIER
        ::= { ipasolinkIx 5 }
    
    -- 1.3.6.1.4.1.119.2.3.69.203.507.5.1
    ipeSystemGroup OBJECT IDENTIFIER
        ::= { system5 1 }
    
    -- 1.3.6.1.4.1.119.2.3.69.203.507.5.1.1
    ipeSysInfoTable OBJECT-TYPE
        SYNTAX      SEQUENCE OF IpeSysInfoEntry
        ACCESS      not-accessible
        STATUS      mandatory
        DESCRIPTION
            "Table of System Information."
        ::= { ipeSystemGroup 1 }
    
    -- 1.3.6.1.4.1.119.2.3.69.203.507.5.1.1.1
    ipeSysInfoEntry OBJECT-TYPE
        SYNTAX      IpeSysInfoEntry
        ACCESS      not-accessible
        STATUS      mandatory
        DESCRIPTION
            "Entry of System Information."
        INDEX       { ipeSysInfoNEAddress, ipeSysInfoIndex }
        ::= { ipeSysInfoTable 1 }
    
    IpeSysInfoEntry ::= SEQUENCE {
        ipeSysInfoIndex                         INTEGER,
        ipeSysInfoNEAddress                     IpAddress,
        ipeSysNeName                            DisplayString,
        ipeSysAreaName                          DisplayString,
        ipeSysNote                              DisplayString,
        ipeSysPrimaryIpAddress                  IpAddress,
        ipeSysSubnetMask                        IpAddress,
        ipeSysDefaultGateway                    IpAddress,
        ipeSysMacAddress                        MacAddress,
        ipeSysMibVersion                        DisplayString,
        ipeSysEquipmentType                     INTEGER,
        ipeSysPmType                            INTEGER,
        ipeSysPrimaryIpv6Address                Ipv6Address,
        ipeSysPrimaryIpv6AddressPrefixLength    InetAddressPrefixLength,
        ipeSysIpv6DefaultGateway                Ipv6Address,
        ipeSysIpv6DefaultGatewayIfIndex         INTEGER,
        ipeSysPrimaryIfIndex                    INTEGER,
        ipeSysIpv4DropFilterEnable              EnableDisableValue
    }
    
    -- 1.3.6.1.4.1.119.2.3.69.203.507.5.1.1.1.1
    ipeSysInfoIndex OBJECT-TYPE
        SYNTAX      INTEGER (1)
        ACCESS      not-accessible
        STATUS      mandatory
        DESCRIPTION
            "Index of Table."
        ::= { ipeSysInfoEntry 1 }
    
    -- 1.3.6.1.4.1.119.2.3.69.203.507.5.1.1.1.2
    ipeSysInfoNEAddress OBJECT-TYPE
        SYNTAX      IpAddress
        ACCESS      not-accessible
        STATUS      mandatory
        DESCRIPTION
            ""
        ::= { ipeSysInfoEntry 2 }
    
    -- 1.3.6.1.4.1.119.2.3.69.203.507.5.1.1.1.3
    ipeSysNeName OBJECT-TYPE
        SYNTAX      DisplayString
        ACCESS      read-only
        STATUS      mandatory
        DESCRIPTION
            "Equipment name (for display)."
        ::= { ipeSysInfoEntry 3 }
    
    -- 1.3.6.1.4.1.119.2.3.69.203.507.5.1.1.1.4
    ipeSysAreaName OBJECT-TYPE
        SYNTAX      DisplayString
        ACCESS      read-only
        STATUS      mandatory
        DESCRIPTION
            "Area name (for display)."
        ::= { ipeSysInfoEntry 4 }
    
    -- 1.3.6.1.4.1.119.2.3.69.203.507.5.1.1.1.5
    ipeSysNote OBJECT-TYPE
        SYNTAX      DisplayString
        ACCESS      read-only
        STATUS      mandatory
        DESCRIPTION
            "Memorandum (for display)."
        ::= { ipeSysInfoEntry 5 }
    
    -- 1.3.6.1.4.1.119.2.3.69.203.507.5.1.1.1.6
    ipeSysPrimaryIpAddress OBJECT-TYPE
        SYNTAX      IpAddress
        ACCESS      read-only
        STATUS      mandatory
        DESCRIPTION
            "Primary IP Address (for display and setting)."
        ::= { ipeSysInfoEntry 6 }
    
    -- 1.3.6.1.4.1.119.2.3.69.203.507.5.1.1.1.7
    ipeSysSubnetMask OBJECT-TYPE
        SYNTAX      IpAddress
        ACCESS      read-only
        STATUS      mandatory
        DESCRIPTION
            "Subnet mask (for display)."
        ::= { ipeSysInfoEntry 7 }
    
    -- 1.3.6.1.4.1.119.2.3.69.203.507.5.1.1.1.8
    ipeSysDefaultGateway OBJECT-TYPE
        SYNTAX      IpAddress
        ACCESS      read-only
        STATUS      mandatory
        DESCRIPTION
            "Default gateway (for display)."
        ::= { ipeSysInfoEntry 8 }
    
    -- 1.3.6.1.4.1.119.2.3.69.203.507.5.1.1.1.9
    ipeSysMacAddress OBJECT-TYPE
        SYNTAX      MacAddress
        ACCESS      read-only
        STATUS      mandatory
        DESCRIPTION
            "MAC address (for display)."
        ::= { ipeSysInfoEntry 9 }
    
    -- 1.3.6.1.4.1.119.2.3.69.203.507.5.1.1.1.10
    ipeSysMibVersion OBJECT-TYPE
        SYNTAX      DisplayString
        ACCESS      read-only
        STATUS      mandatory
        DESCRIPTION
            "MIB version."
        ::= { ipeSysInfoEntry 10 }
    
    -- 1.3.6.1.4.1.119.2.3.69.203.507.5.1.1.1.11
    ipeSysEquipmentType OBJECT-TYPE
        SYNTAX      INTEGER
        ACCESS      read-only
        STATUS      mandatory
        DESCRIPTION
            "Equipment type."
        ::= { ipeSysInfoEntry 11 }
    
    -- 1.3.6.1.4.1.119.2.3.69.203.507.5.1.1.1.12
    ipeSysPmType OBJECT-TYPE
        SYNTAX      INTEGER (1..20)
        ACCESS      read-only
        STATUS      mandatory
        DESCRIPTION
            "Number of Branch.
             1=normalNE mode.
             1!=branchNE mode (2<= ipeSysPmType <= 20).
             7Branches(7), 8Branches(8) can not be set to this (iPASOLINK EX
             Advanced).
             The value Bridge1(11), Bridge2(12), Bridge3(13),
             Bridge4(14), Bridge5(15) Bridge6(16) are available (iPASOLINK EX
             Advanced)."
        ::= { ipeSysInfoEntry 12 }
    
    -- 1.3.6.1.4.1.119.2.3.69.203.507.5.1.1.1.13
    ipeSysPrimaryIpv6Address OBJECT-TYPE
        SYNTAX      Ipv6Address
        ACCESS      read-only
        STATUS      mandatory
        DESCRIPTION
            "Primary IPv6 Address (for display)."
        ::= { ipeSysInfoEntry 13 }
    
    -- 1.3.6.1.4.1.119.2.3.69.203.507.5.1.1.1.14
    ipeSysPrimaryIpv6AddressPrefixLength OBJECT-TYPE
        SYNTAX      InetAddressPrefixLength
        ACCESS      read-only
        STATUS      mandatory
        DESCRIPTION
            "Primary IPv6 Address Prefix Length (for display)."
        ::= { ipeSysInfoEntry 14 }
    
    -- 1.3.6.1.4.1.119.2.3.69.203.507.5.1.1.1.15
    ipeSysIpv6DefaultGateway OBJECT-TYPE
        SYNTAX      Ipv6Address
        ACCESS      read-only
        STATUS      mandatory
        DESCRIPTION
            "IPv6 Default gateway (for display)."
        ::= { ipeSysInfoEntry 15 }
    
    -- 1.3.6.1.4.1.119.2.3.69.203.507.5.1.1.1.16
    ipeSysIpv6DefaultGatewayIfIndex OBJECT-TYPE
        SYNTAX      INTEGER { any(0), bridge1(11), bridge2(12), bridge3(13),
                        bridge4(14), bridge5(15), bridge6(16), bridge7(17),
                        bridge8(18), bridge9(19), bridge10(20), bridge11(21),
                        bridge12(22), bridge13(23), bridge14(24),
                        bridge15(25), bridge16(26), bridge17(27),
                        bridge18(28), bridge19(29), bridge20(30) }
        ACCESS      read-only
        STATUS      mandatory
        DESCRIPTION
            "The index value which uniquely identifies the local
             interface through which the default gateway is
             reachable."
        ::= { ipeSysInfoEntry 16 }
    
    -- 1.3.6.1.4.1.119.2.3.69.203.507.5.1.1.1.17
    ipeSysPrimaryIfIndex OBJECT-TYPE
        SYNTAX      INTEGER { any(0), bridge1(11), bridge2(12), bridge3(13),
                        bridge4(14), bridge5(15), bridge6(16), bridge7(17),
                        bridge8(18), bridge9(19), bridge10(20), bridge11(21),
                        bridge12(22), bridge13(23), bridge14(24),
                        bridge15(25), bridge16(26), bridge17(27),
                        bridge18(28), bridge19(29), bridge20(30) }
        ACCESS      read-only
        STATUS      mandatory
        DESCRIPTION
            "Interface index of Prymary Ip Address."
        ::= { ipeSysInfoEntry 17 }
    
    -- 1.3.6.1.4.1.119.2.3.69.203.507.5.1.1.1.18
    ipeSysIpv4DropFilterEnable OBJECT-TYPE
        SYNTAX      EnableDisableValue
        ACCESS      read-only
        STATUS      mandatory
        DESCRIPTION
            "Enables or disables the drop filter for IPv4 packets on bridge
             and LCT interfaces.
             The disable(1) means to pass both incoming and outgoing IPv4
             packets on these interfaces.
             The enable(2) means to drop both incoming and outgoing IPv4
             packets on these interfaces.
             Note that ipeCfgBridgeIpStackMode: ipv4(1) and
             ipeSysIpv4DropFilterEnable: enable(2) cannot be set for the
             establishment of IPv4 communication."
        ::= { ipeSysInfoEntry 18 }
    
    -- 1.3.6.1.4.1.119.2.3.69.203.507.5.1.2
    ipeSysInventoryInfoTable OBJECT-TYPE
        SYNTAX      SEQUENCE OF IpeSysInventoryInfoEntry
        ACCESS      not-accessible
        STATUS      mandatory
        DESCRIPTION
            "Table of system basic information."
        ::= { ipeSystemGroup 2 }
    
    -- 1.3.6.1.4.1.119.2.3.69.203.507.5.1.2.1
    ipeSysInventoryInfoEntry OBJECT-TYPE
        SYNTAX      IpeSysInventoryInfoEntry
        ACCESS      not-accessible
        STATUS      mandatory
        DESCRIPTION
            "Entry of system basic information."
        INDEX       { ipeSysInventoryInfoNEAddress, ipeSysInventoryInfoIndex }
        ::= { ipeSysInventoryInfoTable 1 }
    
    IpeSysInventoryInfoEntry ::= SEQUENCE {
        ipeSysInventoryInfoIndex            INTEGER,
        ipeSysInventoryInfoNEAddress        IpAddress,
        ipeSysInvSoftwareVersion            DisplayString,
        ipeSysInvSoftwareReleaseDate        DateAndTime,
        ipeSysInvDlSoftwareVersion          DisplayString,
        ipeSysInvOperationSide              INTEGER,
        ipeSysInvStandbySoftwareVersion     DisplayString
    }
    
    -- 1.3.6.1.4.1.119.2.3.69.203.507.5.1.2.1.1
    ipeSysInventoryInfoIndex OBJECT-TYPE
        SYNTAX      INTEGER (1)
        ACCESS      not-accessible
        STATUS      mandatory
        DESCRIPTION
            "Index of table."
        ::= { ipeSysInventoryInfoEntry 1 }
    
    -- 1.3.6.1.4.1.119.2.3.69.203.507.5.1.2.1.2
    ipeSysInventoryInfoNEAddress OBJECT-TYPE
        SYNTAX      IpAddress
        ACCESS      not-accessible
        STATUS      mandatory
        DESCRIPTION
            ""
        ::= { ipeSysInventoryInfoEntry 2 }
    
    -- 1.3.6.1.4.1.119.2.3.69.203.507.5.1.2.1.3
    ipeSysInvSoftwareVersion OBJECT-TYPE
        SYNTAX      DisplayString
        ACCESS      read-only
        STATUS      mandatory
        DESCRIPTION
            "Software version."
        ::= { ipeSysInventoryInfoEntry 3 }
    
    -- 1.3.6.1.4.1.119.2.3.69.203.507.5.1.2.1.4
    ipeSysInvSoftwareReleaseDate OBJECT-TYPE
        SYNTAX      DateAndTime
        ACCESS      read-only
        STATUS      mandatory
        DESCRIPTION
            "Software update date and time."
        ::= { ipeSysInventoryInfoEntry 4 }
    
    -- 1.3.6.1.4.1.119.2.3.69.203.507.5.1.2.1.5
    ipeSysInvDlSoftwareVersion OBJECT-TYPE
        SYNTAX      DisplayString
        ACCESS      read-only
        STATUS      mandatory
        DESCRIPTION
            "Download control."
        ::= { ipeSysInventoryInfoEntry 5 }
    
    -- 1.3.6.1.4.1.119.2.3.69.203.507.5.1.2.1.6
    ipeSysInvOperationSide OBJECT-TYPE
        SYNTAX      INTEGER
        ACCESS      read-only
        STATUS      mandatory
        DESCRIPTION
            "Active side information."
        ::= { ipeSysInventoryInfoEntry 6 }
    
    -- 1.3.6.1.4.1.119.2.3.69.203.507.5.1.2.1.7
    ipeSysInvStandbySoftwareVersion OBJECT-TYPE
        SYNTAX      DisplayString
        ACCESS      read-only
        STATUS      mandatory
        DESCRIPTION
            "Firmware version of inactive side."
        ::= { ipeSysInventoryInfoEntry 7 }
    
    -- 1.3.6.1.4.1.119.2.3.69.203.507.5.1.3
    ipeSysOperationGroup OBJECT IDENTIFIER
        ::= { ipeSystemGroup 3 }
    
    -- 1.3.6.1.4.1.119.2.3.69.203.507.5.1.3.1
    ipeSysOpTimeTable OBJECT-TYPE
        SYNTAX      SEQUENCE OF IpeSysOpTimeEntry
        ACCESS      not-accessible
        STATUS      mandatory
        DESCRIPTION
            "Table of date and time."
        ::= { ipeSysOperationGroup 1 }
    
    -- 1.3.6.1.4.1.119.2.3.69.203.507.5.1.3.1.1
    ipeSysOpTimeEntry OBJECT-TYPE
        SYNTAX      IpeSysOpTimeEntry
        ACCESS      not-accessible
        STATUS      mandatory
        DESCRIPTION
            "Entry of date and time."
        INDEX       { ipeSysOpTimeNEAddress, ipeSysOpTimeIndex }
        ::= { ipeSysOpTimeTable 1 }
    
    IpeSysOpTimeEntry ::= SEQUENCE {
        ipeSysOpTimeIndex       INTEGER,
        ipeSysOpTimeNEAddress   IpAddress,
        ipeSysOpCurrentTime     DateAndTime,
        ipeSysOpStartTime       DateAndTime,
        ipeSysOpUpTime          Counter
    }
    
    -- 1.3.6.1.4.1.119.2.3.69.203.507.5.1.3.1.1.1
    ipeSysOpTimeIndex OBJECT-TYPE
        SYNTAX      INTEGER (1)
        ACCESS      not-accessible
        STATUS      mandatory
        DESCRIPTION
            "Index of table."
        ::= { ipeSysOpTimeEntry 1 }
    
    -- 1.3.6.1.4.1.119.2.3.69.203.507.5.1.3.1.1.2
    ipeSysOpTimeNEAddress OBJECT-TYPE
        SYNTAX      IpAddress
        ACCESS      not-accessible
        STATUS      mandatory
        DESCRIPTION
            ""
        ::= { ipeSysOpTimeEntry 2 }
    
    -- 1.3.6.1.4.1.119.2.3.69.203.507.5.1.3.1.1.3
    ipeSysOpCurrentTime OBJECT-TYPE
        SYNTAX      DateAndTime
        ACCESS      read-only
        STATUS      mandatory
        DESCRIPTION
            "Current time."
        ::= { ipeSysOpTimeEntry 3 }
    
    -- 1.3.6.1.4.1.119.2.3.69.203.507.5.1.3.1.1.4
    ipeSysOpStartTime OBJECT-TYPE
        SYNTAX      DateAndTime
        ACCESS      read-only
        STATUS      mandatory
        DESCRIPTION
            "OS started time."
        ::= { ipeSysOpTimeEntry 4 }
    
    -- 1.3.6.1.4.1.119.2.3.69.203.507.5.1.3.1.1.5
    ipeSysOpUpTime OBJECT-TYPE
        SYNTAX      Counter
        ACCESS      read-only
        STATUS      mandatory
        DESCRIPTION
            "Duration after OS started (second)."
        ::= { ipeSysOpTimeEntry 5 }
    
    -- 1.3.6.1.4.1.119.2.3.69.203.507.5.1.3.2
    ipeSysOpFileDownloadTable OBJECT-TYPE
        SYNTAX      SEQUENCE OF IpeSysOpFileDownloadEntry
        ACCESS      not-accessible
        STATUS      mandatory
        DESCRIPTION
            "Table of file download."
        ::= { ipeSysOperationGroup 2 }
    
    -- 1.3.6.1.4.1.119.2.3.69.203.507.5.1.3.2.1
    ipeSysOpFileDownloadEntry OBJECT-TYPE
        SYNTAX      IpeSysOpFileDownloadEntry
        ACCESS      not-accessible
        STATUS      mandatory
        DESCRIPTION
            "Entry of file download."
        INDEX       { ipeSysOpFileDownloadNEAddress, ipeSysOpFileDownloadIndex }
        ::= { ipeSysOpFileDownloadTable 1 }
    
    IpeSysOpFileDownloadEntry ::= SEQUENCE {
        ipeSysOpFileDownloadIndex           INTEGER,
        ipeSysOpFileDownloadNEAddress       IpAddress,
        ipeSysOpFileDownloadModule          INTEGER,
        ipeSysOpFileDownloadCpuResetDetail  INTEGER,
        ipeSysOpFileDownloadStatus          INTEGER,
        ipeSysOpFileDownloadCtrl            INTEGER,
        ipeSysOpFileDownloadProtocolType    INTEGER
    }
    
    -- 1.3.6.1.4.1.119.2.3.69.203.507.5.1.3.2.1.1
    ipeSysOpFileDownloadIndex OBJECT-TYPE
        SYNTAX      INTEGER (1)
        ACCESS      not-accessible
        STATUS      mandatory
        DESCRIPTION
            "Index of table."
        ::= { ipeSysOpFileDownloadEntry 1 }
    
    -- 1.3.6.1.4.1.119.2.3.69.203.507.5.1.3.2.1.2
    ipeSysOpFileDownloadNEAddress OBJECT-TYPE
        SYNTAX      IpAddress
        ACCESS      not-accessible
        STATUS      mandatory
        DESCRIPTION
            ""
        ::= { ipeSysOpFileDownloadEntry 2 }
    
    -- 1.3.6.1.4.1.119.2.3.69.203.507.5.1.3.2.1.3
    ipeSysOpFileDownloadModule OBJECT-TYPE
        SYNTAX      INTEGER { invalid(0), idu(1), odu(2), mdprm(3),
                        raFpga(4), ipeFpga(5), softkey(7), cfgNet(8),
                        cfgEqu(9), cfgUser(10), https(11), httpsKey(19),
                        httpsCrt(21) }
        ACCESS      read-only
        STATUS      mandatory
        DESCRIPTION
            "Program type. *'0:Invalidity' is used as an initial state.
             cliScripo(15) can not be set to this (iPASOLINK EX Advanced).
             The value controller(23) is available only for the iPASOLINK EX
             Advanced."
        ::= { ipeSysOpFileDownloadEntry 3 }
    
    -- 1.3.6.1.4.1.119.2.3.69.203.507.5.1.3.2.1.4
    ipeSysOpFileDownloadCpuResetDetail OBJECT-TYPE
        SYNTAX      INTEGER { invalid(0), revertReset(1), normReset(2) }
        ACCESS      read-only
        STATUS      mandatory
        DESCRIPTION
            "CPU reset control.
    
             0:Invalidity
             1:revert reset
             2:normal reset( without revert )
    
             *'0:Invalidity' is used as an initial state."
        ::= { ipeSysOpFileDownloadEntry 4 }
    
    -- 1.3.6.1.4.1.119.2.3.69.203.507.5.1.3.2.1.5
    ipeSysOpFileDownloadStatus OBJECT-TYPE
        SYNTAX      INTEGER { invalid(0), downloadCompleted(1),
                        downloadFailed(2), downloadExecuting(3),
                        downloadSuspending(4) }
        ACCESS      read-only
        STATUS      mandatory
        DESCRIPTION
            "Download result.
    
             0:Invalidity
             1:Completed
             2:Failed
             3:Executing
             4:Suspending
    
             *'0:Invalidity' is used as an initial state.
    
             *A change state is the following three kinds.
             1)When it operates normally:
               (Start)->(3:Executing)->(1:Completed)
             2)When it cancels on the way:
               (Start)->(3:Executing)->(4:Suspending)-> (Completed)
             3)When unusual detection is carried out on the way:
               (Start)->(3:Executing)->(2:Failed)
    
             *The download start from excluding (3:Executing) is permitted.
             *The download start from (3:Executing) is not permitted.
    
             *Pertinent details: ipeSysOpFileDownloadCtrl"
        ::= { ipeSysOpFileDownloadEntry 5 }
    
    -- 1.3.6.1.4.1.119.2.3.69.203.507.5.1.3.2.1.6
    ipeSysOpFileDownloadCtrl OBJECT-TYPE
        SYNTAX      INTEGER { invalid(0), startDownload(1),
                        suspendDownload(2), startUpload(3), endUpload(4),
                        resetDownload(5) }
        ACCESS      read-only
        STATUS      mandatory
        DESCRIPTION
            "Download control.
    
             0:Invalidity
             1:Download start
             2:Download suspend
             3:Upload start
             4:Upload end
             5:Download reset
    
             *'0:Invalidity' is used as an initial state.
             *'5:Download reset' terminates the FTP server(vsftpd) with the
             deletion processing in the type of the file for all download
             directory.
    
             *The object file name allows only alphanumeric character '0-9',
             'a-z', 'A-Z' of ASCII code, and sign '-_.+'.
    
             *Pertinent details: ipeSysOpFileDownloadProtocolType
             *Pertinent details: ipeSysOpFileDownloadModule
             *Pertinent details: ipeSysOpFileDownloadStatus
             *Pertinent details: ipeFsUpdateFileStatus
             *Pertinent details: ipeFsUsbProcStatus
    
             [Race condition]
             *When ipeSysOpFileDownloadStatus is (3:Executing) or
             (4:Suspending), (1:Download start) is invalid.
             *When ipeSysOpFileDownloadStatus is (4:Suspending), (2:Download
             suspend) is invalid.
             *When ipeSysOpFileDownloadStatus is (0:Invalidity), (1:Download
             start) is valid, but do nothing.
             *When ipeFsUpdateFileStatusis(3:Executing), it is invalid. Other
             one is valid.
             *When ipeFsUsbProcStatus is (2:Normal:Process executing), it is
             invalid. Other one is valid.
    
             [Indispensable condition]
             *When it is  (1:Download start) or (3:Upload start), (4:Upload
             end),ipeSysOpFileDownloadProtocolType setup is indispensable."
        ::= { ipeSysOpFileDownloadEntry 6 }
    
    -- 1.3.6.1.4.1.119.2.3.69.203.507.5.1.3.2.1.7
    ipeSysOpFileDownloadProtocolType OBJECT-TYPE
        SYNTAX      INTEGER { invalid(0), ftp(1), sftp(2), http(3) }
        ACCESS      read-only
        STATUS      mandatory
        DESCRIPTION
            "Kind of protocol,
    
             *'0:Invalidity' is used as an initial state.
    
             *Pertinent details: ipeSysOpFileDownloadCtrl"
        ::= { ipeSysOpFileDownloadEntry 7 }
    
    -- 1.3.6.1.4.1.119.2.3.69.203.507.5.1.3.3
    ipeSysOpProgramPmonRmonClearTable OBJECT-TYPE
        SYNTAX      SEQUENCE OF IpeSysOpProgramPmonRmonClearEntry
        ACCESS      not-accessible
        STATUS      mandatory
        DESCRIPTION
            ""
        ::= { ipeSysOperationGroup 3 }
    
    -- 1.3.6.1.4.1.119.2.3.69.203.507.5.1.3.3.1
    ipeSysOpProgramPmonRmonClearEntry OBJECT-TYPE
        SYNTAX      IpeSysOpProgramPmonRmonClearEntry
        ACCESS      not-accessible
        STATUS      mandatory
        DESCRIPTION
            ""
        INDEX       { ipeSysOpProgramPmonRmonClearNEAddress, ipeSysOpProgramPmonRmonClearIndex }
        ::= { ipeSysOpProgramPmonRmonClearTable 1 }
    
    IpeSysOpProgramPmonRmonClearEntry ::= SEQUENCE {
        ipeSysOpProgramPmonRmonClearIndex       INTEGER,
        ipeSysOpProgramPmonRmonClearNEAddress   IpAddress,
        ipeSysOpProgramPmonRmonClear            INTEGER,
        ipeSysOpProgramPmonRmonClearResult      INTEGER
    }
    
    -- 1.3.6.1.4.1.119.2.3.69.203.507.5.1.3.3.1.1
    ipeSysOpProgramPmonRmonClearIndex OBJECT-TYPE
        SYNTAX      INTEGER (1)
        ACCESS      not-accessible
        STATUS      mandatory
        DESCRIPTION
            ""
        ::= { ipeSysOpProgramPmonRmonClearEntry 1 }
    
    -- 1.3.6.1.4.1.119.2.3.69.203.507.5.1.3.3.1.2
    ipeSysOpProgramPmonRmonClearNEAddress OBJECT-TYPE
        SYNTAX      IpAddress
        ACCESS      not-accessible
        STATUS      mandatory
        DESCRIPTION
            ""
        ::= { ipeSysOpProgramPmonRmonClearEntry 2 }
    
    -- 1.3.6.1.4.1.119.2.3.69.203.507.5.1.3.3.1.3
    ipeSysOpProgramPmonRmonClear OBJECT-TYPE
        SYNTAX      INTEGER
        ACCESS      read-only
        STATUS      mandatory
        DESCRIPTION
            "PMON data clear control
             0:FIXED VALUE 1:REQUEST"
        ::= { ipeSysOpProgramPmonRmonClearEntry 3 }
    
    -- 1.3.6.1.4.1.119.2.3.69.203.507.5.1.3.3.1.4
    ipeSysOpProgramPmonRmonClearResult OBJECT-TYPE
        SYNTAX      INTEGER { invalid(0), completed(1), failed(2),
                        executing(3) }
        ACCESS      read-only
        STATUS      mandatory
        DESCRIPTION
            "PMON data clear control response
             1:COMPLETED
             2:FAILED
             3:EXECUTING"
        ::= { ipeSysOpProgramPmonRmonClearEntry 4 }
    
    -- 1.3.6.1.4.1.119.2.3.69.203.507.5.2
    ipeFileSystemGroup OBJECT IDENTIFIER
        ::= { system5 2 }
    
    -- 1.3.6.1.4.1.119.2.3.69.203.507.5.2.1
    ipeFsFileInfoTable OBJECT-TYPE
        SYNTAX      SEQUENCE OF IpeFsFileInfoEntry
        ACCESS      not-accessible
        STATUS      mandatory
        DESCRIPTION
            "Table of file information."
        ::= { ipeFileSystemGroup 1 }
    
    -- 1.3.6.1.4.1.119.2.3.69.203.507.5.2.1.1
    ipeFsFileInfoEntry OBJECT-TYPE
        SYNTAX      IpeFsFileInfoEntry
        ACCESS      not-accessible
        STATUS      mandatory
        DESCRIPTION
            "Entry of file information."
        INDEX       { ipeFsFileInfoNEAddress, ipeFsFileInfoIndex }
        ::= { ipeFsFileInfoTable 1 }
    
    IpeFsFileInfoEntry ::= SEQUENCE {
        ipeFsFileInfoIndex              INTEGER,
        ipeFsFileInfoNEAddress          IpAddress,
        ipeFsFileListType               INTEGER,
        ipeFsFileListCurrent            DisplayString,
        ipeFsFileListTemp               DisplayString,
        ipeFsUpdateFileDetail           DisplayString,
        ipeFsUpdateFileStatus           INTEGER,
        ipeFsUpdateFileStatusDetail     OCTET STRING,
        ipeFsUpdateFileProgressBase     INTEGER,
        ipeFsUpdateFileProgress         INTEGER,
        ipeFsUpdateFileUpdateList       DisplayString,
        ipeFsUpdateFileConfigPartial    OCTET STRING
    }
    
    -- 1.3.6.1.4.1.119.2.3.69.203.507.5.2.1.1.1
    ipeFsFileInfoIndex OBJECT-TYPE
        SYNTAX      INTEGER (1)
        ACCESS      not-accessible
        STATUS      mandatory
        DESCRIPTION
            "Index of Table."
        ::= { ipeFsFileInfoEntry 1 }
    
    -- 1.3.6.1.4.1.119.2.3.69.203.507.5.2.1.1.2
    ipeFsFileInfoNEAddress OBJECT-TYPE
        SYNTAX      IpAddress
        ACCESS      not-accessible
        STATUS      mandatory
        DESCRIPTION
            ""
        ::= { ipeFsFileInfoEntry 2 }
    
    -- 1.3.6.1.4.1.119.2.3.69.203.507.5.2.1.1.3
    ipeFsFileListType OBJECT-TYPE
        SYNTAX      INTEGER { invalid(0), idu(1), odu(2), mdprm(3),
                        raFpga(4), ipeFpga(5), softkey(7), cfgNet(8),
                        cfgEqu(9), cfgUser(10), https(11), pmon(12),
                        rmon(13), log(14), inventory(15), mac(16), all(17),
                        httpsKey(19), httpsCsr(20), httpsCrt(21) }
        ACCESS      read-only
        STATUS      mandatory
        DESCRIPTION
            "Type for acquisition
    
             0:Invalidity
             1: IDU
             2: ODU
             3: MODEM Parameter
             4: FPGA(Other slot)
             5: FPGA(Ctrl)
             6: MSE
             7: Software Key License
             8: Network Config
             9: Equipment Config
             10: User Config
             11: Server Certificate for HTTPS/HTTPS certificate issue request
             12: PMON data
             13: RMON data
             14: Command/event/alarm LOG
             15: Device Inventory file
             16: MAC learning entry
             17: all(All types)
             18: Card Firmware
             19: Private key for SSL Server Certificate
             20: CSR (Certificate Signing Request) for SSL Server Certificate
             21: CA (Certification Authority) certificate for SSL Server
             Certificate
             22: Modem Controller(valid for MODEM-AV)
             51: TRP
    
             *'0:Invalidity' is used as an initial state.
    
             *Pertinent details: ipeFsFileListCurrent
             *Pertinent details: ipeFsFileListTemp"
        ::= { ipeFsFileInfoEntry 3 }
    
    -- 1.3.6.1.4.1.119.2.3.69.203.507.5.2.1.1.4
    ipeFsFileListCurrent OBJECT-TYPE
        SYNTAX      DisplayString
        ACCESS      read-only
        STATUS      mandatory
        DESCRIPTION
            "Current file list (Flash-ROM).
    
             The list of the type set to ipeFsFileListType is acquired.
    
             Form of file list:
    
             It's 1 item by  'file name (It included in a path),file
             size,CRC'.
             Each item is divided at space.
    
             *CRC is fixed '0'.
    
             Ex) FilePath1/FileName1,size,CRC FilePath2/FileName2,size,CRC...
    
             [Indispensable condition]
             *ipeFsFileListType setup is indispensable."
        ::= { ipeFsFileInfoEntry 4 }
    
    -- 1.3.6.1.4.1.119.2.3.69.203.507.5.2.1.1.5
    ipeFsFileListTemp OBJECT-TYPE
        SYNTAX      DisplayString
        ACCESS      read-only
        STATUS      mandatory
        DESCRIPTION
            "Temporary file list (DRAM).
    
             The list of the type set to ipeFsFileListType is acquired.
    
             Form of file list:
    
             It's 1 item by 'file name (It isn't included in a pass),file
             size,CRC'.
             Each item is divided at space.
    
             *CRC is fixed '0'.
    
             Ex) Filename1,size,CRC Filename2,size,CRC...
    
             [Indispensable condition]
             *ipeFsFileListType setup is indispensable."
        ::= { ipeFsFileInfoEntry 5 }
    
    -- 1.3.6.1.4.1.119.2.3.69.203.507.5.2.1.1.6
    ipeFsUpdateFileDetail OBJECT-TYPE
        SYNTAX      DisplayString
        ACCESS      read-only
        STATUS      mandatory
        DESCRIPTION
            "File update control.
    
             Thing to specify object file after it downloads it by
             'ipeSysOpFileDownloadCtrl','ipeFsUsbCommand' and to demand file
             update.
    
             Ex) Filename1
    
             *The object file name allows only alphanumeric character '0-9',
             'a-z', 'A-Z' of ASCII code, and sign '-_.+'.
    
             *Pertinent details: ipeSysOpFileDownloadModule
             *Pertinent details: ipeFsUpdateFileUpdateList
             *Pertinent details: ipeSysOpFileDownloadStatus
             *Pertinent details: ipeFsUpdateFileStatus
             *Pertinent details: ipeFsUsbProcStatus
    
             [Race condition]
             *When ipeSysOpFileDownloadStatus is (3:Executing) or
             (4:Suspending), it is invalid.
             *When ipeFsUpdateFileStatusis(3:Executing), it is invalid.
             *When ipeFsUsbProcStatus is (2:Normal :Process executing), it is
             invalid.
    
             [Indispensable condition]
             *When ipeSysOpFileDownloadModule is 'odu(2)', 'mdprm(3)', or
             'raFpga(4)', ipeFsUpdateFileUpdateList setup is indispensable."
        ::= { ipeFsFileInfoEntry 6 }
    
    -- 1.3.6.1.4.1.119.2.3.69.203.507.5.2.1.1.7
    ipeFsUpdateFileStatus OBJECT-TYPE
        SYNTAX      INTEGER { invalid(0), success(1), failure(2),
                        executing(3), checking(4),
                        successWithoutRestrictedUser(5) }
        ACCESS      read-only
        STATUS      mandatory
        DESCRIPTION
            "Update result.
             0:Invalidity
             1:Success
             2:Failed
             3:Executing
             4:Checking
             5:Success but some restricted UserName(s) are ignored
    
             *'0:Invalidity' is used as an initial state.
    
             *The slot result of the correspondence is set to
             'IpeFsUpdateFileStatusDetail',
             and processing is continued when failing in the two or more
             slot update.
    
             *Pertinent details: ipeFsUpdateFileDetail
             *Pertinent details: ipeFsUpdateFileStatusDetail"
        ::= { ipeFsFileInfoEntry 7 }
    
    -- 1.3.6.1.4.1.119.2.3.69.203.507.5.2.1.1.8
    ipeFsUpdateFileStatusDetail OBJECT-TYPE
        SYNTAX      OCTET STRING (SIZE(42))
        ACCESS      read-only
        STATUS      mandatory
        DESCRIPTION
            "Update result is detailed.
    
             OCT: Update result of each slot
                   1: Completed
                   2: Failed
    
             The slot for which the current state is used becomes the
             following.
    
             OCT[0] : MainBoard(iPASO200)   or SLOT0
             OCT[1] : MODEM1(iPASO200)      or SLOT1
             OCT[2] : MODEM2(iPASO200)      or SLOT2
             OCT[3] : Option Card(iPASO200) or SLOT3
               :
             OCT[33]: ODU1
             OCT[34]: ODU2
             OCT[35]: ODU3
               :
    
             *Pertinent details: ipeSysOpFileDownloadCtrl
             *Pertinent details: ipeFsUpdateFileDetail
             *Pertinent details: ipeFsUsbCommand"
        ::= { ipeFsFileInfoEntry 8 }
    
    -- 1.3.6.1.4.1.119.2.3.69.203.507.5.2.1.1.9
    ipeFsUpdateFileProgressBase OBJECT-TYPE
        SYNTAX      INTEGER
        ACCESS      read-only
        STATUS      mandatory
        DESCRIPTION
            "Progress of update (denominator).
    
             *Pertinent details: ipeSysOpFileDownloadModule
             *Pertinent details: ipeFsUpdateFileStatus"
        ::= { ipeFsFileInfoEntry 9 }
    
    -- 1.3.6.1.4.1.119.2.3.69.203.507.5.2.1.1.10
    ipeFsUpdateFileProgress OBJECT-TYPE
        SYNTAX      INTEGER
        ACCESS      read-only
        STATUS      mandatory
        DESCRIPTION
            "Progress of update (molecule).
    
             *Pertinent details: ipeSysOpFileDownloadModule
             *Pertinent details: ipeFsUpdateFileStatus"
        ::= { ipeFsFileInfoEntry 10 }
    
    -- 1.3.6.1.4.1.119.2.3.69.203.507.5.2.1.1.11
    ipeFsUpdateFileUpdateList OBJECT-TYPE
        SYNTAX      DisplayString
        ACCESS      read-only
        STATUS      mandatory
        DESCRIPTION
            "Definition of update slot number.
    
             Form of file list:
             When downloading it to ODU/FPGA/MDPRM, the forwarding site slot
             number is enumerated by a comma end.
    
             Ex) 0,5,1,6,10...
               The slot number of relating MODEM and fpga must set the slot
             number of
               Option Card to odu and mdprm according to inventory
             information.
    
             The slot number to which the current state can be set becomes the
             following.
    
             iPASO200             iPASO400,1000
             0 : MainBoard     or SLOT0
             1 : MODEM1        or SLOT1
             2 : MODEM2        or SLOT2
             3 : Option Card   or SLOT3
                   :
             33: ODU1
             34: ODU2
             35: ODU3
                   :
    
             *Pertinent details: ipeFsUpdateFileDetail"
        ::= { ipeFsFileInfoEntry 11 }
    
    -- 1.3.6.1.4.1.119.2.3.69.203.507.5.2.1.1.12
    ipeFsUpdateFileConfigPartial OBJECT-TYPE
        SYNTAX      OCTET STRING (SIZE(4))
        ACCESS      read-only
        STATUS      mandatory
        DESCRIPTION
            "Specify Equipment Configuration Partial Download pattern.
             If this object is set with ipeFsUpdateFileDetail, the system will
             perform the partial download, otherwise the system will perform
             the normal download. And Partial Download is performed only when
             Equipment Configuration Dowload.
    
             SYNTAX is 32bit string. The definition of each bit is shown
             below.
    
             - bit1-4: specify download mode.
              0001 : normal mode
              other value : reserved (system rejects the request)
             - bit5-32: specify the equipment config part. Setting 1 to each
             bit means corresponding config download is activated.
              Bit5 : Equipment Configuration (must set when the normal mode)
              Bit6 : Radio Configuration
              Bit7 : Radio Configuration w/o Radio Frequency
                     Bit6 and Bit7 cannot be set to 1 simultaneously.
              Bit8 : E1/STM1 Mapping (must set when Bit6 or Bit7 is activated)
              Bit9 : MODEM Function setting
              Bit10: ETH Function setting
              Bit11: E1/STM1/Cross Connect Setting
              Bit12: PWE Setting
              Bit13: Equipment Clock/Synchronization Setting
              Bit14: Relay-Alarm Mapping
              Bit15: V11/OW Setting
              Bit16: Alarm/AIS Setting
              Bit17: PMON/RMON Setting
              Bit18: AUX Setting
    
              other: reserved (don't care)
    
             Example)
              the pattern of downloading the equipment configuration, radio
             configuration, E1/STM1 mapping, ETH Function Setting on normal
             mode.
               ipeFsUpdateFileConfigPartial =
                       '00011101010000000000000000000000'"
        ::= { ipeFsFileInfoEntry 12 }
    
    -- 1.3.6.1.4.1.119.2.3.69.203.507.5.2.2
    ipeFsUsbInfoTable OBJECT-TYPE
        SYNTAX      SEQUENCE OF IpeFsUsbInfoEntry
        ACCESS      not-accessible
        STATUS      mandatory
        DESCRIPTION
            "Table of USB memory information."
        ::= { ipeFileSystemGroup 2 }
    
    -- 1.3.6.1.4.1.119.2.3.69.203.507.5.2.2.1
    ipeFsUsbInfoEntry OBJECT-TYPE
        SYNTAX      IpeFsUsbInfoEntry
        ACCESS      not-accessible
        STATUS      mandatory
        DESCRIPTION
            "Entry of USB mamory information."
        INDEX       { ipeFsUsbInfoNEAddress, ipeFsUsbInfoIndex }
        ::= { ipeFsUsbInfoTable 1 }
    
    IpeFsUsbInfoEntry ::= SEQUENCE {
        ipeFsUsbInfoIndex       INTEGER,
        ipeFsUsbInfoNEAddress   IpAddress,
        ipeFsUsbCommand         DisplayString,
        ipeFsUsbProcStatus      INTEGER,
        ipeFsUsbList            DisplayString,
        ipeFsUsbConnectStatus   INTEGER
    }
    
    -- 1.3.6.1.4.1.119.2.3.69.203.507.5.2.2.1.1
    ipeFsUsbInfoIndex OBJECT-TYPE
        SYNTAX      INTEGER (1)
        ACCESS      not-accessible
        STATUS      mandatory
        DESCRIPTION
            "Index of Table."
        ::= { ipeFsUsbInfoEntry 1 }
    
    -- 1.3.6.1.4.1.119.2.3.69.203.507.5.2.2.1.2
    ipeFsUsbInfoNEAddress OBJECT-TYPE
        SYNTAX      IpAddress
        ACCESS      not-accessible
        STATUS      mandatory
        DESCRIPTION
            ""
        ::= { ipeFsUsbInfoEntry 2 }
    
    -- 1.3.6.1.4.1.119.2.3.69.203.507.5.2.2.1.3
    ipeFsUsbCommand OBJECT-TYPE
        SYNTAX      DisplayString
        ACCESS      read-only
        STATUS      mandatory
        DESCRIPTION
            "USB control mode/USB file path/Program type specification.
    
             [Mode],[Arg1],[Type]
               Mode:USB control mode
                 0:DL, 1:UL
               Arg1:object file path -1 (original file path (path from a
             chroot subordinate) When DL: Inside of USB, When UL: Inside of
             IPE)
                   Case of DL: Ex.) idu/iPASOLINK200-idufw-v1.00.XX.bin
                   Case of UL: Ex.) export/config/iPASOLINK-network.cfg
               Type:Program type
                   The program type set to  'ipeSysOpFileDownloadModule' is
             specified.
                   *The unsetting is allowed for an arbitrary, set item.
    
                  0: Invalid
                  1: IDU F/W
                  2: ODU F/W
                  3: MODEM Parameter
                  4: FPGA(Option Card)
                  5: FPGA(MainBoard)
                  6: MSE Card F/W
                  7: Software License Key
                  8: Network Config
                  9: Equipment Config
                 10: User Config
                 11: HTTPS Server Certificate
    
             *The object file name allows only alphanumeric character '0-9',
             'a-z', 'A-Z' of ASCII code, and sign '-_.+'.
    
             *Pertinent details: ipeSysOpFileDownloadModule
             *Pertinent details: ipeSysOpFileDownloadStatus
             *Pertinent details: ipeFsUpdateFileStatus
             *Pertinent details: ipeFsUsbProcStatus
    
             [Race condition]
             *When ipeSysOpFileDownloadStatus is (3:Executing) or
             (4:Suspending), (0:DL) is invalid.
             *When ipeFsUpdateFileStatusis (3:Executing),  (0:DL) is invalid.
             *When ipeFsUsbProcStatus is (2:Normal :Process executing),
             (0:DL) is invalid."
        ::= { ipeFsUsbInfoEntry 3 }
    
    -- 1.3.6.1.4.1.119.2.3.69.203.507.5.2.2.1.4
    ipeFsUsbProcStatus OBJECT-TYPE
        SYNTAX      INTEGER { invalid(0), completed(1), executing(2),
                        diskFullError(98), noSuchFileError(99),
                        unKnownFileError(101), notInsertError(102),
                        accessError(103), otherError(127) }
        ACCESS      read-only
        STATUS      mandatory
        DESCRIPTION
            "Status of USB memory control result.
    
             The classification of a setting value and the meaning are as
             follows.
               0:Invalidity
               1:NORMAL:Normal end
               2:NORMAL:Executing
              98:ERROR:The lack of free space on disk or media
              99:ERROR:File/directory not found
             101:ERROR:The kind of designated files,the size, contents, etc.
             are unjust
             102:ERROR:Media aren't inserted
             103:ERROR:Media access error (ex:unjust format)
             127:ERROR:Undefined error (other errors)
             When having a control instruction, it's made '2:Executing'.
    
             *'0:Invalidity' is used as an initial state.
    
             *Pertinent details: ipeFsUsbCommand"
        ::= { ipeFsUsbInfoEntry 4 }
    
    -- 1.3.6.1.4.1.119.2.3.69.203.507.5.2.2.1.5
    ipeFsUsbList OBJECT-TYPE
        SYNTAX      DisplayString
        ACCESS      read-only
        STATUS      mandatory
        DESCRIPTION
            "File list format.
    
             Form of file list:
    
             It's 1 item by 'file name (path from a chroot subordinate),file
             size,CRC'.
             Each item is divided at space.
    
             *CRC is fixed '0'.
    
             Ex) FilePath1/FileName1,size,CRC FilePath2/FileName2,size,CRC..."
        ::= { ipeFsUsbInfoEntry 5 }
    
    -- 1.3.6.1.4.1.119.2.3.69.203.507.5.2.2.1.6
    ipeFsUsbConnectStatus OBJECT-TYPE
        SYNTAX      INTEGER { usbConnect(1), usbNoConnect(2) }
        ACCESS      read-only
        STATUS      mandatory
        DESCRIPTION
            "Status of connection USB memory.
    
             1:Connect
             2:Not connect"
        ::= { ipeFsUsbInfoEntry 6 }
    
    -- 1.3.6.1.4.1.119.2.3.69.203.507.5.3
    ipeConfigurationGroup OBJECT IDENTIFIER
        ::= { system5 3 }
    
    -- 1.3.6.1.4.1.119.2.3.69.203.507.5.3.1
    ipeCfgSystemTable OBJECT-TYPE
        SYNTAX      SEQUENCE OF IpeCfgSystemEntry
        ACCESS      not-accessible
        STATUS      mandatory
        DESCRIPTION
            "Table of System Item Information."
        ::= { ipeConfigurationGroup 1 }
    
    -- 1.3.6.1.4.1.119.2.3.69.203.507.5.3.1.1
    ipeCfgSystemEntry OBJECT-TYPE
        SYNTAX      IpeCfgSystemEntry
        ACCESS      not-accessible
        STATUS      mandatory
        DESCRIPTION
            "Entry of System Item Information."
        INDEX       { ipeCfgSystemNEAddress, ipeCfgSystemIndex }
        ::= { ipeCfgSystemTable 1 }
    
    IpeCfgSystemEntry ::= SEQUENCE {
        ipeCfgSystemIndex       INTEGER,
        ipeCfgSystemNEAddress   IpAddress,
        ipeCfgNeName            DisplayString,
        ipeCfgAreaName          DisplayString,
        ipeCfgMemo              DisplayString
    }
    
    -- 1.3.6.1.4.1.119.2.3.69.203.507.5.3.1.1.1
    ipeCfgSystemIndex OBJECT-TYPE
        SYNTAX      INTEGER (1)
        ACCESS      not-accessible
        STATUS      mandatory
        DESCRIPTION
            "Index of table."
        ::= { ipeCfgSystemEntry 1 }
    
    -- 1.3.6.1.4.1.119.2.3.69.203.507.5.3.1.1.2
    ipeCfgSystemNEAddress OBJECT-TYPE
        SYNTAX      IpAddress
        ACCESS      not-accessible
        STATUS      mandatory
        DESCRIPTION
            ""
        ::= { ipeCfgSystemEntry 2 }
    
    -- 1.3.6.1.4.1.119.2.3.69.203.507.5.3.1.1.3
    ipeCfgNeName OBJECT-TYPE
        SYNTAX      DisplayString
        ACCESS      read-only
        STATUS      mandatory
        DESCRIPTION
            "PASOLINK unit name. White space characters are not allowed for
             head or tail of characters."
        ::= { ipeCfgSystemEntry 3 }
    
    -- 1.3.6.1.4.1.119.2.3.69.203.507.5.3.1.1.4
    ipeCfgAreaName OBJECT-TYPE
        SYNTAX      DisplayString
        ACCESS      read-only
        STATUS      mandatory
        DESCRIPTION
            "Area name. White space characters are not allowed for head or
             tail of characters."
        ::= { ipeCfgSystemEntry 4 }
    
    -- 1.3.6.1.4.1.119.2.3.69.203.507.5.3.1.1.5
    ipeCfgMemo OBJECT-TYPE
        SYNTAX      DisplayString
        ACCESS      read-only
        STATUS      mandatory
        DESCRIPTION
            "Memorandum. White space characters are not allowed for head or
             tail of characters."
        ::= { ipeCfgSystemEntry 5 }
    
    -- 1.3.6.1.4.1.119.2.3.69.203.507.5.3.2
    ipeCfgOemTable OBJECT-TYPE
        SYNTAX      SEQUENCE OF IpeCfgOemEntry
        ACCESS      not-accessible
        STATUS      mandatory
        DESCRIPTION
            "Table of Equipment Item Information."
        ::= { ipeConfigurationGroup 2 }
    
    -- 1.3.6.1.4.1.119.2.3.69.203.507.5.3.2.1
    ipeCfgOemEntry OBJECT-TYPE
        SYNTAX      IpeCfgOemEntry
        ACCESS      not-accessible
        STATUS      mandatory
        DESCRIPTION
            "Entry of Equipment Item Information."
        INDEX       { ipeCfgOemNEAddress, ipeCfgOemIndex }
        ::= { ipeCfgOemTable 1 }
    
    IpeCfgOemEntry ::= SEQUENCE {
        ipeCfgOemIndex          INTEGER,
        ipeCfgOemNEAddress      IpAddress,
        ipeCfgOemSysDescr       DisplayString,
        ipeCfgOemSysContact     DisplayString,
        ipeCfgOemSysName        DisplayString,
        ipeCfgOemSysLocation    DisplayString
    }
    
    -- 1.3.6.1.4.1.119.2.3.69.203.507.5.3.2.1.1
    ipeCfgOemIndex OBJECT-TYPE
        SYNTAX      INTEGER (1)
        ACCESS      not-accessible
        STATUS      mandatory
        DESCRIPTION
            "Index of table."
        ::= { ipeCfgOemEntry 1 }
    
    -- 1.3.6.1.4.1.119.2.3.69.203.507.5.3.2.1.2
    ipeCfgOemNEAddress OBJECT-TYPE
        SYNTAX      IpAddress
        ACCESS      not-accessible
        STATUS      mandatory
        DESCRIPTION
            ""
        ::= { ipeCfgOemEntry 2 }
    
    -- 1.3.6.1.4.1.119.2.3.69.203.507.5.3.2.1.3
    ipeCfgOemSysDescr OBJECT-TYPE
        SYNTAX      DisplayString
        ACCESS      read-only
        STATUS      mandatory
        DESCRIPTION
            "System Description.
             The space of the begininng and end dose not permit it."
        ::= { ipeCfgOemEntry 3 }
    
    -- 1.3.6.1.4.1.119.2.3.69.203.507.5.3.2.1.4
    ipeCfgOemSysContact OBJECT-TYPE
        SYNTAX      DisplayString
        ACCESS      read-only
        STATUS      mandatory
        DESCRIPTION
            "System contact.
             The space of the begininng and end dose not permit it."
        ::= { ipeCfgOemEntry 4 }
    
    -- 1.3.6.1.4.1.119.2.3.69.203.507.5.3.2.1.5
    ipeCfgOemSysName OBJECT-TYPE
        SYNTAX      DisplayString
        ACCESS      read-only
        STATUS      mandatory
        DESCRIPTION
            "System name.
             The space of the begininng and end dose not permit it."
        ::= { ipeCfgOemEntry 5 }
    
    -- 1.3.6.1.4.1.119.2.3.69.203.507.5.3.2.1.6
    ipeCfgOemSysLocation OBJECT-TYPE
        SYNTAX      DisplayString
        ACCESS      read-only
        STATUS      mandatory
        DESCRIPTION
            "System location.
             The space of the begininng and end dose not permit it."
        ::= { ipeCfgOemEntry 6 }
    
    -- 1.3.6.1.4.1.119.2.3.69.203.507.5.3.4
    ipeCfgNtp OBJECT IDENTIFIER
        ::= { ipeConfigurationGroup 4 }
    
    -- 1.3.6.1.4.1.119.2.3.69.203.507.5.3.4.1
    ipeCfgNtpServiceTable OBJECT-TYPE
        SYNTAX      SEQUENCE OF IpeCfgNtpServiceEntry
        ACCESS      not-accessible
        STATUS      mandatory
        DESCRIPTION
            "Table of NTP configuration information."
        ::= { ipeCfgNtp 1 }
    
    -- 1.3.6.1.4.1.119.2.3.69.203.507.5.3.4.1.1
    ipeCfgNtpServiceEntry OBJECT-TYPE
        SYNTAX      IpeCfgNtpServiceEntry
        ACCESS      not-accessible
        STATUS      mandatory
        DESCRIPTION
            "Entry of NTP configuration information."
        INDEX       { ipeCfgNtpServiceNEAddress, ipeCfgNtpServiceIndex }
        ::= { ipeCfgNtpServiceTable 1 }
    
    IpeCfgNtpServiceEntry ::= SEQUENCE {
        ipeCfgNtpServiceIndex                   INTEGER,
        ipeCfgNtpServiceNEAddress               IpAddress,
        ipeCfgNtpServiceEnable                  INTEGER,
        ipeCfgNtpServerMode                     INTEGER,
        ipeCfgNtpClientMode                     INTEGER,
        ipeCfgNtpServerStratum                  INTEGER,
        ipeCfgNtpServerMulticastPort            INTEGER,
        ipeCfgNtpServerMulticastIntervalTime    INTEGER
    }
    
    -- 1.3.6.1.4.1.119.2.3.69.203.507.5.3.4.1.1.1
    ipeCfgNtpServiceIndex OBJECT-TYPE
        SYNTAX      INTEGER (1)
        ACCESS      not-accessible
        STATUS      mandatory
        DESCRIPTION
            "Index of table."
        ::= { ipeCfgNtpServiceEntry 1 }
    
    -- 1.3.6.1.4.1.119.2.3.69.203.507.5.3.4.1.1.2
    ipeCfgNtpServiceNEAddress OBJECT-TYPE
        SYNTAX      IpAddress
        ACCESS      not-accessible
        STATUS      mandatory
        DESCRIPTION
            ""
        ::= { ipeCfgNtpServiceEntry 2 }
    
    -- 1.3.6.1.4.1.119.2.3.69.203.507.5.3.4.1.1.3
    ipeCfgNtpServiceEnable OBJECT-TYPE
        SYNTAX      INTEGER { invalid(0), disabled(1), enabled(2) }
        ACCESS      read-only
        STATUS      mandatory
        DESCRIPTION
            "NTP control enable."
        ::= { ipeCfgNtpServiceEntry 3 }
    
    -- 1.3.6.1.4.1.119.2.3.69.203.507.5.3.4.1.1.4
    ipeCfgNtpServerMode OBJECT-TYPE
        SYNTAX      INTEGER { invalid(0), unicast(1), multicast(2),
                        disabled(3) }
        ACCESS      read-only
        STATUS      mandatory
        DESCRIPTION
            "NTP server mode."
        ::= { ipeCfgNtpServiceEntry 4 }
    
    -- 1.3.6.1.4.1.119.2.3.69.203.507.5.3.4.1.1.5
    ipeCfgNtpClientMode OBJECT-TYPE
        SYNTAX      INTEGER { invalid(0), unicast(1), multicast(2),
                        disabled(3) }
        ACCESS      read-only
        STATUS      mandatory
        DESCRIPTION
            "NTP client mode."
        ::= { ipeCfgNtpServiceEntry 5 }
    
    -- 1.3.6.1.4.1.119.2.3.69.203.507.5.3.4.1.1.6
    ipeCfgNtpServerStratum OBJECT-TYPE
        SYNTAX      INTEGER (2..15)
        ACCESS      read-only
        STATUS      mandatory
        DESCRIPTION
            "NTP Stratum."
        ::= { ipeCfgNtpServiceEntry 6 }
    
    -- 1.3.6.1.4.1.119.2.3.69.203.507.5.3.4.1.1.7
    ipeCfgNtpServerMulticastPort OBJECT-TYPE
        SYNTAX      INTEGER
        ACCESS      read-only
        STATUS      mandatory
        DESCRIPTION
            "NTP server multicast port.
             Bridge7(17), Bridge8(18) can not be set to this (iPASOLINK EX
             Advanced).
             The value Bridge1(11), Bridge2(12), Bridge3(13),
             Bridge4(14), Bridge5(15) Bridge6(16) are available (iPASOLINK EX
             Advanced)."
        ::= { ipeCfgNtpServiceEntry 7 }
    
    -- 1.3.6.1.4.1.119.2.3.69.203.507.5.3.4.1.1.8
    ipeCfgNtpServerMulticastIntervalTime OBJECT-TYPE
        SYNTAX      INTEGER (4..17)
        ACCESS      read-only
        STATUS      mandatory
        DESCRIPTION
            "Value of NTP multicast polling time."
        ::= { ipeCfgNtpServiceEntry 8 }
    
    -- 1.3.6.1.4.1.119.2.3.69.203.507.5.3.4.2
    ipeCfgNtpServerTable OBJECT-TYPE
        SYNTAX      SEQUENCE OF IpeCfgNtpServerEntry
        ACCESS      not-accessible
        STATUS      mandatory
        DESCRIPTION
            "Table of NTP server information."
        ::= { ipeCfgNtp 2 }
    
    -- 1.3.6.1.4.1.119.2.3.69.203.507.5.3.4.2.1
    ipeCfgNtpServerEntry OBJECT-TYPE
        SYNTAX      IpeCfgNtpServerEntry
        ACCESS      not-accessible
        STATUS      mandatory
        DESCRIPTION
            "Entry of NTP server information."
        INDEX       { ipeCfgNtpServerNEAddress, ipeCfgNtpServerIndex }
        ::= { ipeCfgNtpServerTable 1 }
    
    IpeCfgNtpServerEntry ::= SEQUENCE {
        ipeCfgNtpServerIndex        INTEGER,
        ipeCfgNtpServerNEAddress    IpAddress,
        ipeCfgNtpServerAddress      IpAddress,
        ipeCfgNtpVersion            INTEGER,
        ipeCfgNtpPollTime           INTEGER,
        ipeCfgNtpServerV6Address    Ipv6Address,
        ipeCfgNtpServerAddressType  INTEGER
    }
    
    -- 1.3.6.1.4.1.119.2.3.69.203.507.5.3.4.2.1.1
    ipeCfgNtpServerIndex OBJECT-TYPE
        SYNTAX      INTEGER (1..4)
        ACCESS      not-accessible
        STATUS      mandatory
        DESCRIPTION
            "Index of table."
        ::= { ipeCfgNtpServerEntry 1 }
    
    -- 1.3.6.1.4.1.119.2.3.69.203.507.5.3.4.2.1.2
    ipeCfgNtpServerNEAddress OBJECT-TYPE
        SYNTAX      IpAddress
        ACCESS      not-accessible
        STATUS      mandatory
        DESCRIPTION
            ""
        ::= { ipeCfgNtpServerEntry 2 }
    
    -- 1.3.6.1.4.1.119.2.3.69.203.507.5.3.4.2.1.3
    ipeCfgNtpServerAddress OBJECT-TYPE
        SYNTAX      IpAddress
        ACCESS      read-only
        STATUS      mandatory
        DESCRIPTION
            "IP Address of NTP server."
        ::= { ipeCfgNtpServerEntry 3 }
    
    -- 1.3.6.1.4.1.119.2.3.69.203.507.5.3.4.2.1.4
    ipeCfgNtpVersion OBJECT-TYPE
        SYNTAX      INTEGER (3..4)
        ACCESS      read-only
        STATUS      mandatory
        DESCRIPTION
            "Version of supported NTP message."
        ::= { ipeCfgNtpServerEntry 4 }
    
    -- 1.3.6.1.4.1.119.2.3.69.203.507.5.3.4.2.1.5
    ipeCfgNtpPollTime OBJECT-TYPE
        SYNTAX      INTEGER (4..17)
        ACCESS      read-only
        STATUS      mandatory
        DESCRIPTION
            "NTP Polling Time, in seconds as a power of two.
             For instance, a value of six indicates a interval of 64 seconds.
    
             Note) The value less than 6 is rejected by the agent because of
             the system recommendation.
              iPASOLINK 200/400/1000 series : R3.5 or later.
              iPASOLINK AOR : R1.0 or later."
        ::= { ipeCfgNtpServerEntry 5 }
    
    -- 1.3.6.1.4.1.119.2.3.69.203.507.5.3.4.2.1.7
    ipeCfgNtpServerV6Address OBJECT-TYPE
        SYNTAX      Ipv6Address
        ACCESS      read-only
        STATUS      mandatory
        DESCRIPTION
            "IPv6 Address of NTP Server.
    
             When this object is configured, the NTP Client will run
             over IPv6 and the ipeCfgNtpServerAddress will be
             unconfigured (reset to 0.0.0.0).
    
             When configuring ipeCfgNtpServerAddress, the NTP Client
             will run over IPv4 and this object will be unconfigured
             (reset to ::).
    
             The following are not valid addresses:
               ::1/128 IPv6 Loopback
               FE80::/10 Link local
               FF00::/8 IPv6 Multicasts"
        ::= { ipeCfgNtpServerEntry 7 }
    
    -- 1.3.6.1.4.1.119.2.3.69.203.507.5.3.4.2.1.8
    ipeCfgNtpServerAddressType OBJECT-TYPE
        SYNTAX      INTEGER { invalid(0), ipv4(1), ipv6(2) }
        ACCESS      read-only
        STATUS      mandatory
        DESCRIPTION
            "Indicate IP address type of this server.
    
             ipv4 : server has IPv4 address.
             ipv6 : server has IPv6 address."
        ::= { ipeCfgNtpServerEntry 8 }
    
    -- 1.3.6.1.4.1.119.2.3.69.203.507.5.3.7
    ipeCfgFtp OBJECT IDENTIFIER
        ::= { ipeConfigurationGroup 7 }
    
    -- 1.3.6.1.4.1.119.2.3.69.203.507.5.3.7.1
    ipeCfgFtpServerTable OBJECT-TYPE
        SYNTAX      SEQUENCE OF IpeCfgFtpServerEntry
        ACCESS      not-accessible
        STATUS      mandatory
        DESCRIPTION
            "Table of FTP server configuration information."
        ::= { ipeCfgFtp 1 }
    
    -- 1.3.6.1.4.1.119.2.3.69.203.507.5.3.7.1.1
    ipeCfgFtpServerEntry OBJECT-TYPE
        SYNTAX      IpeCfgFtpServerEntry
        ACCESS      not-accessible
        STATUS      mandatory
        DESCRIPTION
            "Entry of FTP server configuration information."
        INDEX       { ipeCfgFtpServerNEAddress, ipeCfgFtpServerIndex }
        ::= { ipeCfgFtpServerTable 1 }
    
    IpeCfgFtpServerEntry ::= SEQUENCE {
        ipeCfgFtpServerIndex            INTEGER,
        ipeCfgFtpServerNEAddress        IpAddress,
        ipeCfgFtpServerEnable           INTEGER,
        ipeCfgFtpServerCommandTcpPort   INTEGER,
        ipeCfgFtpServerDataTcpPort      INTEGER,
        ipeCfgFtpServerMaxSession       INTEGER,
        ipeCfgFtpServerAutoDisable      INTEGER
    }
    
    -- 1.3.6.1.4.1.119.2.3.69.203.507.5.3.7.1.1.1
    ipeCfgFtpServerIndex OBJECT-TYPE
        SYNTAX      INTEGER (1)
        ACCESS      not-accessible
        STATUS      mandatory
        DESCRIPTION
            "Index of table."
        ::= { ipeCfgFtpServerEntry 1 }
    
    -- 1.3.6.1.4.1.119.2.3.69.203.507.5.3.7.1.1.2
    ipeCfgFtpServerNEAddress OBJECT-TYPE
        SYNTAX      IpAddress
        ACCESS      not-accessible
        STATUS      mandatory
        DESCRIPTION
            ""
        ::= { ipeCfgFtpServerEntry 2 }
    
    -- 1.3.6.1.4.1.119.2.3.69.203.507.5.3.7.1.1.3
    ipeCfgFtpServerEnable OBJECT-TYPE
        SYNTAX      INTEGER { invalid(0), serviceDisable(1),
                        serviceEnable(2), alwaysEnable(3) }
        ACCESS      read-only
        STATUS      mandatory
        DESCRIPTION
            "FTP control enable."
        ::= { ipeCfgFtpServerEntry 3 }
    
    -- 1.3.6.1.4.1.119.2.3.69.203.507.5.3.7.1.1.4
    ipeCfgFtpServerCommandTcpPort OBJECT-TYPE
        SYNTAX      INTEGER (1..65535)
        ACCESS      read-only
        STATUS      mandatory
        DESCRIPTION
            "Port number of FTP command."
        ::= { ipeCfgFtpServerEntry 4 }
    
    -- 1.3.6.1.4.1.119.2.3.69.203.507.5.3.7.1.1.5
    ipeCfgFtpServerDataTcpPort OBJECT-TYPE
        SYNTAX      INTEGER (1..65535)
        ACCESS      read-only
        STATUS      mandatory
        DESCRIPTION
            "Port number of FTP data transfer."
        ::= { ipeCfgFtpServerEntry 5 }
    
    -- 1.3.6.1.4.1.119.2.3.69.203.507.5.3.7.1.1.6
    ipeCfgFtpServerMaxSession OBJECT-TYPE
        SYNTAX      INTEGER (1..3)
        ACCESS      read-only
        STATUS      mandatory
        DESCRIPTION
            "Number of max connections."
        ::= { ipeCfgFtpServerEntry 6 }
    
    -- 1.3.6.1.4.1.119.2.3.69.203.507.5.3.7.1.1.7
    ipeCfgFtpServerAutoDisable OBJECT-TYPE
        SYNTAX      INTEGER { invalid(0), disabled(1), enabled(2) }
        ACCESS      read-only
        STATUS      mandatory
        DESCRIPTION
            "FTP automatic stop control enable."
        ::= { ipeCfgFtpServerEntry 7 }
    
    -- 1.3.6.1.4.1.119.2.3.69.203.507.5.3.8
    ipeCfgSftp OBJECT IDENTIFIER
        ::= { ipeConfigurationGroup 8 }
    
    -- 1.3.6.1.4.1.119.2.3.69.203.507.5.3.8.1
    ipeCfgSftpServerTable OBJECT-TYPE
        SYNTAX      SEQUENCE OF IpeCfgSftpServerEntry
        ACCESS      not-accessible
        STATUS      mandatory
        DESCRIPTION
            "Table of SFTP server configuration information."
        ::= { ipeCfgSftp 1 }
    
    -- 1.3.6.1.4.1.119.2.3.69.203.507.5.3.8.1.1
    ipeCfgSftpServerEntry OBJECT-TYPE
        SYNTAX      IpeCfgSftpServerEntry
        ACCESS      not-accessible
        STATUS      mandatory
        DESCRIPTION
            "Entry of SFTP server configuration information."
        INDEX       { ipeCfgSftpServerNEAddress, ipeCfgSftpServerIndex }
        ::= { ipeCfgSftpServerTable 1 }
    
    IpeCfgSftpServerEntry ::= SEQUENCE {
        ipeCfgSftpServerIndex           INTEGER,
        ipeCfgSftpServerNEAddress       IpAddress,
        ipeCfgSftpServerEnable          INTEGER,
        ipeCfgSftpServerAutoDisable     INTEGER
    }
    
    -- 1.3.6.1.4.1.119.2.3.69.203.507.5.3.8.1.1.1
    ipeCfgSftpServerIndex OBJECT-TYPE
        SYNTAX      INTEGER (1)
        ACCESS      not-accessible
        STATUS      mandatory
        DESCRIPTION
            "Index of table."
        ::= { ipeCfgSftpServerEntry 1 }
    
    -- 1.3.6.1.4.1.119.2.3.69.203.507.5.3.8.1.1.2
    ipeCfgSftpServerNEAddress OBJECT-TYPE
        SYNTAX      IpAddress
        ACCESS      not-accessible
        STATUS      mandatory
        DESCRIPTION
            ""
        ::= { ipeCfgSftpServerEntry 2 }
    
    -- 1.3.6.1.4.1.119.2.3.69.203.507.5.3.8.1.1.3
    ipeCfgSftpServerEnable OBJECT-TYPE
        SYNTAX      INTEGER { invalid(0), serviceDisable(1),
                        serviceEnable(2), alwaysEnable(3) }
        ACCESS      read-only
        STATUS      mandatory
        DESCRIPTION
            "SFTP control enable."
        ::= { ipeCfgSftpServerEntry 3 }
    
    -- 1.3.6.1.4.1.119.2.3.69.203.507.5.3.8.1.1.4
    ipeCfgSftpServerAutoDisable OBJECT-TYPE
        SYNTAX      INTEGER { invalid(0), disabled(1), enabled(2) }
        ACCESS      read-only
        STATUS      mandatory
        DESCRIPTION
            "SFTP automatic stop control enable."
        ::= { ipeCfgSftpServerEntry 4 }
    
    -- 1.3.6.1.4.1.119.2.3.69.203.507.5.3.9
    ipeCfgHttp OBJECT IDENTIFIER
        ::= { ipeConfigurationGroup 9 }
    
    -- 1.3.6.1.4.1.119.2.3.69.203.507.5.3.9.1
    ipeCfgHttpServerTable OBJECT-TYPE
        SYNTAX      SEQUENCE OF IpeCfgHttpServerEntry
        ACCESS      not-accessible
        STATUS      mandatory
        DESCRIPTION
            "Table of HTTP configuration information."
        ::= { ipeCfgHttp 1 }
    
    -- 1.3.6.1.4.1.119.2.3.69.203.507.5.3.9.1.1
    ipeCfgHttpServerEntry OBJECT-TYPE
        SYNTAX      IpeCfgHttpServerEntry
        ACCESS      not-accessible
        STATUS      mandatory
        DESCRIPTION
            "Entry of HTTP configuration information."
        INDEX       { ipeCfgHttpServerNEAddress, ipeCfgHttpServerIndex }
        ::= { ipeCfgHttpServerTable 1 }
    
    IpeCfgHttpServerEntry ::= SEQUENCE {
        ipeCfgHttpServerIndex       INTEGER,
        ipeCfgHttpServerNEAddress   IpAddress,
        ipeCfgHttpServerEnable      INTEGER,
        ipeCfgHttpServerTcpPort     INTEGER
    }
    
    -- 1.3.6.1.4.1.119.2.3.69.203.507.5.3.9.1.1.1
    ipeCfgHttpServerIndex OBJECT-TYPE
        SYNTAX      INTEGER (1)
        ACCESS      not-accessible
        STATUS      mandatory
        DESCRIPTION
            "Index of table."
        ::= { ipeCfgHttpServerEntry 1 }
    
    -- 1.3.6.1.4.1.119.2.3.69.203.507.5.3.9.1.1.2
    ipeCfgHttpServerNEAddress OBJECT-TYPE
        SYNTAX      IpAddress
        ACCESS      not-accessible
        STATUS      mandatory
        DESCRIPTION
            ""
        ::= { ipeCfgHttpServerEntry 2 }
    
    -- 1.3.6.1.4.1.119.2.3.69.203.507.5.3.9.1.1.3
    ipeCfgHttpServerEnable OBJECT-TYPE
        SYNTAX      INTEGER { invalid(0), disabled(1), enabled(2) }
        ACCESS      read-only
        STATUS      mandatory
        DESCRIPTION
            "HTTP control enable."
        ::= { ipeCfgHttpServerEntry 3 }
    
    -- 1.3.6.1.4.1.119.2.3.69.203.507.5.3.9.1.1.4
    ipeCfgHttpServerTcpPort OBJECT-TYPE
        SYNTAX      INTEGER (1..65535)
        ACCESS      read-only
        STATUS      mandatory
        DESCRIPTION
            "Port number of HTTP."
        ::= { ipeCfgHttpServerEntry 4 }
    
    -- 1.3.6.1.4.1.119.2.3.69.203.507.5.3.10
    ipeCfgHttps OBJECT IDENTIFIER
        ::= { ipeConfigurationGroup 10 }
    
    -- 1.3.6.1.4.1.119.2.3.69.203.507.5.3.10.1
    ipeCfgHttpsServerTable OBJECT-TYPE
        SYNTAX      SEQUENCE OF IpeCfgHttpsServerEntry
        ACCESS      not-accessible
        STATUS      mandatory
        DESCRIPTION
            "Table of HTTPS configuration information."
        ::= { ipeCfgHttps 1 }
    
    -- 1.3.6.1.4.1.119.2.3.69.203.507.5.3.10.1.1
    ipeCfgHttpsServerEntry OBJECT-TYPE
        SYNTAX      IpeCfgHttpsServerEntry
        ACCESS      not-accessible
        STATUS      mandatory
        DESCRIPTION
            "Entry of HTTPS configuration information."
        INDEX       { ipeCfgHttpsServerNEAddress, ipeCfgHttpsServerIndex }
        ::= { ipeCfgHttpsServerTable 1 }
    
    IpeCfgHttpsServerEntry ::= SEQUENCE {
        ipeCfgHttpsServerIndex      INTEGER,
        ipeCfgHttpsServerNEAddress  IpAddress,
        ipeCfgHttpsServerEnable     INTEGER,
        ipeCfgHttpsServerTcpPort    INTEGER
    }
    
    -- 1.3.6.1.4.1.119.2.3.69.203.507.5.3.10.1.1.1
    ipeCfgHttpsServerIndex OBJECT-TYPE
        SYNTAX      INTEGER (1)
        ACCESS      not-accessible
        STATUS      mandatory
        DESCRIPTION
            "Index of table."
        ::= { ipeCfgHttpsServerEntry 1 }
    
    -- 1.3.6.1.4.1.119.2.3.69.203.507.5.3.10.1.1.2
    ipeCfgHttpsServerNEAddress OBJECT-TYPE
        SYNTAX      IpAddress
        ACCESS      not-accessible
        STATUS      mandatory
        DESCRIPTION
            ""
        ::= { ipeCfgHttpsServerEntry 2 }
    
    -- 1.3.6.1.4.1.119.2.3.69.203.507.5.3.10.1.1.3
    ipeCfgHttpsServerEnable OBJECT-TYPE
        SYNTAX      INTEGER { invalid(0), disabled(1), enabled(2) }
        ACCESS      read-only
        STATUS      mandatory
        DESCRIPTION
            "HTTPS control enable."
        ::= { ipeCfgHttpsServerEntry 3 }
    
    -- 1.3.6.1.4.1.119.2.3.69.203.507.5.3.10.1.1.4
    ipeCfgHttpsServerTcpPort OBJECT-TYPE
        SYNTAX      INTEGER (1..65535)
        ACCESS      read-only
        STATUS      mandatory
        DESCRIPTION
            "TCP port number of HTTPS."
        ::= { ipeCfgHttpsServerEntry 4 }
    
    -- 1.3.6.1.4.1.119.2.3.69.203.507.5.3.10.2
    ipeCfgHttpsRsaTable OBJECT-TYPE
        SYNTAX      SEQUENCE OF IpeCfgHttpsRsaEntry
        ACCESS      not-accessible
        STATUS      mandatory
        DESCRIPTION
            "Table of HTTPS RSA configuration information."
        ::= { ipeCfgHttps 2 }
    
    -- 1.3.6.1.4.1.119.2.3.69.203.507.5.3.10.2.1
    ipeCfgHttpsRsaEntry OBJECT-TYPE
        SYNTAX      IpeCfgHttpsRsaEntry
        ACCESS      not-accessible
        STATUS      mandatory
        DESCRIPTION
            "Entry of HTTPS RSA configuration information."
        INDEX       { ipeCfgHttpsRsaNEAddress, ipeCfgHttpsRsaIndex }
        ::= { ipeCfgHttpsRsaTable 1 }
    
    IpeCfgHttpsRsaEntry ::= SEQUENCE {
        ipeCfgHttpsRsaIndex             INTEGER,
        ipeCfgHttpsRsaNEAddress         IpAddress,
        ipeCfgHttpsRsaPassPhrase        DisplayString,
        ipeCfgHttpsRsaEncryptAlgorithm  INTEGER
    }
    
    -- 1.3.6.1.4.1.119.2.3.69.203.507.5.3.10.2.1.1
    ipeCfgHttpsRsaIndex OBJECT-TYPE
        SYNTAX      INTEGER (1)
        ACCESS      not-accessible
        STATUS      mandatory
        DESCRIPTION
            "Index of table."
        ::= { ipeCfgHttpsRsaEntry 1 }
    
    -- 1.3.6.1.4.1.119.2.3.69.203.507.5.3.10.2.1.2
    ipeCfgHttpsRsaNEAddress OBJECT-TYPE
        SYNTAX      IpAddress
        ACCESS      not-accessible
        STATUS      mandatory
        DESCRIPTION
            ""
        ::= { ipeCfgHttpsRsaEntry 2 }
    
    -- 1.3.6.1.4.1.119.2.3.69.203.507.5.3.10.2.1.3
    ipeCfgHttpsRsaPassPhrase OBJECT-TYPE
        SYNTAX      DisplayString (SIZE(8..128))
        ACCESS      read-only
        STATUS      mandatory
        DESCRIPTION
            "Pass-phrase for the RSA private key. The valid length of user
             input value must be 8 to 64 chars.  After the encryption, the
             contents will be changed, and the length might be longer than 64
             chars."
        ::= { ipeCfgHttpsRsaEntry 3 }
    
    -- 1.3.6.1.4.1.119.2.3.69.203.507.5.3.10.2.1.4
    ipeCfgHttpsRsaEncryptAlgorithm OBJECT-TYPE
        SYNTAX      INTEGER { invalid(0), aes128(1), aes192(2), aes256(3),
                        camellia128(4), camellia192(5), camellia256(6),
                        des3(7) }
        ACCESS      read-only
        STATUS      mandatory
        DESCRIPTION
            "Encryption algorithm for the RSA private key."
        ::= { ipeCfgHttpsRsaEntry 4 }
    
    -- 1.3.6.1.4.1.119.2.3.69.203.507.5.3.10.3
    ipeCfgHttpsCsrTable OBJECT-TYPE
        SYNTAX      SEQUENCE OF IpeCfgHttpsCsrEntry
        ACCESS      not-accessible
        STATUS      mandatory
        DESCRIPTION
            "Table of HTTPS CSR configuration information."
        ::= { ipeCfgHttps 3 }
    
    -- 1.3.6.1.4.1.119.2.3.69.203.507.5.3.10.3.1
    ipeCfgHttpsCsrEntry OBJECT-TYPE
        SYNTAX      IpeCfgHttpsCsrEntry
        ACCESS      not-accessible
        STATUS      mandatory
        DESCRIPTION
            "Entry of HTTPS CSR configuration information."
        INDEX       { ipeCfgHttpsCsrNEAddress, ipeCfgHttpsCsrIndex }
        ::= { ipeCfgHttpsCsrTable 1 }
    
    IpeCfgHttpsCsrEntry ::= SEQUENCE {
        ipeCfgHttpsCsrIndex                     INTEGER,
        ipeCfgHttpsCsrNEAddress                 IpAddress,
        ipeCfgHttpsCsrRsaPassPhrase             DisplayString,
        ipeCfgHttpsCsrMessageDigestAlgorithm    INTEGER,
        ipeCfgHttpsCsrCountry                   DisplayString,
        ipeCfgHttpsCsrState                     DisplayString,
        ipeCfgHttpsCsrLocality                  DisplayString,
        ipeCfgHttpsCsrOrganization              DisplayString,
        ipeCfgHttpsCsrOrganizationalUnit        DisplayString,
        ipeCfgHttpsCsrCommonName                DisplayString
    }
    
    -- 1.3.6.1.4.1.119.2.3.69.203.507.5.3.10.3.1.1
    ipeCfgHttpsCsrIndex OBJECT-TYPE
        SYNTAX      INTEGER (1)
        ACCESS      not-accessible
        STATUS      mandatory
        DESCRIPTION
            "Index of table."
        ::= { ipeCfgHttpsCsrEntry 1 }
    
    -- 1.3.6.1.4.1.119.2.3.69.203.507.5.3.10.3.1.2
    ipeCfgHttpsCsrNEAddress OBJECT-TYPE
        SYNTAX      IpAddress
        ACCESS      not-accessible
        STATUS      mandatory
        DESCRIPTION
            ""
        ::= { ipeCfgHttpsCsrEntry 2 }
    
    -- 1.3.6.1.4.1.119.2.3.69.203.507.5.3.10.3.1.3
    ipeCfgHttpsCsrRsaPassPhrase OBJECT-TYPE
        SYNTAX      DisplayString (SIZE(8..128))
        ACCESS      read-only
        STATUS      mandatory
        DESCRIPTION
            "Pass-phrase for the RSA private key. This is same as
             ipeCfgHttpsRsaPassPhrase."
        ::= { ipeCfgHttpsCsrEntry 3 }
    
    -- 1.3.6.1.4.1.119.2.3.69.203.507.5.3.10.3.1.4
    ipeCfgHttpsCsrMessageDigestAlgorithm OBJECT-TYPE
        SYNTAX      INTEGER { invalid(0), sha224(1), sha256(2), sha384(3),
                        sha512(4) }
        ACCESS      read-only
        STATUS      mandatory
        DESCRIPTION
            "Message Digest algorithm for the CSR."
        ::= { ipeCfgHttpsCsrEntry 4 }
    
    -- 1.3.6.1.4.1.119.2.3.69.203.507.5.3.10.3.1.5
    ipeCfgHttpsCsrCountry OBJECT-TYPE
        SYNTAX      DisplayString (SIZE(2))
        ACCESS      read-only
        STATUS      mandatory
        DESCRIPTION
            "HTTPS CSR country name. 2 letter code. eg, US."
        ::= { ipeCfgHttpsCsrEntry 5 }
    
    -- 1.3.6.1.4.1.119.2.3.69.203.507.5.3.10.3.1.6
    ipeCfgHttpsCsrState OBJECT-TYPE
        SYNTAX      DisplayString (SIZE(2..64))
        ACCESS      read-only
        STATUS      mandatory
        DESCRIPTION
            "HTTPS CSR state or province name. eg, California (full name)."
        ::= { ipeCfgHttpsCsrEntry 6 }
    
    -- 1.3.6.1.4.1.119.2.3.69.203.507.5.3.10.3.1.7
    ipeCfgHttpsCsrLocality OBJECT-TYPE
        SYNTAX      DisplayString (SIZE(2..64))
        ACCESS      read-only
        STATUS      mandatory
        DESCRIPTION
            "HTTPS CSR locality name. eg, Saint Louis (city)."
        ::= { ipeCfgHttpsCsrEntry 7 }
    
    -- 1.3.6.1.4.1.119.2.3.69.203.507.5.3.10.3.1.8
    ipeCfgHttpsCsrOrganization OBJECT-TYPE
        SYNTAX      DisplayString (SIZE(2..64))
        ACCESS      read-only
        STATUS      mandatory
        DESCRIPTION
            "HTTPS CSR organization. eg, NEC Corporation."
        ::= { ipeCfgHttpsCsrEntry 8 }
    
    -- 1.3.6.1.4.1.119.2.3.69.203.507.5.3.10.3.1.9
    ipeCfgHttpsCsrOrganizationalUnit OBJECT-TYPE
        SYNTAX      DisplayString (SIZE(2..64))
        ACCESS      read-only
        STATUS      mandatory
        DESCRIPTION
            "HTTPS CSR organizational unit. eg, SSL Department (section)."
        ::= { ipeCfgHttpsCsrEntry 9 }
    
    -- 1.3.6.1.4.1.119.2.3.69.203.507.5.3.10.3.1.10
    ipeCfgHttpsCsrCommonName OBJECT-TYPE
        SYNTAX      DisplayString (SIZE(2..64))
        ACCESS      read-only
        STATUS      mandatory
        DESCRIPTION
            "HTTPS CSR common name. eg, apache.netsure.net (your name or your
             server's hostname)."
        ::= { ipeCfgHttpsCsrEntry 10 }
    
    -- 1.3.6.1.4.1.119.2.3.69.203.507.5.3.11
    ipeCfgSnmp OBJECT IDENTIFIER
        ::= { ipeConfigurationGroup 11 }
    
    -- 1.3.6.1.4.1.119.2.3.69.203.507.5.3.11.1
    ipeCfgSnmpServerTable OBJECT-TYPE
        SYNTAX      SEQUENCE OF IpeCfgSnmpServerEntry
        ACCESS      not-accessible
        STATUS      mandatory
        DESCRIPTION
            "A table of SNMP configuration information."
        ::= { ipeCfgSnmp 1 }
    
    -- 1.3.6.1.4.1.119.2.3.69.203.507.5.3.11.1.1
    ipeCfgSnmpServerEntry OBJECT-TYPE
        SYNTAX      IpeCfgSnmpServerEntry
        ACCESS      not-accessible
        STATUS      mandatory
        DESCRIPTION
            "A set of SNMP configuration information."
        INDEX       { ipeCfgSnmpServerNEAddress, ipeCfgSnmpServerIndex }
        ::= { ipeCfgSnmpServerTable 1 }
    
    IpeCfgSnmpServerEntry ::= SEQUENCE {
        ipeCfgSnmpServerIndex       INTEGER,
        ipeCfgSnmpServerNEAddress   IpAddress,
        ipeCfgSnmpV1V2cEnable       INTEGER,
        ipeCfgSnmpV3Enable          INTEGER,
        ipeCfgSnmpServerPort        INTEGER
    }
    
    -- 1.3.6.1.4.1.119.2.3.69.203.507.5.3.11.1.1.1
    ipeCfgSnmpServerIndex OBJECT-TYPE
        SYNTAX      INTEGER (1)
        ACCESS      not-accessible
        STATUS      mandatory
        DESCRIPTION
            "Index of this ipeCfgSnmpServerEntry.
             It's a fiexed value(= 1)."
        ::= { ipeCfgSnmpServerEntry 1 }
    
    -- 1.3.6.1.4.1.119.2.3.69.203.507.5.3.11.1.1.2
    ipeCfgSnmpServerNEAddress OBJECT-TYPE
        SYNTAX      IpAddress
        ACCESS      not-accessible
        STATUS      mandatory
        DESCRIPTION
            ""
        ::= { ipeCfgSnmpServerEntry 2 }
    
    -- 1.3.6.1.4.1.119.2.3.69.203.507.5.3.11.1.1.3
    ipeCfgSnmpV1V2cEnable OBJECT-TYPE
        SYNTAX      INTEGER { invalid(0), disabled(1), enabled(2) }
        ACCESS      read-only
        STATUS      mandatory
        DESCRIPTION
            "Indicates the SNMP entity is permitted to receive & process
             SNMPv1/v2c PDU or is not permitted to do.
    
             Even if it is disabled, SNMPv1/v2c Traps is sent."
        ::= { ipeCfgSnmpServerEntry 3 }
    
    -- 1.3.6.1.4.1.119.2.3.69.203.507.5.3.11.1.1.4
    ipeCfgSnmpV3Enable OBJECT-TYPE
        SYNTAX      INTEGER { invalid(0), disabled(1), enabled(2) }
        ACCESS      read-only
        STATUS      mandatory
        DESCRIPTION
            "Indicates the SNMP entity is permitted to receive & process
             SNMPv3 PDU or is not permitted to do.
    
             Even if it is disabled, SNMPv3 Traps is sent."
        ::= { ipeCfgSnmpServerEntry 4 }
    
    -- 1.3.6.1.4.1.119.2.3.69.203.507.5.3.11.1.1.5
    ipeCfgSnmpServerPort OBJECT-TYPE
        SYNTAX      INTEGER (1..65535)
        ACCESS      read-only
        STATUS      mandatory
        DESCRIPTION
            "A UDP port number to receive all SNMP Request-PDU.
             The reboot of the system is necessary to reflect setting."
        ::= { ipeCfgSnmpServerEntry 5 }
    
    -- 1.3.6.1.4.1.119.2.3.69.203.507.5.3.11.2
    ipeCfgSnmpCommunityTable OBJECT-TYPE
        SYNTAX      SEQUENCE OF IpeCfgSnmpCommunityEntry
        ACCESS      not-accessible
        STATUS      mandatory
        DESCRIPTION
            "A table of SNMP community information."
        ::= { ipeCfgSnmp 2 }
    
    -- 1.3.6.1.4.1.119.2.3.69.203.507.5.3.11.2.1
    ipeCfgSnmpCommunityEntry OBJECT-TYPE
        SYNTAX      IpeCfgSnmpCommunityEntry
        ACCESS      not-accessible
        STATUS      mandatory
        DESCRIPTION
            "A set of SNMP community information."
        INDEX       { ipeCfgSnmpCommunityNEAddress, ipeCfgSnmpCommunityIndex }
        ::= { ipeCfgSnmpCommunityTable 1 }
    
    IpeCfgSnmpCommunityEntry ::= SEQUENCE {
        ipeCfgSnmpCommunityIndex                    INTEGER,
        ipeCfgSnmpCommunityNEAddress                IpAddress,
        ipeCfgSnmpCommunityName                     DisplayString,
        ipeCfgSnmpCommunityAccessLevel              INTEGER,
        ipeCfgSnmpCommunityAccessAddress            IpAddress,
        ipeCfgSnmpCommunityAccessPrefixLength       INTEGER,
        ipeCfgSnmpCommunityRowStatus                RowStatus,
        ipeCfgSnmpCommunityAccessAddress2           IpAddress,
        ipeCfgSnmpCommunityAccessPrefixLength2      INTEGER,
        ipeCfgSnmpCommunityAccessAddress3           IpAddress,
        ipeCfgSnmpCommunityAccessPrefixLength3      INTEGER,
        ipeCfgSnmpCommunityAccessUsage              UsedNotusedValue,
        ipeCfgSnmpCommunityAccessUsage2             UsedNotusedValue,
        ipeCfgSnmpCommunityAccessUsage3             UsedNotusedValue,
        ipeCfgSnmpCommunityAccessV6Address          Ipv6Address,
        ipeCfgSnmpCommunityAccessV6PrefixLength     INTEGER,
        ipeCfgSnmpCommunityAccessV6Address2         Ipv6Address,
        ipeCfgSnmpCommunityAccessV6PrefixLength2    INTEGER,
        ipeCfgSnmpCommunityAccessV6Address3         Ipv6Address,
        ipeCfgSnmpCommunityAccessV6PrefixLength3    INTEGER,
        ipeCfgSnmpCommunityAccessAddressType        INTEGER,
        ipeCfgSnmpCommunityAccessV6Usage            UsedNotusedValue,
        ipeCfgSnmpCommunityAccessV6Usage2           UsedNotusedValue,
        ipeCfgSnmpCommunityAccessV6Usage3           UsedNotusedValue
    }
    
    -- 1.3.6.1.4.1.119.2.3.69.203.507.5.3.11.2.1.1
    ipeCfgSnmpCommunityIndex OBJECT-TYPE
        SYNTAX      INTEGER (1..10)
        ACCESS      not-accessible
        STATUS      mandatory
        DESCRIPTION
            "Index of this ipeCfgSnmpCommunityEntry.
             You have to choose a value  from 1 to 10."
        ::= { ipeCfgSnmpCommunityEntry 1 }
    
    -- 1.3.6.1.4.1.119.2.3.69.203.507.5.3.11.2.1.2
    ipeCfgSnmpCommunityNEAddress OBJECT-TYPE
        SYNTAX      IpAddress
        ACCESS      not-accessible
        STATUS      mandatory
        DESCRIPTION
            ""
        ::= { ipeCfgSnmpCommunityEntry 2 }
    
    -- 1.3.6.1.4.1.119.2.3.69.203.507.5.3.11.2.1.3
    ipeCfgSnmpCommunityName OBJECT-TYPE
        SYNTAX      DisplayString (SIZE(1..31))
        ACCESS      read-only
        STATUS      mandatory
        DESCRIPTION
            "This entity's community name.
    
             Please use ASCII code.
    
             The characters which can be used are '-', '_','0'-'9', 'a'-'z'
             and 'A'-'Z'."
        ::= { ipeCfgSnmpCommunityEntry 3 }
    
    -- 1.3.6.1.4.1.119.2.3.69.203.507.5.3.11.2.1.4
    ipeCfgSnmpCommunityAccessLevel OBJECT-TYPE
        SYNTAX      INTEGER { invalid(0), operatorLevel(1), configLevel(2),
                        adminLevel(3) }
        ACCESS      read-only
        STATUS      mandatory
        DESCRIPTION
            "A access level of a connection using this entry's community
             name."
        ::= { ipeCfgSnmpCommunityEntry 4 }
    
    -- 1.3.6.1.4.1.119.2.3.69.203.507.5.3.11.2.1.5
    ipeCfgSnmpCommunityAccessAddress OBJECT-TYPE
        SYNTAX      IpAddress
        ACCESS      read-only
        STATUS      mandatory
        DESCRIPTION
            "An address which is permitted to use this entry's community
             name.
             When masking in ipeCfgSnmpCommunityAccessPrefixLength, the host
             address part has to be a zero, if any.
    
             Also the following address can't be used.
             127.0.0.0/8 Loopback
             224.0.0.0/4 Multicasts (former Class D)
             240.0.0.0/4 Reserved (former Class E)"
        ::= { ipeCfgSnmpCommunityEntry 5 }
    
    -- 1.3.6.1.4.1.119.2.3.69.203.507.5.3.11.2.1.6
    ipeCfgSnmpCommunityAccessPrefixLength OBJECT-TYPE
        SYNTAX      INTEGER (0..32)
        ACCESS      read-only
        STATUS      mandatory
        DESCRIPTION
            "A prefix length of ipeCfgSnmpCommunityAccessAddress."
        ::= { ipeCfgSnmpCommunityEntry 6 }
    
    -- 1.3.6.1.4.1.119.2.3.69.203.507.5.3.11.2.1.7
    ipeCfgSnmpCommunityRowStatus OBJECT-TYPE
        SYNTAX      RowStatus { active(1), createAndGo(4), destroy(6) }
        ACCESS      read-only
        STATUS      mandatory
        DESCRIPTION
            "This RowStatus has a status only  active(1).
             You can SET only createAndGo(4) or Destroy(6).
    
             1) how to create
             To create a new row, you must SET objects indicated below.
    
             ipeCfgSnmpCommunityName
             ipeCfgSnmpCommunityAccessLevel
             ipeCfgSnmpCommunityAccessAddress
             ipeCfgSnmpCommunityAccessPrefixLength
             ipeCfgSnmpCommunityAccessAddress2 *
             ipeCfgSnmpCommunityAccessPrefixLength2 *
             ipeCfgSnmpCommunityAccessAddress3 *
             ipeCfgSnmpCommunityAccessPrefixLength3 *
             ipeCfgSnmpCommunityAccessUsage *
             ipeCfgSnmpCommunityAccessUsage2 *
             ipeCfgSnmpCommunityAccessUsage3 *
             ipeCfgSnmpCommunityAccessV6Address
             ipeCfgSnmpCommunityAccessV6PrefixLength
             ipeCfgSnmpCommunityAccessV6Address2 *
             ipeCfgSnmpCommunityAccessV6PrefixLength2 *
             ipeCfgSnmpCommunityAccessV6Address3 *
             ipeCfgSnmpCommunityAccessV6PrefixLength3 *
             ipeCfgSnmpCommunityAccessAddressType *
             ipeCfgSnmpCommunityAccessV6Usage *
             ipeCfgSnmpCommunityAccessV6Usage2 *
             ipeCfgSnmpCommunityAccessV6Usage3 *
             ipeCfgSnmpCommunityRowStatus <- createAndGo(4)
    
             * NOT for EX CPRI
    
             Either ipeCfgSnmpCommunityAccessAddress/Address2/Address3 or
             ipeCfgSnmpCommunityAccessV6Address/Address2/Address3 can be
             configured depending on ipeCfgSnmpCommunityAccessAddressType.
    
             ipeCfgSnmpCommunityIndex is an index of this entry.
    
             2) how to destroy
             To destroy a exist row, you must SET a destory(6) to
             ipeCfgSnmpCommunityRowStatus.
    
             3) how to modify
             It is not possible.
             Please destroy a exist row, and create a new row.
             < Attention >
             You have to restart equipment to apply this entry(creating,
             deleting) to actual movement."
        ::= { ipeCfgSnmpCommunityEntry 7 }
    
    -- 1.3.6.1.4.1.119.2.3.69.203.507.5.3.11.2.1.8
    ipeCfgSnmpCommunityAccessAddress2 OBJECT-TYPE
        SYNTAX      IpAddress
        ACCESS      read-only
        STATUS      mandatory
        DESCRIPTION
            "An address which is permitted to use this entry's community
             name.
             When masking in ipeCfgSnmpCommunityAccessPrefixLength, the host
             address part has to be a zero, if any.
    
             Also the following address can't be used.
             127.0.0.0/8 Loopback
             224.0.0.0/4 Multicasts (former Class D)
             240.0.0.0/4 Reserved (former Class E)"
        ::= { ipeCfgSnmpCommunityEntry 8 }
    
    -- 1.3.6.1.4.1.119.2.3.69.203.507.5.3.11.2.1.9
    ipeCfgSnmpCommunityAccessPrefixLength2 OBJECT-TYPE
        SYNTAX      INTEGER (0..32)
        ACCESS      read-only
        STATUS      mandatory
        DESCRIPTION
            "A prefix length of ipeCfgSnmpCommunityAccessAddress."
        ::= { ipeCfgSnmpCommunityEntry 9 }
    
    -- 1.3.6.1.4.1.119.2.3.69.203.507.5.3.11.2.1.10
    ipeCfgSnmpCommunityAccessAddress3 OBJECT-TYPE
        SYNTAX      IpAddress
        ACCESS      read-only
        STATUS      mandatory
        DESCRIPTION
            "An address which is permitted to use this entry's community
             name.
             When masking in ipeCfgSnmpCommunityAccessPrefixLength, the host
             address part has to be a zero, if any.
    
             Also the following address can't be used.
             127.0.0.0/8 Loopback
             224.0.0.0/4 Multicasts (former Class D)
             240.0.0.0/4 Reserved (former Class E)"
        ::= { ipeCfgSnmpCommunityEntry 10 }
    
    -- 1.3.6.1.4.1.119.2.3.69.203.507.5.3.11.2.1.11
    ipeCfgSnmpCommunityAccessPrefixLength3 OBJECT-TYPE
        SYNTAX      INTEGER (0..32)
        ACCESS      read-only
        STATUS      mandatory
        DESCRIPTION
            "A prefix length of ipeCfgSnmpCommunityAccessAddress."
        ::= { ipeCfgSnmpCommunityEntry 11 }
    
    -- 1.3.6.1.4.1.119.2.3.69.203.507.5.3.11.2.1.12
    ipeCfgSnmpCommunityAccessUsage OBJECT-TYPE
        SYNTAX      UsedNotusedValue
        ACCESS      read-only
        STATUS      mandatory
        DESCRIPTION
            "Access Control Usage."
        DEFVAL      { notUsed }
        ::= { ipeCfgSnmpCommunityEntry 12 }
    
    -- 1.3.6.1.4.1.119.2.3.69.203.507.5.3.11.2.1.13
    ipeCfgSnmpCommunityAccessUsage2 OBJECT-TYPE
        SYNTAX      UsedNotusedValue
        ACCESS      read-only
        STATUS      mandatory
        DESCRIPTION
            "Access Control Usage."
        DEFVAL      { notUsed }
        ::= { ipeCfgSnmpCommunityEntry 13 }
    
    -- 1.3.6.1.4.1.119.2.3.69.203.507.5.3.11.2.1.14
    ipeCfgSnmpCommunityAccessUsage3 OBJECT-TYPE
        SYNTAX      UsedNotusedValue
        ACCESS      read-only
        STATUS      mandatory
        DESCRIPTION
            "Access Control Usage."
        DEFVAL      { notUsed }
        ::= { ipeCfgSnmpCommunityEntry 14 }
    
    -- 1.3.6.1.4.1.119.2.3.69.203.507.5.3.11.2.1.15
    ipeCfgSnmpCommunityAccessV6Address OBJECT-TYPE
        SYNTAX      Ipv6Address
        ACCESS      read-only
        STATUS      mandatory
        DESCRIPTION
            "An IPv6 address which is permitted to use this entry's community
             name.
             The following are not valid addresses:
               ::1/128 IPv6 Loopback
               FF00::/8 IPv6 Multicasts
               FE80::/10 Link local"
        ::= { ipeCfgSnmpCommunityEntry 15 }
    
    -- 1.3.6.1.4.1.119.2.3.69.203.507.5.3.11.2.1.16
    ipeCfgSnmpCommunityAccessV6PrefixLength OBJECT-TYPE
        SYNTAX      INTEGER (0..128)
        ACCESS      read-only
        STATUS      mandatory
        DESCRIPTION
            "A prefix length of ipeCfgSnmpCommunityAccessV6Address."
        ::= { ipeCfgSnmpCommunityEntry 16 }
    
    -- 1.3.6.1.4.1.119.2.3.69.203.507.5.3.11.2.1.17
    ipeCfgSnmpCommunityAccessV6Address2 OBJECT-TYPE
        SYNTAX      Ipv6Address
        ACCESS      read-only
        STATUS      mandatory
        DESCRIPTION
            "An IPv6 address which is permitted to use this entry's community
             name.
             The following are not valid addresses
               ::1/128 IPv6 Loopback
               FF00::/8 IPv6 Multicasts
               FE80::/10 Link local"
        ::= { ipeCfgSnmpCommunityEntry 17 }
    
    -- 1.3.6.1.4.1.119.2.3.69.203.507.5.3.11.2.1.18
    ipeCfgSnmpCommunityAccessV6PrefixLength2 OBJECT-TYPE
        SYNTAX      INTEGER (0..128)
        ACCESS      read-only
        STATUS      mandatory
        DESCRIPTION
            "A prefix length of ipeCfgSnmpCommunityAccessV6Address."
        ::= { ipeCfgSnmpCommunityEntry 18 }
    
    -- 1.3.6.1.4.1.119.2.3.69.203.507.5.3.11.2.1.19
    ipeCfgSnmpCommunityAccessV6Address3 OBJECT-TYPE
        SYNTAX      Ipv6Address
        ACCESS      read-only
        STATUS      mandatory
        DESCRIPTION
            "An IPv6 address which is permitted to use this entry's community
             name.
             The following are not valid addresses
               ::1/128 IPv6 Loopback
               FF00::/8 IPv6 Multicasts
               FE80::/10 Link local"
        ::= { ipeCfgSnmpCommunityEntry 19 }
    
    -- 1.3.6.1.4.1.119.2.3.69.203.507.5.3.11.2.1.20
    ipeCfgSnmpCommunityAccessV6PrefixLength3 OBJECT-TYPE
        SYNTAX      INTEGER (0..128)
        ACCESS      read-only
        STATUS      mandatory
        DESCRIPTION
            "A prefix length of ipeCfgSnmpCommunityAccessV6Address."
        ::= { ipeCfgSnmpCommunityEntry 20 }
    
    -- 1.3.6.1.4.1.119.2.3.69.203.507.5.3.11.2.1.21
    ipeCfgSnmpCommunityAccessAddressType OBJECT-TYPE
        SYNTAX      INTEGER { invalid(0), ipv4(1), ipv6(2) }
        ACCESS      read-only
        STATUS      mandatory
        DESCRIPTION
            "An address type to be used for the community access."
        ::= { ipeCfgSnmpCommunityEntry 21 }
    
    -- 1.3.6.1.4.1.119.2.3.69.203.507.5.3.11.2.1.22
    ipeCfgSnmpCommunityAccessV6Usage OBJECT-TYPE
        SYNTAX      UsedNotusedValue
        ACCESS      read-only
        STATUS      mandatory
        DESCRIPTION
            "Access Control IPv6 Usage."
        ::= { ipeCfgSnmpCommunityEntry 22 }
    
    -- 1.3.6.1.4.1.119.2.3.69.203.507.5.3.11.2.1.23
    ipeCfgSnmpCommunityAccessV6Usage2 OBJECT-TYPE
        SYNTAX      UsedNotusedValue
        ACCESS      read-only
        STATUS      mandatory
        DESCRIPTION
            "Access Control IPv6 Usage."
        ::= { ipeCfgSnmpCommunityEntry 23 }
    
    -- 1.3.6.1.4.1.119.2.3.69.203.507.5.3.11.2.1.24
    ipeCfgSnmpCommunityAccessV6Usage3 OBJECT-TYPE
        SYNTAX      UsedNotusedValue
        ACCESS      read-only
        STATUS      mandatory
        DESCRIPTION
            "Access Control IPv6 Usage."
        ::= { ipeCfgSnmpCommunityEntry 24 }
    
    -- 1.3.6.1.4.1.119.2.3.69.203.507.5.3.11.3
    ipeCfgSnmpTrapTable OBJECT-TYPE
        SYNTAX      SEQUENCE OF IpeCfgSnmpTrapEntry
        ACCESS      not-accessible
        STATUS      mandatory
        DESCRIPTION
            "A table of notification information."
        ::= { ipeCfgSnmp 3 }
    
    -- 1.3.6.1.4.1.119.2.3.69.203.507.5.3.11.3.1
    ipeCfgSnmpTrapEntry OBJECT-TYPE
        SYNTAX      IpeCfgSnmpTrapEntry
        ACCESS      not-accessible
        STATUS      mandatory
        DESCRIPTION
            "A set of notification information."
        INDEX       { ipeCfgSnmpTrapEntryNEAddress, ipeCfgSnmpTrapEntryIndex }
        ::= { ipeCfgSnmpTrapTable 1 }
    
    IpeCfgSnmpTrapEntry ::= SEQUENCE {
        ipeCfgSnmpTrapEntryIndex            INTEGER,
        ipeCfgSnmpTrapEntryNEAddress        IpAddress,
        ipeCfgSnmpTrapVersion               INTEGER,
        ipeCfgSnmpTrapNotifyType            INTEGER,
        ipeCfgSnmpTrapTargetAddress         IpAddress,
        ipeCfgSnmpTrapTargetPort            INTEGER,
        ipeCfgSnmpTrapSecurityName          DisplayString,
        ipeCfgSnmpTrapSecurityLevel         INTEGER,
        ipeCfgSnmpTrapEngineId              OCTET STRING,
        ipeCfgSnmpTrapAuthAlgorithm         INTEGER,
        ipeCfgSnmpTrapAuthKey               DisplayString,
        ipeCfgSnmpTrapPrivAlgorithm         INTEGER,
        ipeCfgSnmpTrapPrivKey               DisplayString,
        ipeCfgSnmpTrapRowStatus             RowStatus,
        ipeCfgSnmpTrapTargetV6Address       Ipv6Address,
        ipeCfgSnmpTrapTargetIfIndex         INTEGER,
        ipeCfgSnmpTrapTargetAddressType     INTEGER
    }
    
    -- 1.3.6.1.4.1.119.2.3.69.203.507.5.3.11.3.1.1
    ipeCfgSnmpTrapEntryIndex OBJECT-TYPE
        SYNTAX      INTEGER (1..6)
        ACCESS      not-accessible
        STATUS      mandatory
        DESCRIPTION
            "Index of this ipeCfgSnmpTrapEntry.
             You have to choose a value from 1 to 6.
    
             The entry by which an index is 4,5 and 6 is volatile. Those entry
             is eliminated at the equipment reboot."
        ::= { ipeCfgSnmpTrapEntry 1 }
    
    -- 1.3.6.1.4.1.119.2.3.69.203.507.5.3.11.3.1.2
    ipeCfgSnmpTrapEntryNEAddress OBJECT-TYPE
        SYNTAX      IpAddress
        ACCESS      not-accessible
        STATUS      mandatory
        DESCRIPTION
            ""
        ::= { ipeCfgSnmpTrapEntry 2 }
    
    -- 1.3.6.1.4.1.119.2.3.69.203.507.5.3.11.3.1.3
    ipeCfgSnmpTrapVersion OBJECT-TYPE
        SYNTAX      INTEGER { invalid(0), v1(1), v2c(2), v3(3) }
        ACCESS      read-only
        STATUS      mandatory
        DESCRIPTION
            "A version of this entry's notification."
        ::= { ipeCfgSnmpTrapEntry 3 }
    
    -- 1.3.6.1.4.1.119.2.3.69.203.507.5.3.11.3.1.4
    ipeCfgSnmpTrapNotifyType OBJECT-TYPE
        SYNTAX      INTEGER { invalid(0), trap(1), inform(2) }
        ACCESS      read-only
        STATUS      mandatory
        DESCRIPTION
            "A notification type of this entry's notification."
        ::= { ipeCfgSnmpTrapEntry 4 }
    
    -- 1.3.6.1.4.1.119.2.3.69.203.507.5.3.11.3.1.5
    ipeCfgSnmpTrapTargetAddress OBJECT-TYPE
        SYNTAX      IpAddress
        ACCESS      read-only
        STATUS      mandatory
        DESCRIPTION
            "Destination IP address of this entry's notification.
    
             The following address can't be used.
             127.0.0.0/8 Loopback
             0.0.0.0/0    Current network
             224.0.0.0/4 Multicasts (former Class D)
             240.0.0.0/4 Reserved (former Class E)"
        ::= { ipeCfgSnmpTrapEntry 5 }
    
    -- 1.3.6.1.4.1.119.2.3.69.203.507.5.3.11.3.1.6
    ipeCfgSnmpTrapTargetPort OBJECT-TYPE
        SYNTAX      INTEGER (1..65535)
        ACCESS      read-only
        STATUS      mandatory
        DESCRIPTION
            "Destination UDP port this entry's notification."
        ::= { ipeCfgSnmpTrapEntry 6 }
    
    -- 1.3.6.1.4.1.119.2.3.69.203.507.5.3.11.3.1.7
    ipeCfgSnmpTrapSecurityName OBJECT-TYPE
        SYNTAX      DisplayString (SIZE(1..31))
        ACCESS      read-only
        STATUS      mandatory
        DESCRIPTION
            "A security name.
             The meaning is different depending on ipeCfgSnmpTrapVersion.
    
             v1/v2c  : It's meaning a community name.
             v3      : It's meaning a user name.
    
             Please use ASCII code.
    
             The characters which can be used are '-', '_','0'-'9', 'a'-'z'
             and 'A'-'Z'.
    
             When there was the same combination to the other index,
             ipeCfgSnmpTrapSecurityName and ipeCfgSnmpTrapEngineId become
             error."
        ::= { ipeCfgSnmpTrapEntry 7 }
    
    -- 1.3.6.1.4.1.119.2.3.69.203.507.5.3.11.3.1.8
    ipeCfgSnmpTrapSecurityLevel OBJECT-TYPE
        SYNTAX      INTEGER { invalid(0), noAuthNoPriv(1), authNoPriv(2),
                        authPriv(3) }
        ACCESS      read-only
        STATUS      mandatory
        DESCRIPTION
            "A security level of this entry's notification.
    
             When ipeCfgSnmpTrapVersion is v1(1) or v2c(2), you have to SET
             noAuthNoPriv(1)."
        ::= { ipeCfgSnmpTrapEntry 8 }
    
    -- 1.3.6.1.4.1.119.2.3.69.203.507.5.3.11.3.1.9
    ipeCfgSnmpTrapEngineId OBJECT-TYPE
        SYNTAX      OCTET STRING (SIZE(5..32))
        ACCESS      read-only
        STATUS      mandatory
        DESCRIPTION
            "A snmpEngineID which this entry's notification uses.(5-32 octet)
             ipeCfgSnmpTrapNotifyType is effective only at the time of
             inform(2).
             A snmpEngineID of a destination SNMP entity.
    
             When there was the same combination to the other index,
             ipeCfgSnmpTrapSecurityName and ipeCfgSnmpTrapEngineId become
             error."
        ::= { ipeCfgSnmpTrapEntry 9 }
    
    -- 1.3.6.1.4.1.119.2.3.69.203.507.5.3.11.3.1.10
    ipeCfgSnmpTrapAuthAlgorithm OBJECT-TYPE
        SYNTAX      INTEGER { invalid(0), md5(1), sha(2) }
        ACCESS      read-only
        STATUS      mandatory
        DESCRIPTION
            "Authentication protocol.
    
             ipeCfgSnmpTrapNotifyType is effective for the SET only at the
             time of inform(2). Even if it is done SET in the case of trap(1),
             I am ignored. In addition, a value of
             ipeCfgAccountUserSnmpV3AuthAlgorithm is acquired at time to get."
        ::= { ipeCfgSnmpTrapEntry 10 }
    
    -- 1.3.6.1.4.1.119.2.3.69.203.507.5.3.11.3.1.11
    ipeCfgSnmpTrapAuthKey OBJECT-TYPE
        SYNTAX      DisplayString (SIZE(8..128))
        ACCESS      read-only
        STATUS      mandatory
        DESCRIPTION
            "Authenticate password for SNMP inform PDU.
             This object expects encrypted password by blowfish, not original
             password. Therefore, the size of this object is not same as
             original password size (8..31).
    
             When the object 'ipeCfgSnmpTrapNotifyType' is trap(1), SET
             request is not processed (discarded), and GET request returns the
             same value as 'ipeCfgAccountUserSnmpV3AuthKey'."
        ::= { ipeCfgSnmpTrapEntry 11 }
    
    -- 1.3.6.1.4.1.119.2.3.69.203.507.5.3.11.3.1.12
    ipeCfgSnmpTrapPrivAlgorithm OBJECT-TYPE
        SYNTAX      INTEGER { invalid(0), des(1), aes(2) }
        ACCESS      read-only
        STATUS      mandatory
        DESCRIPTION
            "privacy protocol.
    
             ipeCfgSnmpTrapNotifyType is effective for the SET only at the
             time of inform(2). Even if it is done SET in the case of trap(1),
             I am ignored. In addition, a value of
             ipeCfgAccountUserSnmpV3PrivAlgorithm is acquired at time to get."
        ::= { ipeCfgSnmpTrapEntry 12 }
    
    -- 1.3.6.1.4.1.119.2.3.69.203.507.5.3.11.3.1.13
    ipeCfgSnmpTrapPrivKey OBJECT-TYPE
        SYNTAX      DisplayString (SIZE(8..128))
        ACCESS      read-only
        STATUS      mandatory
        DESCRIPTION
            "Privacy password for SNMP inform PDU.
             This object expects encrypted password by blowfish, not original
             password. Therefore, the size of this object is not same as
             orignal password size (8..31).
    
             When the object 'ipeCfgSnmpTrapNotifyType' is trap(1), SET
             request is not processed (discarded), and GET request returns the
             same value as 'ipeCfgAccountUserSnmpV3PrivKey'."
        ::= { ipeCfgSnmpTrapEntry 13 }
    
    -- 1.3.6.1.4.1.119.2.3.69.203.507.5.3.11.3.1.14
    ipeCfgSnmpTrapRowStatus OBJECT-TYPE
        SYNTAX      RowStatus { active(1), createAndGo(4), destroy(6) }
        ACCESS      read-only
        STATUS      mandatory
        DESCRIPTION
            "This RowStatus has a status only  active(1).
             You can SET only createAndGo(4) or destroy(6).
    
             1) how to create
             1.1) SNMPv1/v2c
             To create a new row, you must SET objects indicated below.
    
             ipeCfgSnmpTrapEntryIndex, ipeCfgSnmpTrapVersion,
             ipeCfgSnmpTrapNotifyType, ipeCfgSnmpTrapTargetAddress,
             ipeCfgSnmpTrapTargetV6Address,
             ipeCfgSnmpTrapTargetAddressType(*), ipeCfgSnmpTrapTaergetPort,
             ipeCfgSnmpTrapSecurityName
             ipeCfgSnmpTrapRowStatus     # Only createAndGo(4).
    
             It isn't necessary to set ipeCfgSnmpTrapSecurityLevel. When set
             it, the value is checked, so all except for noAuthNoPriv (1) will
             be NG.
             And, the other object is not necessary. Even if it is done SET,
             it is checked the value, but ignored.
    
             1.2) SNMPv3 (ipeCfgSnmpTrapNotifyType = trap(1))
             ipeCfgSnmpTrapVersion, ipeCfgSnmpTrapNotifyType,
             ipeCfgSnmpTrapTargetAddress, ipeCfgSnmpTrapTargetV6Address,
             ipeCfgSnmpTrapTargetAddressType(*), ipeCfgSnmpTrapTaergetPort,
             ipeCfgSnmpTrapSecurityName
             ipeCfgSnmpTrapRowStatus     # Only createAndGo(4).
    
             Other object is not necessary. Even if it is done SET, it is
             checked the value, but ignored.
    
             1.3) SNMPv3 (ipeCfgSnmpTrapNotifyType = inform(2))
             To create a new row, you must SET objects indicated below.
    
             ipeCfgSnmpTrapVersion, ipeCfgSnmpTrapNotifyType,
             ipeCfgSnmpTrapTargetAddress, ipeCfgSnmpTrapTargetV6Address,
             ipeCfgSnmpTrapTargetAddressType(*), ipeCfgSnmpTrapTaergetPort,
             ipeCfgSnmpTrapSecurityName, ipeCfgSnmpTrapSecurityLevel,
             ipeCfgSnmpTrapEngineId, ipeCfgSnmpTrapAuthAlgorithm,
             ipeCfgSnmpTrapAuthKey, ipeCfgSnmpTrapPrivAlgorithm,
             ipeCfgSnmpTrapPrivKey
             ipeCfgSnmpTrapRowStatus    # Only createAndGo(4).
    
             * NOT for EX CPRI
    
             ipeCfgSnmpTrapEntryIndex is an index of this entry.
    
             2) how to destroy
             To destroy a exist row, you must SET a destory(6) to
             ipeCfgSnmpCommunityRowStatus.
    
             3) how to modify
             It is not possible.
             Please destroy a exist row, and create a new row."
        ::= { ipeCfgSnmpTrapEntry 14 }
    
    -- 1.3.6.1.4.1.119.2.3.69.203.507.5.3.11.3.1.15
    ipeCfgSnmpTrapTargetV6Address OBJECT-TYPE
        SYNTAX      Ipv6Address
        ACCESS      read-only
        STATUS      mandatory
        DESCRIPTION
            "Destination IPv6 address of this entry's notification.
             The following are not valid addresses:
                 ::1/128 IPv6 Loopback
                 ::/128 Unspecified
                 FF00::/8 IPv6 Multicasts"
        ::= { ipeCfgSnmpTrapEntry 15 }
    
    -- 1.3.6.1.4.1.119.2.3.69.203.507.5.3.11.3.1.16
    ipeCfgSnmpTrapTargetIfIndex OBJECT-TYPE
        SYNTAX      INTEGER { invalid(0), bridge1(11), bridge2(12),
                        bridge3(13), bridge4(14), bridge5(15), bridge6(16),
                        bridge7(17), bridge8(18), bridge9(19), bridge10(20),
                        bridge11(21), bridge12(22), bridge13(23),
                        bridge14(24), bridge15(25), bridge16(26),
                        bridge17(27), bridge18(28), bridge19(29),
                        bridge20(30) }
        ACCESS      read-only
        STATUS      mandatory
        DESCRIPTION
            "The interface index through which the Server is reachable.
             When ipeCfgSnmpTrapTargetV6Address is configured with
             Link-local address, this object must be configured
             to proper Interface index. For any other address type,
             value of this object shall be 0."
        ::= { ipeCfgSnmpTrapEntry 16 }
    
    -- 1.3.6.1.4.1.119.2.3.69.203.507.5.3.11.3.1.17
    ipeCfgSnmpTrapTargetAddressType OBJECT-TYPE
        SYNTAX      INTEGER { invalid(0), ipv4(1), ipv6(2) }
        ACCESS      read-only
        STATUS      mandatory
        DESCRIPTION
            "Indicate IP address type of this trap target.
    
             ipv4 : trap target address has IPv4 address.
             ipv6 : trap target address has IPv6 address.
             When this object is not specified at the object creation with the
             index 4 through 6, 'ipv4' is as the default."
        ::= { ipeCfgSnmpTrapEntry 17 }
    
    -- 1.3.6.1.4.1.119.2.3.69.203.507.5.3.12
    ipeCfgAccount OBJECT IDENTIFIER
        ::= { ipeConfigurationGroup 12 }
    
    -- 1.3.6.1.4.1.119.2.3.69.203.507.5.3.12.1
    ipeCfgAccountUserInfoTable OBJECT-TYPE
        SYNTAX      SEQUENCE OF IpeCfgAccountUserInfoEntry
        ACCESS      not-accessible
        STATUS      mandatory
        DESCRIPTION
            "Table of user Information."
        ::= { ipeCfgAccount 1 }
    
    -- 1.3.6.1.4.1.119.2.3.69.203.507.5.3.12.1.1
    ipeCfgAccountUserInfoEntry OBJECT-TYPE
        SYNTAX      IpeCfgAccountUserInfoEntry
        ACCESS      not-accessible
        STATUS      mandatory
        DESCRIPTION
            "Entry of user information."
        INDEX       { ipeCfgAccountUserNEAddress, ipeCfgAccountUserIndex }
        ::= { ipeCfgAccountUserInfoTable 1 }
    
    IpeCfgAccountUserInfoEntry ::= SEQUENCE {
        ipeCfgAccountUserIndex                  INTEGER,
        ipeCfgAccountUserNEAddress              IpAddress,
        ipeCfgAccountUserName                   DisplayString,
        ipeCfgAccountUserKey                    DisplayString,
        ipeCfgAccountUserGroup                  DisplayString,
        ipeCfgAccountUserSnmpV3SecurityLevel    INTEGER,
        ipeCfgAccountUserSnmpV3AuthAlgorithm    INTEGER,
        ipeCfgAccountUserSnmpV3AuthKey          DisplayString,
        ipeCfgAccountUserSnmpV3PrivAlgorithm    INTEGER,
        ipeCfgAccountUserSnmpV3PrivKey          DisplayString,
        ipeCfgAccountUserRowStatus              RowStatus
    }
    
    -- 1.3.6.1.4.1.119.2.3.69.203.507.5.3.12.1.1.1
    ipeCfgAccountUserIndex OBJECT-TYPE
        SYNTAX      INTEGER (1..102)
        ACCESS      not-accessible
        STATUS      mandatory
        DESCRIPTION
            "Index of table."
        ::= { ipeCfgAccountUserInfoEntry 1 }
    
    -- 1.3.6.1.4.1.119.2.3.69.203.507.5.3.12.1.1.2
    ipeCfgAccountUserNEAddress OBJECT-TYPE
        SYNTAX      IpAddress
        ACCESS      not-accessible
        STATUS      mandatory
        DESCRIPTION
            ""
        ::= { ipeCfgAccountUserInfoEntry 2 }
    
    -- 1.3.6.1.4.1.119.2.3.69.203.507.5.3.12.1.1.3
    ipeCfgAccountUserName OBJECT-TYPE
        SYNTAX      DisplayString (SIZE(1..31))
        ACCESS      read-only
        STATUS      mandatory
        DESCRIPTION
            "User Name.
             An overlap of a user name isn't permitted.
    
             Please use ASCII code.
    
             The characters which can be used are '-', '_','0'-'9', 'a'-'z'
             and 'A'-'Z'."
        ::= { ipeCfgAccountUserInfoEntry 3 }
    
    -- 1.3.6.1.4.1.119.2.3.69.203.507.5.3.12.1.1.4
    ipeCfgAccountUserKey OBJECT-TYPE
        SYNTAX      DisplayString (SIZE(8..128))
        ACCESS      read-only
        STATUS      mandatory
        DESCRIPTION
            "User password encrypted by blowfish.
             Acceptable characters for this object is shown below.
    
             '-', '_','0'-'9', 'a'-'z' and 'A'-'Z'."
        ::= { ipeCfgAccountUserInfoEntry 4 }
    
    -- 1.3.6.1.4.1.119.2.3.69.203.507.5.3.12.1.1.5
    ipeCfgAccountUserGroup OBJECT-TYPE
        SYNTAX      DisplayString (SIZE(1..31))
        ACCESS      read-only
        STATUS      mandatory
        DESCRIPTION
            "This object defines the privilege for the user.
             Acceptable characters for this object is shown below.
    
             '-', '_','0'-'9', 'a'-'z' and 'A'-'Z'."
        ::= { ipeCfgAccountUserInfoEntry 5 }
    
    -- 1.3.6.1.4.1.119.2.3.69.203.507.5.3.12.1.1.6
    ipeCfgAccountUserSnmpV3SecurityLevel OBJECT-TYPE
        SYNTAX      INTEGER { invalid(0), noAuthNoPriv(1), authNoPriv(2),
                        authPriv(3) }
        ACCESS      read-only
        STATUS      mandatory
        DESCRIPTION
            "SNMPv3 security level.
    
             Setting for SET/GET/TRAP at the time of the SNMPv3 use(INFORM is
             inapplicable)"
        ::= { ipeCfgAccountUserInfoEntry 6 }
    
    -- 1.3.6.1.4.1.119.2.3.69.203.507.5.3.12.1.1.7
    ipeCfgAccountUserSnmpV3AuthAlgorithm OBJECT-TYPE
        SYNTAX      INTEGER { invalid(0), md5(1), sha(2) }
        ACCESS      read-only
        STATUS      mandatory
        DESCRIPTION
            "Hash calculate algorithm of authenticate password.
    
             Setting for SET/GET/TRAP at the time of the SNMPv3 use(INFORM is
             inapplicable)"
        ::= { ipeCfgAccountUserInfoEntry 7 }
    
    -- 1.3.6.1.4.1.119.2.3.69.203.507.5.3.12.1.1.8
    ipeCfgAccountUserSnmpV3AuthKey OBJECT-TYPE
        SYNTAX      DisplayString (SIZE(8..128))
        ACCESS      read-only
        STATUS      mandatory
        DESCRIPTION
            "Authenticate password for SNMP SET/GET/TRAP PDU.
             This object expects encrypted password by blowfish, not original
             password. Therefore, the size of this object is not same as
             orignal password (8..31).
    
             When the object 'ipeCfgSnmpTrapNotifyType' is set to inform(2),
             the INFORM PDU Authenticate key is configured by
             'ipeCfgSnmpTrapAuthKey'."
        ::= { ipeCfgAccountUserInfoEntry 8 }
    
    -- 1.3.6.1.4.1.119.2.3.69.203.507.5.3.12.1.1.9
    ipeCfgAccountUserSnmpV3PrivAlgorithm OBJECT-TYPE
        SYNTAX      INTEGER { invalid(0), des(1), aes(2) }
        ACCESS      read-only
        STATUS      mandatory
        DESCRIPTION
            "Cipher algorithm.
    
             Setting for SET/GET/TRAP at the time of the SNMPv3 use(INFORM is
             inapplicable)"
        ::= { ipeCfgAccountUserInfoEntry 9 }
    
    -- 1.3.6.1.4.1.119.2.3.69.203.507.5.3.12.1.1.10
    ipeCfgAccountUserSnmpV3PrivKey OBJECT-TYPE
        SYNTAX      DisplayString (SIZE(8..128))
        ACCESS      read-only
        STATUS      mandatory
        DESCRIPTION
            "Privacy password for SNMP SET/GET/TRAP PDU.
             This object expects encrypted password by blowfish, not original
             password. Therefore, the size of this object is not same as
             orignal password (8..31).
    
             When the 'ipeCfgSnmpTrapNotifyType' is set to inform(2), the
             INFORM PDU Authenticate key is configured by
             'ipeCfgSnmpTrapAuthKey'."
        ::= { ipeCfgAccountUserInfoEntry 10 }
    
    -- 1.3.6.1.4.1.119.2.3.69.203.507.5.3.12.1.1.11
    ipeCfgAccountUserRowStatus OBJECT-TYPE
        SYNTAX      RowStatus { active(1), createAndGo(4), destroy(6) }
        ACCESS      read-only
        STATUS      mandatory
        DESCRIPTION
            "This RowStatus has a status only active(1).
    
             1) creating a entry
             When you make a new entry, you must SET objects indicated below.
    
             ipeCfgAccountUserIndex
             ipeCfgAccountUserName
             ipeCfgAccountUserKey
             ipeCfgAccountUserGroup
             ipeCfgAccountUserSnmpV3SecurityLevel
             ipeCfgAccountUserSnmpV3AuthAlgorithm
             ipeCfgAccountUserSnmpV3AuthKey
             ipeCfgAccountUserSnmpV3PrivAlgorithm
             ipeCfgAccountUserSnmpV3PrivKey
             ipeCfgAccountUserRowStatus <- createAndGo(4)
    
             2) modifing a entry
             ipeCfgAccountUserKey can only be changed.
             Other items can not be updated. Please do destroy of entry and a
             create.
    
             3) deleting a entry
             When you SET a destroy(6) to ipeCfgAccountUserRowStatus, the
             entry is destroyed.
    
             4) About SNMPv3
             When there is not ipeCfgAccountGroupInfoEntry corresponding to
             ipeCfgAccountUserGroup, SNMPv3-TRAP which I used
             ipeCfgAccountUserName for is output, but cannot use
             SNMPv3-Set/Get-Request."
        ::= { ipeCfgAccountUserInfoEntry 11 }
    
    -- 1.3.6.1.4.1.119.2.3.69.203.507.5.3.12.2
    ipeCfgAccountGroupInfoTable OBJECT-TYPE
        SYNTAX      SEQUENCE OF IpeCfgAccountGroupInfoEntry
        ACCESS      not-accessible
        STATUS      mandatory
        DESCRIPTION
            "Table of Group Information."
        ::= { ipeCfgAccount 2 }
    
    -- 1.3.6.1.4.1.119.2.3.69.203.507.5.3.12.2.1
    ipeCfgAccountGroupInfoEntry OBJECT-TYPE
        SYNTAX      IpeCfgAccountGroupInfoEntry
        ACCESS      not-accessible
        STATUS      mandatory
        DESCRIPTION
            "Entry of Group Information."
        INDEX       { ipeCfgAccountGroupNEAddress, ipeCfgAccountGroupIndex }
        ::= { ipeCfgAccountGroupInfoTable 1 }
    
    IpeCfgAccountGroupInfoEntry ::= SEQUENCE {
        ipeCfgAccountGroupIndex         INTEGER,
        ipeCfgAccountGroupNEAddress     IpAddress,
        ipeCfgAccountGroupName          DisplayString,
        ipeCfgAccountGroupTelnet        INTEGER,
        ipeCfgAccountGroupSsh           INTEGER,
        ipeCfgAccountGroupFtp           INTEGER,
        ipeCfgAccountGroupSftp          INTEGER,
        ipeCfgAccountGroupHttp          INTEGER,
        ipeCfgAccountGroupHttps         INTEGER,
        ipeCfgAccountGroupSnmp          INTEGER,
        ipeCfgAccountGroupAccessLevel   INTEGER,
        ipeCfgAccountGroupRowStatus     RowStatus
    }
    
    -- 1.3.6.1.4.1.119.2.3.69.203.507.5.3.12.2.1.1
    ipeCfgAccountGroupIndex OBJECT-TYPE
        SYNTAX      INTEGER (1..10)
        ACCESS      not-accessible
        STATUS      mandatory
        DESCRIPTION
            "Index of table."
        ::= { ipeCfgAccountGroupInfoEntry 1 }
    
    -- 1.3.6.1.4.1.119.2.3.69.203.507.5.3.12.2.1.2
    ipeCfgAccountGroupNEAddress OBJECT-TYPE
        SYNTAX      IpAddress
        ACCESS      not-accessible
        STATUS      mandatory
        DESCRIPTION
            ""
        ::= { ipeCfgAccountGroupInfoEntry 2 }
    
    -- 1.3.6.1.4.1.119.2.3.69.203.507.5.3.12.2.1.3
    ipeCfgAccountGroupName OBJECT-TYPE
        SYNTAX      DisplayString (SIZE(1..31))
        ACCESS      read-only
        STATUS      mandatory
        DESCRIPTION
            "Group name.
             An overlap of a group name isn't permitted.
    
             Please use ASCII code.
    
             The characters which can be used are '-', '_','0'-'9', 'a'-'z'
             and 'A'-'Z'."
        ::= { ipeCfgAccountGroupInfoEntry 3 }
    
    -- 1.3.6.1.4.1.119.2.3.69.203.507.5.3.12.2.1.4
    ipeCfgAccountGroupTelnet OBJECT-TYPE
        SYNTAX      INTEGER { invalid(0), disabled(1), enabled(2) }
        ACCESS      read-only
        STATUS      mandatory
        DESCRIPTION
            "TELNET enable."
        ::= { ipeCfgAccountGroupInfoEntry 4 }
    
    -- 1.3.6.1.4.1.119.2.3.69.203.507.5.3.12.2.1.5
    ipeCfgAccountGroupSsh OBJECT-TYPE
        SYNTAX      INTEGER { invalid(0), disabled(1), enabled(2) }
        ACCESS      read-only
        STATUS      mandatory
        DESCRIPTION
            "SSH enable."
        ::= { ipeCfgAccountGroupInfoEntry 5 }
    
    -- 1.3.6.1.4.1.119.2.3.69.203.507.5.3.12.2.1.6
    ipeCfgAccountGroupFtp OBJECT-TYPE
        SYNTAX      INTEGER { invalid(0), disabled(1), enabled(2) }
        ACCESS      read-only
        STATUS      mandatory
        DESCRIPTION
            "FTP enable."
        ::= { ipeCfgAccountGroupInfoEntry 6 }
    
    -- 1.3.6.1.4.1.119.2.3.69.203.507.5.3.12.2.1.7
    ipeCfgAccountGroupSftp OBJECT-TYPE
        SYNTAX      INTEGER { invalid(0), disabled(1), enabled(2) }
        ACCESS      read-only
        STATUS      mandatory
        DESCRIPTION
            "SFTP enable."
        ::= { ipeCfgAccountGroupInfoEntry 7 }
    
    -- 1.3.6.1.4.1.119.2.3.69.203.507.5.3.12.2.1.8
    ipeCfgAccountGroupHttp OBJECT-TYPE
        SYNTAX      INTEGER { invalid(0), disabled(1), enabled(2) }
        ACCESS      read-only
        STATUS      mandatory
        DESCRIPTION
            "HTTP enable."
        ::= { ipeCfgAccountGroupInfoEntry 8 }
    
    -- 1.3.6.1.4.1.119.2.3.69.203.507.5.3.12.2.1.9
    ipeCfgAccountGroupHttps OBJECT-TYPE
        SYNTAX      INTEGER { invalid(0), disabled(1), enabled(2) }
        ACCESS      read-only
        STATUS      mandatory
        DESCRIPTION
            "HTTPS enable."
        ::= { ipeCfgAccountGroupInfoEntry 9 }
    
    -- 1.3.6.1.4.1.119.2.3.69.203.507.5.3.12.2.1.10
    ipeCfgAccountGroupSnmp OBJECT-TYPE
        SYNTAX      INTEGER { invalid(0), disabled(1), enabled(2) }
        ACCESS      read-only
        STATUS      mandatory
        DESCRIPTION
            "SNMP enable."
        ::= { ipeCfgAccountGroupInfoEntry 10 }
    
    -- 1.3.6.1.4.1.119.2.3.69.203.507.5.3.12.2.1.11
    ipeCfgAccountGroupAccessLevel OBJECT-TYPE
        SYNTAX      INTEGER { invalid(0), operatorLevel(1), configLevel(2),
                        adminLevel(3) }
        ACCESS      read-only
        STATUS      mandatory
        DESCRIPTION
            "Access level."
        ::= { ipeCfgAccountGroupInfoEntry 11 }
    
    -- 1.3.6.1.4.1.119.2.3.69.203.507.5.3.12.2.1.12
    ipeCfgAccountGroupRowStatus OBJECT-TYPE
        SYNTAX      RowStatus { active(1), createAndGo(4), destroy(6) }
        ACCESS      read-only
        STATUS      mandatory
        DESCRIPTION
            "This RowStatus has a status only 'active(1)'.
    
             1) creating a entry.
             When you make a new entry, you must SET objects indicated below.
    
             ipeCfgAccountGroupName
             ipeCfgAccountGroupTelnet
             ipeCfgAccountGroupSsh
             ipeCfgAccountGroupFtp
             ipeCfgAccountGroupSftp
             ipeCfgAccountGroupHttp
             ipeCfgAccountGroupHttps
             ipeCfgAccountGroupSnmp
             ipeCfgAccountGroupAccessLevel
             ipeCfgAccountGroupRowStatus <- createAndGo(4)
    
             ipeCfgAccountGroupIndex is an index of this entry.
    
             2) deleting a entry.
             When you SET a destroy(6) to ipeCfgAccountGroupRowStatus, the
             entry is destroyed.
    
             Information that synchronizes and is deleted:
              User Information setting(ssh/ftp/http login information)
              SNMPv3-Set/Get-Req user info
             (The SNMPv3-TRAP information is left)
    
             3) modifing a entry
             It can change it other than ipeCfgAccountGroupName,
             ipeCfgAccountGroupRowStatus.
             But the entry of default (ADMIN/OPERATOR/CONFIG) is impossible of
             a change ipeCfgAccountGroupName."
        ::= { ipeCfgAccountGroupInfoEntry 12 }
    
    -- 1.3.6.1.4.1.119.2.3.69.203.507.5.3.12.4
    ipeCfgUserAccountAuthTable OBJECT-TYPE
        SYNTAX      SEQUENCE OF IpeCfgUserAccountAuthEntry
        ACCESS      not-accessible
        STATUS      mandatory
        DESCRIPTION
            "Configure user authentication method about Web LCT."
        ::= { ipeCfgAccount 4 }
    
    -- 1.3.6.1.4.1.119.2.3.69.203.507.5.3.12.4.1
    ipeCfgUserAccountAuthEntry OBJECT-TYPE
        SYNTAX      IpeCfgUserAccountAuthEntry
        ACCESS      not-accessible
        STATUS      mandatory
        DESCRIPTION
            "..."
        INDEX       { ipeCfgUserAccountAuthNEAddress, ipeCfgUserAccountAuthIndex }
        ::= { ipeCfgUserAccountAuthTable 1 }
    
    IpeCfgUserAccountAuthEntry ::= SEQUENCE {
        ipeCfgUserAccountAuthIndex          INTEGER,
        ipeCfgUserAccountAuthNEAddress      IpAddress,
        ipeCfgUserAccountAuthMode           INTEGER,
        ipeCfgUserAccountAuthOrder          INTEGER,
        ipeCfgUserAccountAuthTrapEnable     INTEGER,
        ipeCfgUserAccountAuthTrapLocal      INTEGER,
        ipeCfgUserAccountAuthTrapExternal   INTEGER
    }
    
    -- 1.3.6.1.4.1.119.2.3.69.203.507.5.3.12.4.1.1
    ipeCfgUserAccountAuthIndex OBJECT-TYPE
        SYNTAX      INTEGER (1)
        ACCESS      not-accessible
        STATUS      mandatory
        DESCRIPTION
            "The index of this table."
        ::= { ipeCfgUserAccountAuthEntry 1 }
    
    -- 1.3.6.1.4.1.119.2.3.69.203.507.5.3.12.4.1.2
    ipeCfgUserAccountAuthNEAddress OBJECT-TYPE
        SYNTAX      IpAddress
        ACCESS      not-accessible
        STATUS      mandatory
        DESCRIPTION
            "Reserved object for northbound interface."
        ::= { ipeCfgUserAccountAuthEntry 2 }
    
    -- 1.3.6.1.4.1.119.2.3.69.203.507.5.3.12.4.1.3
    ipeCfgUserAccountAuthMode OBJECT-TYPE
        SYNTAX      INTEGER { invalid(0), mode1(1), mode2(2), mode3(3) }
        ACCESS      read-only
        STATUS      mandatory
        DESCRIPTION
            "Indicate the user authentication mode.
    
             mode1 : local authentication only.
             mode2 : local and LDAP authentication. (NOT SUPPORTED)
             mode3 : local and RADIUS authentication.
    
             mode2 will be supprted in future version."
        DEFVAL      { mode1 }
        ::= { ipeCfgUserAccountAuthEntry 3 }
    
    -- 1.3.6.1.4.1.119.2.3.69.203.507.5.3.12.4.1.4
    ipeCfgUserAccountAuthOrder OBJECT-TYPE
        SYNTAX      INTEGER { invalid(0), localAuthFirst(1),
                        externalAuthFirst(2) }
        ACCESS      read-only
        STATUS      mandatory
        DESCRIPTION
            "Indicate the user authentication order.
             This object is effective only if ipeCfgUserAccountAuthMode
             is set to mode2 or mode3.
             External authentication means authentication with RADIUS or
             LDAP.
    
             localAuthFirst    : local -> external
             externalAuthFirst : external -> local"
        DEFVAL      { localAuthFirst }
        ::= { ipeCfgUserAccountAuthEntry 4 }
    
    -- 1.3.6.1.4.1.119.2.3.69.203.507.5.3.12.4.1.5
    ipeCfgUserAccountAuthTrapEnable OBJECT-TYPE
        SYNTAX      INTEGER { invalid(0), disable(1), enable(2) }
        ACCESS      read-only
        STATUS      mandatory
        DESCRIPTION
            "Enable or disable user login trap.
             In case this object is set to enable, the system sends trap
             when user attempt to login to Web LCT."
        DEFVAL      { enable }
        ::= { ipeCfgUserAccountAuthEntry 5 }
    
    -- 1.3.6.1.4.1.119.2.3.69.203.507.5.3.12.4.1.6
    ipeCfgUserAccountAuthTrapLocal OBJECT-TYPE
        SYNTAX      INTEGER { invalid(0), success(1), failure(2) }
        ACCESS      read-only
        STATUS      mandatory
        DESCRIPTION
            "Indicate authentication result of local authentication.
             This object is dedicated for login control trap.
             If you read this object, the system returns invalid(0)."
        DEFVAL      { invalid }
        ::= { ipeCfgUserAccountAuthEntry 6 }
    
    -- 1.3.6.1.4.1.119.2.3.69.203.507.5.3.12.4.1.7
    ipeCfgUserAccountAuthTrapExternal OBJECT-TYPE
        SYNTAX      INTEGER { invalid(0), success(1), failure(2) }
        ACCESS      read-only
        STATUS      mandatory
        DESCRIPTION
            "Indicate authentication result of externel authentication.
             This object is dedicated for login control trap.
             If you read this object, the system returns invalid(0)."
        DEFVAL      { invalid }
        ::= { ipeCfgUserAccountAuthEntry 7 }
    
    -- 1.3.6.1.4.1.119.2.3.69.203.507.5.3.13
    ipeCfgDhcpGroup OBJECT IDENTIFIER
        ::= { ipeConfigurationGroup 13 }
    
    -- 1.3.6.1.4.1.119.2.3.69.203.507.5.3.13.1
    ipeCfgDhcpServerTable OBJECT-TYPE
        SYNTAX      SEQUENCE OF IpeCfgDhcpServerEntry
        ACCESS      not-accessible
        STATUS      mandatory
        DESCRIPTION
            "DHCPserver table."
        ::= { ipeCfgDhcpGroup 1 }
    
    -- 1.3.6.1.4.1.119.2.3.69.203.507.5.3.13.1.1
    ipeCfgDhcpServerEntry OBJECT-TYPE
        SYNTAX      IpeCfgDhcpServerEntry
        ACCESS      not-accessible
        STATUS      mandatory
        DESCRIPTION
            "entry of DHCPserver table."
        INDEX       { ipeCfgDhcpServerNEAddress, ipeCfgDhcpServerIndex }
        ::= { ipeCfgDhcpServerTable 1 }
    
    IpeCfgDhcpServerEntry ::= SEQUENCE {
        ipeCfgDhcpServerIndex           INTEGER,
        ipeCfgDhcpServerNEAddress       IpAddress,
        ipeCfgDhcpServerEnable          INTEGER,
        ipeCfgDhcpLeaseAddrRangeBegin   IpAddress,
        ipeCfgDhcpLeaseAddrRangeEnd     IpAddress
    }
    
    -- 1.3.6.1.4.1.119.2.3.69.203.507.5.3.13.1.1.1
    ipeCfgDhcpServerIndex OBJECT-TYPE
        SYNTAX      INTEGER (1..2)
        ACCESS      not-accessible
        STATUS      mandatory
        DESCRIPTION
            "Index of this table.
             Index value '2' is used for redundant Ctrl card."
        ::= { ipeCfgDhcpServerEntry 1 }
    
    -- 1.3.6.1.4.1.119.2.3.69.203.507.5.3.13.1.1.2
    ipeCfgDhcpServerNEAddress OBJECT-TYPE
        SYNTAX      IpAddress
        ACCESS      not-accessible
        STATUS      mandatory
        DESCRIPTION
            ""
        ::= { ipeCfgDhcpServerEntry 2 }
    
    -- 1.3.6.1.4.1.119.2.3.69.203.507.5.3.13.1.1.3
    ipeCfgDhcpServerEnable OBJECT-TYPE
        SYNTAX      INTEGER { start(1), stop(2), restart(3) }
        ACCESS      read-only
        STATUS      mandatory
        DESCRIPTION
            "Effective/invalid setting of DHCP.
             value range:start(1)
                         stop(2)
                         restart(3)
             DHCPD has already started. When the start is specified, DHCPD
             restart."
        ::= { ipeCfgDhcpServerEntry 3 }
    
    -- 1.3.6.1.4.1.119.2.3.69.203.507.5.3.13.1.1.4
    ipeCfgDhcpLeaseAddrRangeBegin OBJECT-TYPE
        SYNTAX      IpAddress
        ACCESS      read-only
        STATUS      mandatory
        DESCRIPTION
            "Beginning IPaddress within the range of lease address.
             value range:Dotted decimal notation
             denial value:0.0.0.0 , 127.0.0.1 , 255.255.255.255
             ipeCfgDhcpLeaseAddrRangeBegin don't same as
             ipeCfgPortLctIpAddress value"
        ::= { ipeCfgDhcpServerEntry 4 }
    
    -- 1.3.6.1.4.1.119.2.3.69.203.507.5.3.13.1.1.5
    ipeCfgDhcpLeaseAddrRangeEnd OBJECT-TYPE
        SYNTAX      IpAddress
        ACCESS      read-only
        STATUS      mandatory
        DESCRIPTION
            "End IPaddress within the range of lease address.
             value range:Dotted decimal notation
             denial value:0.0.0.0 , 127.0.0.1 , 255.255.255.255
             ipeCfgDhcpLeaseAddrRangeEnd don't same as ipeCfgPortLctIpAddress
             value"
        ::= { ipeCfgDhcpServerEntry 5 }
    
    -- 1.3.6.1.4.1.119.2.3.69.203.507.5.3.14
    ipeCfgStpGroup OBJECT IDENTIFIER
        ::= { ipeConfigurationGroup 14 }
    
    -- 1.3.6.1.4.1.119.2.3.69.203.507.5.3.14.1
    ipeCfgStpBridgeTable OBJECT-TYPE
        SYNTAX      SEQUENCE OF IpeCfgStpBridgeEntry
        ACCESS      not-accessible
        STATUS      mandatory
        DESCRIPTION
            "STP state setting table."
        ::= { ipeCfgStpGroup 1 }
    
    -- 1.3.6.1.4.1.119.2.3.69.203.507.5.3.14.1.1
    ipeCfgStpBridgeEntry OBJECT-TYPE
        SYNTAX      IpeCfgStpBridgeEntry
        ACCESS      not-accessible
        STATUS      mandatory
        DESCRIPTION
            "entry of STP state setting table."
        INDEX       { ipeCfgStpBridgeNEAddress, ipeCfgStpBridgeIndex }
        ::= { ipeCfgStpBridgeTable 1 }
    
    IpeCfgStpBridgeEntry ::= SEQUENCE {
        ipeCfgStpBridgeIndex            INTEGER,
        ipeCfgStpBridgeNEAddress        IpAddress,
        ipeCfgStpEnable                 INTEGER,
        ipeCfgStpPriority               INTEGER,
        ipeCfgStpBridgeMaxAge           Timeout,
        ipeCfgStpBridgeHelloTime        Timeout,
        ipeCfgStpBridgeForwardDelay     Timeout,
        ipeCfgStpBridgeAutoEnable       OffOnValue
    }
    
    -- 1.3.6.1.4.1.119.2.3.69.203.507.5.3.14.1.1.1
    ipeCfgStpBridgeIndex OBJECT-TYPE
        SYNTAX      INTEGER (1..20)
        ACCESS      not-accessible
        STATUS      mandatory
        DESCRIPTION
            "Index of this ipeCfgStpBridgeEntry.
             Range from 1 o 20."
        ::= { ipeCfgStpBridgeEntry 1 }
    
    -- 1.3.6.1.4.1.119.2.3.69.203.507.5.3.14.1.1.2
    ipeCfgStpBridgeNEAddress OBJECT-TYPE
        SYNTAX      IpAddress
        ACCESS      not-accessible
        STATUS      mandatory
        DESCRIPTION
            ""
        ::= { ipeCfgStpBridgeEntry 2 }
    
    -- 1.3.6.1.4.1.119.2.3.69.203.507.5.3.14.1.1.3
    ipeCfgStpEnable OBJECT-TYPE
        SYNTAX      INTEGER { enabled(1), disabled(2) }
        ACCESS      read-only
        STATUS      mandatory
        DESCRIPTION
            "Effective/invalid setting of STP.
             value :enabled
                    disabled"
        ::= { ipeCfgStpBridgeEntry 3 }
    
    -- 1.3.6.1.4.1.119.2.3.69.203.507.5.3.14.1.1.4
    ipeCfgStpPriority OBJECT-TYPE
        SYNTAX      INTEGER (0..65535)
        ACCESS      read-only
        STATUS      mandatory
        DESCRIPTION
            "Bridge priority.
             value range:0 to 65535"
        ::= { ipeCfgStpBridgeEntry 4 }
    
    -- 1.3.6.1.4.1.119.2.3.69.203.507.5.3.14.1.1.5
    ipeCfgStpBridgeMaxAge OBJECT-TYPE
        SYNTAX      Timeout (600..4000)
        ACCESS      read-only
        STATUS      mandatory
        DESCRIPTION
            "MaxAge (in units of hundredths of a second).
             value range:600 to 4000
             rule: 2 * (ipeCfgStpBridgeForwardDelay - 1) =>
             ipeCfgStpBridgeMaxAge
                  ipeCfgStpBridgeMaxAge >= 2 * (ipeCfgStpBridgeHelloTime + 1)"
        ::= { ipeCfgStpBridgeEntry 5 }
    
    -- 1.3.6.1.4.1.119.2.3.69.203.507.5.3.14.1.1.6
    ipeCfgStpBridgeHelloTime OBJECT-TYPE
        SYNTAX      Timeout (100..1000)
        ACCESS      read-only
        STATUS      mandatory
        DESCRIPTION
            "HelloTime (in units of hundredths of a second).
             value range:100 to 1000
             rule:ipeCfgStpBridgeMaxAge >= 2x(ipeCfgStpBridgeHelloTime + 1)"
        ::= { ipeCfgStpBridgeEntry 6 }
    
    -- 1.3.6.1.4.1.119.2.3.69.203.507.5.3.14.1.1.7
    ipeCfgStpBridgeForwardDelay OBJECT-TYPE
        SYNTAX      Timeout (400..3000)
        ACCESS      read-only
        STATUS      mandatory
        DESCRIPTION
            "ForwardDelay (in units of hundredths of a second).
             value range:400 to 3000
             rule: 2 * (ipeCfgStpBridgeForwardDelay - 1) >=
             ipeCfgStpBridgeMaxAge"
        ::= { ipeCfgStpBridgeEntry 7 }
    
    -- 1.3.6.1.4.1.119.2.3.69.203.507.5.3.14.1.1.8
    ipeCfgStpBridgeAutoEnable OBJECT-TYPE
        SYNTAX      OffOnValue
        ACCESS      read-only
        STATUS      mandatory
        DESCRIPTION
            "This object configures automatic enabling M-plane STP.
             When the automatic enabling is configured, 'ipeCfgStpEnable' does
             not control STP function, STP function will be enabled by the
             system automatically."
        ::= { ipeCfgStpBridgeEntry 8 }
    
    -- 1.3.6.1.4.1.119.2.3.69.203.507.5.3.14.2
    ipeCfgStpPortTable OBJECT-TYPE
        SYNTAX      SEQUENCE OF IpeCfgStpPortEntry
        ACCESS      not-accessible
        STATUS      mandatory
        DESCRIPTION
            "STP port information table."
        ::= { ipeCfgStpGroup 2 }
    
    -- 1.3.6.1.4.1.119.2.3.69.203.507.5.3.14.2.1
    ipeCfgStpPortEntry OBJECT-TYPE
        SYNTAX      IpeCfgStpPortEntry
        ACCESS      not-accessible
        STATUS      mandatory
        DESCRIPTION
            "entry of  STP port information table."
        INDEX       { ipeCfgStpPortNEAddress, ipeCfgStpPortIfIndex }
        ::= { ipeCfgStpPortTable 1 }
    
    IpeCfgStpPortEntry ::= SEQUENCE {
        ipeCfgStpPortIfIndex        InterfaceIndex,
        ipeCfgStpPortNEAddress      IpAddress,
        ipeCfgStpPortPriority       INTEGER,
        ipeCfgStpPortPathCost       INTEGER,
        ipeCfgStpPortEdgeEnable     INTEGER
    }
    
    -- 1.3.6.1.4.1.119.2.3.69.203.507.5.3.14.2.1.1
    ipeCfgStpPortIfIndex OBJECT-TYPE
        SYNTAX      InterfaceIndex
        ACCESS      not-accessible
        STATUS      mandatory
        DESCRIPTION
            "Index of I/F table."
        ::= { ipeCfgStpPortEntry 1 }
    
    -- 1.3.6.1.4.1.119.2.3.69.203.507.5.3.14.2.1.2
    ipeCfgStpPortNEAddress OBJECT-TYPE
        SYNTAX      IpAddress
        ACCESS      not-accessible
        STATUS      mandatory
        DESCRIPTION
            ""
        ::= { ipeCfgStpPortEntry 2 }
    
    -- 1.3.6.1.4.1.119.2.3.69.203.507.5.3.14.2.1.3
    ipeCfgStpPortPriority OBJECT-TYPE
        SYNTAX      INTEGER (0..63)
        ACCESS      read-only
        STATUS      mandatory
        DESCRIPTION
            "Port priority.
             value range:0 to 63"
        ::= { ipeCfgStpPortEntry 3 }
    
    -- 1.3.6.1.4.1.119.2.3.69.203.507.5.3.14.2.1.4
    ipeCfgStpPortPathCost OBJECT-TYPE
        SYNTAX      INTEGER (1..65535)
        ACCESS      read-only
        STATUS      mandatory
        DESCRIPTION
            "Pathcost.
             value range:1 to 65535"
        ::= { ipeCfgStpPortEntry 4 }
    
    -- 1.3.6.1.4.1.119.2.3.69.203.507.5.3.14.2.1.5
    ipeCfgStpPortEdgeEnable OBJECT-TYPE
        SYNTAX      INTEGER { enabled(1), disabled(2) }
        ACCESS      read-only
        STATUS      mandatory
        DESCRIPTION
            "Effective/invalid setting of BPDU.
             value range:enabled(1)
                         disabled(2)"
        ::= { ipeCfgStpPortEntry 5 }
    
    -- 1.3.6.1.4.1.119.2.3.69.203.507.5.3.15
    ipeCfgPortGroup OBJECT IDENTIFIER
        ::= { ipeConfigurationGroup 15 }
    
    -- 1.3.6.1.4.1.119.2.3.69.203.507.5.3.15.1
    ipeCfgPortModemTable OBJECT-TYPE
        SYNTAX      SEQUENCE OF IpeCfgPortModemEntry
        ACCESS      not-accessible
        STATUS      mandatory
        DESCRIPTION
            "MODEM port set up information table."
        ::= { ipeCfgPortGroup 1 }
    
    -- 1.3.6.1.4.1.119.2.3.69.203.507.5.3.15.1.1
    ipeCfgPortModemEntry OBJECT-TYPE
        SYNTAX      IpeCfgPortModemEntry
        ACCESS      not-accessible
        STATUS      mandatory
        DESCRIPTION
            "entry of  MODEM port set up information table."
        INDEX       { ipeCfgPortModemNEAddress, ipeCfgPortModemIfIndex }
        ::= { ipeCfgPortModemTable 1 }
    
    IpeCfgPortModemEntry ::= SEQUENCE {
        ipeCfgPortModemIfIndex      InterfaceIndex,
        ipeCfgPortModemNEAddress    IpAddress,
        ipeCfgPortModemEnable       INTEGER
    }
    
    -- 1.3.6.1.4.1.119.2.3.69.203.507.5.3.15.1.1.1
    ipeCfgPortModemIfIndex OBJECT-TYPE
        SYNTAX      InterfaceIndex
        ACCESS      not-accessible
        STATUS      mandatory
        DESCRIPTION
            "Index of table."
        ::= { ipeCfgPortModemEntry 1 }
    
    -- 1.3.6.1.4.1.119.2.3.69.203.507.5.3.15.1.1.2
    ipeCfgPortModemNEAddress OBJECT-TYPE
        SYNTAX      IpAddress
        ACCESS      not-accessible
        STATUS      mandatory
        DESCRIPTION
            ""
        ::= { ipeCfgPortModemEntry 2 }
    
    -- 1.3.6.1.4.1.119.2.3.69.203.507.5.3.15.1.1.3
    ipeCfgPortModemEnable OBJECT-TYPE
        SYNTAX      INTEGER { enabled(1), disabled(2) }
        ACCESS      read-only
        STATUS      mandatory
        DESCRIPTION
            "Effective/invalid setting of MODEM port.
             value range: enabled(1)
                         disabled(2)"
        ::= { ipeCfgPortModemEntry 3 }
    
    -- 1.3.6.1.4.1.119.2.3.69.203.507.5.3.15.2
    ipeCfgPortLctTable OBJECT-TYPE
        SYNTAX      SEQUENCE OF IpeCfgPortLctEntry
        ACCESS      not-accessible
        STATUS      mandatory
        DESCRIPTION
            "LCT port set up information table."
        ::= { ipeCfgPortGroup 2 }
    
    -- 1.3.6.1.4.1.119.2.3.69.203.507.5.3.15.2.1
    ipeCfgPortLctEntry OBJECT-TYPE
        SYNTAX      IpeCfgPortLctEntry
        ACCESS      not-accessible
        STATUS      mandatory
        DESCRIPTION
            "entry of  LCT port set up information table."
        INDEX       { ipeCfgPortLctNEAddress, ipeCfgPortLctIfIndex }
        ::= { ipeCfgPortLctTable 1 }
    
    IpeCfgPortLctEntry ::= SEQUENCE {
        ipeCfgPortLctIfIndex                    InterfaceIndex,
        ipeCfgPortLctNEAddress                  IpAddress,
        ipeCfgPortLctIpAddress                  IpAddress,
        ipeCfgPortLctNetMask                    IpAddress,
        ipeCfgPortLctEnable                     INTEGER,
        ipeCfgPortLctMtu                        INTEGER,
        ipeCfgPortLctAutoNeg                    INTEGER,
        ipeCfgPortLctLinkLocalAddress           Ipv6Address,
        ipeCfgPortLctLinkLocalAddressOrigin     INTEGER,
        ipeCfgPortLctHttpReverseProxyEnable     EnableDisableValue
    }
    
    -- 1.3.6.1.4.1.119.2.3.69.203.507.5.3.15.2.1.1
    ipeCfgPortLctIfIndex OBJECT-TYPE
        SYNTAX      InterfaceIndex
        ACCESS      not-accessible
        STATUS      mandatory
        DESCRIPTION
            "Index of table."
        ::= { ipeCfgPortLctEntry 1 }
    
    -- 1.3.6.1.4.1.119.2.3.69.203.507.5.3.15.2.1.2
    ipeCfgPortLctNEAddress OBJECT-TYPE
        SYNTAX      IpAddress
        ACCESS      not-accessible
        STATUS      mandatory
        DESCRIPTION
            ""
        ::= { ipeCfgPortLctEntry 2 }
    
    -- 1.3.6.1.4.1.119.2.3.69.203.507.5.3.15.2.1.3
    ipeCfgPortLctIpAddress OBJECT-TYPE
        SYNTAX      IpAddress
        ACCESS      read-only
        STATUS      mandatory
        DESCRIPTION
            "IPaddress of LCT port.
             It makes an error of the Internet Protocol address setting that
             overlaps in the port in the device.
             The object port and the range of the value are described as
             follows.
             Object port: Lct, InbandMngVLAN1-16, Bridge1-Bridge20, NE2
             Value range:0x00000000-0xdfffffff(0.0.0.0-223.255.255.255)
             The relation is not in the state and the number of Branch of
             interfaces and the Internet Protocol address repetition check is
             checked.
    
             When 0.0.0.0 is set to ipeCfgPortLctIpAddress, it becomes an
             Internet Protocol address deletion."
        ::= { ipeCfgPortLctEntry 3 }
    
    -- 1.3.6.1.4.1.119.2.3.69.203.507.5.3.15.2.1.4
    ipeCfgPortLctNetMask OBJECT-TYPE
        SYNTAX      IpAddress
        ACCESS      read-only
        STATUS      mandatory
        DESCRIPTION
            "Subnet mask of LCT port.
             When it isn't proper as subnetmask, it'll be an error.
             Value range:0x00000000-0xfffffffc(0-30bit)"
        ::= { ipeCfgPortLctEntry 4 }
    
    -- 1.3.6.1.4.1.119.2.3.69.203.507.5.3.15.2.1.5
    ipeCfgPortLctEnable OBJECT-TYPE
        SYNTAX      INTEGER { enabled(1), disabled(2) }
        ACCESS      read-only
        STATUS      mandatory
        DESCRIPTION
            "Effective/invalid setting of LCT port.
             value range: enabled
                         disabled"
        ::= { ipeCfgPortLctEntry 5 }
    
    -- 1.3.6.1.4.1.119.2.3.69.203.507.5.3.15.2.1.6
    ipeCfgPortLctMtu OBJECT-TYPE
        SYNTAX      INTEGER (256..1500)
        ACCESS      read-only
        STATUS      mandatory
        DESCRIPTION
            "MTU value of LCT.
             value range:256 to 1500"
        ::= { ipeCfgPortLctEntry 6 }
    
    -- 1.3.6.1.4.1.119.2.3.69.203.507.5.3.15.2.1.7
    ipeCfgPortLctAutoNeg OBJECT-TYPE
        SYNTAX      INTEGER { enabled(1), disabled(2) }
        ACCESS      read-only
        STATUS      mandatory
        DESCRIPTION
            "Effective/invalid setting of LCT AUTO NEGOTIATION.
             value range: enabled
                         disabled"
        ::= { ipeCfgPortLctEntry 7 }
    
    -- 1.3.6.1.4.1.119.2.3.69.203.507.5.3.15.2.1.8
    ipeCfgPortLctLinkLocalAddress OBJECT-TYPE
        SYNTAX      Ipv6Address
        ACCESS      read-only
        STATUS      mandatory
        DESCRIPTION
            "The IPv6 Link Local address of the LCT port."
        ::= { ipeCfgPortLctEntry 8 }
    
    -- 1.3.6.1.4.1.119.2.3.69.203.507.5.3.15.2.1.9
    ipeCfgPortLctLinkLocalAddressOrigin OBJECT-TYPE
        SYNTAX      INTEGER { invalid(0), manual(1), linklayer(2) }
        ACCESS      read-only
        STATUS      mandatory
        DESCRIPTION
            "The origin of the address.
             manual(1) indicates that the address was manually
                    configured to a specified address, e.g., by user
                    configuration.
    
             linklayer(2) indicates the address to be created
                       by IPv6 stateless address auto-configuration."
        DEFVAL      { manual }
        ::= { ipeCfgPortLctEntry 9 }
    
    -- 1.3.6.1.4.1.119.2.3.69.203.507.5.3.15.2.1.10
    ipeCfgPortLctHttpReverseProxyEnable OBJECT-TYPE
        SYNTAX      EnableDisableValue
        ACCESS      read-only
        STATUS      mandatory
        DESCRIPTION
            "Enables or disables HTTP/HTTPS Reverse proxy on this interface."
        DEFVAL      { enable }
        ::= { ipeCfgPortLctEntry 10 }
    
    -- 1.3.6.1.4.1.119.2.3.69.203.507.5.3.15.3
    ipeCfgPortEtherTable OBJECT-TYPE
        SYNTAX      SEQUENCE OF IpeCfgPortEtherEntry
        ACCESS      not-accessible
        STATUS      mandatory
        DESCRIPTION
            "NMS/NE1 port set up information table."
        ::= { ipeCfgPortGroup 3 }
    
    -- 1.3.6.1.4.1.119.2.3.69.203.507.5.3.15.3.1
    ipeCfgPortEtherEntry OBJECT-TYPE
        SYNTAX      IpeCfgPortEtherEntry
        ACCESS      not-accessible
        STATUS      mandatory
        DESCRIPTION
            "entry of  NMS/NE1 port set up information table."
        INDEX       { ipeCfgPortEtherNEAddress, ipeCfgPortEtherIfIndex }
        ::= { ipeCfgPortEtherTable 1 }
    
    IpeCfgPortEtherEntry ::= SEQUENCE {
        ipeCfgPortEtherIfIndex          InterfaceIndex,
        ipeCfgPortEtherNEAddress        IpAddress,
        ipeCfgPortEtherEnable           INTEGER,
        ipeCfgPortEtherAutoNeg          INTEGER,
        ipeCfgPortEtherSpecialFilter    INTEGER,
        ipeCfgPortEtherLldpMode         INTEGER
    }
    
    -- 1.3.6.1.4.1.119.2.3.69.203.507.5.3.15.3.1.1
    ipeCfgPortEtherIfIndex OBJECT-TYPE
        SYNTAX      InterfaceIndex
        ACCESS      not-accessible
        STATUS      mandatory
        DESCRIPTION
            "Index of table."
        ::= { ipeCfgPortEtherEntry 1 }
    
    -- 1.3.6.1.4.1.119.2.3.69.203.507.5.3.15.3.1.2
    ipeCfgPortEtherNEAddress OBJECT-TYPE
        SYNTAX      IpAddress
        ACCESS      not-accessible
        STATUS      mandatory
        DESCRIPTION
            ""
        ::= { ipeCfgPortEtherEntry 2 }
    
    -- 1.3.6.1.4.1.119.2.3.69.203.507.5.3.15.3.1.3
    ipeCfgPortEtherEnable OBJECT-TYPE
        SYNTAX      INTEGER { enabled(1), disabled(2) }
        ACCESS      read-only
        STATUS      mandatory
        DESCRIPTION
            "Effective/invalid setting of NMS/NE1 port.
             value range: enabled(1)
                         disabled(2)
             default value is 'enabled'.(iPASOLINK EX Advanced)"
        DEFVAL      { enabled }
        ::= { ipeCfgPortEtherEntry 3 }
    
    -- 1.3.6.1.4.1.119.2.3.69.203.507.5.3.15.3.1.4
    ipeCfgPortEtherAutoNeg OBJECT-TYPE
        SYNTAX      INTEGER { enabled(1), disabled(2) }
        ACCESS      read-only
        STATUS      mandatory
        DESCRIPTION
            "Auto negotiation invalid effective/setting of NMS/NE1 port.
             value range: enabled(1)
                         disabled(2)"
        ::= { ipeCfgPortEtherEntry 4 }
    
    -- 1.3.6.1.4.1.119.2.3.69.203.507.5.3.15.3.1.5
    ipeCfgPortEtherSpecialFilter OBJECT-TYPE
        SYNTAX      INTEGER { true(1), false(2) }
        ACCESS      read-only
        STATUS      mandatory
        DESCRIPTION
            "Setting of whether a special broadcast packet is blocked."
        ::= { ipeCfgPortEtherEntry 5 }
    
    -- 1.3.6.1.4.1.119.2.3.69.203.507.5.3.15.3.1.6
    ipeCfgPortEtherLldpMode OBJECT-TYPE
        SYNTAX      INTEGER { invalid(0), standardMode(1),
                        proprietaryMode(2) }
        ACCESS      read-only
        STATUS      mandatory
        DESCRIPTION
            "Switch to select MAC address of LLDP Frame.
    
             standardMode    : MAC address of LLDP Frame is
                               01-80-C2-00-00-0E.
             proprietaryMode : MAC address of LLDP Frame is configured in
                               ipeCfgLldpProprietaryModeMacAddress."
        DEFVAL      { standardMode }
        ::= { ipeCfgPortEtherEntry 6 }
    
    -- 1.3.6.1.4.1.119.2.3.69.203.507.5.3.15.4
    ipeCfgPortNe2Table OBJECT-TYPE
        SYNTAX      SEQUENCE OF IpeCfgPortNe2Entry
        ACCESS      not-accessible
        STATUS      mandatory
        DESCRIPTION
            "NE2 port set up information table."
        ::= { ipeCfgPortGroup 4 }
    
    -- 1.3.6.1.4.1.119.2.3.69.203.507.5.3.15.4.1
    ipeCfgPortNe2Entry OBJECT-TYPE
        SYNTAX      IpeCfgPortNe2Entry
        ACCESS      not-accessible
        STATUS      mandatory
        DESCRIPTION
            "entry of NE2 port set up information table."
        INDEX       { ipeCfgPortNe2NEAddress, ipeCfgPortNe2IfIndex }
        ::= { ipeCfgPortNe2Table 1 }
    
    IpeCfgPortNe2Entry ::= SEQUENCE {
        ipeCfgPortNe2IfIndex            InterfaceIndex,
        ipeCfgPortNe2NEAddress          IpAddress,
        ipeCfgPortNe2IpAddress          IpAddress,
        ipeCfgPortNe2Enable             INTEGER,
        ipeCfgPortNe2Speed              INTEGER,
        ipeCfgPortNe2NeighborMibEnable  INTEGER
    }
    
    -- 1.3.6.1.4.1.119.2.3.69.203.507.5.3.15.4.1.1
    ipeCfgPortNe2IfIndex OBJECT-TYPE
        SYNTAX      InterfaceIndex
        ACCESS      not-accessible
        STATUS      mandatory
        DESCRIPTION
            "Index of table."
        ::= { ipeCfgPortNe2Entry 1 }
    
    -- 1.3.6.1.4.1.119.2.3.69.203.507.5.3.15.4.1.2
    ipeCfgPortNe2NEAddress OBJECT-TYPE
        SYNTAX      IpAddress
        ACCESS      not-accessible
        STATUS      mandatory
        DESCRIPTION
            ""
        ::= { ipeCfgPortNe2Entry 2 }
    
    -- 1.3.6.1.4.1.119.2.3.69.203.507.5.3.15.4.1.3
    ipeCfgPortNe2IpAddress OBJECT-TYPE
        SYNTAX      IpAddress
        ACCESS      read-only
        STATUS      mandatory
        DESCRIPTION
            "NE2 port IP Address.
             value range:0x00000000 - 0xdfffffff(0.0.0.0 - 223.255.255.255)
             The ppp function is restarted when setting it."
        ::= { ipeCfgPortNe2Entry 3 }
    
    -- 1.3.6.1.4.1.119.2.3.69.203.507.5.3.15.4.1.4
    ipeCfgPortNe2Enable OBJECT-TYPE
        SYNTAX      INTEGER { enabled(1), disabled(2) }
        ACCESS      read-only
        STATUS      mandatory
        DESCRIPTION
            "NE2 port enable.
             value range:enabled(1)
                         disabled(2)"
        ::= { ipeCfgPortNe2Entry 4 }
    
    -- 1.3.6.1.4.1.119.2.3.69.203.507.5.3.15.4.1.5
    ipeCfgPortNe2Speed OBJECT-TYPE
        SYNTAX      INTEGER { speed9600(9600), speed19200(19200) }
        ACCESS      read-only
        STATUS      mandatory
        DESCRIPTION
            "NE2 port baud rate.
             value range:9600bps(9600)
                         19200bps(19200)
             The ppp function is restarted when setting it."
        ::= { ipeCfgPortNe2Entry 5 }
    
    -- 1.3.6.1.4.1.119.2.3.69.203.507.5.3.15.4.1.6
    ipeCfgPortNe2NeighborMibEnable OBJECT-TYPE
        SYNTAX      INTEGER { enabled(1), disabled(2) }
        ACCESS      read-only
        STATUS      mandatory
        DESCRIPTION
            "NE2 port neighbor detection enable.
             value range:enabled(1)
                         disabled(2)
             The ppp function is restarted when setting it."
        ::= { ipeCfgPortNe2Entry 6 }
    
    -- 1.3.6.1.4.1.119.2.3.69.203.507.5.3.15.5
    ipeCfgPortE1Table OBJECT-TYPE
        SYNTAX      SEQUENCE OF IpeCfgPortE1Entry
        ACCESS      not-accessible
        STATUS      mandatory
        DESCRIPTION
            "E1 port set up information table."
        ::= { ipeCfgPortGroup 5 }
    
    -- 1.3.6.1.4.1.119.2.3.69.203.507.5.3.15.5.1
    ipeCfgPortE1Entry OBJECT-TYPE
        SYNTAX      IpeCfgPortE1Entry
        ACCESS      not-accessible
        STATUS      mandatory
        DESCRIPTION
            "entry of  E1 port set up information table."
        INDEX       { ipeCfgPortE1NEAddress, ipeCfgPortE1IfIndex }
        ::= { ipeCfgPortE1Table 1 }
    
    IpeCfgPortE1Entry ::= SEQUENCE {
        ipeCfgPortE1IfIndex         InterfaceIndex,
        ipeCfgPortE1NEAddress       IpAddress,
        ipeCfgPortE1Enable          INTEGER,
        ipeCfgPortE1ChannelNumber   INTEGER
    }
    
    -- 1.3.6.1.4.1.119.2.3.69.203.507.5.3.15.5.1.1
    ipeCfgPortE1IfIndex OBJECT-TYPE
        SYNTAX      InterfaceIndex
        ACCESS      not-accessible
        STATUS      mandatory
        DESCRIPTION
            "Index of table."
        ::= { ipeCfgPortE1Entry 1 }
    
    -- 1.3.6.1.4.1.119.2.3.69.203.507.5.3.15.5.1.2
    ipeCfgPortE1NEAddress OBJECT-TYPE
        SYNTAX      IpAddress
        ACCESS      not-accessible
        STATUS      mandatory
        DESCRIPTION
            ""
        ::= { ipeCfgPortE1Entry 2 }
    
    -- 1.3.6.1.4.1.119.2.3.69.203.507.5.3.15.5.1.3
    ipeCfgPortE1Enable OBJECT-TYPE
        SYNTAX      INTEGER { enabled(1), disabled(2) }
        ACCESS      read-only
        STATUS      mandatory
        DESCRIPTION
            "Effective/invalid setting of E1 port.
             value range: enabled(1)
                         disabled(2)"
        ::= { ipeCfgPortE1Entry 3 }
    
    -- 1.3.6.1.4.1.119.2.3.69.203.507.5.3.15.5.1.4
    ipeCfgPortE1ChannelNumber OBJECT-TYPE
        SYNTAX      INTEGER (1..16)
        ACCESS      read-only
        STATUS      mandatory
        DESCRIPTION
            "Use channel of E1 port.
             value range:1 to 16"
        ::= { ipeCfgPortE1Entry 4 }
    
    -- 1.3.6.1.4.1.119.2.3.69.203.507.5.3.15.6
    ipeCfgPortInbandTable OBJECT-TYPE
        SYNTAX      SEQUENCE OF IpeCfgPortInbandEntry
        ACCESS      not-accessible
        STATUS      mandatory
        DESCRIPTION
            "InBand Management VLAN port set up information table."
        ::= { ipeCfgPortGroup 6 }
    
    -- 1.3.6.1.4.1.119.2.3.69.203.507.5.3.15.6.1
    ipeCfgPortInbandEntry OBJECT-TYPE
        SYNTAX      IpeCfgPortInbandEntry
        ACCESS      not-accessible
        STATUS      mandatory
        DESCRIPTION
            "entry of  INBAND Management VLAN port set up information table."
        INDEX       { ipeCfgPortInbandNEAddress, ipeCfgPortInbandIfIndex }
        ::= { ipeCfgPortInbandTable 1 }
    
    IpeCfgPortInbandEntry ::= SEQUENCE {
        ipeCfgPortInbandIfIndex     InterfaceIndex,
        ipeCfgPortInbandNEAddress   IpAddress,
        ipeCfgPortInbandIpAddress   IpAddress,
        ipeCfgPortInbandNetMask     IpAddress,
        ipeCfgPortInbandEnable      INTEGER,
        ipeCfgPortInbandVlanId      INTEGER,
        ipeCfgPortInbandMtu         INTEGER,
        ipeCfgPortInbandCos         INTEGER
    }
    
    -- 1.3.6.1.4.1.119.2.3.69.203.507.5.3.15.6.1.1
    ipeCfgPortInbandIfIndex OBJECT-TYPE
        SYNTAX      InterfaceIndex
        ACCESS      not-accessible
        STATUS      mandatory
        DESCRIPTION
            "Index of table."
        ::= { ipeCfgPortInbandEntry 1 }
    
    -- 1.3.6.1.4.1.119.2.3.69.203.507.5.3.15.6.1.2
    ipeCfgPortInbandNEAddress OBJECT-TYPE
        SYNTAX      IpAddress
        ACCESS      not-accessible
        STATUS      mandatory
        DESCRIPTION
            ""
        ::= { ipeCfgPortInbandEntry 2 }
    
    -- 1.3.6.1.4.1.119.2.3.69.203.507.5.3.15.6.1.3
    ipeCfgPortInbandIpAddress OBJECT-TYPE
        SYNTAX      IpAddress
        ACCESS      read-only
        STATUS      obsolete
        DESCRIPTION
            "IPaddress of INBAND Management VLAN port.
             It makes an error of the Internet Protocol address setting that
             overlaps in the port in the device.
             The object port and the range of the value are described as
             follows.
             Object port: Lct, InbandMngVLAN1-16, Bridge1-20, NE2
             Value range: 0x00000000 - 0xdfffffff(0.0.0.0 - 223.255.255.255)
             The relation is not in the state and the number of Branch of
             interfaces and the Internet Protocol address repetition check is
             checked.
    
             When 0.0.0.0 is set to ipeCfgPortInbandIpAddress, it becomes an
             Internet Protocol address deletion."
        ::= { ipeCfgPortInbandEntry 3 }
    
    -- 1.3.6.1.4.1.119.2.3.69.203.507.5.3.15.6.1.4
    ipeCfgPortInbandNetMask OBJECT-TYPE
        SYNTAX      IpAddress
        ACCESS      read-only
        STATUS      obsolete
        DESCRIPTION
            "Subnet mask of INBAND Management VLAN port.
             When it isn't proper as subnetmask, it'll be an error.
             Value range:0x00000000 - 0xfffffffc(0 - 30bit)"
        ::= { ipeCfgPortInbandEntry 4 }
    
    -- 1.3.6.1.4.1.119.2.3.69.203.507.5.3.15.6.1.5
    ipeCfgPortInbandEnable OBJECT-TYPE
        SYNTAX      INTEGER { enabled(1), disabled(2) }
        ACCESS      read-only
        STATUS      mandatory
        DESCRIPTION
            "Effective/invalid setting of INBAND Management VLAN port.
             value range: enabled(1)
                         disabled(2)"
        ::= { ipeCfgPortInbandEntry 5 }
    
    -- 1.3.6.1.4.1.119.2.3.69.203.507.5.3.15.6.1.6
    ipeCfgPortInbandVlanId OBJECT-TYPE
        SYNTAX      INTEGER (1..4094)
        ACCESS      read-only
        STATUS      mandatory
        DESCRIPTION
            "VLAN ID of INBAND Management VLAN port.
             value range:1 to 4094"
        ::= { ipeCfgPortInbandEntry 6 }
    
    -- 1.3.6.1.4.1.119.2.3.69.203.507.5.3.15.6.1.7
    ipeCfgPortInbandMtu OBJECT-TYPE
        SYNTAX      INTEGER (256..1500)
        ACCESS      read-only
        STATUS      obsolete
        DESCRIPTION
            "MTU value of INBAND Management VLAN port.
             value range:256 to 1500"
        ::= { ipeCfgPortInbandEntry 7 }
    
    -- 1.3.6.1.4.1.119.2.3.69.203.507.5.3.15.6.1.8
    ipeCfgPortInbandCos OBJECT-TYPE
        SYNTAX      INTEGER (0..7)
        ACCESS      read-only
        STATUS      mandatory
        DESCRIPTION
            "CoS value of INBAND Management VLAN port"
        DEFVAL      { 7 }
        ::= { ipeCfgPortInbandEntry 8 }
    
    -- 1.3.6.1.4.1.119.2.3.69.203.507.5.3.15.7
    ipeCfgPortMainEtherTable OBJECT-TYPE
        SYNTAX      SEQUENCE OF IpeCfgPortMainEtherEntry
        ACCESS      not-accessible
        STATUS      mandatory
        DESCRIPTION
            "Main traffic ether port set up information table."
        ::= { ipeCfgPortGroup 7 }
    
    -- 1.3.6.1.4.1.119.2.3.69.203.507.5.3.15.7.1
    ipeCfgPortMainEtherEntry OBJECT-TYPE
        SYNTAX      IpeCfgPortMainEtherEntry
        ACCESS      not-accessible
        STATUS      mandatory
        DESCRIPTION
            "entry of main traffic ether port set up information table."
        INDEX       { ipeCfgPortMainEtherNEAddress, ipeCfgPortMainEtherIfIndex }
        ::= { ipeCfgPortMainEtherTable 1 }
    
    IpeCfgPortMainEtherEntry ::= SEQUENCE {
        ipeCfgPortMainEtherIfIndex      InterfaceIndex,
        ipeCfgPortMainEtherNEAddress    IpAddress,
        ipeCfgPortMainEtherLldpMode     INTEGER
    }
    
    -- 1.3.6.1.4.1.119.2.3.69.203.507.5.3.15.7.1.1
    ipeCfgPortMainEtherIfIndex OBJECT-TYPE
        SYNTAX      InterfaceIndex
        ACCESS      not-accessible
        STATUS      mandatory
        DESCRIPTION
            "Index of table.
             Ifindex of main traffic ether port."
        ::= { ipeCfgPortMainEtherEntry 1 }
    
    -- 1.3.6.1.4.1.119.2.3.69.203.507.5.3.15.7.1.2
    ipeCfgPortMainEtherNEAddress OBJECT-TYPE
        SYNTAX      IpAddress
        ACCESS      not-accessible
        STATUS      mandatory
        DESCRIPTION
            "reserved."
        ::= { ipeCfgPortMainEtherEntry 2 }
    
    -- 1.3.6.1.4.1.119.2.3.69.203.507.5.3.15.7.1.3
    ipeCfgPortMainEtherLldpMode OBJECT-TYPE
        SYNTAX      INTEGER { invalid(0), standardMode(1),
                        proprietaryMode(2) }
        ACCESS      read-only
        STATUS      mandatory
        DESCRIPTION
            "Switch to select MAC address of LLDP Frame.
    
             standardMode    : MAC address of LLDP Frame is 01-80-C2-00-00-0E.
             proprietaryMode : MAC address of LLDP Frame is configured in
                               ipeCfgLldpProprietaryModeMacAddress."
        DEFVAL      { standardMode }
        ::= { ipeCfgPortMainEtherEntry 3 }
    
    -- 1.3.6.1.4.1.119.2.3.69.203.507.5.3.16
    ipeCfgBridgeGroup OBJECT IDENTIFIER
        ::= { ipeConfigurationGroup 16 }
    
    -- 1.3.6.1.4.1.119.2.3.69.203.507.5.3.16.1
    ipeCfgBridgeTable OBJECT-TYPE
        SYNTAX      SEQUENCE OF IpeCfgBridgeEntry
        ACCESS      not-accessible
        STATUS      mandatory
        DESCRIPTION
            "Bridge set up information table."
        ::= { ipeCfgBridgeGroup 1 }
    
    -- 1.3.6.1.4.1.119.2.3.69.203.507.5.3.16.1.1
    ipeCfgBridgeEntry OBJECT-TYPE
        SYNTAX      IpeCfgBridgeEntry
        ACCESS      not-accessible
        STATUS      mandatory
        DESCRIPTION
            "entry of  Bridge set up information table."
        INDEX       { ipeCfgBridgeNEAddress, ipeCfgBridgeIndex }
        ::= { ipeCfgBridgeTable 1 }
    
    IpeCfgBridgeEntry ::= SEQUENCE {
        ipeCfgBridgeIndex                       INTEGER,
        ipeCfgBridgeNEAddress                   IpAddress,
        ipeCfgBridgeIpAddress                   IpAddress,
        ipeCfgBridgeNetMask                     IpAddress,
        ipeCfgBridgeMtu                         INTEGER,
        ipeCfgBridgeLinkLocalAddress            Ipv6Address,
        ipeCfgBridgeLinkLocalAddressOrigin      INTEGER,
        ipeCfgBridgeGlobalAddress               Ipv6Address,
        ipeCfgBridgeGlobalAddressOrigin         INTEGER,
        ipeCfgBridgeGlobalAddressPrefixLength   InetAddressPrefixLength,
        ipeCfgBridgeIpStackMode                 INTEGER,
        ipeCfgBridgeSendRouterAdvertisement     INTEGER,
        ipeCfgBridgeRADefaultLifeTime           INTEGER,
        ipeCfgBridgeReceiveIcmpRedirects        INTEGER
    }
    
    -- 1.3.6.1.4.1.119.2.3.69.203.507.5.3.16.1.1.1
    ipeCfgBridgeIndex OBJECT-TYPE
        SYNTAX      INTEGER (1..20)
        ACCESS      not-accessible
        STATUS      mandatory
        DESCRIPTION
            "Index of table."
        ::= { ipeCfgBridgeEntry 1 }
    
    -- 1.3.6.1.4.1.119.2.3.69.203.507.5.3.16.1.1.2
    ipeCfgBridgeNEAddress OBJECT-TYPE
        SYNTAX      IpAddress
        ACCESS      not-accessible
        STATUS      mandatory
        DESCRIPTION
            ""
        ::= { ipeCfgBridgeEntry 2 }
    
    -- 1.3.6.1.4.1.119.2.3.69.203.507.5.3.16.1.1.3
    ipeCfgBridgeIpAddress OBJECT-TYPE
        SYNTAX      IpAddress
        ACCESS      read-only
        STATUS      mandatory
        DESCRIPTION
            "IPAddress set to bridge.
             Value range:0x00000000 - 0xdfffffff(0.0.0.0 - 223.255.255.255)
    
             It makes an error of the Internet Protocol address setting that
             overlaps in the port in the device.
             It becomes the following about the port of the Internet Protocol
             address repetition check object.
             Object port: Lct, InbandMngVLAN1-16, Bridge1-Bridge20, NE2
             The relation is not in the state and the number of Branch of
             interfaces and the Internet Protocol address repetition check is
             checked.
    
             There can not be relation and it sets, and it refer the number of
             branch.
             When 0.0.0.0 is set to ipeCfgBridgeIpAddress, it becomes an
             Internet Protocol address deletion."
        ::= { ipeCfgBridgeEntry 3 }
    
    -- 1.3.6.1.4.1.119.2.3.69.203.507.5.3.16.1.1.4
    ipeCfgBridgeNetMask OBJECT-TYPE
        SYNTAX      IpAddress
        ACCESS      read-only
        STATUS      mandatory
        DESCRIPTION
            "Netmask set to bridge.
             When it isn't proper as subnetmask, it'll be an error.
             Value range:0x00000000 - 0xfffffffc(0 - 30bit)
    
             There can not be relation and it sets, and it refer the number of
             branch."
        ::= { ipeCfgBridgeEntry 4 }
    
    -- 1.3.6.1.4.1.119.2.3.69.203.507.5.3.16.1.1.5
    ipeCfgBridgeMtu OBJECT-TYPE
        SYNTAX      INTEGER (256..1500)
        ACCESS      read-only
        STATUS      mandatory
        DESCRIPTION
            "MTU value of bridge.
             value range:256 to 1500
    
             There can not be relation and it sets, and it refer the number of
             branch."
        ::= { ipeCfgBridgeEntry 5 }
    
    -- 1.3.6.1.4.1.119.2.3.69.203.507.5.3.16.1.1.6
    ipeCfgBridgeLinkLocalAddress OBJECT-TYPE
        SYNTAX      Ipv6Address
        ACCESS      read-only
        STATUS      mandatory
        DESCRIPTION
            "IPv6 Link-local Address set to bridge."
        ::= { ipeCfgBridgeEntry 6 }
    
    -- 1.3.6.1.4.1.119.2.3.69.203.507.5.3.16.1.1.7
    ipeCfgBridgeLinkLocalAddressOrigin OBJECT-TYPE
        SYNTAX      INTEGER { invalid(0), manual(1), linklayer(2) }
        ACCESS      read-only
        STATUS      mandatory
        DESCRIPTION
            "The origin of the address.
             manual(1) indicates that the address was manually
             configured to a specified address, e.g., by user
             configuration.
    
             linklayer(2) indicates the address to be created
             by IPv6 stateless address auto-configuration."
        DEFVAL      { linklayer }
        ::= { ipeCfgBridgeEntry 7 }
    
    -- 1.3.6.1.4.1.119.2.3.69.203.507.5.3.16.1.1.8
    ipeCfgBridgeGlobalAddress OBJECT-TYPE
        SYNTAX      Ipv6Address
        ACCESS      read-only
        STATUS      mandatory
        DESCRIPTION
            "The IPv6 global address of this interface.
             The following are not valid addresses:
                ::1/128 IPv6 Loopback
                FE80::/10 Link local
                FF00::/8 IPv6 Multicasts"
        ::= { ipeCfgBridgeEntry 8 }
    
    -- 1.3.6.1.4.1.119.2.3.69.203.507.5.3.16.1.1.9
    ipeCfgBridgeGlobalAddressOrigin OBJECT-TYPE
        SYNTAX      INTEGER { invalid(0), manual(1), linklayer(4) }
        ACCESS      read-only
        STATUS      mandatory
        DESCRIPTION
            "The origin of the address.
             manual(1) indicates that the address was manually
                     configured to a specified address, e.g., by user
                     configuration.
    
             linklayer(4) indicates an address created based on the
                     prefix received from Router Advertisement and this
                     interface is considered as Host interface."
        DEFVAL      { linklayer }
        ::= { ipeCfgBridgeEntry 9 }
    
    -- 1.3.6.1.4.1.119.2.3.69.203.507.5.3.16.1.1.10
    ipeCfgBridgeGlobalAddressPrefixLength OBJECT-TYPE
        SYNTAX      InetAddressPrefixLength
        ACCESS      read-only
        STATUS      mandatory
        DESCRIPTION
            "The prefix length of Global Address."
        ::= { ipeCfgBridgeEntry 10 }
    
    -- 1.3.6.1.4.1.119.2.3.69.203.507.5.3.16.1.1.11
    ipeCfgBridgeIpStackMode OBJECT-TYPE
        SYNTAX      INTEGER { ipv4(1), ipv6(2), dual(3) }
        ACCESS      read-only
        STATUS      mandatory
        DESCRIPTION
            "Indicate IP Stack mode of this interface.
    
             ipv4 : Enable IPv4 support on this interface.
             ipv6 : Enable IPv6 support on this interface.
             dual : Enable IPv4 and IPv6 support on this interface.
    
             Note that ipeCfgBridgeIpStackMode: ipv4(1) and
             ipeSysIpv4DropFilterEnable: enable(2) cannot be set for the
             establishment of IPv4 communication."
        ::= { ipeCfgBridgeEntry 11 }
    
    -- 1.3.6.1.4.1.119.2.3.69.203.507.5.3.16.1.1.12
    ipeCfgBridgeSendRouterAdvertisement OBJECT-TYPE
        SYNTAX      INTEGER { invalid(0), true(1), false(2) }
        ACCESS      read-only
        STATUS      mandatory
        DESCRIPTION
            "A flag indicating whether the router sends periodic
             router advertisements and responds to router solicitations
             on this interface."
        ::= { ipeCfgBridgeEntry 12 }
    
    -- 1.3.6.1.4.1.119.2.3.69.203.507.5.3.16.1.1.13
    ipeCfgBridgeRADefaultLifeTime OBJECT-TYPE
        SYNTAX      INTEGER (0 | 600..9000)
        ACCESS      read-only
        STATUS      mandatory
        DESCRIPTION
            "The value to be placed in the router lifetime field of
             router advertisements sent from this interface.
             This value must be either 0 or between
             ipv6RouterAdvertMaxInterval and
             9000 seconds.
    
             A value of zero indicates that the router is not to be used
             as a default router.
    
             The default is 3 * ipv6RouterAdvertMaxInterval."
        ::= { ipeCfgBridgeEntry 13 }
    
    -- 1.3.6.1.4.1.119.2.3.69.203.507.5.3.16.1.1.14
    ipeCfgBridgeReceiveIcmpRedirects OBJECT-TYPE
        SYNTAX      INTEGER { invalid(0), true(1), false(2) }
        ACCESS      read-only
        STATUS      mandatory
        DESCRIPTION
            "The true/false value to process received ICMP Redirect
             messages from this bridge.
             For router, this object will always be false as router
             does not process Redirects."
        ::= { ipeCfgBridgeEntry 14 }
    
    -- 1.3.6.1.4.1.119.2.3.69.203.507.5.3.16.2
    ipeCfgBridgePortTable OBJECT-TYPE
        SYNTAX      SEQUENCE OF IpeCfgBridgePortEntry
        ACCESS      not-accessible
        STATUS      mandatory
        DESCRIPTION
            "Bridge set up information table."
        ::= { ipeCfgBridgeGroup 2 }
    
    -- 1.3.6.1.4.1.119.2.3.69.203.507.5.3.16.2.1
    ipeCfgBridgePortEntry OBJECT-TYPE
        SYNTAX      IpeCfgBridgePortEntry
        ACCESS      not-accessible
        STATUS      mandatory
        DESCRIPTION
            "entry of  Bridge set up information table."
        INDEX       { ipeCfgBridgePortNEAddress, ipeCfgBridgePortIfIndex }
        ::= { ipeCfgBridgePortTable 1 }
    
    IpeCfgBridgePortEntry ::= SEQUENCE {
        ipeCfgBridgePortIfIndex         InterfaceIndex,
        ipeCfgBridgePortNEAddress       IpAddress,
        ipeCfgBridgePortBridgeIndex     INTEGER
    }
    
    -- 1.3.6.1.4.1.119.2.3.69.203.507.5.3.16.2.1.1
    ipeCfgBridgePortIfIndex OBJECT-TYPE
        SYNTAX      InterfaceIndex
        ACCESS      not-accessible
        STATUS      mandatory
        DESCRIPTION
            "The interface identified by a particular value of this index is
             the same interface as identified by the same value of ifIndex.
             Valid Value(NMS,NE1,E1,RADIO00-10,InbandMngVLAN1-16)"
        ::= { ipeCfgBridgePortEntry 1 }
    
    -- 1.3.6.1.4.1.119.2.3.69.203.507.5.3.16.2.1.2
    ipeCfgBridgePortNEAddress OBJECT-TYPE
        SYNTAX      IpAddress
        ACCESS      not-accessible
        STATUS      mandatory
        DESCRIPTION
            ""
        ::= { ipeCfgBridgePortEntry 2 }
    
    -- 1.3.6.1.4.1.119.2.3.69.203.507.5.3.16.2.1.3
    ipeCfgBridgePortBridgeIndex OBJECT-TYPE
        SYNTAX      INTEGER (0..20)
        ACCESS      read-only
        STATUS      mandatory
        DESCRIPTION
            "Index value of bridge."
        ::= { ipeCfgBridgePortEntry 3 }
    
    -- 1.3.6.1.4.1.119.2.3.69.203.507.5.3.17
    ipeCfgPripGroup OBJECT IDENTIFIER
        ::= { ipeConfigurationGroup 17 }
    
    -- 1.3.6.1.4.1.119.2.3.69.203.507.5.3.17.1
    ipeCfgPripTable OBJECT-TYPE
        SYNTAX      SEQUENCE OF IpeCfgPripEntry
        ACCESS      not-accessible
        STATUS      mandatory
        DESCRIPTION
            "PRIP set up information table."
        ::= { ipeCfgPripGroup 1 }
    
    -- 1.3.6.1.4.1.119.2.3.69.203.507.5.3.17.1.1
    ipeCfgPripEntry OBJECT-TYPE
        SYNTAX      IpeCfgPripEntry
        ACCESS      not-accessible
        STATUS      mandatory
        DESCRIPTION
            "entry of PRIP set up information table."
        INDEX       { ipeCfgPripNEAddress, ipeCfgPripIndex }
        ::= { ipeCfgPripTable 1 }
    
    IpeCfgPripEntry ::= SEQUENCE {
        ipeCfgPripIndex         INTEGER,
        ipeCfgPripNEAddress     IpAddress,
        ipeCfgPripRouteEnable   INTEGER,
        ipeCfgPripUdpPort       INTEGER
    }
    
    -- 1.3.6.1.4.1.119.2.3.69.203.507.5.3.17.1.1.1
    ipeCfgPripIndex OBJECT-TYPE
        SYNTAX      INTEGER (1)
        ACCESS      not-accessible
        STATUS      mandatory
        DESCRIPTION
            "Index of this ipeCfgPripEntry.
             It's a fiexed value(= 1)."
        ::= { ipeCfgPripEntry 1 }
    
    -- 1.3.6.1.4.1.119.2.3.69.203.507.5.3.17.1.1.2
    ipeCfgPripNEAddress OBJECT-TYPE
        SYNTAX      IpAddress
        ACCESS      not-accessible
        STATUS      mandatory
        DESCRIPTION
            ""
        ::= { ipeCfgPripEntry 2 }
    
    -- 1.3.6.1.4.1.119.2.3.69.203.507.5.3.17.1.1.3
    ipeCfgPripRouteEnable OBJECT-TYPE
        SYNTAX      INTEGER { invalid(0), enabled(1), disabled(2) }
        ACCESS      read-only
        STATUS      mandatory
        DESCRIPTION
            "Enable or disables PRIP.
    
             enabled(1):PRIP is enabled.
             disabled(2):PRIP is disabled."
        ::= { ipeCfgPripEntry 3 }
    
    -- 1.3.6.1.4.1.119.2.3.69.203.507.5.3.17.1.1.4
    ipeCfgPripUdpPort OBJECT-TYPE
        SYNTAX      INTEGER { ripdefaultport(520), pripdefaultport(8520) }
        ACCESS      read-only
        STATUS      mandatory
        DESCRIPTION
            "Setting of UDP port number used with PRIP.
    
             Either of 8520 or 520 is set.
    
             This setting is valid since PRIP will start next time."
        ::= { ipeCfgPripEntry 4 }
    
    -- 1.3.6.1.4.1.119.2.3.69.203.507.5.3.17.2
    ipeCfgPripPortTable OBJECT-TYPE
        SYNTAX      SEQUENCE OF IpeCfgPripPortEntry
        ACCESS      not-accessible
        STATUS      mandatory
        DESCRIPTION
            "PRIP set up information table.(per port)"
        ::= { ipeCfgPripGroup 2 }
    
    -- 1.3.6.1.4.1.119.2.3.69.203.507.5.3.17.2.1
    ipeCfgPripPortEntry OBJECT-TYPE
        SYNTAX      IpeCfgPripPortEntry
        ACCESS      not-accessible
        STATUS      mandatory
        DESCRIPTION
            "entry of PRIP set up information table.(per port)"
        INDEX       { ipeCfgPripPortNEAddress, ipeCfgPripPortIfIndex }
        ::= { ipeCfgPripPortTable 1 }
    
    IpeCfgPripPortEntry ::= SEQUENCE {
        ipeCfgPripPortIfIndex               InterfaceIndex,
        ipeCfgPripPortNEAddress             IpAddress,
        ipeCfgPripPortEnable                INTEGER,
        ipeCfgPripPortPropagateNetEnable    INTEGER
    }
    
    -- 1.3.6.1.4.1.119.2.3.69.203.507.5.3.17.2.1.1
    ipeCfgPripPortIfIndex OBJECT-TYPE
        SYNTAX      InterfaceIndex
        ACCESS      not-accessible
        STATUS      mandatory
        DESCRIPTION
            "Index of table."
        ::= { ipeCfgPripPortEntry 1 }
    
    -- 1.3.6.1.4.1.119.2.3.69.203.507.5.3.17.2.1.2
    ipeCfgPripPortNEAddress OBJECT-TYPE
        SYNTAX      IpAddress
        ACCESS      not-accessible
        STATUS      mandatory
        DESCRIPTION
            ""
        ::= { ipeCfgPripPortEntry 2 }
    
    -- 1.3.6.1.4.1.119.2.3.69.203.507.5.3.17.2.1.3
    ipeCfgPripPortEnable OBJECT-TYPE
        SYNTAX      INTEGER { invalid(0), enabled(1), disabled(2) }
        ACCESS      read-only
        STATUS      mandatory
        DESCRIPTION
            "Setting of some port when PRIP will be enabled.
    
             enabled(1)  : this port is enabled.
             disabled(2) : this port is disable."
        ::= { ipeCfgPripPortEntry 3 }
    
    -- 1.3.6.1.4.1.119.2.3.69.203.507.5.3.17.2.1.4
    ipeCfgPripPortPropagateNetEnable OBJECT-TYPE
        SYNTAX      INTEGER { invalid(0), enabled(1), disabled(2) }
        ACCESS      read-only
        STATUS      mandatory
        DESCRIPTION
            "Propagate setting for neighbor NE.
    
             enabled(1)  : this port is propagated.
             disabled(2) : this port is not propagated.
                           (Do not register in the RIP route.)"
        ::= { ipeCfgPripPortEntry 4 }
    
    -- 1.3.6.1.4.1.119.2.3.69.203.507.5.3.18
    ipeCfgNaptGroup OBJECT IDENTIFIER
        ::= { ipeConfigurationGroup 18 }
    
    -- 1.3.6.1.4.1.119.2.3.69.203.507.5.3.18.1
    ipeCfgNaptTable OBJECT-TYPE
        SYNTAX      SEQUENCE OF IpeCfgNaptEntry
        ACCESS      not-accessible
        STATUS      mandatory
        DESCRIPTION
            "NAPT set up information table."
        ::= { ipeCfgNaptGroup 1 }
    
    -- 1.3.6.1.4.1.119.2.3.69.203.507.5.3.18.1.1
    ipeCfgNaptEntry OBJECT-TYPE
        SYNTAX      IpeCfgNaptEntry
        ACCESS      not-accessible
        STATUS      mandatory
        DESCRIPTION
            "entry of  NAPT set up information table."
        INDEX       { ipeCfgNaptNEAddress, ipeCfgNaptIndex }
        ::= { ipeCfgNaptTable 1 }
    
    IpeCfgNaptEntry ::= SEQUENCE {
        ipeCfgNaptIndex         INTEGER,
        ipeCfgNaptNEAddress     IpAddress,
        ipeCfgNaptEnable        INTEGER
    }
    
    -- 1.3.6.1.4.1.119.2.3.69.203.507.5.3.18.1.1.1
    ipeCfgNaptIndex OBJECT-TYPE
        SYNTAX      INTEGER (1)
        ACCESS      not-accessible
        STATUS      mandatory
        DESCRIPTION
            "Index of this ipeCfgNaptEntry.
             It's a fixed value(=1)."
        ::= { ipeCfgNaptEntry 1 }
    
    -- 1.3.6.1.4.1.119.2.3.69.203.507.5.3.18.1.1.2
    ipeCfgNaptNEAddress OBJECT-TYPE
        SYNTAX      IpAddress
        ACCESS      not-accessible
        STATUS      mandatory
        DESCRIPTION
            ""
        ::= { ipeCfgNaptEntry 2 }
    
    -- 1.3.6.1.4.1.119.2.3.69.203.507.5.3.18.1.1.3
    ipeCfgNaptEnable OBJECT-TYPE
        SYNTAX      INTEGER { enabled(1), disabled(2) }
        ACCESS      read-only
        STATUS      mandatory
        DESCRIPTION
            "Address translation invalid effective/setting by NAPT.
             value range: enabled
                         disabled"
        ::= { ipeCfgNaptEntry 3 }
    
    -- 1.3.6.1.4.1.119.2.3.69.203.507.5.3.19
    ipeCfgStaticRouteGroup OBJECT IDENTIFIER
        ::= { ipeConfigurationGroup 19 }
    
    -- 1.3.6.1.4.1.119.2.3.69.203.507.5.3.19.1
    ipeCfgStaticRouteTable OBJECT-TYPE
        SYNTAX      SEQUENCE OF IpeCfgStaticRouteEntry
        ACCESS      not-accessible
        STATUS      mandatory
        DESCRIPTION
            "Static Routing set up information table."
        ::= { ipeCfgStaticRouteGroup 1 }
    
    -- 1.3.6.1.4.1.119.2.3.69.203.507.5.3.19.1.1
    ipeCfgStaticRouteEntry OBJECT-TYPE
        SYNTAX      IpeCfgStaticRouteEntry
        ACCESS      not-accessible
        STATUS      mandatory
        DESCRIPTION
            "entry of  Static Routing set up information table."
        INDEX       { ipeCfgRouteNEAddress, ipeCfgRouteIndex }
        ::= { ipeCfgStaticRouteTable 1 }
    
    IpeCfgStaticRouteEntry ::= SEQUENCE {
        ipeCfgRouteIndex        INTEGER,
        ipeCfgRouteNEAddress    IpAddress,
        ipeCfgRouteDest         IpAddress,
        ipeCfgRouteMask         IpAddress,
        ipeCfgRouteNextHop      IpAddress,
        ipeCfgRouteRowStatus    RowStatus
    }
    
    -- 1.3.6.1.4.1.119.2.3.69.203.507.5.3.19.1.1.1
    ipeCfgRouteIndex OBJECT-TYPE
        SYNTAX      INTEGER (1..128)
        ACCESS      not-accessible
        STATUS      mandatory
        DESCRIPTION
            "Index of table(1 to 128)."
        ::= { ipeCfgStaticRouteEntry 1 }
    
    -- 1.3.6.1.4.1.119.2.3.69.203.507.5.3.19.1.1.2
    ipeCfgRouteNEAddress OBJECT-TYPE
        SYNTAX      IpAddress
        ACCESS      not-accessible
        STATUS      mandatory
        DESCRIPTION
            ""
        ::= { ipeCfgStaticRouteEntry 2 }
    
    -- 1.3.6.1.4.1.119.2.3.69.203.507.5.3.19.1.1.3
    ipeCfgRouteDest OBJECT-TYPE
        SYNTAX      IpAddress
        ACCESS      read-only
        STATUS      mandatory
        DESCRIPTION
            "Static routing object destination address.
             When masking in ipeCfgRouteMask, the host address part has to be
             a zero, if any.
             Value range:0x00000000-0xdfffffff(0.0.0.0-223.255.255.255)
             The value acquisition when unsetting it returns NoSuchObject."
        ::= { ipeCfgStaticRouteEntry 3 }
    
    -- 1.3.6.1.4.1.119.2.3.69.203.507.5.3.19.1.1.4
    ipeCfgRouteMask OBJECT-TYPE
        SYNTAX      IpAddress
        ACCESS      read-only
        STATUS      mandatory
        DESCRIPTION
            "Static routing object subnet mask.
             When it isn't proper as subnetmask, it'll be an error.
             Value range:0x00000000-0xffffffff(0-32bit)
             Only when ipeCfgRouteDest is 0, 0bit is allowed.
             The value acquisition when unsetting it returns NoSuchObject."
        ::= { ipeCfgStaticRouteEntry 4 }
    
    -- 1.3.6.1.4.1.119.2.3.69.203.507.5.3.19.1.1.5
    ipeCfgRouteNextHop OBJECT-TYPE
        SYNTAX      IpAddress
        ACCESS      read-only
        STATUS      mandatory
        DESCRIPTION
            "Static routing object gateway address.
             Value range:0x00000001 - 0xdfffffff(0.0.0.1 - 223.255.255.255)
             The value acquisition when unsetting it returns NoSuchObject."
        ::= { ipeCfgStaticRouteEntry 5 }
    
    -- 1.3.6.1.4.1.119.2.3.69.203.507.5.3.19.1.1.6
    ipeCfgRouteRowStatus OBJECT-TYPE
        SYNTAX      RowStatus { active(1), createAndGo(4), destroy(6) }
        ACCESS      read-only
        STATUS      mandatory
        DESCRIPTION
            "This RowStatus has a status only 'active(1)'.
    
             1) creating a entry
             When you make a new entry, you must SET objects indicated below.
             * ipeCfgRouteDest
             * ipeCfgRouteMask
             * ipeCfgRouteNextHop
             * ipeCfgRouteRowStatus <- createAndGo(4)
    
             2) modifing a entry
             When you make a existing entry, you must SET objects indicated
             below.
             * ipeCfgRouteDest
             * ipeCfgRouteMask
             * ipeCfgRouteNextHop
    
             3) deleting a entry
             When you SET a destroy(6) to ipeCfgRouteRowStatus, the entry is
             destroyed.
             * ipeCfgRouteRowStatus <- destory(6)"
        ::= { ipeCfgStaticRouteEntry 6 }
    
    -- 1.3.6.1.4.1.119.2.3.69.203.507.5.3.19.2
    ipeCfgV6StaticRouteTable OBJECT-TYPE
        SYNTAX      SEQUENCE OF IpeCfgV6StaticRouteEntry
        ACCESS      not-accessible
        STATUS      mandatory
        DESCRIPTION
            "IPv6 Static Routing set up information table."
        ::= { ipeCfgStaticRouteGroup 2 }
    
    -- 1.3.6.1.4.1.119.2.3.69.203.507.5.3.19.2.1
    ipeCfgV6StaticRouteEntry OBJECT-TYPE
        SYNTAX      IpeCfgV6StaticRouteEntry
        ACCESS      not-accessible
        STATUS      mandatory
        DESCRIPTION
            "entry of Static Routing set up information table."
        INDEX       { ipeCfgV6RouteNEAddress, ipeCfgV6RouteIndex }
        ::= { ipeCfgV6StaticRouteTable 1 }
    
    IpeCfgV6StaticRouteEntry ::= SEQUENCE {
        ipeCfgV6RouteIndex              INTEGER,
        ipeCfgV6RouteNEAddress          IpAddress,
        ipeCfgV6RouteDest               Ipv6Address,
        ipeCfgV6RoutePrefixLength       InetAddressPrefixLength,
        ipeCfgV6RouteNextHop            Ipv6Address,
        ipeCfgV6RouteNextHopIfIndex     INTEGER,
        ipeCfgV6RouteRowStatus          RowStatus
    }
    
    -- 1.3.6.1.4.1.119.2.3.69.203.507.5.3.19.2.1.1
    ipeCfgV6RouteIndex OBJECT-TYPE
        SYNTAX      INTEGER (1..128)
        ACCESS      not-accessible
        STATUS      mandatory
        DESCRIPTION
            "Index of table(1 to 128)."
        ::= { ipeCfgV6StaticRouteEntry 1 }
    
    -- 1.3.6.1.4.1.119.2.3.69.203.507.5.3.19.2.1.2
    ipeCfgV6RouteNEAddress OBJECT-TYPE
        SYNTAX      IpAddress
        ACCESS      not-accessible
        STATUS      mandatory
        DESCRIPTION
            ""
        ::= { ipeCfgV6StaticRouteEntry 2 }
    
    -- 1.3.6.1.4.1.119.2.3.69.203.507.5.3.19.2.1.3
    ipeCfgV6RouteDest OBJECT-TYPE
        SYNTAX      Ipv6Address
        ACCESS      read-only
        STATUS      mandatory
        DESCRIPTION
            "Static routing object destination address.
             The value acquisition when unsetting it returns NoSuchObject."
        ::= { ipeCfgV6StaticRouteEntry 3 }
    
    -- 1.3.6.1.4.1.119.2.3.69.203.507.5.3.19.2.1.4
    ipeCfgV6RoutePrefixLength OBJECT-TYPE
        SYNTAX      InetAddressPrefixLength
        ACCESS      read-only
        STATUS      mandatory
        DESCRIPTION
            "Static routing object prefix length.
             When it isn't proper as prefix length, it'll be an error.
             Only when ipeCfgV6RouteDest is 0, 0bit is allowed.
             The value acquisition when unsetting it returns NoSuchObject."
        ::= { ipeCfgV6StaticRouteEntry 4 }
    
    -- 1.3.6.1.4.1.119.2.3.69.203.507.5.3.19.2.1.5
    ipeCfgV6RouteNextHop OBJECT-TYPE
        SYNTAX      Ipv6Address
        ACCESS      read-only
        STATUS      mandatory
        DESCRIPTION
            "Static routing object gateway address.
             The value acquisition when unsetting it returns NoSuchObject."
        ::= { ipeCfgV6StaticRouteEntry 5 }
    
    -- 1.3.6.1.4.1.119.2.3.69.203.507.5.3.19.2.1.6
    ipeCfgV6RouteNextHopIfIndex OBJECT-TYPE
        SYNTAX      INTEGER { any(0), bridge1(11), bridge2(12), bridge3(13),
                        bridge4(14), bridge5(15), bridge6(16), bridge7(17),
                        bridge8(18), bridge9(19), bridge10(20), bridge11(21),
                        bridge12(22), bridge13(23), bridge14(24),
                        bridge15(25), bridge16(26), bridge17(27),
                        bridge18(28), bridge19(29), bridge20(30) }
        ACCESS      read-only
        STATUS      mandatory
        DESCRIPTION
            "Static routing object gateway interface index.
             When ipeCfgV6RouteNextHop is specified, setting this value is not
             considered.
    
             When setting Link-local address for ipeCfgV6RouteNextHop, this
             object must be configured.
    
             The value acquisition when unsetting it returns NoSuchObject."
        ::= { ipeCfgV6StaticRouteEntry 6 }
    
    -- 1.3.6.1.4.1.119.2.3.69.203.507.5.3.19.2.1.7
    ipeCfgV6RouteRowStatus OBJECT-TYPE
        SYNTAX      RowStatus { active(1), createAndGo(4), destroy(6) }
        ACCESS      read-only
        STATUS      mandatory
        DESCRIPTION
            "This RowStatus has a status only 'active(1)'.
    
             1) creating a entry
             When you make a new entry, you must SET objects indicated below.
             * ipeCfgV6RouteDest
             * ipeCfgV6RoutePrefixLength
             * ipeCfgV6RouteNextHop
             * ipeCfgV6RouteNextHopIfIndex
             * ipeCfgV6RouteRowStatus <- createAndGo(4)
    
             2) modifing a entry
             When you make a existing entry, you must SET objects indicated
             below.
             * ipeCfgV6RouteDest
             * ipeCfgV6RoutePrefixLength
             * ipeCfgV6RouteNextHop
             * ipeCfgV6RouteNextHopIfIndex
    
             3) deleting a entry
             When you SET a destroy(6) to ipeCfgV6RouteRowStatus, the entry is
             destroyed.
             * ipeCfgV6RouteRowStatus <- destory(6)"
        ::= { ipeCfgV6StaticRouteEntry 7 }
    
    -- 1.3.6.1.4.1.119.2.3.69.203.507.5.3.21
    ipeCfgAccessListGroup OBJECT IDENTIFIER
        ::= { ipeConfigurationGroup 21 }
    
    -- 1.3.6.1.4.1.119.2.3.69.203.507.5.3.21.1
    ipeCfgAccessListRuleTable OBJECT-TYPE
        SYNTAX      SEQUENCE OF IpeCfgAccessListRuleEntry
        ACCESS      not-accessible
        STATUS      mandatory
        DESCRIPTION
            "Table of Access List(Rule)."
        ::= { ipeCfgAccessListGroup 1 }
    
    -- 1.3.6.1.4.1.119.2.3.69.203.507.5.3.21.1.1
    ipeCfgAccessListRuleEntry OBJECT-TYPE
        SYNTAX      IpeCfgAccessListRuleEntry
        ACCESS      not-accessible
        STATUS      mandatory
        DESCRIPTION
            "Entry of Access List(Rule)."
        INDEX       { ipeCfgAccessListRuleNEAddress, ipeCfgAccessListRuleEnableIndex }
        ::= { ipeCfgAccessListRuleTable 1 }
    
    IpeCfgAccessListRuleEntry ::= SEQUENCE {
        ipeCfgAccessListRuleEnableIndex         INTEGER,
        ipeCfgAccessListRuleNEAddress           IpAddress,
        ipeCfgAccessListInputRuleEnable         INTEGER,
        ipeCfgAccessListForwardRuleEnable       INTEGER,
        ipeCfgAccessListInputDefaultAction      INTEGER,
        ipeCfgAccessListForwardDefaultAction    INTEGER
    }
    
    -- 1.3.6.1.4.1.119.2.3.69.203.507.5.3.21.1.1.1
    ipeCfgAccessListRuleEnableIndex OBJECT-TYPE
        SYNTAX      INTEGER (1)
        ACCESS      not-accessible
        STATUS      mandatory
        DESCRIPTION
            "Index of this ipeCfgAccessListRuleEntry.
             It's a fixed value(=1)."
        ::= { ipeCfgAccessListRuleEntry 1 }
    
    -- 1.3.6.1.4.1.119.2.3.69.203.507.5.3.21.1.1.2
    ipeCfgAccessListRuleNEAddress OBJECT-TYPE
        SYNTAX      IpAddress
        ACCESS      not-accessible
        STATUS      mandatory
        DESCRIPTION
            ""
        ::= { ipeCfgAccessListRuleEntry 2 }
    
    -- 1.3.6.1.4.1.119.2.3.69.203.507.5.3.21.1.1.3
    ipeCfgAccessListInputRuleEnable OBJECT-TYPE
        SYNTAX      INTEGER { invalid(0), disable(1), enable(2) }
        ACCESS      read-only
        STATUS      mandatory
        DESCRIPTION
            "IP Access Control Input Filter Rule"
        ::= { ipeCfgAccessListRuleEntry 3 }
    
    -- 1.3.6.1.4.1.119.2.3.69.203.507.5.3.21.1.1.4
    ipeCfgAccessListForwardRuleEnable OBJECT-TYPE
        SYNTAX      INTEGER { invalid(0), disable(1), enable(2) }
        ACCESS      read-only
        STATUS      mandatory
        DESCRIPTION
            "IP Access Control Forwarding Filter Rule"
        ::= { ipeCfgAccessListRuleEntry 4 }
    
    -- 1.3.6.1.4.1.119.2.3.69.203.507.5.3.21.1.1.5
    ipeCfgAccessListInputDefaultAction OBJECT-TYPE
        SYNTAX      INTEGER { permit(1), deny(2) }
        ACCESS      read-only
        STATUS      mandatory
        DESCRIPTION
            "IP Access Control Input Default Action."
        ::= { ipeCfgAccessListRuleEntry 5 }
    
    -- 1.3.6.1.4.1.119.2.3.69.203.507.5.3.21.1.1.6
    ipeCfgAccessListForwardDefaultAction OBJECT-TYPE
        SYNTAX      INTEGER { permit(1), deny(2) }
        ACCESS      read-only
        STATUS      mandatory
        DESCRIPTION
            "IP Access Control Forwarding Default Action"
        ::= { ipeCfgAccessListRuleEntry 6 }
    
    -- 1.3.6.1.4.1.119.2.3.69.203.507.5.3.21.2
    ipeCfgAccessListInputTable OBJECT-TYPE
        SYNTAX      SEQUENCE OF IpeCfgAccessListInputEntry
        ACCESS      not-accessible
        STATUS      mandatory
        DESCRIPTION
            "Table of Access List(Input Direction)."
        ::= { ipeCfgAccessListGroup 2 }
    
    -- 1.3.6.1.4.1.119.2.3.69.203.507.5.3.21.2.1
    ipeCfgAccessListInputEntry OBJECT-TYPE
        SYNTAX      IpeCfgAccessListInputEntry
        ACCESS      not-accessible
        STATUS      mandatory
        DESCRIPTION
            "Entry of Access List(Input Direction)."
        INDEX       { ipeCfgAccessListInputNEAddress, ipeCfgAccessListInputOrderNum }
        ::= { ipeCfgAccessListInputTable 1 }
    
    IpeCfgAccessListInputEntry ::= SEQUENCE {
        ipeCfgAccessListInputOrderNum       INTEGER,
        ipeCfgAccessListInputNEAddress      IpAddress,
        ipeCfgAccessListInputInIfIndex      INTEGER,
        ipeCfgAccessListInputSrcIpAddress   IpAddress,
        ipeCfgAccessListInputSrcNetMask     IpAddress,
        ipeCfgAccessListInputProtocol       INTEGER,
        ipeCfgAccessListInputDstPortNum     INTEGER,
        ipeCfgAccessListInputAction         INTEGER,
        ipeCfgAccessListInputRowStatus      RowStatus
    }
    
    -- 1.3.6.1.4.1.119.2.3.69.203.507.5.3.21.2.1.1
    ipeCfgAccessListInputOrderNum OBJECT-TYPE
        SYNTAX      INTEGER (1..50)
        ACCESS      not-accessible
        STATUS      mandatory
        DESCRIPTION
            "Index of table(1-50)."
        ::= { ipeCfgAccessListInputEntry 1 }
    
    -- 1.3.6.1.4.1.119.2.3.69.203.507.5.3.21.2.1.2
    ipeCfgAccessListInputNEAddress OBJECT-TYPE
        SYNTAX      IpAddress
        ACCESS      not-accessible
        STATUS      mandatory
        DESCRIPTION
            ""
        ::= { ipeCfgAccessListInputEntry 2 }
    
    -- 1.3.6.1.4.1.119.2.3.69.203.507.5.3.21.2.1.3
    ipeCfgAccessListInputInIfIndex OBJECT-TYPE
        SYNTAX      INTEGER { any(0), inband(3), ne2(4), bridge1(11),
                        bridge2(12), bridge3(13), bridge4(14), bridge5(15),
                        bridge6(16), bridge7(17), bridge8(18), bridge9(19),
                        bridge10(20), bridge11(21), bridge12(22),
                        bridge13(23), bridge14(24), bridge15(25),
                        bridge16(26), bridge17(27), bridge18(28),
                        bridge19(29), bridge20(30) }
        ACCESS      read-only
        STATUS      mandatory
        DESCRIPTION
            "IP Access Control Input Filter Interface.
    
             The value 'inband' is not supported.
             Bridge7(17), Bridge8(18) can not be set to this (iPASOLINK EX
             Advanced).
             The value Bridge1(11), Bridge2(12), Bridge3(13),
             Bridge4(14), Bridge5(15) Bridge6(16) are available (iPASOLINK EX
             Advanced)."
        ::= { ipeCfgAccessListInputEntry 3 }
    
    -- 1.3.6.1.4.1.119.2.3.69.203.507.5.3.21.2.1.4
    ipeCfgAccessListInputSrcIpAddress OBJECT-TYPE
        SYNTAX      IpAddress
        ACCESS      read-only
        STATUS      mandatory
        DESCRIPTION
            "IP Access Control Input Filter Source IP Address"
        ::= { ipeCfgAccessListInputEntry 4 }
    
    -- 1.3.6.1.4.1.119.2.3.69.203.507.5.3.21.2.1.5
    ipeCfgAccessListInputSrcNetMask OBJECT-TYPE
        SYNTAX      IpAddress
        ACCESS      read-only
        STATUS      mandatory
        DESCRIPTION
            "IP Access Control Input Filter Source Subnet Mask.
             '0.0.0.0' matches all IP addresses. i.e. '0.0.0.0' acts as
             'Any'."
        ::= { ipeCfgAccessListInputEntry 5 }
    
    -- 1.3.6.1.4.1.119.2.3.69.203.507.5.3.21.2.1.6
    ipeCfgAccessListInputProtocol OBJECT-TYPE
        SYNTAX      INTEGER
        ACCESS      read-only
        STATUS      mandatory
        DESCRIPTION
            "IP Access Control Input Filter Protocol.
             '-1' acts as 'Any'."
        ::= { ipeCfgAccessListInputEntry 6 }
    
    -- 1.3.6.1.4.1.119.2.3.69.203.507.5.3.21.2.1.7
    ipeCfgAccessListInputDstPortNum OBJECT-TYPE
        SYNTAX      INTEGER
        ACCESS      read-only
        STATUS      mandatory
        DESCRIPTION
            "IP Access Control Input Filter Port Number.
             '-1' acts as 'Any'."
        ::= { ipeCfgAccessListInputEntry 7 }
    
    -- 1.3.6.1.4.1.119.2.3.69.203.507.5.3.21.2.1.8
    ipeCfgAccessListInputAction OBJECT-TYPE
        SYNTAX      INTEGER { permit(1), deny(2) }
        ACCESS      read-only
        STATUS      mandatory
        DESCRIPTION
            "IP Access Control Input Filter Action."
        ::= { ipeCfgAccessListInputEntry 8 }
    
    -- 1.3.6.1.4.1.119.2.3.69.203.507.5.3.21.2.1.9
    ipeCfgAccessListInputRowStatus OBJECT-TYPE
        SYNTAX      RowStatus { active(1), createAndGo(4), destroy(6) }
        ACCESS      read-only
        STATUS      mandatory
        DESCRIPTION
            "This RowStatus has a status only 'active(1)'.
    
             1) creating a entry
             When you make a new entry, you must SET objects indicated below.
             ipeCfgAccessListInputAction
             ipeCfgAccessListInputRowStatus <- createAndGo(4)
    
    
             When you are not setting a value of items as follows, it is set
             as 'any'.
             ipeCfgAccessListInputInIfIndex
             ipeCfgAccessListInputSrcIpAddress
             ipeCfgAccessListInputSrcNetMask(*1)
             ipeCfgAccessListInputProtocol
             ipeCfgAccessListInputDstPortNum(*2)
    
             *1 When you not set ipeCfgAccessListInputSrcIpAddress, even when
             ipeCfgAccessListInputSrcNetMask is set, it is set as 'any'.When
             ipeCfgAccessListInputSrcIpAddress set to 'any',
             ipeCfgAccessListInputSrcNetMask is set as 'any'.
             *2 When you not set ipeCfgAccessListInputProtocol to '6' or '17',
             even when ipeCfgAccessListInputDstPortNum is set, it is set as
             'any'.
    
             2) modifing a entry
             It isn't possible.
    
             3) deleting a entry
             When you SET a destroy(6) to ipeCfgAccessListInputRowStatus, the
             entry is destroyed."
        ::= { ipeCfgAccessListInputEntry 9 }
    
    -- 1.3.6.1.4.1.119.2.3.69.203.507.5.3.21.3
    ipeCfgAccessListForwardTable OBJECT-TYPE
        SYNTAX      SEQUENCE OF IpeCfgAccessListForwardEntry
        ACCESS      not-accessible
        STATUS      mandatory
        DESCRIPTION
            "Table of Access List(Forward Direction)."
        ::= { ipeCfgAccessListGroup 3 }
    
    -- 1.3.6.1.4.1.119.2.3.69.203.507.5.3.21.3.1
    ipeCfgAccessListForwardEntry OBJECT-TYPE
        SYNTAX      IpeCfgAccessListForwardEntry
        ACCESS      not-accessible
        STATUS      mandatory
        DESCRIPTION
            "Entry of Access List(Forward Direction)."
        INDEX       { ipeCfgAccessListForwardNEAddress, ipeCfgAccessListForwardOrderNum }
        ::= { ipeCfgAccessListForwardTable 1 }
    
    IpeCfgAccessListForwardEntry ::= SEQUENCE {
        ipeCfgAccessListForwardOrderNum         INTEGER,
        ipeCfgAccessListForwardNEAddress        IpAddress,
        ipeCfgAccessListForwardInIfIndex        INTEGER,
        ipeCfgAccessListForwardOutIfIndex       INTEGER,
        ipeCfgAccessListForwardSrcIpAddress     IpAddress,
        ipeCfgAccessListForwardSrcNetMask       IpAddress,
        ipeCfgAccessListForwardDstIpAddress     IpAddress,
        ipeCfgAccessListForwardDstNetMask       IpAddress,
        ipeCfgAccessListForwardProtocol         INTEGER,
        ipeCfgAccessListForwardSrcPortNum       INTEGER,
        ipeCfgAccessListForwardDstPortNum       INTEGER,
        ipeCfgAccessListForwardAction           INTEGER,
        ipeCfgAccessListForwardRowStatus        RowStatus
    }
    
    -- 1.3.6.1.4.1.119.2.3.69.203.507.5.3.21.3.1.1
    ipeCfgAccessListForwardOrderNum OBJECT-TYPE
        SYNTAX      INTEGER (1..50)
        ACCESS      not-accessible
        STATUS      mandatory
        DESCRIPTION
            "Index of table(1-50)."
        ::= { ipeCfgAccessListForwardEntry 1 }
    
    -- 1.3.6.1.4.1.119.2.3.69.203.507.5.3.21.3.1.2
    ipeCfgAccessListForwardNEAddress OBJECT-TYPE
        SYNTAX      IpAddress
        ACCESS      not-accessible
        STATUS      mandatory
        DESCRIPTION
            ""
        ::= { ipeCfgAccessListForwardEntry 2 }
    
    -- 1.3.6.1.4.1.119.2.3.69.203.507.5.3.21.3.1.3
    ipeCfgAccessListForwardInIfIndex OBJECT-TYPE
        SYNTAX      INTEGER { any(0), inband(3), ne2(4), bridge1(11),
                        bridge2(12), bridge3(13), bridge4(14), bridge5(15),
                        bridge6(16), bridge7(17), bridge8(18), bridge9(19),
                        bridge10(20), bridge11(21), bridge12(22),
                        bridge13(23), bridge14(24), bridge15(25),
                        bridge16(26), bridge17(27), bridge18(28),
                        bridge19(29), bridge20(30) }
        ACCESS      read-only
        STATUS      mandatory
        DESCRIPTION
            "IP Access Control Forward Filter Input Interface.
    
             The value 'inband' is not supported.
             Bridge7(17), Bridge8(18) can not be set to this (iPASOLINK EX
             Advanced)."
        ::= { ipeCfgAccessListForwardEntry 3 }
    
    -- 1.3.6.1.4.1.119.2.3.69.203.507.5.3.21.3.1.4
    ipeCfgAccessListForwardOutIfIndex OBJECT-TYPE
        SYNTAX      INTEGER { any(0), inband(3), ne2(4), bridge1(11),
                        bridge2(12), bridge3(13), bridge4(14), bridge5(15),
                        bridge6(16), bridge7(17), bridge8(18), bridge9(19),
                        bridge10(20), bridge11(21), bridge12(22),
                        bridge13(23), bridge14(24), bridge15(25),
                        bridge16(26), bridge17(27), bridge18(28),
                        bridge19(29), bridge20(30) }
        ACCESS      read-only
        STATUS      mandatory
        DESCRIPTION
            "IP Access Control Forward Filter Output Interface.
    
             The value 'inband' is not supported.
             Bridge7(17), Bridge8(18) can not be set to this (iPASOLINK EX
             Advanced)."
        ::= { ipeCfgAccessListForwardEntry 4 }
    
    -- 1.3.6.1.4.1.119.2.3.69.203.507.5.3.21.3.1.5
    ipeCfgAccessListForwardSrcIpAddress OBJECT-TYPE
        SYNTAX      IpAddress
        ACCESS      read-only
        STATUS      mandatory
        DESCRIPTION
            "IP Access Control Forward Filter Source IP Address."
        ::= { ipeCfgAccessListForwardEntry 5 }
    
    -- 1.3.6.1.4.1.119.2.3.69.203.507.5.3.21.3.1.6
    ipeCfgAccessListForwardSrcNetMask OBJECT-TYPE
        SYNTAX      IpAddress
        ACCESS      read-only
        STATUS      mandatory
        DESCRIPTION
            "IP Access Control Forward Filter Source Subnet Mask.
             '0.0.0.0' matches all IP addresses. i.e. '0.0.0.0' acts as 'Any'"
        ::= { ipeCfgAccessListForwardEntry 6 }
    
    -- 1.3.6.1.4.1.119.2.3.69.203.507.5.3.21.3.1.7
    ipeCfgAccessListForwardDstIpAddress OBJECT-TYPE
        SYNTAX      IpAddress
        ACCESS      read-only
        STATUS      mandatory
        DESCRIPTION
            "IP Access Control Forward Filter Destination IP Address."
        ::= { ipeCfgAccessListForwardEntry 7 }
    
    -- 1.3.6.1.4.1.119.2.3.69.203.507.5.3.21.3.1.8
    ipeCfgAccessListForwardDstNetMask OBJECT-TYPE
        SYNTAX      IpAddress
        ACCESS      read-only
        STATUS      mandatory
        DESCRIPTION
            "IP Access Control Forward Filter Destination Subnet Mask.
             '0.0.0.0' matches all IP addresses. i.e. '0.0.0.0' acts as
             'Any'."
        ::= { ipeCfgAccessListForwardEntry 8 }
    
    -- 1.3.6.1.4.1.119.2.3.69.203.507.5.3.21.3.1.9
    ipeCfgAccessListForwardProtocol OBJECT-TYPE
        SYNTAX      INTEGER
        ACCESS      read-only
        STATUS      mandatory
        DESCRIPTION
            "IP Access Control Forward Filter Protocol.
             '-1' acts as 'Any'."
        ::= { ipeCfgAccessListForwardEntry 9 }
    
    -- 1.3.6.1.4.1.119.2.3.69.203.507.5.3.21.3.1.10
    ipeCfgAccessListForwardSrcPortNum OBJECT-TYPE
        SYNTAX      INTEGER
        ACCESS      read-only
        STATUS      mandatory
        DESCRIPTION
            "IP Access Control Forward Filter Source Port Number.
             '-1' acts as 'Any'."
        ::= { ipeCfgAccessListForwardEntry 10 }
    
    -- 1.3.6.1.4.1.119.2.3.69.203.507.5.3.21.3.1.11
    ipeCfgAccessListForwardDstPortNum OBJECT-TYPE
        SYNTAX      INTEGER
        ACCESS      read-only
        STATUS      mandatory
        DESCRIPTION
            "IP Access Control Forward Filter Destination Port Number.
             '-1' acts as 'Any'."
        ::= { ipeCfgAccessListForwardEntry 11 }
    
    -- 1.3.6.1.4.1.119.2.3.69.203.507.5.3.21.3.1.12
    ipeCfgAccessListForwardAction OBJECT-TYPE
        SYNTAX      INTEGER { permit(1), deny(2) }
        ACCESS      read-only
        STATUS      mandatory
        DESCRIPTION
            "IP Access Control Forward Filter Action."
        ::= { ipeCfgAccessListForwardEntry 12 }
    
    -- 1.3.6.1.4.1.119.2.3.69.203.507.5.3.21.3.1.13
    ipeCfgAccessListForwardRowStatus OBJECT-TYPE
        SYNTAX      RowStatus { active(1), createAndGo(4), destroy(6) }
        ACCESS      read-only
        STATUS      mandatory
        DESCRIPTION
            "This RowStatus has a status only 'active(1)'.
    
             1) creating a entry
             When you make a new entry, you must SET objects indicated below.
             ipeCfgAccessListForwardAction
             ipeCfgAccessListForwardRowStatus <- createAndGo(4)
    
    
             When you are not setting a value of items as follows, it is set
             as 'any'.
             ipeCfgAccessListForwardInIfIndex
             ipeCfgAccessListForwardOutIfIndex
             ipeCfgAccessListForwardSrcIpAddress
             ipeCfgAccessListForwardSrcNetMask(*1)
             ipeCfgAccessListForwardDstIpAddress
             ipeCfgAccessListForwardDstNetMask(*2)
             ipeCfgAccessListForwardProtocol
             ipeCfgAccessListForwardSrcPortNum(*3)
             ipeCfgAccessListForwardDstPortNum(*3)
    
             *1 When you not set ipeCfgAccessListForwardSrcIpAddress, even
             when ipeCfgAccessListForwardSrcNetMask is set, it is set as
             'any'.When ipeCfgAccessListForwardSrcIpAddress set to 'any',
             ipeCfgAccessListForwardSrcNetMask is set as 'any'.
             *2 When you not set ipeCfgAccessListForwardDstIpAddress, even
             when ipeCfgAccessListForwardDstNetMask is set, it is set as
             'any'.When ipeCfgAccessListForwardDstIpAddress set to 'any',
             ipeCfgAccessListForwardDstNetMask is set as 'any'.
             *3 When you not set ipeCfgAccessListForwardProtocol to '6' or
             '17',, even when ipeCfgAccessListForwardSrcPortNum and
             ipeCfgAccessListForwardDstPortNum are set, it is set as 'any'.
    
             2) modifing a entry
             It isn't possible.
    
             3) deleting a entry
             When you SET a destroy(6) to ipeCfgAccessListForwardRowStatus,
             the entry is destroyed."
        ::= { ipeCfgAccessListForwardEntry 13 }
    
    -- 1.3.6.1.4.1.119.2.3.69.203.507.5.3.22
    ipeCfgAutoIpGroup OBJECT IDENTIFIER
        ::= { ipeConfigurationGroup 22 }
    
    -- 1.3.6.1.4.1.119.2.3.69.203.507.5.3.22.1
    ipeCfgAutoIpTable OBJECT-TYPE
        SYNTAX      SEQUENCE OF IpeCfgAutoIpEntry
        ACCESS      not-accessible
        STATUS      mandatory
        DESCRIPTION
            "Table of AutoIP configuration information."
        ::= { ipeCfgAutoIpGroup 1 }
    
    -- 1.3.6.1.4.1.119.2.3.69.203.507.5.3.22.1.1
    ipeCfgAutoIpEntry OBJECT-TYPE
        SYNTAX      IpeCfgAutoIpEntry
        ACCESS      not-accessible
        STATUS      mandatory
        DESCRIPTION
            "Entry of AutoIP configuration information."
        INDEX       { ipeCfgAutoIpNEAddress, ipeCfgAutoIpIndex }
        ::= { ipeCfgAutoIpTable 1 }
    
    IpeCfgAutoIpEntry ::= SEQUENCE {
        ipeCfgAutoIpIndex           INTEGER,
        ipeCfgAutoIpNEAddress       IpAddress,
        ipeCfgAutoIpNetworkAddress  IpAddress,
        ipeCfgAutoIpNetMask         IpAddress
    }
    
    -- 1.3.6.1.4.1.119.2.3.69.203.507.5.3.22.1.1.1
    ipeCfgAutoIpIndex OBJECT-TYPE
        SYNTAX      INTEGER (1)
        ACCESS      not-accessible
        STATUS      mandatory
        DESCRIPTION
            "Index of table.
             It's a fixed value(=1)."
        ::= { ipeCfgAutoIpEntry 1 }
    
    -- 1.3.6.1.4.1.119.2.3.69.203.507.5.3.22.1.1.2
    ipeCfgAutoIpNEAddress OBJECT-TYPE
        SYNTAX      IpAddress
        ACCESS      not-accessible
        STATUS      mandatory
        DESCRIPTION
            ""
        ::= { ipeCfgAutoIpEntry 2 }
    
    -- 1.3.6.1.4.1.119.2.3.69.203.507.5.3.22.1.1.3
    ipeCfgAutoIpNetworkAddress OBJECT-TYPE
        SYNTAX      IpAddress
        ACCESS      read-only
        STATUS      mandatory
        DESCRIPTION
            "Aggregation Net of AutoIP.
             A set value becomes a binary.
             Value range:0x00000000-0xdfffffff(0.0.0.0-223.255.255.255)
             If this value is changed in state of 'now setting' or 'automatic
             setting', AutoIP will set IP Address again."
        ::= { ipeCfgAutoIpEntry 3 }
    
    -- 1.3.6.1.4.1.119.2.3.69.203.507.5.3.22.1.1.4
    ipeCfgAutoIpNetMask OBJECT-TYPE
        SYNTAX      IpAddress
        ACCESS      read-only
        STATUS      mandatory
        DESCRIPTION
            "Aggregation NetMask of AutoIp.
             A set value becomes a binary.
             Value range:0x80000000-0xfffffffc(1-30bit)
             If this value is changed in state of 'now setting' or 'automatic
             setting', AutoIP will set IP Address again."
        ::= { ipeCfgAutoIpEntry 4 }
    
    -- 1.3.6.1.4.1.119.2.3.69.203.507.5.3.25
    ipeCfgSysNE1PortTable OBJECT-TYPE
        SYNTAX      SEQUENCE OF IpeCfgSysNE1PortEntry
        ACCESS      not-accessible
        STATUS      mandatory
        DESCRIPTION
            "NE1 Port Mode Configuration Table."
        ::= { ipeConfigurationGroup 25 }
    
    -- 1.3.6.1.4.1.119.2.3.69.203.507.5.3.25.1
    ipeCfgSysNE1PortEntry OBJECT-TYPE
        SYNTAX      IpeCfgSysNE1PortEntry
        ACCESS      not-accessible
        STATUS      mandatory
        DESCRIPTION
            ""
        INDEX       { ipeCfgSysNE1PortNEAddress, ipeCfgSysNE1PortIndex }
        ::= { ipeCfgSysNE1PortTable 1 }
    
    IpeCfgSysNE1PortEntry ::= SEQUENCE {
        ipeCfgSysNE1PortIndex       INTEGER,
        ipeCfgSysNE1PortNEAddress   IpAddress,
        ipeCfgSysNE1PortMode        INTEGER
    }
    
    -- 1.3.6.1.4.1.119.2.3.69.203.507.5.3.25.1.1
    ipeCfgSysNE1PortIndex OBJECT-TYPE
        SYNTAX      INTEGER (1)
        ACCESS      not-accessible
        STATUS      mandatory
        DESCRIPTION
            "Index of this table."
        ::= { ipeCfgSysNE1PortEntry 1 }
    
    -- 1.3.6.1.4.1.119.2.3.69.203.507.5.3.25.1.2
    ipeCfgSysNE1PortNEAddress OBJECT-TYPE
        SYNTAX      IpAddress
        ACCESS      not-accessible
        STATUS      mandatory
        DESCRIPTION
            ""
        ::= { ipeCfgSysNE1PortEntry 2 }
    
    -- 1.3.6.1.4.1.119.2.3.69.203.507.5.3.25.1.3
    ipeCfgSysNE1PortMode OBJECT-TYPE
        SYNTAX      INTEGER { invalid(0), userPort(1), mgmtPort(2) }
        ACCESS      read-only
        STATUS      mandatory
        DESCRIPTION
            "NE1 Port Mode Configuration
             This value is not available [iPASOLINK EX Advanced]"
        DEFVAL      { userPort }
        ::= { ipeCfgSysNE1PortEntry 3 }
    
    -- 1.3.6.1.4.1.119.2.3.69.203.507.5.3.27
    ipeCfgRadiusGroup OBJECT IDENTIFIER
        ::= { ipeConfigurationGroup 27 }
    
    -- 1.3.6.1.4.1.119.2.3.69.203.507.5.3.27.1
    ipeCfgRadiusGeneralTable OBJECT-TYPE
        SYNTAX      SEQUENCE OF IpeCfgRadiusGeneralEntry
        ACCESS      not-accessible
        STATUS      mandatory
        DESCRIPTION
            "Configure RADIUS parameters."
        ::= { ipeCfgRadiusGroup 1 }
    
    -- 1.3.6.1.4.1.119.2.3.69.203.507.5.3.27.1.1
    ipeCfgRadiusGeneralEntry OBJECT-TYPE
        SYNTAX      IpeCfgRadiusGeneralEntry
        ACCESS      not-accessible
        STATUS      mandatory
        DESCRIPTION
            "..."
        INDEX       { ipeCfgRadiusGeneralNEAddress, ipeCfgRadiusGeneralIndex }
        ::= { ipeCfgRadiusGeneralTable 1 }
    
    IpeCfgRadiusGeneralEntry ::= SEQUENCE {
        ipeCfgRadiusGeneralIndex                    INTEGER,
        ipeCfgRadiusGeneralNEAddress                IpAddress,
        ipeCfgRadiusGeneralAuthClientRetransmit     INTEGER,
        ipeCfgRadiusGeneralAuthClientTimeout        INTEGER
    }
    
    -- 1.3.6.1.4.1.119.2.3.69.203.507.5.3.27.1.1.1
    ipeCfgRadiusGeneralIndex OBJECT-TYPE
        SYNTAX      INTEGER (1)
        ACCESS      not-accessible
        STATUS      mandatory
        DESCRIPTION
            "The index of this table."
        ::= { ipeCfgRadiusGeneralEntry 1 }
    
    -- 1.3.6.1.4.1.119.2.3.69.203.507.5.3.27.1.1.2
    ipeCfgRadiusGeneralNEAddress OBJECT-TYPE
        SYNTAX      IpAddress
        ACCESS      not-accessible
        STATUS      mandatory
        DESCRIPTION
            "Reserved object for northbound interface."
        ::= { ipeCfgRadiusGeneralEntry 2 }
    
    -- 1.3.6.1.4.1.119.2.3.69.203.507.5.3.27.1.1.3
    ipeCfgRadiusGeneralAuthClientRetransmit OBJECT-TYPE
        SYNTAX      INTEGER (0..255)
        ACCESS      read-only
        STATUS      mandatory
        DESCRIPTION
            "Indicate maximum retransmit number of Access-Request
             message.
             The system retransmits Access-Request message to server
             according to this configuration."
        DEFVAL      { 3 }
        ::= { ipeCfgRadiusGeneralEntry 3 }
    
    -- 1.3.6.1.4.1.119.2.3.69.203.507.5.3.27.1.1.4
    ipeCfgRadiusGeneralAuthClientTimeout OBJECT-TYPE
        SYNTAX      INTEGER (0..65535)
        ACCESS      read-only
        STATUS      mandatory
        DESCRIPTION
            "Indicate timeout period for response to Access-Request
             message.
             In case response (Access-Accept message) is not received
             in this period, the system will retransmit message."
        DEFVAL      { 10 }
        ::= { ipeCfgRadiusGeneralEntry 4 }
    
    -- 1.3.6.1.4.1.119.2.3.69.203.507.5.3.27.2
    ipeCfgRadiusAuthServerExtTable OBJECT-TYPE
        SYNTAX      SEQUENCE OF IpeCfgRadiusAuthServerExtEntry
        ACCESS      not-accessible
        STATUS      mandatory
        DESCRIPTION
            "Configure RADIUS authentication server parameters."
        ::= { ipeCfgRadiusGroup 2 }
    
    -- 1.3.6.1.4.1.119.2.3.69.203.507.5.3.27.2.1
    ipeCfgRadiusAuthServerExtEntry OBJECT-TYPE
        SYNTAX      IpeCfgRadiusAuthServerExtEntry
        ACCESS      not-accessible
        STATUS      mandatory
        DESCRIPTION
            "..."
        INDEX       { ipeCfgRadiusAuthServerNEAddress, ipeCfgRadiusAuthServerExtIndex }
        ::= { ipeCfgRadiusAuthServerExtTable 1 }
    
    IpeCfgRadiusAuthServerExtEntry ::= SEQUENCE {
        ipeCfgRadiusAuthServerExtIndex          INTEGER,
        ipeCfgRadiusAuthServerNEAddress         IpAddress,
        ipeCfgRadiusAuthServerAddressType       INTEGER,
        ipeCfgRadiusAuthServerAddress           IpAddress,
        ipeCfgRadiusAuthClientServerPortNumber  INTEGER,
        ipeCfgRadiusAuthClientPasswordType      INTEGER,
        ipeCfgRadiusAuthClientSecretKey         DisplayString,
        ipeCfgRadiusAuthServerExtRowStatus      RowStatus
    }
    
    -- 1.3.6.1.4.1.119.2.3.69.203.507.5.3.27.2.1.1
    ipeCfgRadiusAuthServerExtIndex OBJECT-TYPE
        SYNTAX      INTEGER (1..3)
        ACCESS      not-accessible
        STATUS      mandatory
        DESCRIPTION
            "The index of this table."
        ::= { ipeCfgRadiusAuthServerExtEntry 1 }
    
    -- 1.3.6.1.4.1.119.2.3.69.203.507.5.3.27.2.1.2
    ipeCfgRadiusAuthServerNEAddress OBJECT-TYPE
        SYNTAX      IpAddress
        ACCESS      not-accessible
        STATUS      mandatory
        DESCRIPTION
            "Reserved object for northbound interface."
        ::= { ipeCfgRadiusAuthServerExtEntry 2 }
    
    -- 1.3.6.1.4.1.119.2.3.69.203.507.5.3.27.2.1.3
    ipeCfgRadiusAuthServerAddressType OBJECT-TYPE
        SYNTAX      INTEGER { invalid(0), ipv4(1), ipv6(2) }
        ACCESS      read-only
        STATUS      mandatory
        DESCRIPTION
            "Indicate IP address type of this server.
    
             ipv4 : server has IPv4 address.
             ipv6 : server has IPv6 address. (NOT SUPPORTED)
    
             ipv6 will be supprted in future version."
        DEFVAL      { ipv4 }
        ::= { ipeCfgRadiusAuthServerExtEntry 3 }
    
    -- 1.3.6.1.4.1.119.2.3.69.203.507.5.3.27.2.1.4
    ipeCfgRadiusAuthServerAddress OBJECT-TYPE
        SYNTAX      IpAddress
        ACCESS      read-only
        STATUS      mandatory
        DESCRIPTION
            "Indicate IP address of this server."
        ::= { ipeCfgRadiusAuthServerExtEntry 4 }
    
    -- 1.3.6.1.4.1.119.2.3.69.203.507.5.3.27.2.1.5
    ipeCfgRadiusAuthClientServerPortNumber OBJECT-TYPE
        SYNTAX      INTEGER (0..65535)
        ACCESS      read-only
        STATUS      mandatory
        DESCRIPTION
            "Indicate port number of RADIUS authentication protocol on
             this server."
        DEFVAL      { 1812 }
        ::= { ipeCfgRadiusAuthServerExtEntry 5 }
    
    -- 1.3.6.1.4.1.119.2.3.69.203.507.5.3.27.2.1.6
    ipeCfgRadiusAuthClientPasswordType OBJECT-TYPE
        SYNTAX      INTEGER { invalid(0), user(1), chap(2) }
        ACCESS      read-only
        STATUS      mandatory
        DESCRIPTION
            "Indicate password authentication type. The system select
             password attribute on Access-Request message.
    
             user : use User-Password attribute.
             chap : use CHAP-Password attribute.
    
             See RFC 2865 for details."
        DEFVAL      { user }
        ::= { ipeCfgRadiusAuthServerExtEntry 6 }
    
    -- 1.3.6.1.4.1.119.2.3.69.203.507.5.3.27.2.1.7
    ipeCfgRadiusAuthClientSecretKey OBJECT-TYPE
        SYNTAX      DisplayString (SIZE(8..128))
        ACCESS      read-only
        STATUS      mandatory
        DESCRIPTION
            "Indicate RADIUS shared secret encrypted by blowfish.
             This object is used to confirm  received RADIUS message is
             sent from authenticated server.
             This object is also used to encrypt User-Password attribute
             on Access-Request message.
             See RFC 2865 for details.
    
             The secret key(before encryption) range is 1-63 characters.
             The characters which can be used are '-', '_','0'-'9',
             'a'-'z' and 'A'-'Z'."
        ::= { ipeCfgRadiusAuthServerExtEntry 7 }
    
    -- 1.3.6.1.4.1.119.2.3.69.203.507.5.3.27.2.1.8
    ipeCfgRadiusAuthServerExtRowStatus OBJECT-TYPE
        SYNTAX      RowStatus
        ACCESS      read-only
        STATUS      mandatory
        DESCRIPTION
            "The row status of this table."
        ::= { ipeCfgRadiusAuthServerExtEntry 8 }
    
    -- 1.3.6.1.4.1.119.2.3.69.203.507.5.3.27.3
    ipeCfgRadiusPrivLevelGeneralTable OBJECT-TYPE
        SYNTAX      SEQUENCE OF IpeCfgRadiusPrivLevelGeneralEntry
        ACCESS      not-accessible
        STATUS      mandatory
        DESCRIPTION
            "Configure general privilege level for RADIUS
             authetication."
        ::= { ipeCfgRadiusGroup 3 }
    
    -- 1.3.6.1.4.1.119.2.3.69.203.507.5.3.27.3.1
    ipeCfgRadiusPrivLevelGeneralEntry OBJECT-TYPE
        SYNTAX      IpeCfgRadiusPrivLevelGeneralEntry
        ACCESS      not-accessible
        STATUS      mandatory
        DESCRIPTION
            "..."
        INDEX       { ipeCfgRadiusPrivLevelGeneralNEAddress, ipeCfgRadiusPrivLevelGeneralIndex }
        ::= { ipeCfgRadiusPrivLevelGeneralTable 1 }
    
    IpeCfgRadiusPrivLevelGeneralEntry ::= SEQUENCE {
        ipeCfgRadiusPrivLevelGeneralIndex           INTEGER,
        ipeCfgRadiusPrivLevelGeneralNEAddress       IpAddress,
        ipeCfgRadiusPrivLevelGeneralDefaultAction   INTEGER,
        ipeCfgRadiusPrivLevelGeneralDefaultGroup    DisplayString
    }
    
    -- 1.3.6.1.4.1.119.2.3.69.203.507.5.3.27.3.1.1
    ipeCfgRadiusPrivLevelGeneralIndex OBJECT-TYPE
        SYNTAX      INTEGER (1)
        ACCESS      not-accessible
        STATUS      mandatory
        DESCRIPTION
            "The index of this table."
        ::= { ipeCfgRadiusPrivLevelGeneralEntry 1 }
    
    -- 1.3.6.1.4.1.119.2.3.69.203.507.5.3.27.3.1.2
    ipeCfgRadiusPrivLevelGeneralNEAddress OBJECT-TYPE
        SYNTAX      IpAddress
        ACCESS      not-accessible
        STATUS      mandatory
        DESCRIPTION
            "Reserved object for northbound interface."
        ::= { ipeCfgRadiusPrivLevelGeneralEntry 2 }
    
    -- 1.3.6.1.4.1.119.2.3.69.203.507.5.3.27.3.1.3
    ipeCfgRadiusPrivLevelGeneralDefaultAction OBJECT-TYPE
        SYNTAX      INTEGER { invalid(0), denyLogin(1), useDefaultGroup(2) }
        ACCESS      read-only
        STATUS      mandatory
        DESCRIPTION
            "Indicate system default action in case privilege level
             is not specified on Access-Accept message or received
             privilege level is set to disable in
             ipeCfgRadiusGroupPrivLevelMappingEnable.
    
             denyLogin       : deny login.
             useDefaultGroup : use group specified in
                               ipeCfgRadiusPrivLevelGeneralDefaultGroup."
        DEFVAL      { useDefaultGroup }
        ::= { ipeCfgRadiusPrivLevelGeneralEntry 3 }
    
    -- 1.3.6.1.4.1.119.2.3.69.203.507.5.3.27.3.1.4
    ipeCfgRadiusPrivLevelGeneralDefaultGroup OBJECT-TYPE
        SYNTAX      DisplayString (SIZE(1..32))
        ACCESS      read-only
        STATUS      mandatory
        DESCRIPTION
            "Indicate default group in case privilege level is not
             specified.
             This object is effective only if
             ipeCfgRadiusPrivLevelGeneralDefaultAction is
             useDefaultGroup.
    
             The value of this object should be registered group name in
             the system (as ipeCfgAccountGroupName).
    
             The characters which can be used are '-', '_','0'-'9',
             'a'-'z' and 'A'-'Z'."
        DEFVAL      { "Operator" }
        ::= { ipeCfgRadiusPrivLevelGeneralEntry 4 }
    
    -- 1.3.6.1.4.1.119.2.3.69.203.507.5.3.27.4
    ipeCfgRadiusGroupPrivLevelMappingTable OBJECT-TYPE
        SYNTAX      SEQUENCE OF IpeCfgRadiusGroupPrivLevelMappingEntry
        ACCESS      not-accessible
        STATUS      mandatory
        DESCRIPTION
            "Configure privilege level mapping for RADIUS
             authentication."
        ::= { ipeCfgRadiusGroup 4 }
    
    -- 1.3.6.1.4.1.119.2.3.69.203.507.5.3.27.4.1
    ipeCfgRadiusGroupPrivLevelMappingEntry OBJECT-TYPE
        SYNTAX      IpeCfgRadiusGroupPrivLevelMappingEntry
        ACCESS      not-accessible
        STATUS      mandatory
        DESCRIPTION
            "..."
        INDEX       { ipeCfgRadiusGroupPrivLevelMappingNEAddress, ipeCfgRadiusGroupPrivLevelMappingPrivLevel }
        ::= { ipeCfgRadiusGroupPrivLevelMappingTable 1 }
    
    IpeCfgRadiusGroupPrivLevelMappingEntry ::= SEQUENCE {
        ipeCfgRadiusGroupPrivLevelMappingPrivLevel  INTEGER,
        ipeCfgRadiusGroupPrivLevelMappingNEAddress  IpAddress,
        ipeCfgRadiusGroupPrivLevelMappingEnable     INTEGER,
        ipeCfgRadiusGroupPrivLevelMappingGroup      DisplayString
    }
    
    -- 1.3.6.1.4.1.119.2.3.69.203.507.5.3.27.4.1.1
    ipeCfgRadiusGroupPrivLevelMappingPrivLevel OBJECT-TYPE
        SYNTAX      INTEGER (0..15)
        ACCESS      not-accessible
        STATUS      mandatory
        DESCRIPTION
            "The index of this table.
             The value corresponds to received privilege level on
             Access-Accept message."
        ::= { ipeCfgRadiusGroupPrivLevelMappingEntry 1 }
    
    -- 1.3.6.1.4.1.119.2.3.69.203.507.5.3.27.4.1.2
    ipeCfgRadiusGroupPrivLevelMappingNEAddress OBJECT-TYPE
        SYNTAX      IpAddress
        ACCESS      not-accessible
        STATUS      mandatory
        DESCRIPTION
            "Reserved object for northbound interface."
        ::= { ipeCfgRadiusGroupPrivLevelMappingEntry 2 }
    
    -- 1.3.6.1.4.1.119.2.3.69.203.507.5.3.27.4.1.3
    ipeCfgRadiusGroupPrivLevelMappingEnable OBJECT-TYPE
        SYNTAX      INTEGER { invalid(0), disable(1), enable(2) }
        ACCESS      read-only
        STATUS      mandatory
        DESCRIPTION
            "Enable or disable privilege level mapping on this
             privilege level.
    
             disable : privilege level mapping is disabled.
             enable  : privilege level mapping is enabled.
    
             The system default value of this object shown below.
    
             PrivLevel=1, 7, 15 : enable
             other PrivLevel    : disable
    
             In case this object is set to disable, the system
             behave according to
             ipeCfgRadiusPrivLevelGeneralDefaultAction."
        DEFVAL      { disable }
        ::= { ipeCfgRadiusGroupPrivLevelMappingEntry 3 }
    
    -- 1.3.6.1.4.1.119.2.3.69.203.507.5.3.27.4.1.4
    ipeCfgRadiusGroupPrivLevelMappingGroup OBJECT-TYPE
        SYNTAX      DisplayString (SIZE(1..32))
        ACCESS      read-only
        STATUS      mandatory
        DESCRIPTION
            "Indicate group name correspond to privilege level.
             This object is effective only if
             ipeCfgRadiusGroupPrivLevelMappingEnable is enable.
             When the system received Access-Accept message with certain
             privilege level, login user has same privilege as this
             group.
    
             The system default value of this object shown below.
    
             PrivLevel=1  : Operator
             PrivLevel=7  : Config
             PrivLevel=15 : Admin
    
             The value should be registered group name registerd in
             the system (as ipeCfgAccountGroupName).
             The characters which can be used are '-', '_','0'-'9',
             'a'-'z' and 'A'-'Z'."
        ::= { ipeCfgRadiusGroupPrivLevelMappingEntry 4 }
    
    -- 1.3.6.1.4.1.119.2.3.69.203.507.5.3.28
    ipeCfgLldpGroup OBJECT IDENTIFIER
        ::= { ipeConfigurationGroup 28 }
    
    -- 1.3.6.1.4.1.119.2.3.69.203.507.5.3.28.1
    ipeCfgLldpTable OBJECT-TYPE
        SYNTAX      SEQUENCE OF IpeCfgLldpEntry
        ACCESS      not-accessible
        STATUS      mandatory
        DESCRIPTION
            "LLDP set up information table."
        ::= { ipeCfgLldpGroup 1 }
    
    -- 1.3.6.1.4.1.119.2.3.69.203.507.5.3.28.1.1
    ipeCfgLldpEntry OBJECT-TYPE
        SYNTAX      IpeCfgLldpEntry
        ACCESS      not-accessible
        STATUS      mandatory
        DESCRIPTION
            "entry of LLDP set up information table."
        INDEX       { ipeCfgLldpNEAddress, ipeCfgLldpIndex }
        ::= { ipeCfgLldpTable 1 }
    
    IpeCfgLldpEntry ::= SEQUENCE {
        ipeCfgLldpIndex                         INTEGER,
        ipeCfgLldpNEAddress                     IpAddress,
        ipeCfgLldpProprietaryModeMacAddress     MacAddress
    }
    
    -- 1.3.6.1.4.1.119.2.3.69.203.507.5.3.28.1.1.1
    ipeCfgLldpIndex OBJECT-TYPE
        SYNTAX      INTEGER (1)
        ACCESS      not-accessible
        STATUS      mandatory
        DESCRIPTION
            "The index of this table."
        ::= { ipeCfgLldpEntry 1 }
    
    -- 1.3.6.1.4.1.119.2.3.69.203.507.5.3.28.1.1.2
    ipeCfgLldpNEAddress OBJECT-TYPE
        SYNTAX      IpAddress
        ACCESS      not-accessible
        STATUS      mandatory
        DESCRIPTION
            "reserved."
        ::= { ipeCfgLldpEntry 2 }
    
    -- 1.3.6.1.4.1.119.2.3.69.203.507.5.3.28.1.1.3
    ipeCfgLldpProprietaryModeMacAddress OBJECT-TYPE
        SYNTAX      MacAddress
        ACCESS      read-only
        STATUS      mandatory
        DESCRIPTION
            "MAC address of LLDP Frame in NEC mode.
             This object is effective only if ipeCfgPortXXXXXLldpMode is set
             to proprietaryMode."
        DEFVAL      { '01004c01da50'H }
        ::= { ipeCfgLldpEntry 3 }
    
    -- 1.3.6.1.4.1.119.2.3.69.203.507.5.3.29
    ipeCfgMgmtTrafficGrop OBJECT IDENTIFIER
        ::= { ipeConfigurationGroup 29 }
    
    -- 1.3.6.1.4.1.119.2.3.69.203.507.5.3.29.1
    ipeCfgMgmtTrafficControlTable OBJECT-TYPE
        SYNTAX      SEQUENCE OF IpeCfgMgmtTrafficControlEntry
        ACCESS      not-accessible
        STATUS      mandatory
        DESCRIPTION
            "This table configures the M-plane traffic."
        ::= { ipeCfgMgmtTrafficGrop 1 }
    
    -- 1.3.6.1.4.1.119.2.3.69.203.507.5.3.29.1.1
    ipeCfgMgmtTrafficControlEntry OBJECT-TYPE
        SYNTAX      IpeCfgMgmtTrafficControlEntry
        ACCESS      not-accessible
        STATUS      mandatory
        DESCRIPTION
            ""
        INDEX       { ipeCfgMgmtTrafficControlNEAddress, ipeCfgMgmtTrafficControlIndex }
        ::= { ipeCfgMgmtTrafficControlTable 1 }
    
    IpeCfgMgmtTrafficControlEntry ::= SEQUENCE {
        ipeCfgMgmtTrafficControlIndex       INTEGER,
        ipeCfgMgmtTrafficControlNEAddress   IpAddress,
        ipeCfgMgmtTrafficRate               INTEGER,
        ipeCfgMgmtTraffcEgressCos           INTEGER
    }
    
    -- 1.3.6.1.4.1.119.2.3.69.203.507.5.3.29.1.1.1
    ipeCfgMgmtTrafficControlIndex OBJECT-TYPE
        SYNTAX      INTEGER (1)
        ACCESS      not-accessible
        STATUS      mandatory
        DESCRIPTION
            "Indef of this table."
        ::= { ipeCfgMgmtTrafficControlEntry 1 }
    
    -- 1.3.6.1.4.1.119.2.3.69.203.507.5.3.29.1.1.2
    ipeCfgMgmtTrafficControlNEAddress OBJECT-TYPE
        SYNTAX      IpAddress
        ACCESS      not-accessible
        STATUS      mandatory
        DESCRIPTION
            "reserved."
        ::= { ipeCfgMgmtTrafficControlEntry 2 }
    
    -- 1.3.6.1.4.1.119.2.3.69.203.507.5.3.29.1.1.3
    ipeCfgMgmtTrafficRate OBJECT-TYPE
        SYNTAX      INTEGER (0 | 500..10000)
        ACCESS      read-only
        STATUS      mandatory
        DESCRIPTION
            "The maximum bandwidth of M-plane traffic.
             This object limits the rate of ingress traffic and limits the
             rate of egress traffic to Radio Link (i.e. excluding the
             NMS/NE1/Inband traffic).
    
             Value '0' means the rate limit is disabled.
    
    
             range: 0,500~10000[iPASOLINK200/400/1000series/EX/iX],
                    0,500~ 2000[iPASOLINK VR series]"
        ::= { ipeCfgMgmtTrafficControlEntry 3 }
    
    -- 1.3.6.1.4.1.119.2.3.69.203.507.5.3.29.1.1.4
    ipeCfgMgmtTraffcEgressCos OBJECT-TYPE
        SYNTAX      INTEGER (0..8)
        ACCESS      read-only
        STATUS      mandatory
        DESCRIPTION
            "CoS value for M-plane egress traffic to Radio Link.
             When the CPU sends M-plane data to the Radio link, the frame has
             the CoS value which is configured by this object.
             And the agent controls the priority of egress traffic depending
             on this CoS value.
    
             range: 5~7[iPASOLINK200/400/1000series/EX/iX],
                    0~7,8(highest)[iPASOLINK VR series]"
        ::= { ipeCfgMgmtTrafficControlEntry 4 }
    
    -- 1.3.6.1.4.1.119.2.3.69.203.507.5.3.30
    ipeCfgMgmtInterfaceGroup OBJECT IDENTIFIER
        ::= { ipeConfigurationGroup 30 }
    
    -- 1.3.6.1.4.1.119.2.3.69.203.507.5.3.30.1
    ipeCfgMplaneInterfaceModeTable OBJECT-TYPE
        SYNTAX      SEQUENCE OF IpeCfgMplaneInterfaceModeEntry
        ACCESS      not-accessible
        STATUS      mandatory
        DESCRIPTION
            "This table contains management interface mode information."
        ::= { ipeCfgMgmtInterfaceGroup 1 }
    
    -- 1.3.6.1.4.1.119.2.3.69.203.507.5.3.30.1.1
    ipeCfgMplaneInterfaceModeEntry OBJECT-TYPE
        SYNTAX      IpeCfgMplaneInterfaceModeEntry
        ACCESS      not-accessible
        STATUS      mandatory
        DESCRIPTION
            ""
        INDEX       { ipeCfgMplaneInterfaceNEAddress, ipeCfgMplaneInterfaceModeIndex }
        ::= { ipeCfgMplaneInterfaceModeTable 1 }
    
    IpeCfgMplaneInterfaceModeEntry ::= SEQUENCE {
        ipeCfgMplaneInterfaceModeIndex  INTEGER,
        ipeCfgMplaneInterfaceNEAddress  IpAddress,
        ipeCfgMplaneInterfaceMode       INTEGER
    }
    
    -- 1.3.6.1.4.1.119.2.3.69.203.507.5.3.30.1.1.1
    ipeCfgMplaneInterfaceModeIndex OBJECT-TYPE
        SYNTAX      INTEGER (1)
        ACCESS      not-accessible
        STATUS      mandatory
        DESCRIPTION
            "Index of this table."
        ::= { ipeCfgMplaneInterfaceModeEntry 1 }
    
    -- 1.3.6.1.4.1.119.2.3.69.203.507.5.3.30.1.1.2
    ipeCfgMplaneInterfaceNEAddress OBJECT-TYPE
        SYNTAX      IpAddress
        ACCESS      not-accessible
        STATUS      mandatory
        DESCRIPTION
            "reserved."
        ::= { ipeCfgMplaneInterfaceModeEntry 2 }
    
    -- 1.3.6.1.4.1.119.2.3.69.203.507.5.3.30.1.1.3
    ipeCfgMplaneInterfaceMode OBJECT-TYPE
        SYNTAX      INTEGER { invalid(0), lct(1), nms(2) }
        ACCESS      read-only
        STATUS      mandatory
        DESCRIPTION
            "This object configures the interface mode. The object is
             available only for the system which has shared port for LCT
             interface and NMS interface."
        ::= { ipeCfgMplaneInterfaceModeEntry 3 }
    
    -- 1.3.6.1.4.1.119.2.3.69.203.507.5.4
    ipeCommunicationsGroup OBJECT IDENTIFIER
        ::= { system5 4 }
    
    -- 1.3.6.1.4.1.119.2.3.69.203.507.5.4.1
    ipeNeighborInfoTable OBJECT-TYPE
        SYNTAX      SEQUENCE OF IpeNeighborInfoEntry
        ACCESS      not-accessible
        STATUS      mandatory
        DESCRIPTION
            "Neighbor NE table."
        ::= { ipeCommunicationsGroup 1 }
    
    -- 1.3.6.1.4.1.119.2.3.69.203.507.5.4.1.1
    ipeNeighborInfoEntry OBJECT-TYPE
        SYNTAX      IpeNeighborInfoEntry
        ACCESS      not-accessible
        STATUS      mandatory
        DESCRIPTION
            "Neighbor NE entry."
        INDEX       { ipeNeighborInfoNEAddress, ipeNeighborInfoIndex }
        ::= { ipeNeighborInfoTable 1 }
    
    IpeNeighborInfoEntry ::= SEQUENCE {
        ipeNeighborInfoIndex        InterfaceIndex,
        ipeNeighborInfoNEAddress    IpAddress,
        ipeNeighborIpAddress        OCTET STRING,
        ipeNeighborIpv4Ipv6Address  OCTET STRING
    }
    
    -- 1.3.6.1.4.1.119.2.3.69.203.507.5.4.1.1.1
    ipeNeighborInfoIndex OBJECT-TYPE
        SYNTAX      InterfaceIndex
        ACCESS      not-accessible
        STATUS      mandatory
        DESCRIPTION
            "Index of table."
        ::= { ipeNeighborInfoEntry 1 }
    
    -- 1.3.6.1.4.1.119.2.3.69.203.507.5.4.1.1.2
    ipeNeighborInfoNEAddress OBJECT-TYPE
        SYNTAX      IpAddress
        ACCESS      not-accessible
        STATUS      mandatory
        DESCRIPTION
            ""
        ::= { ipeNeighborInfoEntry 2 }
    
    -- 1.3.6.1.4.1.119.2.3.69.203.507.5.4.1.1.3
    ipeNeighborIpAddress OBJECT-TYPE
        SYNTAX      OCTET STRING (SIZE(0..240))
        ACCESS      read-only
        STATUS      mandatory
        DESCRIPTION
            "[iPASOLINK200/400/1000series/EX/iX]
             Neighbor NE is displayed as unit of registration every eight
             bytes of Internet Protocol address (4byte) + Node TYPE(4byte).The
             number of maximum registration is 30 (240byte). Attention: ne2
             set the IpAddress only, do not set the Node type.
    
             [iPASOLINK VR series/iPASOLINK EX Advanced]
             The number of maximum registration is 13.
             Type(1byte) and Length(1byte) are common information is 2byte.
    
             Unit of registration of each neighbor as
             IPv4 Address(4bytes) + Node Type(4bytes) + MAC Address(6bytes) +
             ifindex(4bytes)."
        ::= { ipeNeighborInfoEntry 3 }
    
    -- 1.3.6.1.4.1.119.2.3.69.203.507.5.4.1.1.4
    ipeNeighborIpv4Ipv6Address OBJECT-TYPE
        SYNTAX      OCTET STRING (SIZE(0..512))
        ACCESS      read-only
        STATUS      mandatory
        DESCRIPTION
            "[EX CPRI]
             The number of maximum registration is 17 (510byte).
             Type(7bit) and Length(9bit) are common information is 2byte.
    
             Unit of registration of each neighbor as IPv6 Address(16byte) +
             IPv4 Address(4byte) + Node Type(4byte) + MAC address(6byte).
    
             [iPASOLINK VR series/iPASOLINK iX/iPASOLINK EX Advanced]
             The number of maximum registration is 15.
             Type(7bit) and Length(9bit) are common information is 2byte.
    
             Unit of registration of each neighbor as IPv6 Address(16bytes) +
             IPv4 Address(4bytes) + Node Type(4bytes) + MAC Address(6bytes) +
             ifindex(4bytes)."
        ::= { ipeNeighborInfoEntry 4 }
    
    -- 1.3.6.1.4.1.119.2.3.69.203.507.501
    pasoNeoIpe-common OBJECT IDENTIFIER
        ::= { ipasolinkIx 501 }
    
    -- 1.3.6.1.4.1.119.2.3.69.203.507.507
    pasoNeoIpe-ix OBJECT IDENTIFIER
        ::= { ipasolinkIx 507 }
    
END -- end of module MIB-EMS-IPASOLINK-IX-SYSTEM-MIB.
