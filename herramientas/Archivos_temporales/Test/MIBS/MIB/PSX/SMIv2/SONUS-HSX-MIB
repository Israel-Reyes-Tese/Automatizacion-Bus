--
-- This SMIv2 module has been generated by smidump 0.2-cvs. Do not edit.
--

SONUS-HSX-MIB DEFINITIONS ::= BEGIN

IMPORTS
    Counter32, Gauge32, Integer32, MODULE-IDENTITY, NOTIFICATION-TYPE, 
    OBJECT-TYPE, TimeTicks
        FROM SNMPv2-SMI
    sonusEventClass, sonusEventDescription, sonusEventLevel, 
    sonusEventTime
        FROM SONUS-COMMON-MIB
    sonusServicesMIBs
        FROM SONUS-SMI;

sonusHomeSubscriberServerMIB MODULE-IDENTITY
    LAST-UPDATED    "200603290000Z"
    ORGANIZATION    
            "Sonus Networks, Inc."
    CONTACT-INFO    
            "   Customer Support    
             Sonus Networks, Inc.
             250 Apollo Drive
             Chelmsford, MA 01824
             USA
             
             Tel: 978-614-8100
             Fax: 978-614-8609"
    DESCRIPTION     
            "The MIB Module for Home Subscriber Server Management."
    ::= { sonusServicesMIBs 29 }


sonusHomeSubscriberServerMIBObjects OBJECT IDENTIFIER
    ::= { sonusHomeSubscriberServerMIB 1 }

sonusHomeSubscriberServerStatistics OBJECT IDENTIFIER
    ::= { sonusHomeSubscriberServerMIBObjects 1 }

sonusHssCxCounters OBJECT IDENTIFIER
    ::= { sonusHomeSubscriberServerStatistics 1 }

sonusHssCxCountersIncomingSAR OBJECT-TYPE
    SYNTAX          Counter32
    MAX-ACCESS      read-only
    STATUS          current
    DESCRIPTION     
            "This counter keeps track of incoming Cx SAR requests."
    ::= { sonusHssCxCounters 1 }

sonusHssCxCountersIncomingMAR OBJECT-TYPE
    SYNTAX          Counter32
    MAX-ACCESS      read-only
    STATUS          current
    DESCRIPTION     
            "This counter keeps track of incoming Cx MAR requests."
    ::= { sonusHssCxCounters 2 }

sonusHssCxCountersIncomingUAR OBJECT-TYPE
    SYNTAX          Counter32
    MAX-ACCESS      read-only
    STATUS          current
    DESCRIPTION     
            "This counter keeps track of incoming Cx UAR requests."
    ::= { sonusHssCxCounters 3 }

sonusHssCxCountersIncomingLIR OBJECT-TYPE
    SYNTAX          Counter32
    MAX-ACCESS      read-only
    STATUS          current
    DESCRIPTION     
            "This counter keeps track of incoming Cx LIR requests."
    ::= { sonusHssCxCounters 4 }

sonusHssCxCountersOutgoingRTR OBJECT-TYPE
    SYNTAX          Counter32
    MAX-ACCESS      read-only
    STATUS          current
    DESCRIPTION     
            "This counter keeps track of outgoing Cx RTR requests."
    ::= { sonusHssCxCounters 5 }

sonusHssCxCountersOutgoingPPR OBJECT-TYPE
    SYNTAX          Counter32
    MAX-ACCESS      read-only
    STATUS          current
    DESCRIPTION     
            "This counter keeps track of outgoing Cx PPR requests."
    ::= { sonusHssCxCounters 6 }

sonusHssShCounters OBJECT IDENTIFIER
    ::= { sonusHomeSubscriberServerStatistics 2 }

sonusHssShCountersIncomingUDR OBJECT-TYPE
    SYNTAX          Counter32
    MAX-ACCESS      read-only
    STATUS          current
    DESCRIPTION     
            "This counter keeps track of incoming Sh UDR requests."
    ::= { sonusHssShCounters 1 }

sonusHssShCountersIncomingPUR OBJECT-TYPE
    SYNTAX          Counter32
    MAX-ACCESS      read-only
    STATUS          current
    DESCRIPTION     
            "This counter keeps track of incoming Sh PUR requests."
    ::= { sonusHssShCounters 2 }

sonusHssShCountersIncomingSNR OBJECT-TYPE
    SYNTAX          Counter32
    MAX-ACCESS      read-only
    STATUS          current
    DESCRIPTION     
            "This counter keeps track of incoming Sh SNR requests."
    ::= { sonusHssShCounters 3 }

sonusHssShCountersOutgoingPNR OBJECT-TYPE
    SYNTAX          Counter32
    MAX-ACCESS      read-only
    STATUS          current
    DESCRIPTION     
            "This counter keeps track of outgoing Sh PNR requests."
    ::= { sonusHssShCounters 4 }

sonusHssDiameterCounters OBJECT IDENTIFIER
    ::= { sonusHomeSubscriberServerStatistics 3 }

sonusHssDiameterCountersRequestTimeout OBJECT-TYPE
    SYNTAX          Counter32
    MAX-ACCESS      read-only
    STATUS          current
    DESCRIPTION     
            "This counter keeps track of timeouts for outgoing Diameter requests."
    ::= { sonusHssDiameterCounters 1 }

sonusHomeSubscriberServerMIBNotifications OBJECT IDENTIFIER
    ::= { sonusHomeSubscriberServerMIB 2 }

sonusHomeSubscriberServerMIBNotificationsPrefix OBJECT IDENTIFIER
    ::= { sonusHomeSubscriberServerMIBNotifications 0 }

sonusHomeSubscriberServerMIBNotificationsObjects OBJECT IDENTIFIER
    ::= { sonusHomeSubscriberServerMIBNotifications 1 }

sonusHssDiameterPeerName OBJECT-TYPE
    SYNTAX          OCTET STRING
    MAX-ACCESS      read-only
    STATUS          current
    DESCRIPTION     
            "Diameter Peer Name."
    ::= { sonusHomeSubscriberServerMIBNotificationsObjects 1 }

sonusHssPipeErrorCode OBJECT-TYPE
    SYNTAX          Integer32
    MAX-ACCESS      read-only
    STATUS          current
    DESCRIPTION     
            "The unix error code, if any, will be available in this field."
    ::= { sonusHomeSubscriberServerMIBNotificationsObjects 2 }

sonusHssUpNotification NOTIFICATION-TYPE
    OBJECTS         { sonusEventDescription, sonusEventClass, 
                      sonusEventLevel, sonusEventTime }
    STATUS          current
    DESCRIPTION     
            "SoftSwitch Hss is up."
    ::= { sonusHomeSubscriberServerMIBNotificationsPrefix 1 }

sonusHssDownNotification NOTIFICATION-TYPE
    OBJECTS         { sonusEventDescription, sonusEventClass, 
                      sonusEventLevel, sonusEventTime }
    STATUS          current
    DESCRIPTION     
            "SoftSwitch Hss is down."
    ::= { sonusHomeSubscriberServerMIBNotificationsPrefix 2 }

sonusHssDiameterPeerOpenNotification NOTIFICATION-TYPE
    OBJECTS         { sonusHssDiameterPeerName, sonusEventDescription, 
                      sonusEventClass, sonusEventLevel, sonusEventTime }
    STATUS          current
    DESCRIPTION     
            "SoftSwitch Hss Diameter Peer enters OPEN state."
    ::= { sonusHomeSubscriberServerMIBNotificationsPrefix 3 }

sonusHssDiameterPeerCloseNotification NOTIFICATION-TYPE
    OBJECTS         { sonusHssDiameterPeerName, sonusEventDescription, 
                      sonusEventClass, sonusEventLevel, sonusEventTime }
    STATUS          current
    DESCRIPTION     
            "SoftSwitch Hss Diameter Peer leaves OPEN state."
    ::= { sonusHomeSubscriberServerMIBNotificationsPrefix 4 }

sonusHssDiameterPendingReqestsHighNotification NOTIFICATION-TYPE
    OBJECTS         { sonusEventDescription, sonusEventClass, 
                      sonusEventLevel, sonusEventTime }
    STATUS          current
    DESCRIPTION     
            "SoftSwitch Hss Diameter pending request number crossed over
             high water mark (80% of MAX)."
    ::= { sonusHomeSubscriberServerMIBNotificationsPrefix 5 }

sonusHssDiameterPendingReqestsNotHighNotification NOTIFICATION-TYPE
    OBJECTS         { sonusEventDescription, sonusEventClass, 
                      sonusEventLevel, sonusEventTime }
    STATUS          current
    DESCRIPTION     
            "SoftSwitch Hss Diameter pending request number crossed under
             low water mark (70% of MAX)."
    ::= { sonusHomeSubscriberServerMIBNotificationsPrefix 6 }

sonusHssPipeCommunicationUpNotification NOTIFICATION-TYPE
    OBJECTS         { sonusEventDescription, sonusEventClass, 
                      sonusEventLevel, sonusEventTime }
    STATUS          current
    DESCRIPTION     
            "'hss' process establishes connection with master 'pipe' process."
    ::= { sonusHomeSubscriberServerMIBNotificationsPrefix 7 }

sonusHssPipeRegistrationSuccessNotification NOTIFICATION-TYPE
    OBJECTS         { sonusEventDescription, sonusEventClass, 
                      sonusEventLevel, sonusEventTime }
    STATUS          current
    DESCRIPTION     
            "'hss' process registers with master 'pipe' process."
    ::= { sonusHomeSubscriberServerMIBNotificationsPrefix 8 }

sonusHssPipeCommunicationDownNotification NOTIFICATION-TYPE
    OBJECTS         { sonusHssPipeErrorCode, sonusEventDescription, 
                      sonusEventClass, sonusEventLevel, sonusEventTime }
    STATUS          current
    DESCRIPTION     
            "'hss' process was unable to establish connection with master 'pipe' process."
    ::= { sonusHomeSubscriberServerMIBNotificationsPrefix 9 }

sonusHssPipeRegistrationFailureNotification NOTIFICATION-TYPE
    OBJECTS         { sonusHssPipeErrorCode, sonusEventDescription, 
                      sonusEventClass, sonusEventLevel, sonusEventTime }
    STATUS          current
    DESCRIPTION     
            "'hss' process was unable to register with master 'pipe' process."
    ::= { sonusHomeSubscriberServerMIBNotificationsPrefix 10 }

sonusHssPipeIOErrorNotification NOTIFICATION-TYPE
    OBJECTS         { sonusHssPipeErrorCode, sonusEventDescription, 
                      sonusEventClass, sonusEventLevel, sonusEventTime }
    STATUS          current
    DESCRIPTION     
            "'hss' process was unable to send/receive an update to 'pipe' process."
    ::= { sonusHomeSubscriberServerMIBNotificationsPrefix 11 }

END -- end of module SONUS-HSX-MIB.
