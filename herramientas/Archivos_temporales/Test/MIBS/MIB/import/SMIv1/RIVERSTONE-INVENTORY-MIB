--
-- This SMIv1 module has been generated by smidump 0.2-cvs. Do not edit.
--

RIVERSTONE-INVENTORY-MIB DEFINITIONS ::= BEGIN

IMPORTS
    entPhysicalIndex
        FROM ENTITY-MIB
    OBJECT-TYPE
        FROM RFC-1212
    riverstoneMibs
        FROM RIVERSTONE-SMI-MIB
    SnmpAdminString
        FROM SNMP-FRAMEWORK-MIB;

rsInventoryMIB OBJECT IDENTIFIER
    ::= { riverstoneMibs 40 }

-- rsInventoryMIB MODULE-IDENTITY
--     LAST-UPDATED    "200108220000Z"
--     ORGANIZATION    
--             "Riverstone Networks, Inc"
--     CONTACT-INFO    
--             "Riverstone Networks
--              Customer Service
--              
--               Postal:
--              Riverstone Networks, Inc
--              5200 Great America Parkway
--               Santa Clara CA 95054 USA
--              
--               PHONE:+1 408.878.6500
--               EMAIL: nms-eng@riverstonenet.com
--               WEB: http://www.riverstonenet.com"
--     DESCRIPTION     
--             "This module defines a schema to do an inventory of an RS system."
--     REVISION        "200108220000Z"
--     DESCRIPTION     
--             "Change the CLEI object to read-write. Delete fabric and submodule
--              groups."
--     REVISION        "200106190000Z"
--     DESCRIPTION     
--             "Comments from review meeting with NMS team. Delete all objects
--              pertaining to the state of the system. This MIB will focus on the
--              inventory of the system. The state of the system would be in 
--              another MIB. Get rid of all extra objects. Delete the following
--              tables: rsInventoryPortTable. Delete the following objects: 
--              rsInventoryChassisType, rsInventoryChassisMaxSlots, 
--              rsInventoryChassisNumModules, rsInventoryModuleType, 
--              rsInventoryModuleNumPorts, rsInventoryModuleState. Change name
--              from rstone-hardware-mib.txt to rstone-inventory-mib.txt. Delete
--              textual conventions RSChassisType, RSModuleType, RSModuleState, 
--              RSPortType, RSPortConnectorType. Change the length of 
--              RSModuleServiceString"
--     REVISION        "200106110000Z"
--     DESCRIPTION     
--             "Comments from Mike MacFaden. Use INTEGER only for enumerations, 
--              otherwise use Integer32. Use OBJECT-IDENTITY instead of 
--              OBJECT-IDENTIFIER? Don't use -1 for enumerations? Add more 
--              comments in REVISION DESCRIPTION. 
--              
--              Comments from Thippana Hongal. Change range of RSMemorySize to
--              start from 0. Rename the enumerations in RSChassisType. Give an
--              example of RSModuleServiceString? Rename enumerations for 
--              RSModuleState. Make the ordering of rsChassisMaxSlots and 
--              rsInventoryChassisNumModules consistent with their order in 
--              SEQUENCE RsInventoryChassisEntry. Give an example of 
--              rsInventoryChassisId. Add an object describing the position of
--              the modules in the chassis?"
--     REVISION        "200106010000Z"
--     DESCRIPTION     
--             "Comments from Kenshin Sakura. Add IA product line. Stop 
--              using internal names. Make RSModuleType enumerations consistent 
--              like this: <type><# of ports><bandwidth>. Capitalize the 
--              connector name in a more consistent matter. For example 
--              fiberSCsmLH from fiberScSMLH. Modify the description for 
--              rsInventoryModuleMemorySize so power supply and fan
--              would not be mentioned."
--     REVISION        "200105220000Z"
--     DESCRIPTION     
--             "First Version of the Riverstone Inventory MIB."
--     ::= { riverstoneMibs 40 }


RSMemorySize ::=
    INTEGER (0..2147483647)

-- RSMemorySize ::= TEXTUAL-CONVENTION
--     STATUS          mandatory
--     DESCRIPTION     
--             "An integer that represents the size of memory in Megabytes. 0
--              represents not-available or not-applicable value."
--     SYNTAX          INTEGER (0..2147483647)

RSModuleServiceString ::=
    OCTET STRING (SIZE(0..255))

-- RSModuleServiceString ::= TEXTUAL-CONVENTION
--     STATUS          mandatory
--     DESCRIPTION     
--             "A string that is unique to a module in production. This 
--              string is used by Service and Manufacturing to identify 
--              shipped inventory."
--     SYNTAX          OCTET STRING (SIZE(0..255))

rsInventoryMIBObjects OBJECT IDENTIFIER
    ::= { rsInventoryMIB 1 }

rsInventoryOther OBJECT IDENTIFIER
    ::= { rsInventoryMIBObjects 1 }

rsInventoryUnknown OBJECT IDENTIFIER
    ::= { rsInventoryMIBObjects 2 }

rsInventoryChassis OBJECT IDENTIFIER
    ::= { rsInventoryMIBObjects 3 }

rsInventoryChassisTable OBJECT-TYPE
    SYNTAX          SEQUENCE OF RsInventoryChassisEntry
    ACCESS          not-accessible
    STATUS          mandatory
    DESCRIPTION     
            ""
    ::= { rsInventoryChassis 1 }

rsInventoryChassisEntry OBJECT-TYPE
    SYNTAX          RsInventoryChassisEntry
    ACCESS          not-accessible
    STATUS          mandatory
    DESCRIPTION     
            ""
    INDEX           { entPhysicalIndex }
    ::= { rsInventoryChassisTable 1 }

RsInventoryChassisEntry ::=
    SEQUENCE {
        rsInventoryChassisId            SnmpAdminString,
        rsInventoryChassisAssetCLEI     SnmpAdminString
    }

rsInventoryChassisId OBJECT-TYPE
    SYNTAX          SnmpAdminString
    ACCESS          read-only
    STATUS          mandatory
    DESCRIPTION     
            "Operator defined serial number for this particular chassis."
    ::= { rsInventoryChassisEntry 1 }

rsInventoryChassisAssetCLEI OBJECT-TYPE
    SYNTAX          SnmpAdminString (SIZE(0 | 10))
    ACCESS          read-write
    STATUS          mandatory
    DESCRIPTION     
            "The CLEI (Common Language Equipment Identifier) code for 
             the chassis. If the string has length 0, then the physical entity 
             does not have a CLEI code assisgned to it. This object can be changed
             if the physical entity has incorrect or no CLEI code."
--     REFERENCE       
--             "Bellcore Technical reference GR-485-CORE, COMMON LANGUAGE
--              Equipment Processes and Guidelines, Issue 2, October, 1995."
    ::= { rsInventoryChassisEntry 2 }

rsInventoryBackplane OBJECT IDENTIFIER
    ::= { rsInventoryMIBObjects 4 }

rsInventoryPowerSupply OBJECT IDENTIFIER
    ::= { rsInventoryMIBObjects 6 }

rsInventoryPowerSupplyTable OBJECT-TYPE
    SYNTAX          SEQUENCE OF RsInventoryPowerSupplyEntry
    ACCESS          not-accessible
    STATUS          mandatory
    DESCRIPTION     
            "This table contains one row per power supply for each chassis."
    ::= { rsInventoryPowerSupply 1 }

rsInventoryPowerSupplyEntry OBJECT-TYPE
    SYNTAX          RsInventoryPowerSupplyEntry
    ACCESS          not-accessible
    STATUS          mandatory
    DESCRIPTION     
            "Each entry contains information for one power supply."
    INDEX           { entPhysicalIndex }
    ::= { rsInventoryPowerSupplyTable 1 }

RsInventoryPowerSupplyEntry ::=
    SEQUENCE {
        rsInventoryPowerSupplyAssetCLEI SnmpAdminString
    }

rsInventoryPowerSupplyAssetCLEI OBJECT-TYPE
    SYNTAX          SnmpAdminString (SIZE(0 | 10))
    ACCESS          read-write
    STATUS          mandatory
    DESCRIPTION     
            "The CLEI (Common Language Equipment Identifier) code for 
             this equipment. If the string has length 0, then the physical entity 
             does not have a CLEI code assisgned to it. This object can be changed
             if the physical entity has incorrect or no CLEI code."
--     REFERENCE       
--             "Bellcore Technical reference GR-485-CORE, COMMON LANGUAGE
--              Equipment Processes and Guidelines, Issue 2, October, 1995."
    ::= { rsInventoryPowerSupplyEntry 1 }

rsInventoryFan OBJECT IDENTIFIER
    ::= { rsInventoryMIBObjects 7 }

rsInventoryFanTable OBJECT-TYPE
    SYNTAX          SEQUENCE OF RsInventoryFanEntry
    ACCESS          not-accessible
    STATUS          mandatory
    DESCRIPTION     
            "This table contains one row per fan for each chassis."
    ::= { rsInventoryFan 1 }

rsInventoryFanEntry OBJECT-TYPE
    SYNTAX          RsInventoryFanEntry
    ACCESS          not-accessible
    STATUS          mandatory
    DESCRIPTION     
            "Each entry contains information for a fan."
    INDEX           { entPhysicalIndex }
    ::= { rsInventoryFanTable 1 }

RsInventoryFanEntry ::=
    SEQUENCE {
        rsInventoryFanAssetCLEI         SnmpAdminString
    }

rsInventoryFanAssetCLEI OBJECT-TYPE
    SYNTAX          SnmpAdminString (SIZE(0 | 10))
    ACCESS          read-write
    STATUS          mandatory
    DESCRIPTION     
            "The CLEI (Common Language Equipment Identifier) code for 
             this equipment. If the string has length 0, then the physical entity 
             does not have a CLEI code assisgned to it. This object can be changed
             if the physical entity has incorrect or no CLEI code."
--     REFERENCE       
--             "Bellcore Technical reference GR-485-CORE, COMMON LANGUAGE
--              Equipment Processes and Guidelines, Issue 2, October, 1995."
    ::= { rsInventoryFanEntry 1 }

rsInventorySensor OBJECT IDENTIFIER
    ::= { rsInventoryMIBObjects 8 }

rsInventoryModule OBJECT IDENTIFIER
    ::= { rsInventoryMIBObjects 9 }

rsInventoryModuleTable OBJECT-TYPE
    SYNTAX          SEQUENCE OF RsInventoryModuleEntry
    ACCESS          not-accessible
    STATUS          mandatory
    DESCRIPTION     
            ""
    ::= { rsInventoryModule 1 }

rsInventoryModuleEntry OBJECT-TYPE
    SYNTAX          RsInventoryModuleEntry
    ACCESS          not-accessible
    STATUS          mandatory
    DESCRIPTION     
            ""
    INDEX           { entPhysicalIndex }
    ::= { rsInventoryModuleTable 1 }

RsInventoryModuleEntry ::=
    SEQUENCE {
        rsInventoryModuleMemorySize     RSMemorySize,
        rsInventoryModuleServiceString  RSModuleServiceString,
        rsInventoryModuleAssetCLEI      SnmpAdminString
    }

rsInventoryModuleMemorySize OBJECT-TYPE
    SYNTAX          RSMemorySize
    ACCESS          read-only
    STATUS          mandatory
    DESCRIPTION     
            "System Memory size available on the Module. Reports
             -1 if no memory exists on this module."
    ::= { rsInventoryModuleEntry 1 }

rsInventoryModuleServiceString OBJECT-TYPE
    SYNTAX          RSModuleServiceString
    ACCESS          read-only
    STATUS          mandatory
    DESCRIPTION     
            "The service identifier string for this Card/Module.The board serial
             number is appended to the string too."
    ::= { rsInventoryModuleEntry 2 }

rsInventoryModuleAssetCLEI OBJECT-TYPE
    SYNTAX          SnmpAdminString (SIZE(0 | 10))
    ACCESS          read-write
    STATUS          mandatory
    DESCRIPTION     
            "The CLEI (Common Language Equipment Identifier) code for 
             the chassis. If the string has length 0, then the physical entity 
             does not have a CLEI code assisgned to it. This object can be changed
             if the physical entity has incorrect or no CLEI code."
--     REFERENCE       
--             "Bellcore Technical reference GR-485-CORE, COMMON LANGUAGE
--              Equipment Processes and Guidelines, Issue 2, October, 1995."
    ::= { rsInventoryModuleEntry 3 }

rsInventoryPort OBJECT IDENTIFIER
    ::= { rsInventoryMIBObjects 10 }

rsInventoryStack OBJECT IDENTIFIER
    ::= { rsInventoryMIBObjects 11 }

rsInventoryConformance OBJECT IDENTIFIER
    ::= { rsInventoryMIB 3 }

rsInventoryCompliances OBJECT IDENTIFIER
    ::= { rsInventoryConformance 1 }

rsInventoryGroups OBJECT IDENTIFIER
    ::= { rsInventoryConformance 2 }

rsChassisGroup OBJECT IDENTIFIER
    ::= { rsInventoryGroups 1 }

-- rsChassisGroup OBJECT-GROUP
--     OBJECTS         { rsInventoryChassisId, 
--                       rsInventoryChassisAssetCLEI }
--     STATUS          mandatory
--     DESCRIPTION     
--             ""
--     ::= { rsInventoryGroups 1 }

rsModuleGroup OBJECT IDENTIFIER
    ::= { rsInventoryGroups 2 }

-- rsModuleGroup OBJECT-GROUP
--     OBJECTS         { rsInventoryModuleMemorySize, 
--                       rsInventoryModuleServiceString, 
--                       rsInventoryModuleAssetCLEI }
--     STATUS          mandatory
--     DESCRIPTION     
--             ""
--     ::= { rsInventoryGroups 2 }

rsEnvGroup OBJECT IDENTIFIER
    ::= { rsInventoryGroups 3 }

-- rsEnvGroup OBJECT-GROUP
--     OBJECTS         { rsInventoryPowerSupplyAssetCLEI, 
--                       rsInventoryFanAssetCLEI }
--     STATUS          mandatory
--     DESCRIPTION     
--             ""
--     ::= { rsInventoryGroups 3 }

rsInventoryCompliance OBJECT IDENTIFIER
    ::= { rsInventoryCompliances 1 }

-- rsInventoryCompliance MODULE-COMPLIANCE
--     STATUS          mandatory
--     DESCRIPTION     
--             ""

--     MODULE          -- -- this module

--         MANDATORY-GROUPS    { rsChassisGroup, rsModuleGroup, 
--                       rsEnvGroup }

--     ::= { rsInventoryCompliances 1 }

END -- end of module RIVERSTONE-INVENTORY-MIB.
