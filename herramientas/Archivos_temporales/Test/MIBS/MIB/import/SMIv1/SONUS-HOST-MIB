--
-- This SMIv1 module has been generated by smidump 0.2-cvs. Do not edit.
--

SONUS-HOST-MIB DEFINITIONS ::= BEGIN

IMPORTS
    OBJECT-TYPE
        FROM RFC-1212
    TRAP-TYPE
        FROM RFC-1215
    DisplayString
        FROM SNMPv2-TC
    sonusEventClass, sonusEventDescription, sonusEventLevel, 
    sonusEventTime
        FROM SONUS-COMMON-MIB
    sonusSystemMIBs
        FROM SONUS-SMI;

sonusHostMIB OBJECT IDENTIFIER
    ::= { sonusSystemMIBs 12 }

-- sonusHostMIB MODULE-IDENTITY
--     LAST-UPDATED    "200811210000Z"
--     ORGANIZATION    
--             "Sonus Networks, Inc."
--     CONTACT-INFO    
--             "   Customer Support    
--              Sonus Networks, Inc.
--              250 Apollo Drive
--              Chelmsford, MA 01824
--              USA
--              
--              Tel: 978-614-8100
--              Fax: 978-614-8609"
--     DESCRIPTION     
--             "The MIB Module for application host monitoring related objects."
--     ::= { sonusSystemMIBs 12 }


sonusHostMIBObjects OBJECT IDENTIFIER
    ::= { sonusHostMIB 1 }

sonusHostNotifications OBJECT IDENTIFIER
    ::= { sonusHostMIB 2 }

sonusHostNotificationsPrefix OBJECT IDENTIFIER
    ::= { sonusHostNotifications 0 }

sonusHostResourceObjects OBJECT IDENTIFIER
    ::= { sonusHostMIB 3 }

sonusHostCpuID OBJECT-TYPE
    SYNTAX          DisplayString
    ACCESS          read-only
    STATUS          mandatory
    DESCRIPTION     
            "CPU identifier."
    ::= { sonusHostResourceObjects 1 }

sonusHostExecName OBJECT-TYPE
    SYNTAX          DisplayString
    ACCESS          read-only
    STATUS          mandatory
    DESCRIPTION     
            "Executable name."
    ::= { sonusHostResourceObjects 2 }

sonusHostFileSystemPath OBJECT-TYPE
    SYNTAX          DisplayString
    ACCESS          read-only
    STATUS          mandatory
    DESCRIPTION     
            "File system path name."
    ::= { sonusHostResourceObjects 3 }

sonusHostProcessID OBJECT-TYPE
    SYNTAX          Gauge
    ACCESS          read-only
    STATUS          mandatory
    DESCRIPTION     
            "Process ID."
    ::= { sonusHostResourceObjects 4 }

sonusHostManagementObjects OBJECT IDENTIFIER
    ::= { sonusHostMIB 4 }

sonusHostClrSet OBJECT-TYPE
    SYNTAX          INTEGER { clear(0), set(1) }
    ACCESS          read-only
    STATUS          mandatory
    DESCRIPTION     
            "Alarm clear and set flag for an event."
    ::= { sonusHostManagementObjects 1 }

sonusHostExpectedInstanceCount OBJECT-TYPE
    SYNTAX          Gauge
    ACCESS          read-only
    STATUS          mandatory
    DESCRIPTION     
            "Expected number of application instances."
    ::= { sonusHostManagementObjects 2 }

sonusHostSampleInstanceCount OBJECT-TYPE
    SYNTAX          Gauge
    ACCESS          read-only
    STATUS          mandatory
    DESCRIPTION     
            "Actual number of application instance from 
             sampling poll."
    ::= { sonusHostManagementObjects 3 }

-- sonusHostThresholdTriggerValue OBJECT-TYPE
--     SYNTAX          Counter64
--     ACCESS          read-only
--     STATUS          mandatory
--     DESCRIPTION     
--             "Threshold trigger value."
--     ::= { sonusHostManagementObjects 4 }

-- sonusHostThresholdSampleValue OBJECT-TYPE
--     SYNTAX          Counter64
--     ACCESS          read-only
--     STATUS          mandatory
--     DESCRIPTION     
--             "Actual sampling value that trigger a threshold-crossing event."
--     ::= { sonusHostManagementObjects 5 }

sonusHostThresholdName OBJECT-TYPE
    SYNTAX          DisplayString
    ACCESS          read-only
    STATUS          mandatory
    DESCRIPTION     
            "Threshold name configured for a threshold-crossing notification."
    ::= { sonusHostManagementObjects 6 }

sonusHostID OBJECT-TYPE
    SYNTAX          OCTET STRING (SIZE(1..32))
    ACCESS          read-only
    STATUS          mandatory
    DESCRIPTION     
            "The unique id or serial number for this host. The serial number is an ASCII representation of the hardware-specific serial number of the physical machine. It may contain non-numeric characters."
    ::= { sonusHostManagementObjects 7 }

sonusHostDiskDevName OBJECT-TYPE
    SYNTAX          OCTET STRING (SIZE(1..32))
    ACCESS          read-only
    STATUS          mandatory
    DESCRIPTION     
            "Disk device name in descriptive format. Example: cXtYdZ"
    ::= { sonusHostManagementObjects 8 }

sonusHostDiskErrorCount OBJECT-TYPE
    SYNTAX          Gauge
    ACCESS          read-only
    STATUS          mandatory
    DESCRIPTION     
            "Error count representing the difference between last and present polled value."
    ::= { sonusHostManagementObjects 9 }

sonusHostResourceUsageStats OBJECT IDENTIFIER
    ::= { sonusHostMIB 5 }

sonusHostCpuAvgUsage OBJECT-TYPE
    SYNTAX          INTEGER
    ACCESS          read-only
    STATUS          mandatory
    DESCRIPTION     
            "CPU usage as percentage.  Total CPU time is the sum of 4 values: user time, kernel time, IO-wait time, and idle time.  Each time value is calculated by taking the difference between present and the previous samples.  The sampling period is 5 seconds.  Usage is calculated using this formula: (user time+kernel time)/(user time+kernel time+IO-wait time+idle time)*100.  The value is round up to an integer. The calculation is performed for each CPU, and the usage value is the average."
    ::= { sonusHostResourceUsageStats 1 }

sonusHostMemUsage OBJECT-TYPE
    SYNTAX          INTEGER
    ACCESS          read-only
    STATUS          mandatory
    DESCRIPTION     
            "Host physical memory usage as percentage.  Usage value is calculated by dividing total in-use memory by total physical memory in the system.  Usage value is represented in percentage and round up to an integer.  Sampling period is 5 seconds.  "
    ::= { sonusHostResourceUsageStats 2 }

sonusHostSwapSpaceUsage OBJECT-TYPE
    SYNTAX          INTEGER
    ACCESS          read-only
    STATUS          mandatory
    DESCRIPTION     
            "Host swap space usage as percentage.  Usage value is calculated by dividing total in-use swap space by total available swap space.  Usage value is represented in percentage and it is round up to an integer.  Sampling period is 5 seconds. "
    ::= { sonusHostResourceUsageStats 3 }

sonusHostFsUsageTable OBJECT-TYPE
    SYNTAX          SEQUENCE OF SonusFileSystemUsageEntry
    ACCESS          not-accessible
    STATUS          mandatory
    DESCRIPTION     
            "Host File System Usage Table."
    ::= { sonusHostResourceUsageStats 4 }

sonusFileSystemUsageEntry OBJECT-TYPE
    SYNTAX          SonusFileSystemUsageEntry
    ACCESS          not-accessible
    STATUS          mandatory
    DESCRIPTION     
            "File System Usage table entry."
    INDEX           { sonusHostFileSystemPathName }
    ::= { sonusHostFsUsageTable 1 }

SonusFileSystemUsageEntry ::=
    SEQUENCE {
        sonusHostFileSystemPathName     DisplayString,
        sonusHostFileSystemUsage        INTEGER
    }

sonusHostFileSystemPathName OBJECT-TYPE
    SYNTAX          DisplayString
    ACCESS          read-only
    STATUS          mandatory
    DESCRIPTION     
            "File System Path Name."
    ::= { sonusFileSystemUsageEntry 1 }

sonusHostFileSystemUsage OBJECT-TYPE
    SYNTAX          INTEGER
    ACCESS          read-only
    STATUS          mandatory
    DESCRIPTION     
            "File System Usage as percentage.  Usage value is calculated by dividing disk space in use by total available space in a file system.  Usage value is represented in percentage and round up to an integer.  Sampling period is 60 seconds."
    ::= { sonusFileSystemUsageEntry 2 }

sonusHostApplResUsageTable OBJECT-TYPE
    SYNTAX          SEQUENCE OF SonusApplResUsageEntry
    ACCESS          not-accessible
    STATUS          mandatory
    DESCRIPTION     
            "Host application resource usage Table."
    ::= { sonusHostResourceUsageStats 5 }

sonusApplResUsageEntry OBJECT-TYPE
    SYNTAX          SonusApplResUsageEntry
    ACCESS          not-accessible
    STATUS          mandatory
    DESCRIPTION     
            "File System Usage table entry."
    INDEX           { sonusHostApplPID }
    ::= { sonusHostApplResUsageTable 1 }

SonusApplResUsageEntry ::=
    SEQUENCE {
        sonusHostApplPID                Gauge,
        sonusHostApplExecName           DisplayString,
        sonusHostApplCpuUsage           INTEGER,
        sonusHostApplMemSize            Gauge,
        sonusHostApplVMSize             Gauge
    }

sonusHostApplPID OBJECT-TYPE
    SYNTAX          Gauge
    ACCESS          read-only
    STATUS          mandatory
    DESCRIPTION     
            "Application process ID (PID)."
    ::= { sonusApplResUsageEntry 1 }

sonusHostApplExecName OBJECT-TYPE
    SYNTAX          DisplayString
    ACCESS          read-only
    STATUS          mandatory
    DESCRIPTION     
            "Application executable name."
    ::= { sonusApplResUsageEntry 2 }

sonusHostApplCpuUsage OBJECT-TYPE
    SYNTAX          INTEGER
    ACCESS          read-only
    STATUS          mandatory
    DESCRIPTION     
            "Application CPU usage as percentage.  Usage value is round up to an integer.  CPU usage is collected from the process table in operating system kernel. Sampling period is 30 seconds. "
    ::= { sonusApplResUsageEntry 3 }

sonusHostApplMemSize OBJECT-TYPE
    SYNTAX          Gauge
    ACCESS          read-only
    STATUS          mandatory
    DESCRIPTION     
            "Application physical memory size in kbytes.  Usage value is collected from process table in operating system kernel.  Sampling period is 30 seconds."
    ::= { sonusApplResUsageEntry 4 }

sonusHostApplVMSize OBJECT-TYPE
    SYNTAX          Gauge
    ACCESS          read-only
    STATUS          mandatory
    DESCRIPTION     
            "Application virtual memory usage size in kbytes.  Usage value is collected from process table in operating system kernel.  Sampling period is 30 seconds."
    ::= { sonusApplResUsageEntry 5 }

sonusHostCpuUsageRisingThresholdNotification TRAP-TYPE
    ENTERPRISE      sonusHostNotifications
    VARIABLES       { sonusHostCpuID, sonusHostThresholdTriggerValue, 
                      sonusHostThresholdSampleValue, sonusEventTime, 
                      sonusEventDescription, sonusEventClass, 
                      sonusEventLevel, sonusHostClrSet, 
                      sonusHostThresholdName, sonusHostID }
--     STATUS          mandatory
    DESCRIPTION     
            "Reports a CPU usage exceeds a predefind 
             threshold value."
    ::= 1

sonusHostCpuUsageFallingThresholdNotification TRAP-TYPE
    ENTERPRISE      sonusHostNotifications
    VARIABLES       { sonusHostCpuID, sonusHostThresholdTriggerValue, 
                      sonusHostThresholdSampleValue, sonusEventTime, 
                      sonusEventDescription, sonusEventClass, 
                      sonusEventLevel, sonusHostClrSet, 
                      sonusHostThresholdName, sonusHostID }
--     STATUS          mandatory
    DESCRIPTION     
            "Reports a CPU usage falls below a predefind 
             threshold value."
    ::= 2

sonusHostCpuAvgUsageRisingThresholdNotification TRAP-TYPE
    ENTERPRISE      sonusHostNotifications
    VARIABLES       { sonusHostThresholdTriggerValue, 
                      sonusHostThresholdSampleValue, sonusEventTime, 
                      sonusEventDescription, sonusEventClass, 
                      sonusEventLevel, sonusHostClrSet, 
                      sonusHostThresholdName, sonusHostID }
--     STATUS          mandatory
    DESCRIPTION     
            "Report average CPU usage exceeds a threshold 
             value."
    ::= 3

sonusHostCpuAvgUsageFallingThresholdNotification TRAP-TYPE
    ENTERPRISE      sonusHostNotifications
    VARIABLES       { sonusHostThresholdTriggerValue, 
                      sonusHostThresholdSampleValue, sonusEventTime, 
                      sonusEventDescription, sonusEventClass, 
                      sonusEventLevel, sonusHostClrSet, 
                      sonusHostThresholdName, sonusHostID }
--     STATUS          mandatory
    DESCRIPTION     
            "Report average CPU usage falls below a threshold 
             value."
    ::= 4

sonusHostFsUsageRisingThresholdNotification TRAP-TYPE
    ENTERPRISE      sonusHostNotifications
    VARIABLES       { sonusHostFileSystemPath, 
                      sonusHostThresholdTriggerValue, 
                      sonusHostThresholdSampleValue, sonusEventTime, 
                      sonusEventDescription, sonusEventClass, 
                      sonusEventLevel, sonusHostClrSet, 
                      sonusHostThresholdName, sonusHostID }
--     STATUS          mandatory
    DESCRIPTION     
            "Reports usage of a file system exceeds a predefined
             threshold value."
    ::= 5

sonusHostFsUsageFallingThresholdNotification TRAP-TYPE
    ENTERPRISE      sonusHostNotifications
    VARIABLES       { sonusHostFileSystemPath, 
                      sonusHostThresholdTriggerValue, 
                      sonusHostThresholdSampleValue, sonusEventTime, 
                      sonusEventDescription, sonusEventClass, 
                      sonusEventLevel, sonusHostClrSet, 
                      sonusHostThresholdName, sonusHostID }
--     STATUS          mandatory
    DESCRIPTION     
            "Reports usage of a file system falls below 
             a predefined threshold value."
    ::= 6

sonusHostMemUsageRisingThrshldNotification TRAP-TYPE
    ENTERPRISE      sonusHostNotifications
    VARIABLES       { sonusHostThresholdTriggerValue, 
                      sonusHostThresholdSampleValue, sonusEventTime, 
                      sonusEventDescription, sonusEventClass, 
                      sonusEventLevel, sonusHostClrSet, 
                      sonusHostThresholdName, sonusHostID }
--     STATUS          mandatory
    DESCRIPTION     
            "Reports memory usage of the host exceeds a 
             given threshold value."
    ::= 7

sonusHostMemUsageFallingThrshldNotification TRAP-TYPE
    ENTERPRISE      sonusHostNotifications
    VARIABLES       { sonusHostThresholdTriggerValue, 
                      sonusHostThresholdSampleValue, sonusEventTime, 
                      sonusEventDescription, sonusEventClass, 
                      sonusEventLevel, sonusHostClrSet, 
                      sonusHostThresholdName, sonusHostID }
--     STATUS          mandatory
    DESCRIPTION     
            "Reports memory usage of the host falls below a
             given threshold value."
    ::= 8

sonusHostSwapUsageRisingThresholdNotification TRAP-TYPE
    ENTERPRISE      sonusHostNotifications
    VARIABLES       { sonusHostThresholdTriggerValue, 
                      sonusHostThresholdSampleValue, sonusEventTime, 
                      sonusEventDescription, sonusEventClass, 
                      sonusEventLevel, sonusHostClrSet, 
                      sonusHostThresholdName, sonusHostID }
--     STATUS          mandatory
    DESCRIPTION     
            "Reports the swap space usage exceeds a given 
             threshold."
    ::= 9

sonusHostSwapUsageFallingThresholdNotification TRAP-TYPE
    ENTERPRISE      sonusHostNotifications
    VARIABLES       { sonusHostThresholdTriggerValue, 
                      sonusHostThresholdSampleValue, sonusEventTime, 
                      sonusEventDescription, sonusEventClass, 
                      sonusEventLevel, sonusHostClrSet, 
                      sonusHostThresholdName, sonusHostID }
--     STATUS          mandatory
    DESCRIPTION     
            "Reports the swap space usage exceeds a given 
             threshold."
    ::= 10

sonusHostApplicationRuntimeErrorNotification TRAP-TYPE
    ENTERPRISE      sonusHostNotifications
    VARIABLES       { sonusHostExecName, sonusHostExpectedInstanceCount, 
                      sonusHostSampleInstanceCount, sonusEventTime, 
                      sonusEventDescription, sonusEventClass, 
                      sonusEventLevel, sonusHostID }
--     STATUS          mandatory
    DESCRIPTION     
            "Reports runtime errors occur by detecting
             the number of application running instances 
             does not match the expected number."
    ::= 11

sonusHostApplicationRuntimeErrorRecoverNotification TRAP-TYPE
    ENTERPRISE      sonusHostNotifications
    VARIABLES       { sonusHostExecName, sonusHostExpectedInstanceCount, 
                      sonusHostSampleInstanceCount, sonusEventTime, 
                      sonusEventDescription, sonusEventClass, 
                      sonusEventLevel, sonusHostID }
--     STATUS          mandatory
    DESCRIPTION     
            "Informs the runtime errors report previously 
             is recovered."
    ::= 12

sonusHostApplicationExitNotification TRAP-TYPE
    ENTERPRISE      sonusHostNotifications
    VARIABLES       { sonusHostExecName, sonusHostProcessID, 
                      sonusEventTime, sonusEventDescription, 
                      sonusEventClass, sonusEventLevel, sonusHostID }
--     STATUS          mandatory
    DESCRIPTION     
            "Reports a previously running application 
             exits."
    ::= 13

sonusHostApplicationStartupNotification TRAP-TYPE
    ENTERPRISE      sonusHostNotifications
    VARIABLES       { sonusHostExecName, sonusHostProcessID, 
                      sonusEventTime, sonusEventDescription, 
                      sonusEventClass, sonusEventLevel, sonusHostID }
--     STATUS          mandatory
    DESCRIPTION     
            "Informs an application just starts up."
    ::= 14

sonusHostApplCpuUsageRisingThresholdNotification TRAP-TYPE
    ENTERPRISE      sonusHostNotifications
    VARIABLES       { sonusHostExecName, sonusHostThresholdTriggerValue, 
                      sonusHostThresholdSampleValue, sonusHostProcessID, 
                      sonusEventTime, sonusEventDescription, 
                      sonusEventClass, sonusEventLevel, sonusHostClrSet, 
                      sonusHostThresholdName, sonusHostID }
--     STATUS          mandatory
    DESCRIPTION     
            "Reports an application's instance usage exceeds 
             a given threhold value."
    ::= 15

sonusHostApplCpuUsageFallingThresholdNotification TRAP-TYPE
    ENTERPRISE      sonusHostNotifications
    VARIABLES       { sonusHostExecName, sonusHostThresholdTriggerValue, 
                      sonusHostThresholdSampleValue, sonusHostProcessID, 
                      sonusEventTime, sonusEventDescription, 
                      sonusEventClass, sonusEventLevel, sonusHostClrSet, 
                      sonusHostThresholdName, sonusHostID }
--     STATUS          mandatory
    DESCRIPTION     
            "Reports an application's instance usage falling 
             a given threhold value."
    ::= 16

sonusHostApplMemUsageRisingThresholdNotification TRAP-TYPE
    ENTERPRISE      sonusHostNotifications
    VARIABLES       { sonusHostExecName, sonusHostThresholdTriggerValue, 
                      sonusHostThresholdSampleValue, sonusHostProcessID, 
                      sonusEventTime, sonusEventDescription, 
                      sonusEventClass, sonusEventLevel, sonusHostClrSet, 
                      sonusHostThresholdName, sonusHostID }
--     STATUS          mandatory
    DESCRIPTION     
            "Reports an application instance's memory usage
             exceeds a given threshold value."
    ::= 17

sonusHostApplMemUsageFallingThresholdNotification TRAP-TYPE
    ENTERPRISE      sonusHostNotifications
    VARIABLES       { sonusHostExecName, sonusHostThresholdTriggerValue, 
                      sonusHostThresholdSampleValue, sonusHostProcessID, 
                      sonusEventTime, sonusEventDescription, 
                      sonusEventClass, sonusEventLevel, sonusHostClrSet, 
                      sonusHostThresholdName, sonusHostID }
--     STATUS          mandatory
    DESCRIPTION     
            "Reports an application instance's memory usage
             falls below a given threshold value."
    ::= 18

sonusHostDiskMonSoftErrorNotification TRAP-TYPE
    ENTERPRISE      sonusHostNotifications
    VARIABLES       { sonusEventTime, sonusEventDescription, 
                      sonusEventClass, sonusEventLevel, sonusHostID, 
                      sonusHostDiskDevName, sonusHostDiskErrorCount }
--     STATUS          mandatory
    DESCRIPTION     
            "Reports that the soft error count for the disk 
             identified by sonusHostDiskDevName has increased by 
             the value of sonusHostDiskErrorCount since the  
             last poll."
    ::= 19

sonusHostDiskMonHardErrorNotification TRAP-TYPE
    ENTERPRISE      sonusHostNotifications
    VARIABLES       { sonusEventTime, sonusEventDescription, 
                      sonusEventClass, sonusEventLevel, sonusHostID, 
                      sonusHostDiskDevName, sonusHostDiskErrorCount }
--     STATUS          mandatory
    DESCRIPTION     
            "Reports that the soft error count for the disk 
             identified by sonusHostDiskDevName has increased by 
             the value of sonusHostDiskErrorCount since the  
             last poll."
    ::= 20

sonusHostDiskMonTransportErrorNotification TRAP-TYPE
    ENTERPRISE      sonusHostNotifications
    VARIABLES       { sonusEventTime, sonusEventDescription, 
                      sonusEventClass, sonusEventLevel, sonusHostID, 
                      sonusHostDiskDevName, sonusHostDiskErrorCount }
--     STATUS          mandatory
    DESCRIPTION     
            "Reports that the transport error count for the disk 
             identified by sonusHostDiskDevName has increased by 
             the value of sonusHostDiskErrorCount since the  
             last poll."
    ::= 21

sonusHostDiskMonSMARTErrorNotification TRAP-TYPE
    ENTERPRISE      sonusHostNotifications
    VARIABLES       { sonusEventTime, sonusEventDescription, 
                      sonusEventClass, sonusEventLevel, sonusHostID }
--     STATUS          mandatory
    DESCRIPTION     
            "SMARTmon error was reported.  Detailed error is specified in sonusEventDescription."
    ::= 22

sonusHostDiskMonSMARTWarnNotification TRAP-TYPE
    ENTERPRISE      sonusHostNotifications
    VARIABLES       { sonusEventTime, sonusEventDescription, 
                      sonusEventClass, sonusEventLevel, sonusHostID }
--     STATUS          mandatory
    DESCRIPTION     
            "SMARTmon warning was reported.  Detailed message is specified in sonusEventDescription."
    ::= 23

END -- end of module SONUS-HOST-MIB.
