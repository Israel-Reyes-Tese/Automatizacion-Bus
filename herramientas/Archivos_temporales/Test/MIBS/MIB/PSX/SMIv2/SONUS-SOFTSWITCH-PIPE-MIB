--
-- This SMIv2 module has been generated by smidump 0.2-cvs. Do not edit.
--

SONUS-SOFTSWITCH-PIPE-MIB DEFINITIONS ::= BEGIN

IMPORTS
    MODULE-IDENTITY, NOTIFICATION-TYPE
        FROM SNMPv2-SMI
    sonusEventClass, sonusEventDescription, sonusEventLevel, 
    sonusEventTime
        FROM SONUS-COMMON-MIB
    sonusServicesMIBs
        FROM SONUS-SMI
    sonusSoftSwitchTMAddressNature, sonusSoftSwitchTMElementType, 
    sonusSoftSwitchTMIdentifier1, sonusSoftSwitchTMIdentifier2, 
    sonusSoftSwitchTMProvControlType
        FROM SONUS-SOFTSWITCH-MIB;

sonusSoftSwitchPIPEMIB MODULE-IDENTITY
    LAST-UPDATED    "200211040000Z"
    ORGANIZATION    
            "Sonus Networks, Inc."
    CONTACT-INFO    
            "   Customer Support    
             Sonus Networks, Inc.
             250 Apollo Drive
             Chelmsford, MA 01824
             USA
             
             Tel: 978-614-8100
             Fax: 978-614-8609"
    DESCRIPTION     
            "The MIB Module for SoftSwitch PIPE Management."
    ::= { sonusServicesMIBs 18 }


sonusSoftSwitchPIPEMIBObjects OBJECT IDENTIFIER
    ::= { sonusSoftSwitchPIPEMIB 1 }

sonusSoftSwitchPIPEMIBNotifications OBJECT IDENTIFIER
    ::= { sonusSoftSwitchPIPEMIB 2 }

sonusSoftSwitchPIPEMIBNotificationsPrefix OBJECT IDENTIFIER
    ::= { sonusSoftSwitchPIPEMIBNotifications 0 }

sonusSoftSwitchPIPEMIBNotificationsObjects OBJECT IDENTIFIER
    ::= { sonusSoftSwitchPIPEMIBNotifications 1 }

sonusSoftSwitchPipeDownNotification NOTIFICATION-TYPE
    OBJECTS         { sonusEventDescription, sonusEventClass, 
                      sonusEventLevel, sonusEventTime }
    STATUS          current
    DESCRIPTION     
            "PIPE is down"
    ::= { sonusSoftSwitchPIPEMIBNotificationsPrefix 1 }

sonusSoftSwitchPipeUpNotification NOTIFICATION-TYPE
    OBJECTS         { sonusEventDescription, sonusEventClass, 
                      sonusEventLevel, sonusEventTime }
    STATUS          current
    DESCRIPTION     
            "PIPE is up"
    ::= { sonusSoftSwitchPIPEMIBNotificationsPrefix 2 }

sonusSoftSwitchPipeTMControlProvisionedNotification NOTIFICATION-TYPE
    OBJECTS         { sonusSoftSwitchTMElementType, 
                      sonusSoftSwitchTMIdentifier1, 
                      sonusSoftSwitchTMIdentifier2, 
                      sonusSoftSwitchTMProvControlType, 
                      sonusSoftSwitchTMAddressNature, 
                      sonusEventDescription, sonusEventClass, 
                      sonusEventLevel, sonusEventTime }
    STATUS          current
    DESCRIPTION     
            "A traffic control has been provisioned."
    ::= { sonusSoftSwitchPIPEMIBNotificationsPrefix 3 }

sonusSoftSwitchPipeTMControlRemovedNotification NOTIFICATION-TYPE
    OBJECTS         { sonusSoftSwitchTMElementType, 
                      sonusSoftSwitchTMIdentifier1, 
                      sonusSoftSwitchTMIdentifier2, 
                      sonusSoftSwitchTMProvControlType, 
                      sonusSoftSwitchTMAddressNature, 
                      sonusEventDescription, sonusEventClass, 
                      sonusEventLevel, sonusEventTime }
    STATUS          current
    DESCRIPTION     
            "A traffic control has been removed."
    ::= { sonusSoftSwitchPIPEMIBNotificationsPrefix 4 }

sonusSoftSwitchPipeTMControlModifiedNotification NOTIFICATION-TYPE
    OBJECTS         { sonusSoftSwitchTMElementType, 
                      sonusSoftSwitchTMIdentifier1, 
                      sonusSoftSwitchTMIdentifier2, 
                      sonusSoftSwitchTMProvControlType, 
                      sonusSoftSwitchTMAddressNature, 
                      sonusEventDescription, sonusEventClass, 
                      sonusEventLevel, sonusEventTime }
    STATUS          current
    DESCRIPTION     
            "A traffic control has been modified."
    ::= { sonusSoftSwitchPIPEMIBNotificationsPrefix 5 }

sonusSoftSwitchMasterKeyNotification NOTIFICATION-TYPE
    OBJECTS         { sonusEventDescription, sonusEventClass, 
                      sonusEventLevel, sonusEventTime }
    STATUS          current
    DESCRIPTION     
            "Master Key has not been Configured.Please Configure Master Key"
    ::= { sonusSoftSwitchPIPEMIBNotificationsPrefix 6 }

END -- end of module SONUS-SOFTSWITCH-PIPE-MIB.
