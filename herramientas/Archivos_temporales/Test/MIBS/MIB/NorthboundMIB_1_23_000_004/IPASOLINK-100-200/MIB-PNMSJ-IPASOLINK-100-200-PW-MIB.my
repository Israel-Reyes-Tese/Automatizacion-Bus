--
-- MIB-PNMSJ-IPASOLINK-100-200-PW-MIB.my
-- Monday, August 29, 2011
--

	MIB-PNMSJ-IPASOLINK-100-200-PW-MIB DEFINITIONS ::= BEGIN
 
		IMPORTS
			InterfaceIndex			
				FROM IF-MIB			
			OBJECT-TYPE			
				FROM RFC-1212			
			enterprises, IpAddress			
				FROM RFC1155-SMI			
			DisplayString			
				FROM RFC1213-MIB;
	
	
--
-- Type definitions
--
	
		IpePwIndex ::= INTEGER (1..2147483647)

		RowStatus ::= INTEGER
			{
			active(1),
			notInService(2),
			notReady(3),
			createAndGo(4),
			createAndWait(5),
			destroy(6)
			}

		IpeAtmVpi ::= INTEGER (0..255)

		IpeAtmVci ::= INTEGER (32..65535)

		IpeEnableDisableValue ::= INTEGER
			{
			invalid(0),
			disabled(1),
			enabled(2)
			}

		IpeVlanIndex ::= INTEGER (1..4094)

		MacAddress ::= OCTET STRING (SIZE (6))

		IpeExpBitValue ::= INTEGER (0..7)

		IpeLabelIndex ::= INTEGER (0..1048575)

		IpeVlanIndexOrZero ::= INTEGER (0..4094)

	
--
-- Node definitions
--
	
		-- 1.3.6.1.4.1.119
		nec OBJECT IDENTIFIER ::= { enterprises 119 }

		
		-- 1.3.6.1.4.1.119.2
		nec-mib OBJECT IDENTIFIER ::= { nec 2 }

		
		-- 1.3.6.1.4.1.119.2.3
		necProductDepend OBJECT IDENTIFIER ::= { nec-mib 3 }

		
		-- 1.3.6.1.4.1.119.2.3.69
		radioEquipment OBJECT IDENTIFIER ::= { necProductDepend 69 }

		
		-- 1.3.6.1.4.1.119.2.3.69.203
		commonPnms OBJECT IDENTIFIER ::= { radioEquipment 203 }

		
		-- 1.3.6.1.4.1.119.2.3.69.203.502
		ipasolink200 OBJECT IDENTIFIER ::= { commonPnms 502 }

		
		-- 1.3.6.1.4.1.119.2.3.69.203.502.501
		pasoNeoIpe-common OBJECT IDENTIFIER ::= { ipasolink200 501 }

		
		-- 1.3.6.1.4.1.119.2.3.69.203.502.501.5
		provisioningGroup OBJECT IDENTIFIER ::= { pasoNeoIpe-common 5 }

		
		-- 1.3.6.1.4.1.119.2.3.69.203.502.501.5.42
		provPwGroup OBJECT IDENTIFIER ::= { provisioningGroup 42 }

		
		-- 1.3.6.1.4.1.119.2.3.69.203.502.501.5.42.4
		provPwTdmLineTable OBJECT-TYPE
			SYNTAX SEQUENCE OF ProvPwTdmLineEntry
			ACCESS not-accessible
			STATUS mandatory
			DESCRIPTION
				" "
			::= { provPwGroup 4 }

		
		-- 1.3.6.1.4.1.119.2.3.69.203.502.501.5.42.4.1
		provPwTdmLineEntry OBJECT-TYPE
			SYNTAX ProvPwTdmLineEntry
			ACCESS not-accessible
			STATUS mandatory
			DESCRIPTION
				" "
			INDEX { provPwTdmLineNEAddress, provPwTdmLineIfIndex }
			::= { provPwTdmLineTable 1 }

		
		ProvPwTdmLineEntry ::=
			SEQUENCE { 
				provPwTdmLineIfIndex
					InterfaceIndex,
				provPwTdmLineNEAddress
					IpAddress,
				provPwTdmLineFrameMode
					INTEGER,
				provPwTdmLineCasMode
					IpeEnableDisableValue,
				provPwTdmLineCrc4Mode
					IpeEnableDisableValue,
				provPwTdmLineJtrBfrDepth
					INTEGER,
				provPwTdmLineDstMacCheck
					IpeEnableDisableValue
			 }

		-- 1.3.6.1.4.1.119.2.3.69.203.502.501.5.42.4.1.1
		provPwTdmLineIfIndex OBJECT-TYPE
			SYNTAX InterfaceIndex
			ACCESS read-only
			STATUS mandatory
			DESCRIPTION
				" "
			::= { provPwTdmLineEntry 1 }

		
		-- 1.3.6.1.4.1.119.2.3.69.203.502.501.5.42.4.1.2
		provPwTdmLineNEAddress OBJECT-TYPE
			SYNTAX IpAddress
			ACCESS read-only
			STATUS mandatory
			DESCRIPTION
				" "
			::= { provPwTdmLineEntry 2 }

		
		-- 1.3.6.1.4.1.119.2.3.69.203.502.501.5.42.4.1.3
		provPwTdmLineFrameMode OBJECT-TYPE
			SYNTAX INTEGER
				{
				invalid(0),
				unframed(1),
				framed(2)
				}
			ACCESS read-only
			STATUS mandatory
			DESCRIPTION
				" "
			DEFVAL { unframed }
			::= { provPwTdmLineEntry 3 }

		
		-- 1.3.6.1.4.1.119.2.3.69.203.502.501.5.42.4.1.4
		provPwTdmLineCasMode OBJECT-TYPE
			SYNTAX IpeEnableDisableValue
			ACCESS read-only
			STATUS mandatory
			DESCRIPTION
				" "
			DEFVAL { disabled }
			::= { provPwTdmLineEntry 4 }

		
		-- 1.3.6.1.4.1.119.2.3.69.203.502.501.5.42.4.1.5
		provPwTdmLineCrc4Mode OBJECT-TYPE
			SYNTAX IpeEnableDisableValue
			ACCESS read-only
			STATUS mandatory
			DESCRIPTION
				" "
			DEFVAL { disabled }
			::= { provPwTdmLineEntry 5 }

		
		-- 1.3.6.1.4.1.119.2.3.69.203.502.501.5.42.4.1.6
		provPwTdmLineJtrBfrDepth OBJECT-TYPE
			SYNTAX INTEGER
				{
				invalid(0),
				jtr2ms(1),
				jtr4ms(2),
				jtr8ms(3),
				jtr16ms(4),
				jtr32ms(5),
				jtr64ms(6),
				jtr128ms(7)
				}
			ACCESS read-only
			STATUS mandatory
			DESCRIPTION
				" "
			DEFVAL { jtr8ms }
			::= { provPwTdmLineEntry 6 }

		
		-- 1.3.6.1.4.1.119.2.3.69.203.502.501.5.42.4.1.7
		provPwTdmLineDstMacCheck OBJECT-TYPE
			SYNTAX IpeEnableDisableValue
			ACCESS read-only
			STATUS mandatory
			DESCRIPTION
				" "
			DEFVAL { enabled }
			::= { provPwTdmLineEntry 7 }

		
		-- 1.3.6.1.4.1.119.2.3.69.203.502.501.5.42.5
		provPwTdmTable OBJECT-TYPE
			SYNTAX SEQUENCE OF ProvPwTdmEntry
			ACCESS not-accessible
			STATUS mandatory
			DESCRIPTION
				" "
			::= { provPwGroup 5 }

		
		-- 1.3.6.1.4.1.119.2.3.69.203.502.501.5.42.5.1
		provPwTdmEntry OBJECT-TYPE
			SYNTAX ProvPwTdmEntry
			ACCESS not-accessible
			STATUS mandatory
			DESCRIPTION
				" "
			INDEX { provPwTdmNEAddress, provPwTdmPwIndex }
			::= { provPwTdmTable 1 }

		
		ProvPwTdmEntry ::=
			SEQUENCE { 
				provPwTdmPwIndex
					IpePwIndex,
				provPwTdmNEAddress
					IpAddress,
				provPwTdmIfIndex
					InterfaceIndex,
				provPwTdmRtpHdrUsed
					IpeEnableDisableValue,
				provPwTdmFrameLength
					INTEGER,
				provPwTdmEncapMode
					INTEGER,
				provPwTdmRowStatus
					RowStatus,
				provPwTdmAdaptiveClkSource
					IpeEnableDisableValue
			 }

		-- 1.3.6.1.4.1.119.2.3.69.203.502.501.5.42.5.1.1
		provPwTdmPwIndex OBJECT-TYPE
			SYNTAX IpePwIndex
			ACCESS read-only
			STATUS mandatory
			DESCRIPTION
				" "
			::= { provPwTdmEntry 1 }

		
		-- 1.3.6.1.4.1.119.2.3.69.203.502.501.5.42.5.1.2
		provPwTdmNEAddress OBJECT-TYPE
			SYNTAX IpAddress
			ACCESS read-only
			STATUS mandatory
			DESCRIPTION
				" "
			::= { provPwTdmEntry 2 }

		
		-- 1.3.6.1.4.1.119.2.3.69.203.502.501.5.42.5.1.3
		provPwTdmIfIndex OBJECT-TYPE
			SYNTAX InterfaceIndex
			ACCESS read-only
			STATUS mandatory
			DESCRIPTION
				" "
			::= { provPwTdmEntry 3 }

		
		-- 1.3.6.1.4.1.119.2.3.69.203.502.501.5.42.5.1.4
		provPwTdmRtpHdrUsed OBJECT-TYPE
			SYNTAX IpeEnableDisableValue
			ACCESS read-only
			STATUS mandatory
			DESCRIPTION
				" "
			DEFVAL { disabled }
			::= { provPwTdmEntry 4 }

		
		-- 1.3.6.1.4.1.119.2.3.69.203.502.501.5.42.5.1.5
		provPwTdmFrameLength OBJECT-TYPE
			SYNTAX INTEGER (1..8)
			ACCESS read-only
			STATUS mandatory
			DESCRIPTION
				" "
			DEFVAL { 8 }
			::= { provPwTdmEntry 5 }

		
		-- 1.3.6.1.4.1.119.2.3.69.203.502.501.5.42.5.1.6
		provPwTdmEncapMode OBJECT-TYPE
			SYNTAX INTEGER
				{
				invalid(0),
				tdmOverEther(1),
				tdmOverMpls(2)
				}
			ACCESS read-only
			STATUS mandatory
			DESCRIPTION
				" "
			DEFVAL { tdmOverEther }
			::= { provPwTdmEntry 6 }

		
		-- 1.3.6.1.4.1.119.2.3.69.203.502.501.5.42.5.1.7
		provPwTdmRowStatus OBJECT-TYPE
			SYNTAX RowStatus
			ACCESS read-only
			STATUS mandatory
			DESCRIPTION
				" "
			::= { provPwTdmEntry 7 }

		
		-- 1.3.6.1.4.1.119.2.3.69.203.502.501.5.42.5.1.8
		provPwTdmAdaptiveClkSource OBJECT-TYPE
			SYNTAX IpeEnableDisableValue
			ACCESS read-only
			STATUS mandatory
			DESCRIPTION
				" "
			DEFVAL { disabled }
			::= { provPwTdmEntry 8 }

		
		-- 1.3.6.1.4.1.119.2.3.69.203.502.501.5.42.11
		provPwOverEthTable OBJECT-TYPE
			SYNTAX SEQUENCE OF ProvPwOverEthEntry
			ACCESS not-accessible
			STATUS mandatory
			DESCRIPTION
				" "
			::= { provPwGroup 11 }

		
		-- 1.3.6.1.4.1.119.2.3.69.203.502.501.5.42.11.1
		provPwOverEthEntry OBJECT-TYPE
			SYNTAX ProvPwOverEthEntry
			ACCESS not-accessible
			STATUS mandatory
			DESCRIPTION
				" "
			INDEX { provPwOverEthNEAddress, provPwOverEthPwIndex }
			::= { provPwOverEthTable 1 }

		
		ProvPwOverEthEntry ::=
			SEQUENCE { 
				provPwOverEthPwIndex
					IpePwIndex,
				provPwOverEthNEAddress
					IpAddress,
				provPwOverEthVlanId
					IpeVlanIndex,
				provPwOverEthCosValue
					INTEGER,
				provPwOverEthEcid
					INTEGER,
				provPwOverEthName
					DisplayString,
				provPwOverEthDstMacAddress
					MacAddress
			 }

		-- 1.3.6.1.4.1.119.2.3.69.203.502.501.5.42.11.1.1
		provPwOverEthPwIndex OBJECT-TYPE
			SYNTAX IpePwIndex
			ACCESS read-only
			STATUS mandatory
			DESCRIPTION
				" "
			::= { provPwOverEthEntry 1 }

		
		-- 1.3.6.1.4.1.119.2.3.69.203.502.501.5.42.11.1.2
		provPwOverEthNEAddress OBJECT-TYPE
			SYNTAX IpAddress
			ACCESS read-only
			STATUS mandatory
			DESCRIPTION
				" "
			::= { provPwOverEthEntry 2 }

		
		-- 1.3.6.1.4.1.119.2.3.69.203.502.501.5.42.11.1.3
		provPwOverEthVlanId OBJECT-TYPE
			SYNTAX IpeVlanIndex
			ACCESS read-only
			STATUS mandatory
			DESCRIPTION
				" "
			::= { provPwOverEthEntry 3 }

		
		-- 1.3.6.1.4.1.119.2.3.69.203.502.501.5.42.11.1.5
		provPwOverEthCosValue OBJECT-TYPE
			SYNTAX INTEGER (0..7)
			ACCESS read-only
			STATUS mandatory
			DESCRIPTION
				" "
			DEFVAL { 5 }
			::= { provPwOverEthEntry 5 }

		
		-- 1.3.6.1.4.1.119.2.3.69.203.502.501.5.42.11.1.6
		provPwOverEthEcid OBJECT-TYPE
			SYNTAX INTEGER (1..1048575)
			ACCESS read-only
			STATUS mandatory
			DESCRIPTION
				" "
			::= { provPwOverEthEntry 6 }

		
		-- 1.3.6.1.4.1.119.2.3.69.203.502.501.5.42.11.1.7
		provPwOverEthName OBJECT-TYPE
			SYNTAX DisplayString (SIZE (0..32))
			ACCESS read-only
			STATUS mandatory
			DESCRIPTION
				" "
			DEFVAL { ''h }
			::= { provPwOverEthEntry 7 }

		
		-- 1.3.6.1.4.1.119.2.3.69.203.502.501.5.42.11.1.8
		provPwOverEthDstMacAddress OBJECT-TYPE
			SYNTAX MacAddress
			ACCESS read-only
			STATUS mandatory
			DESCRIPTION
				" "
			::= { provPwOverEthEntry 8 }

		
	
	END

--
-- MIB-PNMSJ-IPASOLINK-100-200-PW-MIB.my
--
